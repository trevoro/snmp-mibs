XEDIA-POLICY-MIB DEFINITIONS ::= BEGIN

IMPORTS 
    MODULE-IDENTITY, OBJECT-TYPE, IpAddress, Integer32
         FROM SNMPv2-SMI
    MODULE-COMPLIANCE, OBJECT-GROUP
         FROM SNMPv2-CONF
    TEXTUAL-CONVENTION, DisplayString, RowStatus, TruthValue
 	 FROM SNMPv2-TC
    xediaMibs
         FROM XEDIA-REG
    ;    

xediaPolicyMIB MODULE-IDENTITY
    LAST-UPDATED "9702182155Z" -- February 18, 1997
    ORGANIZATION "Xedia Corp."
    CONTACT-INFO
        "support@xedia.com"
    DESCRIPTION
        "This module defines objects for the management of 
        Routing Policies in Xedia devices."
    ::= { xediaMibs 10 }

-- Top-level organization of the MIB

xpolicyObjects          OBJECT IDENTIFIER ::= { xediaPolicyMIB 1 }
xpolicyTables           OBJECT IDENTIFIER ::= { xediaPolicyMIB 2 }
xpolicyConformance      OBJECT IDENTIFIER ::= { xediaPolicyMIB 3 }

--
-- The enumerated values for the 'Names' and AS strings
--
XPolicyName ::= TEXTUAL-CONVENTION
    STATUS      current
    DESCRIPTION
    "The unique name used to identify an entry in a policy table." 
    SYNTAX      DisplayString  (SIZE (1..32))

XPriPolicyName ::= TEXTUAL-CONVENTION
    STATUS      current
    DESCRIPTION
    "The unique name used to identify an entry in a priority policy table.
     The name must contain at least one priority value which is interpreted
     in the getnext.  This type of name MAY have a '[<priority value>]' prepended
     for SET/GET requests.  It WILL have a '[<priority value>]' prepended for all 
     of GETNext requests. This piece of the index in interpreted in a special way.
     The name portion is simply a label, while the first portion of the specified
     priority assignes the relative positon in the tree.  Then, the subsesquent
     priority numbers assign the entry under the top level entry. The format of
     the names is name.X.Y,... " 
    SYNTAX      DisplayString  (SIZE (1..32))

XPolicyAsString ::= TEXTUAL-CONVENTION
    STATUS      current
    DESCRIPTION
    "The AS string used to match paths."
    SYNTAX      DisplayString  (SIZE (0..32))

-- ****************************************************************
-- Xedia Policy General Objects  
-- ****************************************************************
xpolicyGeneral    OBJECT IDENTIFIER ::= { xpolicyObjects 1 }
xpolicyCounts     OBJECT IDENTIFIER ::= { xpolicyObjects 2 }
xpolicyRxCounts   OBJECT IDENTIFIER ::= { xpolicyCounts  1 }
xpolicyTxCounts   OBJECT IDENTIFIER ::= { xpolicyCounts  2 }

-- ****************************************************************
-- Xedia Policy Receive Counts   
-- ****************************************************************
xpolicyNumRxConfiguredTotal OBJECT-TYPE
    SYNTAX      Integer32
    MAX-ACCESS  read-only
    STATUS      current
    DESCRIPTION
    "The total number of configured 'receive' policies."
    ::= { xpolicyRxCounts 1 }

xpolicyNumRxConfiguredValid OBJECT-TYPE
    SYNTAX      Integer32
    MAX-ACCESS  read-only
    STATUS      current
    DESCRIPTION
    "Represents the number of configured 'receive' policies that have a
     RowStatus of 'active'.  This means that they are configured
     correctly without any conflicts among the elements in the row."
    ::= { xpolicyRxCounts 2 }

xpolicyNumRxConfiguredInValid OBJECT-TYPE
    SYNTAX      Integer32
    MAX-ACCESS  read-only
    STATUS      current
    DESCRIPTION
    "Represents the number of configured 'receive' policies that have a
     RowStatus of 'notReady'.  This means that they are configured,
     but have conflicts among the elements in the row."
    ::= { xpolicyRxCounts 3 }

xpolicyNumRxInUseTotal OBJECT-TYPE
    SYNTAX      Integer32
    MAX-ACCESS  read-only
    STATUS      current
    DESCRIPTION
    "Represents the number of 'receive' policies that are currently being 
     used by the run-time application.  Normally this number is 
     the same as the number of Configured Valid Policies."
    ::= { xpolicyRxCounts 4 }

xpolicyNumRxInUseBGP OBJECT-TYPE
    SYNTAX      Integer32
    MAX-ACCESS  read-only
    STATUS      current
    DESCRIPTION
    "Represents the number of BGP 'receive' policies that are currently being 
     used by the run-time application."
    ::= { xpolicyRxCounts 5 }

xpolicyNumRxInUseOSPF OBJECT-TYPE
    SYNTAX      Integer32
    MAX-ACCESS  read-only
    STATUS      current
    DESCRIPTION
    "Represents the number of OSPF 'receive' policies that are currently being 
     used by the run-time application."
    ::= { xpolicyRxCounts 6 }

xpolicyNumRxInUseRIP OBJECT-TYPE
    SYNTAX      Integer32
    MAX-ACCESS  read-only
    STATUS      current
    DESCRIPTION
    "Represents the number of RIP 'receive' policies that are currently being 
     used by the run-time application."
    ::= { xpolicyRxCounts 7 }

xpolicyNumRxInUseStatic OBJECT-TYPE
    SYNTAX      Integer32
    MAX-ACCESS  read-only
    STATUS      current
    DESCRIPTION
    "Represents the number of static 'receive' policies that are currently being 
     used by the run-time application."
    ::= { xpolicyRxCounts 8 }

-- ****************************************************************
-- Xedia Policy Send Counts   
-- ****************************************************************
xpolicyNumTxConfiguredTotal OBJECT-TYPE
    SYNTAX      Integer32
    MAX-ACCESS  read-only
    STATUS      current
    DESCRIPTION
    "The total number of configured 'send' policies."
    ::= { xpolicyTxCounts 1 }

xpolicyNumTxConfiguredValid OBJECT-TYPE
    SYNTAX      Integer32
    MAX-ACCESS  read-only
    STATUS      current
    DESCRIPTION
    "Represents the number of configured 'send' policies that have a
     RowStatus of 'active'.  This means that they are configured
     correctly without any conflicts among the elements in the row."
    ::= { xpolicyTxCounts 2 }

xpolicyNumTxConfiguredInValid OBJECT-TYPE
    SYNTAX      Integer32
    MAX-ACCESS  read-only
    STATUS      current
    DESCRIPTION
    "Represents the number of configured 'send' policies that have a
     RowStatus of 'notReady'.  This means that they are configured,
     but have conflicts among the elements in the row."
    ::= { xpolicyTxCounts 3 }

xpolicyNumTxInUseTotal OBJECT-TYPE
    SYNTAX      Integer32
    MAX-ACCESS  read-only
    STATUS      current
    DESCRIPTION
    "Represents the number of 'send' policies that are currently being 
     used by the run-time application.  Normally this number is 
     the same as the number of Configured Valid Policies."
    ::= { xpolicyTxCounts 4 }

xpolicyNumTxInUseBGP OBJECT-TYPE
    SYNTAX      Integer32
    MAX-ACCESS  read-only
    STATUS      current
    DESCRIPTION
    "Represents the number of BGP 'send' policies that are currently being 
     used by the run-time application."
    ::= { xpolicyTxCounts 5 }

xpolicyNumTxInUseOSPF OBJECT-TYPE
    SYNTAX      Integer32
    MAX-ACCESS  read-only
    STATUS      current
    DESCRIPTION
    "Represents the number of OSPF 'send' policies that are currently being 
     used by the run-time application."
    ::= { xpolicyTxCounts 6 }

xpolicyNumTxInUseRIP OBJECT-TYPE
    SYNTAX      Integer32
    MAX-ACCESS  read-only
    STATUS      current
    DESCRIPTION
    "Represents the number of RIP 'send' policies that are currently being 
     used by the run-time application."
    ::= { xpolicyTxCounts 7 }

-- ****************************************************************
-- Xedia Policy Routing Tables  
-- ****************************************************************
xpolicyRouting    OBJECT IDENTIFIER ::= { xpolicyTables 1 }

--
-- Policy Route Receive Table
--
xpolicyReceiveTable OBJECT-TYPE
    SYNTAX  SEQUENCE OF XpolicyReceiveEntry
    MAX-ACCESS  not-accessible
    STATUS  current  
    DESCRIPTION
    "This entity's Route Policy Receive table."
    ::= { xpolicyRouting 1 }

xpolicyReceiveEntry OBJECT-TYPE
    SYNTAX  XpolicyReceiveEntry
    MAX-ACCESS  not-accessible
    STATUS  current  
    DESCRIPTION
    "An entry to the Route Policy Receive Table."
    INDEX { xpolicyRxProtocol, xpolicyRxPeer, xpolicyRxName }
    ::= { xpolicyReceiveTable 1 }

XpolicyReceiveEntry ::=
    SEQUENCE {
    xpolicyRxProtocol       INTEGER,  
    xpolicyRxPeer           IpAddress,
    xpolicyRxName           XPolicyName,
    xpolicyRxAddrStart      IpAddress,
    xpolicyRxAddrEnd        IpAddress,
    xpolicyRxAsString       XPolicyAsString,
    xpolicyRxCommunityId    INTEGER,
    xpolicyRxReceiveOption  INTEGER,
    xpolicyRxLocalPref      Integer32,
    xpolicyRxRowStatus      RowStatus,
    xpolicyRxPrefixMin 	    INTEGER,
    xpolicyRxPrefixMax      INTEGER
    }

xpolicyRxProtocol OBJECT-TYPE
    SYNTAX      INTEGER { bgp(1), ospf(2), rip(3) }
    MAX-ACCESS  read-only
    STATUS      current
    DESCRIPTION
    "The protocol from which the update was received."
    ::= { xpolicyReceiveEntry 1 }

xpolicyRxPeer OBJECT-TYPE
    SYNTAX      IpAddress
    MAX-ACCESS  read-only
    STATUS      current
    DESCRIPTION
    "The destination IP address of the routing update.  If it is 
     zero, then all peers are accepted." 
    ::= { xpolicyReceiveEntry 2 }

 xpolicyRxName OBJECT-TYPE
    SYNTAX      XPolicyName 
    MAX-ACCESS  read-only
    STATUS      current
    DESCRIPTION
    "A unique name for this entry, including the optional priority number, 
     which can be represented in dotted notation.  When used, the priority
     numbers allow hiearchical matching.

     Format of the string is:  <name>.<priority>

     Examples of strings:      name, name.1, name.1.1, name.2"
    ::= { xpolicyReceiveEntry 3 }

xpolicyRxAddrStart OBJECT-TYPE
    SYNTAX      IpAddress
    MAX-ACCESS  read-create
    STATUS      current
    DESCRIPTION
    "The base of the IP Address range to match in routing
     update destinations."
    DEFVAL      { '00000000'h }
    ::= { xpolicyReceiveEntry 4 }

xpolicyRxAddrEnd OBJECT-TYPE
    SYNTAX      IpAddress
    MAX-ACCESS  read-create
    STATUS      current
    DESCRIPTION
    "The end of the IP Address range to match in routing
     update destinations."
    DEFVAL      { 'ffffffff'h }
    ::= { xpolicyReceiveEntry 5 }

 xpolicyRxAsString OBJECT-TYPE
    SYNTAX      XPolicyAsString
    MAX-ACCESS  read-create
    STATUS      current
    DESCRIPTION
    "A string describing a complete, or partial 'Autonomyous System'
     inwhich to perform matches.
     
     This string uses a limited form of regular expression syntax
     to define what values of an AS path to match.  The special
     characters used are '^' and '$' to specify 'start' and
     'end' respectively.

        100     -  a path with 100 in it
        ^100$   -  exactly the path of 100 (adjacent AS)
        ^100    -  any path starting with 100
        100$    -  any path ending with 100
        100.200 - a path with the sequence 100.200 in it.
  
    note: this is only valid for routes sourced from BGP."
    DEFVAL      { "" }
    ::= { xpolicyReceiveEntry 6 }

xpolicyRxCommunityId OBJECT-TYPE
    SYNTAX      INTEGER('00'h..'ffffffff'h)
    MAX-ACCESS  read-create
    STATUS      current
    DESCRIPTION
    "Allows matching on one of the integers listed in the community
     attrubute list.  This is only valid for routes sourced from BGP."
    DEFVAL      { '10000'h }
    ::= { xpolicyReceiveEntry 7 }

xpolicyRxReceiveOption OBJECT-TYPE
    SYNTAX      INTEGER {
		   ignore(1),
		   receive(2),
		   drop(3)
		   }
    MAX-ACCESS  read-create
    STATUS      current
    DESCRIPTION
    "Receive action/options taken on 'matching' entries."
    DEFVAL      { receive }
    ::= { xpolicyReceiveEntry 8 }

xpolicyRxLocalPref OBJECT-TYPE
    SYNTAX      Integer32
    MAX-ACCESS  read-create
    STATUS      current
    DESCRIPTION
    "A positive four byte integer defining the preference 
     to a matched routes.  Higher values assign greater
     preference.  Internal routes use 0xffffffff.
     
     note: It is only used for BGP."
    DEFVAL      { -1 }
    ::= { xpolicyReceiveEntry 9 }

xpolicyRxRowStatus OBJECT-TYPE
    SYNTAX      RowStatus
    MAX-ACCESS  read-create
    STATUS      current
    DESCRIPTION
        "This object is used to add and remove entries from the
        table."
    REFERENCE
        "RFC1903: Textual Conventions for Version 2 of the Simple
        Network Management Protocol (SNMPv2)."
    ::= { xpolicyReceiveEntry 10 }

xpolicyRxPrefixMin OBJECT-TYPE
    SYNTAX      INTEGER (0..32)
    MAX-ACCESS  read-create
    STATUS      current
    DESCRIPTION
    "Minimum length of IP Address prefix to match in
     routing update destinations."
    DEFVAL      { 0 }
    ::= { xpolicyReceiveEntry 11 }

xpolicyRxPrefixMax OBJECT-TYPE
    SYNTAX      INTEGER (0..32)
    MAX-ACCESS  read-create
    STATUS      current
    DESCRIPTION
    "Maximum length of IP Address prefix to match in
     routing update destinations."
    DEFVAL      { 32 }
    ::= { xpolicyReceiveEntry 12 }

--
-- Policy Route Send Table
--
xpolicySendTable OBJECT-TYPE
    SYNTAX  SEQUENCE OF XpolicySendEntry
    MAX-ACCESS  not-accessible
    STATUS  current  
    DESCRIPTION
    "This entity's Route Policy Send table."
    ::= { xpolicyRouting 2 }

xpolicySendEntry OBJECT-TYPE
    SYNTAX  XpolicySendEntry
    MAX-ACCESS  not-accessible
    STATUS  current  
    DESCRIPTION
    "An entry to the Route Policy Table."
    INDEX { xpolicyTxProtocol, xpolicyTxPeer, xpolicyTxName }
    ::= { xpolicySendTable 1 }

XpolicySendEntry ::=
    SEQUENCE {
    xpolicyTxProtocol        INTEGER,
    xpolicyTxPeer            IpAddress,
    xpolicyTxName            XPolicyName,
    xpolicyTxSrcProtocol     INTEGER,
    xpolicyTxSrcProtSubType  INTEGER,
    xpolicyTxAddrStart       IpAddress,
    xpolicyTxAddrEnd         IpAddress,
    xpolicyTxAsString        XPolicyAsString,
    xpolicyTxCommunityId     INTEGER,
    xpolicyTxSendOption      INTEGER,
    xpolicyTxMED             Integer32,
    xpolicyTxMEDAuto         INTEGER,  
    xpolicyTxAsPrepend       Integer32,
    xpolicyTxSendCommunityId INTEGER,
    xpolicyTxIgpMetric       Integer32,
    xpolicyTxIgpMetricType   INTEGER,
    xpolicyTxIgpMetricAuto   INTEGER, 
    xpolicyTxNextHopSelf     TruthValue,  
    xpolicyTxRowStatus       RowStatus,
    xpolicyTxPrefixMin	     INTEGER,
    xpolicyTxPrefixMax	     INTEGER
    }

xpolicyTxProtocol OBJECT-TYPE
    SYNTAX      INTEGER { bgp(1), ospf(2), rip(3) }
    MAX-ACCESS  read-only
    STATUS      current
    DESCRIPTION
    "The protocol identifying where the update will be sent."
    ::= { xpolicySendEntry 1 }

xpolicyTxPeer OBJECT-TYPE
    SYNTAX      IpAddress
    MAX-ACCESS  read-only
    STATUS      current
    DESCRIPTION
    "The destination IP address of the routing update. If zero,
     then all peers receive them.  For OSPF and RIP, this value
     should be zero.  BGP should not use 0." 
    ::= { xpolicySendEntry 2 }

 xpolicyTxName OBJECT-TYPE
    SYNTAX      XPolicyName 
    MAX-ACCESS  read-only
    STATUS      current
    DESCRIPTION
    "A unique name for this entry, including the optional priority number, 
     which can be represented in dotted notation.  When used, the priority
     numbers allow hiearchical matching.

     Format of the string is:  <name>.<priority>

     Examples of strings:      name, name.1, name.1.1, name.2"
    ::= { xpolicySendEntry 3 }

xpolicyTxSrcProtocol OBJECT-TYPE
    SYNTAX      INTEGER { bgp(1), ospf(2), rip(3), local(4), static(5) }
    MAX-ACCESS  read-create
    STATUS      current
    DESCRIPTION
    "The protocol identifying the origin of the update.  Often this 
     'src protocol will be the same as the TX Protocol index.  This allows 
     routes learned by BGP to be filtered towards other BGP routes."
    DEFVAL      { bgp }
    ::= { xpolicySendEntry 4 }

xpolicyTxSrcProtSubType OBJECT-TYPE
    SYNTAX      INTEGER { any(1), internal(2), external(3) }
    MAX-ACCESS  read-create
    STATUS      current
    DESCRIPTION
    "The protocol sub-type discription.  Currently, this only applies to
     OSPF entries."
    DEFVAL      { any }
    ::= { xpolicySendEntry 5 }

xpolicyTxAddrStart OBJECT-TYPE
    SYNTAX      IpAddress
    MAX-ACCESS  read-create
    STATUS      current
    DESCRIPTION
    "The base of the IP Address range to match in routing
     update destinations."
    DEFVAL      { '00000000'h }
    ::= { xpolicySendEntry 6 }

xpolicyTxAddrEnd OBJECT-TYPE
    SYNTAX      IpAddress
    MAX-ACCESS  read-create
    STATUS      current
    DESCRIPTION
    "The end of the IP Address range to match in routing
     update destinations."
    DEFVAL      { 'ffffffff'h }
    ::= { xpolicySendEntry 7 }

 xpolicyTxAsString OBJECT-TYPE
    SYNTAX      XPolicyAsString 
    MAX-ACCESS  read-create
    STATUS      current
    DESCRIPTION
    "A string describing a complete, or partial 'Autonomyous System'
     inwhich to perform matches.
     
     This string uses a limited form of regular expression syntax
     to define what values of an AS path to match.  The special
     characters used are '^' and '$' to specify 'start' and
     'end' respectively.

        100     -  a path with 100 in it
        ^100$   -  exactly the path of 100 (adjacent AS)
        ^100    -  any path starting with 100
        100$    -  any path ending with 100
        100.200 - a path with the sequence 100.200 in it.
  
    note: this is only valid for routes sourced from BGP."
    DEFVAL      { "" }
    ::= { xpolicySendEntry 8 }

xpolicyTxCommunityId OBJECT-TYPE
    SYNTAX      INTEGER('00'h..'ffffffff'h)
    MAX-ACCESS  read-create
    STATUS      current
    DESCRIPTION
    "Allows matching on one of the integers listed in the community
     attrubute list.  This is only valid for routes sourced from BGP."
    DEFVAL      { '10000'h }
    ::= { xpolicySendEntry 9 }

xpolicyTxSendOption OBJECT-TYPE
    SYNTAX      INTEGER {
		   ignore(1),
		   never(2),
		   normal(3),
		   aggregate(4)
		   }
    MAX-ACCESS  read-create
    STATUS      current
    DESCRIPTION
    "Send action/options taken on 'matching' entries.  Never, indicates that
     routes within the range are not sent to the peer.  Normal, allows routes
     within the specified range to be sent to the peer.  Aggregate adds the 
     specified range to routes that are currently within the specified range.
     In the aggregate case, the range must be a power of two."
    DEFVAL      { normal }
    ::= { xpolicySendEntry 10 }

xpolicyTxMED OBJECT-TYPE
    SYNTAX      Integer32
    MAX-ACCESS  read-create
    STATUS      current
    DESCRIPTION
    "The 'Multi-Exit-Descriminator'.  A lower value assigns a higher
     preference to the route.  Normally, the MED attribute ia attached to all
     matched routes.  Except in the case of 0xffffffff, which means the MED
     will not be sent.
     
     note: It is only used for BGP.  If it is used (>0), then the 
           'xpolicyTxSendOption' can NOT be set to 'never'."
    DEFVAL      { 'ffffffff'h  }
    ::= { xpolicySendEntry 11 }

xpolicyTxMEDAuto OBJECT-TYPE
    SYNTAX      INTEGER  { on(1), off(2) }
    MAX-ACCESS  read-create
    STATUS      current
    DESCRIPTION
    "Admininstative status for calculating the 'Multi-Exit-Descriminator'
     using IGP_metric + 1."
    DEFVAL      { on }
    ::= { xpolicySendEntry 12 }

xpolicyTxAsPrepend  OBJECT-TYPE
    SYNTAX      Integer32
    MAX-ACCESS  read-create
    STATUS      current
    DESCRIPTION
    "The number of times to prepend the router's AS to the transmitted
     AS path in updates to the peer for all matching routes.  
     
     note: It is only used for BGP.  If it is used (>0), then the 
           'xpolicyTxSendOption' can NOT be set to 'never'."
    DEFVAL      { 0 }
    ::= { xpolicySendEntry 13 }

xpolicyTxSendCommunityId OBJECT-TYPE
    SYNTAX      INTEGER('00'h..'ffffffff'h)
    MAX-ACCESS  read-create
    STATUS      current
    DESCRIPTION
    "The value that is added to the community attribute for all matched
     routes.  
     
     note: It is only used for BGP.  If it is used (>0), then the 
           'xpolicyTxSendOption' can NOT be set to 'never'."
    DEFVAL      { '10000'h }
    ::= { xpolicySendEntry 14 }

xpolicyTxIgpMetric OBJECT-TYPE
    SYNTAX      Integer32
    MAX-ACCESS  read-create
    STATUS      current
    DESCRIPTION
    "The metric used for IGP."
    DEFVAL      { 0 }
    ::= { xpolicySendEntry 15 }

xpolicyTxIgpMetricType OBJECT-TYPE
    SYNTAX      INTEGER { ospfExtType1(1), ospfExtType2(2) }
    MAX-ACCESS  read-create
    STATUS      current
    DESCRIPTION
    "Type of metric being used.  Currently, only for defining OSPF internal
     and external routes."
    DEFVAL      { ospfExtType1 }
    ::= { xpolicySendEntry 16 }

xpolicyTxIgpMetricAuto OBJECT-TYPE
    SYNTAX      INTEGER { off(1), localPref(2), med(3), igp(4) }
    MAX-ACCESS  read-create
    STATUS      current
    DESCRIPTION
    "Administrative status for generating an 'auto' metric.  If set to
    localPref, the igp's metric is igpMetric - localPref.  If set to 
    MED, the the igp's metric is igpMetric + MED.  If set to igp, then
    the entry controls routes imported from one IGP to another."
    DEFVAL      { off }
    ::= { xpolicySendEntry 17 }

xpolicyTxNextHopSelf OBJECT-TYPE
    SYNTAX      TruthValue
    MAX-ACCESS  read-create
    STATUS      current
    DESCRIPTION
    "Setting this object to the value 'true(1)' will set the BGP NEXT_HOP
     attribute to the local router address instead of leaving it as
     it was received from an EBGP peer."
    DEFVAL      { false }
    ::= { xpolicySendEntry 18 }

xpolicyTxRowStatus OBJECT-TYPE
    SYNTAX      RowStatus
    MAX-ACCESS  read-create
    STATUS      current
    DESCRIPTION
        "This object is used to add and remove entries from the
        table."
    REFERENCE
        "RFC1903: Textual Conventions for Version 2 of the Simple
        Network Management Protocol (SNMPv2)."
    ::= { xpolicySendEntry 19 }

xpolicyTxPrefixMin OBJECT-TYPE
    SYNTAX      INTEGER (0..32)
    MAX-ACCESS  read-create
    STATUS      current
    DESCRIPTION
    "Minimum length of IP Address prefix to match in
     routing update destinations."
    DEFVAL      { 0 }
    ::= { xpolicySendEntry 20 }

xpolicyTxPrefixMax OBJECT-TYPE
    SYNTAX      INTEGER (0..32)
    MAX-ACCESS  read-create
    STATUS      current
    DESCRIPTION
    "Maximum length of IP Address prefix to match in
     routing update destinations."
    DEFVAL      { 32 }
    ::= { xpolicySendEntry 21 }

-- ****************************************
-- The Internal Policy Display Table
-- ****************************************
xpolicyDisplayTable OBJECT-TYPE
    SYNTAX      SEQUENCE OF XpolicyDisplayEntry
    MAX-ACCESS  not-accessible
    STATUS      current
    DESCRIPTION
        "This table contains a read-only display of the internally
	 linked list of policy entries."
    ::= { xpolicyTables 2 }

xpolicyDisplayEntry OBJECT-TYPE
    SYNTAX      XpolicyDisplayEntry
    MAX-ACCESS  not-accessible
    STATUS      current
    DESCRIPTION
        "Individual piece of text information regarding a policy entry."
    INDEX       { xpolicyDisplayIndex }
    ::= { xpolicyDisplayTable 1 }
    
XpolicyDisplayEntry ::= SEQUENCE {
    xpolicyDisplayIndex      Integer32,
    xpolicyRxDisplayString   DisplayString,
    xpolicyTxDisplayString   DisplayString
}

xpolicyDisplayIndex OBJECT-TYPE
    SYNTAX      Integer32
    MAX-ACCESS  not-accessible
    STATUS      current
    DESCRIPTION
        "The row number in the table."
    ::= { xpolicyDisplayEntry 1 }

xpolicyRxDisplayString OBJECT-TYPE
    SYNTAX      DisplayString
    MAX-ACCESS  read-only
    STATUS      current
    DESCRIPTION
        "A single text line of information about a particular 
	 Receive policy."
    ::= { xpolicyDisplayEntry 2 }
    
xpolicyTxDisplayString OBJECT-TYPE
    SYNTAX      DisplayString
    MAX-ACCESS  read-only
    STATUS      current
    DESCRIPTION
        "A single text line of information about a particular 
	 Send policy."
    ::= { xpolicyDisplayEntry 3 }

-- ********************
-- The Peer Group Table
-- ********************
xpolicyPeerGroupTable OBJECT-TYPE
    SYNTAX      SEQUENCE OF XpolicyPeerGroupEntry
    MAX-ACCESS  not-accessible
    STATUS      current
    DESCRIPTION
        "This table contains configuration for policy peer group members."
    ::= { xpolicyTables 3 }

xpolicyPeerGroupEntry OBJECT-TYPE
    SYNTAX      XpolicyPeerGroupEntry
    MAX-ACCESS  not-accessible
    STATUS      current
    DESCRIPTION
        "Individual peer group configuration."
    INDEX       { xpolicyPeerGroupIndex, xpolicyPeerGroupPeer }
    ::= { xpolicyPeerGroupTable 1 }
    
XpolicyPeerGroupEntry ::= SEQUENCE {
    xpolicyPeerGroupIndex     INTEGER,
    xpolicyPeerGroupPeer      IpAddress,
    xpolicyPeerGroupRowStatus RowStatus
}

xpolicyPeerGroupIndex OBJECT-TYPE
    SYNTAX      INTEGER (1..16)
    MAX-ACCESS  read-only
    STATUS      current
    DESCRIPTION
        "The index used to identify this peer group."
    ::= { xpolicyPeerGroupEntry 1 }

xpolicyPeerGroupPeer OBJECT-TYPE
    SYNTAX      IpAddress
    MAX-ACCESS  read-only
    STATUS      current
    DESCRIPTION
    "The peer contained in this group."
    ::= { xpolicyPeerGroupEntry 2 }

xpolicyPeerGroupRowStatus OBJECT-TYPE
    SYNTAX      RowStatus
    MAX-ACCESS  read-create
    STATUS      current
    DESCRIPTION
        "This object is used to add and remove entries from the
        table."
    REFERENCE
        "RFC1903: Textual Conventions for Version 2 of the Simple
        Network Management Protocol (SNMPv2)."
    ::= { xpolicyPeerGroupEntry 3 }


-- ****************************************************************
-- Xedia Priority Policy Routing Tables  
-- ****************************************************************
xpolicyPriRouting    OBJECT IDENTIFIER ::= { xpolicyTables 4 }

--
-- Policy Route Receive Table
--
xpolicyPriReceiveTable OBJECT-TYPE
    SYNTAX  SEQUENCE OF XpolicyPriReceiveEntry
    MAX-ACCESS  not-accessible
    STATUS  current  
    DESCRIPTION
    "This entity's Route Policy Receive table."
    ::= { xpolicyPriRouting 1 }

xpolicyPriReceiveEntry OBJECT-TYPE
    SYNTAX  XpolicyPriReceiveEntry
    MAX-ACCESS  not-accessible
    STATUS  current  
    DESCRIPTION
    "An entry to the Route Policy Receive Table."
    INDEX { xpolicyRxProtocol, xpolicyRxName }
    ::= { xpolicyPriReceiveTable 1 }

XpolicyPriReceiveEntry ::=
    SEQUENCE {
    xpolicyPriRxProtocol       INTEGER,
    xpolicyPriRxPeer           IpAddress,
    xpolicyPriRxName           XPriPolicyName,
    xpolicyPriRxAddrStart      IpAddress,
    xpolicyPriRxAddrEnd        IpAddress,
    xpolicyPriRxAsString       XPolicyAsString,
    xpolicyPriRxCommunityId    INTEGER,
    xpolicyPriRxReceiveOption  INTEGER,
    xpolicyPriRxLocalPref      Integer32,
    xpolicyPriRxRowStatus      RowStatus,
    xpolicyPriRxPrefixMin      INTEGER,
    xpolicyPriRxPrefixMax      INTEGER,
    xpolicyPriRxDistance       INTEGER
    }

xpolicyPriRxProtocol OBJECT-TYPE
    SYNTAX      INTEGER { bgp(1), ospf(2), rip(3), static(5) }
    MAX-ACCESS  read-only
    STATUS      current
    DESCRIPTION
    "The protocol from which the update was received."
    ::= { xpolicyPriReceiveEntry 1 }

xpolicyPriRxPeer OBJECT-TYPE
    SYNTAX      IpAddress
    MAX-ACCESS  read-create
    STATUS      current
    DESCRIPTION
    "The destination IP address of the routing update.  If it is 
     zero, then all peers are accepted." 
    ::= { xpolicyPriReceiveEntry 2 }

 xpolicyPriRxName OBJECT-TYPE
    SYNTAX      XPriPolicyName 
    MAX-ACCESS  read-only
    STATUS      current
    DESCRIPTION
    "A unique name for this entry, including the optional priority number, 
     which can be represented in dotted notation.  When used, the priority
     numbers allow hiearchical matching.

     Format of the string is:  <name>.<priority>

     Examples of strings:      name, name.1, name.1.1, name.2"
    ::= { xpolicyPriReceiveEntry 3 }

xpolicyPriRxAddrStart OBJECT-TYPE
    SYNTAX      IpAddress
    MAX-ACCESS  read-create
    STATUS      current
    DESCRIPTION
    "The base of the IP Address range to match in routing
     update destinations."
    DEFVAL      { '00000000'h }
    ::= { xpolicyPriReceiveEntry 4 }

xpolicyPriRxAddrEnd OBJECT-TYPE
    SYNTAX      IpAddress
    MAX-ACCESS  read-create
    STATUS      current
    DESCRIPTION
    "The end of the IP Address range to match in routing
     update destinations."
    DEFVAL      { 'ffffffff'h }
    ::= { xpolicyPriReceiveEntry 5 }

 xpolicyPriRxAsString OBJECT-TYPE
    SYNTAX      XPolicyAsString
    MAX-ACCESS  read-create
    STATUS      current
    DESCRIPTION
    "A string describing a complete, or partial 'Autonomyous System'
     inwhich to perform matches.
     
     This string uses a limited form of regular expression syntax
     to define what values of an AS path to match.  The special
     characters used are '^' and '$' to specify 'start' and
     'end' respectively.

        100     -  a path with 100 in it
        ^100$   -  exactly the path of 100 (adjacent AS)
        ^100    -  any path starting with 100
        100$    -  any path ending with 100
        100.200 - a path with the sequence 100.200 in it.
  
    note: this is only valid for routes sourced from BGP."
    DEFVAL      { "" }
    ::= { xpolicyPriReceiveEntry 6 }

xpolicyPriRxCommunityId OBJECT-TYPE
    SYNTAX      INTEGER('00'h..'ffffffff'h)
    MAX-ACCESS  read-create
    STATUS      current
    DESCRIPTION
    "Allows matching on one of the integers listed in the community
     attrubute list.  This is only valid for routes sourced from BGP."
    DEFVAL      { '10000'h }
    ::= { xpolicyPriReceiveEntry 7 }

xpolicyPriRxReceiveOption OBJECT-TYPE
    SYNTAX      INTEGER {
		   ignore(1),
		   receive(2),
		   drop(3)
		   }
    MAX-ACCESS  read-create
    STATUS      current
    DESCRIPTION
    "Receive action/options taken on 'matching' entries."
    DEFVAL      { receive }
    ::= { xpolicyPriReceiveEntry 8 }

xpolicyPriRxLocalPref OBJECT-TYPE
    SYNTAX      Integer32
    MAX-ACCESS  read-create
    STATUS      current
    DESCRIPTION
    "A positive four byte integer defining the preference 
     to a matched routes.  Higher values assign greater
     preference.  Internal routes use 0xffffffff.
     
     note: It is only used for BGP."
    DEFVAL      { -1 }
    ::= { xpolicyPriReceiveEntry 9 }

xpolicyPriRxRowStatus OBJECT-TYPE
    SYNTAX      RowStatus
    MAX-ACCESS  read-create
    STATUS      current
    DESCRIPTION
        "This object is used to add and remove entries from the
        table."
    REFERENCE
        "RFC1903: Textual Conventions for Version 2 of the Simple
        Network Management Protocol (SNMPv2)."
    ::= { xpolicyPriReceiveEntry 10 }

xpolicyPriRxPrefixMin OBJECT-TYPE
    SYNTAX      INTEGER (0..32)
    MAX-ACCESS  read-create
    STATUS      current
    DESCRIPTION
    "Minimum length of IP Address prefix to match in
     routing update destinations."
    DEFVAL      { 0 }
    ::= { xpolicyPriReceiveEntry 11 }

xpolicyPriRxPrefixMax OBJECT-TYPE
    SYNTAX      INTEGER (0..32)
    MAX-ACCESS  read-create
    STATUS      current
    DESCRIPTION
    "Maximum length of IP Address prefix to match in
     routing update destinations."
    DEFVAL      { 32 }
    ::= { xpolicyPriReceiveEntry 12 }

xpolicyPriRxDistance OBJECT-TYPE
    SYNTAX      INTEGER (-1..255)
    MAX-ACCESS  read-create
    STATUS      current
    DESCRIPTION
    "Administrative distance value to be set to
     a matched route."
    DEFVAL      { -1 }
    ::= { xpolicyPriReceiveEntry 13 }

--
-- Policy Route Send Table
--
xpolicyPriSendTable OBJECT-TYPE
    SYNTAX  SEQUENCE OF XpolicyPriSendEntry
    MAX-ACCESS  not-accessible
    STATUS  current  
    DESCRIPTION
    "This entity's Route Policy Send table."
    ::= { xpolicyPriRouting 2 }

xpolicyPriSendEntry OBJECT-TYPE
    SYNTAX  XpolicyPriSendEntry
    MAX-ACCESS  not-accessible
    STATUS  current  
    DESCRIPTION
    "An entry to the Route Policy Table."
    INDEX { xpolicyTxProtocol, xpolicyTxName }
    ::= { xpolicyPriSendTable 1 }

XpolicyPriSendEntry ::=
    SEQUENCE {
    xpolicyPriTxProtocol        INTEGER,
    xpolicyPriTxPeer            IpAddress,
    xpolicyPriTxName            XPriPolicyName,
    xpolicyPriTxSrcProtocol     INTEGER,
    xpolicyPriTxSrcProtSubType  INTEGER,
    xpolicyPriTxAddrStart       IpAddress,
    xpolicyPriTxAddrEnd         IpAddress,
    xpolicyPriTxAsString        XPolicyAsString,
    xpolicyPriTxCommunityId     INTEGER,
    xpolicyPriTxSendOption      INTEGER,
    xpolicyPriTxMED             Integer32,
    xpolicyPriTxMEDAuto         INTEGER,  
    xpolicyPriTxAsPrepend       Integer32,
    xpolicyPriTxSendCommunityId INTEGER,
    xpolicyPriTxIgpMetric       Integer32,
    xpolicyPriTxIgpMetricType   INTEGER,
    xpolicyPriTxIgpMetricAuto   INTEGER, 
    xpolicyPriTxNextHopSelf     TruthValue,  
    xpolicyPriTxRowStatus       RowStatus,
    xpolicyPriTxPrefixMin	INTEGER,
    xpolicyPriTxPrefixMax	INTEGER
    }

xpolicyPriTxProtocol OBJECT-TYPE
    SYNTAX      INTEGER { bgp(1), ospf(2), rip(3) }
    MAX-ACCESS  read-only
    STATUS      current
    DESCRIPTION
    "The protocol identifying where the update will be sent."
    ::= { xpolicyPriSendEntry 1 }

xpolicyPriTxPeer OBJECT-TYPE
    SYNTAX      IpAddress
    MAX-ACCESS  read-create
    STATUS      current
    DESCRIPTION
    "The destination IP address of the routing update. If zero,
     then all peers receive them.  For OSPF and RIP, this value
     should be zero.  BGP should not use 0." 
    ::= { xpolicyPriSendEntry 2 }

 xpolicyPriTxName OBJECT-TYPE
    SYNTAX      XPriPolicyName 
    MAX-ACCESS  read-only
    STATUS      current
    DESCRIPTION
    "A unique name for this entry, including the optional priority number, 
     which can be represented in dotted notation.  When used, the priority
     numbers allow hiearchical matching.

     Format of the string is:  <name>.<priority>

     Examples of strings:      name, name.1, name.1.1, name.2"
    ::= { xpolicyPriSendEntry 3 }

xpolicyPriTxSrcProtocol OBJECT-TYPE
    SYNTAX      INTEGER { bgp(1), ospf(2), rip(3), local(4), static(5) }
    MAX-ACCESS  read-create
    STATUS      current
    DESCRIPTION
    "The protocol identifying the origin of the update.  Often this 
     'src protocol will be the same as the TX Protocol index.  This allows 
     routes learned by BGP to be filtered towards other BGP routes."
    DEFVAL      { bgp }
    ::= { xpolicyPriSendEntry 4 }

xpolicyPriTxSrcProtSubType OBJECT-TYPE
    SYNTAX      INTEGER { any(1), internal(2), external(3) }
    MAX-ACCESS  read-create
    STATUS      current
    DESCRIPTION
    "The protocol sub-type discription.  Currently, this only applies to
     OSPF entries."
    DEFVAL      { any }
    ::= { xpolicyPriSendEntry 5 }

xpolicyPriTxAddrStart OBJECT-TYPE
    SYNTAX      IpAddress
    MAX-ACCESS  read-create
    STATUS      current
    DESCRIPTION
    "The base of the IP Address range to match in routing
     update destinations."
    DEFVAL      { '00000000'h }
    ::= { xpolicyPriSendEntry 6 }

xpolicyPriTxAddrEnd OBJECT-TYPE
    SYNTAX      IpAddress
    MAX-ACCESS  read-create
    STATUS      current
    DESCRIPTION
    "The end of the IP Address range to match in routing
     update destinations."
    DEFVAL      { 'ffffffff'h }
    ::= { xpolicyPriSendEntry 7 }

 xpolicyPriTxAsString OBJECT-TYPE
    SYNTAX      XPolicyAsString 
    MAX-ACCESS  read-create
    STATUS      current
    DESCRIPTION
    "A string describing a complete, or partial 'Autonomyous System'
     inwhich to perform matches.
     
     This string uses a limited form of regular expression syntax
     to define what values of an AS path to match.  The special
     characters used are '^' and '$' to specify 'start' and
     'end' respectively.

        100     -  a path with 100 in it
        ^100$   -  exactly the path of 100 (adjacent AS)
        ^100    -  any path starting with 100
        100$    -  any path ending with 100
        100.200 - a path with the sequence 100.200 in it.
  
    note: this is only valid for routes sourced from BGP."
    DEFVAL      { "" }
    ::= { xpolicyPriSendEntry 8 }

xpolicyPriTxCommunityId OBJECT-TYPE
    SYNTAX      INTEGER('00'h..'ffffffff'h)
    MAX-ACCESS  read-create
    STATUS      current
    DESCRIPTION
    "Allows matching on one of the integers listed in the community
     attrubute list.  This is only valid for routes sourced from BGP."
    DEFVAL      { '10000'h }
    ::= { xpolicyPriSendEntry 9 }

xpolicyPriTxSendOption OBJECT-TYPE
    SYNTAX      INTEGER {
		   ignore(1),
		   never(2),
		   normal(3),
		   aggregate(4)
		   }
    MAX-ACCESS  read-create
    STATUS      current
    DESCRIPTION
    "Send action/options taken on 'matching' entries.  Never, indicates that
     routes within the range are not sent to the peer.  Normal, allows routes
     within the specified range to be sent to the peer.  Aggregate adds the 
     specified range to routes that are currently within the specified range.
     In the aggregate case, the range must be a power of two."
    DEFVAL      { normal }
    ::= { xpolicyPriSendEntry 10 }

xpolicyPriTxMED OBJECT-TYPE
    SYNTAX      Integer32
    MAX-ACCESS  read-create
    STATUS      current
    DESCRIPTION
    "The 'Multi-Exit-Descriminator'.  A lower value assigns a higher
     preference to the route.  Normally, the MED attribute ia attached to all
     matched routes.  Except in the case of 0xffffffff, which means the MED
     will not be sent.
     
     note: It is only used for BGP.  If it is used (>0), then the 
           'xpolicyTxSendOption' can NOT be set to 'never'."
    DEFVAL      { 'ffffffff'h  }
    ::= { xpolicyPriSendEntry 11 }

xpolicyPriTxMEDAuto OBJECT-TYPE
    SYNTAX      INTEGER  { on(1), off(2) }
    MAX-ACCESS  read-create
    STATUS      current
    DESCRIPTION
    "Admininstative status for calculating the 'Multi-Exit-Descriminator'
     using IGP_metric + 1."
    DEFVAL      { on }
    ::= { xpolicyPriSendEntry 12 }

xpolicyPriTxAsPrepend  OBJECT-TYPE
    SYNTAX      Integer32
    MAX-ACCESS  read-create
    STATUS      current
    DESCRIPTION
    "The number of times to prepend the router's AS to the transmitted
     AS path in updates to the peer for all matching routes.  
     
     note: It is only used for BGP.  If it is used (>0), then the 
           'xpolicyTxSendOption' can NOT be set to 'never'."
    DEFVAL      { 0 }
    ::= { xpolicyPriSendEntry 13 }

xpolicyPriTxSendCommunityId OBJECT-TYPE
    SYNTAX      INTEGER('00'h..'ffffffff'h)
    MAX-ACCESS  read-create
    STATUS      current
    DESCRIPTION
    "The value that is added to the community attribute for all matched
     routes.  
     
     note: It is only used for BGP.  If it is used (>0), then the 
           'xpolicyTxSendOption' can NOT be set to 'never'."
    DEFVAL      { '10000'h }
    ::= { xpolicyPriSendEntry 14 }

xpolicyPriTxIgpMetric OBJECT-TYPE
    SYNTAX      Integer32
    MAX-ACCESS  read-create
    STATUS      current
    DESCRIPTION
    "The metric used for IGP."
    DEFVAL      { 0 }
    ::= { xpolicyPriSendEntry 15 }

xpolicyPriTxIgpMetricType OBJECT-TYPE
    SYNTAX      INTEGER { ospfExtType1(1), ospfExtType2(2) }
    MAX-ACCESS  read-create
    STATUS      current
    DESCRIPTION
    "Type of metric being used.  Currently, only for defining OSPF internal
     and external routes."
    DEFVAL      { ospfExtType1 }
    ::= { xpolicyPriSendEntry 16 }

xpolicyPriTxIgpMetricAuto OBJECT-TYPE
    SYNTAX      INTEGER { off(1), localPref(2), med(3), igp(4) }
    MAX-ACCESS  read-create
    STATUS      current
    DESCRIPTION
    "Administrative status for generating an 'auto' metric.  If set to
    localPref, the igp's metric is igpMetric - localPref.  If set to 
    MED, the the igp's metric is igpMetric + MED.  If set to igp, then
    the entry controls routes imported from one IGP to another."
    DEFVAL      { off }
    ::= { xpolicyPriSendEntry 17 }

xpolicyPriTxNextHopSelf OBJECT-TYPE
    SYNTAX      TruthValue
    MAX-ACCESS  read-create
    STATUS      current
    DESCRIPTION
    "Setting this object to the value 'true(1)' will set the BGP NEXT_HOP
     attribute to the local router address instead of leaving it as
     it was received from an EBGP peer."
    DEFVAL      { false }
    ::= { xpolicyPriSendEntry 18 }

xpolicyPriTxRowStatus OBJECT-TYPE
    SYNTAX      RowStatus
    MAX-ACCESS  read-create
    STATUS      current
    DESCRIPTION
        "This object is used to add and remove entries from the
        table."
    REFERENCE
        "RFC1903: Textual Conventions for Version 2 of the Simple
        Network Management Protocol (SNMPv2)."
    ::= { xpolicyPriSendEntry 19 }

xpolicyPriTxPrefixMin OBJECT-TYPE
    SYNTAX      INTEGER (0..32)
    MAX-ACCESS  read-create
    STATUS      current
    DESCRIPTION
    "Minimum length of IP Address prefix to match in
     routing update destinations."
    DEFVAL      { 0 }
    ::= { xpolicyPriSendEntry 20 }

xpolicyPriTxPrefixMax OBJECT-TYPE
    SYNTAX      INTEGER (0..32)
    MAX-ACCESS  read-create
    STATUS      current
    DESCRIPTION
    "Maximum length of IP Address prefix to match in
     routing update destinations."
    DEFVAL      { 32 }
    ::= { xpolicyPriSendEntry 21 }


-- ****************************************************************
-- Conformance Information
-- ****************************************************************

xpolicyCompliances OBJECT IDENTIFIER ::= { xpolicyConformance 1 }
xpolicyGroups      OBJECT IDENTIFIER ::= { xpolicyConformance 2 }

--
-- Compliance Statements
--

xpolicyCompliance MODULE-COMPLIANCE
    STATUS      current
    DESCRIPTION
        "The compliance statement for all agents that support this
        MIB. A compliant agent implements all objects defined in this
        MIB."
    MODULE  -- this module
    MANDATORY-GROUPS {
        xpolicyAllGroup
    }
    ::= { xpolicyCompliances 1 }

--
-- All Object Groups
--
xpolicyAllGroup OBJECT-GROUP
    OBJECTS {
    xpolicyNumRxConfiguredTotal, 
    xpolicyNumRxConfiguredValid, 
    xpolicyNumRxConfiguredInValid, 
    xpolicyNumRxInUseTotal, 
    xpolicyNumRxInUseBGP, 
    xpolicyNumRxInUseOSPF, 
    xpolicyNumRxInUseRIP, 
    xpolicyNumRxInUseStatic, 

    xpolicyNumTxConfiguredTotal, 
    xpolicyNumTxConfiguredValid, 
    xpolicyNumTxConfiguredInValid, 
    xpolicyNumTxInUseTotal, 
    xpolicyNumTxInUseBGP, 
    xpolicyNumTxInUseOSPF, 
    xpolicyNumTxInUseRIP, 
	
    xpolicyRxProtocol,  
    xpolicyRxPeer,
    xpolicyRxName,
    xpolicyRxAddrStart,
    xpolicyRxAddrEnd,
    xpolicyRxAsString,
    xpolicyRxCommunityId,
    xpolicyRxReceiveOption,
    xpolicyRxLocalPref,
    xpolicyRxRowStatus,
    xpolicyRxPrefixMin,
    xpolicyRxPrefixMax,

    xpolicyTxProtocol,  
    xpolicyTxPeer,
    xpolicyTxName,
    xpolicyTxSrcProtocol,  
    xpolicyTxSrcProtSubType,
    xpolicyTxAddrStart,
    xpolicyTxAddrEnd,
    xpolicyTxAsString,
    xpolicyTxCommunityId,
    xpolicyTxSendOption,
    xpolicyTxMED,
    xpolicyTxMEDAuto,  
    xpolicyTxAsPrepend,
    xpolicyTxSendCommunityId,
    xpolicyTxIgpMetric,
    xpolicyTxIgpMetricType,
    xpolicyTxIgpMetricAuto, 
    xpolicyTxNextHopSelf, 
    xpolicyTxRowStatus, 
    xpolicyTxPrefixMin,
    xpolicyTxPrefixMax,

    xpolicyRxDisplayString,
    xpolicyTxDisplayString,

    xpolicyPeerGroupIndex,
    xpolicyPeerGroupPeer,
    xpolicyPeerGroupRowStatus,


    xpolicyPriRxProtocol,  
    xpolicyPriRxPeer,
    xpolicyPriRxName,
    xpolicyPriRxAddrStart,
    xpolicyPriRxAddrEnd,
    xpolicyPriRxAsString,
    xpolicyPriRxCommunityId,
    xpolicyPriRxReceiveOption,
    xpolicyPriRxLocalPref,
    xpolicyPriRxRowStatus,
    xpolicyPriRxPrefixMin,
    xpolicyPriRxPrefixMax,

    xpolicyPriTxProtocol,  
    xpolicyPriTxPeer,
    xpolicyPriTxName,
    xpolicyPriTxSrcProtocol,  
    xpolicyPriTxSrcProtSubType,
    xpolicyPriTxAddrStart,
    xpolicyPriTxAddrEnd,
    xpolicyPriTxAsString,
    xpolicyPriTxCommunityId,
    xpolicyPriTxSendOption,
    xpolicyPriTxMED,
    xpolicyPriTxMEDAuto,  
    xpolicyPriTxAsPrepend,
    xpolicyPriTxSendCommunityId,
    xpolicyPriTxIgpMetric,
    xpolicyPriTxIgpMetricType,
    xpolicyPriTxIgpMetricAuto, 
    xpolicyPriTxNextHopSelf, 
    xpolicyPriTxRowStatus,
    xpolicyPriTxPrefixMin,
    xpolicyPriTxPrefixMax
    }
    STATUS      current
    DESCRIPTION
        "The set of all accessible objects in this MIB."
    ::= { xpolicyGroups 1 }

END
