-- extracted from draft-ietf-pwe3-pw-atm-mib-00.txt
-- at Thu Feb  5 06:16:36 2004

PW-ATM-MIB-DRAFT-00 DEFINITIONS ::= BEGIN 
    
    IMPORTS 
    MODULE-IDENTITY, OBJECT-TYPE, experimental, Integer32,
    Counter32, Counter64
          FROM SNMPv2-SMI 
    
    MODULE-COMPLIANCE, OBJECT-GROUP 
          FROM SNMPv2-CONF 
   
    TruthValue, RowStatus, RowPointer
          FROM SNMPv2-TC 
    
    InterfaceIndex 
          FROM IF-MIB 
    
    pwVcIndex 
          FROM PW-MIB 
    
    AtmVpIdentifier, AtmVcIdentifier
          FROM ATM-TC-MIB;


      pwAtmMIB MODULE-IDENTITY 
      LAST-UPDATED "200302161200Z"  -- 16 February 2003 12:00:00 EST 
      ORGANIZATION "Pseudo-Wire Emulation Edge-to-Edge (PWE3) 
                    Working Group" 
      CONTACT-INFO 
          "Senthilkumar Sathappan  
           Postal: 1000 Marconi Drive
                   Warrendale PA 15086
           Tel:    +1-724-742-6147
           Email:  senthilkumar.sathappan@marconi.com


           Marichetty Venkatesan
           Postal: 1000 Marconi Drive
                   Warrendale PA 15086
           Tel:    +1-724-742-7058
           Email:  venkatesan.marichetty@marconi.com


           Thomas D. Nadeau
           Postal: Cisco Systems, Inc.
           250 Apollo Drive
           Chelmsford, MA 01824
           Tel:    +1-978-497-3051
           Email:  tnadeau@cisco.com


           Discussion and general questions should be posed to 
           the PWE3 Working Group (pwe3@ietf.org)." 

      DESCRIPTION 
          "This MIB contains managed object definitions for Pseudo Wire
       emulation of ATM over Packet Switched Networks(PSN).
    
           This MIB reports to the PW-MIB. The PW-MIB contains 
           structures and MIB associations generic to Pseudo-Wire 
           Virtual Circuit (VC) emulation. VC-specific MIBs (such as 
           this) contain config and stats for specific VC types." 
           
      -- Revision history. 
      REVISION "200302161200Z"  -- 16 October 2003 12:00:00 EST 
      DESCRIPTION "Initial Version"
      ::= { experimental 979 } -- To be assigned by IANA 
    
    -- Top-level components of this MIB


    pwAtmNotifications OBJECT IDENTIFIER ::= { pwAtmMIB 0 }
    pwAtmObjects       OBJECT IDENTIFIER ::= { pwAtmMIB 1 }
    pwAtmConformance   OBJECT IDENTIFIER ::= { pwAtmMIB 2 }


    -- PW VC ATM Outboud Table


    pwAtmOutboundTable OBJECT-TYPE
    SYNTAX    SEQUENCE OF PwAtmOutboundEntry
    MAX-ACCESS        not-accessible
    STATUS            current
    DESCRIPTION
        "This table specifies the information for an ATM VC to be
carried
         over PSN in the outbound direction."
    ::= { pwAtmObjects 1 }


    pwAtmOutboundEntry OBJECT-TYPE
    SYNTAX        PwAtmOutboundEntry
    MAX-ACCESS    not-accessible
    STATUS        current
    DESCRIPTION
        "A row in this table represents an ATM VC that needs to be 
         adapted and carried over PSN. This table is indexed by
pwVcIndex
         from pwVcTable." 
        INDEX { pwVcIndex }
    ::= { pwAtmOutboundTable 1 }
    
    PwAtmOutboundEntry ::= SEQUENCE {
      pwAtmOutboundAtmIf                InterfaceIndex,
      pwAtmOutboundVpi                  AtmVpIdentifier,
      pwAtmOutboundVci                  AtmVcIdentifier,
      pwAtmOutboundTrafficParamDescr    RowPointer,
      pwAtmOutboundRowStatus            RowStatus,
      pwAtmOutboundClpQosMapping        TruthValue,
      pwAtmOutboundOamCellSupported     TruthValue,
      pwAtmOutboundQosScalingFactor     Integer32
    }


    pwAtmOutboundAtmIf OBJECT-TYPE
    SYNTAX        InterfaceIndex 
    MAX-ACCESS    read-create
    STATUS        current
    DESCRIPTION
        "The ATM Interface that receives cells from the ATM network."
    ::= { pwAtmOutboundEntry 1 }


    pwAtmOutboundVpi OBJECT-TYPE
    SYNTAX        AtmVpIdentifier 
    MAX-ACCESS    read-create
    STATUS        current
    DESCRIPTION
        "VPI value of this ATM VC. 
        If the pwVcType is atmNto1Transparent then the value will be set


        to zero."
    ::= { pwAtmOutboundEntry 2 }


    pwAtmOutboundVci OBJECT-TYPE
    SYNTAX        AtmVcIdentifier 
    MAX-ACCESS    read-create
    STATUS        current
    DESCRIPTION
        "VCI value of this ATM VC. 
        If the pwVcType is atmNto1Transparent, atmCell1to1Vpc or
        atmCellNto1Vpc then the value should be set to zero."
    ::= { pwAtmOutboundEntry 3 }


    pwAtmOutboundTrafficParamDescr OBJECT-TYPE
    SYNTAX        RowPointer 
    MAX-ACCESS    read-create
    STATUS        current
    DESCRIPTION
        "This object represents a pointer to a ATM traffic parameter 
         specification table which will be employed while receiving
cells
         from the ATM network. This table should contain a set of 
         self-consistent ATM traffic parameters including the ATM 
         traffic service category. A value of 0.0 indicates Best Effort"
    ::= { pwAtmOutboundEntry 4 }


    pwAtmOutboundRowStatus OBJECT-TYPE
    SYNTAX        RowStatus 
    MAX-ACCESS    read-create
    STATUS        current
    DESCRIPTION
        "This Object is used to create, modify or delete a row in this 
         table."
    ::= { pwAtmOutboundEntry 5 }
    
    pwAtmOutboundClpQosMapping OBJECT-TYPE
    SYNTAX        TruthValue 
    MAX-ACCESS    read-create
    STATUS        current
    DESCRIPTION
        "This Object indicates whether the CLP bits are considered when 
         determining the value placed in the Quality of Service fields 
         (e.g. EXP fields of the MPLS Label Stack) of the encapsulating 
         protocol."
    ::= { pwAtmOutboundEntry 6 }


    pwAtmOutboundOamCellSupported OBJECT-TYPE
    SYNTAX        TruthValue 
    MAX-ACCESS    read-create
    STATUS        current
    DESCRIPTION
        "This Object indicates whether OAM Cells are transported on this


         VC."
    ::= { pwAtmOutboundEntry 7 }


pwAtmOutboundQosScalingFactor OBJECT-TYPE
        SYNTAX          Integer32
        MAX-ACCESS      read-create
        STATUS          current
        DESCRIPTION
            "This Object represents the scaling factor (% value) to be
             applied to ATM QoS rates when calculating QoS rates for the
             PSN domain . For example, in the cell transport mode the 
             bandwidth needed in the PSN domain will be higher (since
PSN
             Transport header, PW header, and optional control word have
             to transmitted with every cell), whereas in the AAL5 mode 
             the bandwidth needed in PSN domain will be less since cell
             headers will be removed after reassembly." 
        DEFVAL { 100 }
    ::= { pwAtmOutboundEntry 8 }


    -- End of PW VC ATM Outbound Table


    -- PW VC ATM Outbound Perf Table


    pwAtmOutboundPerfTable OBJECT-TYPE
    SYNTAX    SEQUENCE OF PwAtmOutboundPerfEntry
    MAX-ACCESS        not-accessible
    STATUS            current
    DESCRIPTION
        "This table specifies performance-related attributes for
         an ATM VC in the outbound direction." 
    ::= { pwAtmObjects 2 }
    pwAtmOutboundPerfEntry OBJECT-TYPE
    SYNTAX    PwAtmOutboundPerfEntry
    MAX-ACCESS    not-accessible
    STATUS        current
    DESCRIPTION
        "A row in this table represents performance for an ATM VC in the


         outbound direction" 
        AUGMENTS { pwAtmOutboundEntry }
    ::= { pwAtmOutboundPerfTable 1 }
    
    PwAtmOutboundPerfEntry ::= SEQUENCE {
      pwAtmOutboundCellsReceived    Counter32,
      pwAtmOutboundCellsRejected    Counter32,
      pwAtmOutboundCellsTagged      Counter32,
      pwAtmOutboundHCCellsReceived  Counter64,
      pwAtmOutboundHCCellsRejected  Counter64,    
      pwAtmOutboundHCCellsTagged    Counter64
    }   


    pwAtmOutboundCellsReceived OBJECT-TYPE
    SYNTAX        Counter32 
    MAX-ACCESS    read-only
    STATUS        current
    DESCRIPTION
        "This Object indicates the number of cells received by this VC."
    ::= { pwAtmOutboundPerfEntry 1 }


    pwAtmOutboundCellsRejected OBJECT-TYPE
    SYNTAX        Counter32 
    MAX-ACCESS    read-only
    STATUS        current
    DESCRIPTION
        "This Object indicates the number of cells that were rejected by


         this VC because of policing."
    ::= { pwAtmOutboundPerfEntry 2 }


    pwAtmOutboundCellsTagged OBJECT-TYPE
    SYNTAX        Counter32 
    MAX-ACCESS    read-only
    STATUS        current
    DESCRIPTION
        "This Object indicates the number of cells that were Tagged."
        ::= { pwAtmOutboundPerfEntry 3 }


    pwAtmOutboundHCCellsReceived OBJECT-TYPE
    SYNTAX        Counter64 
    MAX-ACCESS    read-only
    STATUS        current
    DESCRIPTION
        "High capacity counter for number of cells received by this VC."
        ::= { pwAtmOutboundPerfEntry 4 }


    pwAtmOutboundHCCellsRejected OBJECT-TYPE
    SYNTAX        Counter64 
    MAX-ACCESS    read-only
    STATUS        current
    DESCRIPTION
        "High Capacity counter for number of cells that were rejected by


         this VC because of policing."
        ::= { pwAtmOutboundPerfEntry 5 }


    pwAtmOutboundHCCellsTagged OBJECT-TYPE
    SYNTAX        Counter64 
    MAX-ACCESS    read-only
    STATUS        current
    DESCRIPTION
        "High capacity counter for number of cells that were Tagged."
        ::= { pwAtmOutboundPerfEntry 6 }


    -- End of PW VC ATM Outbound Perf Table


    -- PW VC ATM Inbound Table


    pwAtmInboundTable OBJECT-TYPE
    SYNTAX    SEQUENCE OF PwAtmInboundEntry
    MAX-ACCESS        not-accessible
    STATUS            current
    DESCRIPTION
        "This table specifies the information for an ATM VC in the 
         Inbound direction."
    ::= { pwAtmObjects 3 }


    pwAtmInboundEntry OBJECT-TYPE
    SYNTAX    PwAtmInboundEntry
    MAX-ACCESS    not-accessible
    STATUS        current
    DESCRIPTION
        "A row in this table represents an ATM VC that needs to be sent 
         into the ATM Network after reconstructing cells from Packets 
         received from a PSN This table is indexed by pwVcIndex from 
         pwVcTable" 
    INDEX { pwVcIndex }
    ::= { pwAtmInboundTable 1 }
  
    PwAtmInboundEntry ::= SEQUENCE {
      pwAtmInboundAtmIf              InterfaceIndex,
      pwAtmInboundVpi                AtmVpIdentifier,
      pwAtmInboundVci                AtmVcIdentifier,
      pwAtmInboundTrafficParamDescr  RowPointer,
      pwAtmInboundRowStatus          RowStatus,
      pwAtmInboundOamCellSupported   TruthValue
    }


    pwAtmInboundAtmIf OBJECT-TYPE
    SYNTAX        InterfaceIndex 
    MAX-ACCESS    read-create
    STATUS        current
    DESCRIPTION
        "The ATM Interface that sends cells into the ATM network after 
         reconstructing cells from packets received from a PSN."
    ::= { pwAtmInboundEntry 1 }


    pwAtmInboundVpi OBJECT-TYPE
    SYNTAX        AtmVpIdentifier 
    MAX-ACCESS    read-create
    STATUS    current
    DESCRIPTION
        "VPI value of this ATM VC. 
         If the pwVcType is atmNto1Transparent then the value will be
set
         to zero."
        ::= { pwAtmInboundEntry 2 }


    pwAtmInboundVci OBJECT-TYPE
    SYNTAX        AtmVcIdentifier 
    MAX-ACCESS    read-create
    STATUS    current
    DESCRIPTION
        "VCI value of this ATM VC. 
         If the pwVcType is atmNto1Transparent atmCell1to1Vpc or
         atmCellNto1Vpc then the value should be set to zero."
        ::= { pwAtmInboundEntry 3 }


    pwAtmInboundTrafficParamDescr OBJECT-TYPE
    SYNTAX        RowPointer 
    MAX-ACCESS    read-create
    STATUS        current
    DESCRIPTION
        "This object represents a pointer to a ATM traffic parameter 
         specification table which will be employed while transmit into 
         the ATM network. This table contains a set of self-consistent
         ATM traffic parameters including the ATM traffic service 
         category.
         A value of 0.0 indicates Best Effort"
        ::= { pwAtmInboundEntry 4 }


    pwAtmInboundRowStatus OBJECT-TYPE
    SYNTAX        RowStatus 
    MAX-ACCESS    read-create
    STATUS        current
        DESCRIPTION
        "This Object is used to create, modify or delete a row in this
        table."
        ::= { pwAtmInboundEntry 5 }


    pwAtmInboundOamCellSupported OBJECT-TYPE
    SYNTAX        TruthValue 
    MAX-ACCESS    read-create
    STATUS        current
    DESCRIPTION
        "This Object indicates whether this VC can receive OAM Cells."
        ::= { pwAtmInboundEntry 6 }


    -- End of PW VC ATM Inbound Table


    -- PW VC ATM Inbound Perf Table


    pwAtmInboundPerfTable OBJECT-TYPE
    SYNTAX    SEQUENCE OF PwAtmInboundPerfEntry
    MAX-ACCESS        not-accessible
    STATUS            current
    DESCRIPTION
        "This table specifies the performance for an ATM VC in the 
         Inbound direction."
    ::= { pwAtmObjects 4 }


    pwAtmInboundPerfEntry OBJECT-TYPE
    SYNTAX    PwAtmInboundPerfEntry
    MAX-ACCESS    not-accessible
    STATUS        current
    DESCRIPTION
        "This table specifies performance-related attributes for
         an ATM VC in the inbound direction." 
    AUGMENTS { pwAtmInboundEntry }
    ::= {pwAtmInboundPerfTable 1}


    PwAtmInboundPerfEntry ::= SEQUENCE {
      pwAtmInboundPerfCellsXmit    Counter32, 
      pwAtmInboundPerfCellsLost    Counter32, 
      pwAtmInboundPerfHCCellsXmit  Counter64, 
      pwAtmInboundPerfHCCellsLost  Counter64
    }


    pwAtmInboundPerfCellsXmit OBJECT-TYPE
        SYNTAX        Counter32 
    MAX-ACCESS    read-only
    STATUS        current
    DESCRIPTION
        "This Object indicates the number of cells that were transmitted


         into ATM network by this VC."
        ::= { pwAtmInboundPerfEntry 1 }

    pwAtmInboundPerfCellsLost OBJECT-TYPE
    SYNTAX        Counter32 
    MAX-ACCESS    read-only
    STATUS        current
    DESCRIPTION
        "This Object indicates the number of cells that were dropped by 
         this VC."
        ::= { pwAtmInboundPerfEntry 2 }


    pwAtmInboundPerfHCCellsXmit OBJECT-TYPE
    SYNTAX        Counter64 
    MAX-ACCESS    read-only
    STATUS        current
    DESCRIPTION
        "High Capacity counter for the number of cells that were 
         transmitted into ATM network by this VC."
        ::= { pwAtmInboundPerfEntry 3 }


    pwAtmInboundPerfHCCellsLost OBJECT-TYPE
    SYNTAX        Counter64 
    MAX-ACCESS    read-only
    STATUS        current
    DESCRIPTION
        "High Capacity counter for number of cells that were dropped by 
         this VC."
        ::= { pwAtmInboundPerfEntry 4 }


    -- End of PW VC ATM Inbound Table


    -- conformance information


    pwAtmGroups      OBJECT IDENTIFIER ::= { pwAtmConformance 1 }
    pwAtmCompliances OBJECT IDENTIFIER ::= { pwAtmConformance 2 }


    pwAtmModuleCompliance MODULE-COMPLIANCE
    STATUS  current
    DESCRIPTION
            "The compliance statement for agent that support PW 
             ATM."


    MODULE  -- this module
        MANDATORY-GROUPS { pwAtmOutboundGroup,
                           pwAtmOutboundPerfGroup,
                           pwAtmInboundGroup,
                           pwAtmInboundPerfGroup
                         }
    ::= { pwAtmCompliances 1 }


-- Units of conformance.
    pwAtmOutboundGroup OBJECT-GROUP 
    OBJECTS { pwAtmOutboundAtmIf,           
             pwAtmOutboundVpi,             
             pwAtmOutboundVci,             
             pwAtmOutboundTrafficParamDescr,
             pwAtmOutboundRowStatus,       
             pwAtmOutboundClpQosMapping,   
             pwAtmOutboundOamCellSupported,
             pwAtmOutboundQosScalingFactor
    }
    STATUS  current
    DESCRIPTION
              "Collection of objects for basic ATM PW outbound config."
    ::= { pwAtmGroups 1 }


    pwAtmOutboundPerfGroup OBJECT-GROUP 
    OBJECTS { pwAtmOutboundCellsReceived,      
             pwAtmOutboundCellsRejected,  
             pwAtmOutboundCellsTagged,    
             pwAtmOutboundHCCellsReceived,
             pwAtmOutboundHCCellsRejected,
             pwAtmOutboundHCCellsTagged  
    }          
    STATUS  current
    DESCRIPTION
          "Collection of objects counting various outbound ATM PW 
           statistics."
    ::= { pwAtmGroups 2 }


    pwAtmInboundGroup OBJECT-GROUP 
    OBJECTS { pwAtmInboundAtmIf,            
             pwAtmInboundVpi,              
             pwAtmInboundVci,              
             pwAtmInboundTrafficParamDescr,
             pwAtmInboundRowStatus,        
             pwAtmInboundOamCellSupported 
    }          
    STATUS  current
    DESCRIPTION
          "Collection of objects for basic ATM PW inbound config."
    ::= { pwAtmGroups 3 }


    pwAtmInboundPerfGroup OBJECT-GROUP 
    OBJECTS { pwAtmInboundPerfCellsXmit,  
             pwAtmInboundPerfCellsLost,  
             pwAtmInboundPerfHCCellsXmit,
             pwAtmInboundPerfHCCellsLost
    }          
    STATUS  current
    DESCRIPTION
          "Collection of objects counting various inbound ATM PW
           statistics."
    ::= { pwAtmGroups 4 }


END

-- 
-- 
--    Copyright (C) The Internet Society (2000).  All Rights Reserved.
--    
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
--    
--    The limited permissions granted above are perpetual and will not be
--    revoked by the Internet Society or its successors or assigns. This
--    document and the information contained herein is provided on an "AS
--    IS" basis and THE INTERNET SOCIETY AND THE INTERNET ENGINEERING TASK
--    FORCE DISCLAIMS ALL WARRANTIES, EXPRESS OR IMPLIED, INCLUDING BUT NOT
--    LIMITED TO ANY WARRANTY THAT THE USE OF THE INFORMATION HEREIN WILL
--    NOT INFRINGE ANY RIGHTS OR ANY IMPLIED WARRANTIES OF MERCHANTABILITY
--    OR FITNESS FOR A PARTICULAR PURPOSE.
