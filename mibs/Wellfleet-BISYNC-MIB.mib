Wellfleet-BISYNC-MIB DEFINITIONS ::= BEGIN

-- Created by mdl2asn version 3.1
-- Creation date: Wed Sep  6 16:57:22 EDT 1995
-- Edited: ksheth 10/12/95 - removed some enumerations for clock speed
--         ksheth 04/09/96 - removed some IMPORTS statments


    IMPORTS

      Counter, Gauge, TimeTicks
        FROM RFC1155-SMI
      OBJECT-TYPE
        FROM RFC-1212
      wfBisyncGroup
        FROM Wellfleet-COMMON-MIB;


    wfBisyncTable OBJECT-TYPE
        SYNTAX	SEQUENCE OF WfBisyncEntry
        ACCESS	not-accessible
        STATUS	mandatory
        DESCRIPTION
                "*   BISYNC  line record *"
        ::= { wfBisyncGroup 1 }

    wfBisyncEntry OBJECT-TYPE
        SYNTAX	WfBisyncEntry
        ACCESS	not-accessible
        STATUS	mandatory
        DESCRIPTION
                "An entry in the BISYNC table"
        INDEX	{ wfBisyncSlot,
    		  wfBisyncConnector }
        ::= { wfBisyncTable 1 }

    WfBisyncEntry ::= SEQUENCE {
    	    wfBisyncDelete
    		INTEGER,
    	    wfBisyncDisable
    		INTEGER,
    	    wfBisyncCct
    		INTEGER,
    	    wfBisyncMtu
    		INTEGER,
    	    wfBisyncMediaType
    		INTEGER,
    	    wfBisyncCableType
    		INTEGER,
    	    wfBisyncClkSource
    		INTEGER,
    	    wfBisyncClkSpeed
    		INTEGER,
    	    wfBisyncService
    		INTEGER,
    	    wfBisyncCfgTxQueueLength
    		INTEGER,
    	    wfBisyncCfgRxQueueLength
    		INTEGER,
    	    wfBisyncCharMode
    		INTEGER,
    	    wfBisyncLineNumber
    		INTEGER,
    	    wfBisyncRtsEnable
    		INTEGER,
    	    wfBisyncExternalClkSpeed
    		INTEGER,
    	    wfBisyncModule
    		INTEGER,
    	    wfBisyncActualConnector
    		INTEGER,
    	    wfBisyncConnector
    		INTEGER,
    	    wfBisyncSlot
    		INTEGER,
    	    wfBisyncActiveCct
    		INTEGER,
    	    wfBisyncState
    		INTEGER,
    	    wfBisyncLastState
    		INTEGER,
    	    wfBisyncRxOctets
    		Counter,
    	    wfBisyncTxOctets
    		Counter,
    	    wfBisyncRxFrames
    		Counter,
    	    wfBisyncTxFrames
    		Counter,
    	    wfBisyncRxErrors
    		Counter,
    	    wfBisyncTxErrors
    		Counter,
    	    wfBisyncTxLackRescs
    		Counter,
    	    wfBisyncTxUnderFlows
    		Counter,
    	    wfBisyncRxOverFlows
    		Counter,
    	    wfBisyncRxBadFrames
    		Counter,
    	    wfBisyncRxRunts
    		Counter,
    	    wfBisyncTxQueueLength
    		INTEGER,
    	    wfBisyncRxQueueLength
    		INTEGER,
    	    wfBisyncRxReplenMisses
    		Counter,
    	    wfBisyncLastChange
    		TimeTicks,
    	    wfBisyncOutQLen
    		Gauge,
    	    wfBisyncRxLackRescsChar
    		Counter,
    	    wfBisyncIsrBCZero
    		Counter,
    	    wfBisyncIsrBCSix
    		Counter,
    	    wfBisyncIsrBCInvalid
    		Counter,
    	    wfBisyncIsrBCErrors
    		Counter,
            wfBisyncLocalConnectionState
                INTEGER,
            wfBisyncRemoteConnectionState
	    	INTEGER,
	    wfBisyncAdditionalSyncPairs
                INTEGER               
        }

    wfBisyncDelete OBJECT-TYPE
        SYNTAX	INTEGER {
    		    created(1),
    		    deleted(2)
    		}
        ACCESS	read-write
        STATUS	mandatory
        DESCRIPTION
                "Create/Delete parameter"
        DEFVAL	{ created }
        ::= { wfBisyncEntry 1 }

    wfBisyncDisable OBJECT-TYPE
        SYNTAX	INTEGER {
    		    enabled(1),
    		    disabled(2)
    		}
        ACCESS	read-write
        STATUS	mandatory
        DESCRIPTION
                "Enable/Disable parameter"
        DEFVAL	{ enabled }
        ::= { wfBisyncEntry 2 }

    wfBisyncCct OBJECT-TYPE
        SYNTAX	INTEGER(1..1023)
        ACCESS	read-write
        STATUS	mandatory
        DESCRIPTION
                "CCT number for this line instance"
        ::= { wfBisyncEntry 3 }

    wfBisyncMtu OBJECT-TYPE
        SYNTAX	INTEGER(1..4568)
        ACCESS	read-write
        STATUS	mandatory
        DESCRIPTION
                "MTU parameter, this is buffer size for BISYNC media, fixed"
        DEFVAL	{ 1580 }
        ::= { wfBisyncEntry 4 }

    wfBisyncMediaType OBJECT-TYPE
        SYNTAX	INTEGER {
    		    default(1),
    		    raisedtr(2),
    		    v25bis(3)
    		}
        ACCESS	read-write
        STATUS	mandatory
        DESCRIPTION
                "Media type selection is provided via this parameter"
        DEFVAL	{ default }
        ::= { wfBisyncEntry 5 }

    wfBisyncCableType OBJECT-TYPE
        SYNTAX	INTEGER {
    		    rs232(1),
    		    rs422(2),
    		    v35(3),
    		    x21(4)
    		}
        ACCESS	read-write
        STATUS	mandatory
        DESCRIPTION
                "Type of Cable attached to the Bisync port - this is
                needed for V.25bis and Raise DTR to properly
                communicate with the modem"
        DEFVAL	{ rs232 }
        ::= { wfBisyncEntry 6 }

    wfBisyncClkSource OBJECT-TYPE
        SYNTAX	INTEGER {
    		    internal(1),
    		    external(2)
    		}
        ACCESS	read-write
        STATUS	mandatory
        DESCRIPTION
                "Tx/Rx clock source is either internally or external generated."
        DEFVAL	{ external }
        ::= { wfBisyncEntry 7 }

    wfBisyncClkSpeed OBJECT-TYPE
        SYNTAX	INTEGER {
    		    clk1200b(1200),
    		    clk2400b(2401),
    		    clk4800b(4807),
    		    clk7200b(7204),
    		    clk9600b(9615),
    		    clk19200b(19230) 
    		}
        ACCESS	read-write
        STATUS	mandatory
        DESCRIPTION
                "Tx/Rx clock speed. This speed selection is valid when either
                internal or external clocking is selected.  In some cases,  router
                software uses this attribute for route selection.  If Priority
                Queuing is configured, it chooses queue depths based on this
                attribute.  If internal clocking is selected, this attribute
                effects hardware initialization.  If external
                clocking is selected,  this attribute should be set to the speed that
                most closely corresponds to the speed of the external clock."
        DEFVAL	{ clk9600b }
        ::= { wfBisyncEntry 8 }

    wfBisyncService OBJECT-TYPE
        SYNTAX	INTEGER {
    		    dlsw(1),
    		    tunneling(2)
    		}
        ACCESS	read-write
        STATUS	mandatory
        DESCRIPTION
                "Service Type selection is provided via this parameter. The
                supported services can be selected per interface."
        DEFVAL	{ tunneling }
        ::= { wfBisyncEntry 9 }

    wfBisyncCfgTxQueueLength OBJECT-TYPE
        SYNTAX	INTEGER(0..255)
        ACCESS	read-write
        STATUS	mandatory
        DESCRIPTION
                "Configured Transmit Queue Length. Values other than zero
                over-ride the router selected values.  A value of zero has a
                special meaning.  Zero causes router based default values to
                be used.  Values larger than the compiled ring size are
                truncated to the compiled ring size. "
        ::= { wfBisyncEntry 10 }

    wfBisyncCfgRxQueueLength OBJECT-TYPE
        SYNTAX	INTEGER(0..255)
        ACCESS	read-write
        STATUS	mandatory
        DESCRIPTION
                "Configured Receive Queue Length. Values other than zero
                over-ride the router selected values.  A value of zero has
                a special meaning.  Zero causes router based default values
                to be used.  Values larger than the compiled ring size are
                truncated to the compiled ring size. "
        ::= { wfBisyncEntry 11 }

    wfBisyncCharMode OBJECT-TYPE
        SYNTAX	INTEGER {
    		    ebcdic(1),
    		    ascii(2)
    		}
        ACCESS	read-write
        STATUS	mandatory
        DESCRIPTION
                "Control Character Mode - ASCII/EBCDIC"
        DEFVAL	{ ebcdic }
        ::= { wfBisyncEntry 12 }

    wfBisyncLineNumber OBJECT-TYPE
        SYNTAX	INTEGER
        ACCESS	read-write
        STATUS	mandatory
        DESCRIPTION
                "line number for this line instance"
        ::= { wfBisyncEntry 13 }

    wfBisyncRtsEnable OBJECT-TYPE
        SYNTAX	INTEGER {
    		    enabled(1),
    		    disabled(2)
    		}
        ACCESS	read-write
        STATUS	mandatory
        DESCRIPTION
                "The RTS parameter enables/disables detection of RTS signals on the
                interface. Normal default mode is running without RTS enabled"
        DEFVAL	{ disabled }
        ::= { wfBisyncEntry 14 }

    wfBisyncExternalClkSpeed OBJECT-TYPE
        SYNTAX	INTEGER(1200..19200)
        ACCESS	read-write
        STATUS	mandatory
        DESCRIPTION
                "External Clock Speed. If external clocking is configured, this
                attribute should be set to the clock speed of the externally
                supplied clock. Depending on the protocols configured in the
                interface, this value may control internal decision making in the
                router. In soe cases, router software uses this attribute for route
                selection. If Priority Queueing is configured, it chooses queue depths
                based on this attribute. This attribute has no effect when Internal
                Clocking is configured."
        DEFVAL	{ 9600 }
        ::= { wfBisyncEntry 15 }

    wfBisyncModule OBJECT-TYPE
        SYNTAX	INTEGER {
    		    one(1),
    		    two(2),
    		    three(3),
    		    four(4)
    		}
        ACCESS	read-only
        STATUS	mandatory
        DESCRIPTION
                "Module number for ASN platform, filled in by driver. For non-ASN
                platforms, this attribute will not be used "
        ::= { wfBisyncEntry 16 }

    wfBisyncActualConnector OBJECT-TYPE
        SYNTAX	INTEGER {
    		    one(1),
    		    two(2),
    		    three(3),
    		    four(4),
    		    five(5),
    		    six(6),
    		    seven(7),
    		    eight(8)
    		}
        ACCESS	read-only
        STATUS	mandatory
        DESCRIPTION
                "Actual Connector Number for ASN platform, filled in by driver.
                For non-ASN platforms, this attribute will not be used."
        ::= { wfBisyncEntry 17 }

    wfBisyncConnector OBJECT-TYPE
        SYNTAX	INTEGER {
    		    one(1),
    		    two(2),
    		    three(3),
    		    four(4)
    		}
        ACCESS	read-only
        STATUS	mandatory
        DESCRIPTION
                "Instance ID Connector, filled in by driver. For the ASN
                this attribute is an encoded value and is equal to
                'module'*10 + 'connector'. Where 'module' is defined in
                attribute mm and 'connector' is defined in attribute cc
                of this table. For non-ASN platforms this attribute is
                the physical connector number on the slot."
        ::= { wfBisyncEntry 18 }

    wfBisyncSlot OBJECT-TYPE
        SYNTAX	INTEGER
        ACCESS	read-only
        STATUS	mandatory
        DESCRIPTION
                "Instance ID Slot, filled in by driver"
        ::= { wfBisyncEntry 19 }

    wfBisyncActiveCct OBJECT-TYPE
        SYNTAX	INTEGER(1..1023)
        ACCESS	read-only
        STATUS	mandatory
        DESCRIPTION
                "Active CCT number for this line instance"
        ::= { wfBisyncEntry 20 }

    wfBisyncState OBJECT-TYPE
        SYNTAX	INTEGER {
    		    up(1),
    		    down(2),
    		    init(3),
    		    dsrwait(4),
    		    notpresent(20)
    		}
        ACCESS	read-only
        STATUS	mandatory
        DESCRIPTION
                "Line Driver state variable, Not Present, DSR Wait,
                Init, Down, Up"
        DEFVAL	{ notpresent }
        ::= { wfBisyncEntry 21 }

    wfBisyncLastState OBJECT-TYPE
        SYNTAX	INTEGER {
    		    up(1),
    		    down(2),
    		    init(3),
    		    dsrwait(4),
    		    notpresent(20)
    		}
        ACCESS	read-only
        STATUS	mandatory
        DESCRIPTION
                "The state which the driver was in prior to the most recent re-initiali-
                zation."
        ::= { wfBisyncEntry 22 }

    wfBisyncRxOctets OBJECT-TYPE
        SYNTAX	Counter
        ACCESS	read-only
        STATUS	mandatory
        DESCRIPTION
                "Number of octets received without error"
        ::= { wfBisyncEntry 23 }

    wfBisyncTxOctets OBJECT-TYPE
        SYNTAX	Counter
        ACCESS	read-only
        STATUS	mandatory
        DESCRIPTION
                "Number of octets transmitted without error"
        ::= { wfBisyncEntry 24 }

    wfBisyncRxFrames OBJECT-TYPE
        SYNTAX	Counter
        ACCESS	read-only
        STATUS	mandatory
        DESCRIPTION
                "Number of frames received without error"
        ::= { wfBisyncEntry 25 }

    wfBisyncTxFrames OBJECT-TYPE
        SYNTAX	Counter
        ACCESS	read-only
        STATUS	mandatory
        DESCRIPTION
                "Number of frames transmitted without error"
        ::= { wfBisyncEntry 26 }

    wfBisyncRxErrors OBJECT-TYPE
        SYNTAX	Counter
        ACCESS	read-only
        STATUS	mandatory
        DESCRIPTION
                "Number of receive errors"
        ::= { wfBisyncEntry 27 }

    wfBisyncTxErrors OBJECT-TYPE
        SYNTAX	Counter
        ACCESS	read-only
        STATUS	mandatory
        DESCRIPTION
                "Number of transmission errors"
        ::= { wfBisyncEntry 28 }

    wfBisyncTxLackRescs OBJECT-TYPE
        SYNTAX	Counter
        ACCESS	read-only
        STATUS	mandatory
        DESCRIPTION
                "Number of frames clipped in driver's transmit routine due to transmit
                congestion."
        ::= { wfBisyncEntry 29 }

    wfBisyncTxUnderFlows OBJECT-TYPE
        SYNTAX	Counter
        ACCESS	read-only
        STATUS	mandatory
        DESCRIPTION
                "Number of transmission underflows, device FIFO went empty before
                next DMA request was granted."
        ::= { wfBisyncEntry 30 }

    wfBisyncRxOverFlows OBJECT-TYPE
        SYNTAX	Counter
        ACCESS	read-only
        STATUS	mandatory
        DESCRIPTION
                "Number of receive overflows, device FIFO overflowed before next
                DMA cycle granted.  No buffer resources available."
        ::= { wfBisyncEntry 31 }

    wfBisyncRxBadFrames OBJECT-TYPE
        SYNTAX	Counter
        ACCESS	read-only
        STATUS	mandatory
        DESCRIPTION
                "Number of bad receive frames, caused by FCS errors or
                non octet aligned."
        ::= { wfBisyncEntry 32 }

    wfBisyncRxRunts OBJECT-TYPE
        SYNTAX	Counter
        ACCESS	read-only
        STATUS	mandatory
        DESCRIPTION
                "Number of runt frames received"
        ::= { wfBisyncEntry 33 }

    wfBisyncTxQueueLength OBJECT-TYPE
        SYNTAX	INTEGER
        ACCESS	read-only
        STATUS	mandatory
        DESCRIPTION
                "Current Transmit Queue Length."
        ::= { wfBisyncEntry 34 }

    wfBisyncRxQueueLength OBJECT-TYPE
        SYNTAX	INTEGER
        ACCESS	read-only
        STATUS	mandatory
        DESCRIPTION
                "Current Receive Queue Length."
        ::= { wfBisyncEntry 35 }

    wfBisyncRxReplenMisses OBJECT-TYPE
        SYNTAX	Counter
        ACCESS	read-only
        STATUS	mandatory
        DESCRIPTION
                "Number of packet buffer misses while attempting to replenish driver
                receive ring."
        ::= { wfBisyncEntry 36 }

    wfBisyncLastChange OBJECT-TYPE
        SYNTAX	TimeTicks
        ACCESS	read-only
        STATUS	mandatory
        DESCRIPTION
                "The value of the SysUptime at the time the interface entered it's current
                operational state (UP state). SysUpTime is defined as the time (in
                hundredths of a second) since the network management portion of the system
                was last re-initialized. Usually the time since boot."
        ::= { wfBisyncEntry 37 }

    wfBisyncOutQLen OBJECT-TYPE
        SYNTAX	Gauge
        ACCESS	read-only
        STATUS	mandatory
        DESCRIPTION
                "The instantaneous current length of the output packet queue"
        ::= { wfBisyncEntry 38 }

    wfBisyncRxLackRescsChar OBJECT-TYPE
        SYNTAX	Counter
        ACCESS	read-only
        STATUS	mandatory
        DESCRIPTION
                "Number of Rx characters dropped due to lack of buffer resources"
        ::= { wfBisyncEntry 39 }

    wfBisyncIsrBCZero OBJECT-TYPE
        SYNTAX	Counter
        ACCESS	read-only
        STATUS	mandatory
        DESCRIPTION
                "Number of interrupts with byte count zero"
        ::= { wfBisyncEntry 40 }

    wfBisyncIsrBCSix OBJECT-TYPE
        SYNTAX	Counter
        ACCESS	read-only
        STATUS	mandatory
        DESCRIPTION
                "Number of interrupts with byte count six or more"
        ::= { wfBisyncEntry 41 }

    wfBisyncIsrBCInvalid OBJECT-TYPE
        SYNTAX	Counter
        ACCESS	read-only
        STATUS	mandatory
        DESCRIPTION
                "Number of interrupts with an unexpected message byte"
        ::= { wfBisyncEntry 42 }

    wfBisyncIsrBCErrors OBJECT-TYPE
        SYNTAX	Counter
        ACCESS	read-only
        STATUS	mandatory
        DESCRIPTION
                "Number of interrupt errors"
        ::= { wfBisyncEntry 43 }

    wfBisyncLocalConnectionState OBJECT-TYPE
        SYNTAX  INTEGER {
                    up(1),
                    down(2), 
                    unknown(3)
                }
        ACCESS  read-only
        STATUS  mandatory
        DESCRIPTION
                "The state of the cable at the router end."
        DEFVAL  { unknown }
        ::= { wfBisyncEntry 44 }

    wfBisyncRemoteConnectionState OBJECT-TYPE
        SYNTAX  INTEGER {
                    up(1),
                    down(2),
		    devicestreaming(3),
                    unknown(4)
                }
        ACCESS  read-only
        STATUS  mandatory
        DESCRIPTION
                "The state of the cable at the controller end."
        DEFVAL  { unknown }
        ::= { wfBisyncEntry 45 }
	
    wfBisyncAdditionalSyncPairs OBJECT-TYPE
        SYNTAX  INTEGER (0..100)
        ACCESS  read-write
        STATUS  mandatory
        DESCRIPTION
                "The number of pairs of sync characters, in addition to the first pair, to send between frames. "
        DEFVAL  { 0 }
        ::= { wfBisyncEntry 46 }

END  -- Wellfleet-BISYNC-MIB
