AISYSCFGPOWER-MIB DEFINITIONS ::= BEGIN

IMPORTS
    MODULE-IDENTITY, NOTIFICATION-TYPE, OBJECT-TYPE,
    Integer32,
    enterprises
					FROM SNMPv2-SMI
    DisplayString
					FROM SNMPv2-TC;

    aii OBJECT IDENTIFIER ::= {enterprises 539}
    aiSysCfg OBJECT IDENTIFIER ::= {aii 32}

aiSysCfgPower MODULE-IDENTITY
    LAST-UPDATED "200104301700Z"
    ORGANIZATION "Applied Innovation Inc."
    CONTACT-INFO
"		Engineering MIB Administrator
		Postal: Applied Innovation Inc.
			5800 Innovation Drive
			Dublin, Ohio 43017-3271

		Tel:	614-798-2000
		Fax:	614-798-1770
		Email:	snmp@aiinet.com"
    DESCRIPTION
	"MIB module for Power Supplies."
    REVISION "200104301700Z"
    DESCRIPTION "The initial revision of this module."
    ::= { aiSysCfg 3 }

-- Object definitions (Using "aiSCPower" prefix)

aiSCPowerTrapInfo OBJECT IDENTIFIER ::= { aiSysCfgPower 0 }

aiSCPowerTrapFeedFail NOTIFICATION-TYPE
    OBJECTS	{ aiSCPowerFeedIndex,
		  aiSCPowerFeedStatus }
    STATUS      current
    DESCRIPTION
	"Trap sent when a powerFeed goes into a failure mode."
    ::= { aiSCPowerTrapInfo 1 }

aiSCPowerTrapFeedOk NOTIFICATION-TYPE
    OBJECTS	{ aiSCPowerFeedIndex,
		  aiSCPowerFeedStatus }
    STATUS      current
    DESCRIPTION
	"Trap sent when a powerFeed reverts from a failure mode."
    ::= { aiSCPowerTrapInfo 2 }

aiSCPowerTrapConverterFail NOTIFICATION-TYPE
    OBJECTS	{ aiSCPowerConverterIndex,
		  aiSCPowerConverterStatus }
    STATUS      current
    DESCRIPTION
	"Trap sent when a powerConverter goes into a failure mode."
    ::= { aiSCPowerTrapInfo 3 }

aiSCPowerTrapConverterOk NOTIFICATION-TYPE
    OBJECTS	{ aiSCPowerConverterIndex,
		  aiSCPowerConverterStatus }
    STATUS      current
    DESCRIPTION
	"Trap sent when a powerConverter reverts from a failure mode."
    ::= { aiSCPowerTrapInfo 4 }

aiSCPowerAgregateStatus OBJECT-TYPE
    SYNTAX	INTEGER {okay(1), trouble(2)}
    MAX-ACCESS	read-only
    STATUS	current
    DESCRIPTION
	"Aggregate status of the power in the system.  okay(1)
	indicates no problems, while trouble(2) indicates that some
	part of the power supply system is not functioning properly."
    ::= { aiSysCfgPower 1 }

aiSCPowerFeedTable OBJECT-TYPE
    SYNTAX      SEQUENCE OF AiSCPowerFeedEntry
    MAX-ACCESS  not-accessible
    STATUS      current
    DESCRIPTION
	"A table of information on each power supply."
    ::= { aiSysCfgPower 2 }

aiSCPowerFeedEntry OBJECT-TYPE
    SYNTAX	AiSCPowerFeedEntry
    MAX-ACCESS	not-accessible
    STATUS	current
    DESCRIPTION
	"Information on a given power supply."
    INDEX { aiSCPowerFeedIndex }
    ::= { aiSCPowerFeedTable 1 }

AiSCPowerFeedEntry ::= SEQUENCE {
    aiSCPowerFeedIndex			Integer32,
    aiSCPowerFeedDescription		DisplayString,
    aiSCPowerFeedStatus			INTEGER
}

aiSCPowerFeedIndex OBJECT-TYPE
    SYNTAX	Integer32 (1..2147483647)
    MAX-ACCESS	read-only
    STATUS	current
    DESCRIPTION
	"Self referential index into this table."
    ::= { aiSCPowerFeedEntry 1 }

aiSCPowerFeedDescription OBJECT-TYPE
    SYNTAX	DisplayString (SIZE (0..255))
    MAX-ACCESS	read-only
    STATUS	current
    DESCRIPTION
	"Description of the power feed to which this table entry
	refers."
    ::= { aiSCPowerFeedEntry 2 }

aiSCPowerFeedStatus OBJECT-TYPE
    SYNTAX	INTEGER { okay(1),
    			  fail(2),
			  underVoltage(3),
			  overVoltage(4) }
    MAX-ACCESS	read-only
    STATUS	current
    DESCRIPTION
	"Status of a given power feed."
    ::= { aiSCPowerFeedEntry 3 }

aiSCPowerConverterTable OBJECT-TYPE
    SYNTAX	SEQUENCE OF AiSCPowerConverterEntry
    MAX-ACCESS	not-accessible
    STATUS	current
    DESCRIPTION
	"A table of information on each power converter."
    ::= { aiSysCfgPower 3 }

aiSCPowerConverterEntry OBJECT-TYPE
    SYNTAX	AiSCPowerConverterEntry
    MAX-ACCESS	not-accessible
    STATUS	current
    DESCRIPTION
	"Information on a given power supply."
    INDEX { aiSCPowerConverterIndex }
    ::= { aiSCPowerConverterTable 1 }

AiSCPowerConverterEntry ::=
    SEQUENCE {
	aiSCPowerConverterIndex		Integer32,
	aiSCPowerConverterDescription	DisplayString,
	aiSCPowerConverterStatus	INTEGER
    }

aiSCPowerConverterIndex OBJECT-TYPE
    SYNTAX	Integer32 (1..2147483647)
    MAX-ACCESS	read-only
    STATUS	current
    DESCRIPTION
	"Self referential index into this table."
    ::= { aiSCPowerConverterEntry 1 }

aiSCPowerConverterDescription OBJECT-TYPE
    SYNTAX	DisplayString (SIZE (0..255))
    MAX-ACCESS	read-only
    STATUS	current
    DESCRIPTION
	"Description of the converter to which this table entry
	refers."
    ::= { aiSCPowerConverterEntry 2 }

aiSCPowerConverterStatus OBJECT-TYPE
    SYNTAX	INTEGER { okay(1),
    			  fail(2),
			  underVoltage(3),
			  overVoltage(4) }
    MAX-ACCESS	read-only
    STATUS	current
    DESCRIPTION
	"Status of a given power converter."
    ::= { aiSCPowerConverterEntry 3 }
END
