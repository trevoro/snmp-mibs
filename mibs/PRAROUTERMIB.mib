PRAROUTERMIB DEFINITIONS ::= BEGIN


IMPORTS
	Counter, Gauge, TimeTicks, enterprises, IpAddress
	    FROM RFC1155-SMI
	OBJECT-TYPE
	    FROM RFC-1212
	DisplayString
	    FROM RFC1213-MIB;


-- ITK AG
-- 09.11.1995 FL Erst-Erstellung
-- 06.12.1995 FL Nachbesserungen
-- 19.12.1995 FL pramib von itk 1 auf itk 3 verlegt
-- 18.01.1996 FL praTrapMessage hinzugefuegt
-- 29.01.1996 FL aktualisiert
-- 05.02.1996 FL gesamte Hardware geloescht
--               praUipaddress geloescht 
--               praParamConfTable geloescht
-- 08.02.1996 FL praTrapMessage geloescht
-- 12.02.1996 FL aktualisiert
-- 20.02.1996 FL aktualisiert
-- 22.02.1996 FL aktualisiert 


itk     OBJECT IDENTIFIER ::= { enterprises 1195 }
pramib  OBJECT IDENTIFIER ::= { itk 3 }

--SMUX = pramib

config         OBJECT IDENTIFIER ::= { pramib 1 }

--Fuer Erweiterungen
--hardware       OBJECT IDENTIFIER ::= { config 1 }
--systemsoftware OBJECT IDENTIFIER ::= { config 2 }


prasoftware    OBJECT IDENTIFIER ::= { config 3 }

 
status         OBJECT IDENTIFIER ::= { pramib 2 }
channels       OBJECT IDENTIFIER ::= { status 1 }
watchdog       OBJECT IDENTIFIER ::= { status 2 }
fault          OBJECT IDENTIFIER ::= { status 3 }


performance    OBJECT IDENTIFIER ::= { pramib 3 }
cpu            OBJECT IDENTIFIER ::= { performance 1 }
sessions       OBJECT IDENTIFIER ::= { performance 2 }



-- HARDWARE
    
-- SYSTEM-SOFTWARE

-- PRA-SOFTWARE


praVersion OBJECT-TYPE
    	SYNTAX  OCTET STRING (SIZE (4))
    	ACCESS  read-only
    	STATUS  mandatory
    	DESCRIPTION "Version of Suprimo-Software"
::= { prasoftware 1 }


asIpTable OBJECT-TYPE
    	SYNTAX  SEQUENCE OF AsIpEntry
    	ACCESS  read-only
    	STATUS  mandatory
    	DESCRIPTION "A table of ApplicationServer Ip-Addresses"
::= { prasoftware 2 }

asIpEntry OBJECT-TYPE
    	SYNTAX  AsIpEntry
    	ACCESS  read-only
    	STATUS  mandatory
    	DESCRIPTION "An entry in applicationservertable"
	INDEX { asNumber }
::= { asIpTable 1 }


AsIpEntry ::=
   SEQUENCE {

	   asNumber
	   INTEGER,
 	   asIpAddr
           OCTET STRING

            } -- end of SEQUENCE

asNumber OBJECT-TYPE
    	SYNTAX  INTEGER
    	ACCESS  read-only
    	STATUS  mandatory
    	DESCRIPTION "index"
::= { asIpEntry 1 }

	
asIpAddr OBJECT-TYPE
    	SYNTAX  OCTET STRING
    	ACCESS  read-only
    	STATUS  mandatory
    	DESCRIPTION "IP-Address of Authentication-Servers"
::= { asIpEntry 2 }


linecntPspdn OBJECT-TYPE
	SYNTAX INTEGER
	ACCESS read-only
	STATUS mandatory
	DESCRIPTION "Max number of logical connections to PH (type X.25)."
::= { prasoftware 3 }

linecntPspdnPerBchannel OBJECT-TYPE
	SYNTAX INTEGER
	ACCESS read-only
	STATUS mandatory
	DESCRIPTION "Max number of logical connections per B-Channel to PH"
::= { prasoftware 4 }

linecntPspdnPh OBJECT-TYPE
	SYNTAX INTEGER
	ACCESS read-only
	STATUS mandatory
	DESCRIPTION "Max number of physical connections to PH"
::= { prasoftware 5 }

linecntMax OBJECT-TYPE
	SYNTAX INTEGER
	ACCESS read-only
	STATUS mandatory
	DESCRIPTION "Number of physical b-channels"
::= { prasoftware 6 }

asIpAddrTableMaxIndex OBJECT-TYPE
	SYNTAX INTEGER
	ACCESS read-only
	STATUS mandatory
	DESCRIPTION "Max number of AS-IP-Addresses"
::= { prasoftware 7 }


--STATUS

numberOfEngagedBchan OBJECT-TYPE
	SYNTAX INTEGER
	ACCESS read-only
	STATUS mandatory
	DESCRIPTION "Number of engaged B-Channel."
::= { channels 1 }

numberOfFreeBchan OBJECT-TYPE
	SYNTAX INTEGER
	ACCESS read-only
	STATUS mandatory
	DESCRIPTION "Number of free B-Channel."
::= { channels 2 }

numberOfTransToAs OBJECT-TYPE
	SYNTAX INTEGER
	ACCESS read-only
	STATUS mandatory
	DESCRIPTION "Number of transmissionconnections to AS."
::= { channels 3 }

numberOfRecvToAs OBJECT-TYPE
	SYNTAX INTEGER
	ACCESS read-only
	STATUS mandatory
	DESCRIPTION "Number of receiveconnections to AS."
::= { channels 4 }

temperature OBJECT-TYPE
	SYNTAX INTEGER
	ACCESS read-only
	STATUS mandatory
	DESCRIPTION "Temperature inside the Suprimo-Housing
	             (in ten-th-degrees)"
::= { watchdog 1 }


--fault

isdnMuxOk OBJECT-TYPE
	SYNTAX INTEGER
	ACCESS read-only
	STATUS mandatory
	DESCRIPTION "status of ISDN-Adapter"
::= { fault 1 }

modemAdapterTable OBJECT-TYPE
	SYNTAX SEQUENCE OF ModemEntry
        ACCESS not-accessible
        STATUS mandatory
        DESCRIPTION "A table of Modems. "
::= { fault 2 }

modemEntry OBJECT-TYPE
	SYNTAX ModemEntry
        ACCESS not-accessible
        STATUS mandatory
        DESCRIPTION "An entry in the modemAdapterTable."
        INDEX { modemCardNumber }
::= { modemAdapterTable 1 }


ModemEntry ::= 
      SEQUENCE {
                modemCardNumber	
	        INTEGER,
                modemAdapterOk
	        INTEGER,
		modem1
		INTEGER,
		modem2
	        INTEGER,
		modem3
		INTEGER,
		modem4
		INTEGER,
		modem5
		INTEGER,
		modem6
		INTEGER,
		modem7
		INTEGER,
		modem8
		INTEGER	
         	} -- end of SEQUENCE

modemCardNumber OBJECT-TYPE
	SYNTAX INTEGER
	ACCESS read-only
	STATUS mandatory
	DESCRIPTION "Index."
::= { modemEntry 1 }

modemAdapterOk OBJECT-TYPE
	SYNTAX INTEGER
	ACCESS read-only
	STATUS mandatory
	DESCRIPTION "status of Modem-Adapter"
::= { modemEntry 2 }

modem1 OBJECT-TYPE
	SYNTAX INTEGER
	ACCESS read-only
	STATUS mandatory
	DESCRIPTION "status of Modem1"
::= { modemEntry 3 }

modem2 OBJECT-TYPE
	SYNTAX INTEGER
	ACCESS read-only
	STATUS mandatory
	DESCRIPTION "status of Modem2"
::= { modemEntry 4 }

modem3 OBJECT-TYPE
	SYNTAX INTEGER
	ACCESS read-only
	STATUS mandatory
	DESCRIPTION "status of Modem3"
::= { modemEntry 5 }

modem4 OBJECT-TYPE
	SYNTAX INTEGER
	ACCESS read-only
	STATUS mandatory
	DESCRIPTION "status of Modem4"
::= { modemEntry 6 }

modem5 OBJECT-TYPE
	SYNTAX INTEGER
	ACCESS read-only
	STATUS mandatory
	DESCRIPTION "status of Modem5"
::= { modemEntry 7 }

modem6 OBJECT-TYPE
	SYNTAX INTEGER
	ACCESS read-only
	STATUS mandatory
	DESCRIPTION "status of Modem6"
::= { modemEntry 8 }

modem7 OBJECT-TYPE
	SYNTAX INTEGER
	ACCESS read-only
	STATUS mandatory
	DESCRIPTION "status of Modem7"
::= { modemEntry 9 }

modem8 OBJECT-TYPE
	SYNTAX INTEGER
	ACCESS read-only
	STATUS mandatory
	DESCRIPTION "status of Modem8"
::= { modemEntry 10 }


practrlOk OBJECT-TYPE
	SYNTAX INTEGER
	ACCESS read-only
	STATUS mandatory
	DESCRIPTION "status of process practrl"
::= { fault 3 }

isdnInOk OBJECT-TYPE
	SYNTAX INTEGER
	ACCESS read-only
	STATUS mandatory
	DESCRIPTION "status of process isdn_in"
::= { fault 4 }

isdnOutOk OBJECT-TYPE
	SYNTAX INTEGER
	ACCESS read-only
	STATUS mandatory
	DESCRIPTION "status of process isdn_out"
::= { fault 5 }

pstnInOk OBJECT-TYPE
	SYNTAX INTEGER
	ACCESS read-only
	STATUS mandatory
	DESCRIPTION "status of process pstn_in"
::= { fault 6 }

pspdnOk OBJECT-TYPE
	SYNTAX INTEGER
	ACCESS read-only
	STATUS mandatory
	DESCRIPTION "status of process pspdn"
::= { fault 7 }

modemCardMax OBJECT-TYPE
	SYNTAX INTEGER
	ACCESS read-only
	STATUS mandatory
	DESCRIPTION "Max number of Modem-Adapter"
::= { fault 8 }


--PERFORMANCE

cpuCapacity OBJECT-TYPE
	SYNTAX INTEGER
	ACCESS read-only
	STATUS mandatory
	DESCRIPTION "Free capacity of Cpu (per cent)."
::= { cpu 1 }


sessionTable OBJECT-TYPE
	SYNTAX  SEQUENCE OF SessionEntry
	ACCESS  not-accessible
	STATUS  mandatory
	DESCRIPTION "A table of Sessions."
::= { sessions 1 }
 
sessionEntry OBJECT-TYPE
	SYNTAX  SessionEntry
	ACCESS  not-accessible
	STATUS  mandatory
	DESCRIPTION "An entry in the Session table."
	INDEX   { sessionNumber }
::= { sessionTable 1 }

SessionEntry ::=
	SEQUENCE {

        	sessionNumber
		      INTEGER,
                sessionType 
                      INTEGER,
	        b2Protocol 
	              DisplayString (SIZE (0..30)),
	    
	--T-Interface 
        	cntRcvByteCapi
		     INTEGER,
        	cntSndByteCapi
             	     INTEGER,
        	cntRcvMsgCapi
		     INTEGER,
        	cntSndMsgCapi
             	     INTEGER,
        
	--R-Interface
        	cntRcvBytePsp
		     INTEGER,
        	cntSndBytePsp
             	     INTEGER,
        	cntRcvMsgPsp
		     INTEGER,
        	cntSndMsgPsp
             	     INTEGER

              	} -- end of SEQUENCE

sessionNumber OBJECT-TYPE
	SYNTAX INTEGER
	ACCESS read-only
	STATUS mandatory
	DESCRIPTION "The Sessionnumber to identify this Session.
	             (1 - maxSessionNumber)"
::= { sessionEntry 1 }

sessionType OBJECT-TYPE
        SYNTAX INTEGER
	ACCESS read-only
	STATUS mandatory
	DESCRIPTION "The Sessiontype of this Session."

-- 0 = not used
-- 1 = isdn_in
-- 2 = isdn_out
-- 3 = pstn_in
-- 4 = pspdn

::= { sessionEntry 2 }

b2Protocol OBJECT-TYPE
	SYNTAX DisplayString (SIZE (0..30))
        ACCESS read-only
	STATUS mandatory
	DESCRIPTION "B2-Channel Protocol."
::= { sessionEntry 3 }

cntRcvByteCapi OBJECT-TYPE
	SYNTAX INTEGER
	ACCESS read-only
	STATUS mandatory
	DESCRIPTION "Number of Bytes received from T-Interface."
::= { sessionEntry 4 }

cntSndByteCapi OBJECT-TYPE
	SYNTAX INTEGER
	ACCESS read-only
	STATUS mandatory
	DESCRIPTION "Number of Bytes sent to T-Interface."
::= { sessionEntry 5 }

cntRcvMsgCapi OBJECT-TYPE
	SYNTAX INTEGER
	ACCESS read-only
	STATUS mandatory
	DESCRIPTION "Number of Messages received from T-Interface."
::= { sessionEntry 6 }

cntSndMsgCapi OBJECT-TYPE
	SYNTAX INTEGER
	ACCESS read-only
	STATUS mandatory
	DESCRIPTION "Number of Messages sent to T-Interface."
::= { sessionEntry 7 }

cntRcvBytePsp OBJECT-TYPE
	SYNTAX INTEGER
	ACCESS read-only
	STATUS mandatory
	DESCRIPTION "Number of Bytes received from R-Interface."
::= { sessionEntry 8 }

cntSndBytePsp OBJECT-TYPE
	SYNTAX INTEGER
	ACCESS read-only
	STATUS mandatory
	DESCRIPTION "Number of Bytes sent to R-Interface."
::= { sessionEntry 9 }

cntRcvMsgPsp OBJECT-TYPE
	SYNTAX INTEGER
	ACCESS read-only
	STATUS mandatory
	DESCRIPTION "Number of Messages received from R-Interface."
::= { sessionEntry 10 }

cntSndMsgPsp OBJECT-TYPE
	SYNTAX INTEGER
	ACCESS read-only
	STATUS mandatory
	DESCRIPTION "Number of Messages sent to R-Interface."
::= { sessionEntry 11 }


cntRcvTotalByteCapi OBJECT-TYPE
	SYNTAX INTEGER
	ACCESS read-only
	STATUS mandatory
	DESCRIPTION "Number of Total Bytes[KBytes] received from T-Interface."
::= { sessions 2 }

cntSndTotalByteCapi OBJECT-TYPE
	SYNTAX INTEGER
	ACCESS read-only
	STATUS mandatory
	DESCRIPTION "Number of Total Bytes[KBytes] sent to T-Interface."
::= { sessions 3 }

cntRcvTotalMsgCapi OBJECT-TYPE
	SYNTAX INTEGER
	ACCESS read-only
	STATUS mandatory
	DESCRIPTION "Number of Total Messages received from T-Interface."
::= { sessions 4 }

cntSndTotalMsgCapi OBJECT-TYPE
	SYNTAX INTEGER
	ACCESS read-only
	STATUS mandatory
	DESCRIPTION "Number of Total Messages sent to T-Interface."
::= { sessions 5 }

cntRcvTotalBytePsp OBJECT-TYPE
	SYNTAX INTEGER
	ACCESS read-only
	STATUS mandatory
	DESCRIPTION "Number of Total Bytes[KBytes] received from R-Interface."
::= { sessions 6 }

cntSndTotalBytePsp OBJECT-TYPE
	SYNTAX INTEGER
	ACCESS read-only
	STATUS mandatory
	DESCRIPTION "Number of Total Bytes[KBytes] sent to R-Interface."
::= { sessions 7 }

cntRcvTotalMsgPsp OBJECT-TYPE
	SYNTAX INTEGER
	ACCESS read-only
	STATUS mandatory
	DESCRIPTION "Number of Total Messages received from R-Interface."
::= { sessions 8 }

cntSndTotalMsgPsp OBJECT-TYPE
	SYNTAX INTEGER
	ACCESS read-only
	STATUS mandatory
	DESCRIPTION "Number of Total Messages sent to R-Interface."
::= { sessions 9 }

sessionTableMaxIndex OBJECT-TYPE
	SYNTAX INTEGER
	ACCESS read-only
	STATUS mandatory
	DESCRIPTION "Max Number of Sessionnumber"
::= { sessions 10 }


END -- PRAROUTERMIB
