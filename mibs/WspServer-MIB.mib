WspServer-MIB DEFINITIONS ::= BEGIN

        IMPORTS
                enterprises,
                OBJECT-TYPE,
                Counter
                        FROM RFC1155-SMI
                internetServer
                        FROM InternetServer-MIB;

--      microsoft       OBJECT IDENTIFIER ::= { enterprises 311 }
--      software        OBJECT IDENTIFIER ::= { microsoft 1 }
--      internetServer  OBJECT IDENTIFIER ::= { software 7 }
        wspServer       OBJECT IDENTIFIER ::= { internetServer 12 }
        wspStatistics   OBJECT IDENTIFIER ::= { wspServer 1 }

-- WinSock Proxy Server Statistics
	activeSessions OBJECT-TYPE
		SYNTAX	INTEGER
		ACCESS	read-only
		STATUS	mandatory
		DESCRIPTION 
			"The number of active Firewall service sessions."
		::= { wspStatistics 1 }

	activeTCPConnections OBJECT-TYPE
		SYNTAX	INTEGER
		ACCESS	read-only
		STATUS	mandatory
		DESCRIPTION 
			"The total number of active TCP connections currently passing data. Connections pending or not yet established are counted elsewhere."
		::= { wspStatistics 2 }

	activeUDPConnections OBJECT-TYPE
		SYNTAX	INTEGER
		ACCESS	read-only
		STATUS	mandatory
		DESCRIPTION 
			"The total number of active UDP connections."
		::= { wspStatistics 3 }

	connectingTCPConnections OBJECT-TYPE
		SYNTAX	INTEGER
		ACCESS	read-only
		STATUS	mandatory
		DESCRIPTION 
			"The total number of TCP connections pending. This is the total number of connections that are waiting for a connect call to finish."
		::= { wspStatistics 4 }

	backConnectingTCPConnections OBJECT-TYPE
		SYNTAX	INTEGER
		ACCESS	read-only
		STATUS	mandatory
		DESCRIPTION 
			"The total number of TCP connections awaiting an inbound connect call to finish. These are connections from the Firewall service to a Firewall client after the Firewall service accepted a connection from the Internet on a listening socket."
		::= { wspStatistics 5 }

	acceptingTCPConnections OBJECT-TYPE
		SYNTAX	INTEGER
		ACCESS	read-only
		STATUS	mandatory
		DESCRIPTION 
			"The number of connection objects waiting for a TCP connection from the Firewall client after a successful remote connection."
		::= { wspStatistics 6 }

	listeningTCPConnections OBJECT-TYPE
		SYNTAX	INTEGER
		ACCESS	read-only
		STATUS	mandatory
		DESCRIPTION 
			"The number of connection objects waiting for TCP connections from remote Internet computers (after a successful listen)."
		::= { wspStatistics 7 }

	allocFailureLogs OBJECT-TYPE
		SYNTAX	Counter
		ACCESS	read-only
		STATUS	mandatory
		DESCRIPTION 
			"Number of memory allocation errors."
		::= { wspStatistics 8 }

	pumpTotalRead OBJECT-TYPE
		SYNTAX	Counter
		ACCESS	read-only
		STATUS	mandatory
		DESCRIPTION 
			"Number of bytes read by the data-pump per second."
		::= { wspStatistics 9 }

	pumpTotalWrite OBJECT-TYPE
		SYNTAX	Counter
		ACCESS	read-only
		STATUS	mandatory
		DESCRIPTION 
			"Number of bytes written by data-pump per second."
		::= { wspStatistics 10 }

	pendingGetXByY OBJECT-TYPE
		SYNTAX	Counter
		ACCESS	read-only
		STATUS	mandatory
		DESCRIPTION 
			"Number of gethostbyname and gethostbyaddr API calls pending resolution. These are calls used to resolve host DNS domain names and IP addresses for Firewall service connections."
		::= { wspStatistics 11 }

	successGetXByY OBJECT-TYPE
		SYNTAX	Counter
		ACCESS	read-only
		STATUS	mandatory
		DESCRIPTION 
			"Number of gethostbyname and gethostbyaddr API calls successfully returned. These are calls used to resolve host DNS domain names and IP addresses for Firewall service connections."
		::= { wspStatistics 12 }

	failedGetXByY OBJECT-TYPE
		SYNTAX	Counter
		ACCESS	read-only
		STATUS	mandatory
		DESCRIPTION 
			"Number of gethostbyname and gethostbyaddr API calls that have failed. These are calls used to resolve host DNS domain names and IP addresses for Firewall service connections."
		::= { wspStatistics 13 }

	ctrlWorkerThreads OBJECT-TYPE
		SYNTAX	Counter
		ACCESS	read-only
		STATUS	mandatory
		DESCRIPTION 
			"The number of Firewall service worker threads that are currently alive."
		::= { wspStatistics 14 }

	ctrlAvailableWorkerThreads OBJECT-TYPE
		SYNTAX	INTEGER
		ACCESS	read-only
		STATUS	mandatory
		DESCRIPTION 
			"The number of Firewall service worker threads that are available (waiting in completion port queue)."
		::= { wspStatistics 15 }

	mappings OBJECT-TYPE
		SYNTAX	INTEGER
		ACCESS	read-only
		STATUS	mandatory
		DESCRIPTION 
			"The number of mappings available for UDP connections."
		::= { wspStatistics 16 }

	pNATMappings OBJECT-TYPE
		SYNTAX	INTEGER
		ACCESS	read-only
		STATUS	mandatory
		DESCRIPTION 
			"The number of mappings created by SecureNAT."
		::= { wspStatistics 17 }

	kernelDataPumps OBJECT-TYPE
		SYNTAX	INTEGER
		ACCESS	read-only
		STATUS	mandatory
		DESCRIPTION 
			"The number of kernel mode data pumps created by the Firewall service."
		::= { wspStatistics 18 }

	kernelTotalTCPBytes OBJECT-TYPE
		SYNTAX	Counter
		ACCESS	read-only
		STATUS	mandatory
		DESCRIPTION 
			"Number of TCP bytes transferred by the kernel mode data-pump per second."
		::= { wspStatistics 19 }

	kernelTotalUDPBytes OBJECT-TYPE
		SYNTAX	Counter
		ACCESS	read-only
		STATUS	mandatory
		DESCRIPTION 
			"Number of UDP bytes transferred by the kernel mode data-pump per second."
		::= { wspStatistics 20 }

	dnsCacheEntries OBJECT-TYPE
		SYNTAX	Counter
		ACCESS	read-only
		STATUS	mandatory
		DESCRIPTION 
			"The current number of DNS domain name entries cached by the Firewall service."
		::= { wspStatistics 21 }

	dnsCacheHits OBJECT-TYPE
		SYNTAX	Counter
		ACCESS	read-only
		STATUS	mandatory
		DESCRIPTION 
			"The total number of times a DNS domain name was found within the DNS Cache."
		::= { wspStatistics 22 }

	dnsCacheFlushes OBJECT-TYPE
		SYNTAX	Counter
		ACCESS	read-only
		STATUS	mandatory
		DESCRIPTION 
			"The total number of times that the DNS domain name cache has been flushed or cleared by the Web Proxy Server."
		::= { wspStatistics 23 }

	dnsCacheRetrievals OBJECT-TYPE
		SYNTAX	Counter
		ACCESS	read-only
		STATUS	mandatory
		DESCRIPTION 
			"The total number of DNS domain names that have been retrieved by the Firewall service."
		::= { wspStatistics 24 }

	dnsCacheRatio OBJECT-TYPE
		SYNTAX	INTEGER
		ACCESS	read-only
		STATUS	mandatory
		DESCRIPTION 
			"The percentage of DNS domain names serviced by the DNS cache, out of a total of all DNS entries that have been retrieved by the Firewall service."
		::= { wspStatistics 25 }


END
