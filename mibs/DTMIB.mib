--
-- MIB Definitions for Panther Double-Take
-- 

   DTMIB DEFINITIONS ::= BEGIN


   IMPORTS

	TRAP-TYPE FROM RFC-1215
       enterprises, Counter, IpAddress, TimeTicks, Gauge
         FROM RFC1155-SMI
       DisplayString
         FROM RFC1213-MIB
       OBJECT-TYPE
         FROM RFC-1212;

--
-- This MIB module uses the extended OBJECT-TYPE macro as
-- defined in [14];
--

   nsi            OBJECT IDENTIFIER ::= { enterprises 2592 }
   nsiDoubleTake OBJECT IDENTIFIER ::= { nsi 3 }
   dtTraps        OBJECT IDENTIFIER ::= { nsiDoubleTake 1 }
   dtGeneral      OBJECT IDENTIFIER ::= { nsiDoubleTake 2 }
   dtSource       OBJECT IDENTIFIER ::= { nsiDoubleTake 3 }
   dtTarget       OBJECT IDENTIFIER ::= { nsiDoubleTake 4 }
   dtSecurity     OBJECT IDENTIFIER ::= { nsiDoubleTake 5 }
   dtConnection   OBJECT IDENTIFIER ::= { nsiDoubleTake 6 }

--
-- Some objects
--

--
-- General Stats
--
   dtUpTime OBJECT-TYPE
       SYNTAX TimeTicks
       ACCESS read-only
       STATUS mandatory
       DESCRIPTION
        "Time (in seconds) since Double-Take was last started."
       ::= {dtGeneral 1}

   dtCurrentMemoryUsage OBJECT-TYPE
       SYNTAX Gauge
       ACCESS read-only
       STATUS mandatory
       DESCRIPTION
        "Current amount of memory allocated (in bytes) from the Double-Take memory pool."
       ::= {dtGeneral 2}

   dtMirOpsGenerated OBJECT-TYPE
       SYNTAX Counter
       ACCESS read-only
       STATUS mandatory
       DESCRIPTION
        "Number of mirror ops generated by the mirror driver."
       ::= {dtGeneral 3}

    dtMirBytesGenerated OBJECT-TYPE
       SYNTAX Counter
       ACCESS read-only
       STATUS mandatory
       DESCRIPTION
        "Total bytes mirrored by the mirror driver."
       ::= {dtGeneral 4}

    dtRepOpsGenerated OBJECT-TYPE
       SYNTAX Counter
       ACCESS read-only
       STATUS mandatory
       DESCRIPTION
        "Number of ops generated by the file system driver."
       ::= {dtGeneral 5}

    dtRepBytesGenerated OBJECT-TYPE
       SYNTAX Counter
       ACCESS read-only
       STATUS mandatory
       DESCRIPTION
        "Total bytes generated by the file system driver."
       ::= {dtGeneral 6}

   dtSourceState OBJECT-TYPE
       SYNTAX INTEGER {
          notLoaded(0),
          loadedNoDriver(1),
          loadedWithDriver(2) }
       ACCESS read-only
       STATUS mandatory
       DESCRIPTION
        "0:Source not running, 1:Source running no driver, 2:Source running with driver"
       ::= {dtSource 1}

   dtTargetState OBJECT-TYPE
       SYNTAX INTEGER {
          notLoaded(0),
          loaded(1) }
       ACCESS read-only
       STATUS mandatory
       DESCRIPTION
        "0:Target not running, 1:Target running"
       ::= {dtTarget 1}

   dtRetryCount OBJECT-TYPE
       SYNTAX Counter
       ACCESS read-only
       STATUS mandatory
       DESCRIPTION
        "Number of file operations that have been retried."
       ::= {dtTarget 2}

   dtOpsDroppedCount OBJECT-TYPE
       SYNTAX Counter
       ACCESS read-only
       STATUS mandatory
       DESCRIPTION
        "Number of file operations that have failed and will not be retried."
       ::= {dtTarget 3}

   dtLoginCount OBJECT-TYPE
       SYNTAX Counter
       ACCESS read-only
       STATUS mandatory
       DESCRIPTION
        "Number of successful logins."
       ::= {dtSecurity 1}

   dtFailedLoginCount OBJECT-TYPE
       SYNTAX Counter
       ACCESS read-only
       STATUS mandatory
       DESCRIPTION
        "Number of un-successful logins."
       ::= {dtSecurity 2}

   dtFailedMirrorCount OBJECT-TYPE
       SYNTAX Counter
       ACCESS read-only
       STATUS mandatory
       DESCRIPTION
        "Number of files and Ops that failed to mirror because they couldn't be read on the source."
       ::= {dtGeneral 7}

   dtFailedRepCount OBJECT-TYPE
       SYNTAX Counter
       ACCESS read-only
       STATUS mandatory
       DESCRIPTION
        "Number of Ops that failed to replicate because they couldn't be read on the source."
       ::= {dtGeneral 8}

   dtActFailCount OBJECT-TYPE
       SYNTAX Counter
       ACCESS read-only
       STATUS mandatory
       DESCRIPTION
        "Number of activation code errors."
       ::= {dtGeneral 9}

   dtAutoDisCount OBJECT-TYPE
       SYNTAX Counter
       ACCESS read-only
       STATUS mandatory
       DESCRIPTION
        "Number of Auto-Disconnects."
       ::= {dtGeneral 10}

   dtAutoReCount OBJECT-TYPE
       SYNTAX Counter
       ACCESS read-only
       STATUS mandatory
       DESCRIPTION
        "Number of Auto-Reconnects."
       ::= {dtGeneral 11}

   dtDriverQueuePercent OBJECT-TYPE
       SYNTAX Counter
       ACCESS read-only
       STATUS mandatory
       DESCRIPTION
        "Percentage of the driver queue that is currently in use."
       ::= {dtGeneral 12}
--
-- Connection Stats 
--
    dtConnectionCount OBJECT-TYPE
       SYNTAX Counter
       ACCESS read-only
       STATUS mandatory
       DESCRIPTION
        "The number of connections currently active."
       ::= {dtConnection 1}

    dtConnectionTable OBJECT-TYPE
       SYNTAX SEQUENCE OF DtConnectionEntry
       ACCESS not-accessible
       STATUS mandatory
       DESCRIPTION
        "The entries in the table are defined below, one row per connection."
       ::= {dtConnection 2}

    dtConnectionEntry OBJECT-TYPE
       SYNTAX DtConnectionEntry
       ACCESS not-accessible
       STATUS mandatory
       DESCRIPTION
        "An entry in the table dtConnectionTable."
       INDEX {dtConnectionIndex}
       ::= {dtConnectionTable 1}

    DtConnectionEntry ::= SEQUENCE {
       dtConnectionIndex
           INTEGER,
       dtconIpAddress
           IpAddress,
       dtconConnectTime 
           TimeTicks,
       dtconState
           INTEGER,
       dtconOpsInCmdQueue
           Gauge,
       dtconOpsInAckQueue
           Gauge,
       dtconOpsInRepQueue
           Gauge,
       dtconOpsInMirQueue
           Gauge,
       dtconBytesInRepQueue
           Gauge,
       dtconBytesInMirQueue
           Gauge,
       dtconOpsTx
           Counter,
       dtconBytesTx
           Counter,
       dtconOpsRx
           Counter,
       dtconBytesRx
           Counter,
       dtconResentOpCount
           Counter
    }

--
-- The entries
--
    dtConnectionIndex OBJECT-TYPE
       SYNTAX INTEGER (1..2147483647)
       ACCESS not-accessible
       STATUS mandatory
       DESCRIPTION
        "An index to uniquely identify the entry."
       ::= {dtConnectionEntry 1}

    dtconIpAddress OBJECT-TYPE
       SYNTAX IpAddress
       ACCESS read-only
       STATUS mandatory
       DESCRIPTION
        "Address of the machine on the other end of the connection, this is the key column in the table."
       ::= {dtConnectionEntry 2}

    dtconConnectTime OBJECT-TYPE
       SYNTAX TimeTicks
       ACCESS read-only
       STATUS mandatory
       DESCRIPTION
        "Amount of time (in seconds) connection has been active."
       ::= {dtConnectionEntry 3}

    dtconState OBJECT-TYPE
       SYNTAX INTEGER {
          conError(0),
          conActive(1),
          conPaused(2),
          conScheduled(3),
          conNone(4)
          }
       ACCESS read-only
       STATUS mandatory
       DESCRIPTION
        "Integer coded for the current state of the connection."
       ::= {dtConnectionEntry 4}

    dtconOpsInCmdQueue OBJECT-TYPE
       SYNTAX Gauge
       ACCESS read-only
       STATUS mandatory
       DESCRIPTION
        "The number of ops in the command/retransmit queue."
       ::= {dtConnectionEntry 5}

    dtconOpsInAckQueue OBJECT-TYPE
       SYNTAX Gauge
       ACCESS read-only
       STATUS mandatory
       DESCRIPTION
        "The number of ops awaiting acknowledgements."
       ::= {dtConnectionEntry 6}

    dtconOpsInRepQueue OBJECT-TYPE
       SYNTAX Gauge
       ACCESS read-only
       STATUS mandatory
       DESCRIPTION
        "The number of replication ops queued."
       ::= {dtConnectionEntry 7}

    dtconOpsInMirQueue OBJECT-TYPE
       SYNTAX Gauge
       ACCESS read-only
       STATUS mandatory
       DESCRIPTION
        "The number of mirror ops queued."
       ::= {dtConnectionEntry 8}

    dtconBytesInRepQueue OBJECT-TYPE
       SYNTAX Gauge
       ACCESS read-only
       STATUS mandatory
       DESCRIPTION
        "The number of bytes of data associated with the queued replication ops."
       ::= {dtConnectionEntry 9}

    dtconBytesInMirQueue OBJECT-TYPE
       SYNTAX Gauge
       ACCESS read-only
       STATUS mandatory
       DESCRIPTION
        "The number of bytes of data associated with the queued mirror ops."
       ::= {dtConnectionEntry 10}

    dtconOpsTx OBJECT-TYPE
       SYNTAX Counter
       ACCESS read-only
       STATUS mandatory
       DESCRIPTION
        "Total number of ops transmitted."
       ::= {dtConnectionEntry 11}

    dtconBytesTx OBJECT-TYPE
       SYNTAX Counter
       ACCESS read-only
       STATUS mandatory
       DESCRIPTION
        "Total number of bytes transmitted."
       ::= {dtConnectionEntry 12}

    dtconOpsRx OBJECT-TYPE
       SYNTAX Counter
       ACCESS read-only
       STATUS mandatory
       DESCRIPTION
        "Total number of ops received."
       ::= {dtConnectionEntry 13}

    dtconBytesRx OBJECT-TYPE
       SYNTAX Counter
       ACCESS read-only
       STATUS mandatory
       DESCRIPTION
        "Total number of bytes received."
       ::= {dtConnectionEntry 14}

    dtconResentOpCount OBJECT-TYPE
       SYNTAX Counter
       ACCESS read-only
       STATUS mandatory
       DESCRIPTION
        "Number of Ops that were resent because of ack errors."
       ::= {dtConnectionEntry 15}


--   ===============================================================
--   ===============================================================

--
-- Traps and Events
--

    dttrapKernelStarted TRAP-TYPE
       ENTERPRISE nsi
       DESCRIPTION
        "The Double-Take kernel has started."
    ::= 1

    dttrapKernelStopped TRAP-TYPE
       ENTERPRISE nsi
       DESCRIPTION
        "The Double-Take kernel has stopped."
    ::= 2

    dttrapLicenseViolationStartingSource TRAP-TYPE
       ENTERPRISE nsi
       DESCRIPTION
        "Double-Take source or target cannot be started due to a license violation."
    ::= 3

    dttrapLicenseViolationOnNetwork TRAP-TYPE
       ENTERPRISE nsi
       DESCRIPTION
        "A Double-Take serial number conflict was identified on the network."
    ::= 4

    dttrapSourceStarted TRAP-TYPE
       ENTERPRISE nsi
       DESCRIPTION
        "The Double-Take source module has started."
    ::= 5

    dttrapSourceStopped TRAP-TYPE
       ENTERPRISE nsi
       DESCRIPTION
        "The Double-Take source module has stopped."
    ::= 6

    dttrapTargetStarted TRAP-TYPE
       ENTERPRISE nsi
       DESCRIPTION
        "The Double-Take target module has started."
    ::= 7

    dttrapTargetStopped TRAP-TYPE
       ENTERPRISE nsi
       DESCRIPTION
        "The Double-Take target module is stopped."
    ::= 8

    dttrapConnectionRequested TRAP-TYPE
       ENTERPRISE nsi
       DESCRIPTION
        "A NetOriginator has attempted to connect to a NetResponder normally."
    ::= 9

    dttrapConnectionRequestReceived TRAP-TYPE
       ENTERPRISE nsi
       DESCRIPTION
        "A NetController received a request to start a new connection."
    ::= 10

    dttrapConnectionSucceded TRAP-TYPE
       ENTERPRISE nsi
       DESCRIPTION
        "A NetOriginator successfully achieved a connection."
    ::= 11

    dttrapConnectionPause TRAP-TYPE
       ENTERPRISE nsi
       DESCRIPTION
        "A Transmission was paused."
    ::= 12

    dttrapConnectionResume TRAP-TYPE
       ENTERPRISE nsi
       DESCRIPTION
        "A Transmission was resumed."
    ::= 13

    dttrapConnectionFailed TRAP-TYPE
       ENTERPRISE nsi
       DESCRIPTION
        "A NetOriginator was not successful in achieving a connection."
    ::= 14

    dttrapConnectionLost TRAP-TYPE
       ENTERPRISE nsi
       DESCRIPTION
        "A connection was lost by the NetOriginator or NetResponder."
    ::= 15

    dttrapMemoryLimitReached TRAP-TYPE
       ENTERPRISE nsi
       DESCRIPTION
        "The Double-Take memory pool limit was exceeded."
    ::= 16

    dttrapMemoryLimitRemedied TRAP-TYPE
       ENTERPRISE nsi
       DESCRIPTION
        "Memory has been freed to bring the Double-Take memory pool usage below the limit."
    ::= 17

    dttrapAutoReconnect TRAP-TYPE
       ENTERPRISE nsi
       DESCRIPTION
    "Auto reconnect needs to make a new connection."
    ::= 18

    dttrapScheduledConnectStart TRAP-TYPE
       ENTERPRISE nsi
       DESCRIPTION
    "Start of a scheduled connect period."
    ::= 19

    dttrapScheduledConnectEnd TRAP-TYPE
       ENTERPRISE nsi
       DESCRIPTION
        "End of a scheduled connect period."
    ::= 20

    dttrapAutoDisconnectWriteQueue TRAP-TYPE
       ENTERPRISE nsi
       DESCRIPTION
        "Auto disconnect forced a queue to be written to disk."
    ::= 21

    dttrapAutoDisconnectPauseTransmission TRAP-TYPE
       ENTERPRISE nsi
       DESCRIPTION
        "Auto disconnect requested a source to pause sending ops."
    ::= 22

    dttrapAutoDisconnectEndConnection TRAP-TYPE
       ENTERPRISE nsi
       DESCRIPTION
        "Auto disconnect dropped a connection."
    ::= 23

    dttrapAutoDisconnectShutdown TRAP-TYPE
       ENTERPRISE nsi
       DESCRIPTION
        "Auto disconnect was forced to shut down Double-Take."
    ::= 24

    dttrapReplicationStart TRAP-TYPE
       ENTERPRISE nsi
       DESCRIPTION
        "Replication was started on a connection."
    ::= 25

    dttrapReplicationStop TRAP-TYPE
       ENTERPRISE nsi
       DESCRIPTION
        "Replication was stopped on a connection."
    ::= 26

    dttrapMirrorStart TRAP-TYPE
       ENTERPRISE nsi
       DESCRIPTION
        "Mirroring was started on a connection."
    ::= 27

    dttrapMirrorStop TRAP-TYPE
       ENTERPRISE nsi
       DESCRIPTION
        "Mirroring was stopped on a connection."
    ::= 28

    dttrapMirrorPause TRAP-TYPE
       ENTERPRISE nsi
       DESCRIPTION
        "Mirroring was paused on a connection."
    ::= 29

    dttrapMirrorResume TRAP-TYPE
       ENTERPRISE nsi
       DESCRIPTION
        "Mirroring was resumed on a connection."
    ::= 30

--
-- Notice how the trap number for this is out of sequence?
-- This was added later.
-- It is best to add the number to the end but I want this
-- to appear with the other mirror traps in the mib file.
--
    dttrapMirrorEnd TRAP-TYPE
       ENTERPRISE nsi
       DESCRIPTION
        "Mirroring has ended on a connection."
    ::= 31


    dttrapVerificationStart TRAP-TYPE
       ENTERPRISE nsi
       DESCRIPTION
        "Verification was started."
    ::= 32

    dttrapVerificationEnd TRAP-TYPE
       ENTERPRISE nsi
       DESCRIPTION
        "Verification is finished."
    ::= 33

    dttrapVerficationFailure TRAP-TYPE
       ENTERPRISE nsi
       DESCRIPTION
        "Verification found the source and target out of sync."
    ::= 34

    dttrapRestoreStarted TRAP-TYPE
       ENTERPRISE nsi
       DESCRIPTION
        "Restoration has begun."
    ::= 35

    dttrapRestoreComplete TRAP-TYPE
       ENTERPRISE nsi
       DESCRIPTION
        "Restoration has finished."
    ::= 36

    dttrapRepSetModified TRAP-TYPE
       ENTERPRISE nsi
       DESCRIPTION
        "The replication set was modified."
    ::= 37

    dttrapFailoverConditionMet TRAP-TYPE
       ENTERPRISE nsi
       DESCRIPTION
        "A Failover Condition has been met.  User intervention is necessary!"
    ::= 38

    dttrapFailoverInProgress TRAP-TYPE
       ENTERPRISE nsi
       DESCRIPTION
        "Failover is in progress!"
    ::= 39
    
    dttrapTargetFull TRAP-TYPE
       ENTERPRISE nsi
       DESCRIPTION
       "Target is full."
    ::= 40

   END
