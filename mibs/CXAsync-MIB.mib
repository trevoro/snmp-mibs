CXAsync-MIB DEFINITIONS ::= BEGIN

--#CURRENT-VERSION 1

IMPORTS
   Counter         FROM RFC1155-SMI
   OBJECT-TYPE     FROM RFC-1212
   TRAP-TYPE               FROM RFC-1215
   DisplayString           FROM RFC1213-MIB
   cxAsync,SapIndex,Alias,ThruputClass
            FROM CXProduct-SMI;

-- Proprietary Data Types

PacketSize      ::=     INTEGER {
            bytes16         (4),
            bytes32         (5),
            bytes64         (6),
            bytes128        (7),
            bytes256        (8),
            bytes512        (9),
            bytes1024       (10),
            bytes2048       (11),
            bytes4096       (12)
            }
YesNo           ::=     INTEGER {
            no              (1),
            yes             (2)
            }
ProfIndex       ::=     INTEGER (1..255)
DteIndex        ::=     INTEGER (1..255)


asyX25TxQThreshold OBJECT-TYPE
   SYNTAX  INTEGER (1..255)
   ACCESS  read-write
   STATUS  mandatory
   DESCRIPTION
"Defines the global X.25 queue 
threshold, in number of frames.

When the threshold is exceeded and the SAP (service access point) object 
asySapNetworkFlowControlState is in the Flow Control On state, a Disconnect 
Request, for SVC (switch virtual circuits), or a Reset Request, for PVC 
(permanent virtual circuits), takes place at the X.25 layer.

Range of Values: 1 - 255

Default Value: 10

Configuration Changed: Administrative "

   DEFVAL { 10 }
   ::= { cxAsync 1 }


asyPadIdBanner OBJECT-TYPE
   SYNTAX  DisplayString (SIZE (1..255))
   ACCESS  read-write
   STATUS  mandatory
   DESCRIPTION
"Defines the Async PAD Identification Banner.  This banner is transmitted to the attached
device whenever it raises interface signals.

Range of Values: 1 - 255

Default Value: 
Async PAD

Configuration Changed: Operative "
   DEFVAL {"Async PAD"} 
   ::= { cxAsync 2 }


asyAlarms OBJECT-TYPE
   SYNTAX  INTEGER {
            disabled        (1),
            enable          (2)
            }
   ACCESS  read-write
   STATUS  mandatory
   DESCRIPTION
"Indicates whether this layer produces the object asySapAlarm trap.

Options: 
disabled (1)

enable (2)

Default Value: disable

Configuration Changed: Administrative "
   DEFVAL { disabled }
   ::= { cxAsync 7 }


asySapStatusEvent OBJECT-TYPE
   SYNTAX  INTEGER {
            noEvent        (1)
            }
   ACCESS  read-only
   STATUS  mandatory
   DESCRIPTION
"Identifies the status generated in the object asyAlarmTrap.

This object is used for identification by the trap when it occurs and will 
always return the value noEvent when read."
   ::= { cxAsync 8 }


asySoftwareVersions OBJECT-TYPE
   SYNTAX  DisplayString
   ACCESS  read-only
   STATUS  mandatory
   DESCRIPTION
"Identifies the revision numbers of the Async layer software.

This is a read-only parameter that displays the revision number as a string 
of five numbers.  Each number is separated by a period and is identified 
as follows:

1. main version number

2. main revision number

3. branch version number

4. branch revision number

5. part number"
   ::= { cxAsync 9 }


asyMibLevel OBJECT-TYPE
   SYNTAX  INTEGER
   ACCESS  read-only
   STATUS  mandatory
   DESCRIPTION
"Used to determine current MIB module release supported
by the agent. Object is in decimal."
   --#STARTING-VERSION 1
   ::= { cxAsync 10 }


-- gap (10) for future global parameters



--  Async Service Access Point Configuration Table

--  The table describing:
--      parameters required to configure an async service access point
--      controls available to manipulate an async service access point
--      status available for monitoring the current state of an async 
--      service access point statistics available for monitoring any 
--      async service access point.
--    Service access points of this type exist at the lower interface of 
--      the Async layer, and are usually used to communicate with the 
--      Media Access Control (MAC) layer.


asySapTable OBJECT-TYPE
   SYNTAX  SEQUENCE OF AsySapEntry
   ACCESS  not-accessible
   STATUS  mandatory
   DESCRIPTION
"Contains configuration information about each Async layer SAP (service 
access point)."
   ::= { cxAsync 20 }


   asySapEntry OBJECT-TYPE
      SYNTAX  AsySapEntry
      ACCESS  not-accessible
      STATUS  mandatory
      DESCRIPTION
"Contains the parameters for a specific Async layer SAP (service access point)."
      INDEX { asySapNumber }
      ::= { asySapTable 1 }


   AsySapEntry ::=
      SEQUENCE { 
 -- Parameters
         asySapNumber                            SapIndex,
         asySapRowStatus                         INTEGER,
         asySapAlias                             Alias,
         asySapMCompanionAlias                   Alias,
         asySapNCompanionAlias                   Alias,
         asySapX3Profile                         INTEGER,
         asySapNUI                               DisplayString,
         asySapAddress                           DisplayString,
         asySapDisconnectRequest                 YesNo,
         asySapTxThruputClass                    ThruputClass,
         asySapRxThruputClass                    ThruputClass,   
         asySapTxPacketSize                      PacketSize,
         asySapRxPacketSize                      PacketSize,
         asySapTxWindowSize                      INTEGER,
         asySapRxWindowSize                      INTEGER,   
         asySapYTTimer                           INTEGER,
         asySapSRTimer                           INTEGER,
         asySapNUILength                         INTEGER,
         asySapReverseChargingAcceptance         YesNo,
         asySapChargingInformation               YesNo,
         asySapSubscriptionCUG                   YesNo,
         asySapSubscriptionCUGOA                 YesNo,
         asySapSubscriptionCUGIA                 YesNo,
         asySapPreferentialCUGIndex              INTEGER,
         asySapReceiptConfirmation               INTEGER,
         asySapEnableProtocolId                  YesNo,
         asySapProtocolId                DisplayString,
         asySapPromptSignal                      DisplayString,
         asySapAutoConnectDteId                  DisplayString,
         asySapAutoConnectRetry                  INTEGER,
         asySapAutoConnectDelayTimer             INTEGER,
         asySapHardwareFlowControl               YesNo,
         asySapProtocolType			INTEGER,
-- Control
         asySapControl                                           INTEGER,
-- Status
         asySapState                             INTEGER,
         asySapAsyncFlowControlState             INTEGER,
         asySapNetworkFlowControlState           INTEGER,
         asySapAsyncTxQueueSize                  Counter,
         asySapX25TxQueueSize                    Counter,
-- Statistics
         asySapNumberConnects                    Counter,
         asySapNumberDisconnects                 Counter,
         asySapTxDataCharacters                  Counter,
         asySapRxDataCharacters                  Counter,
         asySapParityErrors                      Counter,
         asySapOverruns                          Counter,
         asySapFlowControlByUser                 Counter,
         asySapFlowControlByX25                  Counter,
         asySapFlowControlToUser                 Counter,
         asySapFlowControlToX25                  Counter,
         asySapRxReset                           Counter,
         asySapRxBreak                           Counter,
         asySapTxBreak                           Counter,
         asySapRxDiscardCharacters       	Counter
         }



   asySapNumber OBJECT-TYPE
      SYNTAX  SapIndex
      ACCESS  read-only
      STATUS  mandatory
      DESCRIPTION
"Indicates the table row containing configuration or monitoring objects for 
a SAP (service access point) associated with the slot of a card, a port of this 
card, and a logical channel on this port. 

Range of Values: 11x to 71x

Note: First number is the slot, second number is the port, and x is the
logical channel.

Default Value: None"
      ::= { asySapEntry 1 }


   asySapRowStatus OBJECT-TYPE
      SYNTAX  INTEGER {
               invalid         (1),
               valid           (2)
               }
      ACCESS  read-write
      STATUS  mandatory
      DESCRIPTION
"Indicates whether or not this specific entry is configured within the MIB.

Options: 
invalid (1): Row is flagged and deleted from the table after the next reset.

valid (2): Parameter is added or modified if it already exists in the table.

Default Value: valid

Configuration Changed: Operative for valid entry and administrative for 
invalid entry "
      ::= { asySapEntry 2 }


   asySapAlias OBJECT-TYPE
      SYNTAX  Alias
      ACCESS  read-write
      STATUS  mandatory
      DESCRIPTION
"Determines the name which uniquely identifies the SAP (service access 
point).

Range of Values: 1 to 16 alphanumeric characters beginning with an
alpha character

Default Value: none

Configuration Changed: Administrative "
      ::= { asySapEntry 3 }


   asySapMCompanionAlias OBJECT-TYPE
      SYNTAX  Alias
      ACCESS  read-write
      STATUS  mandatory
      DESCRIPTION
"Determines the name which uniquely identifies the companion MAC SAP 
(service access point) which will communicate with this SAP.

Range of Values: 1 to 16 alphanumeric characters beginning with an
alpha character

Default Value: none

Changed: Administrative "
      ::= { asySapEntry 4 }

   asySapNCompanionAlias OBJECT-TYPE
      SYNTAX  Alias
      ACCESS  read-write
      STATUS  mandatory
      DESCRIPTION
"Determines the name which uniquely identifies the X.25 SAP (service access 
point) which will communicate with this SAP.

Range of Values: 1 to 16 alphanumeric characters beginning with an
alpha character

Default Value: none

Configuration Changed: Administrative "
      ::= { asySapEntry 5 }



   asySapX3Profile OBJECT-TYPE
      SYNTAX  INTEGER (1..255)
      ACCESS  read-write
      STATUS  mandatory
      DESCRIPTION
"Tells the SAP (service access point) which set of X.3 parameters to use.

Range of Values: 1 - 255

Default Value: 92

Configuration Changed: Operative "
      DEFVAL { 92 }
      ::= { asySapEntry 6 }


   asySapNUI OBJECT-TYPE
      SYNTAX  DisplayString (SIZE (0..14))
      ACCESS  read-write
      STATUS  mandatory
      DESCRIPTION
"Defines the Network User ID for this SAP (service access point).

Options: 1 to 14 alphanumeric characters

Default Value: 0

Configuration Changed: Operative "
       DEFVAL {""}
      ::= { asySapEntry 7 }


   asySapAddress OBJECT-TYPE
      SYNTAX  DisplayString (SIZE (0..15))
      ACCESS  read-write
      STATUS  mandatory
      DESCRIPTION
"Defines the calling address for this SAP (service access point).

Range of Values: 1 to 15 digits

Default Value: 0

Configuration Changed: Operative "
       DEFVAL {""}
      ::= { asySapEntry 8 }


asySapDisconnectRequest OBJECT-TYPE
      SYNTAX  YesNo
      ACCESS  read-write
      STATUS  mandatory
      DESCRIPTION
"Sends a Disconnect Request to the MAC layer when the YT timer expires.

Options: 
Yes = Enable the disconnect request
No = Disable the disconnect request

Default Value: No

Configuration Changed: Operative "
      DEFVAL { no }
      ::= { asySapEntry 9}


   asySapRxThruputClass OBJECT-TYPE
      SYNTAX  ThruputClass
      ACCESS  read-write
      STATUS  mandatory
      DESCRIPTION
"Defines the default receive throughput class that is used at this SAP (service 
access point).

Range of Values: 75 - 64000 bps

Default Value: 9600 bps

Configuration Changed: Operative "
      REFERENCE  "CCITT(1988) Section 7.2.2.2 and Table 30/X.25"
      DEFVAL { bps9600 }
      ::= { asySapEntry 10 }


   asySapTxThruputClass OBJECT-TYPE
      SYNTAX  ThruputClass
      ACCESS  read-write
      STATUS  mandatory
      DESCRIPTION
"Defines the default transmit throughput class that is used at this SAP 
(service access point).

Range of Values: 75 to 64000 bps

Default Value: 9600 bps

Configuration Changed: Operative "
      REFERENCE  "CCITT(1988) Section 7.2.2.2 and Table 30/X.25"
      DEFVAL { bps9600 }
      ::= { asySapEntry 11 }


   asySapTxPacketSize OBJECT-TYPE
      SYNTAX  PacketSize
      ACCESS  read-write
      STATUS  mandatory
      DESCRIPTION
"Defines the size of the transmit packet for the Async layer.

Range of Values: 16 to 4096 bytes

Default Value: 128 bytes

Configuration Changed: Operative "
      DEFVAL { bytes128 }
      ::= { asySapEntry 12}

   
   asySapRxPacketSize OBJECT-TYPE
      SYNTAX  PacketSize
      ACCESS  read-write
      STATUS  mandatory
      DESCRIPTION
"Defines the size of the receive packet for the Async layer.

Range of Values: 16 to 4096 bytes

Default Value: 128 bytes

Configuration Changed: Operative "
      DEFVAL { bytes128 }
      ::= { asySapEntry 13 }


   asySapTxWindowSize OBJECT-TYPE
      SYNTAX  INTEGER (1..127)
      ACCESS  read-write
      STATUS  mandatory
      DESCRIPTION
"Defines the size of the transmit window for the Async layer.  

Range of Values: 1 to 127

Default Value: 2

Configuration Changed: Operative "
      DEFVAL { 2 }
      ::= { asySapEntry 14 }


   asySapRxWindowSize OBJECT-TYPE
      SYNTAX  INTEGER (1..127)
      ACCESS  read-write
      STATUS  mandatory
      DESCRIPTION
"Defines the size of the receive window for the Async layer.  

Range of Values: 1 to 127

Default Value: 2

Configuration Changed: Operative "
      DEFVAL { 2 }
      ::= { asySapEntry 15 }


   asySapYTTimer OBJECT-TYPE
      SYNTAX  INTEGER (0..255)
      ACCESS  read-write
      STATUS  mandatory
      DESCRIPTION
"Defines the time of inactivity, in seconds, after which the SAP (service 
access point) will send a disconnect request to the MAC layer.  The timer 
starts when the line is enabled or the virtual circuit is cleared and stops 
when the first character of a command is entered.

Range of Values: 0 to 255

Note: A value of 0 means that the timer is disabled.

Default Value: 60

Configuration Changed: Operative "
      REFERENCE  "CCITT X.28 Annex B Table B-1/X.28."
      DEFVAL { 60 }
      ::= { asySapEntry 16 }


   asySapSRTimer OBJECT-TYPE
      SYNTAX  INTEGER (0..255)
      ACCESS  read-write
      STATUS  mandatory
      DESCRIPTION
"Defines the time of inactivity, in seconds, between command characters. 
The timer starts when the command mode is entered or when a character of a 
command is entered and stops when a command is entered or when data mode is 
entered. A time-out will generate an error message.

Range of Values: 0 to 255

Note: A value of 0 means that the timer is disabled.

Default Value: 60

Configuration Changed: Operative "
      REFERENCE  "CCITT X.28 Annex B Table B-1/X.28."
      DEFVAL { 60 }
      ::= { asySapEntry 17 }


   asySapNUILength OBJECT-TYPE
      SYNTAX  INTEGER (0..14)
      ACCESS  read-write
      STATUS  obsolete
      DESCRIPTION
"Defines the length, in nibbles, allowed for the Network User ID.

Range of Values: 1 to 14

Default Value: 0

Configuration Changed: Operative "
      DEFVAL { 0 }
      ::= { asySapEntry 18 }


   asySapReverseChargingAcceptance OBJECT-TYPE
      SYNTAX  YesNo
      ACCESS  read-write
      STATUS  mandatory
      DESCRIPTION
"Authorizes the DCE (Async application) to transmit incoming calls to the DTE 
(Async user) that requested the reverse charging, if reverse charging acceptance 
is allowed.  If acceptance is not allowed, the DCE (Async application) 
will not transmit the incoming calls to the DTE which requested the reverse 
charging.

Options: 
Yes

No

Default Value: No

Configuration Changed: Operative "
      REFERENCE     "CCITT X.25 6.19"
      DEFVAL { no }
      ::= { asySapEntry 19 }


   asySapChargingInformation OBJECT-TYPE
      SYNTAX  YesNo
      ACCESS  read-write
      STATUS  mandatory
      DESCRIPTION
"Authorizes the DCE (Async application) to send charging information to the DTE 
(user) with the Clear Indication or Clear Confirmation packet.

Options: 
Yes

No

Default Value: No

Configuration Changed: Operative "
      REFERENCE       "CCITT X.25 6.22"
      DEFVAL { no }
      ::= { asySapEntry 20 }


   asySapSubscriptionCUG OBJECT-TYPE
      SYNTAX  YesNo
      ACCESS  read-write
      STATUS  mandatory
      DESCRIPTION
"Enables the DTE (User) to subscribe to one or more CUGs (Closed User Groups).  

A CUG permits the DTEs belonging to the group to communicate with each other in 
the group but prevents communication with all other DTEs.

Options: 
Yes

No

Default Value: No

Configuration Changed: Operative "
      REFERENCE       "CCITT X.25 6.14.1"
      DEFVAL { no }
      ::= { asySapEntry 21 }


   asySapSubscriptionCUGOA OBJECT-TYPE
      SYNTAX  YesNo
      ACCESS  read-write
      STATUS  mandatory
      DESCRIPTION
"Enables the DTE (user) to subscribe to one or more CUGs (Closed User Groups), 
as in object asySapSubscriptionCUG, with outgoing access.  

The DTE can originate virtual calls to DTEs in the open part of the network 
(DTEs not belonging to a CUG), and to DTEs belonging to other CUGs with 
incoming access capability.

Options: 
Yes

No

Default Value: No

Configuration Changed: Operative "
      REFERENCE       "CCITT X.25 6.14.2"
      DEFVAL { no }
      ::= { asySapEntry 22 }


   asySapSubscriptionCUGIA OBJECT-TYPE
      SYNTAX  YesNo
      ACCESS  read-write
      STATUS  mandatory
      DESCRIPTION
"Enables the DTE (user) to subscribe to one or more CUGs (Closed User Groups), 
as in object asySapSubscriptionCUG, with incoming access.  

The DTE can receive incoming calls from DTEs in the open part of the network 
(DTEs not belonging to a CUG), and from DTEs belonging to other CUGs with 
outgoing access capability.

Options: 
Yes

No

Default Value: No

Configuration Changed: Operative "
      REFERENCE       "CCITT X.25 6.14.3"
      DEFVAL { no }
      ::= { asySapEntry 23 }


   asySapPreferentialCUGIndex OBJECT-TYPE
      SYNTAX  INTEGER (0..99)
      ACCESS  read-write
      STATUS  mandatory
      DESCRIPTION
"Defines the preferential CUG (Closed 
User Group) for a DTE (user) with a CUG, 
CUGOA or CUGIA subscription.

Range of Values: 0 to 99

Note: 0 = No preferential CUG, 1 to 99 = Basic format values allowed

Default Value: 0

Configuration Changed: Operative "
      REFERENCE       "CCITT X.25 6.14.1"
      DEFVAL { 0 }
      ::= { asySapEntry 24 }



   asySapReceiptConfirmation OBJECT-TYPE
      SYNTAX  INTEGER {
               noAck           (1),
               dBit            (2),
               localAck        (3),
               xmitAck         (4)
               }
      ACCESS  read-write
      STATUS  mandatory
      DESCRIPTION
"Tells the X.25 layer which receipt confirmation value is required by this 
SAP (service access point).

Options: 
noAck

dBit

localAck

xmitAck

Default Value: noAck

Configuration Changed: Operative "
      DEFVAL { noAck }
      ::= { asySapEntry 25 }


   asySapEnableProtocolId OBJECT-TYPE
      SYNTAX  YesNo
      ACCESS  read-write
      STATUS  mandatory
      DESCRIPTION
"Controls whether or not the Protocol ID field of the user data is inserted by 
the Async layer.  

Options: 
enable = Allows up to 12 bytes, or 124 bytes for fast select, of user data for 
the X.28 value command where the Protocol ID field of the user data is 
inserted by the Async layer

disable = Allows up to 16 bytes, or 128 bytes for fast select, of user data for 
the X.28 value command where the Protocol ID field of the user data is 
not inserted by the Async layer)

Default Value: enable

Configuration Changed: Operative "
      REFERENCE       "CCITT X.29 1.3, 4.2"
      DEFVAL { yes }
      ::= { asySapEntry 26 }


   asySapProtocolId OBJECT-TYPE
      SYNTAX DisplayString (SIZE (7..11))
      ACCESS  read-write
      STATUS  mandatory
      DESCRIPTION
"Defines the protocol format that is used for incoming call or call request 
packets to the X.25 call data field. 

The field consists of 4 hexadecimal octets where the first octet is coded as 
follows:

bits 8 & 7

- 00 for CCITT use
- 01 for national use
- 10 reserved for international user bodies
- 11 for DTE-DTE use

When bits 8 & 7 are equal to 00, bits 6 to 1 will be equal to 000001.  The first 
octet is shown as 01, 00, 00, 00.  The first 0 in each number is optional and 
may be shown as 1, 0, 0, 0.

All bits of octets 2, 3 and 4 are set to 0.  They are reserved as a future 
mechanism for providing the called PAD or packet mode DTE (user) with 
additional information pertaining to the calling party.

Default Value:   01,00,00,00

Configuration Changed: Operative "
      REFERENCE       "CCITT X.28 3.1.3, X.29 4.2"
      DEFVAL { "01,00,00,00" }
      ::= { asySapEntry 27 }

   asySapPromptSignal      OBJECT-TYPE
      SYNTAX  DisplayString (SIZE (1..16))
      ACCESS  read-write
      STATUS  mandatory
      DESCRIPTION
"Defines the prompt PAD service signal (banner) that is sent to the MAC layer 
whenever the Async PAD enters a PAD waiting state or waiting for command state.

Options: 1 to 16 alphanumeric characters

Default Value: Character 2/10 (*)

Configuration Changed: Operative "
      REFERENCE       "CCITT X.28 3.1.3, 3.5.23"
      DEFVAL {"*"}
      ::= { asySapEntry 28 }


   asySapAutoConnectDteId OBJECT-TYPE
      SYNTAX  DisplayString
      ACCESS  read-write
      STATUS  mandatory
      DESCRIPTION
"Identifies the remote DTE (by name) to be connected to whenever the async 
sap receives a Connect Indication or Connect Confirm from the MAC layer.  
If no name is identified the Auto Connect is disabled for this sap"
      DEFVAL {"" }
      ::= { asySapEntry 29 }


   asySapAutoConnectRetry OBJECT-TYPE
      SYNTAX  INTEGER (0..100)
      ACCESS  read-write
      STATUS  mandatory
      DESCRIPTION
"Defines the number of times this async sap will try to connect (if Connect 
Accept is not received from the X.25 layer) to the remote DTE defined by the 
object asySapAutoConnectDteId whenever the async sap receives a Connect 
Indication or Connect Confirm from the MAC layer. The async sap will wait 
the asySapAutoConnectDelayTimer before trying to connect. a value of '0' 
means continuous retries." 
      DEFVAL { 10 }
      ::= { asySapEntry 30 }


   asySapAutoConnectDelayTimer OBJECT-TYPE
      SYNTAX  INTEGER (1..60)
      ACCESS  read-write
      STATUS  mandatory
      DESCRIPTION
"Defines the time in seconds this async sap will wait before trying to 
connect to the remote DTE defined by the object asySapAutoConnectDteId 
whenever the async sap receives a Connect Indication or Connect Confirm 
from the MAC layer. " 
      DEFVAL { 5 }
      ::= { asySapEntry 31 }


   asySapHardwareFlowControl OBJECT-TYPE
      SYNTAX  YesNo
      ACCESS  read-write
      STATUS  mandatory
      DESCRIPTION
"Enables the MAC to flow control the device via the EIA RTS/CTS signal.

Options: 
Yes

No

Default Value: No

Configuration Changed: Operative "
      DEFVAL { no }
      ::= { asySapEntry 32 }


asySapProtocolType OBJECT-TYPE
SYNTAX  INTEGER {
               normal         	   (1),
               iocProtocol         (2),
               modifiedudf         (3)
	}
      ACCESS  read-write
      STATUS  mandatory
      DESCRIPTION
"Defines the Async Protocol type for this sap.

Options: 
normal (1)  for Normal Async (X.3, X.28, X.29) protocol.

iocProtocol (2) for IOC Protocol.

ModifiedUDF (3) for the Modified IOC Protocol.

Default Value: 1

Configuration Changed: Operative "
      DEFVAL { normal }
      --#STARTING-VERSION 1
      ::= { asySapEntry 33 }


-- gap (4)   for future configuration objects

   asySapControl OBJECT-TYPE
      SYNTAX  INTEGER {
               clearStats              (1),
               enableSap               (2),
               disableSapImmediately   (3),
               disableSapGracefully    (4)
               }
      ACCESS  write-only
      STATUS  mandatory
      DESCRIPTION
"Defines the control that is used with 
the specified Async layer SAP (service 
access point).

Options:
clearStats (1): Zeros all the statistic counters for this SAP.

enableSAP (2): Enables the transmission and reception of data to and from the 
SAP.

disableSAPImmediately (3): Disables the transmission and reception of data to 
and from the SAP and any open virtual calls are cleared immediately.

disableSAPGracefully (4): Disables the transmission and reception of data to 
and from SAP after the virtual call has been cleared by the X.28 or network 
layer interface.

Configuration Changed: Operative "
      ::= { asySapEntry 37 }

-- gap (2)   future control objects

   asySapState OBJECT-TYPE
      SYNTAX  INTEGER {
            disconnected    (1),
            enabled         (2),
            connecting      (3),
            dataTransfer    (4),
            resetting       (5)
            }
      ACCESS  read-only
      STATUS  mandatory
      DESCRIPTION
"Indicates the current state of the Async layer SAP(service access point).

Options:
disconnected (1)

enabled (2)

connecting (3)

data Transfer (4)

resetting (5)

Default Value None"
      ::= { asySapEntry 40 }


   asySapAsyncFlowControlState OBJECT-TYPE
      SYNTAX  INTEGER {
               flowControlOff  (1),
               flowControlOn   (2)
               }
      ACCESS  read-only
      STATUS  mandatory
      DESCRIPTION
"Indicates whether this SAP (service access point) was forced to initiate 
flow control procedures by the MAC (media access control) layer.  

Options:
flowControlOff (1)

flowControlOn (2)

Note: 
When flow control is forced at this SAP, this object takes on the value, 
flowControlOn.

Default Value: flowControlOff"
      ::= { asySapEntry 41 }


   asySapNetworkFlowControlState OBJECT-TYPE
      SYNTAX  INTEGER {
               flowControlOff  (1),
               flowControlOn   (2)
               }
      ACCESS  read-only
      STATUS  mandatory
      DESCRIPTION
"Indicates whether or not this SAP (service access point) was forced to 
initiate flow control procedures by the network layer.  

Options: 
flowControlOff (1)

flowControlON (2)

Note: When flow control is forced at this SAP, this object takes on the value, 
flowControlOn."
      ::= { asySapEntry 42 }



   asySapAsyncTxQueueSize OBJECT-TYPE
      SYNTAX  Counter
      ACCESS  read-only
      STATUS  mandatory
      DESCRIPTION
"Indicates the current number of frames to be transmitted to the MAC (media 
access control) layer."
      ::= { asySapEntry 43 }


   asySapX25TxQueueSize OBJECT-TYPE
      SYNTAX  Counter
      ACCESS  read-only
      STATUS  mandatory
      DESCRIPTION
"Indicates the current number of frames to be send to the network layer."
      ::= { asySapEntry 44 }

-- gap (5)  for future status objects

   asySapNumberConnects OBJECT-TYPE
      SYNTAX  Counter
      ACCESS  read-only
      STATUS  mandatory
      DESCRIPTION
"Indicates the number of call attempts by this SAP (service access point)."
      ::= { asySapEntry 50 }


   asySapNumberDisconnects OBJECT-TYPE
      SYNTAX  Counter
      ACCESS  read-only
      STATUS  mandatory
      DESCRIPTION
"Indicates the number of disconnects for this SAP (service access point)."
      ::= { asySapEntry 51 }


   asySapTxDataCharacters OBJECT-TYPE
      SYNTAX  Counter
      ACCESS  read-only
      STATUS  mandatory
      DESCRIPTION
"Indicates the number of data characters that were transmitted from this SAP 
(service access point) to the MAC layer."
      ::= { asySapEntry  52 }


   asySapRxDataCharacters OBJECT-TYPE
      SYNTAX  Counter
      ACCESS  read-only
      STATUS  mandatory
      DESCRIPTION
"Indicates the number of data characters that were received at this SAP (service 
access point) from the MAC layer."
      ::= { asySapEntry  53 }


   asySapParityErrors OBJECT-TYPE
      SYNTAX  Counter
      ACCESS  read-only
      STATUS  mandatory
      DESCRIPTION
"Indicates the number of characters with parity errors that were received at this 
SAP (service access point)."
      ::= { asySapEntry  54 }


   asySapOverruns OBJECT-TYPE
      SYNTAX  Counter
      ACCESS  read-only
      STATUS  mandatory
      DESCRIPTION
"Indicates the number of characters with overrun errors that were received at 
this SAP (service access point)."
      ::= { asySapEntry  55 }


   asySapFlowControlByUser OBJECT-TYPE
      SYNTAX  Counter
      ACCESS  read-only
      STATUS  mandatory
      DESCRIPTION
"Indicates the number of flow control characters that were received by this 
SAP (service access point) from the Async port."
      ::= { asySapEntry  56 }


   asySapFlowControlByX25 OBJECT-TYPE
      SYNTAX  Counter
      ACCESS  read-only
      STATUS  mandatory
      DESCRIPTION
"Indicates the number of flow control messages that were received by this SAP
(service access point) from the network layer."
      ::= { asySapEntry  57 }


   asySapFlowControlToUser OBJECT-TYPE
      SYNTAX  Counter
      ACCESS  read-only
      STATUS  mandatory
      DESCRIPTION
"Indicates the number of flow control characters that were transmitted by this 
SAP (service access point) to the Async port."
      ::= { asySapEntry  58 }


   asySapFlowControlToX25 OBJECT-TYPE
      SYNTAX  Counter
      ACCESS  read-only
      STATUS  mandatory
      DESCRIPTION
"Indicates the number of flow control messages that were sent by this SAP 
(service access point) to the network layer."
      ::= { asySapEntry  59 }


   asySapRxReset OBJECT-TYPE
      SYNTAX  Counter
      ACCESS  read-only
      STATUS  mandatory
      DESCRIPTION
"Indicates the number of resets that were received at this SAP (service 
access point) from the network layer."
      ::= { asySapEntry  60 }


   asySapRxBreak OBJECT-TYPE
      SYNTAX  Counter
      ACCESS  read-only
      STATUS  mandatory
      DESCRIPTION
"Indicates the number of breaks that were received at this SAP (service 
access point)."
      ::= { asySapEntry  61 }


   asySapTxBreak OBJECT-TYPE
      SYNTAX  Counter
      ACCESS  read-only
      STATUS  mandatory
      DESCRIPTION
"Indicates the number of breaks that were transmitted from this SAP (service 
access point)."
      ::= { asySapEntry  62 }


asySapRxDiscardCharacters OBJECT-TYPE
      SYNTAX  Counter
      ACCESS  read-only
      STATUS  mandatory
      DESCRIPTION
"Indicates the number of discard characters that were received at this SAP (service 
access point)."
      ::= { asySapEntry  63 }



--  X.3 Profile Configuration Table

--  The table describing:
--      parameters required to configure an X.3 profile

--    Service access points of this type are referenced at the lower 
--      interface of the Async layer with parameter 'asySapX3profile'.

asyProfTable OBJECT-TYPE
   SYNTAX  SEQUENCE OF AsyProfEntry
   ACCESS  not-accessible
   STATUS  mandatory
   DESCRIPTION
"Contains the X.3 parameters for each defined X.3 profile."
   ::= { cxAsync 21 }


   asyProfEntry OBJECT-TYPE
      SYNTAX  AsyProfEntry
      ACCESS  not-accessible
      STATUS  mandatory
      DESCRIPTION
"Provides the parameters for a specific X.3 profile SAP (service access point)."
      INDEX { asyProfNumber }
      ::= { asyProfTable 1 }


   AsyProfEntry ::=
      SEQUENCE {
 -- Parameters
         asyProfNumber                   ProfIndex,
         asyProfRowStatus                INTEGER,
         asyProfAlias                    Alias,
         asyProfParameter1               INTEGER,
         asyProfParameter2               INTEGER,
         asyProfParameter3               INTEGER,
         asyProfParameter4               INTEGER,
         asyProfParameter5               INTEGER,
         asyProfParameter6               INTEGER,
         asyProfParameter7               INTEGER,
         asyProfParameter8               INTEGER,
         asyProfParameter9               INTEGER,
         asyProfParameter10              INTEGER,
         asyProfParameter11              INTEGER,
         asyProfParameter12              INTEGER,
         asyProfParameter13              INTEGER,
         asyProfParameter14              INTEGER,
         asyProfParameter15              INTEGER,
         asyProfParameter16              INTEGER,
         asyProfParameter17              INTEGER,
         asyProfParameter18              INTEGER,
         asyProfParameter19              INTEGER,
         asyProfParameter20              INTEGER,
         asyProfParameter21              INTEGER,
         asyProfParameter22              INTEGER,
         asyProfParameter23              INTEGER,
         asyProfParameter24              INTEGER,
         asyProfParameter25              INTEGER,
         asyProfParameter26              INTEGER,
         asyProfParameter27              INTEGER,
         asyProfParameter28              INTEGER
         }


   asyProfNumber OBJECT-TYPE
      SYNTAX  ProfIndex
      ACCESS  read-only
      STATUS  mandatory
      DESCRIPTION
"Identifies the profile SAP (service access point) using a unique numerical value."
      ::= { asyProfEntry 1 }


   asyProfRowStatus OBJECT-TYPE
      SYNTAX  INTEGER {
               invalid         (1),
               valid           (2)
               }
      ACCESS  read-write
      STATUS  mandatory
      DESCRIPTION
"Indicates whether or not this specific entry is configured within the MIB. 

Options:
invalid (1): Row is flagged and deleted from the table after the next reset

valid (1): Parameter is added or modified if it already exists in the table

Default Value: valid "
      ::= { asyProfEntry 2 }


   asyProfAlias OBJECT-TYPE
      SYNTAX  Alias
      ACCESS  read-write
      STATUS  mandatory
      DESCRIPTION
"Identifies the SAP (service access point) using a unique textual name.

Range of Values: 1 to 16 alphanumeric characters beginning with an
alpha character

Default Value: 0

Configuration Changed: Administrative "
      ::= { asyProfEntry 3 }


   asyProfParameter1 OBJECT-TYPE
      SYNTAX  INTEGER  (0..126)
      ACCESS  read-write
      STATUS  mandatory
      DESCRIPTION
"Defines the X.3 parameter 1, PAD recall using a character.  This parameter 
allows the start-stop mode DTE (user) to initiate an escape from the data 
transfer or the connection in progress state in order to send PAD command 
signals.

Range of Values:
0 = Not possible
1 = Character DLE
32 to 126 = Graphic character defined by user

Default Value: 0

Configuration Changed: Operative "
      REFERENCE       "CCITT X.3 Table 1"    
      DEFVAL { 0 }
      ::= { asyProfEntry 5 }


   asyProfParameter2 OBJECT-TYPE
      SYNTAX  INTEGER  (0..1)
      ACCESS  read-write
      STATUS  mandatory
      DESCRIPTION
"Defines the X.3 parameter 2, Echo.  This parameter provides for characters 
received from the start-stop mode DTE (user) to be transmitted back to the 
start-stop mode DTE as well as being interpreted by the PAD.

Options: 
0 = No echo
1 = Echo

Default Value: No echo

Configuration Changed: Operative "
      REFERENCE       "CCITT X.3 Table 1"    
      DEFVAL { 0 }
       ::= { asyProfEntry 6 }


   asyProfParameter3 OBJECT-TYPE
      SYNTAX  INTEGER  (0..126)
      ACCESS  read-write
      STATUS  mandatory
         DESCRIPTION
"Defines the X.3 parameter 3, Selection of data forwarding character(s).  This 
parameter allows the selection of defined sets of characters received from 
the start-stop mode DTE (user) to be recognized by the PAD as an indication 
to complete the assembly and forward a complete packet

Range of Values:
0: No data forwarding character(s)
1: Alphanumeric characters  (A-Z, a-z and 0-9)
2: Character CR
4: Characters ESC, BEL, ENQ and ACK
6: Characters CR, ESC, BEL, ENQ and ACK
8: Characters DEL, CAN and DC2
16: Characters ETX and EOT
18: Characters CR, ETX and EOT
32: Characters HT, LF, VT and FF
64: All characters in columns 0 and 1 of IA5 except those shown for 
	values 2, 4, 8 and 32
126: All characters in columns 0 and 1 and character DEL

Note: Some values are combinations of other values (i.e., value 18 is 
a combination of values 2 and 16).

Default Value: 0

Configuration Changed: Operative "
      REFERENCE       "CCITT X.3 Table 1"    
      DEFVAL { 0 }
         ::= { asyProfEntry 7 }


   asyProfParameter4 OBJECT-TYPE
      SYNTAX  INTEGER  (0..255)
      ACCESS  read-write
      STATUS  mandatory
      DESCRIPTION
"Defines the X.3 parameter 4, Selection of idle timer delay, in tenths of a 
second.  This parameter allows the selection of the duration of an interval 
between successive characters received from the start-stop mode DTE (user).  
When the interval is exceeded, the PAD terminates the assembly of the packet 
and forwards it.

Range of Values: 0 to 255

Default Value: 0

Configuration Changed: Operative "
      REFERENCE       "CCITT X.3 Table 1"    
      DEFVAL { 0 }
       ::= { asyProfEntry 8 }


   asyProfParameter5 OBJECT-TYPE
       SYNTAX  INTEGER  (0..2)
      ACCESS  read-write
         STATUS  mandatory
         DESCRIPTION
"Defines the X.3 parameter 5, Ancillary device control.  This parameter allows 
for flow control between the PAD and the start-stop mode DTE (user).

Options: 
0: No use of X-ON (DC1) and X-OFF (DC3)
1: Use of X-ON and X-OFF (data transfer)
2: Use of X-ON and X-OFF (data transfer and command).

Default Value: No use of X-ON (DC1) and X-OFF (DC3)

Configuration Changed: Operative"
      REFERENCE       "CCITT X.3 Table 1"    
      DEFVAL { 0 }
         ::= { asyProfEntry 9 }


   asyProfParameter6 OBJECT-TYPE
      SYNTAX  INTEGER  (0..5)
      ACCESS  read-write
      STATUS  mandatory
      DESCRIPTION
"Defines the X.3 parameter 6, Control of PAD service signals and PAD command 
signals.  This parameter provides the start-stop mode DTE (user) with the 
ability to decide whether or not and in what format PAD service signals are 
transmitted

Range of Values:
0: No PAD service signals are transmitted to the start-stop mode DTE
1: PAD service signals are transmitted in the standard format
5: PAD service signals and prompt PAD service signal are transmitted in the 
	standard format

Default Value: 0

Configuration Changed: Operative "
      REFERENCE       "CCITT X.3 Table 1"    
      DEFVAL { 0 }
         ::= { asyProfEntry 10 }


   asyProfParameter7 OBJECT-TYPE
      SYNTAX  INTEGER  (0..21)
      ACCESS  read-write
      STATUS  mandatory
      DESCRIPTION
"Defines the X.3 parameter 7, Selection of operation of the PAD on receipt of a 
break signal from the start-stop mode DTE.  This parameter allows the 
selection of the operation of the PAD after the receipt of a break signal 
from the start-stop mode DTE (user).

Range of Values:
0: Nothing
1: Interrupt
2: Reset
4: Send to DTE an indication of break PAD message
5: Interrupt and indication of break
8: Escape from data transfer state
16: Discard output, to start-stop mode DTE
21: Discard output, interrupt and indication of break

Default Value: 0

Configuration Changed: Operative "
      REFERENCE       "CCITT X.3 Table 1"    
      DEFVAL { 0 }
      ::= { asyProfEntry 11 }


   asyProfParameter8 OBJECT-TYPE
       SYNTAX  INTEGER  (0..1)
      ACCESS  read-write
         STATUS  mandatory
         DESCRIPTION
"Defines the X.3 parameter 8, Discard output.  This parameter provides for a 
PAD to discard the content of user sequences in packets upon request rather 
than disassembling and transmitting these to the start-stop mode DTE (user).

Options: 
0: Normal data delivery
1: Discard output

Default Value: Normal data delivery

Configuration Changed: Operative "
      REFERENCE       "CCITT X.3 Table 1"    
      DEFVAL { 0 }
         ::= { asyProfEntry 12 }


   asyProfParameter9 OBJECT-TYPE
       SYNTAX  INTEGER  (0..255)
      ACCESS  read-write
         STATUS  mandatory
         DESCRIPTION
"Defines the X.3 parameter 9, Padding after carriage return (CR).  This 
parameter provides for the automatic insertion of padding characters by the 
PAD after a carriage return by the DTE (user).  This allows the printer of the 
DTE to perform the carriage return function correctly.

Range of Values: 0 to 255

Note:
0: No padding after CR
1 to 255: Number of padding characters inserted after CR

Default Value: 0

Configuration Changed: Operative "
      REFERENCE       "CCITT X.3 Table 1"    
      DEFVAL { 0 }
         ::= { asyProfEntry 13 }


   asyProfParameter10 OBJECT-TYPE
       SYNTAX  INTEGER  (0..255)
      ACCESS  read-write
         STATUS  mandatory
         DESCRIPTION
"Defines the X.3 parameter 10, Line folding.  This parameter provides for 
the automatic insertion of graphic characters by the PAD in the character 
stream transmitted to the start-stop mode DTE (user).  The predetermined 
maximum number of graphic characters per line may be set.

Range of Values: 0 to 255

0: No line folding
1 to 255: Number of graphic characters per line

Default Value: 0

Configuration Changed: Operative "
      REFERENCE       "CCITT X.3 Table 1"    
      DEFVAL { 0 }
         ::= { asyProfEntry 14 }


   asyProfParameter11 OBJECT-TYPE
       SYNTAX  INTEGER  (0..22)
      ACCESS  read-only
         STATUS  mandatory
         DESCRIPTION
"Defines the X.3 parameter 11, Binary 
speed of start-stop mode DTE.

Options:
0: 110 bit/s
1: 134.5 bit/s
2: 300 bit/s
3: 1200 bit/s
4: 600 bit/s
5: 75 bit/s
6: 150 bit/s
7: 1800 bit/s
8: 200 bit/s
9: 100 bit/s
10: 50 bit/s
11: 75/1200 bit/s (not supported)
12: 2400 bit/s
13: 4800 bit/s
14: 9600 bit/s
15: 19200 bit/s
16: 48000 bit/s
17: 56000 bit/s
18: 64000 bit/s
19: 14400 bit/s
20: 38400 bit/s
21: 57600 bit/s
22: 115200 bit/s
255: non standard bit rate

Default Value: 110 bit/s"
      REFERENCE       "CCITT X.3 Table 1"    
      DEFVAL { 0 }
         ::= { asyProfEntry 15 }


   asyProfParameter12 OBJECT-TYPE
       SYNTAX  INTEGER  (0..1)
      ACCESS  read-write
         STATUS  mandatory
         DESCRIPTION
"Defines the X.3 parameter 12, Flow control of the PAD.  This parameter 
allows for flow control between the start-stop mode DTE (user) and the PAD.

Options: 
0: No use of X-ON (DC1) and X-OFF (DC3) for flow control
1: Use of X-ON (DC1) and X-OFF (DC3) for flow control

Default Value: No use of X-ON (DC1) and X-OFF (DC3) for flow control

Configuration Changed: Operative"
      REFERENCE       "CCITT X.3 Table 1"    
      DEFVAL { 0 }
         ::= { asyProfEntry 16 }


   asyProfParameter13 OBJECT-TYPE
       SYNTAX  INTEGER  (0..7)
      ACCESS  read-write
         STATUS  mandatory
         DESCRIPTION
"Defines the X.3 parameter 13, Linefeed insertion after carriage return.  This 
parameter allows for the automatic insertion of a linefeed character in the 
character stream to and from the start-stop DTE (user) or after each carriage 
return.  This parameter applies only in the data transfer state.

Range of Values:
0: No linefeed insertion
1: Insert linefeed after transmission of CR to the start-stop mode DTE
2: Insert linefeed after each CR in the data stream from the start-stop mode DTE
4: Insert linefeed after echo of CR to start-stop mode DTE
5: Insert linefeed after transmission to the start-stop mode DTE and
	after echo of CR
6:Insert linefeed in data stream after CR from start-stop mode DTE 
	and after an echo of a CR to the start-stop mode DTE
7: Insert linefeed in the data stream to and from the start-stop mode 
	DTE and after an echo of a CR to the start-stop mode DTE

Default Value: 0

Configuration Changed: Operative "
      REFERENCE      "CCITT X.3 Table 1"    
      DEFVAL { 0}
         ::= { asyProfEntry 17}


   asyProfParameter14 OBJECT-TYPE
       SYNTAX  INTEGER  (0..7)
      ACCESS  read-write
         STATUS  mandatory
         DESCRIPTION
"Defines the X.3 parameter 14, Padding after linefeed.  This parameter provides 
for the automatic insertion of padding characters in the character stream 
transmitted to the start-stop mode DTE (user) after the occurrence of a 
linefeed character.  This allows the printer of the DTE to perform the 
linefeed operation correctly.  This parameter applies only in the data 
transfer state.

Range of Values:0 to 7

Note: 
0: No padding after linefeed
1 to 7: Number of padding characters inserted after linefeed

Default Value: 0

Configuration Changed: Operative "
         REFERENCE      "CCITT X.3 Table 1"    
      DEFVAL { 0 }
         ::= { asyProfEntry 18 }


   asyProfParameter15 OBJECT-TYPE
       SYNTAX  INTEGER  (0..1)
      ACCESS  read-write
         STATUS  mandatory
         DESCRIPTION
"Defines the X.3 parameter 15, Editing. This parameter provides for character 
size delete, line delete and line display editing capabilities in the PAD 
command state and the data transfer state for the start-stop mode DTE (user).

Options: 
0: No use of editing in the data transfer state
1: Use of editing in the data transfer state

Default Value: No editing

Configuration Changed: Operative "
      REFERENCE       "CCITT X.3 Table 1"    
      DEFVAL { 0 }
         ::= { asyProfEntry 19 }


   asyProfParameter16 OBJECT-TYPE
       SYNTAX  INTEGER  (0..127)
      ACCESS  read-write
         STATUS  mandatory
         DESCRIPTION
"Defines the X.3 parameter 16, Character delete.  

Range of Values: 0 to 127

0 to126: One character from IA5
127: Character 7/15 (DEL)

Default Value: 0

Configuration Changed: Operative "
      REFERENCE       "CCITT X.3 Table 1"    
      DEFVAL { 0 }
         ::= { asyProfEntry 20 }


   asyProfParameter17 OBJECT-TYPE
       SYNTAX  INTEGER  (0..127)
      ACCESS  read-write
         STATUS  mandatory
         DESCRIPTION
"Defines the X.3 parameter 17,  Line delete.  

Range of Values: 0 to 127

0 to 23: One character from the range of IA5
24: Character 1/8 (CAN)
25 to 127: One character from the range of IA5

Default Value: 0

Configuration Changed: Operative "
      REFERENCE       "CCITT X.3 Table 1"    
      DEFVAL { 0 }
         ::= { asyProfEntry 21 }


   asyProfParameter18 OBJECT-TYPE
       SYNTAX  INTEGER  (0..127)
      ACCESS  read-write
         STATUS  mandatory
         DESCRIPTION
"Defines the X.3 parameter 18, Line display.

Range of Values: 0 to 127

0 to 17: One character from the range of IA5
18: Character 1/8 (DC2)
19 to 127: One character from the range of IA5

Default Value: 0

Configuration Changed: Operative "
      REFERENCE       "CCITT X.3 Table 1"    
      DEFVAL { 0 }
         ::= { asyProfEntry 22 }


   asyProfParameter19 OBJECT-TYPE
       SYNTAX  INTEGER  (0..127)
      ACCESS  read-write
         STATUS  mandatory
         DESCRIPTION
"Defines the X.3 parameter 19, Editing PAD service signals.  This parameter 
provides the start-stop mode DTE (user) with the ability to decide whether or 
not editing PAD service signals are transmitted and which format should be used.

Range of Values:
0: No editing PAD service signals
1: Editing PAD service signals for printing terminals
2: Editing PAD service signals for display terminals
8, 32 to 126: Editing PAD service signals using one character from the range of IA5

Default Value: 0

Configuration Changed: Operative "
      REFERENCE       "CCITT X.3 Table 1"    
      DEFVAL { 0 }
         ::= { asyProfEntry 23 }


   asyProfParameter20 OBJECT-TYPE
       SYNTAX  INTEGER  (0..128)
      ACCESS  read-write
         STATUS  mandatory
         DESCRIPTION
"Defines the X.3 parameter 20, Echo mask.  This parameter allows selected 
defined sets of characters received from the start-stop mode DTE (user) not to be 
transmitted back to the DTE.

Range of Values:
0: No echo mask (all characters echoed).
1: No echo of CR.
2: No echo of LF.
4: No echo of VT, HT and FF.
8: No echo of BEL and BS.
16: No echo of ESC and ENQ.
32: No echo of ACK, NAK, STX, SOH, EOT, ETB and ETX.
64: No echo of editing characters as designated by parameters 16, 17 and 18.
128: No echo of all other characters in columns 0 and 1 not mentioned 
	above and DEL.

Default Value: 0

Configuration Changed: Operative "
      REFERENCE       "CCITT X.3 Table 1"    
      DEFVAL { 0 }
         ::= { asyProfEntry 24 }


   asyProfParameter21 OBJECT-TYPE
       SYNTAX  INTEGER  (0..3)
      ACCESS  read-write
         STATUS  mandatory
         DESCRIPTION
"Defines the X.3 parameter 21, Parity treatment.  This parameter allows the 
PAD to check parity in the data stream from the start-stop mode DTE (user) or 
generate parity in the data stream to the DTE.

Options: 
0: No parity checking or generation
1: Parity checking
2: Parity generation
3: Parity checking and parity generation

Default Value: No parity checking or generation 

Configuration Changed: Operative "
      REFERENCE       "CCITT X.3 Table 1"    
      DEFVAL { 0 }
         ::= { asyProfEntry 25 }


   asyProfParameter22 OBJECT-TYPE
       SYNTAX  INTEGER  (0..255)
      ACCESS  read-write
         STATUS  mandatory
         DESCRIPTION
"Defines the X.3 parameter 22, Page wait.  This parameter allows the PAD to 
suspend transmission of additional characters to the start-stop mode DTE 
(user) after a specified number of linefeed characters have been 
transmitted by the PAD.

Range of Values: 0 to 255

0: Page wait disable.
1 to 255: Number of line feed characters considered by the PAD for the 
page wait function.

Default Value: 0

Configuration Changed: Operative "
      REFERENCE       "CCITT X.3 Table 1"    
      DEFVAL { 0 }
         ::= { asyProfEntry 26 }



   asyProfParameter23 OBJECT-TYPE
       SYNTAX  INTEGER  (0..4)
      ACCESS  read-write
         STATUS  mandatory
         DESCRIPTION
"Defines parameter 23 (extension to X.3), Receive parity type.

Options: 
0: Parity disable
1: Even parity
2: Odd parity
3: Space parity
4: Mark parity

Default Value: Parity disable

Configuration Changed: Operative "
      REFERENCE       "CCITT X.3 Table 1"    
      DEFVAL { 0 }
         ::= { asyProfEntry 27 }


   asyProfParameter24 OBJECT-TYPE
       SYNTAX  INTEGER  (0..4)
      ACCESS  read-write
         STATUS  mandatory
         DESCRIPTION
"Defines parameter 24 (extension to 
X.3), Transmit parity type.

Options: 
0: Parity disable
1: Even parity
2: Odd parity
3: Space parity
4: Mark parity

Default Value: Parity disable

Configuration Changed: Operative "
      REFERENCE       "CCITT X.3 Table 1"    
      DEFVAL { 0 }
         ::= { asyProfEntry 28 }



   asyProfParameter25 OBJECT-TYPE
       SYNTAX  INTEGER  (0..127)
      ACCESS  read-write
         STATUS  mandatory
         DESCRIPTION
"Defines parameter 25 (extension to X.3), Flow control on character to PAD.

Range of Values: 0 to 127

Note:
0 to 18: One character from the range of IA5
19: DC3
20 to 127: One character from the range of IA5

Default Value: 0

Configuration Changed: Operative"
      REFERENCE       "CCITT X.3 Table 1"    
      DEFVAL { 0 }
         ::= { asyProfEntry 29 }


   asyProfParameter26 OBJECT-TYPE
       SYNTAX  INTEGER  (0..127)
      ACCESS  read-write
         STATUS  mandatory
         DESCRIPTION
"Defines parameter 26 (extension to X.3), Flow control off character to PAD.

Range of Values: 0 to 127

0 to 16: One character from the range of IA5
17: DC1
18 to 127: One character from the range of IA5

Default Value: 0

Configuration Changed: Operative"
      REFERENCE       "CCITT X.3 Table 1"    
      DEFVAL { 0 }
         ::= { asyProfEntry 30 }


   asyProfParameter27 OBJECT-TYPE
       SYNTAX  INTEGER  (0..127)
      ACCESS  read-write
         STATUS  mandatory
         DESCRIPTION
"Defines parameter 27 (extension to X.3), Flow control on character to 
ancillary device. 

Range of Values: 0 to 127

Note:
0 to 18: One character from the range of IA5
19: DC3
20 to 127: One character from the range of IA5

Default Value: 0

Configuration Changed: Operative"
      REFERENCE       "CCITT X.3 Table 1"    
      DEFVAL { 0 }
         ::= { asyProfEntry 31 }


   asyProfParameter28 OBJECT-TYPE
       SYNTAX  INTEGER  (0..127)
      ACCESS  read-write
         STATUS  mandatory
         DESCRIPTION
"Defines parameter 28 (extension to X.3), Flow control off character to 
ancillary device.

Range of Values: 0 to 127

0 to 16: One character from the range of IA5
17: DC1
18 to 127: One character from the range of IA5

Default Value: 0

Configuration Changed: Operative"
      REFERENCE       "CCITT X.3 Table 1"    
      DEFVAL { 0 }
         ::= { asyProfEntry 32 }





--  Operational Async SAP (Service Access Point) X.3 Profile Table

--  The table describing:
--      parameters required to configure the operational X.3 profile for an 
--      async sap.


asySapProfTable OBJECT-TYPE
   SYNTAX  SEQUENCE OF AsySapProfEntry
   ACCESS  not-accessible
   STATUS  mandatory
   DESCRIPTION
"Contains the operational X.3 parameters for each async SAP (service access point)."
   ::= { cxAsync 22 }


   asySapProfEntry OBJECT-TYPE
      SYNTAX  AsySapProfEntry
      ACCESS  not-accessible
      STATUS  mandatory
      DESCRIPTION
"Provides the operational X.3 parameters for a specific async  sap."
      INDEX { asySapProfSapNumber }
      ::= { asySapProfTable 1 }


   AsySapProfEntry ::=
      SEQUENCE {
 -- Parameters
         asySapProfSapNumber               SapIndex,
         asySapProfParameter1               INTEGER,
         asySapProfParameter2               INTEGER,
         asySapProfParameter3               INTEGER,
         asySapProfParameter4               INTEGER,
         asySapProfParameter5               INTEGER,
         asySapProfParameter6               INTEGER,
         asySapProfParameter7               INTEGER,
         asySapProfParameter8               INTEGER,
         asySapProfParameter9               INTEGER,
         asySapProfParameter10              INTEGER,
         asySapProfParameter11              INTEGER,
         asySapProfParameter12              INTEGER,
         asySapProfParameter13              INTEGER,
         asySapProfParameter14              INTEGER,
         asySapProfParameter15              INTEGER,
         asySapProfParameter16              INTEGER,
         asySapProfParameter17              INTEGER,
         asySapProfParameter18              INTEGER,
         asySapProfParameter19              INTEGER,
         asySapProfParameter20              INTEGER,
         asySapProfParameter21              INTEGER,
         asySapProfParameter22              INTEGER,
         asySapProfParameter23              INTEGER,
         asySapProfParameter24              INTEGER,
         asySapProfParameter25              INTEGER,
         asySapProfParameter26              INTEGER,
         asySapProfParameter27              INTEGER,
         asySapProfParameter28              INTEGER
         }


   asySapProfSapNumber OBJECT-TYPE
      SYNTAX  SapIndex
      ACCESS  read-only
      STATUS  mandatory
      DESCRIPTION
"Identifies the  SAP (service access point) using a unique numerical value."
      ::= { asySapProfEntry 1 }



   asySapProfParameter1 OBJECT-TYPE
      SYNTAX  INTEGER  (0..126)
      ACCESS  read-write
      STATUS  mandatory
      DESCRIPTION
"Defines the X.3 parameter 1, PAD recall using a character.  This parameter 
allows the start-stop mode DTE (user) to initiate an escape from the data 
transfer or the connection in progress state in order to send PAD command signals.

Range of Values:
0: Not possible
1: Character DLE
32 to 126: Graphic character defined by user

Default Value: 0

Configuration Changed: Operative"
      REFERENCE       "CCITT X.3 Table 1"    
      DEFVAL { 0 }
      ::= { asySapProfEntry 5 }


   asySapProfParameter2 OBJECT-TYPE
      SYNTAX  INTEGER  (0..1)
      ACCESS  read-write
      STATUS  mandatory
      DESCRIPTION
"Defines the X.3 parameter 2, Echo. This parameter provides for characters 
received from the start-stop mode DTE (user) to be transmitted back to the 
start-stop mode DTE as well as being interpreted by the PAD.

Options: 
0: No echo
1: Echo

Default Value: No echo

Configuration Changed: Operative"
      REFERENCE       "CCITT X.3 Table 1"    
      DEFVAL { 0 }
       ::= { asySapProfEntry 6 }


   asySapProfParameter3 OBJECT-TYPE
      SYNTAX  INTEGER  (0..126)
      ACCESS  read-write
      STATUS  mandatory
         DESCRIPTION
"Defines the X.3 parameter 3, Selection of data forwarding character(s).  This 
parameter allows the selection of defined sets of characters received from 
the start-stop mode DTE (user) to be recognized by the PAD as an indication 
to complete the assembly and forward a complete packet

Range of Values:
0: No data forwarding character(s)
1: Alphanumeric characters  (A-Z, a-z and 0-9)
2: Character CR
4: Characters ESC, BEL, ENQ and ACK
6: Characters CR, ESC, BEL, ENQ and ACK
8: Characters DEL, CAN and DC2
16: Characters ETX and EOT
18: Characters CR, ETX and EOT
32: Characters HT, LF, VT and FF
64: All characters in columns 0 and 1 of IA5 except those shown 
	for values 2, 4, 8 and 32
126: All characters in columns 0 and 1 and character DEL

Note: Some values are combinations of other values 
(i.e., value 18 is a combination of values 2 and 16).

Default Value: 0

Configuration Changed: Operative"
      REFERENCE       "CCITT X.3 Table 1"    
      DEFVAL { 0 }
         ::= { asySapProfEntry 7 }


   asySapProfParameter4 OBJECT-TYPE
      SYNTAX  INTEGER  (0..255)
      ACCESS  read-write
      STATUS  mandatory
      DESCRIPTION
"Defines the X.3 parameter 4, Selection of idle timer delay, in tenths of a 
second.  This parameter allows the selection of the duration of an interval 
between successive characters received from the start-stop mode DTE (user).  
When the interval is exceeded, the PAD terminates the assembly of the packet 
and forwards it.

Range of Values: 0 to 255

Default Value: 0

Configuration Changed: Operative"
      REFERENCE       "CCITT X.3 Table 1"    
      DEFVAL { 0 }
       ::= { asySapProfEntry 8 }


   asySapProfParameter5 OBJECT-TYPE
       SYNTAX  INTEGER  (0..2)
      ACCESS  read-write
         STATUS  mandatory
         DESCRIPTION
"Defines the X.3 parameter 5, Ancillary device control.  This parameter allows 
for flow control between the PAD and the start-stop mode DTE (user).

Options: 
0: No use of X-ON (DC1) and X-OFF (DC3)
1: Use of X-ON and X-OFF (data transfer)
2: Use of X-ON and X-OFF (data transfer and command).

Default Value: No use of X-ON (DC1) and X-OFF (DC3)

Configuration Changed: Operative

Note: Object asySapProfParameter27, Flow control on character to 
ancillary device, and object asySapProfParameter28, Flow control 
off character to ancillary device, are allowed only if this object is 
set to No use of X-ON (DC1) and X-OFF (DC3)."
      REFERENCE       "CCITT X.3 Table 1"    
      DEFVAL { 0 }
         ::= { asySapProfEntry 9 }


   asySapProfParameter6 OBJECT-TYPE
      SYNTAX  INTEGER  (0..5)
      ACCESS  read-write
      STATUS  mandatory
      DESCRIPTION
"Defines the X.3 parameter 6, Control of PAD service signals and PAD command 
signals.  This parameter provides the start-stop mode DTE (user) with the 
ability to decide whether or not and in what format PAD service signals are 
transmitted

Range of Values:
0: No PAD service signals are transmitted to the start-stop mode DTE
1: PAD service signals are transmitted in the standard format
5: PAD service signals and prompt PAD service signal are transmitted 
	in the standard format

Default Value: 0

Configuration Changed: Operative

The following values are currently not supported:

8 to 15 - PAD service signals are transmitted in a network dependent format
16 - Extended dialog mode, PAD service signals are in English
32 - Extended dialog mode, PAD service signals are in French
48 - Extended dialog mode, PAD service signals are in Spanish"

      REFERENCE       "CCITT X.3 Table 1"    
      DEFVAL { 0 }
         ::= { asySapProfEntry 10 }


   asySapProfParameter7 OBJECT-TYPE
      SYNTAX  INTEGER  (0..21)
      ACCESS  read-write
      STATUS  mandatory
      DESCRIPTION
"Defines the X.3 parameter 7, Selection of operation of the PAD on receipt 
of a break signal from the start-stop mode DTE.  This parameter allows the 
selection of the operation of the PAD after the receipt of a break signal 
from the start-stop mode DTE (user).

Range of Values:
0: Nothing
1: Interrupt
2: Reset
4: Send to DTE an indication of break PAD message
5: Interrupt and indication of break
8: Escape from data transfer state
16: Discard output, to start-stop mode DTE
21: Discard output, interrupt and indication of break

Default Value: 0

Configuration Changed: Operative"
      REFERENCE       "CCITT X.3 Table 1"    
      DEFVAL { 0 }
      ::= { asySapProfEntry 11 }


   asySapProfParameter8 OBJECT-TYPE
       SYNTAX  INTEGER  (0..1)
      ACCESS  read-write
         STATUS  mandatory
         DESCRIPTION
"Defines the X.3 parameter 8, Discard output.  This parameter provides for a 
PAD to discard the content of user sequences in packets upon request rather 
than disassembling and transmitting these to the start-stop mode DTE (user).

Options: 
0: Normal data delivery
1: Discard output

Default Value: Normal data delivery

Configuration Changed: Operative"
      REFERENCE       "CCITT X.3 Table 1"    
      DEFVAL { 0 }
         ::= { asySapProfEntry 12 }


   asySapProfParameter9 OBJECT-TYPE
       SYNTAX  INTEGER  (0..255)
      ACCESS  read-write
         STATUS  mandatory
         DESCRIPTION
"Defines the X.3 parameter 9, Padding after carriage return (CR).  This 
parameter provides for the automatic insertion of padding characters by the 
PAD after a carriage return by the DTE (user).  This allows the printer of the 
DTE to perform the carriage return function correctly.

Range of Values: 0 to 255

0: No padding after CR
1 to 255: Number of padding characters inserted after CR

Default Value: 0

Configuration Changed: Operative"
      REFERENCE       "CCITT X.3 Table 1"    
      DEFVAL { 0 }
         ::= { asySapProfEntry 13 }


   asySapProfParameter10 OBJECT-TYPE
       SYNTAX  INTEGER  (0..255)
      ACCESS  read-write
         STATUS  mandatory
         DESCRIPTION
"Defines the X.3 parameter 10, Line folding.  This parameter provides for 
the automatic insertion of graphic characters by the PAD in the character 
stream transmitted to the start-stop mode DTE (user).  The predetermined 
maximum number of graphic characters per line may be set.

Range of Values: 0 to 255

0: No line folding
1 to 255: Number of graphic characters per line

Default Value: 0

Configuration Changed: Operative"
      REFERENCE       "CCITT X.3 Table 1"    
      DEFVAL { 0 }
         ::= { asySapProfEntry 14 }


   asySapProfParameter11 OBJECT-TYPE
       SYNTAX  INTEGER  (0..22)
      ACCESS  read-only
         STATUS  mandatory
         DESCRIPTION
"Defines the X.3 parameter 11, Binary speed of start-stop mode DTE.

Options:
0: 110 bit/s
1: 134.5 bit/s
2: 300 bit/s
3: 1200 bit/s
4: 600 bit/s
5: 75 bit/s
6: 150 bit/s
7: 1800 bit/s
8: 200 bit/s
9: 100 bit/s
10: 50 bit/s
11: 75/1200 bit/s (not supported)
12: 2400 bit/s
13: 4800 bit/s
14: 9600 bit/s
15: 19200 bit/s
16: 48000 bit/s
17: 56000 bit/s
18: 64000 bit/s
19: 14400 bit/s
20: 38400 bit/s
21: 57600 bit/s
22: 115200 bit/s
255: non standard bit rate

Default Value: 110 bit/s"

      REFERENCE       "CCITT X.3 Table 1"    
      DEFVAL { 0 }
         ::= { asySapProfEntry 15 }


   asySapProfParameter12 OBJECT-TYPE
       SYNTAX  INTEGER  (0..1)
      ACCESS  read-write
         STATUS  mandatory
         DESCRIPTION
"Defines the X.3 parameter 12, Flow control of the PAD.  This parameter 
allows for flow control between the start-stop mode DTE (user) and the PAD.

Options: 
0: No use of X-ON (DC1) and X-OFF (DC3) for flow control
1: Use of X-ON (DC1) and X-OFF (DC3) for flow control

Default Value: No use of X-ON (DC1) and X-OFF (DC3) for flow control

Configuration Changed: Operative

Note: Object asyProfParameter25, Flow control on character to PAD, and 
object asyProfParameter26, Flow control off character to PAD, are 
allowed only if this object is set to No use of X-ON (DC1) and X-OFF (DC3)."
      REFERENCE       "CCITT X.3 Table 1"    
      DEFVAL { 0 }
         ::= { asySapProfEntry 16 }


   asySapProfParameter13 OBJECT-TYPE
       SYNTAX  INTEGER  (0..7)
      ACCESS  read-write
         STATUS  mandatory
         DESCRIPTION
"Defines the X.3 parameter 13, Linefeed insertion after carriage return.  This 
parameter allows for the automatic insertion of a linefeed character in the 
character stream to and from the start-stop DTE (user) or after each carriage 
return.  This parameter applies only in 
the data transfer state.

Range of Values:
0: No linefeed insertion
1: Insert linefeed after transmission of CR to the start-stop mode DTE
2: Insert linefeed after each CR in the data stream from the start-stop mode DTE
4: Insert linefeed after echo of CR to start-stop mode DTE
5: Insert linefeed after transmission to the start-stop mode DTE and after 
	echo of CR
6: Insert linefeed in data stream after CR from start-stop mode DTE 
	and after an echo of a CR to the start-stop mode DTE
7: Insert linefeed in the data stream to and from the start-stop 
	mode DTE and after an echo of a CR to the start-stop mode DTE

Default Value: 0

Configuration Changed: Operative"
      REFERENCE      "CCITT X.3 Table 1"    
      DEFVAL { 0}
         ::= { asySapProfEntry 17}


   asySapProfParameter14 OBJECT-TYPE
       SYNTAX  INTEGER  (0..7)
      ACCESS  read-write
         STATUS  mandatory
         DESCRIPTION
"Defines the X.3 parameter 14, Padding after linefeed.  This parameter provides 
for the automatic insertion of padding characters in the character stream 
transmitted to the start-stop mode DTE (user) after the occurrence of a 
linefeed character.  This allows the printer of the DTE to perform the 
linefeed operation correctly.  This parameter applies only in the data 
transfer state.

Range of Values:0 to 7

0: No padding after linefeed
1 to 7: Number of padding characters inserted after linefeed

Default Value: 0

Configuration Changed: Operative"
      REFERENCE      "CCITT X.3 Table 1"    
      DEFVAL { 0 }
         ::= { asySapProfEntry 18 }


   asySapProfParameter15 OBJECT-TYPE
       SYNTAX  INTEGER  (0..1)
      ACCESS  read-write
      STATUS  mandatory
      DESCRIPTION
"Defines the X.3 parameter 15, Editing. This parameter provides for character 
size delete, line delete and line display editing capabilities in the PAD 
command state and the data transfer state for the start-stop mode DTE (user).

Options: 
0: No use of editing in the data transfer state
1: Use of editing in the data transfer state

Default Value: No editing

Configuration Changed: Operative"
      REFERENCE       "CCITT X.3 Table 1"    
      DEFVAL { 0 }
         ::= { asySapProfEntry 19 }


   asySapProfParameter16 OBJECT-TYPE
       SYNTAX  INTEGER  (0..127)
      ACCESS  read-write
      STATUS  mandatory
      DESCRIPTION
"Defines the X.3 parameter 16, Character delete.  

Range of Values: 0 to 127

0 to126: One character from IA5
127: Character 7/15 (DEL)

Default Value: 0

Configuration Changed: Operative"
      REFERENCE       "CCITT X.3 Table 1"    
      DEFVAL { 0 }
         ::= { asySapProfEntry 20 }


   asySapProfParameter17 OBJECT-TYPE
       SYNTAX  INTEGER  (0..127)
      ACCESS  read-write
         STATUS  mandatory
         DESCRIPTION
"Defines the X.3 parameter 17,  Line delete.  

Range of Values: 0 to 127

0 to 23: One character from the range of IA5
24: Character 1/8 (CAN)
25 to 127: One character from the range of IA5

Default Value: 0

Configuration Changed: Operative"
      REFERENCE       "CCITT X.3 Table 1"    
      DEFVAL { 0 }
         ::= { asySapProfEntry 21 }


   asySapProfParameter18 OBJECT-TYPE
       SYNTAX  INTEGER  (0..127)
      ACCESS  read-write
         STATUS  mandatory
         DESCRIPTION
"Defines the X.3 parameter 18, Line display.

Range of Values: 0 to 127

0 to 17: One character from the range of IA5
18: Character 1/8 (DC2)
19 to 127: One character from the range of IA5

Default Value: 0

Configuration Changed: Operative"
      REFERENCE       "CCITT X.3 Table 1"    
      DEFVAL { 0 }
         ::= { asySapProfEntry 22 }


   asySapProfParameter19 OBJECT-TYPE
       SYNTAX  INTEGER  (0..127)
      ACCESS  read-write
         STATUS  mandatory
         DESCRIPTION
"Defines the X.3 parameter 19, Editing PAD service signals.  This parameter 
provides the start-stop mode DTE (user) with the ability to decide whether or 
not editing PAD service signals are transmitted and which format should be used.

Range of Values:
0 = No editing PAD service signals
1: Editing PAD service signals for printing terminals
2: Editing PAD service signals for display terminals
8, 32 to 126: Editing PAD service signals using one character from the range of IA5

Default Value: 0

Configuration Changed: Operative"
      REFERENCE       "CCITT X.3 Table 1"    
      DEFVAL { 0 }
         ::= { asySapProfEntry 23 }


   asySapProfParameter20 OBJECT-TYPE
       SYNTAX  INTEGER  (0..128)
      ACCESS  read-write
         STATUS  mandatory
         DESCRIPTION
"Defines the X.3 parameter 20, Echo mask.  This parameter allows selected 
defined sets of characters received from the start-stop mode DTE (user) not to be 
transmitted back to the DTE.

Range of Values:
0: No echo mask (all characters echoed)
1: No echo of CR
2: No echo of LF
4: No echo of VT, HT and FF
8: No echo of BEL and BS
16: No echo of ESC and ENQ
32: No echo of ACK, NAK, STX, SOH, EOT, ETB and ETX
64: No echo of editing characters as designated by parameters 16, 17 and 18
128: No echo of all other characters in columns 0 and 1 not mentioned 
	above and DEL

Default Value: 0

Configuration Changed: Operative"
      REFERENCE       "CCITT X.3 Table 1"    
      DEFVAL { 0 }
         ::= { asySapProfEntry 24 }


   asySapProfParameter21 OBJECT-TYPE
       SYNTAX  INTEGER  (0..3)
      ACCESS  read-write
         STATUS  mandatory
         DESCRIPTION
"Defines the X.3 parameter 21, Parity treatment.  This parameter allows the 
PAD to check parity in the data stream from the start-stop mode DTE (user) or 
generate parity in the data stream to the DTE.

Options: 
0: No parity checking or generation
1: Parity checking
2: Parity generation
3: Parity checking and parity generation

Default Value: No parity checking or generation 

Configuration Changed: Operative"
      REFERENCE       "CCITT X.3 Table 1"    
      DEFVAL { 0 }
         ::= { asySapProfEntry 25 }


   asySapProfParameter22 OBJECT-TYPE
       SYNTAX  INTEGER  (0..255)
      ACCESS  read-write
         STATUS  mandatory
         DESCRIPTION
"Defines the X.3 parameter 22, Page wait.  This parameter allows the PAD to 
suspend transmission of additional characters to the start-stop mode DTE 
(user) after a specified number of linefeed characters have been 
transmitted by the PAD.

Range of Values: 0 to 255

0: Page wait disable
1 to 255: Number of line feed characters considered by the PAD 
for the page wait function

Default Value: 0

Configuration Changed: Operative"
      REFERENCE       "CCITT X.3 Table 1"    
      DEFVAL { 0 }
         ::= { asySapProfEntry 26 }



   asySapProfParameter23 OBJECT-TYPE
       SYNTAX  INTEGER  (0..4)
      ACCESS  read-write
         STATUS  mandatory
         DESCRIPTION
"Defines parameter 23 (extension to X.3), Receive parity type.

Options: 
0: Parity disable
1: Even parity
2: Odd parity
3: Space parity
4: Mark parity

Default Value: Parity disable

Configuration Changed: Operative"
      REFERENCE       "CCITT X.3 Table 1"    
      DEFVAL { 0 }
         ::= { asySapProfEntry 27 }


   asySapProfParameter24 OBJECT-TYPE
       SYNTAX  INTEGER  (0..4)
      ACCESS  read-write
         STATUS  mandatory
         DESCRIPTION
"Defines parameter 24 (extension to X.3), Transmit parity type.

Options: 
0: Parity disable
1: Even parity
2: Odd parity
3: Space parity
4: Mark parity

Default Value: Parity disable

Configuration Changed: Operative"
      REFERENCE       "CCITT X.3 Table 1"    
      DEFVAL { 0 }
         ::= { asySapProfEntry 28 }



   asySapProfParameter25 OBJECT-TYPE
       SYNTAX  INTEGER  (0..127)
      ACCESS  read-write
         STATUS  mandatory
         DESCRIPTION
"Defines parameter 25 (extension to X.3), Flow control on character to PAD.

Range of Values: 0 to 127

0 to 18: One character from the range of IA5
19: DC3
20 to 127: One character from the range of IA5

Default Value: 0

Configuration Changed: Operative

Note: This object is allowed only if object asySapProfParameter12, Flow control
of the PAD, is set to No use of X-ON (DC1) and X-OFF (DC3)."
      REFERENCE       "CCITT X.3 Table 1"    
      DEFVAL { 0 }
         ::= { asySapProfEntry 29 }


   asySapProfParameter26 OBJECT-TYPE
       SYNTAX  INTEGER  (0..127)
      ACCESS  read-write
         STATUS  mandatory
         DESCRIPTION
"Defines parameter 26 (extension to X.3), Flow control off character to PAD.

Range of Values: 0 to 127

0 to 16: One character from the range of IA5
17 = DC1
18 to 127: One character from the range of IA5

Default Value: 0

Configuration Changed: Operative

Note: This object is allowed only if object asySapProfParameter12, 
Flow control of the PAD, is set to No use of X-ON (DC1) and X-OFF (DC3)."
      REFERENCE       "CCITT X.3 Table 1"    
      DEFVAL { 0 }
         ::= { asySapProfEntry 30 }


   asySapProfParameter27 OBJECT-TYPE
       SYNTAX  INTEGER  (0..127)
      ACCESS  read-write
         STATUS  mandatory
         DESCRIPTION
"Defines parameter 27 (extension to X.3), Flow control on character to 
ancillary device. 

Range of Values: 0 to 127

Note:
0 to 18: One character from the range of IA5
19: DC3
20 to 127: One character from the range of IA5

Default Value: 0

Configuration Changed: Operative

Note: 
This object is allowed only if object asySapProfParameter5, Ancillary device 
control, is set to No use of X-ON (DC1) and X-OFF (DC3)."
      REFERENCE       "CCITT X.3 Table 1"    
      DEFVAL { 0 }
         ::= { asySapProfEntry 31 }


   asySapProfParameter28 OBJECT-TYPE
       SYNTAX  INTEGER  (0..127)
      ACCESS  read-write
         STATUS  mandatory
         DESCRIPTION
"Defines parameter 28 (extension to X.3), Flow control off character to 
ancillary device.

Range of Values: 0 to 127

0 to 16: One character from the range of IA5
17: DC1
18 to 127: One character from the range of IA5

Default Value: 0

Configuration Changed: Operative

Note: 
This object is allowed only if object
asySapProfParameter5, Ancillary device 
control, is set to No use of X-ON (DC1) 
and X-OFF (DC3)."
      REFERENCE       "CCITT X.3 Table 1"    
      DEFVAL { 0 }
         ::= { asySapProfEntry 32 }







--  Async DTE Table

--  The table describing:
--      parameters required to form an X.28 Selection command and asySap 
--      parameters to be initialized when a logical connections is attempted 
--      manually via 'abbreviated address' or automatically when 
--      'asySapAutoConnect' defines an 'abbreviated address' (future 
--      consideration).


asyDteTable OBJECT-TYPE
   SYNTAX  SEQUENCE OF AsyDteEntry
   ACCESS  not-accessible
   STATUS  mandatory
   DESCRIPTION
"A table containing the DTE X.28 Selection command objects for each defined 
'abbreviated address'."
   ::= { cxAsync 23 }


   asyDteEntry OBJECT-TYPE
      SYNTAX  AsyDteEntry
      ACCESS  not-accessible
      STATUS  mandatory
      DESCRIPTION
"The objects for a specific DTE X.28 Selection entry."
      INDEX { asyDteNumber }
      ::= { asyDteTable 1 }


   AsyDteEntry ::=
      SEQUENCE {
 -- Parameters
asyDteNumber                    DteIndex,
asyDteRowStatus                 INTEGER,
asyDteAlias                                     Alias,
asyDteCalledAddress                     DisplayString,                  
asyDteFacilityField                     DisplayString,                  
asyDteUserDataField                     DisplayString,                  
asyDteX3Profile                 INTEGER                 
}                       


   asyDteNumber OBJECT-TYPE
      SYNTAX  DteIndex
      ACCESS  read-only
      STATUS  mandatory
      DESCRIPTION
"Identifies the DTE X.28 Selection entry by a unique numerical value."
      ::= { asyDteEntry 1 }


   asyDteRowStatus OBJECT-TYPE
      SYNTAX  INTEGER {
               invalid         (1),
               valid           (2)
               }
      ACCESS  read-write
      STATUS  mandatory
      DESCRIPTION
"Indicates whether this specific entry is configured within the MIB.  
Entries (rows) may be created by setting this object value to 'valid', 
or deleted by changing this object value to 'invalid'."
      ::= { asyDteEntry 2 }


   asyDteAlias OBJECT-TYPE
      SYNTAX  Alias
      ACCESS  read-write
      STATUS  mandatory
      DESCRIPTION
"Identifies the DTE entry by a textual name.  Names are unique per service 
access point.

Note: 
Dte alias (name) must be preceded by a '.' (period) when used in an X.28 
Selection with abbreviated address."
      ::= { asyDteEntry 3 }


   asyDteCalledAddress OBJECT-TYPE
      SYNTAX DisplayString (SIZE (0..15))
      ACCESS  read-write
      STATUS  mandatory
      DESCRIPTION
"Defines the network address of a remote device for this DTE entry.
 Allowable values: 1 to 15 numerical digits. "
      REFERENCE  "CCITT X.28 3.5.15.2.1, CCiTT X.25, CCITT X.121"
      DEFVAL { "" }
      ::= { asyDteEntry 5 }


   asyDteFacilityField OBJECT-TYPE
      SYNTAX DisplayString (SIZE (0..64))
      ACCESS  read-write
      STATUS  mandatory
      DESCRIPTION
"Defines the facility codes and parameters requires for the X.28 
Selection command for this DTE entry. The facility codes and parameters
must be entered as defined in the CCITT X.28 Recommendation.  
The following facilities are supported:

- CUG facility 
- CUG with OA facility 
- Called address extension facility 
- Call reselection prevention 
- Fast select with restriction on response 
- Fast select 
- Reverse charge 
- Charge request 
- Network User ID 

A value of null string (blank) means no facilities. "
      REFERENCE       "CCITT X.28 3.5.15.1"
      DEFVAL { "" }
      ::= { asyDteEntry 6 }


   asyDteUserDataField OBJECT-TYPE
      SYNTAX DisplayString (SIZE (0..128))
      ACCESS  read-write
      STATUS  mandatory
      DESCRIPTION
"Defines the user data field of the X.28 Selection command for this DTE 
entry.  A value of nul string (blank) means no user data. "
      REFERENCE       "CCITT X.28 3.5.15.3"
      DEFVAL { "" }
      ::= { asyDteEntry 7 }


asyDteX3Profile OBJECT-TYPE
      SYNTAX  INTEGER (0..255)
      ACCESS  read-write
      STATUS  mandatory
      DESCRIPTION
"Defines the X.3 Profile number for a specific set of X.3 parameters.
The Async layer will initialize its SAP to this X.3 Profile before 
establishing a logical connection for this DTE entry. a value of '0' 
means no X.3 Profile. "
      DEFVAL { 0 }
      ::= { asyDteEntry 8 }




-- Traps


asySapAlarm TRAP-TYPE
   ENTERPRISE      cxAsync
   VARIABLES               {       asySapNumber,
               asySapStatusEvent
            }
   DESCRIPTION
"Indicates that the global object asyStatusEvent has occurred at the 
identified SAP (service access point) if the global object asyAlarms is enabled."
   ::= 1


END
