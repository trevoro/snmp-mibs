--
-- sle-bridge-mib.mib
-- MIB generated by MG-SOFT Visual MIB Builder Version 6.0  Build 88
-- Monday, May 02, 2016 at 13:47:39
--

	SLE-BRIDGE-MIB DEFINITIONS ::= BEGIN
 
		IMPORTS
			sleMgmt			
				FROM DASAN-SMI			
			AddressFamilyNumbers			
				FROM IANA-ADDRESS-FAMILY-NUMBERS-MIB			
			InterfaceIndex			
				FROM IF-MIB			
			InetAddressIPv6			
				FROM INET-ADDRESS-MIB			
			SleControlStatusType, SleControlRequestResultType			
				FROM SLE-TC-MIB			
			OBJECT-GROUP, NOTIFICATION-GROUP			
				FROM SNMPv2-CONF			
			TimeTicks, IpAddress, Integer32, Unsigned32, Gauge32, 
			Counter32, Counter64, OBJECT-TYPE, MODULE-IDENTITY, 
			NOTIFICATION-TYPE			
				FROM SNMPv2-SMI			
			TruthValue, TimeStamp, MacAddress			
				FROM SNMPv2-TC;
	
	
		sleBridge MODULE-IDENTITY 
			LAST-UPDATED "200412080903Z"		-- December 08, 2004 at 09:03 GMT
			ORGANIZATION 
				" "
			CONTACT-INFO 
				" "
			DESCRIPTION 
				"This MIB contains all needed informations about bridgePorts and
				all supported sle bridgeing features."
			REVISION "200412080840Z"		-- December 08, 2004 at 08:40 GMT
			DESCRIPTION 
				"AFI"
			::= { sleMgmt 3 }

		
	
--
-- Type definitions
--
	
		SleIgmpConfControlRequestType ::= INTEGER { setIgmpConfProfile(1) }

		SleIgmpMcastControlRequestType ::= INTEGER
			{
			createIgmpStaticMcast(1),
			destroyIgmpStaticMcast(2)
			}

		Boolean ::= INTEGER
			{
			disable(0),
			enable(1)
			}

		SleLldpManAddrIfSubType ::= INTEGER
			{
			unknown(1),
			ifIndex(2),
			systemPortNumber(3)
			}

		SleLldpSysCapType ::= BITS
			{
			other(0),
			repeater(1),
			bridge(2),
			wlanAccessPoint(3),
			router(4),
			telephone(5),
			docsisCableDevice(6),
			stationOnly(7)
			}

	
	
--
-- Node definitions
--
	
		sleBridgeBase OBJECT IDENTIFIER ::= { sleBridge 1 }

		
		sleBridgeBaseInfo OBJECT IDENTIFIER ::= { sleBridgeBase 1 }

		
		sleBridgeMacAddress OBJECT-TYPE
			SYNTAX OCTET STRING (SIZE (6))
			MAX-ACCESS read-only
			STATUS current
			DESCRIPTION
				"System MAC Address of bridge"
			::= { sleBridgeBaseInfo 1 }

		
		sleBridgePortNum OBJECT-TYPE
			SYNTAX INTEGER (1..256)
			MAX-ACCESS read-only
			STATUS current
			DESCRIPTION
				"Number of bridge ports"
			::= { sleBridgeBaseInfo 2 }

		
		sleBridgeLagMaxId OBJECT-TYPE
			SYNTAX INTEGER (1..14)
			MAX-ACCESS read-only
			STATUS current
			DESCRIPTION
				"This value assigned to the aggregation max id."
			::= { sleBridgeBaseInfo 3 }

		
		sleBridgeLacpActivity OBJECT-TYPE
			SYNTAX INTEGER
				{
				disabled(0),
				enabled(1)
				}
			MAX-ACCESS read-only
			STATUS current
			DESCRIPTION
				"The LACP enabled/disabled status of the switch"
			::= { sleBridgeBaseInfo 4 }

		
		sleBridgeLacpPriority OBJECT-TYPE
			SYNTAX INTEGER (1..65535)
			MAX-ACCESS read-only
			STATUS current
			DESCRIPTION
				"The priority assigned to the Actor System"
			::= { sleBridgeBaseInfo 5 }

		
		sleBridgeVlanSupportMode OBJECT-TYPE
			SYNTAX BITS
				{
				portbased(0),
				protocolbased(1),
				subnetbased(2)
				}
			MAX-ACCESS read-only
			STATUS current
			DESCRIPTION
				"The supported VLAN mode for ingress untagged frame"
			::= { sleBridgeBaseInfo 6 }

		
		sleBridgeVlanMaxNum OBJECT-TYPE
			SYNTAX INTEGER (0..4096)
			MAX-ACCESS read-only
			STATUS current
			DESCRIPTION
				"sleBridgeVlanMaxNum"
			::= { sleBridgeBaseInfo 7 }

		
		sleBridgeDoubleTagProtoId OBJECT-TYPE
			SYNTAX INTEGER
				{
				dtag8100(33024),
				dtag9100(37120)
				}
			MAX-ACCESS read-only
			STATUS current
			DESCRIPTION
				"programmable Double Tag Protocol Identifier.
				It means outerTPID."
			::= { sleBridgeBaseInfo 8 }

		
		sleBridgeMirrorMode OBJECT-TYPE
			SYNTAX INTEGER
				{
				disabled(0),
				enabled(1)
				}
			MAX-ACCESS read-only
			STATUS current
			DESCRIPTION
				"Mirror mode of bridge"
			::= { sleBridgeBaseInfo 9 }

		
		sleBridgeMirrorMonitorPortId OBJECT-TYPE
			SYNTAX INTEGER (1..255)
			MAX-ACCESS read-only
			STATUS current
			DESCRIPTION
				"Mirroring port ID
				1-254: physical port ID
				255: mirror to cpu"
			::= { sleBridgeBaseInfo 10 }

		
		sleBridgeMirroredIngressPorts OBJECT-TYPE
			SYNTAX OCTET STRING (SIZE (0..32))
			MAX-ACCESS read-only
			STATUS current
			DESCRIPTION
				"Ingress mirrored port map"
			::= { sleBridgeBaseInfo 11 }

		
		sleBridgeMirroredEgressPorts OBJECT-TYPE
			SYNTAX OCTET STRING (SIZE (0..32))
			MAX-ACCESS read-only
			STATUS current
			DESCRIPTION
				"Egress mirrored port map"
			::= { sleBridgeBaseInfo 12 }

		
		sleBridgeMaxLearnPerUnit OBJECT-TYPE
			SYNTAX INTEGER (-1..2147483647)
			MAX-ACCESS read-only
			STATUS current
			DESCRIPTION
				"Limit maximum number of MAC addresses learning 
				newly per unit time(one second) on a bridge.
				(0: nothing learned, -l: unlimited.)"
			::= { sleBridgeBaseInfo 13 }

		
		sleBridgeFdbAgeingTime OBJECT-TYPE
			SYNTAX Integer32 (10..21474830)
			MAX-ACCESS read-only
			STATUS current
			DESCRIPTION
				"The timeout period in seconds for aging out 
				dynamically learned forwarding information."
			DEFVAL { 300 }
			::= { sleBridgeBaseInfo 14 }

		
		sleBridgeFdbMaxEntries OBJECT-TYPE
			SYNTAX Integer32
			MAX-ACCESS read-only
			STATUS current
			DESCRIPTION
				"The supported maximum fdb entries."
			::= { sleBridgeBaseInfo 15 }

		
		sleBridgeFdbCurrentEntries OBJECT-TYPE
			SYNTAX Integer32
			MAX-ACCESS read-only
			STATUS current
			DESCRIPTION
				"Number of Fdb entries learned currently."
			::= { sleBridgeBaseInfo 16 }

		
		sleBridgeStackMode OBJECT-TYPE
			SYNTAX INTEGER
				{
				disable(0),
				master(1),
				slave(2)
				}
			MAX-ACCESS read-only
			STATUS current
			DESCRIPTION
				"Stack status of device."
			::= { sleBridgeBaseInfo 17 }

		
		sleBridgeStackDeviceName OBJECT-TYPE
			SYNTAX OCTET STRING (SIZE (0..8))
			MAX-ACCESS read-only
			STATUS current
			DESCRIPTION
				"Device name of stack device."
			::= { sleBridgeBaseInfo 18 }

		
		sleBridgeStackNodeId OBJECT-TYPE
			SYNTAX INTEGER (1..65534)
			MAX-ACCESS read-only
			STATUS current
			DESCRIPTION
				"Node ID of stack device"
			::= { sleBridgeBaseInfo 19 }

		
		sleBridgeLldpMessageTxInterval OBJECT-TYPE
			SYNTAX Integer32 (5..32768)
			MAX-ACCESS read-write
			STATUS current
			DESCRIPTION
				"The interval at which LLDP frames are transmitted on behalf of this LLDP agent."
			::= { sleBridgeBaseInfo 20 }

		
		sleBridgeLldpTxHoldMultiplier OBJECT-TYPE
			SYNTAX Integer32 (2..10)
			MAX-ACCESS read-write
			STATUS current
			DESCRIPTION
				"The time-to-live value expressed as a multiple of the sleBridgeLldpMessageTxInterval object."
			::= { sleBridgeBaseInfo 21 }

		
		sleBridgeLldpReinitDelay OBJECT-TYPE
			SYNTAX Integer32 (1..10)
			MAX-ACCESS read-write
			STATUS current
			DESCRIPTION
				"Delay (in units of seconds) from when lldpPortConfigAdminStatus object of a particular port  becomes 'disabled' until re-initialization will be attempted."
			::= { sleBridgeBaseInfo 22 }

		
		sleBridgeLldpTxDelay OBJECT-TYPE
			SYNTAX Integer32 (1..8192)
			MAX-ACCESS read-write
			STATUS current
			DESCRIPTION
				"Delay (in units of seconds) between successive LLDP frame transmissions initiated by value/status changes in the LLDP local systems MIB."
			::= { sleBridgeBaseInfo 23 }

		
		sleBridgeLldpNotificationInterval OBJECT-TYPE
			SYNTAX Integer32 (5..3600)
			MAX-ACCESS read-write
			STATUS current
			DESCRIPTION
				"The agent must not generate more than one lldpRemTablesChangenotification-event in the indicated period."
			DEFVAL { 5 }
			::= { sleBridgeBaseInfo 24 }

		
		sleBridgeLldpStatsRemTablesLastChangeTime OBJECT-TYPE
			SYNTAX TimeTicks
			MAX-ACCESS read-only
			STATUS current
			DESCRIPTION
				"The value of sysUpTime object (defined in IETF RFC 3418)at the time an entry is created, modified, or deleted in thein tables associated with the lldpRemoteSystemsData objects and all LLDP extension objects associated with remote systems."
			::= { sleBridgeBaseInfo 25 }

		
		sleBridgeLldpStatsRemTablesInserts OBJECT-TYPE
			SYNTAX Integer32
			MAX-ACCESS read-only
			STATUS current
			DESCRIPTION
				"The number of times the complete set of informationadvertised by a particular MSAP has been inserted into tables contained in lldpRemoteSystemsData and lldpExtensions objects."
			::= { sleBridgeBaseInfo 26 }

		
		sleBridgeLldpStatsRemTablesDeletes OBJECT-TYPE
			SYNTAX Integer32
			MAX-ACCESS read-only
			STATUS current
			DESCRIPTION
				"The number of times the complete set of informationadvertised by a particular MSAP has been deleted fromtables contained in lldpRemoteSystemsData and lldpExtensions objects."
			::= { sleBridgeBaseInfo 27 }

		
		sleBridgeLldpStatsRemTablesDrops OBJECT-TYPE
			SYNTAX Integer32
			MAX-ACCESS read-only
			STATUS current
			DESCRIPTION
				"The number of times the complete set of information advertised by a particular MSAP could not be entered intotables contained in lldpRemoteSystemsData and lldpExtensions objects because of insufficient resources."
			::= { sleBridgeBaseInfo 28 }

		
		sleBridgeLldpStatsRemTablesAgeouts OBJECT-TYPE
			SYNTAX Integer32
			MAX-ACCESS read-only
			STATUS current
			DESCRIPTION
				"The number of times the complete set of informationadvertised by a particular MSAP has been deleted from tables contained in lldpRemoteSystemsData and lldpExtensions objectsbecause the information timeliness interval has expired."
			::= { sleBridgeBaseInfo 29 }

		
		sleBridgeLldpLocalChassisIdSubtype OBJECT-TYPE
			SYNTAX INTEGER
				{
				chassisComponent(1),
				interfaceAlias(2),
				portComponent(3),
				macAddress(4),
				networkAddress(5),
				interfaceName(6),
				local(7)
				}
			MAX-ACCESS read-only
			STATUS current
			DESCRIPTION
				"The type of encoding used to identify the chassis associated with the local system."
			::= { sleBridgeBaseInfo 30 }

		
		sleBridgeLldpLocalChassisId OBJECT-TYPE
			SYNTAX OCTET STRING (SIZE (1..255))
			MAX-ACCESS read-only
			STATUS current
			DESCRIPTION
				"The string value used to identify the chassis component associated with the local system."
			::= { sleBridgeBaseInfo 31 }

		
		sleBridgeLldpLocalSysName OBJECT-TYPE
			SYNTAX OCTET STRING (SIZE (0..255))
			MAX-ACCESS read-only
			STATUS current
			DESCRIPTION
				"The string value used to identify the system name of the local system."
			::= { sleBridgeBaseInfo 32 }

		
		sleBridgeLldpLocalSysDes OBJECT-TYPE
			SYNTAX OCTET STRING (SIZE (0..255))
			MAX-ACCESS read-write
			STATUS current
			DESCRIPTION
				"The string value used to identify the system description of the local system."
			::= { sleBridgeBaseInfo 33 }

		
		sleBridgeLldpLocalSysCapSupported OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are supported on the local system."
			::= { sleBridgeBaseInfo 34 }

		
		sleBridgeLldpLocalSysCapEnabled OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are enabled on the local system."
			::= { sleBridgeBaseInfo 35 }

		
		sleBridgeStpActivity OBJECT-TYPE
			SYNTAX INTEGER
				{
				disabled(0),
				enabled(1)
				}
			MAX-ACCESS read-only
			STATUS current
			DESCRIPTION
				"The STP enabled/disabled status of the switch."
			::= { sleBridgeBaseInfo 36 }

		
		sleBridgeStpSelfLoop OBJECT-TYPE
			SYNTAX INTEGER
				{
				disable(0),
				enable(1)
				}
			MAX-ACCESS read-write
			STATUS current
			DESCRIPTION
				"The STP self loop
				0: disabled
				1: enabled
				"
			::= { sleBridgeBaseInfo 37 }

		
		sleBridgePvlanOnePromPortEnable OBJECT-TYPE
			SYNTAX INTEGER
				{
				disable(0),
				enable(1)
				}
			MAX-ACCESS read-write
			STATUS current
			DESCRIPTION
				"The value used to identify that a isolated port can be associated with only one or entire promiscuous ports on the local system."
			DEFVAL { 0 }
			::= { sleBridgeBaseInfo 38 }

		
		sleBridgeTcpSyncookie OBJECT-TYPE
			SYNTAX INTEGER
				{
				disable(0),
				enable(1)
				}
			MAX-ACCESS read-only
			STATUS current
			DESCRIPTION
				"The value permits only when transmitted cookies are returned after sending cookies with SYN"
			::= { sleBridgeBaseInfo 39 }

		
		sleBridgeTcpIgnoreRstUnknown OBJECT-TYPE
			SYNTAX INTEGER
				{
				disable(0),
				enable(1)
				}
			MAX-ACCESS read-only
			STATUS current
			DESCRIPTION
				"The value configures not to send the message that informs TCP connection cannot be done."
			::= { sleBridgeBaseInfo 40 }

		
		sleBridgeAutoInterfaceActivation OBJECT-TYPE
			SYNTAX INTEGER
				{
				enable(1),
				disable(2)
				}
			MAX-ACCESS read-only
			STATUS current
			DESCRIPTION
				"The value configures auto Interface activation.
				(supported only model 5924N)"
			::= { sleBridgeBaseInfo 41 }

		
		sleBridgeLoopDetectStatus OBJECT-TYPE
			SYNTAX INTEGER
				{
				enable(1),
				disable(2)
				}
			MAX-ACCESS read-only
			STATUS current
			DESCRIPTION
				"The global adminStatus of Loop-Detect."
			::= { sleBridgeBaseInfo 42 }

		
		sleBridgeLoopDetectPacketType OBJECT-TYPE
			SYNTAX INTEGER
				{
				laa(1),
				system(2)
				}
			MAX-ACCESS read-only
			STATUS current
			DESCRIPTION
				"The type of srcmac to be detected.
				1.laa : Locally Administered Address
				2.system : System MAC (default)"
			::= { sleBridgeBaseInfo 43 }

		
		sleBridgePvlanPromSelectMode OBJECT-TYPE
			SYNTAX INTEGER
				{
				normal(0),
				manual(1),
				stp(2),
				erp(3)
				}
			MAX-ACCESS read-only
			STATUS current
			DESCRIPTION
				"The value is used to indicate promiscuous ports selection mode:
				normal ?default
				manual ? by user
				stp ? by STP (not supported)
				erp ? by ERP
				"
			::= { sleBridgeBaseInfo 44 }

		
		sleBridgePvlanPromiscuousPorts OBJECT-TYPE
			SYNTAX OCTET STRING
			MAX-ACCESS read-only
			STATUS current
			DESCRIPTION
				"Bitmap of promiscuous ports on bridge."
			::= { sleBridgeBaseInfo 45 }

		
		sleBridgeInnerTagProtoId OBJECT-TYPE
			SYNTAX INTEGER
				{
				dtag8100(33024),
				dtag9100(37120)
				}
			MAX-ACCESS read-only
			STATUS current
			DESCRIPTION
				"programmable Inner Double Tag Protocol Identifier.
				It means innerTPID"
			::= { sleBridgeBaseInfo 46 }

		
		sleBridgeUnknownMcastBlockAllPorts OBJECT-TYPE
			SYNTAX INTEGER
				{
				enable(1),
				disable(2)
				}
			MAX-ACCESS read-only
			STATUS current
			DESCRIPTION
				"Unknown multicast block setting for all ports."
			::= { sleBridgeBaseInfo 47 }

		
		sleBridgeEcmpHashType OBJECT-TYPE
			SYNTAX INTEGER
				{
				sip(1),
				sipDip(2)
				}
			MAX-ACCESS read-only
			STATUS current
			DESCRIPTION
				"ECMP Hash Type"
			::= { sleBridgeBaseInfo 48 }

		
		sleBridgeTcpSynguard OBJECT-TYPE
			SYNTAX Integer32 (0..2147483647)
			MAX-ACCESS read-only
			STATUS current
			DESCRIPTION
				"The tcp-synguard bandwidth."
			::= { sleBridgeBaseInfo 49 }

		
		sleBridgeOuterTagProtoId OBJECT-TYPE
			SYNTAX INTEGER
				{
				dtag8100(33024),
				dtag9100(37120)
				}
			MAX-ACCESS read-only
			STATUS current
			DESCRIPTION
				"programmable outer Double Tag Protocol Identifier.
				It means OutTPID"
			::= { sleBridgeBaseInfo 50 }

		
		sleBridgeMacAntiSpoofing OBJECT-TYPE
			SYNTAX INTEGER
				{
				enable(1),
				disable(2)
				}
			MAX-ACCESS read-only
			STATUS current
			DESCRIPTION
				"The protect uplink mac address"
			::= { sleBridgeBaseInfo 51 }

		
		sleBridgeMacReplace OBJECT-TYPE
			SYNTAX INTEGER
				{
				enable(1),
				disable(2)
				}
			MAX-ACCESS read-only
			STATUS current
			DESCRIPTION
				"The mac address replace mode"
			::= { sleBridgeBaseInfo 52 }

		
		sleBridgeStormControlBcast OBJECT-TYPE
			SYNTAX INTEGER (0 | 1..65535)
			MAX-ACCESS read-only
			STATUS current
			DESCRIPTION
				"The Storm Control Broadcast Configuration
				0: disable bcast
				"
			::= { sleBridgeBaseInfo 53 }

		
		sleBridgeStormControlDLF OBJECT-TYPE
			SYNTAX INTEGER (0 | 1..65535)
			MAX-ACCESS read-only
			STATUS current
			DESCRIPTION
				"The Storm Control DLF Configuration
				0: disable DLF
				"
			::= { sleBridgeBaseInfo 54 }

		
		sleBridgeStormControlMulticast OBJECT-TYPE
			SYNTAX INTEGER (0 | 1..65535)
			MAX-ACCESS read-only
			STATUS current
			DESCRIPTION
				"The Storm Control MultiCast Configuration
				0: disable multicast
				"
			::= { sleBridgeBaseInfo 55 }

		
		sleBridgeMacLearningMode OBJECT-TYPE
			SYNTAX INTEGER
				{
				cml(1),
				sml(2),
				cmlsml(3)
				}
			MAX-ACCESS read-only
			STATUS current
			DESCRIPTION
				"The MAC Learning Mode.
				1: cml
				2: sml
				3: cmlsml"
			::= { sleBridgeBaseInfo 56 }

		
		sleBridgeLagGlobalDistMode OBJECT-TYPE
			SYNTAX INTEGER
				{
				none(0),
				srcmac(1),
				dstmac(2),
				srcdstmac(3),
				srcip(4),
				dstip(5),
				srcdstip(6),
				srcdstl4(7),
				label(8)
				}
			MAX-ACCESS read-only
			STATUS current
			DESCRIPTION
				"The LAG global distmode."
			::= { sleBridgeBaseInfo 57 }

		
		sleBridgeMultiPortLlcfPortA OBJECT-TYPE
			SYNTAX OCTET STRING
			MAX-ACCESS read-only
			STATUS current
			DESCRIPTION
				"The Multi port LLCF - RAPS East/West Port."
			::= { sleBridgeBaseInfo 58 }

		
		sleBridgeMultiPortLlcfPortB OBJECT-TYPE
			SYNTAX OCTET STRING
			MAX-ACCESS read-only
			STATUS current
			DESCRIPTION
				"The Multi port LLCF - RAPS East/West Port."
			::= { sleBridgeBaseInfo 59 }

		
		sleBridgeMultiPortLlcfUpPortC OBJECT-TYPE
			SYNTAX OCTET STRING
			MAX-ACCESS read-only
			STATUS current
			DESCRIPTION
				"The Multi port LLCF - force down ports"
			::= { sleBridgeBaseInfo 60 }

		
		sleBridgeMultiPortLlcfDownPortC OBJECT-TYPE
			SYNTAX OCTET STRING
			MAX-ACCESS read-only
			STATUS current
			DESCRIPTION
				"The Multi port LLCF - force down ports"
			::= { sleBridgeBaseInfo 61 }

		
		sleBridgeMultiPortLlcfPortAStatus OBJECT-TYPE
			SYNTAX INTEGER
				{
				none(0),
				loc(1),
				disable(2),
				forcedToDown(3)
				}
			MAX-ACCESS read-only
			STATUS current
			DESCRIPTION
				"The Multi port LLCF port's status."
			::= { sleBridgeBaseInfo 62 }

		
		sleBridgeMultiPortLlcfPortBStatus OBJECT-TYPE
			SYNTAX INTEGER
				{
				none(0),
				loc(1),
				disable(2),
				forcedToDown(3)
				}
			MAX-ACCESS read-only
			STATUS current
			DESCRIPTION
				"The Multi port LLCF port's status."
			::= { sleBridgeBaseInfo 63 }

		
		sleBridgeMultiPortLlcfUpPortCStatus OBJECT-TYPE
			SYNTAX INTEGER
				{
				none(0),
				loc(1),
				disable(2),
				forcedToDown(3)
				}
			MAX-ACCESS read-only
			STATUS current
			DESCRIPTION
				"The Multi port LLCF port's status."
			::= { sleBridgeBaseInfo 64 }

		
		sleBridgeMultiPortLlcfDownPortCStatus OBJECT-TYPE
			SYNTAX INTEGER
				{
				none(0),
				loc(1),
				disable(2),
				forcedToDown(3)
				}
			MAX-ACCESS read-only
			STATUS current
			DESCRIPTION
				"The Multi port LLCF port's status."
			::= { sleBridgeBaseInfo 65 }

		
		sleBridgeMultiPortLlcfTimer OBJECT-TYPE
			SYNTAX Integer32 (1000..10000)
			MAX-ACCESS read-only
			STATUS current
			DESCRIPTION
				"The LLCF's checking interval. 1000~10000ms
				
				(default: 2500ms)"
			::= { sleBridgeBaseInfo 66 }

		
		sleBridgeChannelGroupLacpMaxBundle OBJECT-TYPE
			SYNTAX Integer32 (1..8)
			MAX-ACCESS read-only
			STATUS current
			DESCRIPTION
				"The channel group LACP max bundle (range 1..8)"
			::= { sleBridgeBaseInfo 67 }

		
		sleBridgeChannelGroupSystemPriority OBJECT-TYPE
			SYNTAX Integer32 (1..65535)
			MAX-ACCESS read-only
			STATUS current
			DESCRIPTION
				"The channel group system priority (default:32768)"
			::= { sleBridgeBaseInfo 68 }

		
		sleBridgeId OBJECT-TYPE
			SYNTAX Integer32 (1..32)
			MAX-ACCESS read-only
			STATUS current
			DESCRIPTION
				"The object is display bridgeId"
			::= { sleBridgeBaseInfo 69 }

		
		sleBridgeProtocol OBJECT-TYPE
			SYNTAX INTEGER
				{
				none(0),
				enableBridgeProtocolIeee(1),
				enableBridgeProtocolIeeeVlan(2),
				enableBridgeProtocolProviderMstp(3),
				enableBridgeProtocolProviderMstpEdge(4)
				}
			MAX-ACCESS read-only
			STATUS current
			DESCRIPTION
				"This object to display the bridge Protocol"
			::= { sleBridgeBaseInfo 70 }

		
		sleBridgeBaseControl OBJECT IDENTIFIER ::= { sleBridgeBase 2 }

		
		sleBridgeControlRequest OBJECT-TYPE
			SYNTAX INTEGER
				{
				setLacpProfile(1),
				setDoubleTagProtoId(2),
				setMirrorProfile(3),
				setMaxLearnPerUnit(4),
				setFdbAgeingTime(5),
				setStackProfile(6),
				setLldpProfile(7),
				setStpProfile(8),
				setTcpSyncookie(9),
				setTcpIgnoreRstUnknown(10),
				setAutoInterfaceActivation(11),
				setLoopDetectProfile(12),
				setPvlanPromSelectMode(13),
				setInnerTagProtoId(14),
				setUnknownMcastBlockAllPorts(15),
				setEcmpHashType(16),
				setTcpSynguard(17),
				setOuterTagProtoId(18),
				setMacAntiSpoofing(19),
				setMacReplace(20),
				setStormControl(21),
				setMacLearningMode(22),
				setLagGlobalDistMode(23),
				setMultiPortLlcf(24),
				delMultiPortLlcf(25),
				setMultiPortLlcfTimer(26),
				setChannelGroupLacpMaxBundle(27),
				delChannelGroupLacpMaxBundle(28),
				setChannelGroupSystemPriority(29),
				delChannelGroupSystemPriority(30),
				setBridgeProtocol(31),
				unsetBridgeProtocol(32)
				}
			MAX-ACCESS read-write
			STATUS current
			DESCRIPTION
				"The request of a user command"
			::= { sleBridgeBaseControl 1 }

		
		sleBridgeControlStatus OBJECT-TYPE
			SYNTAX SleControlStatusType
			MAX-ACCESS read-only
			STATUS current
			DESCRIPTION
				" The status of user command"
			::= { sleBridgeBaseControl 2 }

		
		sleBridgeControlTimer OBJECT-TYPE
			SYNTAX Gauge32
			MAX-ACCESS read-write
			STATUS current
			DESCRIPTION
				" The maximum time for the manager for a long running user command"
			::= { sleBridgeBaseControl 3 }

		
		sleBridgeControlTimeStamp OBJECT-TYPE
			SYNTAX TimeTicks
			MAX-ACCESS read-only
			STATUS current
			DESCRIPTION
				" The time stamp of the last command(end of command)"
			::= { sleBridgeBaseControl 4 }

		
		sleBridgeControlReqResult OBJECT-TYPE
			SYNTAX SleControlRequestResultType
			MAX-ACCESS read-only
			STATUS current
			DESCRIPTION
				"The result of the last user command"
			::= { sleBridgeBaseControl 5 }

		
		sleBridgeControlLacpActivity OBJECT-TYPE
			SYNTAX INTEGER
				{
				disabled(0),
				enabled(1)
				}
			MAX-ACCESS read-write
			STATUS current
			DESCRIPTION
				" The LACP enabled/disabled status of the switch"
			::= { sleBridgeBaseControl 6 }

		
		sleBridgeControlLacpPriority OBJECT-TYPE
			SYNTAX INTEGER (1..65535)
			MAX-ACCESS read-write
			STATUS current
			DESCRIPTION
				" The priority assigned to the Actor System"
			::= { sleBridgeBaseControl 7 }

		
		sleBridgeControlDoubleTagProtoId OBJECT-TYPE
			SYNTAX Integer32
			MAX-ACCESS read-write
			STATUS current
			DESCRIPTION
				" programmable Double Tag Protocol Identifier.
				It means outerTPID.
				"
			::= { sleBridgeBaseControl 8 }

		
		sleBridgeControlMirrorMode OBJECT-TYPE
			SYNTAX INTEGER
				{
				disabled(0),
				enabled(1)
				}
			MAX-ACCESS read-write
			STATUS current
			DESCRIPTION
				" Mirror mode of bridge"
			::= { sleBridgeBaseControl 9 }

		
		sleBridgeControlMirrorMonitorPortId OBJECT-TYPE
			SYNTAX INTEGER (1..255)
			MAX-ACCESS read-write
			STATUS current
			DESCRIPTION
				"Mirroring port ID
				1-254: physical port ID
				255: mirror to cpu"
			::= { sleBridgeBaseControl 10 }

		
		sleBridgeControlMaxLearnPerUnit OBJECT-TYPE
			SYNTAX INTEGER (-1..2147483647)
			MAX-ACCESS read-write
			STATUS current
			DESCRIPTION
				"Limit maximum number of MAC addresses learning 
				newly per unit time(one second) on a bridge.
				(0: nothing learned, -l: unlimited.)"
			::= { sleBridgeBaseControl 11 }

		
		sleBridgeControlFdbAgeingTime OBJECT-TYPE
			SYNTAX Unsigned32 (10..21474830)
			MAX-ACCESS read-write
			STATUS current
			DESCRIPTION
				"The timeout period in seconds for aging out
				dynamically learned forwarding information."
			DEFVAL { 300 }
			::= { sleBridgeBaseControl 12 }

		
		sleBridgeControlStackMode OBJECT-TYPE
			SYNTAX INTEGER
				{
				disable(0),
				master(1),
				slave(2)
				}
			MAX-ACCESS read-write
			STATUS current
			DESCRIPTION
				"Stack status of device."
			::= { sleBridgeBaseControl 13 }

		
		sleBridgeControlStackDeviceName OBJECT-TYPE
			SYNTAX OCTET STRING (SIZE (0..8))
			MAX-ACCESS read-write
			STATUS current
			DESCRIPTION
				"Device name of stack device."
			::= { sleBridgeBaseControl 14 }

		
		sleBridgeControlLldpMessageTxInterval OBJECT-TYPE
			SYNTAX INTEGER (5..32767)
			MAX-ACCESS read-write
			STATUS current
			DESCRIPTION
				" The interval at which LLDP frames are transmitted on behalf of this LLDP agent."
			::= { sleBridgeBaseControl 15 }

		
		sleBridgeControlLldpTxHoldMultiplier OBJECT-TYPE
			SYNTAX INTEGER (2..10)
			MAX-ACCESS read-write
			STATUS current
			DESCRIPTION
				"The time-to-live value expressed as a multiple of the sleBridgeLldpMessageTxInterval object."
			::= { sleBridgeBaseControl 16 }

		
		sleBridgeControlLldpReinitDelay OBJECT-TYPE
			SYNTAX INTEGER (1..10)
			MAX-ACCESS read-write
			STATUS current
			DESCRIPTION
				" Delay (in units of seconds) from when lldpPortConfigAdminStatus object of a particular port  becomes 'disabled' until re-initialization will be attempted."
			::= { sleBridgeBaseControl 17 }

		
		sleBridgeControlLldpTxDelay OBJECT-TYPE
			SYNTAX INTEGER (1..8192)
			MAX-ACCESS read-write
			STATUS current
			DESCRIPTION
				"Delay (in units of seconds) between successive LLDP frame transmissions initiated by value/status changes in the LLDP local systems MIB."
			::= { sleBridgeBaseControl 18 }

		
		sleBridgeControlLldpNotificationInterval OBJECT-TYPE
			SYNTAX INTEGER (5..3600)
			MAX-ACCESS read-write
			STATUS current
			DESCRIPTION
				" The agent must not generate more than one lldpRemTablesChangenotification-event in the indicated period."
			::= { sleBridgeBaseControl 19 }

		
		sleBridgeControlStpActivity OBJECT-TYPE
			SYNTAX INTEGER
				{
				disabled(0),
				enabled(1)
				}
			MAX-ACCESS read-write
			STATUS current
			DESCRIPTION
				" The STP enabled/disabled status of the switch."
			::= { sleBridgeBaseControl 20 }

		
		sleBridgeControlStpSelfLoop OBJECT-TYPE
			SYNTAX INTEGER
				{
				disable(0),
				enable(1)
				}
			MAX-ACCESS read-write
			STATUS current
			DESCRIPTION
				"The STP self loop
				0: disabled
				1: enabled"
			::= { sleBridgeBaseControl 21 }

		
		sleBridgeControlTcpSyncookie OBJECT-TYPE
			SYNTAX INTEGER
				{
				disable(0),
				enable(1)
				}
			MAX-ACCESS read-write
			STATUS current
			DESCRIPTION
				"The value permits only when transmitted cookies are returned after sending cookies with SYN"
			::= { sleBridgeBaseControl 22 }

		
		sleBridgeControlTcpIgnoreRstUnknown OBJECT-TYPE
			SYNTAX INTEGER
				{
				disable(0),
				enable(1)
				}
			MAX-ACCESS read-write
			STATUS current
			DESCRIPTION
				"The value configures not to send the message that informs TCP connection cannot be done."
			::= { sleBridgeBaseControl 23 }

		
		sleBridgeControlAutoInterfaceActivation OBJECT-TYPE
			SYNTAX INTEGER
				{
				enable(1),
				disable(2)
				}
			MAX-ACCESS read-write
			STATUS current
			DESCRIPTION
				"The value configures auto Interface activation.
				(supported only model 5924N)"
			::= { sleBridgeBaseControl 24 }

		
		sleBridgeControlLoopDetectStatus OBJECT-TYPE
			SYNTAX INTEGER
				{
				enable(1),
				disable(2)
				}
			MAX-ACCESS read-write
			STATUS current
			DESCRIPTION
				"The global adminStatus of Loop-Detect."
			::= { sleBridgeBaseControl 25 }

		
		sleBridgeControlLoopDetectPacketType OBJECT-TYPE
			SYNTAX INTEGER
				{
				laa(1),
				system(2)
				}
			MAX-ACCESS read-write
			STATUS current
			DESCRIPTION
				"The type of srcmac to be detected.
				1.laa : Locally Administered Address
				2.system : System MAC (default)"
			::= { sleBridgeBaseControl 26 }

		
		sleBridgeControlPvlanPromSelectMode OBJECT-TYPE
			SYNTAX INTEGER
				{
				normal(0),
				manual(1),
				stp(2),
				erp(3)
				}
			MAX-ACCESS read-write
			STATUS current
			DESCRIPTION
				"The value is used to indicate promiscuous ports selection mode:
				normal ?default
				manual ? by user
				stp ? by STP (not supported)
				erp ? by ERP"
			::= { sleBridgeBaseControl 27 }

		
		sleBridgeControlPvlanPromiscuousPorts OBJECT-TYPE
			SYNTAX OCTET STRING
			MAX-ACCESS read-write
			STATUS current
			DESCRIPTION
				"Valid if only if sleBridgeControlPvlanPromSelectMode is not manual.
				If sleBridgePvlanOnePromPortEnable is enabled, then it can only indicate one port or none."
			::= { sleBridgeBaseControl 28 }

		
		sleBridgeControlInnerTagProtoId OBJECT-TYPE
			SYNTAX INTEGER
				{
				dtag8100(33024),
				dtag9100(37120)
				}
			MAX-ACCESS read-write
			STATUS current
			DESCRIPTION
				"programmable Inner Double Tag Protocol Identifier. It means innerTPID."
			::= { sleBridgeBaseControl 29 }

		
		sleBridgeControlUnknownMcastBlockAllPorts OBJECT-TYPE
			SYNTAX INTEGER
				{
				enable(1),
				disable(2)
				}
			MAX-ACCESS read-write
			STATUS current
			DESCRIPTION
				"Unknown multicast block setting for all ports."
			::= { sleBridgeBaseControl 30 }

		
		sleBridgeControlEcmpHashType OBJECT-TYPE
			SYNTAX INTEGER
				{
				sip(1),
				sipDip(2)
				}
			MAX-ACCESS read-write
			STATUS current
			DESCRIPTION
				"ECMP Hash Type
				"
			::= { sleBridgeBaseControl 31 }

		
		sleBridgeControlTcpSynguard OBJECT-TYPE
			SYNTAX Integer32 (0..2147483647)
			MAX-ACCESS read-write
			STATUS current
			DESCRIPTION
				"The tcp-synguard bandwidth."
			::= { sleBridgeBaseControl 32 }

		
		sleBridgeControlOuterTagProtoId OBJECT-TYPE
			SYNTAX INTEGER
				{
				dtag8100(33024),
				dtag9100(37120)
				}
			MAX-ACCESS read-write
			STATUS current
			DESCRIPTION
				"programmable outer Double Tag Protocol Identifier.
				It means OutTPID"
			::= { sleBridgeBaseControl 33 }

		
		sleBridgeControlMacAntiSpoofing OBJECT-TYPE
			SYNTAX INTEGER
				{
				enable(1),
				disable(2)
				}
			MAX-ACCESS read-write
			STATUS current
			DESCRIPTION
				"The protect uplink mac address
				2011/01/20 V5924CR supports."
			::= { sleBridgeBaseControl 34 }

		
		sleBridgeControlMacReplace OBJECT-TYPE
			SYNTAX INTEGER
				{
				enable(1),
				disable(2)
				}
			MAX-ACCESS read-write
			STATUS current
			DESCRIPTION
				"The mac address replace mode
				2011/01/20 V5924CR supports."
			::= { sleBridgeBaseControl 35 }

		
		sleBridgeControlStormControlBcast OBJECT-TYPE
			SYNTAX INTEGER (0 | 1..65535)
			MAX-ACCESS read-write
			STATUS current
			DESCRIPTION
				"The Storm Control Broadcast Configuration
				0: disable bcast
				"
			::= { sleBridgeBaseControl 36 }

		
		sleBridgeControlStormControlDLF OBJECT-TYPE
			SYNTAX INTEGER (0 | 1..65535)
			MAX-ACCESS read-write
			STATUS current
			DESCRIPTION
				"The Storm Control DLF Configuration
				0: disable DLF
				"
			::= { sleBridgeBaseControl 37 }

		
		sleBridgeControlStormControlMulticast OBJECT-TYPE
			SYNTAX INTEGER (0 | 1..65535)
			MAX-ACCESS read-only
			STATUS current
			DESCRIPTION
				"The Storm Control Multicast Configuration
				0: disable multicast
				"
			::= { sleBridgeBaseControl 38 }

		
		sleBridgeControlMacLearningMode OBJECT-TYPE
			SYNTAX INTEGER
				{
				cml(1),
				sml(2),
				cmlsml(3)
				}
			MAX-ACCESS read-write
			STATUS current
			DESCRIPTION
				"The MAC Learning Mode.
				1: cml
				2: sml
				3: cmlsml"
			::= { sleBridgeBaseControl 39 }

		
		sleBridgeControlLagGlobalDistMode OBJECT-TYPE
			SYNTAX INTEGER
				{
				none(0),
				srcmac(1),
				dstmac(2),
				srcdstmac(3),
				srcip(4),
				dstip(5),
				srcdstip(6),
				srcdstl4(7),
				label(8)
				}
			MAX-ACCESS read-write
			STATUS current
			DESCRIPTION
				"The LAG global distmode."
			::= { sleBridgeBaseControl 40 }

		
		sleBridgeControlMultiPortLlcfPortA OBJECT-TYPE
			SYNTAX OCTET STRING
			MAX-ACCESS read-write
			STATUS current
			DESCRIPTION
				"The Multi port LLCF - RAPS East/West Port."
			::= { sleBridgeBaseControl 41 }

		
		sleBridgeControlMultiPortLlcfPortB OBJECT-TYPE
			SYNTAX OCTET STRING
			MAX-ACCESS read-write
			STATUS current
			DESCRIPTION
				"The Multi port LLCF - RAPS East/West Port."
			::= { sleBridgeBaseControl 42 }

		
		sleBridgeControlMultiPortLlcfPortC OBJECT-TYPE
			SYNTAX OCTET STRING
			MAX-ACCESS read-write
			STATUS current
			DESCRIPTION
				"The Multi port LLCF - force down ports"
			::= { sleBridgeBaseControl 43 }

		
		sleBridgeControlMultiPortLlcfTimer OBJECT-TYPE
			SYNTAX Integer32 (-1 | 1000..10000)
			MAX-ACCESS read-write
			STATUS current
			DESCRIPTION
				"The LLCF's checking interval. 1000~10000ms (default:2500ms)
				clear set value is -1."
			::= { sleBridgeBaseControl 44 }

		
		sleBridgeControlChannelGroupLacpMaxBundle OBJECT-TYPE
			SYNTAX Integer32 (1..8)
			MAX-ACCESS read-write
			STATUS current
			DESCRIPTION
				"The channel group LACP max bundle (range 1..8)"
			::= { sleBridgeBaseControl 45 }

		
		sleBridgeControlChannelGroupSystemPriority OBJECT-TYPE
			SYNTAX Integer32 (1..65535)
			MAX-ACCESS read-write
			STATUS current
			DESCRIPTION
				"The channel group system priority (default:32768)"
			::= { sleBridgeBaseControl 46 }

		
		sleBridgeControlId OBJECT-TYPE
			SYNTAX Integer32 (1..32)
			MAX-ACCESS read-write
			STATUS current
			DESCRIPTION
				"This object is used to set the bridgeid "
			::= { sleBridgeBaseControl 47 }

		
		sleBridgeControlProtocol OBJECT-TYPE
			SYNTAX INTEGER
				{
				enableBridgeProtocolIeee(1),
				enableBridgeProtocolIeeeVlan(2),
				enableBridgeProtocolProviderMstp(3),
				enableBridgeProtocolProviderMstpEdge(4)
				}
			MAX-ACCESS read-only
			STATUS current
			DESCRIPTION
				"This object to display the bridge Protocol"
			::= { sleBridgeBaseControl 48 }

		
		sleBridgeBaseNotification OBJECT IDENTIFIER ::= { sleBridgeBase 3 }

		
		sleBridgeLacpProfileChanged NOTIFICATION-TYPE
			OBJECTS { sleBridgeLacpActivity, sleBridgeLacpPriority, sleBridgeControlRequest, sleBridgeControlTimeStamp, sleBridgeControlReqResult
				 }
			STATUS current
			DESCRIPTION 
				" "
			::= { sleBridgeBaseNotification 1 }

		
		sleBridgeDoubleTagProtoIdChanged NOTIFICATION-TYPE
			OBJECTS { sleBridgeDoubleTagProtoId, sleBridgeControlRequest, sleBridgeControlTimeStamp, sleBridgeControlReqResult }
			STATUS current
			DESCRIPTION 
				" "
			::= { sleBridgeBaseNotification 2 }

		
		sleBridgeMirrorProfileChanged NOTIFICATION-TYPE
			OBJECTS { sleBridgeMirrorMode, sleBridgeMirrorMonitorPortId, sleBridgeControlRequest, sleBridgeControlTimeStamp, sleBridgeControlReqResult
				 }
			STATUS current
			DESCRIPTION 
				" "
			::= { sleBridgeBaseNotification 3 }

		
		sleBridgeMaxLearnPerUnitChanged NOTIFICATION-TYPE
			OBJECTS { sleBridgeControlRequest, sleBridgeControlTimeStamp, sleBridgeControlReqResult, sleBridgeMaxLearnPerUnit }
			STATUS current
			DESCRIPTION 
				"Description."
			::= { sleBridgeBaseNotification 4 }

		
		sleBridgeFdbAgeingTimeChanged NOTIFICATION-TYPE
			OBJECTS { sleBridgeFdbAgeingTime, sleBridgeControlRequest, sleBridgeControlTimeStamp, sleBridgeControlReqResult }
			STATUS current
			DESCRIPTION 
				"Changed Fdb ageding time."
			::= { sleBridgeBaseNotification 5 }

		
		sleBridgeStackProfileChanged NOTIFICATION-TYPE
			OBJECTS { sleBridgeStackMode, sleBridgeStackDeviceName, sleBridgeControlRequest, sleBridgeControlTimeStamp, sleBridgeControlReqResult
				 }
			STATUS current
			DESCRIPTION 
				"Changed Stack device's profile."
			::= { sleBridgeBaseNotification 6 }

		
		sleBridgeLldpProfileChanged NOTIFICATION-TYPE
			OBJECTS { sleBridgeLldpMessageTxInterval, sleBridgeLldpTxHoldMultiplier, sleBridgeLldpReinitDelay, sleBridgeLldpTxDelay, sleBridgeLldpNotificationInterval, 
				sleBridgeControlRequest, sleBridgeControlTimeStamp, sleBridgeControlReqResult }
			STATUS current
			DESCRIPTION 
				" "
			::= { sleBridgeBaseNotification 7 }

		
		sleBridgeStpProfileChanged NOTIFICATION-TYPE
			OBJECTS { sleBridgeControlRequest, sleBridgeControlReqResult, sleBridgeControlTimeStamp, sleBridgeStpActivity, sleBridgeStpSelfLoop
				 }
			STATUS current
			DESCRIPTION 
				" "
			::= { sleBridgeBaseNotification 8 }

		
		sleBridgeTcpSyncookieChanged NOTIFICATION-TYPE
			OBJECTS { sleBridgeControlRequest, sleBridgeControlTimeStamp, sleBridgeControlReqResult, sleBridgeTcpSyncookie }
			STATUS current
			DESCRIPTION 
				"Description."
			::= { sleBridgeBaseNotification 9 }

		
		sleBridgeTcpIgnoreRstUnknownChanged NOTIFICATION-TYPE
			OBJECTS { sleBridgeControlRequest, sleBridgeControlTimeStamp, sleBridgeControlReqResult, sleBridgeTcpIgnoreRstUnknown }
			STATUS current
			DESCRIPTION 
				"Description."
			::= { sleBridgeBaseNotification 10 }

		
		sleBridgeAutoInterfaceActivationChanged NOTIFICATION-TYPE
			OBJECTS { sleBridgeControlRequest, sleBridgeControlTimeStamp, sleBridgeControlReqResult, sleBridgeAutoInterfaceActivation }
			STATUS current
			DESCRIPTION 
				"Description."
			::= { sleBridgeBaseNotification 11 }

		
		sleBridgeLoopDetectProfileChanged NOTIFICATION-TYPE
			OBJECTS { sleBridgeControlRequest, sleBridgeControlTimeStamp, sleBridgeControlReqResult, sleBridgeLoopDetectStatus, sleBridgeLoopDetectPacketType
				 }
			STATUS current
			DESCRIPTION 
				"Description."
			::= { sleBridgeBaseNotification 12 }

		
		sleBridgePvlanPormSelectModeChanged NOTIFICATION-TYPE
			OBJECTS { sleBridgeControlRequest, sleBridgeControlTimeStamp, sleBridgeControlReqResult, sleBridgeControlPvlanPromSelectMode, sleBridgeControlPvlanPromiscuousPorts
				 }
			STATUS current
			DESCRIPTION 
				"Description."
			::= { sleBridgeBaseNotification 13 }

		
		sleBridgeInnerTagProtoIdChanged NOTIFICATION-TYPE
			OBJECTS { sleBridgeControlRequest, sleBridgeControlTimeStamp, sleBridgeControlReqResult, sleBridgeControlInnerTagProtoId }
			STATUS current
			DESCRIPTION 
				"Description."
			::= { sleBridgeBaseNotification 14 }

		
		sleBridgeUnknownMcastBlockAllPortsChanged NOTIFICATION-TYPE
			OBJECTS { sleBridgeControlRequest, sleBridgeControlTimeStamp, sleBridgeControlReqResult, sleBridgeControlUnknownMcastBlockAllPorts }
			STATUS current
			DESCRIPTION 
				"Description."
			::= { sleBridgeBaseNotification 15 }

		
		sleBridgeEcmpHashTypeChanged NOTIFICATION-TYPE
			OBJECTS { sleBridgeControlRequest, sleBridgeControlTimeStamp, sleBridgeControlReqResult, sleBridgeControlEcmpHashType }
			STATUS current
			DESCRIPTION 
				"Description."
			::= { sleBridgeBaseNotification 16 }

		
		sleBridgeTcpSynguardChanged NOTIFICATION-TYPE
			OBJECTS { sleBridgeTcpSynguard, sleBridgeControlRequest, sleBridgeControlTimeStamp, sleBridgeControlReqResult }
			STATUS current
			DESCRIPTION 
				"Description."
			::= { sleBridgeBaseNotification 17 }

		
		sleBridgeOuterTagProtoIdChanged NOTIFICATION-TYPE
			OBJECTS { sleBridgeControlRequest, sleBridgeControlTimeStamp, sleBridgeControlReqResult, sleBridgeControlOuterTagProtoId }
			STATUS current
			DESCRIPTION 
				"sleBridgeControlOuterTagProtoId"
			::= { sleBridgeBaseNotification 18 }

		
		sleBridgeMacAntiSpoofingChanged NOTIFICATION-TYPE
			OBJECTS { sleBridgeControlRequest, sleBridgeControlTimeStamp, sleBridgeControlReqResult, sleBridgeControlMacAntiSpoofing }
			STATUS current
			DESCRIPTION 
				"Description."
			::= { sleBridgeBaseNotification 19 }

		
		sleBridgeMacReplaceChanged NOTIFICATION-TYPE
			OBJECTS { sleBridgeControlRequest, sleBridgeControlTimeStamp, sleBridgeControlReqResult, sleBridgeControlMacReplace }
			STATUS current
			DESCRIPTION 
				"Description."
			::= { sleBridgeBaseNotification 20 }

		
		sleBridgeStormControlChanged NOTIFICATION-TYPE
			OBJECTS { sleBridgeControlRequest, sleBridgeControlTimeStamp, sleBridgeControlReqResult, sleBridgePortNum, sleBridgeControlStormControlBcast, 
				sleBridgeControlStormControlDLF, sleBridgeControlStormControlMulticast }
			STATUS current
			DESCRIPTION 
				"Description."
			::= { sleBridgeBaseNotification 21 }

		
		sleBridgeMacLearningModeChanged NOTIFICATION-TYPE
			OBJECTS { sleBridgeControlRequest, sleBridgeControlTimeStamp, sleBridgeControlReqResult, sleBridgeControlMacLearningMode }
			STATUS current
			DESCRIPTION 
				"Description."
			::= { sleBridgeBaseNotification 22 }

		
		sleBridgeLagGlobalDistModeChanged NOTIFICATION-TYPE
			OBJECTS { sleBridgeControlRequest, sleBridgeControlTimeStamp, sleBridgeControlReqResult, sleBridgeControlLagGlobalDistMode }
			STATUS current
			DESCRIPTION 
				"setLagGlobalDistMode"
			::= { sleBridgeBaseNotification 23 }

		
		sleBridgeMultiPortLlcfChanged NOTIFICATION-TYPE
			OBJECTS { sleBridgeControlRequest, sleBridgeControlTimeStamp, sleBridgeControlReqResult, sleBridgeControlMultiPortLlcfPortA, sleBridgeControlMultiPortLlcfPortB, 
				sleBridgeControlMultiPortLlcfPortC }
			STATUS current
			DESCRIPTION 
				"setMultiPortLlcf "
			::= { sleBridgeBaseNotification 24 }

		
		sleBridgeMultiPortLlcfDeleted NOTIFICATION-TYPE
			OBJECTS { sleBridgeControlRequest, sleBridgeControlTimeStamp, sleBridgeControlReqResult }
			STATUS current
			DESCRIPTION 
				"delMultiPortLlcf "
			::= { sleBridgeBaseNotification 25 }

		
		sleBridgeMultiPortLlcfTimerChanged NOTIFICATION-TYPE
			OBJECTS { sleBridgeControlRequest, sleBridgeControlTimeStamp, sleBridgeControlReqResult, sleBridgeControlMultiPortLlcfTimer }
			STATUS current
			DESCRIPTION 
				"setMultiPortLlcfTimer "
			::= { sleBridgeBaseNotification 26 }

		
		sleBridgeChannelGroupLacpMaxBundleChanged NOTIFICATION-TYPE
			OBJECTS { sleBridgeControlRequest, sleBridgeControlTimeStamp, sleBridgeControlReqResult, sleBridgeControlChannelGroupLacpMaxBundle }
			STATUS current
			DESCRIPTION 
				"setChannelGroupLacpMaxBundle"
			::= { sleBridgeBaseNotification 27 }

		
		sleBridgeChannelGroupLacpMaxBundleDeleted NOTIFICATION-TYPE
			OBJECTS { sleBridgeControlRequest, sleBridgeControlTimeStamp, sleBridgeControlReqResult }
			STATUS current
			DESCRIPTION 
				"delChannelGroupLacpMaxBundle "
			::= { sleBridgeBaseNotification 28 }

		
		sleBridgeChannelGroupSystemPriorityChanged NOTIFICATION-TYPE
			OBJECTS { sleBridgeControlRequest, sleBridgeControlTimeStamp, sleBridgeControlReqResult, sleBridgeControlChannelGroupSystemPriority }
			STATUS current
			DESCRIPTION 
				"setChannelGroupSystemPriority "
			::= { sleBridgeBaseNotification 29 }

		
		sleBridgeChannelGroupSystemPriorityDeleted NOTIFICATION-TYPE
			OBJECTS { sleBridgeControlRequest, sleBridgeControlTimeStamp, sleBridgeControlReqResult }
			STATUS current
			DESCRIPTION 
				"delChannelGroupSystemPriority "
			::= { sleBridgeBaseNotification 30 }

		
		sleBridgePort OBJECT IDENTIFIER ::= { sleBridge 2 }

		
		sleBridgePortTable OBJECT-TYPE
			SYNTAX SEQUENCE OF SleBridgePortEntry
			MAX-ACCESS not-accessible
			STATUS current
			DESCRIPTION
				"Bridge Port Table"
			::= { sleBridgePort 1 }

		
		sleBridgePortEntry OBJECT-TYPE
			SYNTAX SleBridgePortEntry
			MAX-ACCESS not-accessible
			STATUS current
			DESCRIPTION
				"Bridge Port Entry
				key: sleBridgePortIndex"
			INDEX { sleBridgePortIndex }
			::= { sleBridgePortTable 1 }

		
		SleBridgePortEntry ::=
			SEQUENCE { 
				sleBridgePortIndex
					INTEGER,
				sleBridgePortIfIndex
					INTEGER,
				sleBridgePortPVid
					INTEGER,
				sleBridgePortMaxHosts
					INTEGER,
				sleBridgePortCurrentHosts
					INTEGER,
				sleBridgePortMaxLearnPerUnit
					INTEGER,
				sleBridgePortMACFilterPermission
					INTEGER,
				sleBridgePortIngMirrorStatus
					INTEGER,
				sleBridgePortEgMirrorStatus
					INTEGER,
				sleBridgePortBcastThreshold
					INTEGER,
				sleBridgePortMcastThreshold
					INTEGER,
				sleBridgePortDlfThreshold
					INTEGER,
				sleBridgePortQinQStatus
					INTEGER,
				sleBridgePortAdminLinktype
					INTEGER,
				sleBridgePortAdminEdgemode
					INTEGER,
				sleBridgePortOperLinktype
					INTEGER,
				sleBridgePortOperEdgemode
					INTEGER,
				sleBridgePortStpBpduFilter
					INTEGER,
				sleBridgePortPvlanIsolatedStatus
					INTEGER,
				sleBridgePortPvlanPromPorts
					OCTET STRING,
				sleBridgePortDhcpFilterServer
					INTEGER,
				sleBridgePortLoopDetectStatus
					INTEGER,
				sleBridgePortLoopDetectBlock
					INTEGER,
				sleBridgePortLoopDetectPeriod
					INTEGER,
				sleBridgePortLoopDetectTimer
					INTEGER,
				sleBridgePortLoopDetectBlockStatus
					INTEGER,
				sleBridgePortNetBIOSFilter
					INTEGER,
				sleBridgePortPushInnertag
					INTEGER,
				sleBridgePortPopInnertag
					INTEGER,
				sleBridgePortInnertag
					INTEGER,
				sleBridgePortPriority
					INTEGER,
				sleBridgePortInner2outerPri
					INTEGER,
				sleBridgePortInner2outerVid
					INTEGER,
				sleBridgePortLinkUpCnt
					INTEGER,
				sleBridgePortLinkDownCnt
					INTEGER,
				sleBridgePortLinkUpTime
					Counter64,
				sleBridgePortElapsedTimeAfterClearStats
					Counter64,
				sleBridgePortMACLearningStatus
					INTEGER,
				sleBridgePortPortBridgeStatus
					INTEGER,
				sleBridgePortUnknownMcastBlock
					INTEGER,
				sleBridgePortDescription
					OCTET STRING,
				sleBridgePortHoldTime
					Integer32,
				sleBridgePortMacAntiSpoofing
					TruthValue,
				sleBridgePortSwitchType
					INTEGER,
				sleBridgePortSwitchState
					INTEGER,
				sleBridgePortSwitchMode
					INTEGER,
				sleBridgePortSwitchSubMode
					INTEGER,
				sleBridgePortSwitchDefaultVlan
					Integer32,
				sleBridgePortSwitchIngressFilter
					INTEGER,
				sleBridgePortSwitchAccFrameType
					BITS,
				sleBridgePortSwitchNativeVid
					Integer32,
				sleBridgePortSwitchAllowedVlan
					OCTET STRING,
				sleBridgePortSwitchAllowedVlanEtag
					OCTET STRING,
				sleBridgePortSwitchChannelType
					INTEGER,
				sleBridgePortSwitchStaticChannelGroup
					OCTET STRING,
				sleBridgePortSwitchChannelLoadbalance
					INTEGER,
				sleBridgePortSwitchAggrType
					INTEGER,
				sleBridgePortSwitchAggrId
					Integer32,
				sleBridgePortSwitchAggrMode
					INTEGER,
				sleBridgePortLoopDetectPeriodMs
					INTEGER,
				sleBridgePortLoopDetectAdminCount
					Integer32,
				sleBridgePortLoopDetectOperCount
					Integer32,
				sleBridgePortLoopDetectDetectedCount
					Integer32,
				sleBridgePortLoopDetectVlan
					Integer32,
				sleBridgePortMaxNewHosts
					Integer32,
				sleBridgePortStpStatus
					INTEGER,
				sleBridgePortStpBpduGuard
					INTEGER,
				sleBridgePortOuterTpid
					Integer32,
				sleBridgePortMirrorMonitor
					INTEGER,
				sleBridgePortBandwidth
					OCTET STRING,
				sleBridgePortAlias
					OCTET STRING,
				sleBridgePortMulticast
					INTEGER,
				sleBridgePortFloodBlock
					BITS
			 }

		sleBridgePortIndex OBJECT-TYPE
			SYNTAX INTEGER (1..65535)
			MAX-ACCESS read-only
			STATUS current
			DESCRIPTION
				"Same as ifIndex (for all ifTable entries),
				additionally aggregation group index values available."
			::= { sleBridgePortEntry 1 }

		
		sleBridgePortIfIndex OBJECT-TYPE
			SYNTAX INTEGER (1..4094)
			MAX-ACCESS read-only
			STATUS current
			DESCRIPTION
				"Bridge Interface Index."
			::= { sleBridgePortEntry 2 }

		
		sleBridgePortPVid OBJECT-TYPE
			SYNTAX INTEGER (1..4094)
			MAX-ACCESS read-only
			STATUS current
			DESCRIPTION
				"The PVID of port. 
				Taken if no other rule given for VLAN association. 
				If aggregated: only for group."
			::= { sleBridgePortEntry 3 }

		
		sleBridgePortMaxHosts OBJECT-TYPE
			SYNTAX INTEGER (0..2147483647)
			MAX-ACCESS read-only
			STATUS current
			DESCRIPTION
				"The maximum number of hosts allowed. 
				Aggregation group available. Value 0 is allowed. 
				Default value is -1: it means unlimited. "
			::= { sleBridgePortEntry 4 }

		
		sleBridgePortCurrentHosts OBJECT-TYPE
			SYNTAX INTEGER (0..65535)
			MAX-ACCESS read-only
			STATUS current
			DESCRIPTION
				"The number hosts which is allowed to be used. 
				Aggregation group available."
			::= { sleBridgePortEntry 5 }

		
		sleBridgePortMaxLearnPerUnit OBJECT-TYPE
			SYNTAX INTEGER (-1..2147483647)
			MAX-ACCESS read-only
			STATUS current
			DESCRIPTION
				"Limit maximum number of MAC addresses learning 
				newly per unit time(one second) on a port.
				(0: nothing learned, -l: unlimited.)"
			::= { sleBridgePortEntry 6 }

		
		sleBridgePortMACFilterPermission OBJECT-TYPE
			SYNTAX INTEGER
				{
				deny(0),
				permit(1)
				}
			MAX-ACCESS read-only
			STATUS current
			DESCRIPTION
				"The default permission for mac filtering. 
				Valid only for physical ports,
				use values from MFDB Table. "
			DEFVAL { 1 }
			::= { sleBridgePortEntry 7 }

		
		sleBridgePortIngMirrorStatus OBJECT-TYPE
			SYNTAX INTEGER
				{
				disable(0),
				enable(1)
				}
			MAX-ACCESS read-only
			STATUS current
			DESCRIPTION
				"Mirroring on ingress packets. 
				Valid only for physical ports. "
			DEFVAL { 0 }
			::= { sleBridgePortEntry 8 }

		
		sleBridgePortEgMirrorStatus OBJECT-TYPE
			SYNTAX INTEGER
				{
				disable(0),
				enable(1)
				}
			MAX-ACCESS read-only
			STATUS current
			DESCRIPTION
				"Mirroring on egress packets. 
				Valid only for physical ports. "
			DEFVAL { 0 }
			::= { sleBridgePortEntry 9 }

		
		sleBridgePortBcastThreshold OBJECT-TYPE
			SYNTAX INTEGER (0..2097150)
			MAX-ACCESS read-only
			STATUS current
			DESCRIPTION
				"Broadcast packet rate limit(unit: packets/s),
				Valid only for physical ports. 
				Default value is 0: it means BCSC clear-state.
				Value Range: 0-262142(TX/FX),0-2097150(GBIC)."
			DEFVAL { 0 }
			::= { sleBridgePortEntry 10 }

		
		sleBridgePortMcastThreshold OBJECT-TYPE
			SYNTAX INTEGER (0..2097150)
			MAX-ACCESS read-only
			STATUS current
			DESCRIPTION
				"Multicast packet rate limit.(unit: packets/s), 
				Valid only for physical ports. 
				Default value is 0: it means BCSC clear-state.
				Value Range: 0-262142(TX/FX),0-2097150(GBIC)."
			DEFVAL { 0 }
			::= { sleBridgePortEntry 11 }

		
		sleBridgePortDlfThreshold OBJECT-TYPE
			SYNTAX INTEGER (0..2097150)
			MAX-ACCESS read-only
			STATUS current
			DESCRIPTION
				"DLF packet rate limit(unit: packets/s), 
				Valid only for physical ports.
				Default value is 0: it means BCSC clear-state.
				Value Range: 0-262142(TX/FX),0-2097150(GBIC)."
			DEFVAL { 0 }
			::= { sleBridgePortEntry 12 }

		
		sleBridgePortQinQStatus OBJECT-TYPE
			SYNTAX INTEGER
				{
				disable(0),
				enable(1)
				}
			MAX-ACCESS read-only
			STATUS current
			DESCRIPTION
				"QinQ Status of the port. 
				Valid only for physical ports. "
			DEFVAL { 0 }
			::= { sleBridgePortEntry 13 }

		
		sleBridgePortAdminLinktype OBJECT-TYPE
			SYNTAX INTEGER
				{
				shared(0),
				pointTopoint(1),
				automatic(2)
				}
			MAX-ACCESS read-only
			STATUS current
			DESCRIPTION
				"The administrative link-type of port on the xSTP."
			DEFVAL { 2 }
			::= { sleBridgePortEntry 14 }

		
		sleBridgePortAdminEdgemode OBJECT-TYPE
			SYNTAX INTEGER
				{
				disable(0),
				enable(1)
				}
			MAX-ACCESS read-only
			STATUS current
			DESCRIPTION
				"The administrative edgemode of port on the xSTP."
			DEFVAL { 0 }
			::= { sleBridgePortEntry 15 }

		
		sleBridgePortOperLinktype OBJECT-TYPE
			SYNTAX INTEGER
				{
				shared(0),
				pointTopoint(1)
				}
			MAX-ACCESS read-only
			STATUS current
			DESCRIPTION
				"The link-type of the port on the xSTP."
			::= { sleBridgePortEntry 16 }

		
		sleBridgePortOperEdgemode OBJECT-TYPE
			SYNTAX INTEGER
				{
				disabled(0),
				enabled(1)
				}
			MAX-ACCESS read-only
			STATUS current
			DESCRIPTION
				"The edge-mode of the port on the xSTP."
			::= { sleBridgePortEntry 17 }

		
		sleBridgePortStpBpduFilter OBJECT-TYPE
			SYNTAX INTEGER
				{
				disable(0),
				enable(1)
				}
			MAX-ACCESS read-only
			STATUS current
			DESCRIPTION
				"The stp bpdu-filter of the port on the xSTP. Default value is 0. "
			::= { sleBridgePortEntry 18 }

		
		sleBridgePortPvlanIsolatedStatus OBJECT-TYPE
			SYNTAX INTEGER
				{
				disable(0),
				enable(1)
				}
			MAX-ACCESS read-only
			STATUS current
			DESCRIPTION
				"Isolated status of this port. Default value is disable(0). "
			DEFVAL { 0 }
			::= { sleBridgePortEntry 19 }

		
		sleBridgePortPvlanPromPorts OBJECT-TYPE
			SYNTAX OCTET STRING
			MAX-ACCESS read-only
			STATUS current
			DESCRIPTION
				"Portlist for promiscuous ports of this port. The OctetString is a list of pairs of octets each identify an sheBridgePortIndex. The least significant byte is the second octet."
			::= { sleBridgePortEntry 20 }

		
		sleBridgePortDhcpFilterServer OBJECT-TYPE
			SYNTAX INTEGER
				{
				disable(0),
				enable(1)
				}
			MAX-ACCESS read-only
			STATUS current
			DESCRIPTION
				"DHCP filter server status
				0: disabled
				1: enabled"
			::= { sleBridgePortEntry 21 }

		
		sleBridgePortLoopDetectStatus OBJECT-TYPE
			SYNTAX INTEGER
				{
				enable(1),
				disable(2)
				}
			MAX-ACCESS read-only
			STATUS current
			DESCRIPTION
				"The adminStatus of loop-detect per ports."
			::= { sleBridgePortEntry 22 }

		
		sleBridgePortLoopDetectBlock OBJECT-TYPE
			SYNTAX INTEGER
				{
				enable(1),
				disable(2)
				}
			MAX-ACCESS read-only
			STATUS current
			DESCRIPTION
				"The adminBlock mode of loop-detect per ports.
				Indicate whether block port or not."
			::= { sleBridgePortEntry 23 }

		
		sleBridgePortLoopDetectPeriod OBJECT-TYPE
			SYNTAX INTEGER (1..60)
			MAX-ACCESS read-only
			STATUS current
			DESCRIPTION
				"The sending period of detection packet."
			::= { sleBridgePortEntry 24 }

		
		sleBridgePortLoopDetectTimer OBJECT-TYPE
			SYNTAX INTEGER (0 | 1..86400)
			MAX-ACCESS read-only
			STATUS current
			DESCRIPTION
				"The Blocked list expire timer."
			::= { sleBridgePortEntry 25 }

		
		sleBridgePortLoopDetectBlockStatus OBJECT-TYPE
			SYNTAX INTEGER
				{
				block(1),
				unblock(2)
				}
			MAX-ACCESS read-only
			STATUS current
			DESCRIPTION
				"The operStauts of loop-detect per ports."
			::= { sleBridgePortEntry 26 }

		
		sleBridgePortNetBIOSFilter OBJECT-TYPE
			SYNTAX INTEGER
				{
				disable(0),
				enable(1)
				}
			MAX-ACCESS read-only
			STATUS current
			DESCRIPTION
				"The netBios filter status per ports"
			::= { sleBridgePortEntry 27 }

		
		sleBridgePortPushInnertag OBJECT-TYPE
			SYNTAX INTEGER
				{
				disable(0),
				enable(1)
				}
			MAX-ACCESS read-only
			STATUS current
			DESCRIPTION
				"The ingress port that push inner-tag"
			::= { sleBridgePortEntry 28 }

		
		sleBridgePortPopInnertag OBJECT-TYPE
			SYNTAX INTEGER
				{
				disable(0),
				enable(1)
				}
			MAX-ACCESS read-only
			STATUS current
			DESCRIPTION
				"The egress port that pop inner-tag"
			::= { sleBridgePortEntry 29 }

		
		sleBridgePortInnertag OBJECT-TYPE
			SYNTAX INTEGER (0..4096)
			MAX-ACCESS read-only
			STATUS current
			DESCRIPTION
				"The inner-tag value to push for incoming untagged packet"
			::= { sleBridgePortEntry 30 }

		
		sleBridgePortPriority OBJECT-TYPE
			SYNTAX INTEGER (0..7)
			MAX-ACCESS read-only
			STATUS current
			DESCRIPTION
				"The port priority value for incoming untagged packet"
			::= { sleBridgePortEntry 31 }

		
		sleBridgePortInner2outerPri OBJECT-TYPE
			SYNTAX INTEGER
				{
				disable(0),
				enable(1)
				}
			MAX-ACCESS read-only
			STATUS current
			DESCRIPTION
				"Use inner-tag’s priority as outer-tag’s priority."
			::= { sleBridgePortEntry 32 }

		
		sleBridgePortInner2outerVid OBJECT-TYPE
			SYNTAX INTEGER
				{
				disable(0),
				enable(1)
				}
			MAX-ACCESS read-only
			STATUS current
			DESCRIPTION
				"Use inner-tag’s vlan-id as outer-tag’s vlan-id."
			::= { sleBridgePortEntry 33 }

		
		sleBridgePortLinkUpCnt OBJECT-TYPE
			SYNTAX INTEGER (1..65535)
			MAX-ACCESS read-only
			STATUS current
			DESCRIPTION
				"The times of link-up event"
			::= { sleBridgePortEntry 34 }

		
		sleBridgePortLinkDownCnt OBJECT-TYPE
			SYNTAX INTEGER (1..65535)
			MAX-ACCESS read-only
			STATUS current
			DESCRIPTION
				"The times of link-down event"
			::= { sleBridgePortEntry 35 }

		
		sleBridgePortLinkUpTime OBJECT-TYPE
			SYNTAX Counter64
			UNITS "1 sec"
			MAX-ACCESS read-only
			STATUS current
			DESCRIPTION
				"The elapsed time after link is up."
			::= { sleBridgePortEntry 36 }

		
		sleBridgePortElapsedTimeAfterClearStats OBJECT-TYPE
			SYNTAX Counter64
			UNITS "1 sec"
			MAX-ACCESS read-only
			STATUS current
			DESCRIPTION
				"The elapsed time after clearing statistics."
			::= { sleBridgePortEntry 37 }

		
		sleBridgePortMACLearningStatus OBJECT-TYPE
			SYNTAX INTEGER
				{
				enable(1),
				disable(2)
				}
			MAX-ACCESS read-only
			STATUS current
			DESCRIPTION
				"If enable, SLF packet is forwarded with mac-learning.
				Otherwise, SLF packet is forwarded without mac-learning."
			::= { sleBridgePortEntry 38 }

		
		sleBridgePortPortBridgeStatus OBJECT-TYPE
			SYNTAX INTEGER
				{
				enable(1),
				disable(2)
				}
			MAX-ACCESS read-only
			STATUS current
			DESCRIPTION
				"Port Bridge Feature for transmitting the packet out on the same port of which is received."
			::= { sleBridgePortEntry 39 }

		
		sleBridgePortUnknownMcastBlock OBJECT-TYPE
			SYNTAX INTEGER
				{
				enable(1),
				disable(2)
				}
			MAX-ACCESS read-only
			STATUS current
			DESCRIPTION
				"Unknown multicast block setting for a port."
			::= { sleBridgePortEntry 40 }

		
		sleBridgePortDescription OBJECT-TYPE
			SYNTAX OCTET STRING (SIZE (1..128))
			MAX-ACCESS read-write
			STATUS current
			DESCRIPTION
				"The port description."
			::= { sleBridgePortEntry 41 }

		
		sleBridgePortHoldTime OBJECT-TYPE
			SYNTAX Integer32 (1..65535)
			MAX-ACCESS read-only
			STATUS current
			DESCRIPTION
				"The hold-time"
			::= { sleBridgePortEntry 42 }

		
		sleBridgePortMacAntiSpoofing OBJECT-TYPE
			SYNTAX TruthValue
			MAX-ACCESS read-only
			STATUS current
			DESCRIPTION
				"The mac anti-spoofing per port."
			::= { sleBridgePortEntry 43 }

		
		sleBridgePortSwitchType OBJECT-TYPE
			SYNTAX INTEGER
				{
				special(1),
				inner(2),
				vlan(3),
				eth(4),
				portChannel(5),
				tunnel(6),
				unknown(255)
				}
			MAX-ACCESS read-only
			STATUS current
			DESCRIPTION
				"Interface type."
			::= { sleBridgePortEntry 44 }

		
		sleBridgePortSwitchState OBJECT-TYPE
			SYNTAX INTEGER
				{
				switchedPort(1),
				routedPort(2)
				}
			MAX-ACCESS read-only
			STATUS current
			DESCRIPTION
				"The interface mode to switched port or routed port."
			::= { sleBridgePortEntry 45 }

		
		sleBridgePortSwitchMode OBJECT-TYPE
			SYNTAX INTEGER
				{
				access(1),
				hybrid(2),
				trunk(3),
				ce(4),
				cn(5),
				pn(6),
				pe(7),
				cnp(8),
				vip(9),
				pip(10),
				cbp(11),
				invalid(255)
				}
			MAX-ACCESS read-only
			STATUS current
			DESCRIPTION
				"The switching mode of L2 interface."
			::= { sleBridgePortEntry 46 }

		
		sleBridgePortSwitchSubMode OBJECT-TYPE
			SYNTAX INTEGER
				{
				access(1),
				hybrid(2),
				trunk(3),
				ce(4),
				cn(5),
				pn(6),
				pe(7),
				cnp(8),
				vip(9),
				pip(10),
				cbp(11),
				invalid(255)
				}
			MAX-ACCESS read-only
			STATUS current
			DESCRIPTION
				"The switching sub mode of L2 interface."
			::= { sleBridgePortEntry 47 }

		
		sleBridgePortSwitchDefaultVlan OBJECT-TYPE
			SYNTAX Integer32 (1..4094)
			MAX-ACCESS read-only
			STATUS current
			DESCRIPTION
				"The default VLAN of L2 interface."
			::= { sleBridgePortEntry 48 }

		
		sleBridgePortSwitchIngressFilter OBJECT-TYPE
			SYNTAX INTEGER
				{
				enable(1),
				disable(2)
				}
			MAX-ACCESS read-only
			STATUS current
			DESCRIPTION
				"Set the ingress filtering for 
				the received frames.
								"
			::= { sleBridgePortEntry 49 }

		
		sleBridgePortSwitchAccFrameType OBJECT-TYPE
			SYNTAX BITS
				{
				allType(0),
				tagged(1),
				untagged(2)
				}
			MAX-ACCESS read-only
			STATUS current
			DESCRIPTION
				"Set the Layer 2 interface acceptable frame types. 
				This processing occurs
				after VLAN classification.
				vlan-tagged Accept only classified frames 
				which belong to the port's member set.
				
				Hybridge interface only.
				"
			::= { sleBridgePortEntry 50 }

		
		sleBridgePortSwitchNativeVid OBJECT-TYPE
			SYNTAX Integer32 (1..4094)
			MAX-ACCESS read-only
			STATUS current
			DESCRIPTION
				"The native VLAN is used for classifying the incoming untagged packets.
				"
			::= { sleBridgePortEntry 51 }

		
		sleBridgePortSwitchAllowedVlan OBJECT-TYPE
			SYNTAX OCTET STRING
			MAX-ACCESS read-only
			STATUS current
			DESCRIPTION
				"Both tagged and untagged
				frames will be classified over interfaces."
			::= { sleBridgePortEntry 52 }

		
		sleBridgePortSwitchAllowedVlanEtag OBJECT-TYPE
			SYNTAX OCTET STRING
			MAX-ACCESS read-only
			STATUS current
			DESCRIPTION
				"egress Port string"
			::= { sleBridgePortEntry 53 }

		
		sleBridgePortSwitchChannelType OBJECT-TYPE
			SYNTAX INTEGER
				{
				none(0),
				aggregator(1),
				aggregated(2)
				}
			MAX-ACCESS read-only
			STATUS current
			DESCRIPTION
				"Indicate whether port is aggregator or aggregated(member)."
			::= { sleBridgePortEntry 54 }

		
		sleBridgePortSwitchStaticChannelGroup OBJECT-TYPE
			SYNTAX OCTET STRING
			MAX-ACCESS read-only
			STATUS current
			DESCRIPTION
				"Static channel group name"
			::= { sleBridgePortEntry 55 }

		
		sleBridgePortSwitchChannelLoadbalance OBJECT-TYPE
			SYNTAX INTEGER
				{
				dstMac(1),
				srcMac(2),
				srcDstMac(3),
				srcIp(4),
				dstIp(5),
				srcDstIp(6),
				srcPort(7),
				dstPort(8),
				srcDstPort(9)
				}
			MAX-ACCESS read-only
			STATUS current
			DESCRIPTION
				"Channel group hash method."
			::= { sleBridgePortEntry 56 }

		
		sleBridgePortSwitchAggrType OBJECT-TYPE
			SYNTAX INTEGER
				{
				noneAggregated(0),
				aggregatedStatic(1),
				aggregatedLacp(2),
				aggregatorStatic(3),
				aggregatorLacp(4)
				}
			MAX-ACCESS read-only
			STATUS current
			DESCRIPTION
				"aggregate type"
			::= { sleBridgePortEntry 57 }

		
		sleBridgePortSwitchAggrId OBJECT-TYPE
			SYNTAX Integer32 (0 | 1..12)
			MAX-ACCESS read-only
			STATUS current
			DESCRIPTION
				"aggregate ID"
			::= { sleBridgePortEntry 58 }

		
		sleBridgePortSwitchAggrMode OBJECT-TYPE
			SYNTAX INTEGER
				{
				noneAggregated(0),
				aggregatedActive(1),
				aggregatedPassive(2)
				}
			MAX-ACCESS read-only
			STATUS current
			DESCRIPTION
				"aggregate mode"
			::= { sleBridgePortEntry 59 }

		
		sleBridgePortLoopDetectPeriodMs OBJECT-TYPE
			SYNTAX INTEGER (1..60)
			MAX-ACCESS read-only
			STATUS current
			DESCRIPTION
				"The sending period of detection packet. (Unit: milliseconds)"
			::= { sleBridgePortEntry 91 }

		
		sleBridgePortLoopDetectAdminCount OBJECT-TYPE
			SYNTAX Integer32
			MAX-ACCESS read-only
			STATUS current
			DESCRIPTION
				"The looping Admin count of LoopDetect"
			::= { sleBridgePortEntry 92 }

		
		sleBridgePortLoopDetectOperCount OBJECT-TYPE
			SYNTAX Integer32
			MAX-ACCESS read-only
			STATUS current
			DESCRIPTION
				"The looping oper count of LoopDetect compared with adminCount"
			::= { sleBridgePortEntry 93 }

		
		sleBridgePortLoopDetectDetectedCount OBJECT-TYPE
			SYNTAX Integer32
			MAX-ACCESS read-only
			STATUS current
			DESCRIPTION
				"The looping accumulated detected count of LoopDetect"
			::= { sleBridgePortEntry 94 }

		
		sleBridgePortLoopDetectVlan OBJECT-TYPE
			SYNTAX Integer32 (0..4094)
			MAX-ACCESS read-only
			STATUS current
			DESCRIPTION
				"The loop detect vlan. (0: Not Set)"
			::= { sleBridgePortEntry 95 }

		
		sleBridgePortMaxNewHosts OBJECT-TYPE
			SYNTAX Integer32 (0 | 1..65535)
			MAX-ACCESS read-only
			STATUS current
			DESCRIPTION
				"The maximum number of New hosts allowed. Aggregation group available. Default value is 0: it means unlimited."
			::= { sleBridgePortEntry 96 }

		
		sleBridgePortStpStatus OBJECT-TYPE
			SYNTAX INTEGER
				{
				disable(0),
				enable(1)
				}
			MAX-ACCESS read-only
			STATUS current
			DESCRIPTION
				"STP status per interface."
			::= { sleBridgePortEntry 97 }

		
		sleBridgePortStpBpduGuard OBJECT-TYPE
			SYNTAX INTEGER
				{
				disable(0),
				enable(1)
				}
			MAX-ACCESS read-only
			STATUS current
			DESCRIPTION
				"The Spanning-tree bpduguard state"
			::= { sleBridgePortEntry 98 }

		
		sleBridgePortOuterTpid OBJECT-TYPE
			SYNTAX Integer32 (0..65535)
			MAX-ACCESS read-only
			STATUS current
			DESCRIPTION
				"The Ethertype for outer-tag"
			::= { sleBridgePortEntry 99 }

		
		sleBridgePortMirrorMonitor OBJECT-TYPE
			SYNTAX INTEGER
				{
				disable(0),
				enable(1)
				}
			MAX-ACCESS read-only
			STATUS current
			DESCRIPTION
				"The Mirror monitor status"
			::= { sleBridgePortEntry 100 }

		
		sleBridgePortBandwidth OBJECT-TYPE
			SYNTAX OCTET STRING
			MAX-ACCESS read-only
			STATUS current
			DESCRIPTION
				"The bandwidth value for interface."
			::= { sleBridgePortEntry 101 }

		
		sleBridgePortAlias OBJECT-TYPE
			SYNTAX OCTET STRING
			MAX-ACCESS read-only
			STATUS current
			DESCRIPTION
				"The alias name for interface."
			::= { sleBridgePortEntry 102 }

		
		sleBridgePortMulticast OBJECT-TYPE
			SYNTAX INTEGER
				{
				disable(0),
				enable(1)
				}
			MAX-ACCESS read-only
			STATUS current
			DESCRIPTION
				"The interface supports multicast."
			::= { sleBridgePortEntry 103 }

		
		sleBridgePortFloodBlock OBJECT-TYPE
			SYNTAX BITS
				{
				bcast(0),
				dlf(1),
				mcast(2)
				}
			MAX-ACCESS read-only
			STATUS current
			DESCRIPTION
				"Packet flooding discarding."
			::= { sleBridgePortEntry 104 }

		
		sleBridgePortControl OBJECT IDENTIFIER ::= { sleBridgePort 2 }

		
		sleBridgePortControlRequest OBJECT-TYPE
			SYNTAX INTEGER
				{
				setBridgePortPVid(1),
				setBridgePortMaxHosts(2),
				setBridgePortMaxLearnPerUnit(3),
				setBridgePortMACFilterPermission(4),
				setBridgePortMirrorProfile(5),
				setBridgePortBcscThresholdProfile(6),
				setBridgePortQinQStatus(7),
				setBridgePortLinktype(8),
				setBridgePortEdgemode(9),
				setBridgePortStpBpduFilter(10),
				setBridgePortIsolatedStatus(11),
				setBridgePortStpBpduGuardErrRcv(12),
				setBridgePortDhcpFilterServer(13),
				setBridgePortLoopDetectProfile(14),
				setBridgePortLoopDetectUnblock(15),
				setBridgePortNetBIOSFilter(16),
				setBridgePortPushInnertag(17),
				setBridgePortPopInnertag(18),
				setBridgePortInnertag(19),
				setBridgePortPriority(20),
				setBridgePortInner2outerPri(21),
				setBridgePortInner2outerVid(22),
				setBridgePortMacLearningStatus(23),
				setBridgePortPortBridgeStatus(24),
				setBridgePortUnknownMcastBlock(25),
				setBridgePortDescriptopn(26),
				setBridgePortHoldTime(27),
				setBridgePortMacAntiSpoofing(28),
				setBridgePortSwitchStatus(29),
				setBridgePortSwitchMode(30),
				setBridgePortSwitchDefaultVlan(31),
				setBridgePortSwitchNativeVlan(32),
				setBridgePortSwitchAccFramType(33),
				setBridgePortSwitchAddAllowdVlan(34),
				setBridgePortSwitchRemoveAllowdVlan(35),
				setBridgePortSwitchStaticChannel(36),
				setBridgePortSwitchChannelLoadbalance(37),
				clearBridgePortLinkUpCntByIndex(38),
				clearBridgePortLinkUpCntAll(39),
				setBridgePortSwitchChannelProfile(40),
				setBridgePortSwitchNoChannelProfile(41),
				setBridgePortLoopDetectPeriodMs(71),
				setBridgeLoopDetectAdminCount(72),
				setBridgeLoopDetectVlan(73),
				delBridgeLoopDetectVlan(74),
				setBridgePortMaxNewHosts(75),
				clearSpanningTreeDetectedProtocols(76),
				setBridgePortStpStatus(77),
				setBridgePortStpBpduGuard(78),
				setBridgePortOuterTpid(79),
				setBridgePortMirrorMonitor(80),
				setBridgePortBandwidth(81),
				setBridgePortAlias(82),
				unsetBridgePortAlias(83),
				setBridgePortMulticast(84),
				setBridgePortFloodBlock(85)
				}
			MAX-ACCESS read-write
			STATUS current
			DESCRIPTION
				"
				setBridgePortPVid:
				sleBridgePortControlIndex
				sleBridgePortControlPVid
				
				setBridgePortMaxHosts:
				sleBridgePortControlIndex
				sleBridgePortControlMaxHosts
				
				setBridgePortMACFilterPermission:
				sleBridgePortControlIndex
				sleBridgePortControlMACFilterPermission
				
				setBridgePortMirrorProfile:
				sleBridgePortControlIndex
				sleBridgePortControlIngMirrorStatus
				sleBridgePortControlEgMirrorStatus
				            
				setBridgePortBcscThresholdProfile:
				sleBridgePortControlIndex
				sleBridgePortControlBcastThreshold
				sleBridgePortControlMcastThreshold
				sleBridgePortControlDlfThreshold
				            
				setBridgePortQinQStatus:
				sleBridgePortControlIndex
				sleBridgePortControlQinQStatus
				            
				setBridgePortLinktype:
				sleBridgePortControlIndex
				sleBridgePortControlAdminLinktype
				            
				setBridgePortEdgemode:
				sleBridgePortControlIndex
				sleBridgePortControlAdminEdgemode
				
				setBridgePortNetBIOSFilter:
				sleBridgePortControlIndex
				sleBridgePortControlNetBIOSFilter
				"
			::= { sleBridgePortControl 1 }

		
		sleBridgePortControlStatus OBJECT-TYPE
			SYNTAX SleControlStatusType
			MAX-ACCESS read-only
			STATUS current
			DESCRIPTION
				"The status of a user command."
			::= { sleBridgePortControl 2 }

		
		sleBridgePortControlTimer OBJECT-TYPE
			SYNTAX Gauge32
			MAX-ACCESS read-write
			STATUS current
			DESCRIPTION
				"The maximum wait time for the manager for a long running user command."
			::= { sleBridgePortControl 3 }

		
		sleBridgePortControlTimeStamp OBJECT-TYPE
			SYNTAX TimeTicks
			MAX-ACCESS read-only
			STATUS current
			DESCRIPTION
				"The time stamp of the last command (end of command)."
			::= { sleBridgePortControl 4 }

		
		sleBridgePortControlReqResult OBJECT-TYPE
			SYNTAX SleControlRequestResultType
			MAX-ACCESS read-only
			STATUS current
			DESCRIPTION
				"The result of the last user command."
			::= { sleBridgePortControl 5 }

		
		sleBridgePortControlIndex OBJECT-TYPE
			SYNTAX INTEGER (1..255)
			MAX-ACCESS read-write
			STATUS current
			DESCRIPTION
				"sleBridgePortIndex"
			::= { sleBridgePortControl 6 }

		
		sleBridgePortControlPVid OBJECT-TYPE
			SYNTAX INTEGER (1..4094)
			MAX-ACCESS read-write
			STATUS current
			DESCRIPTION
				"The PVID of port. 
				Taken if no other rule given for VLAN association. 
				If aggregated: only for group."
			::= { sleBridgePortControl 7 }

		
		sleBridgePortControlMaxHosts OBJECT-TYPE
			SYNTAX INTEGER (-1..2147483647)
			MAX-ACCESS read-write
			STATUS current
			DESCRIPTION
				"The maximum number of hosts allowed. 
				Aggregation group available. Value 0 is allowed,
				Value -1 is used to clear."
			DEFVAL { -1 }
			::= { sleBridgePortControl 8 }

		
		sleBridgePortControlMaxLearnPerUnit OBJECT-TYPE
			SYNTAX INTEGER (-1..2147483647)
			MAX-ACCESS read-write
			STATUS current
			DESCRIPTION
				"Limit maximum number of MAC addresses learning 
				newly per unit time(one second) on a port.
				(0: nothing learned, -l: unlimited.)"
			::= { sleBridgePortControl 9 }

		
		sleBridgePortControlMACFilterPermission OBJECT-TYPE
			SYNTAX INTEGER
				{
				deny(0),
				permit(1)
				}
			MAX-ACCESS read-write
			STATUS current
			DESCRIPTION
				"The default permission for mac filtering. 
				Valid only for physical ports, 
				use values from MFDB  Table."
			DEFVAL { 1 }
			::= { sleBridgePortControl 10 }

		
		sleBridgePortControlIngMirrorStatus OBJECT-TYPE
			SYNTAX INTEGER
				{
				disable(0),
				enable(1)
				}
			MAX-ACCESS read-write
			STATUS current
			DESCRIPTION
				"Mirroring on ingress packets. 
				Valid only for physical ports. "
			DEFVAL { 0 }
			::= { sleBridgePortControl 11 }

		
		sleBridgePortControlEgMirrorStatus OBJECT-TYPE
			SYNTAX INTEGER
				{
				disable(0),
				enable(1)
				}
			MAX-ACCESS read-write
			STATUS current
			DESCRIPTION
				"Mirroring on egress packets. 
				Valid only for physical ports. "
			DEFVAL { 0 }
			::= { sleBridgePortControl 12 }

		
		sleBridgePortControlBcastThreshold OBJECT-TYPE
			SYNTAX INTEGER (0..2097150)
			MAX-ACCESS read-write
			STATUS current
			DESCRIPTION
				"Broadcast packet rate limit (unit: packets/s), 
				Valid only for physical ports. Value 0 is used to clear.
				Value Range: 0-262142(TX/FX),0-2097150(GBIC)."
			DEFVAL { 0 }
			::= { sleBridgePortControl 13 }

		
		sleBridgePortControlMcastThreshold OBJECT-TYPE
			SYNTAX INTEGER (0..2097150)
			MAX-ACCESS read-write
			STATUS current
			DESCRIPTION
				"Multicast packet rate limit (unit: packets/s), 
				Valid only for physical ports. Value 0 is used to clear.
				Value Range: 0-262142(TX/FX),0-2097150(GBIC)."
			DEFVAL { 0 }
			::= { sleBridgePortControl 14 }

		
		sleBridgePortControlDlfThreshold OBJECT-TYPE
			SYNTAX INTEGER (0..2097150)
			MAX-ACCESS read-write
			STATUS current
			DESCRIPTION
				"DLF packet rate limit (unit: packets/s), 
				Valid only for physical ports. Value 0 is used to clear.
				Value Range: 0-262142(TX/FX),0-2097150(GBIC)."
			DEFVAL { 0 }
			::= { sleBridgePortControl 15 }

		
		sleBridgePortControlQinQStatus OBJECT-TYPE
			SYNTAX INTEGER
				{
				disable(0),
				enable(1)
				}
			MAX-ACCESS read-write
			STATUS current
			DESCRIPTION
				"QinQ Status of the port. 
				Valid only for physical ports. "
			DEFVAL { 0 }
			::= { sleBridgePortControl 16 }

		
		sleBridgePortControlAdminLinktype OBJECT-TYPE
			SYNTAX INTEGER
				{
				shared(0),
				pointTopoint(1),
				automatic(2)
				}
			MAX-ACCESS read-write
			STATUS current
			DESCRIPTION
				"The administrative link-type of port on the xSTP. "
			DEFVAL { 2 }
			::= { sleBridgePortControl 17 }

		
		sleBridgePortControlAdminEdgemode OBJECT-TYPE
			SYNTAX INTEGER
				{
				disable(0),
				enable(1)
				}
			MAX-ACCESS read-write
			STATUS current
			DESCRIPTION
				"The administrative edgemode of port on the xSTP. "
			DEFVAL { 0 }
			::= { sleBridgePortControl 18 }

		
		sleBridgePortControlStpBpduFilter OBJECT-TYPE
			SYNTAX INTEGER
				{
				disable(0),
				enable(1)
				}
			MAX-ACCESS read-write
			STATUS current
			DESCRIPTION
				"The stp bpdu-filter of the port on the xSTP. Default value is 0."
			DEFVAL { 0 }
			::= { sleBridgePortControl 19 }

		
		sleBridgePortControlPvlanIsolatedStatus OBJECT-TYPE
			SYNTAX INTEGER
				{
				disable(0),
				enable(1)
				}
			MAX-ACCESS read-write
			STATUS current
			DESCRIPTION
				"Isolated status of this port. Default value is disable(0)."
			DEFVAL { 0 }
			::= { sleBridgePortControl 20 }

		
		sleBridgePortControlPvlanPromPort OBJECT-TYPE
			SYNTAX INTEGER (1..65535)
			MAX-ACCESS read-write
			STATUS current
			DESCRIPTION
				"Portlist for promiscuous ports of this port. The OctetString is a list of pairs of octets each identify an sheBridgePortIndex. The least significant byte is the second octet."
			::= { sleBridgePortControl 21 }

		
		sleBridgePortControlStpBpduGuardErrRcv OBJECT-TYPE
			SYNTAX TruthValue
			MAX-ACCESS read-write
			STATUS current
			DESCRIPTION
				"Trigger manual recovery for the port disabled by Bpdu Guard.
				false : sustain current state.
				true  : trigger recovery."
			DEFVAL { false }
			::= { sleBridgePortControl 22 }

		
		sleBridgePortControlDhcpFilterServer OBJECT-TYPE
			SYNTAX INTEGER
				{
				disable(0),
				enable(1)
				}
			MAX-ACCESS read-write
			STATUS current
			DESCRIPTION
				"DHCP filter server status
				0: disabled
				1: enabled"
			::= { sleBridgePortControl 23 }

		
		sleBridgePortControlLoopDetectStatus OBJECT-TYPE
			SYNTAX INTEGER
				{
				enable(1),
				disable(2)
				}
			MAX-ACCESS read-write
			STATUS current
			DESCRIPTION
				"The adminStatus of loop-detect per ports."
			::= { sleBridgePortControl 24 }

		
		sleBridgePortControlLoopDetectBlock OBJECT-TYPE
			SYNTAX INTEGER
				{
				enable(1),
				disable(2)
				}
			MAX-ACCESS read-only
			STATUS current
			DESCRIPTION
				"The adminBlock mode of loop-detect per ports.
				Indicate whether block port or not."
			::= { sleBridgePortControl 25 }

		
		sleBridgePortControlLoopDetectPeriod OBJECT-TYPE
			SYNTAX INTEGER (1..60)
			MAX-ACCESS read-write
			STATUS current
			DESCRIPTION
				"The sending period of detection packet."
			::= { sleBridgePortControl 26 }

		
		sleBridgePortControlLoopDetectTimer OBJECT-TYPE
			SYNTAX INTEGER (0 | 1..86400)
			MAX-ACCESS read-write
			STATUS current
			DESCRIPTION
				"The Blocked list expire timer."
			::= { sleBridgePortControl 27 }

		
		sleBridgePortControlNetBIOSFilter OBJECT-TYPE
			SYNTAX INTEGER
				{
				disable(0),
				enable(1)
				}
			MAX-ACCESS read-write
			STATUS current
			DESCRIPTION
				"The netBios filter status per ports"
			::= { sleBridgePortControl 28 }

		
		sleBridgePortControlPushInnertag OBJECT-TYPE
			SYNTAX INTEGER
				{
				disable(0),
				enable(1)
				}
			MAX-ACCESS read-write
			STATUS current
			DESCRIPTION
				"Push inner-tag for incoming untagged packet."
			::= { sleBridgePortControl 29 }

		
		sleBridgePortControlPopInnertag OBJECT-TYPE
			SYNTAX INTEGER
				{
				disable(0),
				enable(1)
				}
			MAX-ACCESS read-write
			STATUS current
			DESCRIPTION
				"Pop inner-tag for double tagged packet."
			::= { sleBridgePortControl 30 }

		
		sleBridgePortControlInnertag OBJECT-TYPE
			SYNTAX INTEGER (0..4096)
			MAX-ACCESS read-write
			STATUS current
			DESCRIPTION
				"Inner-tag value to push for incoming untagged packet."
			::= { sleBridgePortControl 31 }

		
		sleBridgePortControlPriority OBJECT-TYPE
			SYNTAX INTEGER (0..7)
			MAX-ACCESS read-write
			STATUS current
			DESCRIPTION
				"The priority value per port.
				Assign priority for untagged packet from port.
				"
			::= { sleBridgePortControl 32 }

		
		sleBridgePortControlInner2outerPri OBJECT-TYPE
			SYNTAX INTEGER
				{
				disable(0),
				enable(1)
				}
			MAX-ACCESS read-write
			STATUS current
			DESCRIPTION
				"If enable, use inner-tag's priority as outer-tag's priority.
				Otherwise, use outer-tag's priority"
			::= { sleBridgePortControl 33 }

		
		sleBridgePortControlInner2outerVid OBJECT-TYPE
			SYNTAX INTEGER
				{
				disable(0),
				enable(1)
				}
			MAX-ACCESS read-write
			STATUS current
			DESCRIPTION
				"If enable, use inner-tag's vlan-id as outer-tag's vlan-id.
				Otherwise, use outer-tag's vlan-id"
			::= { sleBridgePortControl 34 }

		
		sleBridgePortControlMACLearningStatus OBJECT-TYPE
			SYNTAX INTEGER
				{
				enable(1),
				disable(2)
				}
			MAX-ACCESS read-write
			STATUS current
			DESCRIPTION
				"If enable, SLF packet is forwarded with mac-learning.
				Otherwise, SLF packet is forwarded without mac-learning."
			::= { sleBridgePortControl 35 }

		
		sleBridgePortControlPortBridgeStatus OBJECT-TYPE
			SYNTAX INTEGER
				{
				enable(1),
				disable(2)
				}
			MAX-ACCESS read-write
			STATUS current
			DESCRIPTION
				"Port Bridge Feature for transmitting the packet out on the same port of which is received."
			::= { sleBridgePortControl 36 }

		
		sleBridgePortControlUnknownMcastBlock OBJECT-TYPE
			SYNTAX INTEGER
				{
				enable(1),
				disable(2)
				}
			MAX-ACCESS read-write
			STATUS current
			DESCRIPTION
				"Unknown multicast block setting for a port."
			::= { sleBridgePortControl 37 }

		
		sleBridgePortControlDescription OBJECT-TYPE
			SYNTAX OCTET STRING (SIZE (1..128))
			MAX-ACCESS read-write
			STATUS current
			DESCRIPTION
				"The Port Description."
			::= { sleBridgePortControl 38 }

		
		sleBridgePortControlHoldTime OBJECT-TYPE
			SYNTAX Integer32 (1..65535)
			MAX-ACCESS read-write
			STATUS current
			DESCRIPTION
				"The hold-time"
			::= { sleBridgePortControl 39 }

		
		sleBridgePortControlMacAntiSpoofing OBJECT-TYPE
			SYNTAX TruthValue
				{
				true(1),
				false(2)
				}
			MAX-ACCESS read-write
			STATUS current
			DESCRIPTION
				"The mac anti-spoofing per port."
			::= { sleBridgePortControl 40 }

		
		sleBridgePortControlSwitchStatus OBJECT-TYPE
			SYNTAX INTEGER
				{
				switchedPort(1),
				routedPort(2)
				}
			MAX-ACCESS read-write
			STATUS current
			DESCRIPTION
				"The interface mode to switched port or routed port."
			::= { sleBridgePortControl 41 }

		
		sleBridgePortControlSwitchMode OBJECT-TYPE
			SYNTAX INTEGER
				{
				access(1),
				hybrid(2),
				trunk(3),
				ce(4),
				cn(5),
				pn(6),
				pe(7),
				cnp(8),
				vip(9),
				pip(10),
				cbp(11),
				invalid(255)
				}
			MAX-ACCESS read-write
			STATUS current
			DESCRIPTION
				"The switching mode of L2 interface.
				"
			::= { sleBridgePortControl 42 }

		
		sleBridgePortControlSwitchSubMode OBJECT-TYPE
			SYNTAX INTEGER
				{
				access(1),
				hybrid(2),
				trunk(3),
				ce(4),
				cn(5),
				pn(6),
				pe(7),
				cnp(8),
				vip(9),
				pip(10),
				cbp(11),
				invalid(255)
				}
			MAX-ACCESS read-write
			STATUS current
			DESCRIPTION
				"The switching sub mode of L2 interface.
				"
			::= { sleBridgePortControl 43 }

		
		sleBridgePortControlSwitchDefaultVlan OBJECT-TYPE
			SYNTAX Integer32 (1..4094)
			MAX-ACCESS read-write
			STATUS current
			DESCRIPTION
				"The dafulat VLAN of L2 interface"
			::= { sleBridgePortControl 44 }

		
		sleBridgePortControlSwitchIngressFilter OBJECT-TYPE
			SYNTAX INTEGER
				{
				enable(1),
				disable(2)
				}
			MAX-ACCESS read-write
			STATUS current
			DESCRIPTION
				"Set the ingress filtering for 
				the received frames
								"
			::= { sleBridgePortControl 45 }

		
		sleBridgePortControlSwitchAccFrameType OBJECT-TYPE
			SYNTAX BITS
				{
				allType(0),
				tagged(1),
				unTagged(2)
				}
			MAX-ACCESS read-write
			STATUS current
			DESCRIPTION
				"Set the Layer 2 interface acceptable frame types.
				This processing occurs
				after VLAN classification.
				vlan-tagged Accept only classified frames 
				which belong to the port's member set.
				
				Hybridge interface only."
			::= { sleBridgePortControl 46 }

		
		sleBridgePortControlSwitchNativeVid OBJECT-TYPE
			SYNTAX Integer32 (1..4094)
			MAX-ACCESS read-write
			STATUS current
			DESCRIPTION
				"The native VLAN is used for classifying the incoming untagged packets.
				"
			::= { sleBridgePortControl 47 }

		
		sleBridgePortControlSwitchAllowedVlan OBJECT-TYPE
			SYNTAX OCTET STRING
			MAX-ACCESS read-write
			STATUS current
			DESCRIPTION
				"Both tagged and untagged
				frames will be classified over interfaces."
			::= { sleBridgePortControl 48 }

		
		sleBridgePortControlSwitchAllowedVlanEtag OBJECT-TYPE
			SYNTAX OCTET STRING
			MAX-ACCESS read-write
			STATUS current
			DESCRIPTION
				"egress Port string"
			::= { sleBridgePortControl 49 }

		
		sleBridgePortControlSwitchStaticChannelGroup OBJECT-TYPE
			SYNTAX OCTET STRING
			MAX-ACCESS read-write
			STATUS current
			DESCRIPTION
				"Static channel group name"
			::= { sleBridgePortControl 50 }

		
		sleBridgePortControlSwitchChannelLoadbalance OBJECT-TYPE
			SYNTAX INTEGER
				{
				dstMac(1),
				srcMac(2),
				srcDstMac(3),
				srcIp(4),
				dstIp(5),
				srcDstIp(6),
				srcPort(7),
				dstPort(8),
				srcDstPort(9)
				}
			MAX-ACCESS read-write
			STATUS current
			DESCRIPTION
				"Channel group hash method."
			::= { sleBridgePortControl 51 }

		
		sleBridgePortControlSwitchAggrType OBJECT-TYPE
			SYNTAX INTEGER
				{
				noneAggregated(0),
				aggregatedStatic(1),
				aggregatedLacp(2),
				aggregatorStatic(3),
				aggregatorLacp(4)
				}
			MAX-ACCESS read-write
			STATUS current
			DESCRIPTION
				"aggregate type"
			::= { sleBridgePortControl 52 }

		
		sleBridgePortControlSwitchAggrId OBJECT-TYPE
			SYNTAX Integer32 (1..12)
			MAX-ACCESS read-write
			STATUS current
			DESCRIPTION
				"Description."
			::= { sleBridgePortControl 53 }

		
		sleBridgePortControlSwitchAggrMode OBJECT-TYPE
			SYNTAX INTEGER
				{
				noneAggregated(0),
				aggregatedActive(1),
				aggregatedPassive(2)
				}
			MAX-ACCESS read-write
			STATUS current
			DESCRIPTION
				"Description."
			::= { sleBridgePortControl 54 }

		
		sleBridgePortControlLoopDetectPeriodMs OBJECT-TYPE
			SYNTAX INTEGER (1..60)
			MAX-ACCESS read-write
			STATUS current
			DESCRIPTION
				"The sending period of detection packet (Unit: milliseconds)."
			::= { sleBridgePortControl 91 }

		
		sleBridgePortControlLoopDetectAdminCount OBJECT-TYPE
			SYNTAX INTEGER (1..60)
			MAX-ACCESS read-write
			STATUS current
			DESCRIPTION
				"The looping count of LoopDetect"
			::= { sleBridgePortControl 92 }

		
		sleBridgePortControlLoopDetectVlan OBJECT-TYPE
			SYNTAX Integer32 (1..4094)
			MAX-ACCESS read-write
			STATUS current
			DESCRIPTION
				"The loop detect vlan"
			::= { sleBridgePortControl 93 }

		
		sleBridgePortControlMaxNewHosts OBJECT-TYPE
			SYNTAX Integer32 (-1 | 0 | 1..65535)
			MAX-ACCESS read-write
			STATUS current
			DESCRIPTION
				"The maximum number of hosts allowed. 
				Aggregation group available. Value 0 is allowed. 
				Default value is -1: it means unlimited.
				"
			::= { sleBridgePortControl 94 }

		
		sleBridgePortControlStpStatus OBJECT-TYPE
			SYNTAX INTEGER
				{
				disable(0),
				enable(1)
				}
			MAX-ACCESS read-write
			STATUS current
			DESCRIPTION
				"STP status per interface."
			::= { sleBridgePortControl 95 }

		
		sleBridgePortControlStpBpduGuard OBJECT-TYPE
			SYNTAX INTEGER
				{
				disable(0),
				enable(1)
				}
			MAX-ACCESS read-write
			STATUS current
			DESCRIPTION
				"The Spanning-tree bpduguard state"
			::= { sleBridgePortControl 96 }

		
		sleBridgePortControlOuterTpid OBJECT-TYPE
			SYNTAX Integer32 (0..65535)
			MAX-ACCESS read-write
			STATUS current
			DESCRIPTION
				"The Ethertype for outer-tag"
			::= { sleBridgePortControl 97 }

		
		sleBridgePortControlMirrorMonitor OBJECT-TYPE
			SYNTAX INTEGER
				{
				disable(0),
				enable(1)
				}
			MAX-ACCESS read-write
			STATUS current
			DESCRIPTION
				"The Mirror monitor status"
			::= { sleBridgePortControl 98 }

		
		sleBridgePortControlBandwidth OBJECT-TYPE
			SYNTAX OCTET STRING
			MAX-ACCESS read-write
			STATUS current
			DESCRIPTION
				"The bandwidth value for interface."
			::= { sleBridgePortControl 99 }

		
		sleBridgePortControlAlias OBJECT-TYPE
			SYNTAX OCTET STRING
			MAX-ACCESS read-write
			STATUS current
			DESCRIPTION
				"The alias name for interface.
				"
			::= { sleBridgePortControl 100 }

		
		sleBridgePortControlMulticast OBJECT-TYPE
			SYNTAX INTEGER
				{
				disable(0),
				enable(1)
				}
			MAX-ACCESS read-write
			STATUS current
			DESCRIPTION
				"The interface supports multicast."
			::= { sleBridgePortControl 101 }

		
		sleBridgePortControlFloodBlock OBJECT-TYPE
			SYNTAX BITS
				{
				bcast(0),
				dlf(1),
				mcast(2)
				}
			MAX-ACCESS read-write
			STATUS current
			DESCRIPTION
				"Packet flooding discarding."
			::= { sleBridgePortControl 102 }

		
		sleBridgePortNotification OBJECT IDENTIFIER ::= { sleBridgePort 3 }

		
		sleBridgePortPVidChanged NOTIFICATION-TYPE
			OBJECTS { sleBridgePortPVid, sleBridgePortControlRequest, sleBridgePortControlTimeStamp, sleBridgePortControlReqResult }
			STATUS current
			DESCRIPTION 
				"PVid changed"
			::= { sleBridgePortNotification 1 }

		
		sleBridgePortMaxHostsChanged NOTIFICATION-TYPE
			OBJECTS { sleBridgePortMaxHosts, sleBridgePortControlRequest, sleBridgePortControlTimeStamp, sleBridgePortControlReqResult }
			STATUS current
			DESCRIPTION 
				"MaxHosts changed"
			::= { sleBridgePortNotification 2 }

		
		sleBridgePortMaxLearnPerUnitChanged NOTIFICATION-TYPE
			OBJECTS { sleBridgePortControlRequest, sleBridgePortControlTimeStamp, sleBridgePortControlReqResult, sleBridgePortMaxLearnPerUnit }
			STATUS current
			DESCRIPTION 
				"Description."
			::= { sleBridgePortNotification 3 }

		
		sleBridgePortMACFilterPermissionChanged NOTIFICATION-TYPE
			OBJECTS { sleBridgePortMACFilterPermission, sleBridgePortControlRequest, sleBridgePortControlTimeStamp, sleBridgePortControlReqResult }
			STATUS current
			DESCRIPTION 
				"MAC filter permission changed"
			::= { sleBridgePortNotification 4 }

		
		sleBridgePortMirrorProfileChanged NOTIFICATION-TYPE
			OBJECTS { sleBridgePortIngMirrorStatus, sleBridgePortEgMirrorStatus, sleBridgePortControlRequest, sleBridgePortControlTimeStamp, sleBridgePortControlReqResult
				 }
			STATUS current
			DESCRIPTION 
				"Mirror profile changed"
			::= { sleBridgePortNotification 5 }

		
		sleBridgePortBcscThresholdProfileChanged NOTIFICATION-TYPE
			OBJECTS { sleBridgePortBcastThreshold, sleBridgePortMcastThreshold, sleBridgePortDlfThreshold, sleBridgePortControlRequest, sleBridgePortControlTimeStamp, 
				sleBridgePortControlReqResult }
			STATUS current
			DESCRIPTION 
				"BCSC threshold profile changed"
			::= { sleBridgePortNotification 6 }

		
		sleBridgePortQinQStatusChanged NOTIFICATION-TYPE
			OBJECTS { sleBridgePortQinQStatus, sleBridgePortControlRequest, sleBridgePortControlTimeStamp, sleBridgePortControlReqResult }
			STATUS current
			DESCRIPTION 
				"QinQ status changed"
			::= { sleBridgePortNotification 7 }

		
		sleBridgePortLinktypeChanged NOTIFICATION-TYPE
			OBJECTS { sleBridgePortAdminLinktype, sleBridgePortControlRequest, sleBridgePortControlTimeStamp, sleBridgePortControlReqResult }
			STATUS current
			DESCRIPTION 
				"Admin link-type changed"
			::= { sleBridgePortNotification 8 }

		
		sleBridgePortEdgemodeChanged NOTIFICATION-TYPE
			OBJECTS { sleBridgePortAdminEdgemode, sleBridgePortControlRequest, sleBridgePortControlTimeStamp, sleBridgePortControlReqResult }
			STATUS current
			DESCRIPTION 
				"Admin edge-mode changed"
			::= { sleBridgePortNotification 9 }

		
		sleBridgePortStpBpduFilterChanged NOTIFICATION-TYPE
			OBJECTS { sleBridgePortStpBpduFilter, sleBridgePortControlTimeStamp, sleBridgePortControlReqResult, sleBridgePortControlRequest }
			STATUS current
			DESCRIPTION 
				"Description."
			::= { sleBridgePortNotification 10 }

		
		sleBridgePortPvlanIsolatedStatusChanged NOTIFICATION-TYPE
			OBJECTS { sleBridgePortPvlanIsolatedStatus, sleBridgePortPvlanPromPorts, sleBridgePortControlRequest, sleBridgePortControlTimeStamp, sleBridgePortControlReqResult
				 }
			STATUS current
			DESCRIPTION 
				"Description."
			::= { sleBridgePortNotification 11 }

		
		sleBridgePortStpBpduGuardErrRcvChanged NOTIFICATION-TYPE
			OBJECTS { sleBridgePortControlRequest, sleBridgePortControlTimeStamp, sleBridgePortControlReqResult }
			STATUS current
			DESCRIPTION 
				"Description."
			::= { sleBridgePortNotification 12 }

		
		sleBridgePortDhcpFilterServerChanged NOTIFICATION-TYPE
			OBJECTS { sleBridgePortControlRequest, sleBridgePortControlTimeStamp, sleBridgePortControlReqResult, sleBridgePortDhcpFilterServer }
			STATUS current
			DESCRIPTION 
				"Description."
			::= { sleBridgePortNotification 13 }

		
		sleBridgePortLoopDetectProfileChanged NOTIFICATION-TYPE
			OBJECTS { sleBridgePortControlRequest, sleBridgePortControlTimeStamp, sleBridgePortControlReqResult, sleBridgePortLoopDetectStatus, sleBridgePortLoopDetectBlock, 
				sleBridgePortLoopDetectPeriod, sleBridgePortLoopDetectTimer }
			STATUS current
			DESCRIPTION 
				"Description."
			::= { sleBridgePortNotification 14 }

		
		sleBridgePortLoopDetectUnblock NOTIFICATION-TYPE
			OBJECTS { sleBridgePortControlRequest, sleBridgePortControlTimeStamp, sleBridgePortControlReqResult, sleBridgePortLoopDetectBlockStatus }
			STATUS current
			DESCRIPTION 
				"Description."
			::= { sleBridgePortNotification 15 }

		
		sleBridgePortNetBIOSFilterChanged NOTIFICATION-TYPE
			OBJECTS { sleBridgePortControlRequest, sleBridgePortControlTimeStamp, sleBridgePortControlReqResult, sleBridgePortNetBIOSFilter }
			STATUS current
			DESCRIPTION 
				"Description."
			::= { sleBridgePortNotification 16 }

		
		sleBridgePortPushInnertagChanged NOTIFICATION-TYPE
			OBJECTS { sleBridgePortControlRequest, sleBridgePortControlReqResult, sleBridgePortControlTimeStamp, sleBridgePortControlIndex, sleBridgePortControlPushInnertag
				 }
			STATUS current
			DESCRIPTION 
				"setBridgePortPushInnertag"
			::= { sleBridgePortNotification 17 }

		
		sleBridgePortPopInnertagChanged NOTIFICATION-TYPE
			OBJECTS { sleBridgePortControlRequest, sleBridgePortControlReqResult, sleBridgePortControlTimeStamp, sleBridgePortControlIndex, sleBridgePortControlPopInnertag
				 }
			STATUS current
			DESCRIPTION 
				"setBridgePortPopInnertag"
			::= { sleBridgePortNotification 18 }

		
		sleBridgePortInnertagChanged NOTIFICATION-TYPE
			OBJECTS { sleBridgePortControlRequest, sleBridgePortControlReqResult, sleBridgePortControlTimeStamp, sleBridgePortControlIndex, sleBridgePortControlInnertag
				 }
			STATUS current
			DESCRIPTION 
				"setBridgePortInnertag"
			::= { sleBridgePortNotification 19 }

		
		sleBridgePortPriorityChanged NOTIFICATION-TYPE
			OBJECTS { sleBridgePortControlRequest, sleBridgePortControlReqResult, sleBridgePortControlTimeStamp, sleBridgePortControlIndex, sleBridgePortControlPriority
				 }
			STATUS current
			DESCRIPTION 
				"setBridgePortPriority"
			::= { sleBridgePortNotification 20 }

		
		sleBridgePortInner2outerPriChanged NOTIFICATION-TYPE
			OBJECTS { sleBridgePortControlRequest, sleBridgePortControlReqResult, sleBridgePortControlTimeStamp, sleBridgePortControlIndex, sleBridgePortControlInner2outerPri
				 }
			STATUS current
			DESCRIPTION 
				"setBridgePortInner2outerPri"
			::= { sleBridgePortNotification 21 }

		
		sleBridgePortInner2outerVidChanged NOTIFICATION-TYPE
			OBJECTS { sleBridgePortControlRequest, sleBridgePortControlReqResult, sleBridgePortControlTimeStamp, sleBridgePortControlIndex, sleBridgePortControlInner2outerVid
				 }
			STATUS current
			DESCRIPTION 
				"setBridgePortInner2outerVid"
			::= { sleBridgePortNotification 22 }

		
		sleBridgePortMACLearningStatusChanged NOTIFICATION-TYPE
			OBJECTS { sleBridgePortControlRequest, sleBridgePortControlReqResult, sleBridgePortControlTimeStamp, sleBridgePortControlIndex, sleBridgePortControlMACLearningStatus
				 }
			STATUS current
			DESCRIPTION 
				"sleBridgePortMACLearningStatus"
			::= { sleBridgePortNotification 23 }

		
		sleBridgePortPortBridgeStatusChanged NOTIFICATION-TYPE
			OBJECTS { sleBridgePortControlRequest, sleBridgePortControlReqResult, sleBridgePortControlTimeStamp, sleBridgePortControlIndex, sleBridgePortControlPortBridgeStatus
				 }
			STATUS current
			DESCRIPTION 
				"sleBridgePortPortBridgeStatus"
			::= { sleBridgePortNotification 24 }

		
		sleBridgePortUnknownMcastBlockChanged NOTIFICATION-TYPE
			OBJECTS { sleBridgePortControlRequest, sleBridgePortControlTimeStamp, sleBridgePortControlReqResult, sleBridgePortControlIndex, sleBridgePortControlUnknownMcastBlock
				 }
			STATUS current
			DESCRIPTION 
				"Description."
			::= { sleBridgePortNotification 25 }

		
		sleBridgePortDescriptionChanged NOTIFICATION-TYPE
			OBJECTS { sleBridgePortControlRequest, sleBridgePortControlTimeStamp, sleBridgePortControlReqResult, sleBridgePortControlIndex, sleBridgePortControlDescription
				 }
			STATUS current
			DESCRIPTION 
				"Description."
			::= { sleBridgePortNotification 26 }

		
		sleBridgePortHoldTimeChanged NOTIFICATION-TYPE
			OBJECTS { sleBridgePortControlRequest, sleBridgePortControlTimeStamp, sleBridgePortControlReqResult, sleBridgePortControlIndex, sleBridgePortControlHoldTime
				 }
			STATUS current
			DESCRIPTION 
				"Description."
			::= { sleBridgePortNotification 27 }

		
		sleBridgePortMacAntiSpoofChanged NOTIFICATION-TYPE
			OBJECTS { sleBridgePortControlRequest, sleBridgePortControlTimeStamp, sleBridgePortControlReqResult, sleBridgePortControlIndex, sleBridgePortControlMacAntiSpoofing
				 }
			STATUS current
			DESCRIPTION 
				"setBridgePortMacAntiSpoofing"
			::= { sleBridgePortNotification 28 }

		
		sleBridgePortSwitchStatusChanged NOTIFICATION-TYPE
			OBJECTS { sleBridgePortControlRequest, sleBridgePortControlTimeStamp, sleBridgePortControlReqResult, sleBridgePortControlIndex, sleBridgePortControlSwitchStatus
				 }
			STATUS current
			DESCRIPTION 
				"setBridgePortSwitchStatus"
			::= { sleBridgePortNotification 29 }

		
		sleBridgePortSwitchModeChanged NOTIFICATION-TYPE
			OBJECTS { sleBridgePortControlRequest, sleBridgePortControlTimeStamp, sleBridgePortControlReqResult, sleBridgePortControlIndex, sleBridgePortControlSwitchMode, 
				sleBridgePortControlSwitchSubMode, sleBridgePortControlSwitchIngressFilter }
			STATUS current
			DESCRIPTION 
				"setBridgePortSwitchMode"
			::= { sleBridgePortNotification 30 }

		
		sleBridgePortSwitchDefaultVlanChanged NOTIFICATION-TYPE
			OBJECTS { sleBridgePortControlRequest, sleBridgePortControlTimeStamp, sleBridgePortControlReqResult, sleBridgePortControlIndex, sleBridgePortControlSwitchDefaultVlan
				 }
			STATUS current
			DESCRIPTION 
				"setBridgePortSwitchDefaultVlan"
			::= { sleBridgePortNotification 31 }

		
		sleBridgePortSwitchNativeVlanChanged NOTIFICATION-TYPE
			OBJECTS { sleBridgePortControlRequest, sleBridgePortControlTimeStamp, sleBridgePortControlReqResult, sleBridgePortControlIndex, sleBridgePortControlSwitchNativeVid
				 }
			STATUS current
			DESCRIPTION 
				"setBridgePortSwitchNativeVlan"
			::= { sleBridgePortNotification 32 }

		
		sleBridgePortSwitchAccFramTypeChanged NOTIFICATION-TYPE
			OBJECTS { sleBridgePortControlRequest, sleBridgePortControlTimeStamp, sleBridgePortControlReqResult, sleBridgePortControlIndex, sleBridgePortControlSwitchAccFrameType
				 }
			STATUS current
			DESCRIPTION 
				"setBridgePortSwitchAccFramType"
			::= { sleBridgePortNotification 33 }

		
		sleBridgePortSwitchAllowdVlanAdded NOTIFICATION-TYPE
			OBJECTS { sleBridgePortControlRequest, sleBridgePortControlTimeStamp, sleBridgePortControlReqResult, sleBridgePortControlIndex, sleBridgePortControlSwitchAllowedVlan, 
				sleBridgePortControlSwitchAllowedVlanEtag }
			STATUS current
			DESCRIPTION 
				"setBridgePortSwitchAddAllowdVlan"
			::= { sleBridgePortNotification 34 }

		
		sleBridgePortSwitchAllowdVlanDeleted NOTIFICATION-TYPE
			OBJECTS { sleBridgePortControlRequest, sleBridgePortControlTimeStamp, sleBridgePortControlReqResult, sleBridgePortControlIndex, sleBridgePortControlSwitchAllowedVlan, 
				sleBridgePortControlSwitchAllowedVlanEtag }
			STATUS current
			DESCRIPTION 
				"setBridgePortSwitchRemoveAllowdVlan"
			::= { sleBridgePortNotification 35 }

		
		sleBridgePortSwitchStaticChannelChanged NOTIFICATION-TYPE
			OBJECTS { sleBridgePortControlRequest, sleBridgePortControlTimeStamp, sleBridgePortControlReqResult, sleBridgePortControlIndex, sleBridgePortControlSwitchStaticChannelGroup
				 }
			STATUS current
			DESCRIPTION 
				"setBridgePortSwitchStaticChannel"
			::= { sleBridgePortNotification 36 }

		
		sleBridgePortSwitchChannelLoadbalanceChanged NOTIFICATION-TYPE
			OBJECTS { sleBridgePortControlRequest, sleBridgePortControlTimeStamp, sleBridgePortControlReqResult, sleBridgePortControlIndex, sleBridgePortControlSwitchChannelLoadbalance
				 }
			STATUS current
			DESCRIPTION 
				"setBridgePortSwitchChannelLoadbalance"
			::= { sleBridgePortNotification 37 }

		
		sleBridgePortPortLinkCntChanged NOTIFICATION-TYPE
			OBJECTS { sleBridgePortControlRequest, sleBridgePortControlTimeStamp, sleBridgePortControlReqResult }
			STATUS current
			DESCRIPTION 
				"Description."
			::= { sleBridgePortNotification 38 }

		
		sleBridgePortSwitchChannelProfileChanged NOTIFICATION-TYPE
			OBJECTS { sleBridgePortControlRequest, sleBridgePortControlTimeStamp, sleBridgePortControlReqResult, sleBridgePortControlSwitchAggrType, sleBridgePortControlSwitchAggrId, 
				sleBridgePortControlSwitchAggrMode }
			STATUS current
			DESCRIPTION 
				"setBridgePortSwitchChannelProfile"
			::= { sleBridgePortNotification 39 }

		
		sleBridgePortSwitchChannelProfileDeleted NOTIFICATION-TYPE
			OBJECTS { sleBridgePortControlRequest, sleBridgePortControlTimeStamp, sleBridgePortControlReqResult, sleBridgePortControlSwitchAggrType, sleBridgePortControlSwitchAggrId, 
				sleBridgePortControlSwitchAggrMode }
			STATUS current
			DESCRIPTION 
				"setBridgePortSwitchNoChannelProfile"
			::= { sleBridgePortNotification 40 }

		
		sleBridgePortLoopDetectPeriodMsChanged NOTIFICATION-TYPE
			OBJECTS { sleBridgePortControlRequest, sleBridgePortControlTimeStamp, sleBridgePortControlReqResult, sleBridgePortLoopDetectPeriod }
			STATUS current
			DESCRIPTION 
				"Description."
			::= { sleBridgePortNotification 71 }

		
		sleBridgePortLoopDetectLoopingCountChanged NOTIFICATION-TYPE
			OBJECTS { sleBridgePortControlRequest, sleBridgePortControlTimeStamp, sleBridgePortControlReqResult, sleBridgePortControlIndex, sleBridgePortControlLoopDetectAdminCount
				 }
			STATUS current
			DESCRIPTION 
				"Description."
			::= { sleBridgePortNotification 72 }

		
		sleBridgePortLoopDetectVlanChanged NOTIFICATION-TYPE
			OBJECTS { sleBridgePortControlRequest, sleBridgePortControlTimeStamp, sleBridgePortControlReqResult, sleBridgePortControlIndex, sleBridgePortControlLoopDetectVlan
				 }
			STATUS current
			DESCRIPTION 
				"setBridgeLoopDetectVlan"
			::= { sleBridgePortNotification 73 }

		
		sleBridgePortLoopDetectVlanDeleted NOTIFICATION-TYPE
			OBJECTS { sleBridgePortControlRequest, sleBridgePortControlTimeStamp, sleBridgePortControlReqResult, sleBridgePortControlIndex }
			STATUS current
			DESCRIPTION 
				"delBridgeLoopDetectVlan"
			::= { sleBridgePortNotification 74 }

		
		sleBridgePortMaxNewHostsChanged NOTIFICATION-TYPE
			OBJECTS { sleBridgePortControlRequest, sleBridgePortControlTimeStamp, sleBridgePortControlReqResult, sleBridgePortControlIndex, sleBridgePortControlMaxNewHosts
				 }
			STATUS current
			DESCRIPTION 
				"setBridgePortMaxNewHosts"
			::= { sleBridgePortNotification 75 }

		
		sleBridgePortSpanningTreeDetectedProtocolsCleared NOTIFICATION-TYPE
			OBJECTS { sleBridgePortControlRequest, sleBridgePortControlTimeStamp, sleBridgePortControlReqResult, sleBridgePortControlIndex }
			STATUS current
			DESCRIPTION 
				"clearSpanningTreeDetectedProtocols"
			::= { sleBridgePortNotification 76 }

		
		sleBridgePortStpStatusChanged NOTIFICATION-TYPE
			OBJECTS { sleBridgePortControlRequest, sleBridgePortControlTimeStamp, sleBridgePortControlReqResult, sleBridgePortControlIndex, sleBridgePortControlStpStatus
				 }
			STATUS current
			DESCRIPTION 
				"setBridgePortStpStatus"
			::= { sleBridgePortNotification 77 }

		
		sleBridgePortStpBpduGuardChanged NOTIFICATION-TYPE
			OBJECTS { sleBridgePortControlRequest, sleBridgePortControlTimeStamp, sleBridgePortControlReqResult, sleBridgePortControlIndex, sleBridgePortControlStpBpduGuard
				 }
			STATUS current
			DESCRIPTION 
				"setBridgePortStpBpduGuard"
			::= { sleBridgePortNotification 78 }

		
		sleBridgePortOuterTpidChanged NOTIFICATION-TYPE
			OBJECTS { sleBridgePortControlRequest, sleBridgePortControlTimeStamp, sleBridgePortControlReqResult, sleBridgePortControlIndex, sleBridgePortControlOuterTpid
				 }
			STATUS current
			DESCRIPTION 
				"setBridgePortOuterTpid "
			::= { sleBridgePortNotification 79 }

		
		sleBridgePortMirrorMonitorChanged NOTIFICATION-TYPE
			OBJECTS { sleBridgePortControlRequest, sleBridgePortControlTimeStamp, sleBridgePortControlReqResult, sleBridgePortControlIndex, sleBridgePortControlMirrorMonitor
				 }
			STATUS current
			DESCRIPTION 
				"setBridgePortMirrorMonitor"
			::= { sleBridgePortNotification 80 }

		
		sleBridgePortBandwidthChanged NOTIFICATION-TYPE
			OBJECTS { sleBridgePortControlRequest, sleBridgePortControlTimeStamp, sleBridgePortControlReqResult, sleBridgePortControlIndex, sleBridgePortControlBandwidth
				 }
			STATUS current
			DESCRIPTION 
				"setBridgePortBandwidth "
			::= { sleBridgePortNotification 81 }

		
		sleBridgePortAliasSet NOTIFICATION-TYPE
			OBJECTS { sleBridgePortControlRequest, sleBridgePortControlTimeStamp, sleBridgePortControlReqResult, sleBridgePortControlIndex, sleBridgePortControlAlias
				 }
			STATUS current
			DESCRIPTION 
				"Description."
			::= { sleBridgePortNotification 82 }

		
		sleBridgePortAliasUnset NOTIFICATION-TYPE
			OBJECTS { sleBridgePortControlRequest, sleBridgePortControlTimeStamp, sleBridgePortControlReqResult, sleBridgePortControlIndex }
			STATUS current
			DESCRIPTION 
				"Description."
			::= { sleBridgePortNotification 83 }

		
		sleBridgePortMulticastChanged NOTIFICATION-TYPE
			OBJECTS { sleBridgePortControlRequest, sleBridgePortControlTimeStamp, sleBridgePortControlReqResult, sleBridgePortControlIndex, sleBridgePortControlMulticast
				 }
			STATUS current
			DESCRIPTION 
				"Description."
			::= { sleBridgePortNotification 84 }

		
		sleBridgePortFloodBlockChanged NOTIFICATION-TYPE
			OBJECTS { sleBridgePortControlRequest, sleBridgePortControlTimeStamp, sleBridgePortControlReqResult, sleBridgePortControlIndex, sleBridgePortControlFloodBlock
				 }
			STATUS current
			DESCRIPTION 
				"Description."
			::= { sleBridgePortNotification 85 }

		
		sleVlan OBJECT IDENTIFIER ::= { sleBridge 3 }

		
		sleVlanTable OBJECT-TYPE
			SYNTAX SEQUENCE OF SleVlanEntry
			MAX-ACCESS not-accessible
			STATUS current
			DESCRIPTION
				" sle vlan table"
			::= { sleVlan 1 }

		
		sleVlanEntry OBJECT-TYPE
			SYNTAX SleVlanEntry
			MAX-ACCESS not-accessible
			STATUS current
			DESCRIPTION
				" key: sleVlanIndex"
			INDEX { sleVlanIndex }
			::= { sleVlanTable 1 }

		
		SleVlanEntry ::=
			SEQUENCE { 
				sleVlanIndex
					INTEGER,
				sleVlanIfIndex
					Integer32,
				sleVlanName
					OCTET STRING,
				sleVlanStatus
					INTEGER,
				sleVlanEgressPorts
					OCTET STRING,
				sleVlanUnTaggedPorts
					OCTET STRING,
				sleVlanCreationTime
					TimeTicks,
				sleVlanAgeingTime
					INTEGER,
				sleVlanTagTxCounter
					Counter64,
				sleVlanDescription
					OCTET STRING,
				sleVlanElineEnable
					INTEGER,
				sleVlanOperStatus
					INTEGER,
				sleVlanMtu
					Integer32,
				sleVlanType
					INTEGER
			 }

		sleVlanIndex OBJECT-TYPE
			SYNTAX INTEGER (1..4094)
			MAX-ACCESS read-only
			STATUS current
			DESCRIPTION
				"A vlan-identifier."
			::= { sleVlanEntry 1 }

		
		sleVlanIfIndex OBJECT-TYPE
			SYNTAX Integer32
			MAX-ACCESS read-only
			STATUS current
			DESCRIPTION
				"Same as ifIndex (for appropriated ifTable entries)."
			::= { sleVlanEntry 2 }

		
		sleVlanName OBJECT-TYPE
			SYNTAX OCTET STRING
			MAX-ACCESS read-only
			STATUS current
			DESCRIPTION
				"A descriptional name for that vlan."
			::= { sleVlanEntry 3 }

		
		sleVlanStatus OBJECT-TYPE
			SYNTAX INTEGER
				{
				static(1),
				dynamic(2)
				}
			MAX-ACCESS read-only
			STATUS current
			DESCRIPTION
				"static, in future gvrp"
			::= { sleVlanEntry 4 }

		
		sleVlanEgressPorts OBJECT-TYPE
			SYNTAX OCTET STRING
			MAX-ACCESS read-only
			STATUS current
			DESCRIPTION
				"Portlist for all member of this VLAN, they will send tagged or untagged frames.
				The octet string is a list of pairs of octets each identify
				an sleBridgePortIndex. The least significant byte is the
				second octet."
			::= { sleVlanEntry 5 }

		
		sleVlanUnTaggedPorts OBJECT-TYPE
			SYNTAX OCTET STRING
			MAX-ACCESS read-only
			STATUS current
			DESCRIPTION
				"Portlist for members of this Vlan they will send only untagged frames.
				The octet string is a list of pairs of octets each identify
				an sleBridgePortIndex. The least significant byte is the second
				octet."
			::= { sleVlanEntry 6 }

		
		sleVlanCreationTime OBJECT-TYPE
			SYNTAX TimeTicks
			MAX-ACCESS read-only
			STATUS current
			DESCRIPTION
				"Only useful in case of gvrp."
			::= { sleVlanEntry 7 }

		
		sleVlanAgeingTime OBJECT-TYPE
			SYNTAX INTEGER (-1 | 0 | 10..21474830)
			MAX-ACCESS read-only
			STATUS current
			DESCRIPTION
				"The ageing time per vlan"
			::= { sleVlanEntry 8 }

		
		sleVlanTagTxCounter OBJECT-TYPE
			SYNTAX Counter64
			MAX-ACCESS read-only
			STATUS current
			DESCRIPTION
				"The VLAN tag tx counter."
			::= { sleVlanEntry 9 }

		
		sleVlanDescription OBJECT-TYPE
			SYNTAX OCTET STRING (SIZE (0..32))
			MAX-ACCESS read-only
			STATUS current
			DESCRIPTION
				"createVlan:
				(sleVlanControlIndex)
				sleVlanControlName
				sleVlanControlMulticastPermision"
			::= { sleVlanEntry 10 }

		
		sleVlanElineEnable OBJECT-TYPE
			SYNTAX INTEGER
				{
				disable(0),
				enable(1)
				}
			MAX-ACCESS read-only
			STATUS current
			DESCRIPTION
				"Indicate whether E-line service enable or not"
			::= { sleVlanEntry 11 }

		
		sleVlanOperStatus OBJECT-TYPE
			SYNTAX INTEGER
				{
				invalid(0),
				inactive(1),
				active(2)
				}
			MAX-ACCESS read-only
			STATUS current
			DESCRIPTION
				"The Vlan operation status."
			::= { sleVlanEntry 12 }

		
		sleVlanMtu OBJECT-TYPE
			SYNTAX Integer32
			MAX-ACCESS read-only
			STATUS current
			DESCRIPTION
				"The Vlan MTU."
			::= { sleVlanEntry 13 }

		
		sleVlanType OBJECT-TYPE
			SYNTAX INTEGER
				{
				customer(1),
				service(2)
				}
			MAX-ACCESS read-only
			STATUS current
			DESCRIPTION
				"The Vlan service either customer or service."
			DEFVAL { 1 }
			::= { sleVlanEntry 14 }

		
		sleVlanControl OBJECT IDENTIFIER ::= { sleVlan 2 }

		
		sleVlanControlRequest OBJECT-TYPE
			SYNTAX INTEGER
				{
				createVlan(1),
				destroyVlan(2),
				setVlanPortProfile(3),
				setVlanAgeingTime(4),
				createVlanRange(5),
				setVlanDesc(6),
				createElineVlan(7),
				setVlanOperStatus(8),
				setVlanMtu(9),
				setVlanServiceOperStatus(10)
				}
			MAX-ACCESS read-write
			STATUS current
			DESCRIPTION
				"
				createVlan:
				(sleVlanControlIndex)
				sleVlanControlName
				sleVlanControlMulticastPermision
				
				destroyVlan:
				sleVlanControlIndex
				
				setVlanPortProfile:
				sleVlanControlIndex
				sleVlanControlEgressPorts
				sleVlanControlUnTaggedPorts
				
				setVlanMulticastPermission:
				sleVlanControlIndex
				sleVlanControlMulticastPermission
				
				"
			::= { sleVlanControl 1 }

		
		sleVlanControlStatus OBJECT-TYPE
			SYNTAX SleControlStatusType
			MAX-ACCESS read-only
			STATUS current
			DESCRIPTION
				"The status of a user command. 
				"
			::= { sleVlanControl 2 }

		
		sleVlanControlTimer OBJECT-TYPE
			SYNTAX Gauge32
			MAX-ACCESS read-write
			STATUS current
			DESCRIPTION
				"The maximum wait time for the manager for a long running user command. 
				"
			::= { sleVlanControl 3 }

		
		sleVlanControlTimeStamp OBJECT-TYPE
			SYNTAX TimeTicks
			MAX-ACCESS read-only
			STATUS current
			DESCRIPTION
				"The time stamp of the last command (end of command)."
			::= { sleVlanControl 4 }

		
		sleVlanControlReqResult OBJECT-TYPE
			SYNTAX SleControlRequestResultType
			MAX-ACCESS read-only
			STATUS current
			DESCRIPTION
				"The result of the last user command."
			::= { sleVlanControl 5 }

		
		sleVlanControlIndex OBJECT-TYPE
			SYNTAX Integer32 (1..4094)
			MAX-ACCESS read-write
			STATUS current
			DESCRIPTION
				"Vlan's ID
				"
			::= { sleVlanControl 6 }

		
		sleVlanControlName OBJECT-TYPE
			SYNTAX OCTET STRING
			MAX-ACCESS read-write
			STATUS current
			DESCRIPTION
				"Vlan's name."
			::= { sleVlanControl 7 }

		
		sleVlanControlEgressPorts OBJECT-TYPE
			SYNTAX OCTET STRING
			MAX-ACCESS read-write
			STATUS current
			DESCRIPTION
				" Portlist for all member of this VLAN, they will send tagged or untagged frames. The OctetString is a list of pairs of octets each identify an sheBridgePortIndex. The least significant byte is the second octet."
			::= { sleVlanControl 8 }

		
		sleVlanControlUnTaggedPorts OBJECT-TYPE
			SYNTAX OCTET STRING
			MAX-ACCESS read-write
			STATUS current
			DESCRIPTION
				" Portlist for members of this Vlan they will send only untagged frames. The OctetString is a list of pairs of octets each identify an sleBridgePortIndex. The least significant byte is the second octet."
			::= { sleVlanControl 9 }

		
		sleVlanControlAgeingTime OBJECT-TYPE
			SYNTAX INTEGER (-1 | 0 | 10..21474830)
			MAX-ACCESS read-write
			STATUS current
			DESCRIPTION
				"The ageing time per vlan
				(supported only model 5924N)"
			::= { sleVlanControl 10 }

		
		sleVlanControlIndexTo OBJECT-TYPE
			SYNTAX Integer32 (1..4094)
			MAX-ACCESS read-write
			STATUS current
			DESCRIPTION
				"Vlan's ID
				"
			::= { sleVlanControl 11 }

		
		sleVlanControlDescription OBJECT-TYPE
			SYNTAX OCTET STRING (SIZE (0..32))
			MAX-ACCESS read-write
			STATUS current
			DESCRIPTION
				"createVlan:
				(sleVlanControlIndex)
				sleVlanControlName
				sleVlanControlMulticastPermision"
			::= { sleVlanControl 12 }

		
		sleVlanControlElineEnable OBJECT-TYPE
			SYNTAX INTEGER
				{
				disable(0),
				enable(1)
				}
			MAX-ACCESS read-write
			STATUS current
			DESCRIPTION
				"Indicate whether E-line service enable or not"
			::= { sleVlanControl 13 }

		
		sleVlanControlOperStatus OBJECT-TYPE
			SYNTAX INTEGER
				{
				invalid(0),
				inactive(1),
				active(2)
				}
			MAX-ACCESS read-write
			STATUS current
			DESCRIPTION
				"The Vlan operation status."
			::= { sleVlanControl 14 }

		
		sleVlanControlMtu OBJECT-TYPE
			SYNTAX Integer32
			MAX-ACCESS read-write
			STATUS current
			DESCRIPTION
				"The Vlan MTU."
			::= { sleVlanControl 15 }

		
		sleVlanControlType OBJECT-TYPE
			SYNTAX INTEGER
				{
				customer(1),
				service(2)
				}
			MAX-ACCESS read-write
			STATUS current
			DESCRIPTION
				"The Vlan service type."
			::= { sleVlanControl 16 }

		
		sleVlanControlServiceType OBJECT-TYPE
			SYNTAX INTEGER
				{
				pointToPoint(1),
				multipointToMultipoint(2),
				rootedToMultipoint(3)
				}
			MAX-ACCESS read-write
			STATUS current
			DESCRIPTION
				"The Vlan service type."
			::= { sleVlanControl 17 }

		
		sleVlanNotification OBJECT IDENTIFIER ::= { sleVlan 3 }

		
		sleVlanCreated NOTIFICATION-TYPE
			OBJECTS { sleVlanName, sleVlanEgressPorts, sleVlanUnTaggedPorts, sleVlanControlRequest, sleVlanControlTimeStamp, 
				sleVlanControlReqResult, sleVlanIfIndex, sleVlanStatus }
			STATUS current
			DESCRIPTION 
				"Description."
			::= { sleVlanNotification 1 }

		
		sleVlanDestroyed NOTIFICATION-TYPE
			OBJECTS { sleVlanControlRequest, sleVlanControlTimeStamp, sleVlanControlReqResult, sleVlanControlIndex }
			STATUS current
			DESCRIPTION 
				" "
			::= { sleVlanNotification 2 }

		
		sleVlanPortProfileChanged NOTIFICATION-TYPE
			OBJECTS { sleVlanEgressPorts, sleVlanUnTaggedPorts, sleVlanControlRequest, sleVlanControlTimeStamp, sleVlanControlReqResult
				 }
			STATUS current
			DESCRIPTION 
				" "
			::= { sleVlanNotification 3 }

		
		sleVlanAgeingTimeChanged NOTIFICATION-TYPE
			OBJECTS { sleVlanControlRequest, sleVlanControlTimeStamp, sleVlanControlAgeingTime, sleVlanControlIndex, sleVlanControlReqResult
				 }
			STATUS current
			DESCRIPTION 
				"Description."
			::= { sleVlanNotification 4 }

		
		sleVlanRangeCreated NOTIFICATION-TYPE
			OBJECTS { sleVlanControlRequest, sleVlanControlTimeStamp, sleVlanControlReqResult, sleVlanControlIndex, sleVlanControlIndexTo
				 }
			STATUS current
			DESCRIPTION 
				"Description."
			::= { sleVlanNotification 5 }

		
		sleVlanDescriptionChanged NOTIFICATION-TYPE
			OBJECTS { sleVlanControlRequest, sleVlanControlTimeStamp, sleVlanControlReqResult, sleVlanControlIndex, sleVlanControlDescription
				 }
			STATUS current
			DESCRIPTION 
				"setVlanDesc"
			::= { sleVlanNotification 6 }

		
		sleVlanElineVlanCreated NOTIFICATION-TYPE
			OBJECTS { sleVlanControlRequest, sleVlanControlTimeStamp, sleVlanControlReqResult, sleVlanControlIndex, sleVlanControlElineEnable
				 }
			STATUS current
			DESCRIPTION 
				"createElineVlan"
			::= { sleVlanNotification 7 }

		
		sleVlanOperStatusChagned NOTIFICATION-TYPE
			OBJECTS { sleVlanControlRequest, sleVlanControlTimeStamp, sleVlanControlReqResult, sleVlanControlIndex, sleVlanControlOperStatus
				 }
			STATUS current
			DESCRIPTION 
				"setVlanOperStatus"
			::= { sleVlanNotification 8 }

		
		sleVlanMtuChagned NOTIFICATION-TYPE
			OBJECTS { sleVlanControlRequest, sleVlanControlTimeStamp, sleVlanControlReqResult, sleVlanControlIndex, sleVlanControlMtu
				 }
			STATUS current
			DESCRIPTION 
				"sleVlanMtuChanged"
			::= { sleVlanNotification 9 }

		
		sleServiceVlanTable OBJECT-TYPE
			SYNTAX SEQUENCE OF SleServiceVlanEntry
			MAX-ACCESS not-accessible
			STATUS current
			DESCRIPTION
				" sle vlan table"
			::= { sleVlan 4 }

		
		sleServiceVlanEntry OBJECT-TYPE
			SYNTAX SleServiceVlanEntry
			MAX-ACCESS not-accessible
			STATUS current
			DESCRIPTION
				" key: sleVlanIndex"
			INDEX { sleVlanIndex }
			::= { sleServiceVlanTable 1 }

		
		SleServiceVlanEntry ::=
			SEQUENCE { 
				sleServiceVlanIndex
					INTEGER,
				sleServiceVlanName
					OCTET STRING,
				sleServiceVlanDescription
					OCTET STRING,
				sleServiceVlanOperStatus
					INTEGER,
				sleServiceVlanMtu
					Integer32,
				sleServiceVlanStatus
					INTEGER,
				sleServiceVlanType
					INTEGER,
				sleServiceVlanSeviceType
					INTEGER
			 }

		sleServiceVlanIndex OBJECT-TYPE
			SYNTAX INTEGER (1..4094)
			MAX-ACCESS read-only
			STATUS current
			DESCRIPTION
				"A vlan-identifier."
			::= { sleServiceVlanEntry 1 }

		
		sleServiceVlanName OBJECT-TYPE
			SYNTAX OCTET STRING
			MAX-ACCESS read-only
			STATUS current
			DESCRIPTION
				"A descriptional name for that vlan."
			::= { sleServiceVlanEntry 2 }

		
		sleServiceVlanDescription OBJECT-TYPE
			SYNTAX OCTET STRING (SIZE (0..32))
			MAX-ACCESS read-only
			STATUS current
			DESCRIPTION
				"createVlan:
				(sleVlanControlIndex)
				sleVlanControlName
				sleVlanControlMulticastPermision"
			::= { sleServiceVlanEntry 3 }

		
		sleServiceVlanOperStatus OBJECT-TYPE
			SYNTAX INTEGER
				{
				invalid(0),
				inactive(1),
				active(2)
				}
			MAX-ACCESS read-only
			STATUS current
			DESCRIPTION
				"The Vlan operation status."
			::= { sleServiceVlanEntry 4 }

		
		sleServiceVlanMtu OBJECT-TYPE
			SYNTAX Integer32
			MAX-ACCESS read-only
			STATUS current
			DESCRIPTION
				"The Vlan MTU."
			::= { sleServiceVlanEntry 5 }

		
		sleServiceVlanStatus OBJECT-TYPE
			SYNTAX INTEGER
				{
				static(1),
				dynamic(2)
				}
			MAX-ACCESS read-only
			STATUS current
			DESCRIPTION
				"static, in future gvrp"
			::= { sleServiceVlanEntry 6 }

		
		sleServiceVlanType OBJECT-TYPE
			SYNTAX INTEGER
				{
				customer(1),
				service(2)
				}
			MAX-ACCESS read-only
			STATUS current
			DESCRIPTION
				"The Vlan service either customer or service."
			DEFVAL { 1 }
			::= { sleServiceVlanEntry 7 }

		
		sleServiceVlanSeviceType OBJECT-TYPE
			SYNTAX INTEGER
				{
				pointToPoint(1),
				multipointToMultipoint(2),
				rootedToMultipoint(3)
				}
			MAX-ACCESS read-write
			STATUS current
			DESCRIPTION
				"The Vlan service type."
			::= { sleServiceVlanEntry 8 }

		
		sleVlanMap OBJECT IDENTIFIER ::= { sleBridge 4 }

		
		sleVlanMapTable OBJECT-TYPE
			SYNTAX SEQUENCE OF SleVlanMapEntry
			MAX-ACCESS not-accessible
			STATUS current
			DESCRIPTION
				"vlan map table."
			::= { sleVlanMap 1 }

		
		sleVlanMapEntry OBJECT-TYPE
			SYNTAX SleVlanMapEntry
			MAX-ACCESS not-accessible
			STATUS current
			DESCRIPTION
				" key: sleVlanIndex"
			INDEX { sleVlanIndex }
			::= { sleVlanMapTable 1 }

		
		SleVlanMapEntry ::=
			SEQUENCE { 
				sleVlanMapFid
					Unsigned32,
				sleVlanMapStpId
					Unsigned32,
				sleVlanMapErpDomainId
					Unsigned32
			 }

		sleVlanMapFid OBJECT-TYPE
			SYNTAX Unsigned32
			MAX-ACCESS read-only
			STATUS current
			DESCRIPTION
				"Index of the used Filtering Table entry."
			::= { sleVlanMapEntry 1 }

		
		sleVlanMapStpId OBJECT-TYPE
			SYNTAX Unsigned32
			MAX-ACCESS read-only
			STATUS current
			DESCRIPTION
				"Index of the used STP instance."
			::= { sleVlanMapEntry 2 }

		
		sleVlanMapErpDomainId OBJECT-TYPE
			SYNTAX Unsigned32
			MAX-ACCESS read-only
			STATUS current
			DESCRIPTION
				"Index of the used Erp Domain."
			::= { sleVlanMapEntry 3 }

		
		sleVlanMapControl OBJECT IDENTIFIER ::= { sleVlanMap 2 }

		
		sleVlanMapControlRequest OBJECT-TYPE
			SYNTAX INTEGER
				{
				setVlanMapFid(1),
				setVlanMapStpId(2),
				setVlanMapErpDomainId(3)
				}
			MAX-ACCESS read-write
			STATUS current
			DESCRIPTION
				"
				setVlanMapFid:
				sleVlanMapControlIndex
				sleVlanMapFid
				
				setVlanMapStpId:
				sleVlanMapControlIndex
				sleVlanMapStpId
				
				setVlanMapErpDomainId:
				sleVlanMapControlIndex
				sleVlanMapErpDomainId
				
				"
			::= { sleVlanMapControl 1 }

		
		sleVlanMapControlStatus OBJECT-TYPE
			SYNTAX SleControlStatusType
			MAX-ACCESS read-only
			STATUS current
			DESCRIPTION
				"The status of a user command. 
				"
			::= { sleVlanMapControl 2 }

		
		sleVlanMapControlTimer OBJECT-TYPE
			SYNTAX Gauge32
			MAX-ACCESS read-write
			STATUS current
			DESCRIPTION
				"The maximum wait time for the manager for a long running user command. 
				"
			::= { sleVlanMapControl 3 }

		
		sleVlanMapControlTimeStamp OBJECT-TYPE
			SYNTAX TimeTicks
			MAX-ACCESS read-only
			STATUS current
			DESCRIPTION
				"The time stamp of the last command (end of command)."
			::= { sleVlanMapControl 4 }

		
		sleVlanMapControlReqResult OBJECT-TYPE
			SYNTAX SleControlRequestResultType
			MAX-ACCESS read-only
			STATUS current
			DESCRIPTION
				"The result of the last user command."
			::= { sleVlanMapControl 5 }

		
		sleVlanMapControlIndex OBJECT-TYPE
			SYNTAX Integer32 (1..4094)
			MAX-ACCESS read-write
			STATUS current
			DESCRIPTION
				"vlan map index."
			::= { sleVlanMapControl 6 }

		
		sleVlanMapControlFid OBJECT-TYPE
			SYNTAX Unsigned32
			MAX-ACCESS read-write
			STATUS current
			DESCRIPTION
				" FDB identifier"
			::= { sleVlanMapControl 7 }

		
		sleVlanMapControlStpId OBJECT-TYPE
			SYNTAX Unsigned32
			MAX-ACCESS read-write
			STATUS current
			DESCRIPTION
				" STP Instance Identifier"
			::= { sleVlanMapControl 8 }

		
		sleVlanMapControlErpDomainId OBJECT-TYPE
			SYNTAX Unsigned32
			MAX-ACCESS read-write
			STATUS current
			DESCRIPTION
				" The Erp Domain ID."
			::= { sleVlanMapControl 9 }

		
		sleVlanMapNotification OBJECT IDENTIFIER ::= { sleVlanMap 3 }

		
		sleVlanMapFidChanged NOTIFICATION-TYPE
			OBJECTS { sleVlanMapControlTimeStamp, sleVlanMapControlReqResult, sleVlanMapControlRequest, sleVlanMapFid }
			STATUS current
			DESCRIPTION 
				" "
			::= { sleVlanMapNotification 1 }

		
		sleVlanMapStpIdChanged NOTIFICATION-TYPE
			OBJECTS { sleVlanMapStpId, sleVlanMapControlRequest, sleVlanMapControlTimeStamp, sleVlanMapControlReqResult }
			STATUS current
			DESCRIPTION 
				" "
			::= { sleVlanMapNotification 2 }

		
		sleVlanMapErpDomainIdChanged NOTIFICATION-TYPE
			OBJECTS { sleVlanMapErpDomainId, sleVlanMapControlRequest, sleVlanMapControlTimeStamp, sleVlanMapControlReqResult }
			STATUS current
			DESCRIPTION 
				" "
			::= { sleVlanMapNotification 3 }

		
		sleStp OBJECT IDENTIFIER ::= { sleBridge 5 }

		
		sleStpInfo OBJECT IDENTIFIER ::= { sleStp 1 }

		
		sleStpOperationMode OBJECT-TYPE
			SYNTAX INTEGER
				{
				stp(0),
				rstp(1),
				mstp(3),
				pvstp(4),
				pvrstp(5),
				pvrstpPlus(6),
				pvstpPlus(7)
				}
			MAX-ACCESS read-only
			STATUS current
			DESCRIPTION
				"The operation mode of running the STP at the switch."
			::= { sleStpInfo 1 }

		
		sleStpFormatSelector OBJECT-TYPE
			SYNTAX INTEGER (0..65535)
			MAX-ACCESS read-only
			STATUS current
			DESCRIPTION
				"The MST configuration format selector."
			::= { sleStpInfo 2 }

		
		sleStpConfigureName OBJECT-TYPE
			SYNTAX OCTET STRING (SIZE (0..32))
			MAX-ACCESS read-write
			STATUS current
			DESCRIPTION
				"The MST configuration name of at most 32 characters."
			::= { sleStpInfo 3 }

		
		sleStpRevisionLevel OBJECT-TYPE
			SYNTAX INTEGER (0..65535)
			MAX-ACCESS read-only
			STATUS current
			DESCRIPTION
				"The MST configuration revision."
			::= { sleStpInfo 4 }

		
		sleStpFwdDelay OBJECT-TYPE
			SYNTAX INTEGER (4..300)
			MAX-ACCESS read-only
			STATUS current
			DESCRIPTION
				"The STP bridge forward delay."
			::= { sleStpInfo 5 }

		
		sleStpHelloTime OBJECT-TYPE
			SYNTAX INTEGER (1..10)
			MAX-ACCESS read-only
			STATUS current
			DESCRIPTION
				"The STP bridge hello time."
			::= { sleStpInfo 6 }

		
		sleStpMaxAge OBJECT-TYPE
			SYNTAX INTEGER (6..40)
			MAX-ACCESS read-only
			STATUS current
			DESCRIPTION
				"The STP bridge max age."
			::= { sleStpInfo 7 }

		
		sleStpMaxHops OBJECT-TYPE
			SYNTAX INTEGER (1..40)
			MAX-ACCESS read-only
			STATUS current
			DESCRIPTION
				"The MST bridge max hops."
			::= { sleStpInfo 8 }

		
		sleStpExtRootBridgeId OBJECT-TYPE
			SYNTAX OCTET STRING (SIZE (8))
			MAX-ACCESS read-only
			STATUS current
			DESCRIPTION
				"The MST CST root identifier."
			::= { sleStpInfo 9 }

		
		sleStpExtPathcost OBJECT-TYPE
			SYNTAX Unsigned32
			MAX-ACCESS read-only
			STATUS current
			DESCRIPTION
				"The MST CST root path cost."
			::= { sleStpInfo 10 }

		
		sleStpBpduGuardMode OBJECT-TYPE
			SYNTAX INTEGER
				{
				disable(0),
				enable(1)
				}
			MAX-ACCESS read-only
			STATUS current
			DESCRIPTION
				"Indicates the mode of Bpdu Guard Feature on the switch. 
				When the system with Bpdu Guard enabled 
				receives a BPDU from any port, that port is 
				immediately disabled.  	 
				
				disable -- the Bpdu Guard feature is disabled on this
				          switch.
				
				enable -- the Bpdu Guard feature is enabled on this
				          switch. 
				
				           Whether the Bpdu Guard feature is enabled
				           or not on this switch depends on the object
				           value of sleStpControlBpduGuardMode."
			DEFVAL { 0 }
			::= { sleStpInfo 11 }

		
		sleStpBpduGuardAutoRcvMode OBJECT-TYPE
			SYNTAX INTEGER
				{
				disable(0),
				enable(1)
				}
			MAX-ACCESS read-only
			STATUS current
			DESCRIPTION
				"Indicates the automatic recovery mode for the ports disabled by Bpdu Guard.
				
				disable -- the Bpdu Guard Auto Recovery feature is disabled on this
				          switch.
				
				enable -- the Bpdu Guard Auto Recovery feature is enabled on this
				          switch. 
				
				           Whether the Bpdu Guard Auto Recovery feature is enabled
				           or not on this switch depends on the object
				           value of sleStpControlBpduGuardAutoRcvMode."
			DEFVAL { 0 }
			::= { sleStpInfo 12 }

		
		sleStpBpduGuardAutoRcvTime OBJECT-TYPE
			SYNTAX INTEGER (10..1000000)
			MAX-ACCESS read-only
			STATUS current
			DESCRIPTION
				"Indicates the automatic recovery time for the ports disabled by Bpdu Guard.
				Unit: second
				
				The Bpdu Guard Auto Recovery time depends on the object value 
				of sleStpControlBpduGuardAutoRcvTime."
			DEFVAL { 300 }
			::= { sleStpInfo 13 }

		
		sleStpControl OBJECT IDENTIFIER ::= { sleStp 2 }

		
		sleStpControlRequest OBJECT-TYPE
			SYNTAX INTEGER
				{
				setStpOperationMode(1),
				setStpConfigureProfile(2),
				setStpTimerProfile(3),
				setStpBpduGuardProfile(4)
				}
			MAX-ACCESS read-write
			STATUS current
			DESCRIPTION
				"
				setStpOperationMode:
				sleStpControlOperationMode
				
				setStpConfigureProfile:
				sleStpControlConfigureName
				sleStpControlRevisionLevel
				
				setStpTimerProfile
				sleStpControlFwdDelay
				sleStpControlHelloTime
				sleStpControlMaxAge
				sleStpControlMaxHops
				"
			::= { sleStpControl 1 }

		
		sleStpControlStatus OBJECT-TYPE
			SYNTAX SleControlStatusType
			MAX-ACCESS read-only
			STATUS current
			DESCRIPTION
				"The status of a user command. 
				"
			::= { sleStpControl 2 }

		
		sleStpControlTimer OBJECT-TYPE
			SYNTAX Gauge32
			MAX-ACCESS read-write
			STATUS current
			DESCRIPTION
				"The maximum wait time for the manager for a long running user command. 
				"
			::= { sleStpControl 3 }

		
		sleStpControlTimeStamp OBJECT-TYPE
			SYNTAX TimeTicks
			MAX-ACCESS read-only
			STATUS current
			DESCRIPTION
				"The time stamp of the last command (end of command)."
			::= { sleStpControl 4 }

		
		sleStpControlReqResult OBJECT-TYPE
			SYNTAX SleControlRequestResultType
			MAX-ACCESS read-only
			STATUS current
			DESCRIPTION
				"The result of the last user command."
			::= { sleStpControl 5 }

		
		sleStpControlOperationMode OBJECT-TYPE
			SYNTAX INTEGER
				{
				stp(0),
				rstp(1),
				mstp(3),
				pvstp(4),
				pvrstp(5),
				pvrstpPlus(6),
				pvstpPlus(7)
				}
			MAX-ACCESS read-write
			STATUS current
			DESCRIPTION
				" The operation mode of running the STP at the switch."
			::= { sleStpControl 6 }

		
		sleStpControlConfigureName OBJECT-TYPE
			SYNTAX OCTET STRING (SIZE (0..32))
			MAX-ACCESS read-write
			STATUS current
			DESCRIPTION
				" The MST configuration name of at most 32 characters."
			::= { sleStpControl 7 }

		
		sleStpControlRevisionLevel OBJECT-TYPE
			SYNTAX INTEGER (0..65535)
			MAX-ACCESS read-write
			STATUS current
			DESCRIPTION
				" The MST configuration revision."
			::= { sleStpControl 8 }

		
		sleStpControlFwdDelay OBJECT-TYPE
			SYNTAX INTEGER (4..30)
			MAX-ACCESS read-write
			STATUS current
			DESCRIPTION
				" The STP bridge forward delay."
			::= { sleStpControl 9 }

		
		sleStpControlHelloTime OBJECT-TYPE
			SYNTAX INTEGER (1..10)
			MAX-ACCESS read-write
			STATUS current
			DESCRIPTION
				" The STP bridge hello time."
			::= { sleStpControl 10 }

		
		sleStpControlMaxAge OBJECT-TYPE
			SYNTAX INTEGER (4..60)
			MAX-ACCESS read-write
			STATUS current
			DESCRIPTION
				" The STP bridge max age."
			::= { sleStpControl 11 }

		
		sleStpControlMaxHops OBJECT-TYPE
			SYNTAX INTEGER (1..40)
			MAX-ACCESS read-write
			STATUS current
			DESCRIPTION
				" The MST bridge max hops."
			::= { sleStpControl 12 }

		
		sleStpControlBpduGuardMode OBJECT-TYPE
			SYNTAX INTEGER
				{
				disable(0),
				enable(1)
				}
			MAX-ACCESS read-write
			STATUS current
			DESCRIPTION
				"Configures the mode of Bpdu Guard Feature on the switch. 
				When the system with Bpdu Guard enabled 
				receives a BPDU from any port, that port is 
				immediately disabled.  	 
				
				disable -- the Bpdu Guard feature is disabled on this
				          switch.
				
				enable -- the Bpdu Guard feature is enabled on this
				          switch. 
				"
			DEFVAL { 0 }
			::= { sleStpControl 13 }

		
		sleStpControlBpduGuardAutoRcvMode OBJECT-TYPE
			SYNTAX INTEGER
				{
				disable(0),
				enable(1)
				}
			MAX-ACCESS read-write
			STATUS current
			DESCRIPTION
				"Configures the automatic recovery mode for the ports disabled by Bpdu Guard.
				
				disable -- the Bpdu Guard Auto Recovery feature is disabled on this
				          switch.
				
				enable -- the Bpdu Guard Auto Recovery feature is enabled on this
				          switch. "
			DEFVAL { 0 }
			::= { sleStpControl 14 }

		
		sleStpControlBpduGuardAutoRcvTime OBJECT-TYPE
			SYNTAX INTEGER (10..1000000)
			MAX-ACCESS read-write
			STATUS current
			DESCRIPTION
				"Configures the automatic recovery time for the ports disabled by Bpdu Guard.
				Unit: second"
			DEFVAL { 300 }
			::= { sleStpControl 15 }

		
		sleStpNotification OBJECT IDENTIFIER ::= { sleStp 3 }

		
		sleStpOperationModeChanged NOTIFICATION-TYPE
			OBJECTS { sleStpControlRequest, sleStpControlReqResult, sleStpControlTimeStamp, sleStpOperationMode }
			STATUS current
			DESCRIPTION 
				" "
			::= { sleStpNotification 1 }

		
		sleStpConfigureProfileChanged NOTIFICATION-TYPE
			OBJECTS { sleStpControlRequest, sleStpControlReqResult, sleStpControlTimeStamp, sleStpRevisionLevel, sleStpConfigureName
				 }
			STATUS current
			DESCRIPTION 
				" "
			::= { sleStpNotification 2 }

		
		sleStpTimerProfileChanged NOTIFICATION-TYPE
			OBJECTS { sleStpControlRequest, sleStpControlReqResult, sleStpControlTimeStamp, sleStpFwdDelay, sleStpHelloTime, 
				sleStpMaxAge, sleStpMaxHops }
			STATUS current
			DESCRIPTION 
				" "
			::= { sleStpNotification 3 }

		
		sleStpBpduGuardProfileChanged NOTIFICATION-TYPE
			OBJECTS { sleStpControlRequest, sleStpControlReqResult, sleStpControlTimeStamp, sleStpBpduGuardMode, sleStpBpduGuardAutoRcvMode, 
				sleStpBpduGuardAutoRcvTime }
			STATUS current
			DESCRIPTION 
				" "
			::= { sleStpNotification 4 }

		
		sleStpInstance OBJECT IDENTIFIER ::= { sleBridge 6 }

		
		sleStpInstanceTable OBJECT-TYPE
			SYNTAX SEQUENCE OF SleStpInstanceEntry
			MAX-ACCESS not-accessible
			STATUS current
			DESCRIPTION
				" STP instance table."
			::= { sleStpInstance 1 }

		
		sleStpInstanceEntry OBJECT-TYPE
			SYNTAX SleStpInstanceEntry
			MAX-ACCESS not-accessible
			STATUS current
			DESCRIPTION
				" key: sleStpInstanceIndex"
			INDEX { sleStpInstanceIndex }
			::= { sleStpInstanceTable 1 }

		
		SleStpInstanceEntry ::=
			SEQUENCE { 
				sleStpInstanceIndex
					INTEGER,
				sleStpInstanceEnable
					INTEGER,
				sleStpInstancePriority
					Integer32,
				sleStpInstanceRootBridgeId
					OCTET STRING,
				sleStpInstanceRootPathcost
					Integer32,
				sleStpInstanceDesignatedBridgeId
					OCTET STRING,
				sleStpInstanceDesignatedPortId
					INTEGER,
				sleStpInstanceRootPortId
					INTEGER,
				sleStpInstanceFwdDelay
					INTEGER,
				sleStpInstanceHelloTime
					INTEGER,
				sleStpInstanceMaxAge
					INTEGER,
				sleStpInstanceRemainHops
					Integer32,
				sleStpInstanceBrFwdDelay
					INTEGER,
				sleStpInstanceBrHelloTime
					INTEGER,
				sleStpInstanceBrMaxAge
					INTEGER
			 }

		sleStpInstanceIndex OBJECT-TYPE
			SYNTAX INTEGER (0..4096)
			MAX-ACCESS read-only
			STATUS current
			DESCRIPTION
				"The STP instance ID."
			::= { sleStpInstanceEntry 1 }

		
		sleStpInstanceEnable OBJECT-TYPE
			SYNTAX INTEGER
				{
				enable(0),
				disable(1)
				}
			MAX-ACCESS read-only
			STATUS current
			DESCRIPTION
				"The enabled/disabled status of the pvst."
			::= { sleStpInstanceEntry 2 }

		
		sleStpInstancePriority OBJECT-TYPE
			SYNTAX Integer32
			MAX-ACCESS read-only
			STATUS current
			DESCRIPTION
				"The bridge priority."
			::= { sleStpInstanceEntry 3 }

		
		sleStpInstanceRootBridgeId OBJECT-TYPE
			SYNTAX OCTET STRING (SIZE (8))
			MAX-ACCESS read-only
			STATUS current
			DESCRIPTION
				"The STP designated root bridge identifier in a specific instance. Size: 8."
			::= { sleStpInstanceEntry 4 }

		
		sleStpInstanceRootPathcost OBJECT-TYPE
			SYNTAX Integer32
			MAX-ACCESS read-only
			STATUS current
			DESCRIPTION
				"The STP root path cost in a specific instance."
			::= { sleStpInstanceEntry 5 }

		
		sleStpInstanceDesignatedBridgeId OBJECT-TYPE
			SYNTAX OCTET STRING (SIZE (8))
			MAX-ACCESS read-only
			STATUS current
			DESCRIPTION
				"TThe STP designated bridge identifier."
			::= { sleStpInstanceEntry 6 }

		
		sleStpInstanceDesignatedPortId OBJECT-TYPE
			SYNTAX INTEGER (0..256)
			MAX-ACCESS read-only
			STATUS current
			DESCRIPTION
				"The STP designated port identifier."
			::= { sleStpInstanceEntry 7 }

		
		sleStpInstanceRootPortId OBJECT-TYPE
			SYNTAX INTEGER (0..256)
			MAX-ACCESS read-only
			STATUS current
			DESCRIPTION
				"The port number of the port which offers the lowest
				cost path from the this STP instance of this bridge
				to the root bridge."
			::= { sleStpInstanceEntry 8 }

		
		sleStpInstanceFwdDelay OBJECT-TYPE
			SYNTAX INTEGER (4..30)
			MAX-ACCESS read-only
			STATUS current
			DESCRIPTION
				"The current forward delay of the STP Instance."
			::= { sleStpInstanceEntry 9 }

		
		sleStpInstanceHelloTime OBJECT-TYPE
			SYNTAX INTEGER (1..10)
			MAX-ACCESS read-only
			STATUS current
			DESCRIPTION
				"The current hello time of the STP Instance."
			::= { sleStpInstanceEntry 10 }

		
		sleStpInstanceMaxAge OBJECT-TYPE
			SYNTAX INTEGER (4..60)
			MAX-ACCESS read-only
			STATUS current
			DESCRIPTION
				"The current max age of the STP Instance."
			::= { sleStpInstanceEntry 11 }

		
		sleStpInstanceRemainHops OBJECT-TYPE
			SYNTAX Integer32
			MAX-ACCESS read-only
			STATUS current
			DESCRIPTION
				"The current remain hops of the MSTI or pvst."
			::= { sleStpInstanceEntry 12 }

		
		sleStpInstanceBrFwdDelay OBJECT-TYPE
			SYNTAX INTEGER (4..30)
			MAX-ACCESS read-only
			STATUS current
			DESCRIPTION
				"The Setting forward delay of the STP Instance."
			::= { sleStpInstanceEntry 13 }

		
		sleStpInstanceBrHelloTime OBJECT-TYPE
			SYNTAX INTEGER (1..10)
			MAX-ACCESS read-only
			STATUS current
			DESCRIPTION
				"The current hello time of the STP Instance."
			::= { sleStpInstanceEntry 14 }

		
		sleStpInstanceBrMaxAge OBJECT-TYPE
			SYNTAX INTEGER (4..60)
			MAX-ACCESS read-only
			STATUS current
			DESCRIPTION
				"The Setting max age of the STP Instance."
			::= { sleStpInstanceEntry 15 }

		
		sleStpInstanceControl OBJECT IDENTIFIER ::= { sleStpInstance 2 }

		
		sleStpInstanceControlRequest OBJECT-TYPE
			SYNTAX INTEGER
				{
				setStpInstanceEnable(1),
				setStpInstanceConfigProfile(2)
				}
			MAX-ACCESS read-write
			STATUS current
			DESCRIPTION
				"
				createStpInstance:
				sleStpInstanceControlIndex
				sleStpInstanceControlEnable
				sleStpInstanceControlPriority
				sleStpInstanceControlBrFwdDelay
				sleStpInstanceControlBrHelloTime
				sleStpInstanceControlBrMaxAge
				
				destroyStpInstance:
				sleStpInstanceControlIndex
				
				setStpInstanceEnable:
				sleStpInstanceControlIndex
				sleStpInstanceControlEnable
				
				setStpInstanceConfigProfile:
				sleStpInstanceControlIndex
				sleStpInstanceControlPriority
				sleStpInstanceControlBrFwdDelay
				sleStpInstanceControlBrHelloTime
				sleStpInstanceControlBrMaxAge
				"
			::= { sleStpInstanceControl 1 }

		
		sleStpInstanceControlStatus OBJECT-TYPE
			SYNTAX SleControlStatusType
			MAX-ACCESS read-only
			STATUS current
			DESCRIPTION
				"The status of a user command. 
				"
			::= { sleStpInstanceControl 2 }

		
		sleStpInstanceControlTimer OBJECT-TYPE
			SYNTAX Gauge32
			MAX-ACCESS read-write
			STATUS current
			DESCRIPTION
				"The maximum wait time for the manager for a long running user command. 
				"
			::= { sleStpInstanceControl 3 }

		
		sleStpInstanceControlTimeStamp OBJECT-TYPE
			SYNTAX TimeTicks
			MAX-ACCESS read-only
			STATUS current
			DESCRIPTION
				"The time stamp of the last command (end of command)."
			::= { sleStpInstanceControl 4 }

		
		sleStpInstanceControlReqResult OBJECT-TYPE
			SYNTAX SleControlRequestResultType
			MAX-ACCESS read-only
			STATUS current
			DESCRIPTION
				"The result of the last user command."
			::= { sleStpInstanceControl 5 }

		
		sleStpInstanceControlIndex OBJECT-TYPE
			SYNTAX INTEGER (0..4096)
			MAX-ACCESS read-write
			STATUS current
			DESCRIPTION
				" sleStpInstanceIndex"
			::= { sleStpInstanceControl 6 }

		
		sleStpInstanceControlEnable OBJECT-TYPE
			SYNTAX INTEGER
				{
				disable(0),
				enable(1)
				}
			MAX-ACCESS read-write
			STATUS current
			DESCRIPTION
				" The enabled/disabled status of the pvst."
			::= { sleStpInstanceControl 7 }

		
		sleStpInstanceControlPriority OBJECT-TYPE
			SYNTAX INTEGER (0..16)
			MAX-ACCESS read-write
			STATUS current
			DESCRIPTION
				"The Setting bridge priority in a specific instance. 
				This values are matched specific values in CLI.
				sleStpInstanceControlPriority X 4096 is equal to priority value in CLI.
				(ex. 2 in SNMP means 8192 in CLI)"
			DEFVAL { 8 }
			::= { sleStpInstanceControl 8 }

		
		sleStpInstanceControlBrFwdDelay OBJECT-TYPE
			SYNTAX INTEGER (4..30)
			MAX-ACCESS read-write
			STATUS current
			DESCRIPTION
				" The Setting forward delay of the MSTI or pvst."
			DEFVAL { 15 }
			::= { sleStpInstanceControl 9 }

		
		sleStpInstanceControlBrHelloTime OBJECT-TYPE
			SYNTAX INTEGER (1..10)
			MAX-ACCESS read-write
			STATUS current
			DESCRIPTION
				" The current hello time of the MSTI or pvst."
			DEFVAL { 2 }
			::= { sleStpInstanceControl 10 }

		
		sleStpInstanceControlBrMaxAge OBJECT-TYPE
			SYNTAX INTEGER (4..60)
			MAX-ACCESS read-write
			STATUS current
			DESCRIPTION
				" The Setting max age of the MSTI or pvst."
			DEFVAL { 30 }
			::= { sleStpInstanceControl 11 }

		
		sleStpInstanceNotification OBJECT IDENTIFIER ::= { sleStpInstance 3 }

		
		sleStpInstanceEnableChanged NOTIFICATION-TYPE
			OBJECTS { sleStpInstanceControlRequest, sleStpInstanceControlReqResult, sleStpInstanceControlIndex, sleStpInstanceControlEnable, sleStpInstanceControlTimeStamp
				 }
			STATUS current
			DESCRIPTION 
				" "
			::= { sleStpInstanceNotification 1 }

		
		sleStpInstanceConfigProfileChanged NOTIFICATION-TYPE
			OBJECTS { sleStpInstanceControlRequest, sleStpInstanceControlReqResult, sleStpInstanceControlIndex, sleStpInstanceControlPriority, sleStpInstanceControlBrFwdDelay, 
				sleStpInstanceControlBrHelloTime, sleStpInstanceControlBrMaxAge, sleStpInstanceControlTimeStamp }
			STATUS current
			DESCRIPTION 
				" "
			::= { sleStpInstanceNotification 2 }

		
		sleStpInstancePort OBJECT IDENTIFIER ::= { sleBridge 7 }

		
		sleStpInstancePortTable OBJECT-TYPE
			SYNTAX SEQUENCE OF SleStpInstancePortEntry
			MAX-ACCESS not-accessible
			STATUS current
			DESCRIPTION
				" STP instance port table"
			::= { sleStpInstancePort 1 }

		
		sleStpInstancePortEntry OBJECT-TYPE
			SYNTAX SleStpInstancePortEntry
			MAX-ACCESS not-accessible
			STATUS current
			DESCRIPTION
				" key: sleStpInstanceIndex, sleStpInstancePortIndex"
			INDEX { sleStpInstanceIndex, sleStpInstancePortIndex }
			::= { sleStpInstancePortTable 1 }

		
		SleStpInstancePortEntry ::=
			SEQUENCE { 
				sleStpInstancePortIndex
					InterfaceIndex,
				sleStpInstancePortPathcost
					INTEGER,
				sleStpInstancePortPriority
					INTEGER,
				sleStpInstancePortRole
					INTEGER,
				sleStpInstancePortState
					INTEGER,
				sleStpInstancePortRootBridgeId
					OCTET STRING,
				sleStpInstancePortRootPathcost
					Integer32,
				sleStpInstancePortDesignateBridgeId
					OCTET STRING,
				sleStpInstancePortDesignatePortId
					INTEGER,
				sleStpInstancePortRootGuardMode
					INTEGER
			 }

		sleStpInstancePortIndex OBJECT-TYPE
			SYNTAX InterfaceIndex
			MAX-ACCESS read-only
			STATUS current
			DESCRIPTION
				"The Port ID."
			::= { sleStpInstancePortEntry 1 }

		
		sleStpInstancePortPathcost OBJECT-TYPE
			SYNTAX INTEGER (0..200000000)
			MAX-ACCESS read-write
			STATUS current
			DESCRIPTION
				"The STP port path cost."
			::= { sleStpInstancePortEntry 2 }

		
		sleStpInstancePortPriority OBJECT-TYPE
			SYNTAX INTEGER (0..255)
			MAX-ACCESS read-only
			STATUS current
			DESCRIPTION
				"The STP port priority."
			::= { sleStpInstancePortEntry 3 }

		
		sleStpInstancePortRole OBJECT-TYPE
			SYNTAX INTEGER
				{
				disable(0),
				designated(1),
				root(2),
				master(3),
				alternate(4),
				backup(5)
				}
			MAX-ACCESS read-only
			STATUS current
			DESCRIPTION
				"The current STP Role of the Port."
			::= { sleStpInstancePortEntry 4 }

		
		sleStpInstancePortState OBJECT-TYPE
			SYNTAX INTEGER
				{
				disabled(0),
				listening(1),
				learning(2),
				forwarding(3),
				blocking(4)
				}
			MAX-ACCESS read-only
			STATUS current
			DESCRIPTION
				"The STP forwarding state of a specific port."
			::= { sleStpInstancePortEntry 5 }

		
		sleStpInstancePortRootBridgeId OBJECT-TYPE
			SYNTAX OCTET STRING (SIZE (8))
			MAX-ACCESS read-only
			STATUS current
			DESCRIPTION
				"The unique Bridge Identifier of the Bridge recorded
				as the Root in the Configuration BPDUs transmitted
				by the Designated Bridge for the segment to which
				the port is attached."
			::= { sleStpInstancePortEntry 6 }

		
		sleStpInstancePortRootPathcost OBJECT-TYPE
			SYNTAX Integer32
			MAX-ACCESS read-only
			STATUS current
			DESCRIPTION
				"The path cost of the Designated Port of the segment
				connected to this port."
			::= { sleStpInstancePortEntry 7 }

		
		sleStpInstancePortDesignateBridgeId OBJECT-TYPE
			SYNTAX OCTET STRING (SIZE (8))
			MAX-ACCESS read-only
			STATUS current
			DESCRIPTION
				"The Bridge Identifier of the bridge which this port
				considers to be the Designated Bridge for this
				port's segment."
			::= { sleStpInstancePortEntry 8 }

		
		sleStpInstancePortDesignatePortId OBJECT-TYPE
			SYNTAX INTEGER (0..256)
			MAX-ACCESS read-only
			STATUS current
			DESCRIPTION
				"The Port Identifier of the port on the Designated
				Bridge for this port's segment."
			::= { sleStpInstancePortEntry 9 }

		
		sleStpInstancePortRootGuardMode OBJECT-TYPE
			SYNTAX INTEGER
				{
				disable(0),
				enable(1)
				}
			MAX-ACCESS read-only
			STATUS current
			DESCRIPTION
				"An indication of whether the RootGuard capability is enabled
				on this port or not.
				This configuration will be applied to the VLAN or MSTP instance
				in which this port exists.
				
				Whether the RootGuard capability is enabled or not 
				on this switch depends on the object value of 
				sleStpInstancePortControlRootGuardMode."
			DEFVAL { 0 }
			::= { sleStpInstancePortEntry 10 }

		
		sleStpInstancePortControl OBJECT IDENTIFIER ::= { sleStpInstancePort 2 }

		
		sleStpInstancePortControlRequest OBJECT-TYPE
			SYNTAX INTEGER { setStpInstancePortProfile(1) }
			MAX-ACCESS read-write
			STATUS current
			DESCRIPTION
				"
				setStpInstancePortProfile:
				sleStpInstancePortControlIndex
				sleStpInstancePortControlInstanceId
				sleStpInstancePortControlPathcost
				sleStpInstancePortControlPriority
				"
			::= { sleStpInstancePortControl 1 }

		
		sleStpInstancePortControlStatus OBJECT-TYPE
			SYNTAX SleControlStatusType
			MAX-ACCESS read-only
			STATUS current
			DESCRIPTION
				"The status of a user command. 
				"
			::= { sleStpInstancePortControl 2 }

		
		sleStpInstancePortControlTimer OBJECT-TYPE
			SYNTAX Gauge32
			MAX-ACCESS read-write
			STATUS current
			DESCRIPTION
				"The maximum wait time for the manager for a long running user command. 
				"
			::= { sleStpInstancePortControl 3 }

		
		sleStpInstancePortControlTimeStamp OBJECT-TYPE
			SYNTAX TimeTicks
			MAX-ACCESS read-only
			STATUS current
			DESCRIPTION
				"The time stamp of the last command (end of command)."
			::= { sleStpInstancePortControl 4 }

		
		sleStpInstancePortControlReqResult OBJECT-TYPE
			SYNTAX SleControlRequestResultType
			MAX-ACCESS read-only
			STATUS current
			DESCRIPTION
				"The result of the last user command."
			::= { sleStpInstancePortControl 5 }

		
		sleStpInstancePortControlIndex OBJECT-TYPE
			SYNTAX INTEGER (0..65535)
			MAX-ACCESS read-write
			STATUS current
			DESCRIPTION
				"sleStpInstancePortIndex"
			::= { sleStpInstancePortControl 6 }

		
		sleStpInstancePortControlInstanceId OBJECT-TYPE
			SYNTAX INTEGER (0..4096)
			MAX-ACCESS read-write
			STATUS current
			DESCRIPTION
				" sleStpInstanceId"
			::= { sleStpInstancePortControl 7 }

		
		sleStpInstancePortControlPathcost OBJECT-TYPE
			SYNTAX INTEGER (0..200000000)
			MAX-ACCESS read-write
			STATUS current
			DESCRIPTION
				" The path cost of the Designated Port of the segment
				connected to this port."
			::= { sleStpInstancePortControl 8 }

		
		sleStpInstancePortControlPriority OBJECT-TYPE
			SYNTAX INTEGER (0..255)
			MAX-ACCESS read-write
			STATUS current
			DESCRIPTION
				" The STP port priority."
			DEFVAL { 128 }
			::= { sleStpInstancePortControl 9 }

		
		sleStpInstancePortControlRootGuardMode OBJECT-TYPE
			SYNTAX INTEGER
				{
				disable(0),
				enable(1)
				}
			MAX-ACCESS read-write
			STATUS current
			DESCRIPTION
				"Enable or disable RootGuard capability on this port.
				This configuration will be applied to the VLAN or MSTP instance
				in which this port exists."
			DEFVAL { 0 }
			::= { sleStpInstancePortControl 10 }

		
		sleStpInstancePortNotification OBJECT IDENTIFIER ::= { sleStpInstancePort 3 }

		
		sleStpInstancePortProfileChanged NOTIFICATION-TYPE
			OBJECTS { sleStpInstancePortControlRequest, sleStpInstancePortControlReqResult, sleStpInstancePortControlTimeStamp, sleStpInstancePortPathcost, sleStpInstancePortPriority, 
				sleStpInstancePortRootGuardMode }
			STATUS current
			DESCRIPTION 
				" "
			::= { sleStpInstancePortNotification 1 }

		
		sleSubnetVlan OBJECT IDENTIFIER ::= { sleBridge 8 }

		
		sleSubnetVlanTable OBJECT-TYPE
			SYNTAX SEQUENCE OF SleSubnetVlanEntry
			MAX-ACCESS not-accessible
			STATUS current
			DESCRIPTION
				" subnet vlan table."
			::= { sleSubnetVlan 1 }

		
		sleSubnetVlanEntry OBJECT-TYPE
			SYNTAX SleSubnetVlanEntry
			MAX-ACCESS not-accessible
			STATUS current
			DESCRIPTION
				" key: sleSubnetVlanIp, sleSubnetVlanMask"
			INDEX { sleSubnetVlanIp, sleSubnetVlanMask }
			::= { sleSubnetVlanTable 1 }

		
		SleSubnetVlanEntry ::=
			SEQUENCE { 
				sleSubnetVlanIp
					IpAddress,
				sleSubnetVlanMask
					Integer32,
				sleSubnetVlanVid
					Integer32
			 }

		sleSubnetVlanIp OBJECT-TYPE
			SYNTAX IpAddress
			MAX-ACCESS read-only
			STATUS current
			DESCRIPTION
				"Ip address of Subnet"
			::= { sleSubnetVlanEntry 1 }

		
		sleSubnetVlanMask OBJECT-TYPE
			SYNTAX Integer32 (1..32)
			MAX-ACCESS read-only
			STATUS current
			DESCRIPTION
				"Mask bit."
			::= { sleSubnetVlanEntry 2 }

		
		sleSubnetVlanVid OBJECT-TYPE
			SYNTAX Integer32 (1..4094)
			MAX-ACCESS read-only
			STATUS current
			DESCRIPTION
				"Index of the VLAN."
			::= { sleSubnetVlanEntry 3 }

		
		sleSubnetVlanControl OBJECT IDENTIFIER ::= { sleSubnetVlan 2 }

		
		sleSubnetVlanControlRequest OBJECT-TYPE
			SYNTAX INTEGER
				{
				createSubnetVlan(1),
				destorySubnetVlan(2)
				}
			MAX-ACCESS read-write
			STATUS current
			DESCRIPTION
				"
				createSubnetVlan:
				sleSubnetVlanControlPortIndex
				sleSubnetVlanControlIp
				sleSubnetVlanControlMask
				sleSubnetVlanControlVid
				
				destorySubnetVlan:
				sleSubnetVlanControlPortIndex
				
				"
			::= { sleSubnetVlanControl 1 }

		
		sleSubnetVlanControlStatus OBJECT-TYPE
			SYNTAX SleControlStatusType
			MAX-ACCESS read-only
			STATUS current
			DESCRIPTION
				"The status of a user command. 
				"
			::= { sleSubnetVlanControl 2 }

		
		sleSubnetVlanControlTimer OBJECT-TYPE
			SYNTAX Gauge32
			MAX-ACCESS read-write
			STATUS current
			DESCRIPTION
				"The maximum wait time for the manager for a long running user command. 
				"
			::= { sleSubnetVlanControl 3 }

		
		sleSubnetVlanControlTimeStamp OBJECT-TYPE
			SYNTAX TimeTicks
			MAX-ACCESS read-only
			STATUS current
			DESCRIPTION
				"The time stamp of the last command (end of command)."
			::= { sleSubnetVlanControl 4 }

		
		sleSubnetVlanControlReqResult OBJECT-TYPE
			SYNTAX SleControlRequestResultType
			MAX-ACCESS read-only
			STATUS current
			DESCRIPTION
				"The result of the last user command."
			::= { sleSubnetVlanControl 5 }

		
		sleSubnetVlanControlIp OBJECT-TYPE
			SYNTAX IpAddress
			MAX-ACCESS read-write
			STATUS current
			DESCRIPTION
				"IP address"
			::= { sleSubnetVlanControl 6 }

		
		sleSubnetVlanControlMask OBJECT-TYPE
			SYNTAX Integer32 (1..32)
			MAX-ACCESS read-write
			STATUS current
			DESCRIPTION
				"Mask bit
				"
			::= { sleSubnetVlanControl 7 }

		
		sleSubnetVlanControlVid OBJECT-TYPE
			SYNTAX Integer32 (1..4094)
			MAX-ACCESS read-write
			STATUS current
			DESCRIPTION
				"Vlan's ID"
			::= { sleSubnetVlanControl 8 }

		
		sleSubnetVlanNotification OBJECT IDENTIFIER ::= { sleSubnetVlan 3 }

		
		sleSubnetVlanCreated NOTIFICATION-TYPE
			OBJECTS { sleSubnetVlanControlTimeStamp, sleSubnetVlanControlReqResult, sleSubnetVlanControlRequest, sleSubnetVlanVid }
			STATUS current
			DESCRIPTION 
				" "
			::= { sleSubnetVlanNotification 1 }

		
		sleSubnetVlanDestroyed NOTIFICATION-TYPE
			OBJECTS { sleSubnetVlanControlRequest, sleSubnetVlanControlTimeStamp, sleSubnetVlanControlReqResult, sleSubnetVlanVid }
			STATUS current
			DESCRIPTION 
				" "
			::= { sleSubnetVlanNotification 2 }

		
		sleProtocolVlan OBJECT IDENTIFIER ::= { sleBridge 9 }

		
		sleProtocolVlanTable OBJECT-TYPE
			SYNTAX SEQUENCE OF SleProtocolVlanEntry
			MAX-ACCESS not-accessible
			STATUS current
			DESCRIPTION
				" protocol vlan table."
			::= { sleProtocolVlan 1 }

		
		sleProtocolVlanEntry OBJECT-TYPE
			SYNTAX SleProtocolVlanEntry
			MAX-ACCESS not-accessible
			STATUS current
			DESCRIPTION
				" key: sleBridgePortIndex, sleProtocolVlanEtype"
			INDEX { sleBridgePortIndex, sleProtocolVlanEtype }
			::= { sleProtocolVlanTable 1 }

		
		SleProtocolVlanEntry ::=
			SEQUENCE { 
				sleProtocolVlanEtype
					Unsigned32,
				sleProtocolVlanVid
					Integer32
			 }

		sleProtocolVlanEtype OBJECT-TYPE
			SYNTAX Unsigned32 (1..65535)
			MAX-ACCESS read-only
			STATUS current
			DESCRIPTION
				"Ethernet type"
			::= { sleProtocolVlanEntry 1 }

		
		sleProtocolVlanVid OBJECT-TYPE
			SYNTAX Integer32 (1..4094)
			MAX-ACCESS read-only
			STATUS current
			DESCRIPTION
				"Index of the VLAN."
			::= { sleProtocolVlanEntry 2 }

		
		sleProtocolVlanControl OBJECT IDENTIFIER ::= { sleProtocolVlan 2 }

		
		sleProtocolVlanControlRequest OBJECT-TYPE
			SYNTAX INTEGER
				{
				createProtocolVlan(1),
				destoryProtocolVlan(2)
				}
			MAX-ACCESS read-write
			STATUS current
			DESCRIPTION
				"
				createProtocolVlan:
				sleProtocolVlanControlPortIndex
				sleProtocolVlanControlEtype
				sleProtocolVlanControlVid
				
				destoryProtocolVlan:
				sleProtocolVlanControlPortIndex
				
				"
			::= { sleProtocolVlanControl 1 }

		
		sleProtocolVlanControlStatus OBJECT-TYPE
			SYNTAX SleControlStatusType
			MAX-ACCESS read-only
			STATUS current
			DESCRIPTION
				"The status of a user command. 
				"
			::= { sleProtocolVlanControl 2 }

		
		sleProtocolVlanControlTimer OBJECT-TYPE
			SYNTAX Gauge32
			MAX-ACCESS read-write
			STATUS current
			DESCRIPTION
				"The maximum wait time for the manager for a long running user command. 
				"
			::= { sleProtocolVlanControl 3 }

		
		sleProtocolVlanControlTimeStamp OBJECT-TYPE
			SYNTAX TimeTicks
			MAX-ACCESS read-only
			STATUS current
			DESCRIPTION
				"The time stamp of the last command (end of command)."
			::= { sleProtocolVlanControl 4 }

		
		sleProtocolVlanControlReqResult OBJECT-TYPE
			SYNTAX SleControlRequestResultType
			MAX-ACCESS read-only
			STATUS current
			DESCRIPTION
				"The result of the last user command."
			::= { sleProtocolVlanControl 5 }

		
		sleProtocolVlanControlPortIndex OBJECT-TYPE
			SYNTAX InterfaceIndex
			MAX-ACCESS read-write
			STATUS current
			DESCRIPTION
				" sleBridgePortIndex, sleProtocolVlanEtype"
			::= { sleProtocolVlanControl 6 }

		
		sleProtocolVlanControlEtype OBJECT-TYPE
			SYNTAX Unsigned32
			MAX-ACCESS read-write
			STATUS current
			DESCRIPTION
				"Ethernet Type"
			::= { sleProtocolVlanControl 7 }

		
		sleProtocolVlanControlVid OBJECT-TYPE
			SYNTAX Integer32 (1..4094)
			MAX-ACCESS read-write
			STATUS current
			DESCRIPTION
				" sleProtocolVlanControlVid"
			::= { sleProtocolVlanControl 8 }

		
		sleProtocolVlanNotification OBJECT IDENTIFIER ::= { sleProtocolVlan 3 }

		
		sleProtocolVlanCreated NOTIFICATION-TYPE
			OBJECTS { sleProtocolVlanVid, sleProtocolVlanControlRequest, sleProtocolVlanControlTimeStamp, sleProtocolVlanControlReqResult }
			STATUS current
			DESCRIPTION 
				" "
			::= { sleProtocolVlanNotification 1 }

		
		sleProtocolVlanDestroyed NOTIFICATION-TYPE
			OBJECTS { sleProtocolVlanControlRequest, sleProtocolVlanControlTimeStamp, sleProtocolVlanControlReqResult, sleProtocolVlanVid }
			STATUS current
			DESCRIPTION 
				" "
			::= { sleProtocolVlanNotification 2 }

		
		sleLag OBJECT IDENTIFIER ::= { sleBridge 10 }

		
		sleLagTable OBJECT-TYPE
			SYNTAX SEQUENCE OF SleLagEntry
			MAX-ACCESS not-accessible
			STATUS current
			DESCRIPTION
				" lag table."
			::= { sleLag 1 }

		
		sleLagEntry OBJECT-TYPE
			SYNTAX SleLagEntry
			MAX-ACCESS not-accessible
			STATUS current
			DESCRIPTION
				" key: sleLagIndex"
			INDEX { sleLagIndex }
			::= { sleLagTable 1 }

		
		SleLagEntry ::=
			SEQUENCE { 
				sleLagIndex
					Integer32,
				sleLagPortId
					InterfaceIndex,
				sleLagDistMode
					INTEGER,
				sleLagPortMap
					OCTET STRING,
				sleLagMode
					INTEGER,
				sleLagLeastActive
					Integer32
			 }

		sleLagIndex OBJECT-TYPE
			SYNTAX Integer32 (0..13)
			MAX-ACCESS read-only
			STATUS current
			DESCRIPTION
				"This value assigned to the aggregation ID."
			::= { sleLagEntry 1 }

		
		sleLagPortId OBJECT-TYPE
			SYNTAX InterfaceIndex
			MAX-ACCESS read-only
			STATUS current
			DESCRIPTION
				"Port ID of aggregation."
			::= { sleLagEntry 2 }

		
		sleLagDistMode OBJECT-TYPE
			SYNTAX INTEGER
				{
				none(0),
				srcmac(1),
				dstmac(2),
				srcdstmac(3),
				srcip(4),
				dstip(5),
				srcdstip(6),
				srcdstl4(7),
				label(80)
				}
			MAX-ACCESS read-only
			STATUS current
			DESCRIPTION
				"This value assigned to the distributing 
				mode of link aggregation."
			::= { sleLagEntry 3 }

		
		sleLagPortMap OBJECT-TYPE
			SYNTAX OCTET STRING
			MAX-ACCESS read-only
			STATUS current
			DESCRIPTION
				"The value assigned to the port list of  the aggregation."
			::= { sleLagEntry 4 }

		
		sleLagMode OBJECT-TYPE
			SYNTAX INTEGER
				{
				inactive(0),
				trunk(1),
				lacp(2)
				}
			MAX-ACCESS read-only
			STATUS current
			DESCRIPTION
				"The operation mode of  link aggregation."
			::= { sleLagEntry 5 }

		
		sleLagLeastActive OBJECT-TYPE
			SYNTAX Integer32
			MAX-ACCESS read-only
			STATUS current
			DESCRIPTION
				"Description."
			::= { sleLagEntry 6 }

		
		sleLagControl OBJECT IDENTIFIER ::= { sleLag 2 }

		
		sleLagControlRequest OBJECT-TYPE
			SYNTAX INTEGER
				{
				setLagProfile(1),
				setLagProfileActiveLink(2)
				}
			MAX-ACCESS read-write
			STATUS current
			DESCRIPTION
				"The MIB object for the user command.."
			::= { sleLagControl 1 }

		
		sleLagControlStatus OBJECT-TYPE
			SYNTAX SleControlStatusType
			MAX-ACCESS read-only
			STATUS current
			DESCRIPTION
				"Describes the status of a user command group, 
				used for block commands while a command execution in process."
			::= { sleLagControl 2 }

		
		sleLagControlTimer OBJECT-TYPE
			SYNTAX Gauge32
			MAX-ACCESS read-write
			STATUS current
			DESCRIPTION
				"Maximum command duration time in case of long running"
			::= { sleLagControl 3 }

		
		sleLagControlTimeStamp OBJECT-TYPE
			SYNTAX TimeTicks
			MAX-ACCESS read-only
			STATUS current
			DESCRIPTION
				"Command result attribute"
			::= { sleLagControl 4 }

		
		sleLagControlReqResult OBJECT-TYPE
			SYNTAX SleControlRequestResultType
			MAX-ACCESS read-only
			STATUS current
			DESCRIPTION
				"Time stamp attribute set at end of command."
			::= { sleLagControl 5 }

		
		sleLagControlIndex OBJECT-TYPE
			SYNTAX Integer32
			MAX-ACCESS read-write
			STATUS current
			DESCRIPTION
				"This value assigned to the aggregation ID."
			::= { sleLagControl 6 }

		
		sleLagControlDistMode OBJECT-TYPE
			SYNTAX INTEGER
				{
				srcmac(1),
				dstmac(2),
				srcdstmac(3),
				srcip(4),
				dstip(5),
				srcdstip(6),
				srcdstl4(7),
				label(80)
				}
			MAX-ACCESS read-write
			STATUS current
			DESCRIPTION
				"This value assigned to the distributing mode of link aggregation."
			::= { sleLagControl 7 }

		
		sleLagControlPortMap OBJECT-TYPE
			SYNTAX OCTET STRING
			MAX-ACCESS read-write
			STATUS current
			DESCRIPTION
				"Port ID of aggregation."
			::= { sleLagControl 8 }

		
		sleLagControlMode OBJECT-TYPE
			SYNTAX INTEGER
				{
				trunk(1),
				lacp(2)
				}
			MAX-ACCESS read-write
			STATUS current
			DESCRIPTION
				"The operation mode of  link aggregation."
			::= { sleLagControl 9 }

		
		sleLagControlLeastActive OBJECT-TYPE
			SYNTAX Integer32
			MAX-ACCESS read-write
			STATUS current
			DESCRIPTION
				"Description."
			::= { sleLagControl 10 }

		
		sleLagNotification OBJECT IDENTIFIER ::= { sleLag 3 }

		
		sleLagProfileChanged NOTIFICATION-TYPE
			OBJECTS { sleLagControlRequest, sleLagControlReqResult, sleLagControlTimeStamp, sleLagLeastActive, sleLagPortMap, 
				sleLagDistMode, sleLagMode }
			STATUS current
			DESCRIPTION 
				" "
			::= { sleLagNotification 1 }

		
		sleLagProfileActiveLinkChanged NOTIFICATION-TYPE
			OBJECTS { sleLagControlRequest, sleLagControlReqResult, sleLagControlTimeStamp, sleLagLeastActive, sleLagPortMap, 
				sleLagDistMode, sleLagMode }
			STATUS current
			DESCRIPTION 
				" "
			::= { sleLagNotification 2 }

		
		sleLagLacp OBJECT IDENTIFIER ::= { sleBridge 11 }

		
		sleLagLacpTable OBJECT-TYPE
			SYNTAX SEQUENCE OF SleLagLacpEntry
			MAX-ACCESS not-accessible
			STATUS current
			DESCRIPTION
				" lag LACP table."
			::= { sleLagLacp 1 }

		
		sleLagLacpEntry OBJECT-TYPE
			SYNTAX SleLagLacpEntry
			MAX-ACCESS not-accessible
			STATUS current
			DESCRIPTION
				" key: sleLagLacpIndex"
			INDEX { sleLagLacpIndex }
			::= { sleLagLacpTable 1 }

		
		SleLagLacpEntry ::=
			SEQUENCE { 
				sleLagLacpIndex
					Integer32,
				sleLagLacpActorAggregatorKey
					Integer32,
				sleLagLacpActorSystemMAC
					OCTET STRING,
				sleLagLacpPartnerSystemMAC
					OCTET STRING,
				sleLagLacpPartnerSystemPriority
					Integer32,
				sleLagLacpPartnerAggregatorKey
					Integer32
			 }

		sleLagLacpIndex OBJECT-TYPE
			SYNTAX Integer32 (0..13)
			MAX-ACCESS read-only
			STATUS current
			DESCRIPTION
				"Location of authentication."
			::= { sleLagLacpEntry 1 }

		
		sleLagLacpActorAggregatorKey OBJECT-TYPE
			SYNTAX Integer32 (1..65535)
			MAX-ACCESS read-only
			STATUS current
			DESCRIPTION
				"The kind of authentication."
			::= { sleLagLacpEntry 2 }

		
		sleLagLacpActorSystemMAC OBJECT-TYPE
			SYNTAX OCTET STRING
			MAX-ACCESS read-write
			STATUS current
			DESCRIPTION
				"The Actor’s System ID, encoded as a MAC address."
			::= { sleLagLacpEntry 3 }

		
		sleLagLacpPartnerSystemMAC OBJECT-TYPE
			SYNTAX OCTET STRING
			MAX-ACCESS read-only
			STATUS current
			DESCRIPTION
				"Enable or disable the corresponding authen method."
			::= { sleLagLacpEntry 4 }

		
		sleLagLacpPartnerSystemPriority OBJECT-TYPE
			SYNTAX Integer32 (1..65535)
			MAX-ACCESS read-only
			STATUS current
			DESCRIPTION
				"The primary priority of the corresponding authen method."
			::= { sleLagLacpEntry 5 }

		
		sleLagLacpPartnerAggregatorKey OBJECT-TYPE
			SYNTAX Integer32 (1..65535)
			MAX-ACCESS read-only
			STATUS current
			DESCRIPTION
				" "
			::= { sleLagLacpEntry 6 }

		
		sleLagLacpStats OBJECT IDENTIFIER ::= { sleLagLacp 2 }

		
		sleLagLacpStatsPduReceived OBJECT-TYPE
			SYNTAX Counter32
			MAX-ACCESS read-only
			STATUS current
			DESCRIPTION
				"The received LACP PDUs"
			::= { sleLagLacpStats 1 }

		
		sleLagLacpStatsPduReceivedErrrors OBJECT-TYPE
			SYNTAX Counter32
			MAX-ACCESS read-only
			STATUS current
			DESCRIPTION
				"The received LACP PDUs"
			::= { sleLagLacpStats 2 }

		
		sleLagLacpStatsPduSent OBJECT-TYPE
			SYNTAX Counter32
			MAX-ACCESS read-only
			STATUS current
			DESCRIPTION
				"The sent LACP PDUs"
			::= { sleLagLacpStats 3 }

		
		sleLagLacpStatsPduSentError OBJECT-TYPE
			SYNTAX Counter32
			MAX-ACCESS read-only
			STATUS current
			DESCRIPTION
				"The sent LACP PDUs error"
			::= { sleLagLacpStats 4 }

		
		sleLagLacpStatsMarkerReceived OBJECT-TYPE
			SYNTAX Counter32
			MAX-ACCESS read-only
			STATUS current
			DESCRIPTION
				"The received LACP Marker"
			::= { sleLagLacpStats 5 }

		
		sleLagLacpStatsMarkerSent OBJECT-TYPE
			SYNTAX Counter32
			MAX-ACCESS read-only
			STATUS current
			DESCRIPTION
				"The sent LACP Marker"
			::= { sleLagLacpStats 6 }

		
		sleLagLacpStatsMarkerSentError OBJECT-TYPE
			SYNTAX Counter32
			MAX-ACCESS read-only
			STATUS current
			DESCRIPTION
				"The sent LACP Marker error."
			::= { sleLagLacpStats 7 }

		
		sleLagLacpControl OBJECT IDENTIFIER ::= { sleLagLacp 3 }

		
		sleLagLacpControlRequest OBJECT-TYPE
			SYNTAX INTEGER { clearLacpStats(1) }
			MAX-ACCESS read-write
			STATUS current
			DESCRIPTION
				"The request of a user command"
			::= { sleLagLacpControl 1 }

		
		sleLagLacpControlStatus OBJECT-TYPE
			SYNTAX SleControlStatusType
			MAX-ACCESS read-only
			STATUS current
			DESCRIPTION
				"The status of user command"
			::= { sleLagLacpControl 2 }

		
		sleLagLacpControlTimer OBJECT-TYPE
			SYNTAX Gauge32
			MAX-ACCESS read-write
			STATUS current
			DESCRIPTION
				"The maximum time for the manager for a long running user command"
			::= { sleLagLacpControl 3 }

		
		sleLagLacpControlTimeStamp OBJECT-TYPE
			SYNTAX TimeTicks
			MAX-ACCESS read-only
			STATUS current
			DESCRIPTION
				"The time stamp of the last command(end of command)"
			::= { sleLagLacpControl 4 }

		
		sleLagLacpControlReqResult OBJECT-TYPE
			SYNTAX SleControlRequestResultType
			MAX-ACCESS read-only
			STATUS current
			DESCRIPTION
				"The result of the last user command"
			::= { sleLagLacpControl 5 }

		
		sleLagLacpNotification OBJECT IDENTIFIER ::= { sleLagLacp 4 }

		
		sleLagLacpStatsCleared NOTIFICATION-TYPE
			OBJECTS { sleLagLacpControlRequest, sleLagLacpControlTimeStamp, sleLagLacpControlReqResult }
			STATUS current
			DESCRIPTION 
				"Description."
			::= { sleLagLacpNotification 1 }

		
		sleLagLacpPort OBJECT IDENTIFIER ::= { sleBridge 12 }

		
		sleLagLacpPortTable OBJECT-TYPE
			SYNTAX SEQUENCE OF SleLagLacpPortEntry
			MAX-ACCESS not-accessible
			STATUS current
			DESCRIPTION
				" lag LACP port table."
			::= { sleLagLacpPort 1 }

		
		sleLagLacpPortEntry OBJECT-TYPE
			SYNTAX SleLagLacpPortEntry
			MAX-ACCESS not-accessible
			STATUS current
			DESCRIPTION
				" key: sleLagLacpPortIndex"
			INDEX { sleLagLacpPortIndex }
			::= { sleLagLacpPortTable 1 }

		
		SleLagLacpPortEntry ::=
			SEQUENCE { 
				sleLagLacpPortIndex
					InterfaceIndex,
				sleLagLacpPortActivity
					INTEGER,
				sleLagLacpPortActorPriority
					INTEGER,
				sleLagLacpPortActorAggregatorId
					Integer32,
				sleLagLacpPortActorAdminKey
					INTEGER,
				sleLagLacpPortActorAdminState
					BITS,
				sleLagLacpPortActorOperKey
					Integer32,
				sleLagLacpPortActorOperState
					BITS,
				sleLagLacpPortPartnerAdminSystemMAC
					OCTET STRING,
				sleLagLacpPortPartnerAdminSystemPriority
					Integer32,
				sleLagLacpPortPartnerAdminKey
					Integer32,
				sleLagLacpPortPartnerAdminNum
					InterfaceIndex,
				sleLagLacpPortPartnerAdminPriority
					Integer32,
				sleLagLacpPortPartnerAdminState
					BITS,
				sleLagLacpPortPartnerOperSystemMAC
					OCTET STRING,
				sleLagLacpPortPartnerOperSystemPriority
					Integer32,
				sleLagLacpPortPartnerOperKey
					Integer32,
				sleLagLacpPortPartnerOperNum
					InterfaceIndex,
				sleLagLacpPortPartnerOperPriority
					Integer32,
				sleLagLacpPortPartnerOperState
					BITS,
				sleLagLacpPortActorAdminAggregatorId
					Integer32
			 }

		sleLagLacpPortIndex OBJECT-TYPE
			SYNTAX InterfaceIndex
			MAX-ACCESS read-only
			STATUS current
			DESCRIPTION
				"The IP address of the RADIUS server referred 
				to in this table entry."
			::= { sleLagLacpPortEntry 1 }

		
		sleLagLacpPortActivity OBJECT-TYPE
			SYNTAX INTEGER
				{
				disable(0),
				enable(1)
				}
			MAX-ACCESS read-only
			STATUS current
			DESCRIPTION
				"show lacp activity of port"
			::= { sleLagLacpPortEntry 2 }

		
		sleLagLacpPortActorPriority OBJECT-TYPE
			SYNTAX INTEGER (1..65535)
			MAX-ACCESS read-only
			STATUS current
			DESCRIPTION
				"The priority assigned to the port by Actor."
			::= { sleLagLacpPortEntry 3 }

		
		sleLagLacpPortActorAggregatorId OBJECT-TYPE
			SYNTAX Integer32
			MAX-ACCESS read-only
			STATUS current
			DESCRIPTION
				" The aggregator index."
			::= { sleLagLacpPortEntry 4 }

		
		sleLagLacpPortActorAdminKey OBJECT-TYPE
			SYNTAX INTEGER (1..65535)
			MAX-ACCESS read-only
			STATUS current
			DESCRIPTION
				"The administrable Key value assigned to the 
				port by the Actor."
			::= { sleLagLacpPortEntry 5 }

		
		sleLagLacpPortActorAdminState OBJECT-TYPE
			SYNTAX BITS
				{
				expired(0),
				defaulted(1),
				destributing(2),
				collecting(3),
				synchronization(4),
				aggregation(5),
				lacpTimeout(6),
				lacpActivity(7)
				}
			MAX-ACCESS read-only
			STATUS current
			DESCRIPTION
				"The Actor's administrable state variables for the port."
			::= { sleLagLacpPortEntry 6 }

		
		sleLagLacpPortActorOperKey OBJECT-TYPE
			SYNTAX Integer32 (1..65535)
			MAX-ACCESS read-only
			STATUS current
			DESCRIPTION
				"The operational Key value assigned to the 
				port by the Actor."
			::= { sleLagLacpPortEntry 7 }

		
		sleLagLacpPortActorOperState OBJECT-TYPE
			SYNTAX BITS
				{
				expired(0),
				defaulted(1),
				destributing(2),
				collecting(3),
				synchronization(4),
				aggregation(5),
				lacpTmeout(6),
				lacpActivity(7)
				}
			MAX-ACCESS read-only
			STATUS current
			DESCRIPTION
				"The Actor's operational state variables for the port."
			::= { sleLagLacpPortEntry 8 }

		
		sleLagLacpPortPartnerAdminSystemMAC OBJECT-TYPE
			SYNTAX OCTET STRING
			MAX-ACCESS read-only
			STATUS current
			DESCRIPTION
				"The Partner's Administrable System ID, 
				encoded as a MAC address."
			::= { sleLagLacpPortEntry 9 }

		
		sleLagLacpPortPartnerAdminSystemPriority OBJECT-TYPE
			SYNTAX Integer32 (1..65535)
			MAX-ACCESS read-only
			STATUS current
			DESCRIPTION
				"The administrable priority assigned to the 
				Partner System."
			::= { sleLagLacpPortEntry 10 }

		
		sleLagLacpPortPartnerAdminKey OBJECT-TYPE
			SYNTAX Integer32 (1..65535)
			MAX-ACCESS read-only
			STATUS current
			DESCRIPTION
				"The administrable Key value assigned to 
				the port by the Partner."
			::= { sleLagLacpPortEntry 11 }

		
		sleLagLacpPortPartnerAdminNum OBJECT-TYPE
			SYNTAX InterfaceIndex
			MAX-ACCESS read-only
			STATUS current
			DESCRIPTION
				"The administrable number value assigned 
				to the port by the Partner."
			::= { sleLagLacpPortEntry 12 }

		
		sleLagLacpPortPartnerAdminPriority OBJECT-TYPE
			SYNTAX Integer32 (1..65535)
			MAX-ACCESS read-only
			STATUS current
			DESCRIPTION
				"The administrable priority assigned to 
				this port by the Partner."
			::= { sleLagLacpPortEntry 13 }

		
		sleLagLacpPortPartnerAdminState OBJECT-TYPE
			SYNTAX BITS
				{
				expired(0),
				defaulted(1),
				destributing(2),
				collecting(3),
				synchronization(4),
				aggregation(5),
				lacpTmeout(6),
				lacpActivity(7)
				}
			MAX-ACCESS read-only
			STATUS current
			DESCRIPTION
				"The administrable state assigned to this 
				port by the Partner."
			::= { sleLagLacpPortEntry 14 }

		
		sleLagLacpPortPartnerOperSystemMAC OBJECT-TYPE
			SYNTAX OCTET STRING
			MAX-ACCESS read-only
			STATUS current
			DESCRIPTION
				"The Partner's operational System ID, 
				encoded as a MAC address."
			::= { sleLagLacpPortEntry 15 }

		
		sleLagLacpPortPartnerOperSystemPriority OBJECT-TYPE
			SYNTAX Integer32 (1..65535)
			MAX-ACCESS read-only
			STATUS current
			DESCRIPTION
				"The operational priority assigned to 
				the Partner System."
			::= { sleLagLacpPortEntry 16 }

		
		sleLagLacpPortPartnerOperKey OBJECT-TYPE
			SYNTAX Integer32 (1..65535)
			MAX-ACCESS read-only
			STATUS current
			DESCRIPTION
				"The operational Key value assigned to the 
				port by the Partner."
			::= { sleLagLacpPortEntry 17 }

		
		sleLagLacpPortPartnerOperNum OBJECT-TYPE
			SYNTAX InterfaceIndex
			MAX-ACCESS read-only
			STATUS current
			DESCRIPTION
				"The operational number value assigned to 
				the port by the Partner."
			::= { sleLagLacpPortEntry 18 }

		
		sleLagLacpPortPartnerOperPriority OBJECT-TYPE
			SYNTAX Integer32 (1..65535)
			MAX-ACCESS read-only
			STATUS current
			DESCRIPTION
				"The operational priority assigned to 
				this port by the Partner."
			::= { sleLagLacpPortEntry 19 }

		
		sleLagLacpPortPartnerOperState OBJECT-TYPE
			SYNTAX BITS
				{
				expired(0),
				defaulted(1),
				destributing(2),
				collecting(3),
				synchronization(4),
				aggregation(5),
				lacpTimeout(6),
				lacpActivity(7)
				}
			MAX-ACCESS read-only
			STATUS current
			DESCRIPTION
				"The operational state assigned to this 
				port by the Partner."
			::= { sleLagLacpPortEntry 20 }

		
		sleLagLacpPortActorAdminAggregatorId OBJECT-TYPE
			SYNTAX Integer32
			MAX-ACCESS read-only
			STATUS current
			DESCRIPTION
				"Admin aggregator Id."
			::= { sleLagLacpPortEntry 21 }

		
		sleLagLacpPortControl OBJECT IDENTIFIER ::= { sleLagLacpPort 2 }

		
		sleLagLacpPortControlRequest OBJECT-TYPE
			SYNTAX INTEGER
				{
				setLagLacpPortProfile(1),
				setLagLacpPortProfileWithAggr(2)
				}
			MAX-ACCESS read-write
			STATUS current
			DESCRIPTION
				"The MIB object for the user command."
			::= { sleLagLacpPortControl 1 }

		
		sleLagLacpPortControlStatus OBJECT-TYPE
			SYNTAX SleControlStatusType
			MAX-ACCESS read-only
			STATUS current
			DESCRIPTION
				"Describes the status of a user command group, 
				used for block commands while a command execution in process."
			::= { sleLagLacpPortControl 2 }

		
		sleLagLacpPortControlTimer OBJECT-TYPE
			SYNTAX Gauge32
			MAX-ACCESS read-write
			STATUS current
			DESCRIPTION
				"Maximum command duration time in case of long running"
			::= { sleLagLacpPortControl 3 }

		
		sleLagLacpPortControlTimeStamp OBJECT-TYPE
			SYNTAX TimeStamp
			MAX-ACCESS read-only
			STATUS current
			DESCRIPTION
				"Time stamp attribute set at end of command."
			::= { sleLagLacpPortControl 4 }

		
		sleLagLacpPortControlReqResult OBJECT-TYPE
			SYNTAX SleControlRequestResultType
			MAX-ACCESS read-only
			STATUS current
			DESCRIPTION
				"Command result attribute."
			::= { sleLagLacpPortControl 5 }

		
		sleLagLacpPortControlIndex OBJECT-TYPE
			SYNTAX InterfaceIndex
			MAX-ACCESS read-write
			STATUS current
			DESCRIPTION
				"The IP address of the RADIUS server referred to 
				in this table entry."
			::= { sleLagLacpPortControl 6 }

		
		sleLagLacpPortControlActivity OBJECT-TYPE
			SYNTAX INTEGER
				{
				disable(0),
				enable(1)
				}
			MAX-ACCESS read-write
			STATUS current
			DESCRIPTION
				"show lacp activity of port"
			::= { sleLagLacpPortControl 7 }

		
		sleLagLacpPortControlMode OBJECT-TYPE
			SYNTAX INTEGER
				{
				active(1),
				passive(2)
				}
			MAX-ACCESS read-write
			STATUS current
			DESCRIPTION
				"set LACP_Activity in sleLagLacpPortActorAdminState"
			::= { sleLagLacpPortControl 8 }

		
		sleLagLacpPortControlAdminKey OBJECT-TYPE
			SYNTAX Integer32 (0..15)
			MAX-ACCESS read-write
			STATUS current
			DESCRIPTION
				"The administrable Key value assigned to the 
				port by the Actor."
			::= { sleLagLacpPortControl 9 }

		
		sleLagLacpPortControlAggregation OBJECT-TYPE
			SYNTAX INTEGER
				{
				aggregatable(1),
				individual(2)
				}
			MAX-ACCESS read-write
			STATUS current
			DESCRIPTION
				"set Aggregation in sleLagLacpPortActorAdminState."
			::= { sleLagLacpPortControl 10 }

		
		sleLagLacpPortControlPriority OBJECT-TYPE
			SYNTAX Integer32 (1..65535)
			MAX-ACCESS read-write
			STATUS current
			DESCRIPTION
				"The priority assigned to the port by Actor."
			::= { sleLagLacpPortControl 11 }

		
		sleLagLacpPortControlTimeout OBJECT-TYPE
			SYNTAX INTEGER
				{
				short(1),
				long(2)
				}
			MAX-ACCESS read-write
			STATUS current
			DESCRIPTION
				"set LACP_Timeout in sleLagLacpPortActorAdminState."
			::= { sleLagLacpPortControl 12 }

		
		sleLagLacpPortControlAdminAggregatorId OBJECT-TYPE
			SYNTAX Integer32
			MAX-ACCESS read-write
			STATUS current
			DESCRIPTION
				"Admin aggregator Id."
			::= { sleLagLacpPortControl 13 }

		
		sleLagLacpPortNotification OBJECT IDENTIFIER ::= { sleLagLacpPort 3 }

		
		sleLagLacpPortProfileChanged NOTIFICATION-TYPE
			OBJECTS { sleLagLacpPortControlRequest, sleLagLacpPortControlReqResult, sleLagLacpPortControlTimeStamp, sleLagLacpPortActorAdminKey, sleLagLacpPortActorPriority, 
				sleLagLacpPortActorAdminState }
			STATUS current
			DESCRIPTION 
				" "
			::= { sleLagLacpPortNotification 1 }

		
		sleLagLacpPortAggrChanged NOTIFICATION-TYPE
			OBJECTS { sleLagLacpPortControlRequest, sleLagLacpPortControlReqResult, sleLagLacpPortControlTimeStamp, sleLagLacpPortActorAdminAggregatorId }
			STATUS current
			DESCRIPTION 
				" "
			::= { sleLagLacpPortNotification 2 }

		
		sleFdb OBJECT IDENTIFIER ::= { sleBridge 13 }

		
		sleFdbTable OBJECT-TYPE
			SYNTAX SEQUENCE OF SleFdbEntry
			MAX-ACCESS not-accessible
			STATUS current
			DESCRIPTION
				"The table of FDB entries."
			::= { sleFdb 1 }

		
		sleFdbEntry OBJECT-TYPE
			SYNTAX SleFdbEntry
			MAX-ACCESS not-accessible
			STATUS current
			DESCRIPTION
				"The table entry of FDB table.
				key: sleFdbEntryFid, sleFdbEntryPort, sleFdbEntryMacAddress"
			INDEX { sleFdbEntryFid, sleFdbEntryPort, sleFdbEntryMacAddress }
			::= { sleFdbTable 1 }

		
		SleFdbEntry ::=
			SEQUENCE { 
				sleFdbEntryFid
					INTEGER,
				sleFdbEntryPort
					INTEGER,
				sleFdbEntryMacAddress
					OCTET STRING,
				sleFdbEntryVid
					INTEGER,
				sleFdbEntryMode
					INTEGER,
				sleFdbEntryPermission
					INTEGER,
				sleFdbEntryElapsedTime
					Unsigned32
			 }

		sleFdbEntryFid OBJECT-TYPE
			SYNTAX INTEGER (1..4094)
			MAX-ACCESS read-only
			STATUS current
			DESCRIPTION
				"FDB identify."
			::= { sleFdbEntry 1 }

		
		sleFdbEntryPort OBJECT-TYPE
			SYNTAX INTEGER (1..255)
			MAX-ACCESS read-only
			STATUS current
			DESCRIPTION
				"The port number of the port on which 
				a frame having a source address equal 
				to the value of the corresponding instance 
				of dasanFdbAddress has been seen."
			::= { sleFdbEntry 2 }

		
		sleFdbEntryMacAddress OBJECT-TYPE
			SYNTAX OCTET STRING (SIZE (0..6))
			MAX-ACCESS read-only
			STATUS current
			DESCRIPTION
				"A unicast MAC address for which the device has
				forwarding or filtering information."
			::= { sleFdbEntry 3 }

		
		sleFdbEntryVid OBJECT-TYPE
			SYNTAX INTEGER (1..4094)
			MAX-ACCESS read-only
			STATUS current
			DESCRIPTION
				"VLAN ID."
			::= { sleFdbEntry 4 }

		
		sleFdbEntryMode OBJECT-TYPE
			SYNTAX INTEGER
				{
				local(0),
				static(1),
				dynamic(2)
				}
			MAX-ACCESS read-only
			STATUS current
			DESCRIPTION
				"FDB Entry's mode.
				The status of this entry.  The meanings of the values
				are:
				    local(0)   - the value of the corresponding instance 
				                 of sleFdbMacAddress was own.
				    static(1)  - the value of the corresponding instance 
				                 of sleFdbMacAddress was specified by management. 
				    dynamic(2) - the value of the corresponding instance
				                 of sleFdbMacAddress was learned."
			::= { sleFdbEntry 5 }

		
		sleFdbEntryPermission OBJECT-TYPE
			SYNTAX INTEGER
				{
				deny(0),
				permit(1)
				}
			MAX-ACCESS read-only
			STATUS current
			DESCRIPTION
				"The permission of dasanFdbAddress.
				The meanings of the values are:
				    deny(0)   - the value of the corresponding instance
				                of dasanFdbAddress will be dropped.
				    permit(1) - the value of the corresponding instance
				                of dasanFdbAddress will be flooded.
				"
			::= { sleFdbEntry 6 }

		
		sleFdbEntryElapsedTime OBJECT-TYPE
			SYNTAX Unsigned32
			MAX-ACCESS read-only
			STATUS current
			DESCRIPTION
				"Elapsed time after registered"
			::= { sleFdbEntry 7 }

		
		sleFdbControl OBJECT IDENTIFIER ::= { sleFdb 2 }

		
		sleFdbEntryControlRequest OBJECT-TYPE
			SYNTAX INTEGER
				{
				createFdbEntry(1),
				destoryFdbEntry(2),
				clearFdbTableEntries(3)
				}
			MAX-ACCESS read-write
			STATUS current
			DESCRIPTION
				"Control Request."
			::= { sleFdbControl 1 }

		
		sleFdbEntryControlStatus OBJECT-TYPE
			SYNTAX SleControlStatusType
			MAX-ACCESS read-only
			STATUS current
			DESCRIPTION
				"Control Status."
			::= { sleFdbControl 2 }

		
		sleFdbEntryControlTimer OBJECT-TYPE
			SYNTAX Gauge32
			MAX-ACCESS read-write
			STATUS current
			DESCRIPTION
				"Cotrol Timer."
			::= { sleFdbControl 3 }

		
		sleFdbEntryControlTImeStamp OBJECT-TYPE
			SYNTAX TimeTicks
			MAX-ACCESS read-only
			STATUS current
			DESCRIPTION
				" The time stamp of the last command(end of command)"
			::= { sleFdbControl 4 }

		
		sleFdbEntryControlReqResult OBJECT-TYPE
			SYNTAX SleControlRequestResultType
			MAX-ACCESS read-only
			STATUS current
			DESCRIPTION
				" The result of the last user command"
			::= { sleFdbControl 5 }

		
		sleFdbEntryControlFid OBJECT-TYPE
			SYNTAX Integer32 (1..4094)
			MAX-ACCESS read-write
			STATUS current
			DESCRIPTION
				"FDB identifier."
			::= { sleFdbControl 6 }

		
		sleFdbEntryControlPort OBJECT-TYPE
			SYNTAX INTEGER (0..255)
			MAX-ACCESS read-write
			STATUS current
			DESCRIPTION
				"The port number of FDB entry.
				0 : any (all) port."
			::= { sleFdbControl 7 }

		
		sleFdbEntryControlMacAddress OBJECT-TYPE
			SYNTAX OCTET STRING (SIZE (0..6))
			MAX-ACCESS read-write
			STATUS current
			DESCRIPTION
				"MAC address of FDB entry."
			::= { sleFdbControl 8 }

		
		sleFdbNotification OBJECT IDENTIFIER ::= { sleFdb 3 }

		
		sleFdbEntryCreated NOTIFICATION-TYPE
			OBJECTS { sleFdbEntryControlRequest, sleFdbEntryControlTImeStamp, sleFdbEntryControlReqResult, sleFdbEntryPermission }
			STATUS current
			DESCRIPTION 
				"Created FDB Entry."
			::= { sleFdbNotification 1 }

		
		sleFdbEntryDestoryed NOTIFICATION-TYPE
			OBJECTS { sleFdbEntryControlRequest, sleFdbEntryControlTImeStamp, sleFdbEntryControlMacAddress, sleFdbEntryControlReqResult }
			STATUS current
			DESCRIPTION 
				"Destroyed FDB Entry."
			::= { sleFdbNotification 2 }

		
		sleFdbTableEntriesCleared NOTIFICATION-TYPE
			OBJECTS { sleFdbEntryControlRequest, sleFdbEntryControlTImeStamp, sleFdbEntryControlMacAddress, sleFdbEntryControlReqResult }
			STATUS current
			DESCRIPTION 
				"clearFdbTableEntries.
				In this notification PDU, key of sleFdbEntryPort 
				is fid.port.6.0.0.0.0.0.0.
				If port is 0, is cleared on all ports in fid."
			::= { sleFdbNotification 3 }

		
		sleMfdbOld OBJECT IDENTIFIER ::= { sleBridge 14 }

		
		sleMfdbOldTable OBJECT-TYPE
			SYNTAX SEQUENCE OF SleMfdbOldEntry
			MAX-ACCESS not-accessible
			STATUS current
			DESCRIPTION
				"The table of MFDB entries."
			::= { sleMfdbOld 1 }

		
		sleMfdbOldEntry OBJECT-TYPE
			SYNTAX SleMfdbOldEntry
			MAX-ACCESS not-accessible
			STATUS current
			DESCRIPTION
				"Information about a specific MAC address that
				should be forwarding or dropping.
				key: sleMfdbMacAddress"
			INDEX { sleMfdbMacAddress }
			::= { sleMfdbOldTable 1 }

		
		SleMfdbOldEntry ::=
			SEQUENCE { 
				sleMfdbOldMacAddress
					OCTET STRING,
				sleMfdbOldEntryPermission
					INTEGER,
				sleMfdbOldVlanIndex
					INTEGER,
				sleMfdbOldPorts
					OCTET STRING
			 }

		sleMfdbOldMacAddress OBJECT-TYPE
			SYNTAX OCTET STRING (SIZE (0..6))
			MAX-ACCESS read-only
			STATUS current
			DESCRIPTION
				"A unicast MAC address for which the device has
				forwarding or filtering information."
			::= { sleMfdbOldEntry 1 }

		
		sleMfdbOldEntryPermission OBJECT-TYPE
			SYNTAX INTEGER
				{
				deny(0),
				permit(1)
				}
			MAX-ACCESS read-only
			STATUS current
			DESCRIPTION
				"The permission of sleMFdbMacAddress.
				The meanings of the values are: 
				    deny(0)   - the value of the corresponding instance
				                of sleMfdbMacAddress will be dropped.
				    permit(1) - the value of the corresponding instance
				                of sleMfdbMacAddress will be flooded.
				"
			::= { sleMfdbOldEntry 2 }

		
		sleMfdbOldVlanIndex OBJECT-TYPE
			SYNTAX INTEGER (0 | 1..4094)
			MAX-ACCESS read-only
			STATUS current
			DESCRIPTION
				"vlan index
				"
			::= { sleMfdbOldEntry 3 }

		
		sleMfdbOldPorts OBJECT-TYPE
			SYNTAX OCTET STRING (SIZE (0..32))
			MAX-ACCESS read-write
			STATUS current
			DESCRIPTION
				"Port Map"
			::= { sleMfdbOldEntry 4 }

		
		sleMfdbOldControl OBJECT IDENTIFIER ::= { sleMfdbOld 2 }

		
		sleMfdbOldControlRequest OBJECT-TYPE
			SYNTAX INTEGER
				{
				createMfdbEntry(1),
				destoryMfdbEntry(2),
				setMfdbEntryPermission(3),
				clearMfdbEntryTable(4)
				}
			MAX-ACCESS read-write
			STATUS current
			DESCRIPTION
				" The request of a user command"
			::= { sleMfdbOldControl 1 }

		
		sleMfdbOldControlStatus OBJECT-TYPE
			SYNTAX SleControlStatusType
			MAX-ACCESS read-only
			STATUS current
			DESCRIPTION
				" The status of user command"
			::= { sleMfdbOldControl 2 }

		
		sleMfdbOldControlTimer OBJECT-TYPE
			SYNTAX Gauge32
			MAX-ACCESS read-write
			STATUS current
			DESCRIPTION
				" The maximum time for the manager for a long running user command"
			::= { sleMfdbOldControl 3 }

		
		sleMfdbOldControlTimeStamp OBJECT-TYPE
			SYNTAX TimeTicks
			MAX-ACCESS read-only
			STATUS current
			DESCRIPTION
				" The time stamp of the last command(end of command)"
			::= { sleMfdbOldControl 4 }

		
		sleMfdbOldControlReqResult OBJECT-TYPE
			SYNTAX SleControlRequestResultType
			MAX-ACCESS read-only
			STATUS current
			DESCRIPTION
				" The result of the last user command"
			::= { sleMfdbOldControl 5 }

		
		sleMfdbOldControlMacAddress OBJECT-TYPE
			SYNTAX OCTET STRING (SIZE (0..6))
			MAX-ACCESS read-write
			STATUS current
			DESCRIPTION
				"A unicast MAC address for which the device has
				forwarding or filtering information.
				  If MAC address is NULL apply mac-filter list 
				  from file '/etc/mfdb.conf'."
			::= { sleMfdbOldControl 6 }

		
		sleMfdbOldControlEntryPermission OBJECT-TYPE
			SYNTAX INTEGER
				{
				deny(0),
				permit(1)
				}
			MAX-ACCESS read-write
			STATUS current
			DESCRIPTION
				"The permission of sleMFdbControlMacAddress."
			::= { sleMfdbOldControl 7 }

		
		sleMfdbOldControlVlanIndex OBJECT-TYPE
			SYNTAX INTEGER (0 | 1..4094)
			MAX-ACCESS read-write
			STATUS current
			DESCRIPTION
				"vlan index
				The value of 0 is all vlan"
			::= { sleMfdbOldControl 8 }

		
		sleMfdbOldControlPorts OBJECT-TYPE
			SYNTAX OCTET STRING (SIZE (0..32))
			MAX-ACCESS read-write
			STATUS current
			DESCRIPTION
				"Port Map 
				The value of 0x00 is all port
				"
			::= { sleMfdbOldControl 9 }

		
		sleMfdbOldNotification OBJECT IDENTIFIER ::= { sleMfdbOld 3 }

		
		sleMfdbOldEntryCreated NOTIFICATION-TYPE
			OBJECTS { sleMfdbOldControlRequest, sleMfdbOldControlTimeStamp, sleMfdbOldControlReqResult, sleMfdbOldControlEntryPermission }
			STATUS current
			DESCRIPTION 
				"Create new MFDB entry."
			::= { sleMfdbOldNotification 1 }

		
		sleMfdbOldEntryDestoryed NOTIFICATION-TYPE
			OBJECTS { sleMfdbOldControlRequest, sleMfdbOldControlTimeStamp, sleMfdbOldControlReqResult, sleMfdbOldControlMacAddress }
			STATUS current
			DESCRIPTION 
				"Destroyed MFDB entry."
			::= { sleMfdbOldNotification 2 }

		
		sleMfdbOldEntryPermissionChanged NOTIFICATION-TYPE
			OBJECTS { sleMfdbOldControlRequest, sleMfdbOldControlTimeStamp, sleMfdbOldControlReqResult, sleMfdbOldEntryPermission }
			STATUS current
			DESCRIPTION 
				"Changed permission of MFDB entry."
			::= { sleMfdbOldNotification 3 }

		
		sleMfdbOldEntryTableCleared NOTIFICATION-TYPE
			OBJECTS { sleMfdbOldControlRequest, sleMfdbOldControlTimeStamp, sleMfdbOldControlReqResult }
			STATUS current
			DESCRIPTION 
				"Description."
			::= { sleMfdbOldNotification 4 }

		
		sleIgmpConf OBJECT IDENTIFIER ::= { sleBridge 15 }

		
		sleIgmpConfTable OBJECT-TYPE
			SYNTAX SEQUENCE OF SleIgmpConfEntry
			MAX-ACCESS not-accessible
			STATUS current
			DESCRIPTION
				"IGMP configuration table."
			::= { sleIgmpConf 1 }

		
		sleIgmpConfEntry OBJECT-TYPE
			SYNTAX SleIgmpConfEntry
			MAX-ACCESS not-accessible
			STATUS current
			DESCRIPTION
				"key: sleVlanIndex"
			INDEX { sleVlanIndex }
			::= { sleIgmpConfTable 1 }

		
		SleIgmpConfEntry ::=
			SEQUENCE { 
				sleIgmpConfVlanIndex
					Integer32,
				sleIgmpConfEnable
					INTEGER,
				sleIgmpConfMulticastFilter
					INTEGER,
				sleIgmpConfOutmostVlan
					INTEGER,
				sleIgmpConfSnoopEnable
					INTEGER,
				sleIgmpConfSnoopJoinDelay
					Integer32,
				sleIgmpConfSnoopQueryDelay
					Integer32,
				sleIgmpConfSnoopMrouter
					Integer32,
				sleIgmpConfSnoopFastLeave
					INTEGER,
				sleIgmpConfSnoopQuerier
					INTEGER
			 }

		sleIgmpConfVlanIndex OBJECT-TYPE
			SYNTAX Integer32 (0..4094)
			MAX-ACCESS read-only
			STATUS current
			DESCRIPTION
				"sleVlanIndex in sleVlanTable"
			::= { sleIgmpConfEntry 1 }

		
		sleIgmpConfEnable OBJECT-TYPE
			SYNTAX INTEGER
				{
				disable(0),
				enable(1)
				}
			MAX-ACCESS read-only
			STATUS current
			DESCRIPTION
				"If this flag is true, IGMP multicasting is enabled. (not supported)"
			::= { sleIgmpConfEntry 2 }

		
		sleIgmpConfMulticastFilter OBJECT-TYPE
			SYNTAX INTEGER
				{
				disable(0),
				enable(1)
				}
			MAX-ACCESS read-only
			STATUS current
			DESCRIPTION
				"If this flag is true, mac address that is unregistered into IGMP table is filtered. (not supported)"
			::= { sleIgmpConfEntry 3 }

		
		sleIgmpConfOutmostVlan OBJECT-TYPE
			SYNTAX INTEGER
				{
				disable(0),
				enable(1)
				}
			MAX-ACCESS read-only
			STATUS current
			DESCRIPTION
				"Configures outmost VLAN. (not supported)"
			::= { sleIgmpConfEntry 4 }

		
		sleIgmpConfSnoopEnable OBJECT-TYPE
			SYNTAX INTEGER
				{
				disable(0),
				enable(1)
				}
			MAX-ACCESS read-only
			STATUS current
			DESCRIPTION
				"The IGMP snooping enable/disable flag"
			::= { sleIgmpConfEntry 5 }

		
		sleIgmpConfSnoopJoinDelay OBJECT-TYPE
			SYNTAX Integer32 (0..1000)
			MAX-ACCESS read-only
			STATUS current
			DESCRIPTION
				"After join message is received, the time interval until be registered into multicast group. (not supported)"
			::= { sleIgmpConfEntry 6 }

		
		sleIgmpConfSnoopQueryDelay OBJECT-TYPE
			SYNTAX Integer32 (100..900)
			MAX-ACCESS read-only
			STATUS current
			DESCRIPTION
				"After query message is send, the time interval for response waiting."
			::= { sleIgmpConfEntry 7 }

		
		sleIgmpConfSnoopMrouter OBJECT-TYPE
			SYNTAX Integer32
			MAX-ACCESS read-only
			STATUS current
			DESCRIPTION
				"The index of interface connected with multicast router."
			::= { sleIgmpConfEntry 8 }

		
		sleIgmpConfSnoopFastLeave OBJECT-TYPE
			SYNTAX INTEGER
				{
				disable(0),
				enable(1)
				}
			MAX-ACCESS read-only
			STATUS current
			DESCRIPTION
				"If this flag is true, immediately this entry is deleted, when leave message is received,"
			::= { sleIgmpConfEntry 9 }

		
		sleIgmpConfSnoopQuerier OBJECT-TYPE
			SYNTAX INTEGER
				{
				disable(0),
				enable(1)
				}
			MAX-ACCESS read-only
			STATUS current
			DESCRIPTION
				"If this flag is true, perform IGMP snooping querier."
			::= { sleIgmpConfEntry 10 }

		
		sleIgmpConfControl OBJECT IDENTIFIER ::= { sleIgmpConf 2 }

		
		sleIgmpConfControlRequest OBJECT-TYPE
			SYNTAX SleIgmpConfControlRequestType
			MAX-ACCESS read-write
			STATUS current
			DESCRIPTION
				"The request of a user command"
			::= { sleIgmpConfControl 1 }

		
		sleIgmpConfControlStatus OBJECT-TYPE
			SYNTAX SleControlStatusType
			MAX-ACCESS read-only
			STATUS current
			DESCRIPTION
				"The status of user command"
			::= { sleIgmpConfControl 2 }

		
		sleIgmpConfControlTimer OBJECT-TYPE
			SYNTAX Gauge32
			MAX-ACCESS read-write
			STATUS current
			DESCRIPTION
				"The maximum time for the manager for a long running user command"
			::= { sleIgmpConfControl 3 }

		
		sleIgmpConfControlTimeStamp OBJECT-TYPE
			SYNTAX TimeTicks
			MAX-ACCESS read-only
			STATUS current
			DESCRIPTION
				"The time stamp of the last command(end of command)"
			::= { sleIgmpConfControl 4 }

		
		sleIgmpConfControlReqResult OBJECT-TYPE
			SYNTAX SleControlRequestResultType
			MAX-ACCESS read-only
			STATUS current
			DESCRIPTION
				"The result of the last user command"
			::= { sleIgmpConfControl 5 }

		
		sleIgmpConfControlVlanIndex OBJECT-TYPE
			SYNTAX Integer32 (1..4094)
			MAX-ACCESS read-write
			STATUS current
			DESCRIPTION
				"sleVlanIndex in sleVlanTable"
			::= { sleIgmpConfControl 6 }

		
		sleIgmpConfControlEnable OBJECT-TYPE
			SYNTAX INTEGER
				{
				disable(0),
				enable(1)
				}
			MAX-ACCESS read-write
			STATUS current
			DESCRIPTION
				"If this flag is true, IGMP multicasting is enabled."
			::= { sleIgmpConfControl 7 }

		
		sleIgmpConfControlMulticastFilter OBJECT-TYPE
			SYNTAX INTEGER
				{
				disable(0),
				enable(1)
				}
			MAX-ACCESS read-write
			STATUS current
			DESCRIPTION
				"If this flag is true, mac address that is unregistered into IGMP table is filtered."
			::= { sleIgmpConfControl 8 }

		
		sleIgmpConfControlOutmostVlan OBJECT-TYPE
			SYNTAX INTEGER
				{
				disable(0),
				enable(1)
				}
			MAX-ACCESS read-write
			STATUS current
			DESCRIPTION
				"Configures outmost VLAN. (not supported)"
			::= { sleIgmpConfControl 9 }

		
		sleIgmpConfControlSnoopEnable OBJECT-TYPE
			SYNTAX INTEGER
				{
				disable(0),
				enable(1)
				}
			MAX-ACCESS read-write
			STATUS current
			DESCRIPTION
				"The IGMP snooping enable/disable flag"
			::= { sleIgmpConfControl 10 }

		
		sleIgmpConfControlSnoopJoinDelay OBJECT-TYPE
			SYNTAX Integer32 (0..1000)
			MAX-ACCESS read-write
			STATUS current
			DESCRIPTION
				"After join message is received, the time interval until be registered into multicast group. (not supported)"
			::= { sleIgmpConfControl 11 }

		
		sleIgmpConfControlSnoopQueryDelay OBJECT-TYPE
			SYNTAX Integer32 (100..900)
			MAX-ACCESS read-write
			STATUS current
			DESCRIPTION
				"After query message is send, the time interval for response waiting."
			::= { sleIgmpConfControl 12 }

		
		sleIgmpConfControlSnoopMrouter OBJECT-TYPE
			SYNTAX Integer32 (1..255)
			MAX-ACCESS read-write
			STATUS current
			DESCRIPTION
				"The index of interface connected with multicast router."
			DEFVAL { -1 }
			::= { sleIgmpConfControl 13 }

		
		sleIgmpConfControlSnoopFastLeave OBJECT-TYPE
			SYNTAX INTEGER
				{
				disable(0),
				enable(1)
				}
			MAX-ACCESS read-write
			STATUS current
			DESCRIPTION
				"If this flag is true, immediately this entry is deleted, when leave message is received,"
			::= { sleIgmpConfControl 14 }

		
		sleIgmpConfControlSnoopQuerier OBJECT-TYPE
			SYNTAX INTEGER
				{
				disable(0),
				enable(1)
				}
			MAX-ACCESS read-write
			STATUS current
			DESCRIPTION
				"If this flag is true, perform IGMP snooping querier."
			::= { sleIgmpConfControl 15 }

		
		sleIgmpConfNotification OBJECT IDENTIFIER ::= { sleIgmpConf 3 }

		
		sleIgmpConfProfileChanged NOTIFICATION-TYPE
			OBJECTS { sleIgmpConfControlRequest, sleIgmpConfControlReqResult, sleIgmpConfControlTimeStamp, sleIgmpConfSnoopMrouter, sleIgmpConfEnable, 
				sleIgmpConfMulticastFilter, sleIgmpConfOutmostVlan, sleIgmpConfSnoopEnable, sleIgmpConfSnoopJoinDelay, sleIgmpConfSnoopQueryDelay, 
				sleIgmpConfSnoopFastLeave, sleIgmpConfSnoopQuerier }
			STATUS current
			DESCRIPTION 
				"Description."
			::= { sleIgmpConfNotification 1 }

		
		sleIgmpMcast OBJECT IDENTIFIER ::= { sleBridge 16 }

		
		sleIgmpMcastTable OBJECT-TYPE
			SYNTAX SEQUENCE OF SleIgmpMcastEntry
			MAX-ACCESS not-accessible
			STATUS current
			DESCRIPTION
				" IGMP multicast table."
			::= { sleIgmpMcast 1 }

		
		sleIgmpMcastEntry OBJECT-TYPE
			SYNTAX SleIgmpMcastEntry
			MAX-ACCESS not-accessible
			STATUS current
			DESCRIPTION
				" key: sleVlanIndex, sleIgmpMcastIPAddress, sleIgmpMcastPortIndex"
			INDEX { sleVlanIndex, sleIgmpMcastIPAddress, sleIgmpMcastPortIndex }
			::= { sleIgmpMcastTable 1 }

		
		SleIgmpMcastEntry ::=
			SEQUENCE { 
				sleIgmpMcastVlanIndex
					Integer32,
				sleIgmpMcastIPAddress
					IpAddress,
				sleIgmpMcastPortIndex
					Integer32,
				sleIgmpMcastType
					INTEGER,
				sleIgmpMcastExpireTime
					Integer32
			 }

		sleIgmpMcastVlanIndex OBJECT-TYPE
			SYNTAX Integer32 (1..4094)
			MAX-ACCESS read-only
			STATUS current
			DESCRIPTION
				"sleVlanIndex in sleVlanTable"
			::= { sleIgmpMcastEntry 1 }

		
		sleIgmpMcastIPAddress OBJECT-TYPE
			SYNTAX IpAddress
			MAX-ACCESS read-only
			STATUS current
			DESCRIPTION
				"The IP multicast group address for which this entry contains information."
			::= { sleIgmpMcastEntry 2 }

		
		sleIgmpMcastPortIndex OBJECT-TYPE
			SYNTAX Integer32 (1..255)
			MAX-ACCESS read-only
			STATUS current
			DESCRIPTION
				"Port index"
			::= { sleIgmpMcastEntry 3 }

		
		sleIgmpMcastType OBJECT-TYPE
			SYNTAX INTEGER
				{
				static(0),
				dynamic(1)
				}
			MAX-ACCESS read-only
			STATUS current
			DESCRIPTION
				"indicate either static- or dynamic- IP multicast group address"
			::= { sleIgmpMcastEntry 4 }

		
		sleIgmpMcastExpireTime OBJECT-TYPE
			SYNTAX Integer32
			MAX-ACCESS read-only
			STATUS current
			DESCRIPTION
				"Expiry time of this dynamic multicast table entry."
			::= { sleIgmpMcastEntry 5 }

		
		sleIgmpMcastControl OBJECT IDENTIFIER ::= { sleIgmpMcast 2 }

		
		sleIgmpMcastControlReqest OBJECT-TYPE
			SYNTAX SleIgmpMcastControlRequestType
			MAX-ACCESS read-write
			STATUS current
			DESCRIPTION
				" The request of a user command"
			::= { sleIgmpMcastControl 1 }

		
		sleIgmpMcastControlStatus OBJECT-TYPE
			SYNTAX SleControlStatusType
			MAX-ACCESS read-only
			STATUS current
			DESCRIPTION
				"The status of user command"
			::= { sleIgmpMcastControl 2 }

		
		sleIgmpMcastControlTimer OBJECT-TYPE
			SYNTAX Gauge32
			MAX-ACCESS read-write
			STATUS current
			DESCRIPTION
				" The maximum time for the manager for a long running user command"
			::= { sleIgmpMcastControl 3 }

		
		sleIgmpMcastControlTimeStamp OBJECT-TYPE
			SYNTAX TimeTicks
			MAX-ACCESS read-only
			STATUS current
			DESCRIPTION
				" The time stamp of the last command(end of command)"
			::= { sleIgmpMcastControl 4 }

		
		sleIgmpMcastControlReqResult OBJECT-TYPE
			SYNTAX SleControlRequestResultType
			MAX-ACCESS read-only
			STATUS current
			DESCRIPTION
				" The result of the last user command"
			::= { sleIgmpMcastControl 5 }

		
		sleIgmpMcastControlVlanIndex OBJECT-TYPE
			SYNTAX Integer32 (1..4094)
			MAX-ACCESS read-write
			STATUS current
			DESCRIPTION
				" sleVlanIndex in sleVlanTable"
			::= { sleIgmpMcastControl 6 }

		
		sleIgmpMcastControlIPAddress OBJECT-TYPE
			SYNTAX IpAddress
			MAX-ACCESS read-write
			STATUS current
			DESCRIPTION
				" The multicast group address."
			::= { sleIgmpMcastControl 7 }

		
		sleIgmpMcastControlPortIndex OBJECT-TYPE
			SYNTAX Integer32 (1..255)
			MAX-ACCESS read-write
			STATUS current
			DESCRIPTION
				"Port index"
			::= { sleIgmpMcastControl 8 }

		
		sleIgmpMcastNotification OBJECT IDENTIFIER ::= { sleIgmpMcast 3 }

		
		sleIgmpStaticMcastCreated NOTIFICATION-TYPE
			OBJECTS { sleIgmpMcastControlReqest, sleIgmpMcastControlTimeStamp, sleIgmpMcastControlPortIndex, sleIgmpMcastControlReqResult }
			STATUS current
			DESCRIPTION 
				" "
			::= { sleIgmpMcastNotification 1 }

		
		sleIgmpStaticMcastDestroyed NOTIFICATION-TYPE
			OBJECTS { sleIgmpMcastControlReqest, sleIgmpMcastControlReqResult, sleIgmpMcastControlPortIndex, sleIgmpMcastControlTimeStamp }
			STATUS current
			DESCRIPTION 
				" "
			::= { sleIgmpMcastNotification 2 }

		
		sleIgmpMcastCounterInfo OBJECT IDENTIFIER ::= { sleIgmpMcast 4 }

		
		sleIgmpMcastCounterInfoGroupCount OBJECT-TYPE
			SYNTAX Counter32
			MAX-ACCESS read-only
			STATUS current
			DESCRIPTION
				"Count of IGMP Group entry."
			::= { sleIgmpMcastCounterInfo 1 }

		
		sleIgmpMcastCounterInfoSnoopingCount OBJECT-TYPE
			SYNTAX Counter32
			MAX-ACCESS read-only
			STATUS current
			DESCRIPTION
				"Count of IGMP Snooping Group entry."
			::= { sleIgmpMcastCounterInfo 2 }

		
		sleMcastMrouteCounterInfo OBJECT IDENTIFIER ::= { sleIgmpMcast 5 }

		
		sleMcastMrouteJoinedCount OBJECT-TYPE
			SYNTAX Counter32
			MAX-ACCESS read-only
			STATUS current
			DESCRIPTION
				"The count of Mroute Joined channel"
			::= { sleMcastMrouteCounterInfo 1 }

		
		sleStackDevice OBJECT IDENTIFIER ::= { sleBridge 17 }

		
		sleStackDeviceTable OBJECT-TYPE
			SYNTAX SEQUENCE OF SleStackDeviceEntry
			MAX-ACCESS not-accessible
			STATUS current
			DESCRIPTION
				"Information table of stack master/slave devices."
			::= { sleStackDevice 1 }

		
		sleStackDeviceEntry OBJECT-TYPE
			SYNTAX SleStackDeviceEntry
			MAX-ACCESS not-accessible
			STATUS current
			DESCRIPTION
				"Information table entry of stack master/slave devices.
				key: sleStackDeviceMacAddress"
			INDEX { sleStackDeviceMacAddress }
			::= { sleStackDeviceTable 1 }

		
		SleStackDeviceEntry ::=
			SEQUENCE { 
				sleStackDeviceMacAddress
					OCTET STRING,
				sleStackDeviceNodeId
					Integer32,
				sleStackDeviceDescriptor
					OCTET STRING,
				sleStackDeviceMode
					INTEGER,
				sleStackDeviceStatus
					INTEGER,
				sleStackDeviceType
					OCTET STRING,
				sleStackDeviceHostName
					OCTET STRING,
				sleStackDevicePortNum
					INTEGER
			 }

		sleStackDeviceMacAddress OBJECT-TYPE
			SYNTAX OCTET STRING (SIZE (0..6))
			MAX-ACCESS read-only
			STATUS current
			DESCRIPTION
				"MAC address of stack device."
			::= { sleStackDeviceEntry 1 }

		
		sleStackDeviceNodeId OBJECT-TYPE
			SYNTAX Integer32
			MAX-ACCESS read-only
			STATUS current
			DESCRIPTION
				"Index stack device nodes."
			::= { sleStackDeviceEntry 2 }

		
		sleStackDeviceDescriptor OBJECT-TYPE
			SYNTAX OCTET STRING (SIZE (0..256))
			MAX-ACCESS read-only
			STATUS current
			DESCRIPTION
				"Description of stack device."
			::= { sleStackDeviceEntry 3 }

		
		sleStackDeviceMode OBJECT-TYPE
			SYNTAX INTEGER
				{
				master(1),
				slave(2)
				}
			MAX-ACCESS read-only
			STATUS current
			DESCRIPTION
				"Stack status of device."
			::= { sleStackDeviceEntry 4 }

		
		sleStackDeviceStatus OBJECT-TYPE
			SYNTAX INTEGER
				{
				inactive(0),
				active(1)
				}
			MAX-ACCESS read-only
			STATUS current
			DESCRIPTION
				"Stack status of stack device."
			::= { sleStackDeviceEntry 5 }

		
		sleStackDeviceType OBJECT-TYPE
			SYNTAX OCTET STRING (SIZE (0..16))
			MAX-ACCESS read-only
			STATUS current
			DESCRIPTION
				"Device type of stack device."
			::= { sleStackDeviceEntry 6 }

		
		sleStackDeviceHostName OBJECT-TYPE
			SYNTAX OCTET STRING (SIZE (0..32))
			MAX-ACCESS read-only
			STATUS current
			DESCRIPTION
				"Hostname of stack device."
			::= { sleStackDeviceEntry 7 }

		
		sleStackDevicePortNum OBJECT-TYPE
			SYNTAX INTEGER (0..255)
			MAX-ACCESS read-only
			STATUS current
			DESCRIPTION
				"Number of stack device's ports."
			::= { sleStackDeviceEntry 8 }

		
		sleStackDeviceControl OBJECT IDENTIFIER ::= { sleStackDevice 2 }

		
		sleStackDeviceControlRequest OBJECT-TYPE
			SYNTAX INTEGER
				{
				createStackSlaveDevice(1),
				destoryStackSlaveDevice(2)
				}
			MAX-ACCESS read-write
			STATUS current
			DESCRIPTION
				" The request of a user command"
			::= { sleStackDeviceControl 1 }

		
		sleStackDeviceControlStatus OBJECT-TYPE
			SYNTAX SleControlStatusType
			MAX-ACCESS read-only
			STATUS current
			DESCRIPTION
				" The status of user command"
			::= { sleStackDeviceControl 2 }

		
		sleStackDeviceControlTimer OBJECT-TYPE
			SYNTAX Gauge32
			MAX-ACCESS read-write
			STATUS current
			DESCRIPTION
				" The maximum time for the manager for a long running user command"
			::= { sleStackDeviceControl 3 }

		
		sleStackDeviceControlTImeStamp OBJECT-TYPE
			SYNTAX TimeTicks
			MAX-ACCESS read-only
			STATUS current
			DESCRIPTION
				" The time stamp of the last command(end of command)"
			::= { sleStackDeviceControl 4 }

		
		sleStackDeviceControlReqResult OBJECT-TYPE
			SYNTAX SleControlRequestResultType
			MAX-ACCESS read-only
			STATUS current
			DESCRIPTION
				" The result of the last user command"
			::= { sleStackDeviceControl 5 }

		
		sleStackDeviceControlMacAddress OBJECT-TYPE
			SYNTAX OCTET STRING (SIZE (0..6))
			MAX-ACCESS read-write
			STATUS current
			DESCRIPTION
				"MAC address of slave device."
			::= { sleStackDeviceControl 6 }

		
		sleStackDeviceControlDescriptor OBJECT-TYPE
			SYNTAX OCTET STRING (SIZE (0..256))
			MAX-ACCESS read-write
			STATUS current
			DESCRIPTION
				"Description of stack slave device."
			::= { sleStackDeviceControl 7 }

		
		sleStackDeviceNotification OBJECT IDENTIFIER ::= { sleStackDevice 3 }

		
		sleStackDeviceCreated NOTIFICATION-TYPE
			OBJECTS { sleStackDeviceControlRequest, sleStackDeviceControlTImeStamp, sleStackDeviceControlReqResult, sleStackDeviceDescriptor }
			STATUS current
			DESCRIPTION 
				"Added stack slave device to master stack device."
			::= { sleStackDeviceNotification 1 }

		
		sleStackDeviceDestoryed NOTIFICATION-TYPE
			OBJECTS { sleStackDeviceControlRequest, sleStackDeviceControlTImeStamp, sleStackDeviceControlMacAddress, sleStackDeviceControlReqResult }
			STATUS current
			DESCRIPTION 
				"Deleted stack slave device from master stack device."
			::= { sleStackDeviceNotification 2 }

		
		sleErpDomain OBJECT IDENTIFIER ::= { sleBridge 18 }

		
		sleErpDomainTable OBJECT-TYPE
			SYNTAX SEQUENCE OF SleErpDomainEntry
			MAX-ACCESS not-accessible
			STATUS current
			DESCRIPTION
				" erp domain table."
			::= { sleErpDomain 1 }

		
		sleErpDomainEntry OBJECT-TYPE
			SYNTAX SleErpDomainEntry
			MAX-ACCESS not-accessible
			STATUS current
			DESCRIPTION
				" key: sleErpDomainIndex"
			INDEX { sleErpDomainIndex }
			::= { sleErpDomainTable 1 }

		
		SleErpDomainEntry ::=
			SEQUENCE { 
				sleErpDomainIndex
					INTEGER,
				sleErpDomainName
					OCTET STRING,
				sleErpDomainPrimaryPort
					InterfaceIndex,
				sleErpDomainSecondaryPort
					InterfaceIndex,
				sleErpDomainBridgeRole
					INTEGER,
				sleErpDomainProtectionActivation
					INTEGER,
				sleErpDomainOperatorRequest
					INTEGER,
				sleErpDomainWaitToRestoreTime
					INTEGER,
				sleErpDomainTestPacketInterval
					INTEGER,
				sleErpDomainLearningDisabledTime
					INTEGER,
				sleErpDomainNodeStatus
					INTEGER,
				sleErpDomainRingStatus
					INTEGER,
				sleErpDomainLotp
					INTEGER,
				sleErpDomainULotp
					INTEGER,
				sleErpDomainMultipleRM
					INTEGER,
				sleErpDomainRMNodeReacheablility
					INTEGER,
				sleErpDomainHoldOffTime
					INTEGER,
				sleErpDomainRingPriority
					INTEGER
			 }

		sleErpDomainIndex OBJECT-TYPE
			SYNTAX INTEGER (1..4094)
			MAX-ACCESS read-only
			STATUS current
			DESCRIPTION
				"An index value that uniquely identifies an ERP domain."
			::= { sleErpDomainEntry 1 }

		
		sleErpDomainName OBJECT-TYPE
			SYNTAX OCTET STRING
			MAX-ACCESS read-only
			STATUS current
			DESCRIPTION
				"Domain name."
			::= { sleErpDomainEntry 2 }

		
		sleErpDomainPrimaryPort OBJECT-TYPE
			SYNTAX InterfaceIndex
			MAX-ACCESS read-write
			STATUS current
			DESCRIPTION
				"Interface index that represents the primary port of the domain."
			::= { sleErpDomainEntry 3 }

		
		sleErpDomainSecondaryPort OBJECT-TYPE
			SYNTAX InterfaceIndex
			MAX-ACCESS read-only
			STATUS current
			DESCRIPTION
				"Interface index that represents the secondary port of the domain."
			::= { sleErpDomainEntry 4 }

		
		sleErpDomainBridgeRole OBJECT-TYPE
			SYNTAX INTEGER
				{
				normalNode(0),
				rmNode(1)
				}
			MAX-ACCESS read-only
			STATUS current
			DESCRIPTION
				"Mode that the ERP domain may operate in."
			::= { sleErpDomainEntry 5 }

		
		sleErpDomainProtectionActivation OBJECT-TYPE
			SYNTAX INTEGER
				{
				deactivated(0),
				activated(1)
				}
			MAX-ACCESS read-only
			STATUS current
			DESCRIPTION
				"Protection activation."
			::= { sleErpDomainEntry 6 }

		
		sleErpDomainOperatorRequest OBJECT-TYPE
			SYNTAX INTEGER
				{
				clear(0),
				manualToSecondary(1)
				}
			MAX-ACCESS read-only
			STATUS current
			DESCRIPTION
				"Operator Request."
			::= { sleErpDomainEntry 7 }

		
		sleErpDomainWaitToRestoreTime OBJECT-TYPE
			SYNTAX INTEGER (1..720)
			MAX-ACCESS read-only
			STATUS current
			DESCRIPTION
				"Time in seconds taken to verify that ring integrity is restored."
			::= { sleErpDomainEntry 8 }

		
		sleErpDomainTestPacketInterval OBJECT-TYPE
			SYNTAX INTEGER (10..500)
			MAX-ACCESS read-only
			STATUS current
			DESCRIPTION
				"Time in mili seconds between consecutive transmissions of test packages."
			::= { sleErpDomainEntry 9 }

		
		sleErpDomainLearningDisabledTime OBJECT-TYPE
			SYNTAX INTEGER (0..500)
			MAX-ACCESS read-only
			STATUS current
			DESCRIPTION
				"Time in mili seconds during which learning is disabled after a FDB flash."
			::= { sleErpDomainEntry 10 }

		
		sleErpDomainNodeStatus OBJECT-TYPE
			SYNTAX INTEGER
				{
				rmidle(0),
				primaryProtecting(1),
				protecting(2),
				idle(3),
				failedS(4),
				failedP(5),
				preForward(6),
				isolated(7),
				deactivated(8),
				backoff(9)
				}
			MAX-ACCESS read-only
			STATUS current
			DESCRIPTION
				"Node status."
			::= { sleErpDomainEntry 11 }

		
		sleErpDomainRingStatus OBJECT-TYPE
			SYNTAX INTEGER
				{
				normal(0),
				protecting(1),
				unknown(2)
				}
			MAX-ACCESS read-only
			STATUS current
			DESCRIPTION
				"Actual protection state on the ring."
			::= { sleErpDomainEntry 12 }

		
		sleErpDomainLotp OBJECT-TYPE
			SYNTAX INTEGER
				{
				clear(0),
				raised(1)
				}
			MAX-ACCESS read-only
			STATUS current
			DESCRIPTION
				"Loss of Test Packet alarm status. Only meaningful in RM node."
			::= { sleErpDomainEntry 13 }

		
		sleErpDomainULotp OBJECT-TYPE
			SYNTAX INTEGER
				{
				clear(0),
				raised(1)
				}
			MAX-ACCESS read-only
			STATUS current
			DESCRIPTION
				"Unidirectional Detection of  Loss of Test Packet alarm status.
				Only meaningful in RM node."
			::= { sleErpDomainEntry 14 }

		
		sleErpDomainMultipleRM OBJECT-TYPE
			SYNTAX INTEGER
				{
				clear(0),
				raised(1)
				}
			MAX-ACCESS read-only
			STATUS current
			DESCRIPTION
				"Multiple Redundancy Manager alarm status. Only meaningful
				in RM node."
			::= { sleErpDomainEntry 15 }

		
		sleErpDomainRMNodeReacheablility OBJECT-TYPE
			SYNTAX INTEGER
				{
				clear(0),
				raised(1)
				}
			MAX-ACCESS read-only
			STATUS current
			DESCRIPTION
				"RM Node reacheability alarm status. Only meaningful in
				normal node."
			::= { sleErpDomainEntry 16 }

		
		sleErpDomainHoldOffTime OBJECT-TYPE
			SYNTAX INTEGER (0 | 1..20000)
			MAX-ACCESS read-only
			STATUS current
			DESCRIPTION
				"The hold off time."
			::= { sleErpDomainEntry 17 }

		
		sleErpDomainRingPriority OBJECT-TYPE
			SYNTAX INTEGER (0 | 1..255)
			MAX-ACCESS read-only
			STATUS current
			DESCRIPTION
				"The ring priority"
			::= { sleErpDomainEntry 18 }

		
		sleErpDomainControl OBJECT IDENTIFIER ::= { sleErpDomain 2 }

		
		sleErpDomainControlRequest OBJECT-TYPE
			SYNTAX INTEGER
				{
				createErpDomain(1),
				destroyErpDomain(2),
				setErpDomainProfile(3),
				setErpProtectionActivation(4),
				setErpHoldOffTime(5),
				setErpRingPriority(6),
				setErpTrap(7)
				}
			MAX-ACCESS read-write
			STATUS current
			DESCRIPTION
				"
				createErpDomain:
				sleErpDomainControlIndex
				sleErpDomainControlName
				sleErpDomainControlPrimaryPort
				sleErpDomainControlSecondaryPort
				sleErpDomainControlBridgeRole
				sleErpDomainControlProtectionActivation
				sleErpDomainControlOperatorRequest
				sleErpDomainControlWaitToRestoreTime
				sleErpDomainControlTestPacketInterval
				sleErpDomainControlLearningDisabledTime
				
				destroyErpDomain:
				sleErpDomainControlIndex
				 
				setErpDomainProfile:
				sleErpDomainControlIndex 
				sleErpDomainControlName
				sleErpDomainControlPrimaryPort
				sleErpDomainControlSecondaryPort
				sleErpDomainControlBridgeRole
				sleErpDomainControlOperatorRequest
				sleErpDomainControlWaitToRestoreTime
				sleErpDomainControlTestPacketInterval
				sleErpDomainControlLearningDisabledTime
				
				setErpProtectionActivation:
				sleErpDomainControlIndex 
				sleErpDomainControlProtectionActivation
				"
			::= { sleErpDomainControl 1 }

		
		sleErpDomainControlStatus OBJECT-TYPE
			SYNTAX SleControlStatusType
			MAX-ACCESS read-only
			STATUS current
			DESCRIPTION
				"The status of a user command. 
				"
			::= { sleErpDomainControl 2 }

		
		sleErpDomainControlTimer OBJECT-TYPE
			SYNTAX Gauge32
			MAX-ACCESS read-write
			STATUS current
			DESCRIPTION
				"The maximum wait time for the manager for a long running user command. 
				"
			::= { sleErpDomainControl 3 }

		
		sleErpDomainControlTImeStamp OBJECT-TYPE
			SYNTAX TimeTicks
			MAX-ACCESS read-only
			STATUS current
			DESCRIPTION
				"The time stamp of the last command (end of command)."
			::= { sleErpDomainControl 4 }

		
		sleErpDomainControlReqResult OBJECT-TYPE
			SYNTAX SleControlRequestResultType
			MAX-ACCESS read-only
			STATUS current
			DESCRIPTION
				"The result of the last user command."
			::= { sleErpDomainControl 5 }

		
		sleErpDomainControlIndex OBJECT-TYPE
			SYNTAX Integer32
			MAX-ACCESS read-write
			STATUS current
			DESCRIPTION
				" An index value that uniquely identifies an ERP domain."
			::= { sleErpDomainControl 6 }

		
		sleErpDomainControlName OBJECT-TYPE
			SYNTAX OCTET STRING
			MAX-ACCESS read-write
			STATUS current
			DESCRIPTION
				" Domain name."
			::= { sleErpDomainControl 7 }

		
		sleErpDomainControlPrimaryPort OBJECT-TYPE
			SYNTAX InterfaceIndex
			MAX-ACCESS read-write
			STATUS current
			DESCRIPTION
				" Interface index that represents the primary port of the domain."
			::= { sleErpDomainControl 8 }

		
		sleErpDomainControlSecondaryPort OBJECT-TYPE
			SYNTAX InterfaceIndex
			MAX-ACCESS read-write
			STATUS current
			DESCRIPTION
				" Interface index that represents the secondary port of the domain."
			::= { sleErpDomainControl 9 }

		
		sleErpDomainControlBridgeRole OBJECT-TYPE
			SYNTAX INTEGER
				{
				normalNode(0),
				rmNode(1)
				}
			MAX-ACCESS read-write
			STATUS current
			DESCRIPTION
				" Mode that the ERP domain may operate in."
			::= { sleErpDomainControl 10 }

		
		sleErpDomainControlProtectionActivation OBJECT-TYPE
			SYNTAX INTEGER
				{
				deactivated(0),
				activated(1)
				}
			MAX-ACCESS read-write
			STATUS current
			DESCRIPTION
				" Protection activation."
			::= { sleErpDomainControl 11 }

		
		sleErpDomainControlOperatorRequest OBJECT-TYPE
			SYNTAX INTEGER
				{
				clear(0),
				manualToSecondary(1)
				}
			MAX-ACCESS read-write
			STATUS current
			DESCRIPTION
				"Operator Request."
			::= { sleErpDomainControl 12 }

		
		sleErpDomainControlWaitToRestoreTime OBJECT-TYPE
			SYNTAX INTEGER (1..720)
			MAX-ACCESS read-write
			STATUS current
			DESCRIPTION
				" Time in seconds taken to verify that ring integrity is restored."
			::= { sleErpDomainControl 13 }

		
		sleErpDomainControlTestPacketInterval OBJECT-TYPE
			SYNTAX INTEGER (10..500)
			MAX-ACCESS read-write
			STATUS current
			DESCRIPTION
				" Time in mili seconds between consecutive transmissions of test packages."
			::= { sleErpDomainControl 14 }

		
		sleErpDomainControlLearningDisabledTime OBJECT-TYPE
			SYNTAX INTEGER (0..500)
			MAX-ACCESS read-write
			STATUS current
			DESCRIPTION
				" Time in mili seconds during which learning is disabled after a FDB flash."
			::= { sleErpDomainControl 15 }

		
		sleErpDomainControlHoldOffTime OBJECT-TYPE
			SYNTAX INTEGER (0 | 1..20000)
			MAX-ACCESS read-write
			STATUS current
			DESCRIPTION
				"The hold off time."
			::= { sleErpDomainControl 16 }

		
		sleErpDomainControlRingPriority OBJECT-TYPE
			SYNTAX INTEGER (0 | 1..255)
			MAX-ACCESS read-write
			STATUS current
			DESCRIPTION
				"The ring priority"
			::= { sleErpDomainControl 17 }

		
		sleErpDomainControlLotp OBJECT-TYPE
			SYNTAX INTEGER
				{
				clear(0),
				raised(1)
				}
			MAX-ACCESS read-write
			STATUS current
			DESCRIPTION
				"Loss of Test Packet alarm status. Only meaningful in RM node."
			::= { sleErpDomainControl 18 }

		
		sleErpDomainControlULotp OBJECT-TYPE
			SYNTAX INTEGER
				{
				clear(0),
				raised(1)
				}
			MAX-ACCESS read-write
			STATUS current
			DESCRIPTION
				"Unidirectional Detection of  Loss of Test Packet alarm status.
				Only meaningful in RM node."
			::= { sleErpDomainControl 19 }

		
		sleErpDomainControlMultipleRM OBJECT-TYPE
			SYNTAX INTEGER
				{
				clear(0),
				raised(1)
				}
			MAX-ACCESS read-write
			STATUS current
			DESCRIPTION
				"Multiple Redundancy Manager alarm status. Only meaningful
				in RM node.
				"
			::= { sleErpDomainControl 20 }

		
		sleErpDomainControlRMNodeReacheablility OBJECT-TYPE
			SYNTAX INTEGER
				{
				clear(0),
				raised(1)
				}
			MAX-ACCESS read-write
			STATUS current
			DESCRIPTION
				"Multiple Redundancy Manager alarm status. Only meaningful
				in RM node."
			::= { sleErpDomainControl 21 }

		
		sleErpDomainNotification OBJECT IDENTIFIER ::= { sleErpDomain 3 }

		
		sleErpDomainCreated NOTIFICATION-TYPE
			OBJECTS { sleErpDomainControlRequest, sleErpDomainControlReqResult, sleErpDomainControlTImeStamp, sleErpDomainName, sleErpDomainPrimaryPort, 
				sleErpDomainSecondaryPort, sleErpDomainBridgeRole, sleErpDomainProtectionActivation, sleErpDomainOperatorRequest, sleErpDomainWaitToRestoreTime, 
				sleErpDomainTestPacketInterval, sleErpDomainLearningDisabledTime }
			STATUS current
			DESCRIPTION 
				" "
			::= { sleErpDomainNotification 1 }

		
		sleErpDomainDestroyed NOTIFICATION-TYPE
			OBJECTS { sleErpDomainControlRequest, sleErpDomainControlReqResult, sleErpDomainControlIndex, sleErpDomainControlTImeStamp }
			STATUS current
			DESCRIPTION 
				" "
			::= { sleErpDomainNotification 2 }

		
		sleErpDomainProfileChanged NOTIFICATION-TYPE
			OBJECTS { sleErpDomainControlRequest, sleErpDomainControlReqResult, sleErpDomainControlTImeStamp, sleErpDomainName, sleErpDomainPrimaryPort, 
				sleErpDomainSecondaryPort, sleErpDomainBridgeRole, sleErpDomainOperatorRequest, sleErpDomainWaitToRestoreTime, sleErpDomainTestPacketInterval, 
				sleErpDomainLearningDisabledTime }
			STATUS current
			DESCRIPTION 
				" "
			::= { sleErpDomainNotification 3 }

		
		sleErpProtectionActivationChanged NOTIFICATION-TYPE
			OBJECTS { sleErpDomainControlRequest, sleErpDomainControlReqResult, sleErpDomainControlTImeStamp, sleErpDomainProtectionActivation }
			STATUS current
			DESCRIPTION 
				" "
			::= { sleErpDomainNotification 4 }

		
		sleErpHoldOffTimeChanged NOTIFICATION-TYPE
			OBJECTS { sleErpDomainControlRequest, sleErpDomainControlTImeStamp, sleErpDomainControlReqResult, sleErpDomainHoldOffTime }
			STATUS current
			DESCRIPTION 
				"Description."
			::= { sleErpDomainNotification 5 }

		
		sleErpRingPriorityChanged NOTIFICATION-TYPE
			OBJECTS { sleErpDomainControlRequest, sleErpDomainControlTImeStamp, sleErpDomainControlReqResult, sleErpDomainRingPriority }
			STATUS current
			DESCRIPTION 
				"Description."
			::= { sleErpDomainNotification 6 }

		
		sleErpTrapChanged NOTIFICATION-TYPE
			OBJECTS { sleErpDomainControlRequest, sleErpDomainControlTImeStamp, sleErpDomainControlReqResult, sleErpDomainLotp, sleErpDomainULotp, 
				sleErpDomainMultipleRM, sleErpDomainRMNodeReacheablility }
			STATUS current
			DESCRIPTION 
				"Description."
			::= { sleErpDomainNotification 7 }

		
		sleLldpPort OBJECT IDENTIFIER ::= { sleBridge 19 }

		
		sleLldpPortTable OBJECT-TYPE
			SYNTAX SEQUENCE OF SleLldpPortEntry
			MAX-ACCESS not-accessible
			STATUS current
			DESCRIPTION
				"LLDP port table."
			::= { sleLldpPort 1 }

		
		sleLldpPortEntry OBJECT-TYPE
			SYNTAX SleLldpPortEntry
			MAX-ACCESS not-accessible
			STATUS current
			DESCRIPTION
				" key: sleLldpPortIndex"
			INDEX { sleLldpPortIndex }
			::= { sleLldpPortTable 1 }

		
		SleLldpPortEntry ::=
			SEQUENCE { 
				sleLldpPortIndex
					INTEGER,
				sleLldpPortActivity
					Boolean,
				sleLldpPortAdminStatus
					INTEGER,
				sleLldpPortNotificationEnable
					Boolean,
				sleLldpPortTLVsTxEnable
					BITS,
				sleLldpPortMgmtTxEnable
					Boolean,
				sleLldpPortMgmtAddress
					IpAddress,
				sleLldpPortTLVsTxNetworkPolciyProfile
					OCTET STRING,
				sleLldpPortMgmtIPType
					Integer32,
				sleLldpPortMgmtIPAddress
					IpAddress
			 }

		sleLldpPortIndex OBJECT-TYPE
			SYNTAX INTEGER (1..255)
			MAX-ACCESS read-only
			STATUS current
			DESCRIPTION
				" LLDP port index"
			::= { sleLldpPortEntry 1 }

		
		sleLldpPortActivity OBJECT-TYPE
			SYNTAX Boolean
			MAX-ACCESS read-only
			STATUS current
			DESCRIPTION
				"sleLldpPortActivity"
			::= { sleLldpPortEntry 2 }

		
		sleLldpPortAdminStatus OBJECT-TYPE
			SYNTAX INTEGER
				{
				txOnly(1),
				rxOnly(2),
				txAndRx(3),
				disabled(4)
				}
			MAX-ACCESS read-write
			STATUS current
			DESCRIPTION
				"The administratively desired status of the local LLDP agent."
			::= { sleLldpPortEntry 3 }

		
		sleLldpPortNotificationEnable OBJECT-TYPE
			SYNTAX Boolean
			MAX-ACCESS read-write
			STATUS current
			DESCRIPTION
				"It controls, on a per port basis,  whether or not notifications from the agent are enabled. "
			::= { sleLldpPortEntry 4 }

		
		sleLldpPortTLVsTxEnable OBJECT-TYPE
			SYNTAX BITS
				{
				portDesc(0),
				sysName(1),
				sysDesc(2),
				sysCap(3)
				}
			MAX-ACCESS read-write
			STATUS current
			DESCRIPTION
				"Bitmap that includes the basic set of LLDP TLVs whose transmission is allowed on the local LLDP agent by the network management."
			::= { sleLldpPortEntry 5 }

		
		sleLldpPortMgmtTxEnable OBJECT-TYPE
			SYNTAX Boolean
			MAX-ACCESS read-only
			STATUS current
			DESCRIPTION
				"It indicates that the port is either enable or not to transfer management address."
			::= { sleLldpPortEntry 6 }

		
		sleLldpPortMgmtAddress OBJECT-TYPE
			SYNTAX IpAddress
			MAX-ACCESS read-only
			STATUS current
			DESCRIPTION
				"Management address to transfer on the port."
			::= { sleLldpPortEntry 7 }

		
		sleLldpPortTLVsTxNetworkPolciyProfile OBJECT-TYPE
			SYNTAX OCTET STRING
			MAX-ACCESS read-only
			STATUS current
			DESCRIPTION
				"Assigned network-policy profile and specifies the network-policy TLV."
			::= { sleLldpPortEntry 8 }

		
		sleLldpPortMgmtIPType OBJECT-TYPE
			SYNTAX Integer32
			MAX-ACCESS read-only
			STATUS current
			DESCRIPTION
				"Management IP address Type."
			::= { sleLldpPortEntry 9 }

		
		sleLldpPortMgmtIPAddress OBJECT-TYPE
			SYNTAX IpAddress
			MAX-ACCESS read-only
			STATUS current
			DESCRIPTION
				"Management IP address to transfer on the port."
			::= { sleLldpPortEntry 10 }

		
		sleLldpPortControl OBJECT IDENTIFIER ::= { sleLldpPort 2 }

		
		sleLldpPortControlRequest OBJECT-TYPE
			SYNTAX INTEGER
				{
				setLldpPortProfile(1),
				setLldpNetworkPolicyProfile(2)
				}
			MAX-ACCESS read-write
			STATUS current
			DESCRIPTION
				" The request of a user command"
			::= { sleLldpPortControl 1 }

		
		sleLldpPortControlStatus OBJECT-TYPE
			SYNTAX SleControlStatusType
			MAX-ACCESS read-only
			STATUS current
			DESCRIPTION
				" The status of user command"
			::= { sleLldpPortControl 2 }

		
		sleLldpPortControlTimer OBJECT-TYPE
			SYNTAX Gauge32
			MAX-ACCESS read-write
			STATUS current
			DESCRIPTION
				" The maximum time for the manager for a long running user command"
			::= { sleLldpPortControl 3 }

		
		sleLldpPortControlTimeStamp OBJECT-TYPE
			SYNTAX TimeTicks
			MAX-ACCESS read-only
			STATUS current
			DESCRIPTION
				" The time stamp of the last command(end of command)"
			::= { sleLldpPortControl 4 }

		
		sleLldpPortControlReqResult OBJECT-TYPE
			SYNTAX SleControlRequestResultType
			MAX-ACCESS read-only
			STATUS current
			DESCRIPTION
				" The result of the last user command"
			::= { sleLldpPortControl 5 }

		
		sleLldpPortControlIndex OBJECT-TYPE
			SYNTAX INTEGER (1..255)
			MAX-ACCESS read-write
			STATUS current
			DESCRIPTION
				"LLDP port index"
			::= { sleLldpPortControl 6 }

		
		sleLldpPortControlActivity OBJECT-TYPE
			SYNTAX Boolean
			MAX-ACCESS read-write
			STATUS current
			DESCRIPTION
				"sleLldpPortControlActivity"
			::= { sleLldpPortControl 7 }

		
		sleLldpPortControlAdminstatus OBJECT-TYPE
			SYNTAX INTEGER
				{
				txOnly(1),
				rxOnly(2),
				txAndRx(3),
				disabled(4)
				}
			MAX-ACCESS read-write
			STATUS current
			DESCRIPTION
				"The administratively desired status of the local LLDP agent."
			::= { sleLldpPortControl 8 }

		
		sleLldpPortControlNotificationEnable OBJECT-TYPE
			SYNTAX Boolean
			MAX-ACCESS read-write
			STATUS current
			DESCRIPTION
				" It controls, on a per port basis, whether or not notifications from the agent are enabled."
			::= { sleLldpPortControl 9 }

		
		sleLldpPortControlTLVsTxEnable OBJECT-TYPE
			SYNTAX BITS
				{
				portDesc(0),
				sysName(1),
				sysDesc(2),
				sysCap(3)
				}
			MAX-ACCESS read-write
			STATUS current
			DESCRIPTION
				" Bitmap that includes the basic set of LLDP TLVs whose transmission is allowed on the local LLDP agent by the network management."
			::= { sleLldpPortControl 10 }

		
		sleLldpPortControlMgmtTxEnable OBJECT-TYPE
			SYNTAX Boolean
			MAX-ACCESS read-write
			STATUS current
			DESCRIPTION
				"It indicates that the port is either enable or not to transfer management address."
			::= { sleLldpPortControl 11 }

		
		sleLldpPortControlMgmtAddress OBJECT-TYPE
			SYNTAX IpAddress
			MAX-ACCESS read-write
			STATUS current
			DESCRIPTION
				"Management address to transfer on the port."
			::= { sleLldpPortControl 12 }

		
		sleLldpPortControlTLVsTxNetworkPolicyProfile OBJECT-TYPE
			SYNTAX OCTET STRING
			MAX-ACCESS read-write
			STATUS current
			DESCRIPTION
				"Assigned network-policy profile and specifies the network-policy TLV."
			::= { sleLldpPortControl 13 }

		
		sleLldpPortControlMgmtIPType OBJECT-TYPE
			SYNTAX INTEGER
				{
				ipv4(1),
				ipv6(2)
				}
			MAX-ACCESS read-write
			STATUS current
			DESCRIPTION
				"Management IP address Type.
				1: ipv4
				2: ipv6"
			::= { sleLldpPortControl 14 }

		
		sleLldpPortControlMgmtIPAddress OBJECT-TYPE
			SYNTAX IpAddress
			MAX-ACCESS read-write
			STATUS current
			DESCRIPTION
				"Management IP address to transfer on the port."
			::= { sleLldpPortControl 15 }

		
		sleLldpPortNotification OBJECT IDENTIFIER ::= { sleLldpPort 3 }

		
		sleLldpPortProfileChanged NOTIFICATION-TYPE
			OBJECTS { sleLldpPortActivity, sleLldpPortAdminStatus, sleLldpPortNotificationEnable, sleLldpPortTLVsTxEnable, sleLldpPortMgmtTxEnable, 
				sleLldpPortMgmtAddress, sleLldpPortControlRequest, sleLldpPortControlTimeStamp, sleLldpPortControlReqResult }
			STATUS current
			DESCRIPTION 
				" "
			::= { sleLldpPortNotification 1 }

		
		sleLldpPortNetworkPolicyProfileChanged NOTIFICATION-TYPE
			OBJECTS { sleLldpPortControlRequest, sleLldpPortControlTimeStamp, sleLldpPortControlReqResult, sleLldpPortControlTLVsTxNetworkPolicyProfile }
			STATUS current
			DESCRIPTION 
				" "
			::= { sleLldpPortNotification 2 }

		
		sleLldpRemote OBJECT IDENTIFIER ::= { sleBridge 20 }

		
		sleLldpRemoteTable OBJECT-TYPE
			SYNTAX SEQUENCE OF SleLldpRemoteEntry
			MAX-ACCESS not-accessible
			STATUS current
			DESCRIPTION
				" LLDP remote table."
			::= { sleLldpRemote 1 }

		
		sleLldpRemoteEntry OBJECT-TYPE
			SYNTAX SleLldpRemoteEntry
			MAX-ACCESS not-accessible
			STATUS current
			DESCRIPTION
				" key: sleLldpPortIndex, sleLldpRemIndex"
			INDEX { sleLldpPortIndex, sleLldpRemIndex }
			::= { sleLldpRemoteTable 1 }

		
		SleLldpRemoteEntry ::=
			SEQUENCE { 
				sleLldpRemIndex
					Integer32,
				sleLldpRemTimeMark
					TimeTicks,
				sleLldpRemChassisIdSubtype
					INTEGER,
				sleLldpRemChassisId
					OCTET STRING,
				sleLldpRemPortIdSubtype
					INTEGER,
				sleLldpRemPortId
					OCTET STRING,
				sleLldpRemPortDesc
					OCTET STRING,
				sleLldpRemSysName
					OCTET STRING,
				sleLldpRemSysDesc
					OCTET STRING,
				sleLldpRemSysCapSupported
					BITS,
				sleLldpRemSysCapEnabled
					BITS
			 }

		sleLldpRemIndex OBJECT-TYPE
			SYNTAX Integer32 (1..2147483647)
			MAX-ACCESS read-write
			STATUS current
			DESCRIPTION
				"This object represents an arbitrary local integer value used by this agent to identify a particular connection instance, unique only for the indicated remote system."
			::= { sleLldpRemoteEntry 1 }

		
		sleLldpRemTimeMark OBJECT-TYPE
			SYNTAX TimeTicks
			MAX-ACCESS read-only
			STATUS current
			DESCRIPTION
				"The sysUptime that this entry has been created or modified."
			::= { sleLldpRemoteEntry 2 }

		
		sleLldpRemChassisIdSubtype OBJECT-TYPE
			SYNTAX INTEGER
				{
				chassisComponent(1),
				interfaceAlias(2),
				portComponent(3),
				macAddress(4),
				networkAddress(5),
				interfaceName(6),
				local(7)
				}
			MAX-ACCESS read-only
			STATUS current
			DESCRIPTION
				"The type of encoding used to identify the chassis associatedwith the remote system."
			::= { sleLldpRemoteEntry 3 }

		
		sleLldpRemChassisId OBJECT-TYPE
			SYNTAX OCTET STRING (SIZE (1..255))
			MAX-ACCESS read-write
			STATUS current
			DESCRIPTION
				"The type of encoding used to identify the chassis associatedwith the remote system."
			::= { sleLldpRemoteEntry 4 }

		
		sleLldpRemPortIdSubtype OBJECT-TYPE
			SYNTAX INTEGER
				{
				interfaceAlias(1),
				portComponent(2),
				macAddress(3),
				networkAddress(4),
				interfaceName(5),
				agentCircuitId(6),
				local(7)
				}
			MAX-ACCESS read-write
			STATUS current
			DESCRIPTION
				"The type of port identifier encoding used in the associated'lldpRemPortId' object."
			::= { sleLldpRemoteEntry 5 }

		
		sleLldpRemPortId OBJECT-TYPE
			SYNTAX OCTET STRING (SIZE (1..255))
			MAX-ACCESS read-only
			STATUS current
			DESCRIPTION
				"The string value used to identify the port component associated with the remote system."
			::= { sleLldpRemoteEntry 6 }

		
		sleLldpRemPortDesc OBJECT-TYPE
			SYNTAX OCTET STRING (SIZE (0..255))
			MAX-ACCESS read-only
			STATUS current
			DESCRIPTION
				"The string value used to identify the description of the given port associated with the remote system."
			::= { sleLldpRemoteEntry 7 }

		
		sleLldpRemSysName OBJECT-TYPE
			SYNTAX OCTET STRING (SIZE (0..255))
			MAX-ACCESS read-only
			STATUS current
			DESCRIPTION
				"The string value used to identify the system name of the remote system."
			::= { sleLldpRemoteEntry 8 }

		
		sleLldpRemSysDesc OBJECT-TYPE
			SYNTAX OCTET STRING (SIZE (0..255))
			MAX-ACCESS read-only
			STATUS current
			DESCRIPTION
				"The string value used to identify the system description of the remote system."
			::= { sleLldpRemoteEntry 9 }

		
		sleLldpRemSysCapSupported OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are supported on the remote system."
			::= { sleLldpRemoteEntry 10 }

		
		sleLldpRemSysCapEnabled OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are enabled on the remote system."
			::= { sleLldpRemoteEntry 11 }

		
		sleLldpRemoteManAddrTable OBJECT-TYPE
			SYNTAX SEQUENCE OF SleLldpRemoteManAddrEntry
			MAX-ACCESS not-accessible
			STATUS current
			DESCRIPTION
				" LLDP remote table."
			::= { sleLldpRemote 2 }

		
		sleLldpRemoteManAddrEntry OBJECT-TYPE
			SYNTAX SleLldpRemoteManAddrEntry
			MAX-ACCESS not-accessible
			STATUS current
			DESCRIPTION
				" key: sleLldpPortIndex, sleLldpRemIndex"
			INDEX { sleLldpPortIndex, sleLldpRemIndex, sleLldpRemManAddrSubType, sleLldpRemManAddr }
			::= { sleLldpRemoteManAddrTable 1 }

		
		SleLldpRemoteManAddrEntry ::=
			SEQUENCE { 
				sleLldpRemManAddrSubType
					AddressFamilyNumbers,
				sleLldpRemManAddr
					OCTET STRING,
				sleLldpRemManAddrIfSubType
					SleLldpManAddrIfSubType,
				sleLldpRemManAddrIfId
					Integer32,
				sleLldpRemAddrOid
					OBJECT IDENTIFIER
			 }

		sleLldpRemManAddrSubType OBJECT-TYPE
			SYNTAX AddressFamilyNumbers (0..65535)
			MAX-ACCESS read-only
			STATUS current
			DESCRIPTION
				"This object represents an arbitrary local integer value used by this agent to identify a particular connection instance, unique only for the indicated remote system."
			::= { sleLldpRemoteManAddrEntry 1 }

		
		sleLldpRemManAddr OBJECT-TYPE
			SYNTAX OCTET STRING
			MAX-ACCESS read-only
			STATUS current
			DESCRIPTION
				"The sysUptime that this entry has been created or modified."
			::= { sleLldpRemoteManAddrEntry 2 }

		
		sleLldpRemManAddrIfSubType OBJECT-TYPE
			SYNTAX SleLldpManAddrIfSubType
			MAX-ACCESS read-only
			STATUS current
			DESCRIPTION
				"The type of encoding used to identify the chassis associatedwith the remote system."
			::= { sleLldpRemoteManAddrEntry 3 }

		
		sleLldpRemManAddrIfId OBJECT-TYPE
			SYNTAX Integer32
			MAX-ACCESS read-only
			STATUS current
			DESCRIPTION
				"The type of encoding used to identify the chassis associatedwith the remote system."
			::= { sleLldpRemoteManAddrEntry 4 }

		
		sleLldpRemAddrOid OBJECT-TYPE
			SYNTAX OBJECT IDENTIFIER
			MAX-ACCESS read-only
			STATUS current
			DESCRIPTION
				"The type of port identifier encoding used in the associated'lldpRemPortId' object."
			::= { sleLldpRemoteManAddrEntry 5 }

		
		sleLldpStatistics OBJECT IDENTIFIER ::= { sleBridge 21 }

		
		sleLldpStatisticsTable OBJECT-TYPE
			SYNTAX SEQUENCE OF SleLldpStatisticsEntry
			MAX-ACCESS not-accessible
			STATUS current
			DESCRIPTION
				"LLDP statistics table."
			::= { sleLldpStatistics 1 }

		
		sleLldpStatisticsEntry OBJECT-TYPE
			SYNTAX SleLldpStatisticsEntry
			MAX-ACCESS not-accessible
			STATUS current
			DESCRIPTION
				"key: sleLldpPortIndex"
			INDEX { sleLldpPortIndex }
			::= { sleLldpStatisticsTable 1 }

		
		SleLldpStatisticsEntry ::=
			SEQUENCE { 
				sleLldpStatsTxPortFramesTotal
					Integer32,
				sleLldpStatsRxPortFramesDiscardedTotal
					Counter32,
				sleLldpStatsRxPortFramesErrors
					Integer32,
				sleLldpStatsRxPortFramesTotal
					Counter32,
				sleLldpStatsRxPortTLVsDiscardedTotal
					Integer32,
				sleLldpStatsRxPortTLVsUnrecognizedTotal
					Integer32,
				sleLldpStatsRxPortAgeoutsTotal
					Counter32
			 }

		sleLldpStatsTxPortFramesTotal OBJECT-TYPE
			SYNTAX Integer32
			MAX-ACCESS read-only
			STATUS current
			DESCRIPTION
				"The number of LLDP frames transmitted by this LLDP agent on the indicated port."
			::= { sleLldpStatisticsEntry 1 }

		
		sleLldpStatsRxPortFramesDiscardedTotal OBJECT-TYPE
			SYNTAX Counter32
			MAX-ACCESS read-only
			STATUS current
			DESCRIPTION
				"The number of LLDP frames received by this LLDP agent on  the indicated port, and then discarded for any reason."
			::= { sleLldpStatisticsEntry 2 }

		
		sleLldpStatsRxPortFramesErrors OBJECT-TYPE
			SYNTAX Integer32
			MAX-ACCESS read-only
			STATUS current
			DESCRIPTION
				"The number of invalid LLDP frames received by this LLDPagent on the indicated port, while this LLDP agent is enabled."
			::= { sleLldpStatisticsEntry 3 }

		
		sleLldpStatsRxPortFramesTotal OBJECT-TYPE
			SYNTAX Counter32
			MAX-ACCESS read-only
			STATUS current
			DESCRIPTION
				"The number of valid LLDP frames received by this LLDP agent on the indicated port, while this LLDP agent is enabled."
			::= { sleLldpStatisticsEntry 4 }

		
		sleLldpStatsRxPortTLVsDiscardedTotal OBJECT-TYPE
			SYNTAX Integer32
			MAX-ACCESS read-only
			STATUS current
			DESCRIPTION
				"The number of LLDP TLVs discarded for any reason by this LLDP agent on the indicated port."
			::= { sleLldpStatisticsEntry 5 }

		
		sleLldpStatsRxPortTLVsUnrecognizedTotal OBJECT-TYPE
			SYNTAX Integer32
			MAX-ACCESS read-only
			STATUS current
			DESCRIPTION
				"The number of LLDP TLVs received on the given port that are not recognized by this LLDP agent on the indicated port."
			::= { sleLldpStatisticsEntry 6 }

		
		sleLldpStatsRxPortAgeoutsTotal OBJECT-TYPE
			SYNTAX Counter32
			MAX-ACCESS read-only
			STATUS current
			DESCRIPTION
				"The counter that represents the number of age-outs that occurred on a given port."
			::= { sleLldpStatisticsEntry 7 }

		
		sleLldpStatisticsControl OBJECT IDENTIFIER ::= { sleLldpStatistics 2 }

		
		sleLldpStatsControlRequest OBJECT-TYPE
			SYNTAX INTEGER { clearLldpStatistics(1) }
			MAX-ACCESS read-write
			STATUS current
			DESCRIPTION
				"The request of a user command"
			::= { sleLldpStatisticsControl 1 }

		
		sleLldpStatsControlStatus OBJECT-TYPE
			SYNTAX SleControlStatusType
			MAX-ACCESS read-only
			STATUS current
			DESCRIPTION
				"The status of user command"
			::= { sleLldpStatisticsControl 2 }

		
		sleLldpStatsControlTimer OBJECT-TYPE
			SYNTAX Gauge32
			MAX-ACCESS read-write
			STATUS current
			DESCRIPTION
				"The maximum time for the manager for a long running user command"
			::= { sleLldpStatisticsControl 3 }

		
		sleLldpStatsControlTimeStamp OBJECT-TYPE
			SYNTAX TimeTicks
			MAX-ACCESS read-only
			STATUS current
			DESCRIPTION
				"The time stamp of the last command(end of command)"
			::= { sleLldpStatisticsControl 4 }

		
		sleLldpStatsControlReqResult OBJECT-TYPE
			SYNTAX SleControlRequestResultType
			MAX-ACCESS read-only
			STATUS current
			DESCRIPTION
				"The result of the last user command"
			::= { sleLldpStatisticsControl 5 }

		
		sleLldpStatsControlPortIndex OBJECT-TYPE
			SYNTAX Unsigned32 (1..255)
			MAX-ACCESS read-write
			STATUS current
			DESCRIPTION
				"LLDP port index in sleLldpPortTable"
			::= { sleLldpStatisticsControl 6 }

		
		sleLldpStatisticsNotification OBJECT IDENTIFIER ::= { sleLldpStatistics 3 }

		
		sleLldpStatisticsCleared NOTIFICATION-TYPE
			OBJECTS { sleLldpStatsControlRequest, sleLldpStatsControlTimeStamp, sleLldpStatsControlPortIndex, sleLldpStatsControlReqResult }
			STATUS current
			DESCRIPTION 
				"Description."
			::= { sleLldpStatisticsNotification 1 }

		
		sleBridgePortSecurity OBJECT IDENTIFIER ::= { sleBridge 22 }

		
		sleBridgePSTable OBJECT-TYPE
			SYNTAX SEQUENCE OF SleBridgePSEntry
			MAX-ACCESS not-accessible
			STATUS current
			DESCRIPTION
				"bridge port security table."
			::= { sleBridgePortSecurity 1 }

		
		sleBridgePSEntry OBJECT-TYPE
			SYNTAX SleBridgePSEntry
			MAX-ACCESS not-accessible
			STATUS current
			DESCRIPTION
				"key: sleBridgePSIndex"
			INDEX { sleBridgePSIndex }
			::= { sleBridgePSTable 1 }

		
		SleBridgePSEntry ::=
			SEQUENCE { 
				sleBridgePSIndex
					InterfaceIndex,
				sleBridgePSStatus
					INTEGER,
				sleBridgePSMaxCount
					INTEGER,
				sleBridgePSCurrCount
					Unsigned32,
				sleBridgePSAgingType
					INTEGER,
				sleBridgePSAgingTimer
					INTEGER,
				sleBridgePSAgingStatic
					INTEGER,
				sleBridgePSViolation
					INTEGER
			 }

		sleBridgePSIndex OBJECT-TYPE
			SYNTAX InterfaceIndex
			MAX-ACCESS read-only
			STATUS current
			DESCRIPTION
				"The index of logical port"
			::= { sleBridgePSEntry 1 }

		
		sleBridgePSStatus OBJECT-TYPE
			SYNTAX INTEGER
				{
				enable(1),
				disable(2)
				}
			MAX-ACCESS read-only
			STATUS current
			DESCRIPTION
				"The status of port security"
			::= { sleBridgePSEntry 2 }

		
		sleBridgePSMaxCount OBJECT-TYPE
			SYNTAX INTEGER (-1 | 1..16384)
			MAX-ACCESS read-only
			STATUS current
			DESCRIPTION
				"The max secure addresses
				The value of -1 is not used
				"
			::= { sleBridgePSEntry 3 }

		
		sleBridgePSCurrCount OBJECT-TYPE
			SYNTAX Unsigned32
			MAX-ACCESS read-only
			STATUS current
			DESCRIPTION
				"The current count of port security"
			::= { sleBridgePSEntry 4 }

		
		sleBridgePSAgingType OBJECT-TYPE
			SYNTAX INTEGER
				{
				absolute(1),
				inactivity(2)
				}
			MAX-ACCESS read-only
			STATUS current
			DESCRIPTION
				"The aging type of port security"
			::= { sleBridgePSEntry 5 }

		
		sleBridgePSAgingTimer OBJECT-TYPE
			SYNTAX INTEGER (-1 | 0 | 1..2147483647)
			UNITS "second"
			MAX-ACCESS read-only
			STATUS current
			DESCRIPTION
				"The aging time of port security
				The value of -1 and 0 means that aging time fixed to static and it will be not aging out
				But The case of 5924N,
				The value of -1 means that aging time fixed to static and it will be not agint out
				The value of 0 means that aging out disable. "
			::= { sleBridgePSEntry 6 }

		
		sleBridgePSAgingStatic OBJECT-TYPE
			SYNTAX INTEGER
				{
				enable(1),
				disable(2)
				}
			MAX-ACCESS read-only
			STATUS current
			DESCRIPTION
				"The enable aging for configured secure addressess"
			::= { sleBridgePSEntry 7 }

		
		sleBridgePSViolation OBJECT-TYPE
			SYNTAX INTEGER
				{
				shutdown(1),
				protect(2),
				restrict(3)
				}
			MAX-ACCESS read-only
			STATUS current
			DESCRIPTION
				"The security violation mode of port security "
			::= { sleBridgePSEntry 8 }

		
		sleBridgePSControl OBJECT IDENTIFIER ::= { sleBridgePortSecurity 2 }

		
		sleBridgePSControlRequest OBJECT-TYPE
			SYNTAX INTEGER
				{
				setPSStatus(1),
				setPSMaxCount(2),
				setPSProfile(3)
				}
			MAX-ACCESS read-write
			STATUS current
			DESCRIPTION
				"The request of a user command"
			::= { sleBridgePSControl 1 }

		
		sleBridgePSControlStatus OBJECT-TYPE
			SYNTAX SleControlStatusType
			MAX-ACCESS read-only
			STATUS current
			DESCRIPTION
				"The status of user command"
			::= { sleBridgePSControl 2 }

		
		sleBridgePSControlTimer OBJECT-TYPE
			SYNTAX Gauge32
			MAX-ACCESS read-write
			STATUS current
			DESCRIPTION
				"The maximum time for the manager for a long running user command"
			::= { sleBridgePSControl 3 }

		
		sleBridgePSControlTimeStamp OBJECT-TYPE
			SYNTAX TimeTicks
			MAX-ACCESS read-only
			STATUS current
			DESCRIPTION
				"The time stamp of the last command(end of command)"
			::= { sleBridgePSControl 4 }

		
		sleBridgePSControlReqResult OBJECT-TYPE
			SYNTAX SleControlRequestResultType
			MAX-ACCESS read-only
			STATUS current
			DESCRIPTION
				"The result of the last user command"
			::= { sleBridgePSControl 5 }

		
		sleBridgePSControlIndex OBJECT-TYPE
			SYNTAX InterfaceIndex
			MAX-ACCESS read-write
			STATUS current
			DESCRIPTION
				"The index of logical port"
			::= { sleBridgePSControl 6 }

		
		sleBridgePSControlPSStatus OBJECT-TYPE
			SYNTAX INTEGER
				{
				enable(1),
				disable(2)
				}
			MAX-ACCESS read-write
			STATUS current
			DESCRIPTION
				"The status of port security"
			::= { sleBridgePSControl 7 }

		
		sleBridgePSControlMaxCount OBJECT-TYPE
			SYNTAX INTEGER (-1 | 1..16384)
			MAX-ACCESS read-write
			STATUS current
			DESCRIPTION
				"The max secure addresses
				The value of -1 is not used
				"
			::= { sleBridgePSControl 8 }

		
		sleBridgePSControlAgingType OBJECT-TYPE
			SYNTAX INTEGER
				{
				absolute(1),
				inactivity(2)
				}
			MAX-ACCESS read-write
			STATUS current
			DESCRIPTION
				"The aging type of port security"
			::= { sleBridgePSControl 9 }

		
		sleBridgePSControlAgingTimer OBJECT-TYPE
			SYNTAX INTEGER (-1 | 0 | 1..2147483647)
			UNITS "second"
			MAX-ACCESS read-write
			STATUS current
			DESCRIPTION
				"The aging time of port security
				The value -1 and 0 means that aging time fixed to static and it will be not aging out"
			::= { sleBridgePSControl 10 }

		
		sleBridgePSControlAgingStatic OBJECT-TYPE
			SYNTAX INTEGER
				{
				enable(1),
				disable(2)
				}
			MAX-ACCESS read-write
			STATUS current
			DESCRIPTION
				"The enable aging for configured secure addressess"
			::= { sleBridgePSControl 11 }

		
		sleBridgePScontrolViolation OBJECT-TYPE
			SYNTAX INTEGER
				{
				shutdown(1),
				protect(2),
				restrict(3)
				}
			MAX-ACCESS read-write
			STATUS current
			DESCRIPTION
				"The security violation mode of port security "
			::= { sleBridgePSControl 12 }

		
		sleBridgePSNotification OBJECT IDENTIFIER ::= { sleBridgePortSecurity 3 }

		
		sleBridgePSStatusChanged NOTIFICATION-TYPE
			OBJECTS { sleBridgePSControlRequest, sleBridgePSControlTimeStamp, sleBridgePSControlReqResult, sleBridgePSControlIndex, sleBridgePSControlPSStatus
				 }
			STATUS current
			DESCRIPTION 
				"Description."
			::= { sleBridgePSNotification 1 }

		
		sleBridgePSMaxCountChanged NOTIFICATION-TYPE
			OBJECTS { sleBridgePSControlRequest, sleBridgePSControlTimeStamp, sleBridgePSControlReqResult, sleBridgePSControlIndex, sleBridgePSControlMaxCount
				 }
			STATUS current
			DESCRIPTION 
				"Description."
			::= { sleBridgePSNotification 2 }

		
		sleBridgePSProfileChanged NOTIFICATION-TYPE
			OBJECTS { sleBridgePSControlRequest, sleBridgePSControlTimeStamp, sleBridgePSControlReqResult, sleBridgePSControlIndex, sleBridgePSControlAgingType, 
				sleBridgePSControlAgingTimer, sleBridgePSControlAgingStatic, sleBridgePScontrolViolation }
			STATUS current
			DESCRIPTION 
				"Description."
			::= { sleBridgePSNotification 3 }

		
		sleBridgePortSecurityFdb OBJECT IDENTIFIER ::= { sleBridge 23 }

		
		sleBridgePSFdbTable OBJECT-TYPE
			SYNTAX SEQUENCE OF SleBridgePSFdbEntry
			MAX-ACCESS not-accessible
			STATUS current
			DESCRIPTION
				"bridge port security FDB table."
			::= { sleBridgePortSecurityFdb 1 }

		
		sleBridgePSFdbEntry OBJECT-TYPE
			SYNTAX SleBridgePSFdbEntry
			MAX-ACCESS not-accessible
			STATUS current
			DESCRIPTION
				"key: sleBridgePSFdbPort, sleBridgePSFdbVid, sleBridgePSFdbMacAddress"
			INDEX { sleBridgePSFdbPort, sleBridgePSFdbVid, sleBridgePSFdbMacAddress }
			::= { sleBridgePSFdbTable 1 }

		
		SleBridgePSFdbEntry ::=
			SEQUENCE { 
				sleBridgePSFdbPort
					INTEGER,
				sleBridgePSFdbVid
					INTEGER,
				sleBridgePSFdbMacAddress
					OCTET STRING,
				sleBridgePSFdbMode
					INTEGER,
				sleBridgePSFdbElapsedTime
					Unsigned32
			 }

		sleBridgePSFdbPort OBJECT-TYPE
			SYNTAX INTEGER (1..512)
			MAX-ACCESS read-only
			STATUS current
			DESCRIPTION
				"FDB mode configuration.
				1: dynamic
				2: static
				"
			::= { sleBridgePSFdbEntry 1 }

		
		sleBridgePSFdbVid OBJECT-TYPE
			SYNTAX INTEGER (1..4094)
			MAX-ACCESS read-only
			STATUS current
			DESCRIPTION
				"FDB vlan index"
			::= { sleBridgePSFdbEntry 2 }

		
		sleBridgePSFdbMacAddress OBJECT-TYPE
			SYNTAX OCTET STRING (SIZE (0..6))
			MAX-ACCESS read-only
			STATUS current
			DESCRIPTION
				"FDB MAC address"
			::= { sleBridgePSFdbEntry 3 }

		
		sleBridgePSFdbMode OBJECT-TYPE
			SYNTAX INTEGER
				{
				dynamic(1),
				static(2)
				}
			MAX-ACCESS read-only
			STATUS current
			DESCRIPTION
				"FDB mode configuration.
				1: dynamic
				2: static
				"
			::= { sleBridgePSFdbEntry 4 }

		
		sleBridgePSFdbElapsedTime OBJECT-TYPE
			SYNTAX Unsigned32
			MAX-ACCESS read-only
			STATUS current
			DESCRIPTION
				"FDB elapsed time"
			::= { sleBridgePSFdbEntry 5 }

		
		sleBridgePSFdbControl OBJECT IDENTIFIER ::= { sleBridgePortSecurityFdb 2 }

		
		sleBridgePSFdbControlRequest OBJECT-TYPE
			SYNTAX INTEGER
				{
				createPSFedEntry(1),
				destroyPSFdbEntry(2),
				clearPSFdbEntry(3)
				}
			MAX-ACCESS read-write
			STATUS current
			DESCRIPTION
				"The request of a user command"
			::= { sleBridgePSFdbControl 1 }

		
		sleBridgePSFdbControlStatus OBJECT-TYPE
			SYNTAX SleControlStatusType
			MAX-ACCESS read-only
			STATUS current
			DESCRIPTION
				"The status of user command"
			::= { sleBridgePSFdbControl 2 }

		
		sleBridgePSFdbControlTimer OBJECT-TYPE
			SYNTAX Gauge32
			MAX-ACCESS read-write
			STATUS current
			DESCRIPTION
				"The maximum time for the manager for a long running user command"
			::= { sleBridgePSFdbControl 3 }

		
		sleBridgePSFdbControlTimeStamp OBJECT-TYPE
			SYNTAX TimeTicks
			MAX-ACCESS read-only
			STATUS current
			DESCRIPTION
				"The time stamp of the last command(end of command)"
			::= { sleBridgePSFdbControl 4 }

		
		sleBridgePSFdbControlReqResult OBJECT-TYPE
			SYNTAX SleControlRequestResultType
			MAX-ACCESS read-only
			STATUS current
			DESCRIPTION
				"The result of the last user command"
			::= { sleBridgePSFdbControl 5 }

		
		sleBridgePSFdbControlPort OBJECT-TYPE
			SYNTAX INTEGER (1..512)
			MAX-ACCESS read-write
			STATUS current
			DESCRIPTION
				"FDB port"
			::= { sleBridgePSFdbControl 6 }

		
		sleBridgePSFdbControlVid OBJECT-TYPE
			SYNTAX INTEGER (1..4094)
			MAX-ACCESS read-write
			STATUS current
			DESCRIPTION
				"FDB vlan index"
			::= { sleBridgePSFdbControl 7 }

		
		sleBridgePSFdbControlMacAddress OBJECT-TYPE
			SYNTAX OCTET STRING (SIZE (0..6))
			MAX-ACCESS read-write
			STATUS current
			DESCRIPTION
				"FDB MAC address"
			::= { sleBridgePSFdbControl 8 }

		
		sleBridgePSFdbNotification OBJECT IDENTIFIER ::= { sleBridgePortSecurityFdb 3 }

		
		sleBridgePSFdbEntryCreated NOTIFICATION-TYPE
			OBJECTS { sleBridgePSFdbControlRequest, sleBridgePSFdbControlTimeStamp, sleBridgePSFdbControlReqResult, sleBridgePSFdbControlPort, sleBridgePSFdbControlVid, 
				sleBridgePSFdbControlMacAddress }
			STATUS current
			DESCRIPTION 
				"Description."
			::= { sleBridgePSFdbNotification 1 }

		
		sleBridgePSFdbEntryDestroyed NOTIFICATION-TYPE
			OBJECTS { sleBridgePSFdbControlRequest, sleBridgePSFdbControlTimeStamp, sleBridgePSFdbControlReqResult, sleBridgePSFdbControlPort, sleBridgePSFdbControlVid, 
				sleBridgePSFdbControlMacAddress }
			STATUS current
			DESCRIPTION 
				"Description."
			::= { sleBridgePSFdbNotification 2 }

		
		sleBridgePSFdbEntryCleared NOTIFICATION-TYPE
			OBJECTS { sleBridgePSFdbControlRequest, sleBridgePSFdbControlTimeStamp, sleBridgePSFdbControlReqResult, sleBridgePSFdbControlPort, sleBridgePSFdbControlVid, 
				sleBridgePSFdbControlMacAddress }
			STATUS current
			DESCRIPTION 
				"Description."
			::= { sleBridgePSFdbNotification 3 }

		
		sleBridgeFloodGuard OBJECT IDENTIFIER ::= { sleBridge 24 }

		
		sleBridgeFGBase OBJECT IDENTIFIER ::= { sleBridgeFloodGuard 1 }

		
		sleBridgeFGBaseInfo OBJECT IDENTIFIER ::= { sleBridgeFGBase 1 }

		
		sleBridgeFGBaseCfgdEnabled OBJECT-TYPE
			SYNTAX INTEGER
				{
				enable(1),
				disable(2)
				}
			MAX-ACCESS read-only
			STATUS current
			DESCRIPTION
				"The CFG enabled
				1: enable
				2: disable
				"
			::= { sleBridgeFGBaseInfo 1 }

		
		sleBridgeFGBaseMfgdEnabled OBJECT-TYPE
			SYNTAX INTEGER
				{
				enable(1),
				disable(2)
				}
			MAX-ACCESS read-only
			STATUS current
			DESCRIPTION
				"The MFG enabled
				1: enable
				2: disable"
			::= { sleBridgeFGBaseInfo 2 }

		
		sleBridgeFGBaseSfgdEnabled OBJECT-TYPE
			SYNTAX INTEGER
				{
				enable(1),
				disable(2)
				}
			MAX-ACCESS read-only
			STATUS current
			DESCRIPTION
				"The SFG enabled
				1: enable
				2: disable"
			::= { sleBridgeFGBaseInfo 3 }

		
		sleBridgeFGBaseControl OBJECT IDENTIFIER ::= { sleBridgeFGBase 2 }

		
		sleBridgeFGBaseControlRequest OBJECT-TYPE
			SYNTAX INTEGER
				{
				setCfgdEnable(1),
				setSfgdEnable(2)
				}
			MAX-ACCESS read-write
			STATUS current
			DESCRIPTION
				"The request of a user command"
			::= { sleBridgeFGBaseControl 1 }

		
		sleBridgeFGBaseControlStatus OBJECT-TYPE
			SYNTAX SleControlStatusType
			MAX-ACCESS read-only
			STATUS current
			DESCRIPTION
				"The status of user command"
			::= { sleBridgeFGBaseControl 2 }

		
		sleBridgeFGBaseControlTimer OBJECT-TYPE
			SYNTAX Gauge32
			MAX-ACCESS read-write
			STATUS current
			DESCRIPTION
				"The maximum time for the manager for a long running user command"
			::= { sleBridgeFGBaseControl 3 }

		
		sleBridgeFGBaseControlTimeStamp OBJECT-TYPE
			SYNTAX TimeTicks
			MAX-ACCESS read-only
			STATUS current
			DESCRIPTION
				"The time stamp of the last command(end of command)"
			::= { sleBridgeFGBaseControl 4 }

		
		sleBridgeFGBaseControlReqResult OBJECT-TYPE
			SYNTAX SleControlRequestResultType
			MAX-ACCESS read-only
			STATUS current
			DESCRIPTION
				"The result of the last user command"
			::= { sleBridgeFGBaseControl 5 }

		
		sleBridgeFGBaseControlCfgdEnable OBJECT-TYPE
			SYNTAX INTEGER
				{
				enable(1),
				disable(2)
				}
			MAX-ACCESS read-write
			STATUS current
			DESCRIPTION
				"The CFG enabled
				1: enable
				2: disable"
			::= { sleBridgeFGBaseControl 6 }

		
		sleBridgeFGBaseControlSfgdEnable OBJECT-TYPE
			SYNTAX INTEGER
				{
				enable(1),
				disable(2)
				}
			MAX-ACCESS read-write
			STATUS current
			DESCRIPTION
				"The SFG enabled
				1: enable
				2: disable	"
			::= { sleBridgeFGBaseControl 7 }

		
		sleBridgeFGBaseNotification OBJECT IDENTIFIER ::= { sleBridgeFGBase 3 }

		
		sleBridgeFGBaseCfgdStatusChanged NOTIFICATION-TYPE
			OBJECTS { sleBridgeFGBaseControlRequest, sleBridgeFGBaseControlTimeStamp, sleBridgeFGBaseControlReqResult, sleBridgeFGBaseControlCfgdEnable }
			STATUS current
			DESCRIPTION 
				"Description."
			::= { sleBridgeFGBaseNotification 1 }

		
		sleBridgeFGBaseSfgdStatusChanged NOTIFICATION-TYPE
			OBJECTS { sleBridgeFGBaseControlRequest, sleBridgeFGBaseControlTimeStamp, sleBridgeFGBaseControlReqResult, sleBridgeFGBaseControlSfgdEnable }
			STATUS current
			DESCRIPTION 
				"Description."
			::= { sleBridgeFGBaseNotification 2 }

		
		sleBridgeFGPort OBJECT IDENTIFIER ::= { sleBridgeFloodGuard 2 }

		
		sleBridgeFGPortTable OBJECT-TYPE
			SYNTAX SEQUENCE OF SleBridgeFGPortEntry
			MAX-ACCESS not-accessible
			STATUS current
			DESCRIPTION
				"Description."
			::= { sleBridgeFGPort 1 }

		
		sleBridgeFGPortEntry OBJECT-TYPE
			SYNTAX SleBridgeFGPortEntry
			MAX-ACCESS not-accessible
			STATUS current
			DESCRIPTION
				"Description."
			INDEX { sleBridgePortIndex, sleBridgeFGPortType }
			::= { sleBridgeFGPortTable 1 }

		
		SleBridgeFGPortEntry ::=
			SEQUENCE { 
				sleBridgeFGPortType
					INTEGER,
				sleBridgeFGPortFrameType
					INTEGER,
				sleBridgeFGPortFrame
					INTEGER,
				sleBridgeFGPortBlocked
					INTEGER,
				sleBridgeFGPortTimer
					INTEGER
			 }

		sleBridgeFGPortType OBJECT-TYPE
			SYNTAX INTEGER
				{
				systemFloodGuard(1),
				cpuFloodGuard(2),
				macFloodGuard(3)
				}
			MAX-ACCESS read-only
			STATUS current
			DESCRIPTION
				"Flood guard port type
				1 : systemFloodGuard
				2 : cpuFloodGuard
				3 : macFloodGuard"
			::= { sleBridgeFGPortEntry 1 }

		
		sleBridgeFGPortFrameType OBJECT-TYPE
			SYNTAX INTEGER
				{
				none(0),
				multicast(1),
				broadcast(2),
				both(3),
				arp(4),
				dhcp(5),
				dlf(6),
				all(7)
				}
			MAX-ACCESS read-only
			STATUS current
			DESCRIPTION
				"Flood guard frame type
				0 : none
				1 : multicast
				2 : broadcast
				3 : both"
			::= { sleBridgeFGPortEntry 2 }

		
		sleBridgeFGPortFrame OBJECT-TYPE
			SYNTAX INTEGER (-1 | 1..2147483647)
			MAX-ACCESS read-only
			STATUS current
			DESCRIPTION
				"Flood guard frame"
			::= { sleBridgeFGPortEntry 3 }

		
		sleBridgeFGPortBlocked OBJECT-TYPE
			SYNTAX INTEGER
				{
				block(1),
				unblock(2)
				}
			MAX-ACCESS read-only
			STATUS current
			DESCRIPTION
				"Flood guard block status
				1 : block
				2 : unblock"
			::= { sleBridgeFGPortEntry 4 }

		
		sleBridgeFGPortTimer OBJECT-TYPE
			SYNTAX INTEGER (-1 | 10..3600)
			MAX-ACCESS read-only
			STATUS current
			DESCRIPTION
				"Flood guard timer"
			::= { sleBridgeFGPortEntry 5 }

		
		sleBridgeFGPortControl OBJECT IDENTIFIER ::= { sleBridgeFGPort 2 }

		
		sleBridgeFGPortControlRequest OBJECT-TYPE
			SYNTAX INTEGER
				{
				setFgPortProfile(1),
				setFgPortUnblock(2)
				}
			MAX-ACCESS read-write
			STATUS current
			DESCRIPTION
				"The request of a user command"
			::= { sleBridgeFGPortControl 1 }

		
		sleBridgeFGPortControlStatus OBJECT-TYPE
			SYNTAX SleControlStatusType
			MAX-ACCESS read-only
			STATUS current
			DESCRIPTION
				"The status of user command"
			::= { sleBridgeFGPortControl 2 }

		
		sleBridgeFGPortControlTimer OBJECT-TYPE
			SYNTAX Gauge32
			MAX-ACCESS read-only
			STATUS current
			DESCRIPTION
				"The maximum time for the manager for a long running user command"
			::= { sleBridgeFGPortControl 3 }

		
		sleBridgeFGPortControlTimeStamp OBJECT-TYPE
			SYNTAX TimeTicks
			MAX-ACCESS read-only
			STATUS current
			DESCRIPTION
				"The time stamp of the last command(end of command)"
			::= { sleBridgeFGPortControl 4 }

		
		sleBridgeFGPortControlReqResult OBJECT-TYPE
			SYNTAX SleControlRequestResultType
			MAX-ACCESS read-only
			STATUS current
			DESCRIPTION
				"The result of the last user command"
			::= { sleBridgeFGPortControl 5 }

		
		sleBridgeFGPortControlIndex OBJECT-TYPE
			SYNTAX Integer32
			MAX-ACCESS read-write
			STATUS current
			DESCRIPTION
				"Port index"
			::= { sleBridgeFGPortControl 6 }

		
		sleBridgeFGPortControlType OBJECT-TYPE
			SYNTAX INTEGER
				{
				systemfloodguard(1),
				cpufloodguard(2),
				macfloodguard(3)
				}
			MAX-ACCESS read-write
			STATUS current
			DESCRIPTION
				"Flood guard port type
				1 : systemFloodGuard
				2 : cpuFloodGuard
				3 : macFloodGuard"
			::= { sleBridgeFGPortControl 7 }

		
		sleBridgeFGPortControlFrameType OBJECT-TYPE
			SYNTAX INTEGER
				{
				none(0),
				multicast(1),
				broadcast(2),
				both(3),
				arp(4),
				dhcp(5),
				dlf(6),
				all(7)
				}
			MAX-ACCESS read-write
			STATUS current
			DESCRIPTION
				"Flood guard frame type
				0 : none
				1 : multicast
				2 : broadcast
				3 : both
				"
			::= { sleBridgeFGPortControl 8 }

		
		sleBridgeFGPortControlFrame OBJECT-TYPE
			SYNTAX INTEGER (-1 | 1..2147483647)
			MAX-ACCESS read-write
			STATUS current
			DESCRIPTION
				"Flood guard frame"
			::= { sleBridgeFGPortControl 9 }

		
		sleBridgeFGPortControlSetTimer OBJECT-TYPE
			SYNTAX INTEGER (-1 | 10..3600)
			MAX-ACCESS read-write
			STATUS current
			DESCRIPTION
				"Flood guard timer"
			::= { sleBridgeFGPortControl 10 }

		
		sleBridgeFGPortControlBlock OBJECT-TYPE
			SYNTAX INTEGER
				{
				block(1),
				unblock(2)
				}
			MAX-ACCESS read-write
			STATUS current
			DESCRIPTION
				"Flood guard block status
				1 : block
				2 : unblock"
			::= { sleBridgeFGPortControl 11 }

		
		sleBridgeFGPortNotification OBJECT IDENTIFIER ::= { sleBridgeFGPort 3 }

		
		sleBridgeFGPortProfileChanged NOTIFICATION-TYPE
			OBJECTS { sleBridgeFGPortControlReqResult, sleBridgeFGPortControlTimeStamp, sleBridgeFGPortControlRequest, sleBridgeFGPortControlIndex, sleBridgeFGPortControlType, 
				sleBridgeFGPortControlFrameType, sleBridgeFGPortControlFrame, sleBridgeFGPortControlSetTimer, sleBridgeFGPortControlBlock }
			STATUS current
			DESCRIPTION 
				"Description."
			::= { sleBridgeFGPortNotification 1 }

		
		sleBridgeFGPortUnblockChanged NOTIFICATION-TYPE
			OBJECTS { sleBridgeFGPortControlRequest, sleBridgeFGPortControlTimeStamp, sleBridgeFGPortControlReqResult, sleBridgeFGPortControlIndex, sleBridgeFGPortControlType
				 }
			STATUS current
			DESCRIPTION 
				"Description."
			::= { sleBridgeFGPortNotification 2 }

		
		sleBridgeVlanTranslation OBJECT IDENTIFIER ::= { sleBridge 25 }

		
		sleBridgeVTTable OBJECT-TYPE
			SYNTAX SEQUENCE OF SleBridgeVTEntry
			MAX-ACCESS not-accessible
			STATUS current
			DESCRIPTION
				"bridge vlan translation table."
			::= { sleBridgeVlanTranslation 1 }

		
		sleBridgeVTEntry OBJECT-TYPE
			SYNTAX SleBridgeVTEntry
			MAX-ACCESS not-accessible
			STATUS current
			DESCRIPTION
				"key: sleBridgeVTServiceId, sleBridgeVTSubscriberId"
			INDEX { sleBridgeVTServiceId, sleBridgeVTSubscriberId }
			::= { sleBridgeVTTable 1 }

		
		SleBridgeVTEntry ::=
			SEQUENCE { 
				sleBridgeVTServiceId
					INTEGER,
				sleBridgeVTSubscriberId
					INTEGER
			 }

		sleBridgeVTServiceId OBJECT-TYPE
			SYNTAX INTEGER (1..4094)
			MAX-ACCESS read-only
			STATUS current
			DESCRIPTION
				"Service Vlan Id"
			::= { sleBridgeVTEntry 1 }

		
		sleBridgeVTSubscriberId OBJECT-TYPE
			SYNTAX INTEGER (1..4094)
			MAX-ACCESS read-only
			STATUS current
			DESCRIPTION
				"Subscriber Vlan Id"
			::= { sleBridgeVTEntry 2 }

		
		sleBridgeVTRuleTable OBJECT-TYPE
			SYNTAX SEQUENCE OF SleBridgeVTRuleEntry
			MAX-ACCESS not-accessible
			STATUS current
			DESCRIPTION
				"bridge vlan translation rule table."
			::= { sleBridgeVlanTranslation 2 }

		
		sleBridgeVTRuleEntry OBJECT-TYPE
			SYNTAX SleBridgeVTRuleEntry
			MAX-ACCESS not-accessible
			STATUS current
			DESCRIPTION
				"key: sleBridgeVTRuleMac, sleBridgeVTRuleVid"
			INDEX { sleBridgeVTRuleMac, sleBridgeVTRuleVid }
			::= { sleBridgeVTRuleTable 1 }

		
		SleBridgeVTRuleEntry ::=
			SEQUENCE { 
				sleBridgeVTRuleMac
					MacAddress,
				sleBridgeVTRuleVid
					INTEGER,
				sleBridgeVTRuleRDirVid
					INTEGER,
				sleBridgeVTRuleRDirPort
					Integer32,
				sleBridgeVTRuleStatus
					INTEGER
			 }

		sleBridgeVTRuleMac OBJECT-TYPE
			SYNTAX MacAddress
			MAX-ACCESS read-only
			STATUS current
			DESCRIPTION
				"sleBridgeVTRuleMac, sleBridgeVTRuleVid"
			::= { sleBridgeVTRuleEntry 1 }

		
		sleBridgeVTRuleVid OBJECT-TYPE
			SYNTAX INTEGER (1..4094)
			MAX-ACCESS read-only
			STATUS current
			DESCRIPTION
				"Original packet Vid"
			::= { sleBridgeVTRuleEntry 2 }

		
		sleBridgeVTRuleRDirVid OBJECT-TYPE
			SYNTAX INTEGER (1..4094)
			MAX-ACCESS read-only
			STATUS current
			DESCRIPTION
				"Output port"
			::= { sleBridgeVTRuleEntry 3 }

		
		sleBridgeVTRuleRDirPort OBJECT-TYPE
			SYNTAX Integer32
			MAX-ACCESS read-only
			STATUS current
			DESCRIPTION
				"Output Vid"
			::= { sleBridgeVTRuleEntry 4 }

		
		sleBridgeVTRuleStatus OBJECT-TYPE
			SYNTAX INTEGER
				{
				static(1),
				dynamic(2)
				}
			MAX-ACCESS read-only
			STATUS current
			DESCRIPTION
				"Vlan Translation rule status"
			::= { sleBridgeVTRuleEntry 5 }

		
		sleBridgeVTControl OBJECT IDENTIFIER ::= { sleBridgeVlanTranslation 3 }

		
		sleBridgeVTControlRequest OBJECT-TYPE
			SYNTAX INTEGER
				{
				setVT(1),
				clearVT(2)
				}
			MAX-ACCESS read-write
			STATUS current
			DESCRIPTION
				"The request of a user command."
			::= { sleBridgeVTControl 1 }

		
		sleBridgeVTControlStatus OBJECT-TYPE
			SYNTAX SleControlStatusType
			MAX-ACCESS read-only
			STATUS current
			DESCRIPTION
				"The status of a user command."
			::= { sleBridgeVTControl 2 }

		
		sleBridgeVTControlTimer OBJECT-TYPE
			SYNTAX Gauge32
			MAX-ACCESS read-write
			STATUS current
			DESCRIPTION
				"The maximum wait time for the manager for a long running user command."
			::= { sleBridgeVTControl 3 }

		
		sleBridgeVTControlTimeStamp OBJECT-TYPE
			SYNTAX TimeTicks
			MAX-ACCESS read-only
			STATUS current
			DESCRIPTION
				"The time stamp of the last command (end of command)."
			::= { sleBridgeVTControl 4 }

		
		sleBridgeVTControlReqResult OBJECT-TYPE
			SYNTAX SleControlRequestResultType
			MAX-ACCESS read-only
			STATUS current
			DESCRIPTION
				"The result of the last user command."
			::= { sleBridgeVTControl 5 }

		
		sleBridgeVTControlServerId OBJECT-TYPE
			SYNTAX INTEGER (1..4094)
			MAX-ACCESS read-write
			STATUS current
			DESCRIPTION
				"Network Interface Index."
			::= { sleBridgeVTControl 6 }

		
		sleBridgeVTControlClientId OBJECT-TYPE
			SYNTAX INTEGER (1..4094)
			MAX-ACCESS read-write
			STATUS current
			DESCRIPTION
				"Network Interface Index."
			::= { sleBridgeVTControl 7 }

		
		sleBridgeVTNotification OBJECT IDENTIFIER ::= { sleBridgeVlanTranslation 4 }

		
		sleBridgeVTSet NOTIFICATION-TYPE
			OBJECTS { sleBridgeVTControlRequest, sleBridgeVTControlTimeStamp, sleBridgeVTControlServerId, sleBridgeVTControlClientId, sleBridgeVTControlReqResult
				 }
			STATUS current
			DESCRIPTION 
				"Description."
			::= { sleBridgeVTNotification 1 }

		
		sleBridgeVTClear NOTIFICATION-TYPE
			OBJECTS { sleBridgeVTControlRequest, sleBridgeVTControlTimeStamp, sleBridgeVTControlServerId, sleBridgeVTControlClientId, sleBridgeVTControlReqResult
				 }
			STATUS current
			DESCRIPTION 
				"Description."
			::= { sleBridgeVTNotification 2 }

		
		sleBridgeInBoundVTTable OBJECT-TYPE
			SYNTAX SEQUENCE OF SleBridgeInBoundVTEntry
			MAX-ACCESS not-accessible
			STATUS current
			DESCRIPTION
				"bridge inbound vlan translation table."
			::= { sleBridgeVlanTranslation 5 }

		
		sleBridgeInBoundVTEntry OBJECT-TYPE
			SYNTAX SleBridgeInBoundVTEntry
			MAX-ACCESS not-accessible
			STATUS current
			DESCRIPTION
				"key: sleBridgeInBoundVTPortIndex, sleBridgeInBoundVTVlanIndex"
			INDEX { sleBridgeInBoundVTPortIndex, sleBridgeInBoundVTVlanIndex }
			::= { sleBridgeInBoundVTTable 1 }

		
		SleBridgeInBoundVTEntry ::=
			SEQUENCE { 
				sleBridgeInBoundVTPortIndex
					INTEGER,
				sleBridgeInBoundVTVlanIndex
					Integer32,
				sleBridgeInBoundVTNewVid
					Integer32,
				sleBridgeInBoundVTOperStatus
					INTEGER
			 }

		sleBridgeInBoundVTPortIndex OBJECT-TYPE
			SYNTAX INTEGER (0..512)
			MAX-ACCESS read-only
			STATUS current
			DESCRIPTION
				"Port Index."
			::= { sleBridgeInBoundVTEntry 1 }

		
		sleBridgeInBoundVTVlanIndex OBJECT-TYPE
			SYNTAX Integer32 (0..65535)
			MAX-ACCESS read-only
			STATUS current
			DESCRIPTION
				"Vlan Index."
			::= { sleBridgeInBoundVTEntry 2 }

		
		sleBridgeInBoundVTNewVid OBJECT-TYPE
			SYNTAX Integer32
			MAX-ACCESS read-only
			STATUS current
			DESCRIPTION
				"New VID."
			::= { sleBridgeInBoundVTEntry 3 }

		
		sleBridgeInBoundVTOperStatus OBJECT-TYPE
			SYNTAX INTEGER
				{
				on(1),
				off(2)
				}
			MAX-ACCESS read-only
			STATUS current
			DESCRIPTION
				"The operational status of InBound Vlan Translation."
			::= { sleBridgeInBoundVTEntry 4 }

		
		sleBridgeInBoundVTControl OBJECT IDENTIFIER ::= { sleBridgeVlanTranslation 6 }

		
		sleBridgeInBoundVTControlRequest OBJECT-TYPE
			SYNTAX INTEGER
				{
				setInBoundVT(1),
				clearInBoundVT(2)
				}
			MAX-ACCESS read-write
			STATUS current
			DESCRIPTION
				"The request of a user command."
			::= { sleBridgeInBoundVTControl 1 }

		
		sleBridgeInBoundVTControlStatus OBJECT-TYPE
			SYNTAX SleControlStatusType
			MAX-ACCESS read-only
			STATUS current
			DESCRIPTION
				"The status of a user command."
			::= { sleBridgeInBoundVTControl 2 }

		
		sleBridgeInBoundVTControlTimer OBJECT-TYPE
			SYNTAX Gauge32
			MAX-ACCESS read-write
			STATUS current
			DESCRIPTION
				"The maximum wait time for the manager for a long running user command."
			::= { sleBridgeInBoundVTControl 3 }

		
		sleBridgeInBoundVTControlTimeStamp OBJECT-TYPE
			SYNTAX TimeTicks
			MAX-ACCESS read-only
			STATUS current
			DESCRIPTION
				"The time stamp of the last command (end of command)."
			::= { sleBridgeInBoundVTControl 4 }

		
		sleBridgeInBoundVTControlReqResult OBJECT-TYPE
			SYNTAX SleControlRequestResultType
			MAX-ACCESS read-only
			STATUS current
			DESCRIPTION
				"The result of the last user command."
			::= { sleBridgeInBoundVTControl 5 }

		
		sleBridgeInBoundVTControlPortIndex OBJECT-TYPE
			SYNTAX Integer32
			MAX-ACCESS read-write
			STATUS current
			DESCRIPTION
				"Port Index."
			::= { sleBridgeInBoundVTControl 6 }

		
		sleBridgeInBoundVTControlVlanIndex OBJECT-TYPE
			SYNTAX Integer32
			MAX-ACCESS read-write
			STATUS current
			DESCRIPTION
				"Vlan Index."
			::= { sleBridgeInBoundVTControl 7 }

		
		sleBridgeInBoundVTControlNewVid OBJECT-TYPE
			SYNTAX Integer32
			MAX-ACCESS read-write
			STATUS current
			DESCRIPTION
				"New VID."
			::= { sleBridgeInBoundVTControl 8 }

		
		sleBridgeInBoundVTNotification OBJECT IDENTIFIER ::= { sleBridgeVlanTranslation 7 }

		
		sleBridgeInBoundVTSet NOTIFICATION-TYPE
			OBJECTS { sleBridgeInBoundVTControlRequest, sleBridgeInBoundVTControlTimeStamp, sleBridgeInBoundVTControlReqResult, sleBridgeInBoundVTControlPortIndex, sleBridgeInBoundVTControlVlanIndex, 
				sleBridgeInBoundVTControlNewVid }
			STATUS current
			DESCRIPTION 
				"Description."
			::= { sleBridgeInBoundVTNotification 1 }

		
		sleBridgeInBoundVTClear NOTIFICATION-TYPE
			OBJECTS { sleBridgeInBoundVTControlRequest, sleBridgeInBoundVTControlTimeStamp, sleBridgeInBoundVTControlReqResult, sleBridgeInBoundVTControlPortIndex, sleBridgeInBoundVTControlVlanIndex
				 }
			STATUS current
			DESCRIPTION 
				"Description."
			::= { sleBridgeInBoundVTNotification 2 }

		
		sleBridgeOutBoundVTTable OBJECT-TYPE
			SYNTAX SEQUENCE OF SleBridgeOutBoundVTEntry
			MAX-ACCESS not-accessible
			STATUS current
			DESCRIPTION
				"bridge outbound vlan translation table."
			::= { sleBridgeVlanTranslation 8 }

		
		sleBridgeOutBoundVTEntry OBJECT-TYPE
			SYNTAX SleBridgeOutBoundVTEntry
			MAX-ACCESS not-accessible
			STATUS current
			DESCRIPTION
				"key: sleBridgeOutBoundVTPortIndex, sleBridgeOutBoundVTVlanIndex"
			INDEX { sleBridgeOutBoundVTPortIndex, sleBridgeOutBoundVTVlanIndex }
			::= { sleBridgeOutBoundVTTable 1 }

		
		SleBridgeOutBoundVTEntry ::=
			SEQUENCE { 
				sleBridgeOutBoundVTPortIndex
					INTEGER,
				sleBridgeOutBoundVTVlanIndex
					Integer32,
				sleBridgeOutBoundVTNewVid
					Integer32,
				sleBridgeOutBoundVTOperStatus
					INTEGER
			 }

		sleBridgeOutBoundVTPortIndex OBJECT-TYPE
			SYNTAX INTEGER (0..512)
			MAX-ACCESS read-only
			STATUS current
			DESCRIPTION
				"Port Index."
			::= { sleBridgeOutBoundVTEntry 1 }

		
		sleBridgeOutBoundVTVlanIndex OBJECT-TYPE
			SYNTAX Integer32 (0..65535)
			MAX-ACCESS read-only
			STATUS current
			DESCRIPTION
				"Vlan Index."
			::= { sleBridgeOutBoundVTEntry 2 }

		
		sleBridgeOutBoundVTNewVid OBJECT-TYPE
			SYNTAX Integer32
			MAX-ACCESS read-only
			STATUS current
			DESCRIPTION
				"New VID."
			::= { sleBridgeOutBoundVTEntry 3 }

		
		sleBridgeOutBoundVTOperStatus OBJECT-TYPE
			SYNTAX INTEGER
				{
				on(1),
				off(2)
				}
			MAX-ACCESS read-only
			STATUS current
			DESCRIPTION
				"The operational status of InBound Vlan Translation."
			::= { sleBridgeOutBoundVTEntry 4 }

		
		sleBridgeOutBoundVTControl OBJECT IDENTIFIER ::= { sleBridgeVlanTranslation 9 }

		
		sleBridgeOutBoundVTControlRequest OBJECT-TYPE
			SYNTAX INTEGER
				{
				setOutBoundVT(1),
				clearOutBoundVT(2)
				}
			MAX-ACCESS read-write
			STATUS current
			DESCRIPTION
				"The request of a user command."
			::= { sleBridgeOutBoundVTControl 1 }

		
		sleBridgeOutBoundVTControlStatus OBJECT-TYPE
			SYNTAX SleControlStatusType
			MAX-ACCESS read-only
			STATUS current
			DESCRIPTION
				"The status of a user command."
			::= { sleBridgeOutBoundVTControl 2 }

		
		sleBridgeOutBoundVTControlTimer OBJECT-TYPE
			SYNTAX Gauge32
			MAX-ACCESS read-write
			STATUS current
			DESCRIPTION
				"The maximum wait time for the manager for a long running user command."
			::= { sleBridgeOutBoundVTControl 3 }

		
		sleBridgeOutBoundVTControlTimeStamp OBJECT-TYPE
			SYNTAX TimeTicks
			MAX-ACCESS read-only
			STATUS current
			DESCRIPTION
				"The time stamp of the last command (end of command)."
			::= { sleBridgeOutBoundVTControl 4 }

		
		sleBridgeOutBoundVTControlReqResult OBJECT-TYPE
			SYNTAX SleControlRequestResultType
			MAX-ACCESS read-only
			STATUS current
			DESCRIPTION
				"The result of the last user command."
			::= { sleBridgeOutBoundVTControl 5 }

		
		sleBridgeOutBoundVTControlPortIndex OBJECT-TYPE
			SYNTAX Integer32
			MAX-ACCESS read-write
			STATUS current
			DESCRIPTION
				"Port Index."
			::= { sleBridgeOutBoundVTControl 6 }

		
		sleBridgeOutBoundVTControlVlanIndex OBJECT-TYPE
			SYNTAX Integer32
			MAX-ACCESS read-write
			STATUS current
			DESCRIPTION
				"Vlan Index."
			::= { sleBridgeOutBoundVTControl 7 }

		
		sleBridgeOutBoundVTControlNewVid OBJECT-TYPE
			SYNTAX Integer32
			MAX-ACCESS read-write
			STATUS current
			DESCRIPTION
				"New VID."
			::= { sleBridgeOutBoundVTControl 8 }

		
		sleBridgeOutBoundVTNotification OBJECT IDENTIFIER ::= { sleBridgeVlanTranslation 10 }

		
		sleBridgeOutBoundVTSet NOTIFICATION-TYPE
			OBJECTS { sleBridgeOutBoundVTControlRequest, sleBridgeOutBoundVTControlTimeStamp, sleBridgeOutBoundVTControlReqResult, sleBridgeOutBoundVTControlPortIndex, sleBridgeOutBoundVTControlVlanIndex, 
				sleBridgeOutBoundVTControlNewVid }
			STATUS current
			DESCRIPTION 
				"Description."
			::= { sleBridgeOutBoundVTNotification 1 }

		
		sleBridgeOutBoundVTClear NOTIFICATION-TYPE
			OBJECTS { sleBridgeOutBoundVTControlRequest, sleBridgeOutBoundVTControlTimeStamp, sleBridgeOutBoundVTControlReqResult, sleBridgeOutBoundVTControlPortIndex, sleBridgeOutBoundVTControlVlanIndex
				 }
			STATUS current
			DESCRIPTION 
				"Description."
			::= { sleBridgeOutBoundVTNotification 2 }

		
		sleBridgeGarp OBJECT IDENTIFIER ::= { sleBridge 26 }

		
		sleBridgeGarpBase OBJECT IDENTIFIER ::= { sleBridgeGarp 1 }

		
		sleBridgeGarpBaseInfo OBJECT IDENTIFIER ::= { sleBridgeGarpBase 1 }

		
		sleBridgeGvrpStatus OBJECT-TYPE
			SYNTAX INTEGER
				{
				enable(1),
				disable(2)
				}
			MAX-ACCESS read-only
			STATUS current
			DESCRIPTION
				"Global GVRP status"
			::= { sleBridgeGarpBaseInfo 1 }

		
		sleBridgeGmrpStatus OBJECT-TYPE
			SYNTAX INTEGER
				{
				enable(1),
				disable(2)
				}
			MAX-ACCESS read-only
			STATUS current
			DESCRIPTION
				"Global GMRP status"
			::= { sleBridgeGarpBaseInfo 2 }

		
		sleBridgeGarpTimerJoin OBJECT-TYPE
			SYNTAX Integer32
			MAX-ACCESS read-only
			STATUS current
			DESCRIPTION
				"Global Join Timer"
			::= { sleBridgeGarpBaseInfo 3 }

		
		sleBridgeGarpTimerLeave OBJECT-TYPE
			SYNTAX Integer32
			MAX-ACCESS read-only
			STATUS current
			DESCRIPTION
				"Global Leave Timer"
			::= { sleBridgeGarpBaseInfo 4 }

		
		sleBridgeGarpTimerLeaveAll OBJECT-TYPE
			SYNTAX Integer32
			MAX-ACCESS read-only
			STATUS current
			DESCRIPTION
				"Global LeaveAll Timer"
			::= { sleBridgeGarpBaseInfo 5 }

		
		sleBridgeGarpBaseControl OBJECT IDENTIFIER ::= { sleBridgeGarpBase 2 }

		
		sleBridgeGarpBaseControlRequest OBJECT-TYPE
			SYNTAX INTEGER
				{
				setGarpStatus(1),
				setGarpTimer(2)
				}
			MAX-ACCESS read-write
			STATUS current
			DESCRIPTION
				"The request of a user command"
			::= { sleBridgeGarpBaseControl 1 }

		
		sleBridgeGarpBaseControlStatus OBJECT-TYPE
			SYNTAX SleControlStatusType
			MAX-ACCESS read-only
			STATUS current
			DESCRIPTION
				"The status of user command"
			::= { sleBridgeGarpBaseControl 2 }

		
		sleBridgeGarpBaseControlTimer OBJECT-TYPE
			SYNTAX Gauge32
			MAX-ACCESS read-write
			STATUS current
			DESCRIPTION
				"The maximum time for the manager for a long running user command"
			::= { sleBridgeGarpBaseControl 3 }

		
		sleBridgeGarpBaseControlTimeStamp OBJECT-TYPE
			SYNTAX TimeTicks
			MAX-ACCESS read-only
			STATUS current
			DESCRIPTION
				"The time stamp of the last command(end of command)"
			::= { sleBridgeGarpBaseControl 4 }

		
		sleBridgeGarpBaseControlReqResult OBJECT-TYPE
			SYNTAX SleControlRequestResultType
			MAX-ACCESS read-only
			STATUS current
			DESCRIPTION
				"The result of the last user command"
			::= { sleBridgeGarpBaseControl 5 }

		
		sleBridgeGarpBaseControlGvrpStatus OBJECT-TYPE
			SYNTAX INTEGER
				{
				enable(1),
				disable(2)
				}
			MAX-ACCESS read-write
			STATUS current
			DESCRIPTION
				"Global GVRP status"
			::= { sleBridgeGarpBaseControl 6 }

		
		sleBridgeGarpBaseControlGmrpStatus OBJECT-TYPE
			SYNTAX INTEGER
				{
				enable(1),
				disable(2)
				}
			MAX-ACCESS read-write
			STATUS current
			DESCRIPTION
				"Global GMRP status"
			::= { sleBridgeGarpBaseControl 7 }

		
		sleBridgeGarpBaseControlTimerJoin OBJECT-TYPE
			SYNTAX Integer32
			MAX-ACCESS read-write
			STATUS current
			DESCRIPTION
				"Global Join Timer"
			::= { sleBridgeGarpBaseControl 8 }

		
		sleBridgeGarpBaseControlTimerLeave OBJECT-TYPE
			SYNTAX Integer32
			MAX-ACCESS read-write
			STATUS current
			DESCRIPTION
				"Global Leave Timer"
			::= { sleBridgeGarpBaseControl 9 }

		
		sleBridgeGarpBaseControlTimerLeaveAll OBJECT-TYPE
			SYNTAX Integer32
			MAX-ACCESS read-write
			STATUS current
			DESCRIPTION
				"Global LeaveAll Timer"
			::= { sleBridgeGarpBaseControl 10 }

		
		sleBridgeGarpBaseNotification OBJECT IDENTIFIER ::= { sleBridgeGarpBase 3 }

		
		sleBridgeGarpStatusChanged NOTIFICATION-TYPE
			OBJECTS { sleBridgeGarpBaseControlRequest, sleBridgeGarpBaseControlTimeStamp, sleBridgeGarpBaseControlReqResult, sleBridgeGarpBaseControlGvrpStatus, sleBridgeGarpBaseControlGmrpStatus
				 }
			STATUS current
			DESCRIPTION 
				"Description."
			::= { sleBridgeGarpBaseNotification 1 }

		
		sleBridgeGarpTimerChanged NOTIFICATION-TYPE
			OBJECTS { sleBridgeGarpBaseControlRequest, sleBridgeGarpBaseControlTimeStamp, sleBridgeGarpBaseControlReqResult, sleBridgeGarpBaseControlTimerJoin, sleBridgeGarpBaseControlTimerLeave, 
				sleBridgeGarpBaseControlTimerLeaveAll }
			STATUS current
			DESCRIPTION 
				"Description."
			::= { sleBridgeGarpBaseNotification 2 }

		
		sleBridgeGarpApplication OBJECT IDENTIFIER ::= { sleBridgeGarp 2 }

		
		sleBridgeGarpAppPortTable OBJECT-TYPE
			SYNTAX SEQUENCE OF SleBridgeGarpAppPortEntry
			MAX-ACCESS not-accessible
			STATUS current
			DESCRIPTION
				"bridge GARP application port table."
			::= { sleBridgeGarpApplication 1 }

		
		sleBridgeGarpAppPortEntry OBJECT-TYPE
			SYNTAX SleBridgeGarpAppPortEntry
			MAX-ACCESS not-accessible
			STATUS current
			DESCRIPTION
				"key: sleBridgeGarpAppPortIndex, sleBridgeGarpAppPortType"
			INDEX { sleBridgeGarpAppPortIndex, sleBridgeGarpAppPortType }
			::= { sleBridgeGarpAppPortTable 1 }

		
		SleBridgeGarpAppPortEntry ::=
			SEQUENCE { 
				sleBridgeGarpAppPortIndex
					INTEGER,
				sleBridgeGarpAppPortType
					INTEGER,
				sleBridgeGarpAppPortStatus
					INTEGER,
				sleBridgeGarpAppPortFailedRegistrations
					Integer32,
				sleBridgeGarpAppPortLastPduOrigin
					OCTET STRING,
				sleBridgeGarpAppPortRegistration
					INTEGER,
				sleBridgeGarpAppPortApplicant
					INTEGER,
				sleBridgeGarpAppPortFwdAll
					INTEGER,
				sleBridgeGarpAppPortTimerJoin
					Integer32,
				sleBridgeGarpAppPortTimerLeave
					Integer32,
				sleBridgeGarpAppPortTimerLeaveAll
					Integer32
			 }

		sleBridgeGarpAppPortIndex OBJECT-TYPE
			SYNTAX INTEGER (1..65535)
			MAX-ACCESS read-only
			STATUS current
			DESCRIPTION
				"Port index.  Same as ifindex."
			::= { sleBridgeGarpAppPortEntry 1 }

		
		sleBridgeGarpAppPortType OBJECT-TYPE
			SYNTAX INTEGER
				{
				gvrp(1),
				gmrp(2)
				}
			MAX-ACCESS read-only
			STATUS current
			DESCRIPTION
				"GARP Application Type.
				Supports GVRP, GMRP 
				"
			::= { sleBridgeGarpAppPortEntry 2 }

		
		sleBridgeGarpAppPortStatus OBJECT-TYPE
			SYNTAX INTEGER
				{
				enable(1),
				disable(2)
				}
			MAX-ACCESS read-only
			STATUS current
			DESCRIPTION
				"GARP Application port status
				1 : enable
				2 : disable"
			::= { sleBridgeGarpAppPortEntry 3 }

		
		sleBridgeGarpAppPortFailedRegistrations OBJECT-TYPE
			SYNTAX Integer32
			MAX-ACCESS read-only
			STATUS current
			DESCRIPTION
				"The current value of the Failed Registrations counter maintained for a GARP Attribute type."
			::= { sleBridgeGarpAppPortEntry 4 }

		
		sleBridgeGarpAppPortLastPduOrigin OBJECT-TYPE
			SYNTAX OCTET STRING (SIZE (1..6))
			MAX-ACCESS read-only
			STATUS current
			DESCRIPTION
				"MAC Address of the last pdu that caused a state change for a given GARP Attribute."
			::= { sleBridgeGarpAppPortEntry 5 }

		
		sleBridgeGarpAppPortRegistration OBJECT-TYPE
			SYNTAX INTEGER
				{
				nomal(1),
				fixed(2),
				forbidden(3)
				}
			MAX-ACCESS read-only
			STATUS current
			DESCRIPTION
				"GARP registration mode."
			::= { sleBridgeGarpAppPortEntry 6 }

		
		sleBridgeGarpAppPortApplicant OBJECT-TYPE
			SYNTAX INTEGER
				{
				participant(1),
				nonParticipant(2)
				}
			MAX-ACCESS read-only
			STATUS current
			DESCRIPTION
				"Applicant type
				1: Transmissible PDU
				2: Untransmissible PDU
				"
			::= { sleBridgeGarpAppPortEntry 7 }

		
		sleBridgeGarpAppPortFwdAll OBJECT-TYPE
			SYNTAX INTEGER
				{
				enable(1),
				disable(2)
				}
			MAX-ACCESS read-only
			STATUS current
			DESCRIPTION
				"GMRP forward all registered-groups."
			::= { sleBridgeGarpAppPortEntry 8 }

		
		sleBridgeGarpAppPortTimerJoin OBJECT-TYPE
			SYNTAX Integer32
			MAX-ACCESS read-only
			STATUS current
			DESCRIPTION
				"GARP Application port timer join"
			::= { sleBridgeGarpAppPortEntry 9 }

		
		sleBridgeGarpAppPortTimerLeave OBJECT-TYPE
			SYNTAX Integer32
			MAX-ACCESS read-only
			STATUS current
			DESCRIPTION
				"GARP Application port timer leave"
			::= { sleBridgeGarpAppPortEntry 10 }

		
		sleBridgeGarpAppPortTimerLeaveAll OBJECT-TYPE
			SYNTAX Integer32
			MAX-ACCESS read-only
			STATUS current
			DESCRIPTION
				"GARP Application port timer leave all"
			::= { sleBridgeGarpAppPortEntry 11 }

		
		sleBridgeGarpAppPortControl OBJECT IDENTIFIER ::= { sleBridgeGarpApplication 2 }

		
		sleBridgeGarpAppPortControlRequest OBJECT-TYPE
			SYNTAX INTEGER
				{
				setGarpAppStatus(1),
				setGarpAppProfile(2)
				}
			MAX-ACCESS read-write
			STATUS current
			DESCRIPTION
				"The request of a user command"
			::= { sleBridgeGarpAppPortControl 1 }

		
		sleBridgeGarpAppPortControlStatus OBJECT-TYPE
			SYNTAX SleControlStatusType
			MAX-ACCESS read-only
			STATUS current
			DESCRIPTION
				"The status of user command"
			::= { sleBridgeGarpAppPortControl 2 }

		
		sleBridgeGarpAppPortControlTimer OBJECT-TYPE
			SYNTAX Gauge32
			MAX-ACCESS read-write
			STATUS current
			DESCRIPTION
				"The maximum time for the manager for a long running user command"
			::= { sleBridgeGarpAppPortControl 3 }

		
		sleBridgeGarpAppPortControlTimeStamp OBJECT-TYPE
			SYNTAX TimeTicks
			MAX-ACCESS read-only
			STATUS current
			DESCRIPTION
				"The time stamp of the last command(end of command)"
			::= { sleBridgeGarpAppPortControl 4 }

		
		sleBridgeGarpAppPortControlReqResult OBJECT-TYPE
			SYNTAX SleControlRequestResultType
			MAX-ACCESS read-only
			STATUS current
			DESCRIPTION
				"The result of the last user command"
			::= { sleBridgeGarpAppPortControl 5 }

		
		sleBridgeGarpAppPortControlIndex OBJECT-TYPE
			SYNTAX INTEGER (1..65535)
			MAX-ACCESS read-write
			STATUS current
			DESCRIPTION
				"Port index.  Same as ifindex."
			::= { sleBridgeGarpAppPortControl 6 }

		
		sleBridgeGarpAppPortControlType OBJECT-TYPE
			SYNTAX INTEGER
				{
				gvrp(1),
				gmrp(2)
				}
			MAX-ACCESS read-write
			STATUS current
			DESCRIPTION
				"GARP Application Type.
				Supports GVRP, GMRP"
			::= { sleBridgeGarpAppPortControl 7 }

		
		sleBridgeGarpAppPortControlPortStatus OBJECT-TYPE
			SYNTAX INTEGER
				{
				enable(1),
				disable(2)
				}
			MAX-ACCESS read-write
			STATUS current
			DESCRIPTION
				"GARP Application port status
				1 : enable
				2 : disable
				"
			::= { sleBridgeGarpAppPortControl 8 }

		
		sleBridgeGarpAppPortControlRegistration OBJECT-TYPE
			SYNTAX INTEGER
				{
				nomal(1),
				fixed(2),
				forbidden(3)
				}
			MAX-ACCESS read-write
			STATUS current
			DESCRIPTION
				"The current value of the Failed Registrations counter maintained for a GARP Attribute type."
			::= { sleBridgeGarpAppPortControl 9 }

		
		sleBridgeGarpAppPortControlApplicant OBJECT-TYPE
			SYNTAX INTEGER
				{
				participant(1),
				nonPorticipant(2)
				}
			MAX-ACCESS read-write
			STATUS current
			DESCRIPTION
				"Applicant type
				1: Transmissible PDU
				2: Untransmissible PDU"
			::= { sleBridgeGarpAppPortControl 10 }

		
		sleBridgeGarpAppPortControlFwdAll OBJECT-TYPE
			SYNTAX INTEGER
				{
				enable(1),
				disable(2)
				}
			MAX-ACCESS read-write
			STATUS current
			DESCRIPTION
				"Applicant type
				1: Transmissible PDU
				2: Untransmissible PDU
				"
			::= { sleBridgeGarpAppPortControl 11 }

		
		sleBridgeGarpAppPortControlTimerJoin OBJECT-TYPE
			SYNTAX Integer32
			MAX-ACCESS read-write
			STATUS current
			DESCRIPTION
				"GARP Application port timer join"
			::= { sleBridgeGarpAppPortControl 12 }

		
		sleBridgeGarpAppPortControlTimerLeave OBJECT-TYPE
			SYNTAX Integer32
			MAX-ACCESS read-write
			STATUS current
			DESCRIPTION
				"GARP Application port timer leave"
			::= { sleBridgeGarpAppPortControl 13 }

		
		sleBridgeGarpAppPortControlTimerLeaveAll OBJECT-TYPE
			SYNTAX Integer32
			MAX-ACCESS read-write
			STATUS current
			DESCRIPTION
				"GARP Application port timer leave all"
			::= { sleBridgeGarpAppPortControl 14 }

		
		sleBridgeGarpAppPortNotification OBJECT IDENTIFIER ::= { sleBridgeGarpApplication 3 }

		
		sleBridgeGarpAppPortStatusChanged NOTIFICATION-TYPE
			OBJECTS { sleBridgeGarpAppPortControlRequest, sleBridgeGarpAppPortControlTimeStamp, sleBridgeGarpAppPortControlReqResult, sleBridgeGarpAppPortControlIndex, sleBridgeGarpAppPortControlType, 
				sleBridgeGarpAppPortControlPortStatus }
			STATUS current
			DESCRIPTION 
				"Description."
			::= { sleBridgeGarpAppPortNotification 1 }

		
		sleBridgeGarpAppPortProfileChanged NOTIFICATION-TYPE
			OBJECTS { sleBridgeGarpAppPortControlRequest, sleBridgeGarpAppPortControlTimeStamp, sleBridgeGarpAppPortControlReqResult, sleBridgeGarpAppPortControlIndex, sleBridgeGarpAppPortControlType, 
				sleBridgeGarpAppPortControlRegistration, sleBridgeGarpAppPortControlApplicant, sleBridgeGarpAppPortControlFwdAll, sleBridgeGarpAppPortControlTimerJoin, sleBridgeGarpAppPortControlTimerLeave, 
				sleBridgeGarpAppPortControlTimerLeaveAll }
			STATUS current
			DESCRIPTION 
				"Description."
			::= { sleBridgeGarpAppPortNotification 2 }

		
		sleBridgeGarpStats OBJECT IDENTIFIER ::= { sleBridgeGarp 3 }

		
		sleBridgeGarpStatsTable OBJECT-TYPE
			SYNTAX SEQUENCE OF SleBridgeGarpStatsEntry
			MAX-ACCESS not-accessible
			STATUS current
			DESCRIPTION
				"bridge GARP stats table"
			::= { sleBridgeGarpStats 1 }

		
		sleBridgeGarpStatsEntry OBJECT-TYPE
			SYNTAX SleBridgeGarpStatsEntry
			MAX-ACCESS not-accessible
			STATUS current
			DESCRIPTION
				"key: sleBridgeGarpAppPortIndex, sleBridgeGarpAppPortType"
			INDEX { sleBridgeGarpAppPortIndex, sleBridgeGarpAppPortType }
			::= { sleBridgeGarpStatsTable 1 }

		
		SleBridgeGarpStatsEntry ::=
			SEQUENCE { 
				sleBridgeGarpStatsJoinEmptyReceived
					Integer32,
				sleBridgeGarpStatsJoinInReceived
					Integer32,
				sleBridgeGarpStatsEmptyReceived
					Integer32,
				sleBridgeGarpStatsLeaveInReceived
					Integer32,
				sleBridgeGarpStatsLeaveEmptyReceived
					Integer32,
				sleBridgeGarpStatsLeaveAllReceived
					Integer32,
				sleBridgeGarpStatsJoinEmptyTransmitted
					Integer32,
				sleBridgeGarpStatsJoinInTransmitted
					Integer32,
				sleBridgeGarpStatsEmptyTransmitted
					Integer32,
				sleBridgeGarpStatsLeaveInTransmitted
					Integer32,
				sleBridgeGarpStatsLeaveEmptyTransmitted
					Integer32,
				sleBridgeGarpStatsLeaveAllTransmitted
					Integer32
			 }

		sleBridgeGarpStatsJoinEmptyReceived OBJECT-TYPE
			SYNTAX Integer32
			MAX-ACCESS read-only
			STATUS current
			DESCRIPTION
				"GARP stats received:
				join empty"
			::= { sleBridgeGarpStatsEntry 1 }

		
		sleBridgeGarpStatsJoinInReceived OBJECT-TYPE
			SYNTAX Integer32
			MAX-ACCESS read-only
			STATUS current
			DESCRIPTION
				"GARP stats received:
				Joun in
				"
			::= { sleBridgeGarpStatsEntry 2 }

		
		sleBridgeGarpStatsEmptyReceived OBJECT-TYPE
			SYNTAX Integer32
			MAX-ACCESS read-only
			STATUS current
			DESCRIPTION
				"GARP stats received:
				empty "
			::= { sleBridgeGarpStatsEntry 3 }

		
		sleBridgeGarpStatsLeaveInReceived OBJECT-TYPE
			SYNTAX Integer32
			MAX-ACCESS read-only
			STATUS current
			DESCRIPTION
				"GARP stats received:
				Leave in"
			::= { sleBridgeGarpStatsEntry 4 }

		
		sleBridgeGarpStatsLeaveEmptyReceived OBJECT-TYPE
			SYNTAX Integer32
			MAX-ACCESS read-only
			STATUS current
			DESCRIPTION
				"GARP stats received:
				Leave empty"
			::= { sleBridgeGarpStatsEntry 5 }

		
		sleBridgeGarpStatsLeaveAllReceived OBJECT-TYPE
			SYNTAX Integer32
			MAX-ACCESS read-only
			STATUS current
			DESCRIPTION
				"GARP stats received:
				Leave all"
			::= { sleBridgeGarpStatsEntry 6 }

		
		sleBridgeGarpStatsJoinEmptyTransmitted OBJECT-TYPE
			SYNTAX Integer32
			MAX-ACCESS read-only
			STATUS current
			DESCRIPTION
				"GARP stats transmitted:
				Join empty"
			::= { sleBridgeGarpStatsEntry 7 }

		
		sleBridgeGarpStatsJoinInTransmitted OBJECT-TYPE
			SYNTAX Integer32
			MAX-ACCESS read-only
			STATUS current
			DESCRIPTION
				"GARP stats transmitted:
				Join in"
			::= { sleBridgeGarpStatsEntry 8 }

		
		sleBridgeGarpStatsEmptyTransmitted OBJECT-TYPE
			SYNTAX Integer32
			MAX-ACCESS read-only
			STATUS current
			DESCRIPTION
				"GARP stats transmitted:
				Empty
				"
			::= { sleBridgeGarpStatsEntry 9 }

		
		sleBridgeGarpStatsLeaveInTransmitted OBJECT-TYPE
			SYNTAX Integer32
			MAX-ACCESS read-only
			STATUS current
			DESCRIPTION
				"GARP stats transmitted:
				Leave in"
			::= { sleBridgeGarpStatsEntry 10 }

		
		sleBridgeGarpStatsLeaveEmptyTransmitted OBJECT-TYPE
			SYNTAX Integer32
			MAX-ACCESS read-only
			STATUS current
			DESCRIPTION
				"GARP stats transmitted;
				Leave empty"
			::= { sleBridgeGarpStatsEntry 11 }

		
		sleBridgeGarpStatsLeaveAllTransmitted OBJECT-TYPE
			SYNTAX Integer32
			MAX-ACCESS read-only
			STATUS current
			DESCRIPTION
				"GARP stats transmitted:
				Leave all"
			::= { sleBridgeGarpStatsEntry 12 }

		
		sleBridgeGarpStatsControl OBJECT IDENTIFIER ::= { sleBridgeGarpStats 2 }

		
		sleBridgeGarpStatsControlRequest OBJECT-TYPE
			SYNTAX INTEGER { clearGarpPktStatistics(1) }
			MAX-ACCESS read-write
			STATUS current
			DESCRIPTION
				"The request of a user command"
			::= { sleBridgeGarpStatsControl 1 }

		
		sleBridgeGarpStatstControlStatus OBJECT-TYPE
			SYNTAX SleControlStatusType
			MAX-ACCESS read-only
			STATUS current
			DESCRIPTION
				"The status of user command"
			::= { sleBridgeGarpStatsControl 2 }

		
		sleBridgeGarpStatsControlTimer OBJECT-TYPE
			SYNTAX Gauge32
			MAX-ACCESS read-write
			STATUS current
			DESCRIPTION
				"The maximum time for the manager for a long running user command"
			::= { sleBridgeGarpStatsControl 3 }

		
		sleBridgeGarpStatsControlTimeStamp OBJECT-TYPE
			SYNTAX TimeTicks
			MAX-ACCESS read-only
			STATUS current
			DESCRIPTION
				"The time stamp of the last command(end of command)"
			::= { sleBridgeGarpStatsControl 4 }

		
		sleBridgeGarpStatsControlReqResult OBJECT-TYPE
			SYNTAX SleControlRequestResultType
			MAX-ACCESS read-only
			STATUS current
			DESCRIPTION
				"The result of the last user command"
			::= { sleBridgeGarpStatsControl 5 }

		
		sleBridgeGarpStatsControlIndex OBJECT-TYPE
			SYNTAX INTEGER (1..65535)
			MAX-ACCESS read-write
			STATUS current
			DESCRIPTION
				"Port index"
			::= { sleBridgeGarpStatsControl 6 }

		
		sleBridgeGarpStatsControlType OBJECT-TYPE
			SYNTAX INTEGER
				{
				gvrp(1),
				gmrp(2)
				}
			MAX-ACCESS read-write
			STATUS current
			DESCRIPTION
				"Port type
				"
			::= { sleBridgeGarpStatsControl 7 }

		
		sleBridgeGarpStatsNotification OBJECT IDENTIFIER ::= { sleBridgeGarpStats 3 }

		
		sleBridgeGarpStatisticsCleared NOTIFICATION-TYPE
			OBJECTS { sleBridgeGarpStatsControlRequest, sleBridgeGarpStatsControlTimeStamp, sleBridgeGarpStatsControlReqResult, sleBridgeGarpStatsControlIndex, sleBridgeGarpStatsControlType
				 }
			STATUS current
			DESCRIPTION 
				"Description."
			::= { sleBridgeGarpStatsNotification 1 }

		
		sleBridgeGmrpStatic OBJECT IDENTIFIER ::= { sleBridgeGarp 4 }

		
		sleBridgeGmrpStaticTable OBJECT-TYPE
			SYNTAX SEQUENCE OF SleBridgeGmrpStaticEntry
			MAX-ACCESS not-accessible
			STATUS current
			DESCRIPTION
				"bridge GMRP static table"
			::= { sleBridgeGmrpStatic 1 }

		
		sleBridgeGmrpStaticEntry OBJECT-TYPE
			SYNTAX SleBridgeGmrpStaticEntry
			MAX-ACCESS not-accessible
			STATUS current
			DESCRIPTION
				"key: sleBridgeGmrpStaticVid, sleBridgeGmrpStaticPort, sleBridgeGmrpStaticGmac"
			INDEX { sleBridgeGmrpStaticVid, sleBridgeGmrpStaticPort, sleBridgeGmrpStaticGmac }
			::= { sleBridgeGmrpStaticTable 1 }

		
		SleBridgeGmrpStaticEntry ::=
			SEQUENCE { 
				sleBridgeGmrpStaticVid
					INTEGER,
				sleBridgeGmrpStaticPort
					INTEGER,
				sleBridgeGmrpStaticGmac
					OCTET STRING
			 }

		sleBridgeGmrpStaticVid OBJECT-TYPE
			SYNTAX INTEGER (1..65535)
			MAX-ACCESS read-only
			STATUS current
			DESCRIPTION
				"VLAN Id"
			::= { sleBridgeGmrpStaticEntry 1 }

		
		sleBridgeGmrpStaticPort OBJECT-TYPE
			SYNTAX INTEGER (1..65535)
			MAX-ACCESS read-only
			STATUS current
			DESCRIPTION
				"Port index"
			::= { sleBridgeGmrpStaticEntry 2 }

		
		sleBridgeGmrpStaticGmac OBJECT-TYPE
			SYNTAX OCTET STRING (SIZE (0..6))
			MAX-ACCESS read-only
			STATUS current
			DESCRIPTION
				"Group Mac Address"
			::= { sleBridgeGmrpStaticEntry 3 }

		
		sleBridgeGmrpStaticControl OBJECT IDENTIFIER ::= { sleBridgeGmrpStatic 2 }

		
		sleBridgeGmrpStaticControlRequest OBJECT-TYPE
			SYNTAX INTEGER
				{
				addGmrpStatic(1),
				delGmrpStatic(2)
				}
			MAX-ACCESS read-write
			STATUS current
			DESCRIPTION
				"The request of a user command"
			::= { sleBridgeGmrpStaticControl 1 }

		
		sleBridgeGmrpStaticControlStatus OBJECT-TYPE
			SYNTAX SleControlStatusType
			MAX-ACCESS read-only
			STATUS current
			DESCRIPTION
				"The status of user command"
			::= { sleBridgeGmrpStaticControl 2 }

		
		sleBridgeGmrpStaticControlTimer OBJECT-TYPE
			SYNTAX Gauge32
			MAX-ACCESS read-write
			STATUS current
			DESCRIPTION
				"The maximum time for the manager for a long running user command"
			::= { sleBridgeGmrpStaticControl 3 }

		
		sleBridgeGmrpStaticControlTimeStamp OBJECT-TYPE
			SYNTAX TimeTicks
			MAX-ACCESS read-only
			STATUS current
			DESCRIPTION
				"The time stamp of the last command(end of command)"
			::= { sleBridgeGmrpStaticControl 4 }

		
		sleBridgeGmrpStaticControlReqResult OBJECT-TYPE
			SYNTAX SleControlRequestResultType
			MAX-ACCESS read-only
			STATUS current
			DESCRIPTION
				"The result of the last user command"
			::= { sleBridgeGmrpStaticControl 5 }

		
		sleBridgeGmrpStaticControlVid OBJECT-TYPE
			SYNTAX INTEGER (1..65535)
			MAX-ACCESS read-write
			STATUS current
			DESCRIPTION
				"VLAN Id"
			::= { sleBridgeGmrpStaticControl 6 }

		
		sleBridgeGmrpStaticControlPort OBJECT-TYPE
			SYNTAX INTEGER (1..65535)
			MAX-ACCESS read-write
			STATUS current
			DESCRIPTION
				"Port index"
			::= { sleBridgeGmrpStaticControl 7 }

		
		sleBridgeGmrpStaticControlGmac OBJECT-TYPE
			SYNTAX OCTET STRING (SIZE (0..6))
			MAX-ACCESS read-write
			STATUS current
			DESCRIPTION
				"Group Mac Address"
			::= { sleBridgeGmrpStaticControl 8 }

		
		sleBridgeGmrpStaticNotification OBJECT IDENTIFIER ::= { sleBridgeGmrpStatic 3 }

		
		sleBridgeGmrpStaticAdded NOTIFICATION-TYPE
			OBJECTS { sleBridgeGmrpStaticControlRequest, sleBridgeGmrpStaticControlTimeStamp, sleBridgeGmrpStaticControlReqResult, sleBridgeGmrpStaticControlVid, sleBridgeGmrpStaticControlPort, 
				sleBridgeGmrpStaticControlGmac }
			STATUS current
			DESCRIPTION 
				"Description."
			::= { sleBridgeGmrpStaticNotification 1 }

		
		sleBridgeGmrpStaticDeleted NOTIFICATION-TYPE
			OBJECTS { sleBridgeGmrpStaticControlRequest, sleBridgeGmrpStaticControlTimeStamp, sleBridgeGmrpStaticControlReqResult, sleBridgeGmrpStaticControlVid, sleBridgeGmrpStaticControlPort, 
				sleBridgeGmrpStaticControlGmac }
			STATUS current
			DESCRIPTION 
				"Description."
			::= { sleBridgeGmrpStaticNotification 2 }

		
		sleVlanTag OBJECT IDENTIFIER ::= { sleBridge 27 }

		
		sleVlanInboundTag OBJECT IDENTIFIER ::= { sleVlanTag 1 }

		
		sleVlanInboundTagTable OBJECT-TYPE
			SYNTAX SEQUENCE OF SleVlanInboundTagEntry
			MAX-ACCESS not-accessible
			STATUS current
			DESCRIPTION
				"vlan inbound tag table."
			::= { sleVlanInboundTag 1 }

		
		sleVlanInboundTagEntry OBJECT-TYPE
			SYNTAX SleVlanInboundTagEntry
			MAX-ACCESS not-accessible
			STATUS current
			DESCRIPTION
				"key: sleVlanInboundTagPortIndex, sleVlanInboundTagVlanIndex"
			INDEX { sleVlanInboundTagPortIndex, sleVlanInboundTagVlanIndex, sleVlanInboundTagVlanPriority }
			::= { sleVlanInboundTagTable 1 }

		
		SleVlanInboundTagEntry ::=
			SEQUENCE { 
				sleVlanInboundTagPortIndex
					INTEGER,
				sleVlanInboundTagVlanIndex
					INTEGER,
				sleVlanInboundTagOuterVid
					INTEGER,
				sleVlanInboundTagOperStatus
					INTEGER,
				sleVlanInboundTagVlanPriority
					INTEGER,
				sleVlanInboundTagOuterVlanPriority
					INTEGER
			 }

		sleVlanInboundTagPortIndex OBJECT-TYPE
			SYNTAX INTEGER (1..65535)
			MAX-ACCESS read-only
			STATUS current
			DESCRIPTION
				"Bridge Port Index"
			::= { sleVlanInboundTagEntry 1 }

		
		sleVlanInboundTagVlanIndex OBJECT-TYPE
			SYNTAX INTEGER (1..4094)
			MAX-ACCESS read-only
			STATUS current
			DESCRIPTION
				"Vlan Index of inner-tag"
			::= { sleVlanInboundTagEntry 2 }

		
		sleVlanInboundTagOuterVid OBJECT-TYPE
			SYNTAX INTEGER (1..4094)
			MAX-ACCESS read-only
			STATUS current
			DESCRIPTION
				"The Outer Vlan-ID to tag for incoming packet with vlan index"
			::= { sleVlanInboundTagEntry 3 }

		
		sleVlanInboundTagOperStatus OBJECT-TYPE
			SYNTAX INTEGER
				{
				on(1),
				off(2)
				}
			MAX-ACCESS read-only
			STATUS current
			DESCRIPTION
				"The Operational Status of Outer Vlan-ID to tag for incoming packet with vlan index."
			::= { sleVlanInboundTagEntry 4 }

		
		sleVlanInboundTagVlanPriority OBJECT-TYPE
			SYNTAX INTEGER
				{
				cos0(0),
				cos1(1),
				cos2(2),
				cos3(3),
				cos4(4),
				cos5(5),
				cos6(6),
				cos7(7),
				cosAny(8)
				}
			MAX-ACCESS read-only
			STATUS current
			DESCRIPTION
				"Vlan Priority of inner-tag"
			::= { sleVlanInboundTagEntry 5 }

		
		sleVlanInboundTagOuterVlanPriority OBJECT-TYPE
			SYNTAX INTEGER
				{
				cos0(0),
				cos1(1),
				cos2(2),
				cos3(3),
				cos4(4),
				cos5(5),
				cos6(6),
				cos7(7)
				}
			MAX-ACCESS read-only
			STATUS current
			DESCRIPTION
				"The Outer Vlan-Pri to tag for incoming packet with vlan index"
			::= { sleVlanInboundTagEntry 6 }

		
		sleVlanInboundTagControl OBJECT IDENTIFIER ::= { sleVlanInboundTag 2 }

		
		sleVlanInboundTagControlRequest OBJECT-TYPE
			SYNTAX INTEGER
				{
				setInboundVid(1),
				clearInboundVid(2)
				}
			MAX-ACCESS read-write
			STATUS current
			DESCRIPTION
				"The request of a user command"
			::= { sleVlanInboundTagControl 1 }

		
		sleVlanInboundTagControlStatus OBJECT-TYPE
			SYNTAX SleControlStatusType
			MAX-ACCESS read-only
			STATUS current
			DESCRIPTION
				"The status of user command"
			::= { sleVlanInboundTagControl 2 }

		
		sleVlanInboundTagControlTimer OBJECT-TYPE
			SYNTAX Gauge32
			MAX-ACCESS read-write
			STATUS current
			DESCRIPTION
				"The maximum time for the manager for a long running user command"
			::= { sleVlanInboundTagControl 3 }

		
		sleVlanInboundTagControlTimeStamp OBJECT-TYPE
			SYNTAX TimeTicks
			MAX-ACCESS read-only
			STATUS current
			DESCRIPTION
				"The time stamp of the last command(end of command)"
			::= { sleVlanInboundTagControl 4 }

		
		sleVlanInboundTagControlReqResult OBJECT-TYPE
			SYNTAX SleControlRequestResultType
			MAX-ACCESS read-only
			STATUS current
			DESCRIPTION
				"The result of the last user command"
			::= { sleVlanInboundTagControl 5 }

		
		sleVlanInboundTagControlPortIndex OBJECT-TYPE
			SYNTAX INTEGER (1..65535)
			MAX-ACCESS read-write
			STATUS current
			DESCRIPTION
				"sleVlanInboundTagPortIndex"
			::= { sleVlanInboundTagControl 6 }

		
		sleVlanInboundTagControlVlanIndex OBJECT-TYPE
			SYNTAX INTEGER (1..4094)
			MAX-ACCESS read-write
			STATUS current
			DESCRIPTION
				"sleVlanInboundTagVlanIndex"
			::= { sleVlanInboundTagControl 7 }

		
		sleVlanInboundTagControlOuterVid OBJECT-TYPE
			SYNTAX INTEGER (0..4094)
			MAX-ACCESS read-write
			STATUS current
			DESCRIPTION
				"The Vlan-ID for outer-tag
				0 : clear
				"
			::= { sleVlanInboundTagControl 8 }

		
		sleVlanInboundTagControlVlanPriority OBJECT-TYPE
			SYNTAX INTEGER
				{
				cos0(0),
				cos1(1),
				cos2(2),
				cos3(3),
				cos4(4),
				cos5(5),
				cos6(6),
				cos7(7),
				cosAny(8)
				}
			MAX-ACCESS read-write
			STATUS current
			DESCRIPTION
				"Vlan Priority of inner-tag"
			::= { sleVlanInboundTagControl 9 }

		
		sleVlanInboundTagControlOuterVlanPriority OBJECT-TYPE
			SYNTAX INTEGER
				{
				cos0(0),
				cos1(1),
				cos2(2),
				cos3(3),
				cos4(4),
				cos5(5),
				cos6(6),
				cos7(7)
				}
			MAX-ACCESS read-write
			STATUS current
			DESCRIPTION
				"The Outer Vlan-Pri to tag for incoming packet with vlan index"
			::= { sleVlanInboundTagControl 10 }

		
		sleVlanInboundTagNotification OBJECT IDENTIFIER ::= { sleVlanInboundTag 3 }

		
		sleVlanInboundTagChanged NOTIFICATION-TYPE
			OBJECTS { sleVlanInboundTagControlRequest, sleVlanInboundTagControlReqResult, sleVlanInboundTagControlTimeStamp, sleVlanInboundTagControlPortIndex, sleVlanInboundTagControlVlanIndex, 
				sleVlanInboundTagControlOuterVid, sleVlanInboundTagControlVlanPriority, sleVlanInboundTagControlOuterVlanPriority }
			STATUS current
			DESCRIPTION 
				"setInboundVid"
			::= { sleVlanInboundTagNotification 1 }

		
		sleVlanInboundTagCleared NOTIFICATION-TYPE
			OBJECTS { sleVlanInboundTagControlRequest, sleVlanInboundTagControlTimeStamp, sleVlanInboundTagControlReqResult, sleVlanInboundTagControlPortIndex, sleVlanInboundTagControlVlanIndex, 
				sleVlanInboundTagControlVlanPriority }
			STATUS current
			DESCRIPTION 
				"Description."
			::= { sleVlanInboundTagNotification 2 }

		
		sleVlanOutboundTag OBJECT IDENTIFIER ::= { sleVlanTag 2 }

		
		sleVlanOutboundTagTable OBJECT-TYPE
			SYNTAX SEQUENCE OF SleVlanOutboundTagEntry
			MAX-ACCESS not-accessible
			STATUS current
			DESCRIPTION
				"vlan outbound tag table."
			::= { sleVlanOutboundTag 1 }

		
		sleVlanOutboundTagEntry OBJECT-TYPE
			SYNTAX SleVlanOutboundTagEntry
			MAX-ACCESS not-accessible
			STATUS current
			DESCRIPTION
				"key: sleVlanOutboundTagPortIndex, sleVlanOutboundTagVlanIndex"
			INDEX { sleVlanOutboundTagPortIndex, sleVlanOutboundTagVlanIndex }
			::= { sleVlanOutboundTagTable 1 }

		
		SleVlanOutboundTagEntry ::=
			SEQUENCE { 
				sleVlanOutboundTagPortIndex
					INTEGER,
				sleVlanOutboundTagVlanIndex
					INTEGER,
				sleVlanOutboundTagOperStatus
					INTEGER
			 }

		sleVlanOutboundTagPortIndex OBJECT-TYPE
			SYNTAX INTEGER (1..65535)
			MAX-ACCESS read-only
			STATUS current
			DESCRIPTION
				"Bridge Port Index for egress port"
			::= { sleVlanOutboundTagEntry 1 }

		
		sleVlanOutboundTagVlanIndex OBJECT-TYPE
			SYNTAX INTEGER (1..4094)
			MAX-ACCESS read-only
			STATUS current
			DESCRIPTION
				"Vlan index of outer-tag"
			::= { sleVlanOutboundTagEntry 2 }

		
		sleVlanOutboundTagOperStatus OBJECT-TYPE
			SYNTAX INTEGER
				{
				on(1),
				off(2)
				}
			MAX-ACCESS read-only
			STATUS current
			DESCRIPTION
				"The Operational Status of Outer Vlan-ID to tag for outgoing packet with vlan index."
			::= { sleVlanOutboundTagEntry 3 }

		
		sleVlanOutboundTagControl OBJECT IDENTIFIER ::= { sleVlanOutboundTag 2 }

		
		sleVlanOutboundTagControlRequest OBJECT-TYPE
			SYNTAX INTEGER
				{
				setOutboundtag(1),
				clearOutboundtag(2)
				}
			MAX-ACCESS read-write
			STATUS current
			DESCRIPTION
				"The request of a user command"
			::= { sleVlanOutboundTagControl 1 }

		
		sleVlanOutboundTagControlStatus OBJECT-TYPE
			SYNTAX SleControlStatusType
			MAX-ACCESS read-only
			STATUS current
			DESCRIPTION
				"The status of user command"
			::= { sleVlanOutboundTagControl 2 }

		
		sleVlanOutboundTagControlTimer OBJECT-TYPE
			SYNTAX Gauge32
			MAX-ACCESS read-write
			STATUS current
			DESCRIPTION
				"The maximum time for the manager for a long running user command"
			::= { sleVlanOutboundTagControl 3 }

		
		sleVlanOutboundTagControlTimeStamp OBJECT-TYPE
			SYNTAX TimeTicks
			MAX-ACCESS read-only
			STATUS current
			DESCRIPTION
				"The time stamp of the last command(end of command)"
			::= { sleVlanOutboundTagControl 4 }

		
		sleVlanOutboundTagControlReqResult OBJECT-TYPE
			SYNTAX SleControlRequestResultType
			MAX-ACCESS read-only
			STATUS current
			DESCRIPTION
				"The result of the last user command"
			::= { sleVlanOutboundTagControl 5 }

		
		sleVlanOutboundTagControlPortIndex OBJECT-TYPE
			SYNTAX INTEGER (1..65535)
			MAX-ACCESS read-write
			STATUS current
			DESCRIPTION
				"sleVlanOutboundTagPortIndex"
			::= { sleVlanOutboundTagControl 6 }

		
		sleVlanOutboundTagControlOuterVid OBJECT-TYPE
			SYNTAX INTEGER (1..4094)
			MAX-ACCESS read-write
			STATUS current
			DESCRIPTION
				"The outer-tag vid of packet to go out on the egress port"
			::= { sleVlanOutboundTagControl 7 }

		
		sleVlanOutboundTagNotification OBJECT IDENTIFIER ::= { sleVlanOutboundTag 3 }

		
		sleVlanOutboundTagSet NOTIFICATION-TYPE
			OBJECTS { sleVlanOutboundTagControlRequest, sleVlanOutboundTagControlReqResult, sleVlanOutboundTagControlTimeStamp, sleVlanOutboundTagControlPortIndex, sleVlanOutboundTagControlOuterVid
				 }
			STATUS current
			DESCRIPTION 
				"setOutboundtag"
			::= { sleVlanOutboundTagNotification 1 }

		
		sleVlanOutboundTagClear NOTIFICATION-TYPE
			OBJECTS { sleVlanOutboundTagControlRequest, sleVlanOutboundTagControlReqResult, sleVlanOutboundTagControlTimeStamp, sleVlanOutboundTagControlPortIndex, sleVlanOutboundTagControlOuterVid
				 }
			STATUS current
			DESCRIPTION 
				"clearOutboundtag"
			::= { sleVlanOutboundTagNotification 2 }

		
		sleVlanRangeInboundTag OBJECT IDENTIFIER ::= { sleVlanTag 3 }

		
		sleVlanRangeInboundTagTable OBJECT-TYPE
			SYNTAX SEQUENCE OF SleVlanRangeInboundTagEntry
			MAX-ACCESS not-accessible
			STATUS current
			DESCRIPTION
				"vlan range inbound tag table."
			::= { sleVlanRangeInboundTag 1 }

		
		sleVlanRangeInboundTagEntry OBJECT-TYPE
			SYNTAX SleVlanRangeInboundTagEntry
			MAX-ACCESS not-accessible
			STATUS current
			DESCRIPTION
				"key: sleVlanRangeInboundTagPortIndex, sleVlanRangeInboundTagMinVlanIndex, sleVlanRangeInboundTagMaxVlanIndex"
			INDEX { sleVlanRangeInboundTagPortIndex, sleVlanRangeInboundTagMinVlanIndex, sleVlanRangeInboundTagMaxVlanIndex }
			::= { sleVlanRangeInboundTagTable 1 }

		
		SleVlanRangeInboundTagEntry ::=
			SEQUENCE { 
				sleVlanRangeInboundTagPortIndex
					Integer32,
				sleVlanRangeInboundTagMinVlanIndex
					Integer32,
				sleVlanRangeInboundTagMaxVlanIndex
					Integer32,
				sleVlanRangeInboundTagOuterVid
					Integer32,
				sleVlanRangeInboundTagOperStatus
					INTEGER
			 }

		sleVlanRangeInboundTagPortIndex OBJECT-TYPE
			SYNTAX Integer32 (1..512)
			MAX-ACCESS read-only
			STATUS current
			DESCRIPTION
				"Bridge Port Index."
			::= { sleVlanRangeInboundTagEntry 1 }

		
		sleVlanRangeInboundTagMinVlanIndex OBJECT-TYPE
			SYNTAX Integer32 (1..65535)
			MAX-ACCESS read-only
			STATUS current
			DESCRIPTION
				"Min Vlan Index of inner-tag."
			::= { sleVlanRangeInboundTagEntry 2 }

		
		sleVlanRangeInboundTagMaxVlanIndex OBJECT-TYPE
			SYNTAX Integer32 (1..65535)
			MAX-ACCESS read-only
			STATUS current
			DESCRIPTION
				"Max Vlan Index of inner-tag."
			::= { sleVlanRangeInboundTagEntry 3 }

		
		sleVlanRangeInboundTagOuterVid OBJECT-TYPE
			SYNTAX Integer32 (1..65535)
			MAX-ACCESS read-only
			STATUS current
			DESCRIPTION
				"The Outer Vlan-ID to tag for incoming packet with vlan index."
			::= { sleVlanRangeInboundTagEntry 4 }

		
		sleVlanRangeInboundTagOperStatus OBJECT-TYPE
			SYNTAX INTEGER
				{
				on(1),
				off(2)
				}
			MAX-ACCESS read-only
			STATUS current
			DESCRIPTION
				"The Operational Status of Outer Vlan-ID to tag for incoming packet with vlan index."
			::= { sleVlanRangeInboundTagEntry 5 }

		
		sleVlanRangeInboundTagControl OBJECT IDENTIFIER ::= { sleVlanRangeInboundTag 2 }

		
		sleVlanRangeInboundTagControlRequest OBJECT-TYPE
			SYNTAX INTEGER
				{
				setRangeInboundVid(1),
				clearRangeInboundVid(2)
				}
			MAX-ACCESS read-write
			STATUS current
			DESCRIPTION
				"The request of a user command."
			::= { sleVlanRangeInboundTagControl 1 }

		
		sleVlanRangeInboundTagControlStatus OBJECT-TYPE
			SYNTAX SleControlStatusType
			MAX-ACCESS read-only
			STATUS current
			DESCRIPTION
				"The status of a user command."
			::= { sleVlanRangeInboundTagControl 2 }

		
		sleVlanRangeInboundTagControlTimer OBJECT-TYPE
			SYNTAX Gauge32
			MAX-ACCESS read-write
			STATUS current
			DESCRIPTION
				"The maximum wait time for the manager for a long running user command."
			::= { sleVlanRangeInboundTagControl 3 }

		
		sleVlanRangeInboundTagControlTimeStamp OBJECT-TYPE
			SYNTAX TimeTicks
			MAX-ACCESS read-only
			STATUS current
			DESCRIPTION
				"The time stamp of the last command (end of command)."
			::= { sleVlanRangeInboundTagControl 4 }

		
		sleVlanRangeInboundTagControlReqResult OBJECT-TYPE
			SYNTAX SleControlRequestResultType
			MAX-ACCESS read-only
			STATUS current
			DESCRIPTION
				"The result of the last user command."
			::= { sleVlanRangeInboundTagControl 5 }

		
		sleVlanRangeInboundTagControlPortIndex OBJECT-TYPE
			SYNTAX Integer32 (1..512)
			MAX-ACCESS read-write
			STATUS current
			DESCRIPTION
				"Bridge Port Index."
			::= { sleVlanRangeInboundTagControl 6 }

		
		sleVlanRangeInboundTagControlMinVlanIndex OBJECT-TYPE
			SYNTAX Integer32 (1..65535)
			MAX-ACCESS read-write
			STATUS current
			DESCRIPTION
				"Min vlan Index of inner-tag."
			::= { sleVlanRangeInboundTagControl 7 }

		
		sleVlanRangeInboundTagControlMaxVlanIndex OBJECT-TYPE
			SYNTAX Integer32 (1..65535)
			MAX-ACCESS read-write
			STATUS current
			DESCRIPTION
				"Max vlan Index of inner-tag."
			::= { sleVlanRangeInboundTagControl 8 }

		
		sleVlanRangeInboundTagControlOuterVid OBJECT-TYPE
			SYNTAX Integer32 (1..65535)
			MAX-ACCESS read-write
			STATUS current
			DESCRIPTION
				"The Outer Vlan-ID to tag for incoming packet with vlan index."
			::= { sleVlanRangeInboundTagControl 9 }

		
		sleVlanRangeInboundTagNotification OBJECT IDENTIFIER ::= { sleVlanRangeInboundTag 3 }

		
		sleVlanRangeInboundTagChanged NOTIFICATION-TYPE
			OBJECTS { sleVlanRangeInboundTagControlRequest, sleVlanRangeInboundTagControlTimeStamp, sleVlanRangeInboundTagControlReqResult, sleVlanRangeInboundTagControlPortIndex, sleVlanRangeInboundTagControlMinVlanIndex, 
				sleVlanRangeInboundTagControlMaxVlanIndex, sleVlanRangeInboundTagControlOuterVid }
			STATUS current
			DESCRIPTION 
				"Description."
			::= { sleVlanRangeInboundTagNotification 1 }

		
		sleVlanRangeInboundTagCleared NOTIFICATION-TYPE
			OBJECTS { sleVlanRangeInboundTagControlRequest, sleVlanRangeInboundTagControlTimeStamp, sleVlanRangeInboundTagControlReqResult, sleVlanRangeInboundTagControlPortIndex, sleVlanRangeInboundTagControlMinVlanIndex, 
				sleVlanRangeInboundTagControlMaxVlanIndex }
			STATUS current
			DESCRIPTION 
				"Description."
			::= { sleVlanRangeInboundTagNotification 2 }

		
		sleVlanProtoId OBJECT IDENTIFIER ::= { sleVlanTag 4 }

		
		sleVlanProtoIdTable OBJECT-TYPE
			SYNTAX SEQUENCE OF SleVlanProtoIdEntry
			MAX-ACCESS not-accessible
			STATUS current
			DESCRIPTION
				"vlan proto id table"
			::= { sleVlanProtoId 1 }

		
		sleVlanProtoIdEntry OBJECT-TYPE
			SYNTAX SleVlanProtoIdEntry
			MAX-ACCESS not-accessible
			STATUS current
			DESCRIPTION
				"key: sleVlanProtoIdVid"
			INDEX { sleVlanProtoIdVid }
			::= { sleVlanProtoIdTable 1 }

		
		SleVlanProtoIdEntry ::=
			SEQUENCE { 
				sleVlanProtoIdVid
					Integer32,
				sleVlanProtoIdOuterProtoId
					INTEGER
			 }

		sleVlanProtoIdVid OBJECT-TYPE
			SYNTAX Integer32 (0..65535)
			MAX-ACCESS read-only
			STATUS current
			DESCRIPTION
				"The Vlan ID."
			::= { sleVlanProtoIdEntry 1 }

		
		sleVlanProtoIdOuterProtoId OBJECT-TYPE
			SYNTAX INTEGER
				{
				dtag8100(33024),
				dtag9100(37120)
				}
			MAX-ACCESS read-only
			STATUS current
			DESCRIPTION
				"programmable outer Double Tag Protocol Identifier."
			::= { sleVlanProtoIdEntry 2 }

		
		sleVlanProtoIdControl OBJECT IDENTIFIER ::= { sleVlanProtoId 2 }

		
		sleVlanProtoIdControlRequest OBJECT-TYPE
			SYNTAX INTEGER { setVlanProtoIdOuterTpid(1) }
			MAX-ACCESS read-write
			STATUS current
			DESCRIPTION
				"The request of a user command"
			::= { sleVlanProtoIdControl 1 }

		
		sleVlanProtoIdControlStatus OBJECT-TYPE
			SYNTAX SleControlStatusType
			MAX-ACCESS read-only
			STATUS current
			DESCRIPTION
				"The status of user command"
			::= { sleVlanProtoIdControl 2 }

		
		sleVlanProtoIdControlTimer OBJECT-TYPE
			SYNTAX Gauge32
			MAX-ACCESS read-write
			STATUS current
			DESCRIPTION
				"The maximum time for the manager for a long running user command"
			::= { sleVlanProtoIdControl 3 }

		
		sleVlanProtoIdControlTimeStamp OBJECT-TYPE
			SYNTAX TimeTicks
			MAX-ACCESS read-only
			STATUS current
			DESCRIPTION
				"The time stamp of the last command(end of command)"
			::= { sleVlanProtoIdControl 4 }

		
		sleVlanProtoIdControlReqResult OBJECT-TYPE
			SYNTAX SleControlRequestResultType
			MAX-ACCESS read-only
			STATUS current
			DESCRIPTION
				"The result of the last user command"
			::= { sleVlanProtoIdControl 5 }

		
		sleVlanProtoIdControlVid OBJECT-TYPE
			SYNTAX Integer32
			MAX-ACCESS read-write
			STATUS current
			DESCRIPTION
				"The Vlan Index."
			::= { sleVlanProtoIdControl 6 }

		
		sleVlanProtoIdControlOuterProtoId OBJECT-TYPE
			SYNTAX Integer32
			MAX-ACCESS read-write
			STATUS current
			DESCRIPTION
				"The programmable outer Double Tag Protocol Identifier"
			::= { sleVlanProtoIdControl 7 }

		
		sleVlanProtoIdNotification OBJECT IDENTIFIER ::= { sleVlanProtoId 3 }

		
		sleVlanProtoIdOuterProtoIdChanged NOTIFICATION-TYPE
			OBJECTS { sleVlanProtoIdControlRequest, sleVlanProtoIdControlTimeStamp, sleVlanProtoIdControlReqResult, sleVlanProtoIdControlVid, sleVlanProtoIdControlOuterProtoId
				 }
			STATUS current
			DESCRIPTION 
				"Description."
			::= { sleVlanProtoIdNotification 1 }

		
		sleVlanMapping OBJECT IDENTIFIER ::= { sleBridge 28 }

		
		sleVlanMappingTable OBJECT-TYPE
			SYNTAX SEQUENCE OF SleVlanMappingEntry
			MAX-ACCESS not-accessible
			STATUS current
			DESCRIPTION
				"vlan mapping table"
			::= { sleVlanMapping 1 }

		
		sleVlanMappingEntry OBJECT-TYPE
			SYNTAX SleVlanMappingEntry
			MAX-ACCESS not-accessible
			STATUS current
			DESCRIPTION
				"key: sleVlanMappingIndex"
			INDEX { sleVlanMappingIndex }
			::= { sleVlanMappingTable 1 }

		
		SleVlanMappingEntry ::=
			SEQUENCE { 
				sleVlanMappingIndex
					INTEGER,
				sleVlanMappingPortId
					INTEGER,
				sleVlanMappingOriVlanId
					INTEGER,
				sleVlanMappingTransVlanId
					INTEGER,
				sleVlanMappingMode
					INTEGER,
				sleVlanMappingMatchCos
					Integer32,
				sleVlanMappingMatchDscp
					Integer32,
				sleVlanMappingMatchEthType
					INTEGER,
				sleVlanMappingMatchIPPrecedence
					Integer32,
				sleVlanMappingMatchTos
					Integer32,
				sleVlanMappingRateLimit
					INTEGER,
				sleVlanMappingCos
					Integer32,
				sleVlanMappingDscp
					Integer32
			 }

		sleVlanMappingIndex OBJECT-TYPE
			SYNTAX INTEGER (1..65535)
			MAX-ACCESS read-only
			STATUS current
			DESCRIPTION
				"The Vlan index"
			::= { sleVlanMappingEntry 1 }

		
		sleVlanMappingPortId OBJECT-TYPE
			SYNTAX INTEGER (1..65535)
			MAX-ACCESS read-only
			STATUS current
			DESCRIPTION
				"The port index."
			::= { sleVlanMappingEntry 2 }

		
		sleVlanMappingOriVlanId OBJECT-TYPE
			SYNTAX INTEGER (1..4094)
			MAX-ACCESS read-only
			STATUS current
			DESCRIPTION
				"The original vlan index."
			::= { sleVlanMappingEntry 3 }

		
		sleVlanMappingTransVlanId OBJECT-TYPE
			SYNTAX INTEGER (1..4094)
			MAX-ACCESS read-only
			STATUS current
			DESCRIPTION
				"The translation vlan index"
			::= { sleVlanMappingEntry 4 }

		
		sleVlanMappingMode OBJECT-TYPE
			SYNTAX INTEGER
				{
				default(0),
				cos(1),
				dscp(2),
				matchCos(3),
				matchDscp(4),
				matchEthType(5),
				matchIpPrecedence(6),
				matchTos(7),
				rateLimit(8)
				}
			MAX-ACCESS read-only
			STATUS current
			DESCRIPTION
				"The vlan mapping mode configuration"
			::= { sleVlanMappingEntry 5 }

		
		sleVlanMappingMatchCos OBJECT-TYPE
			SYNTAX Integer32 (-1 | 0..7)
			MAX-ACCESS read-only
			STATUS current
			DESCRIPTION
				"The match CoS value"
			::= { sleVlanMappingEntry 6 }

		
		sleVlanMappingMatchDscp OBJECT-TYPE
			SYNTAX Integer32 (-1 | 0..63)
			MAX-ACCESS read-only
			STATUS current
			DESCRIPTION
				"The match DSCP value"
			::= { sleVlanMappingEntry 7 }

		
		sleVlanMappingMatchEthType OBJECT-TYPE
			SYNTAX INTEGER (-1 | 1..65535)
			MAX-ACCESS read-only
			STATUS current
			DESCRIPTION
				"The match Ethernet type value"
			::= { sleVlanMappingEntry 8 }

		
		sleVlanMappingMatchIPPrecedence OBJECT-TYPE
			SYNTAX Integer32 (-1 | 0..7)
			MAX-ACCESS read-only
			STATUS current
			DESCRIPTION
				"The Match IP precedence value"
			::= { sleVlanMappingEntry 9 }

		
		sleVlanMappingMatchTos OBJECT-TYPE
			SYNTAX Integer32 (-1 | 0..255)
			MAX-ACCESS read-only
			STATUS current
			DESCRIPTION
				"The match ToS value"
			::= { sleVlanMappingEntry 10 }

		
		sleVlanMappingRateLimit OBJECT-TYPE
			SYNTAX INTEGER (-1 | 1..65535)
			MAX-ACCESS read-only
			STATUS current
			DESCRIPTION
				"The rate limit value"
			::= { sleVlanMappingEntry 11 }

		
		sleVlanMappingCos OBJECT-TYPE
			SYNTAX Integer32 (-1 | 0..7)
			MAX-ACCESS read-only
			STATUS current
			DESCRIPTION
				"The CoS value"
			::= { sleVlanMappingEntry 12 }

		
		sleVlanMappingDscp OBJECT-TYPE
			SYNTAX Integer32 (-1 | 0..63)
			MAX-ACCESS read-only
			STATUS current
			DESCRIPTION
				"The DSCP value"
			::= { sleVlanMappingEntry 13 }

		
		sleVlanMappingControl OBJECT IDENTIFIER ::= { sleVlanMapping 2 }

		
		sleVlanMappingControlRequest OBJECT-TYPE
			SYNTAX INTEGER
				{
				addVlanMapping(1),
				delVlanMapping(2)
				}
			MAX-ACCESS read-write
			STATUS current
			DESCRIPTION
				"The request of a user command"
			::= { sleVlanMappingControl 1 }

		
		sleVlanMappingControlStatus OBJECT-TYPE
			SYNTAX SleControlStatusType
			MAX-ACCESS read-write
			STATUS current
			DESCRIPTION
				"The status of user command"
			::= { sleVlanMappingControl 2 }

		
		sleVlanMappingControlTimer OBJECT-TYPE
			SYNTAX Gauge32
			MAX-ACCESS read-write
			STATUS current
			DESCRIPTION
				"The maximum time for the manager for a long running user command"
			::= { sleVlanMappingControl 3 }

		
		sleVlanMappingControlTimeStamp OBJECT-TYPE
			SYNTAX TimeTicks
			MAX-ACCESS read-write
			STATUS current
			DESCRIPTION
				"The time stamp of the last command(end of command)"
			::= { sleVlanMappingControl 4 }

		
		sleVlanMappingControlReqResult OBJECT-TYPE
			SYNTAX SleControlRequestResultType
			MAX-ACCESS read-write
			STATUS current
			DESCRIPTION
				"The result of the last user command"
			::= { sleVlanMappingControl 5 }

		
		sleVlanMappingControlIndex OBJECT-TYPE
			SYNTAX INTEGER (1..65535)
			MAX-ACCESS read-write
			STATUS current
			DESCRIPTION
				"The Vlan index"
			::= { sleVlanMappingControl 6 }

		
		sleVlanMappingControlPortId OBJECT-TYPE
			SYNTAX INTEGER (1..65535)
			MAX-ACCESS read-write
			STATUS current
			DESCRIPTION
				"The port index."
			::= { sleVlanMappingControl 7 }

		
		sleVlanMappingControlOriVlanId OBJECT-TYPE
			SYNTAX INTEGER (1..4094)
			MAX-ACCESS read-write
			STATUS current
			DESCRIPTION
				"The original vlan index."
			::= { sleVlanMappingControl 8 }

		
		sleVlanMappingControlTransVlanID OBJECT-TYPE
			SYNTAX INTEGER (1..4094)
			MAX-ACCESS read-write
			STATUS current
			DESCRIPTION
				"The translation vlan index"
			::= { sleVlanMappingControl 9 }

		
		sleVlanMappingControlMode OBJECT-TYPE
			SYNTAX INTEGER
				{
				default(0),
				cos(1),
				dscp(2),
				matchCos(3),
				matchDscp(4),
				matchEthType(5),
				matchIpPrecedence(6),
				matchTos(7),
				rateLimit(8)
				}
			MAX-ACCESS read-write
			STATUS current
			DESCRIPTION
				"The vlan mapping mode configuration"
			::= { sleVlanMappingControl 10 }

		
		sleVlanMappingControlMatchCos OBJECT-TYPE
			SYNTAX Integer32 (-1 | 0..7)
			MAX-ACCESS read-write
			STATUS current
			DESCRIPTION
				"The match CoS value"
			::= { sleVlanMappingControl 11 }

		
		sleVlanMappingControlMatchDscp OBJECT-TYPE
			SYNTAX Integer32 (-1 | 0..63)
			MAX-ACCESS read-write
			STATUS current
			DESCRIPTION
				"The match DSCP value"
			::= { sleVlanMappingControl 12 }

		
		sleVlanMappingControlMatchEthType OBJECT-TYPE
			SYNTAX INTEGER (-1 | 1..65535)
			MAX-ACCESS read-write
			STATUS current
			DESCRIPTION
				"The match Ethernet type value"
			::= { sleVlanMappingControl 13 }

		
		sleVlanMappingControlMatchIPPrecedence OBJECT-TYPE
			SYNTAX Integer32 (-1 | 0..7)
			MAX-ACCESS read-write
			STATUS current
			DESCRIPTION
				"The Match IP precedence value"
			::= { sleVlanMappingControl 14 }

		
		sleVlanMappingControlMatchTos OBJECT-TYPE
			SYNTAX Integer32 (-1 | 0..255)
			MAX-ACCESS read-write
			STATUS current
			DESCRIPTION
				"The match ToS value"
			::= { sleVlanMappingControl 15 }

		
		sleVlanMappingControlRateLimit OBJECT-TYPE
			SYNTAX INTEGER (-1 | 1..65535)
			MAX-ACCESS read-write
			STATUS current
			DESCRIPTION
				"The rate limit value"
			::= { sleVlanMappingControl 16 }

		
		sleVlanMappingControlCos OBJECT-TYPE
			SYNTAX Integer32 (-1 | 0..7)
			MAX-ACCESS read-write
			STATUS current
			DESCRIPTION
				"The CoS value"
			::= { sleVlanMappingControl 17 }

		
		sleVlanMappingControlDscp OBJECT-TYPE
			SYNTAX Integer32 (-1 | 0..255)
			MAX-ACCESS read-write
			STATUS current
			DESCRIPTION
				"The DSCP value"
			::= { sleVlanMappingControl 18 }

		
		sleVlanMappingNotification OBJECT IDENTIFIER ::= { sleVlanMapping 3 }

		
		sleVlanMappingCreated NOTIFICATION-TYPE
			OBJECTS { sleVlanMappingControlRequest, sleVlanMappingControlTimeStamp, sleVlanMappingControlReqResult, sleVlanMappingControlPortId, sleVlanMappingControlOriVlanId, 
				sleVlanMappingControlTransVlanID, sleVlanMappingControlMode, sleVlanMappingControlMatchCos, sleVlanMappingControlMatchDscp, sleVlanMappingControlMatchEthType, 
				sleVlanMappingControlMatchIPPrecedence, sleVlanMappingControlMatchTos, sleVlanMappingControlRateLimit, sleVlanMappingControlCos, sleVlanMappingControlDscp
				 }
			STATUS current
			DESCRIPTION 
				"Description."
			::= { sleVlanMappingNotification 1 }

		
		sleVlanMappingDeleted NOTIFICATION-TYPE
			OBJECTS { sleVlanMappingControlRequest, sleVlanMappingControlTimeStamp, sleVlanMappingControlIndex, sleVlanMappingControlReqResult }
			STATUS current
			DESCRIPTION 
				"Description."
			::= { sleVlanMappingNotification 2 }

		
		slePowerInline OBJECT IDENTIFIER ::= { sleBridge 29 }

		
		slePowerInlineTable OBJECT-TYPE
			SYNTAX SEQUENCE OF SlePowerInlineEntry
			MAX-ACCESS not-accessible
			STATUS current
			DESCRIPTION
				"The poe snmp main table"
			::= { slePowerInline 1 }

		
		slePowerInlineEntry OBJECT-TYPE
			SYNTAX SlePowerInlineEntry
			MAX-ACCESS not-accessible
			STATUS current
			DESCRIPTION
				"The poe snmp entry table"
			INDEX { slePowerInlinePortIndex }
			::= { slePowerInlineTable 1 }

		
		SlePowerInlineEntry ::=
			SEQUENCE { 
				slePowerInlinePortIndex
					INTEGER,
				slePowerInlineAdminStatus
					INTEGER,
				slePowerInlinePortStatus
					INTEGER,
				slePowerInlineDetectionStatus
					INTEGER,
				slePowerInlinePortClass
					INTEGER,
				slePowerInlinePortMaxPow
					INTEGER,
				slePowerInlinePortLegacy
					INTEGER,
				slePowerInlinePortPriority
					INTEGER,
				slePowerInlinePortPower
					OCTET STRING,
				slePowerInlinePortCurrent
					OCTET STRING,
				slePowerInlinePortVoltage
					OCTET STRING,
				slePowerInlinePortTemperture
					OCTET STRING
			 }

		slePowerInlinePortIndex OBJECT-TYPE
			SYNTAX INTEGER (1..65535)
			MAX-ACCESS read-only
			STATUS current
			DESCRIPTION
				"The number of poe port."
			::= { slePowerInlineEntry 1 }

		
		slePowerInlineAdminStatus OBJECT-TYPE
			SYNTAX INTEGER
				{
				auto(1),
				static(2),
				null(3)
				}
			MAX-ACCESS read-only
			STATUS current
			DESCRIPTION
				"The poe port Admin status"
			::= { slePowerInlineEntry 2 }

		
		slePowerInlinePortStatus OBJECT-TYPE
			SYNTAX INTEGER
				{
				enable(1),
				disable(2)
				}
			MAX-ACCESS read-only
			STATUS current
			DESCRIPTION
				"The poe port operate status"
			::= { slePowerInlineEntry 3 }

		
		slePowerInlineDetectionStatus OBJECT-TYPE
			SYNTAX INTEGER
				{
				disable(1),
				searching(2),
				delivingPower(3),
				test(4),
				fault(5),
				overloadFault(6),
				requestPower(7)
				}
			MAX-ACCESS read-only
			STATUS current
			DESCRIPTION
				"The poe port detection status"
			::= { slePowerInlineEntry 4 }

		
		slePowerInlinePortClass OBJECT-TYPE
			SYNTAX INTEGER
				{
				class0(1),
				class1(2),
				class2(3),
				class3(4)
				}
			MAX-ACCESS read-only
			STATUS current
			DESCRIPTION
				"The poe port class type."
			::= { slePowerInlineEntry 5 }

		
		slePowerInlinePortMaxPow OBJECT-TYPE
			SYNTAX INTEGER (3000..30000)
			MAX-ACCESS read-only
			STATUS current
			DESCRIPTION
				"The max power value."
			::= { slePowerInlineEntry 6 }

		
		slePowerInlinePortLegacy OBJECT-TYPE
			SYNTAX INTEGER
				{
				enable(1),
				disable(2)
				}
			MAX-ACCESS read-only
			STATUS current
			DESCRIPTION
				"The poe port legacy mode."
			::= { slePowerInlineEntry 7 }

		
		slePowerInlinePortPriority OBJECT-TYPE
			SYNTAX INTEGER
				{
				low(1),
				medium(2),
				high(3)
				}
			MAX-ACCESS read-only
			STATUS current
			DESCRIPTION
				"The poe port priority level."
			::= { slePowerInlineEntry 8 }

		
		slePowerInlinePortPower OBJECT-TYPE
			SYNTAX OCTET STRING (SIZE (1..8))
			MAX-ACCESS read-only
			STATUS current
			DESCRIPTION
				"The poe port detected power."
			::= { slePowerInlineEntry 9 }

		
		slePowerInlinePortCurrent OBJECT-TYPE
			SYNTAX OCTET STRING (SIZE (1..8))
			MAX-ACCESS read-only
			STATUS current
			DESCRIPTION
				"The poe port detected current."
			::= { slePowerInlineEntry 10 }

		
		slePowerInlinePortVoltage OBJECT-TYPE
			SYNTAX OCTET STRING (SIZE (1..8))
			MAX-ACCESS read-only
			STATUS current
			DESCRIPTION
				"The poe port detected voltage."
			::= { slePowerInlineEntry 11 }

		
		slePowerInlinePortTemperture OBJECT-TYPE
			SYNTAX OCTET STRING (SIZE (1..8))
			MAX-ACCESS read-only
			STATUS current
			DESCRIPTION
				"The poe port detected temperture."
			::= { slePowerInlineEntry 12 }

		
		slePowerInlineControl OBJECT IDENTIFIER ::= { slePowerInline 2 }

		
		slePowerInlineControlRequest OBJECT-TYPE
			SYNTAX INTEGER
				{
				setPowerInlineEnable(1),
				setPowerInlineDisable(2),
				setPowerInlineReset(3),
				setPowerInlineLegacy(4),
				setPowerInlinePriority(5),
				setPowerInlineClass(6),
				setPowerInlinePower(7)
				}
			MAX-ACCESS read-write
			STATUS current
			DESCRIPTION
				"The poe control request type"
			::= { slePowerInlineControl 1 }

		
		slePowerInlineControlStatus OBJECT-TYPE
			SYNTAX SleControlStatusType
			MAX-ACCESS read-only
			STATUS current
			DESCRIPTION
				"The poe control status type"
			::= { slePowerInlineControl 2 }

		
		slePowerInlineControlTimer OBJECT-TYPE
			SYNTAX Gauge32
			MAX-ACCESS read-write
			STATUS current
			DESCRIPTION
				"The poe control flag"
			::= { slePowerInlineControl 3 }

		
		slePowerInlineControlTimeStamp OBJECT-TYPE
			SYNTAX TimeTicks
			MAX-ACCESS read-only
			STATUS current
			DESCRIPTION
				"The poe control timestamp"
			::= { slePowerInlineControl 4 }

		
		slePowerInlineControlReqResult OBJECT-TYPE
			SYNTAX SleControlRequestResultType
			MAX-ACCESS read-only
			STATUS current
			DESCRIPTION
				"Result of the last command."
			::= { slePowerInlineControl 5 }

		
		slePowerInlineControlPortIndex OBJECT-TYPE
			SYNTAX INTEGER (1..65535)
			MAX-ACCESS read-write
			STATUS current
			DESCRIPTION
				"The Index of poe port."
			::= { slePowerInlineControl 6 }

		
		slePowerInlineControlAdminStatus OBJECT-TYPE
			SYNTAX INTEGER
				{
				auto(1),
				static(2),
				null(3)
				}
			MAX-ACCESS read-write
			STATUS current
			DESCRIPTION
				"The poe port admin status"
			::= { slePowerInlineControl 7 }

		
		slePowerInlineControlPortStatus OBJECT-TYPE
			SYNTAX INTEGER
				{
				enable(1),
				disable(2)
				}
			MAX-ACCESS read-write
			STATUS current
			DESCRIPTION
				"The poe port operate status."
			::= { slePowerInlineControl 8 }

		
		slePowerInlineControlPortClass OBJECT-TYPE
			SYNTAX INTEGER
				{
				class0(1),
				class1(2),
				class2(3),
				class3(4)
				}
			MAX-ACCESS read-write
			STATUS current
			DESCRIPTION
				"The poe port class type."
			::= { slePowerInlineControl 9 }

		
		slePowerInlineControlPortMaxPower OBJECT-TYPE
			SYNTAX INTEGER (3000..30000)
			MAX-ACCESS read-write
			STATUS current
			DESCRIPTION
				"The max power value."
			::= { slePowerInlineControl 10 }

		
		slePowerInlineControlPortLegacy OBJECT-TYPE
			SYNTAX INTEGER
				{
				enable(1),
				disable(2)
				}
			MAX-ACCESS read-write
			STATUS current
			DESCRIPTION
				"The poe port legacy mode."
			::= { slePowerInlineControl 11 }

		
		slePowerInlineControlPriority OBJECT-TYPE
			SYNTAX INTEGER
				{
				low(1),
				medium(2),
				high(3)
				}
			MAX-ACCESS read-write
			STATUS current
			DESCRIPTION
				"The poe port priority level."
			::= { slePowerInlineControl 12 }

		
		slePowerInlineNotification OBJECT IDENTIFIER ::= { slePowerInline 3 }

		
		slePowerInlineEnableChanged NOTIFICATION-TYPE
			OBJECTS { slePowerInlineControlRequest, slePowerInlineControlTimeStamp, slePowerInlineControlReqResult, slePowerInlineControlPortIndex, slePowerInlineControlPortStatus, 
				slePowerInlineControlPortClass, slePowerInlineControlPortMaxPower, slePowerInlineControlPortLegacy, slePowerInlineControlPriority }
			STATUS current
			DESCRIPTION 
				"setPowerInlineEnable"
			::= { slePowerInlineNotification 1 }

		
		slePowerInlineDisableChanged NOTIFICATION-TYPE
			OBJECTS { slePowerInlineControlRequest, slePowerInlineControlTimeStamp, slePowerInlineControlReqResult, slePowerInlineControlPortIndex, slePowerInlineControlPortStatus
				 }
			STATUS current
			DESCRIPTION 
				"setPowerInlineDisable"
			::= { slePowerInlineNotification 2 }

		
		slePowerInlineResetChanged NOTIFICATION-TYPE
			OBJECTS { slePowerInlineControlRequest, slePowerInlineControlTimeStamp, slePowerInlineControlReqResult, slePowerInlineControlPortIndex, slePowerInlineControlPortStatus, 
				slePowerInlineControlPortClass, slePowerInlineControlPortMaxPower, slePowerInlineControlPortLegacy, slePowerInlineControlPriority }
			STATUS current
			DESCRIPTION 
				"setPowerInlineReset"
			::= { slePowerInlineNotification 3 }

		
		slePowerInlineLegacyChanged NOTIFICATION-TYPE
			OBJECTS { slePowerInlineControlRequest, slePowerInlineControlTimeStamp, slePowerInlineControlReqResult, slePowerInlineControlPortIndex, slePowerInlineControlPortStatus, 
				slePowerInlineControlPortLegacy }
			STATUS current
			DESCRIPTION 
				"setPowerInlineLegacy"
			::= { slePowerInlineNotification 4 }

		
		slePowerInlinePriorityChanged NOTIFICATION-TYPE
			OBJECTS { slePowerInlineControlRequest, slePowerInlineControlTimeStamp, slePowerInlineControlReqResult, slePowerInlineControlPortIndex, slePowerInlineControlPortStatus, 
				slePowerInlineControlPriority }
			STATUS current
			DESCRIPTION 
				"setPowerInlinePriority"
			::= { slePowerInlineNotification 5 }

		
		slePowerInlineClassChanged NOTIFICATION-TYPE
			OBJECTS { slePowerInlineControlRequest, slePowerInlineControlTimeStamp, slePowerInlineControlReqResult, slePowerInlineControlPortIndex, slePowerInlineControlPortStatus, 
				slePowerInlineControlPortClass }
			STATUS current
			DESCRIPTION 
				"setPowerInlineClass"
			::= { slePowerInlineNotification 6 }

		
		slePowerInlinePowerChanged NOTIFICATION-TYPE
			OBJECTS { slePowerInlineControlRequest, slePowerInlineControlTimeStamp, slePowerInlineControlReqResult, slePowerInlineControlPortIndex, slePowerInlineControlPortStatus, 
				slePowerInlineControlPortClass, slePowerInlineControlPortMaxPower, slePowerInlineControlPortLegacy }
			STATUS current
			DESCRIPTION 
				"setPowerInlinePower"
			::= { slePowerInlineNotification 7 }

		
		sleMfdb OBJECT IDENTIFIER ::= { sleBridge 30 }

		
		sleMfdbTable OBJECT-TYPE
			SYNTAX SEQUENCE OF SleMfdbEntry
			MAX-ACCESS not-accessible
			STATUS current
			DESCRIPTION
				"The table of MFDB entries."
			::= { sleMfdb 1 }

		
		sleMfdbEntry OBJECT-TYPE
			SYNTAX SleMfdbEntry
			MAX-ACCESS not-accessible
			STATUS current
			DESCRIPTION
				"Information about a specific MAC address that
				should be forwarding or dropping.
				key: sleMfdbMacAddress"
			INDEX { sleMfdbMacAddress, sleMfdbVlanIndex }
			::= { sleMfdbTable 1 }

		
		SleMfdbEntry ::=
			SEQUENCE { 
				sleMfdbMacAddress
					OCTET STRING,
				sleMfdbEntryPermission
					INTEGER,
				sleMfdbVlanIndex
					INTEGER,
				sleMfdbPorts
					OCTET STRING
			 }

		sleMfdbMacAddress OBJECT-TYPE
			SYNTAX OCTET STRING (SIZE (0..6))
			MAX-ACCESS read-only
			STATUS current
			DESCRIPTION
				"A unicast MAC address for which the device has
				forwarding or filtering information."
			::= { sleMfdbEntry 1 }

		
		sleMfdbEntryPermission OBJECT-TYPE
			SYNTAX INTEGER
				{
				deny(0),
				permit(1)
				}
			MAX-ACCESS read-only
			STATUS current
			DESCRIPTION
				"The permission of sleMFdbMacAddress.
				The meanings of the values are: 
				    deny(0)   - the value of the corresponding instance
				                of sleMfdbMacAddress will be dropped.
				    permit(1) - the value of the corresponding instance
				                of sleMfdbMacAddress will be flooded.
				"
			::= { sleMfdbEntry 2 }

		
		sleMfdbVlanIndex OBJECT-TYPE
			SYNTAX INTEGER (0 | 1..4094)
			MAX-ACCESS read-only
			STATUS current
			DESCRIPTION
				"vlan index
				"
			::= { sleMfdbEntry 3 }

		
		sleMfdbPorts OBJECT-TYPE
			SYNTAX OCTET STRING (SIZE (0..32))
			MAX-ACCESS read-write
			STATUS current
			DESCRIPTION
				"Port Map"
			::= { sleMfdbEntry 4 }

		
		sleMfdbControl OBJECT IDENTIFIER ::= { sleMfdb 2 }

		
		sleMfdbControlRequest OBJECT-TYPE
			SYNTAX INTEGER
				{
				createMfdbEntry(1),
				destoryMfdbEntry(2),
				setMfdbEntryPermission(3),
				clearMfdbEntryTable(4)
				}
			MAX-ACCESS read-write
			STATUS current
			DESCRIPTION
				" The request of a user command"
			::= { sleMfdbControl 1 }

		
		sleMfdbControlStatus OBJECT-TYPE
			SYNTAX SleControlStatusType
			MAX-ACCESS read-only
			STATUS current
			DESCRIPTION
				" The status of user command"
			::= { sleMfdbControl 2 }

		
		sleMfdbControlTimer OBJECT-TYPE
			SYNTAX Gauge32
			MAX-ACCESS read-write
			STATUS current
			DESCRIPTION
				" The maximum time for the manager for a long running user command"
			::= { sleMfdbControl 3 }

		
		sleMfdbControlTimeStamp OBJECT-TYPE
			SYNTAX TimeTicks
			MAX-ACCESS read-only
			STATUS current
			DESCRIPTION
				" The time stamp of the last command(end of command)"
			::= { sleMfdbControl 4 }

		
		sleMfdbControlReqResult OBJECT-TYPE
			SYNTAX SleControlRequestResultType
			MAX-ACCESS read-only
			STATUS current
			DESCRIPTION
				" The result of the last user command"
			::= { sleMfdbControl 5 }

		
		sleMfdbControlMacAddress OBJECT-TYPE
			SYNTAX OCTET STRING (SIZE (0..6))
			MAX-ACCESS read-write
			STATUS current
			DESCRIPTION
				"A unicast MAC address for which the device has
				forwarding or filtering information.
				  If MAC address is NULL apply mac-filter list 
				  from file '/etc/mfdb.conf'."
			::= { sleMfdbControl 6 }

		
		sleMfdbControlEntryPermission OBJECT-TYPE
			SYNTAX INTEGER
				{
				deny(0),
				permit(1)
				}
			MAX-ACCESS read-write
			STATUS current
			DESCRIPTION
				"The permission of sleMFdbControlMacAddress."
			::= { sleMfdbControl 7 }

		
		sleMfdbControlVlanIndex OBJECT-TYPE
			SYNTAX INTEGER (0 | 1..4094)
			MAX-ACCESS read-write
			STATUS current
			DESCRIPTION
				"vlan index
				The value of 0 is all vlan"
			::= { sleMfdbControl 8 }

		
		sleMfdbControlPorts OBJECT-TYPE
			SYNTAX OCTET STRING (SIZE (0..32))
			MAX-ACCESS read-write
			STATUS current
			DESCRIPTION
				"Port Map 
				The value of 0x00 is all port
				"
			::= { sleMfdbControl 9 }

		
		sleMfdbNotification OBJECT IDENTIFIER ::= { sleMfdb 3 }

		
		sleMfdbEntryCreated NOTIFICATION-TYPE
			OBJECTS { sleMfdbControlRequest, sleMfdbControlReqResult, sleMfdbControlTimeStamp, sleMfdbControlMacAddress, sleMfdbControlVlanIndex
				 }
			STATUS current
			DESCRIPTION 
				"Create new MFDB entry."
			::= { sleMfdbNotification 1 }

		
		sleMfdbEntryDestoryed NOTIFICATION-TYPE
			OBJECTS { sleMfdbControlRequest, sleMfdbControlReqResult, sleMfdbControlTimeStamp, sleMfdbControlMacAddress, sleMfdbControlVlanIndex
				 }
			STATUS current
			DESCRIPTION 
				"Destroyed MFDB entry."
			::= { sleMfdbNotification 2 }

		
		sleMfdbEntryPermissionChanged NOTIFICATION-TYPE
			OBJECTS { sleMfdbControlRequest, sleMfdbControlReqResult, sleMfdbControlTimeStamp, sleMfdbControlEntryPermission }
			STATUS current
			DESCRIPTION 
				"Changed permission of MFDB entry."
			::= { sleMfdbNotification 3 }

		
		sleMfdbEntryTableCleared NOTIFICATION-TYPE
			OBJECTS { sleMfdbControlRequest, sleMfdbControlReqResult, sleMfdbControlTimeStamp }
			STATUS current
			DESCRIPTION 
				"Description."
			::= { sleMfdbNotification 4 }

		
		sleLldpMed OBJECT IDENTIFIER ::= { sleBridge 31 }

		
		sleLldpMedNetworkPolicyProfile OBJECT IDENTIFIER ::= { sleLldpMed 1 }

		
		sleLldpMedNetworkPolicyProfileTable OBJECT-TYPE
			SYNTAX SEQUENCE OF SleLldpMedNetworkPolicyProfileEntry
			MAX-ACCESS not-accessible
			STATUS current
			DESCRIPTION
				"Description."
			::= { sleLldpMedNetworkPolicyProfile 1 }

		
		sleLldpMedNetworkPolicyProfileEntry OBJECT-TYPE
			SYNTAX SleLldpMedNetworkPolicyProfileEntry
			MAX-ACCESS not-accessible
			STATUS current
			DESCRIPTION
				"Description."
			INDEX { sleLldpMedNetworkPolicyProfileIndex }
			::= { sleLldpMedNetworkPolicyProfileTable 1 }

		
		SleLldpMedNetworkPolicyProfileEntry ::=
			SEQUENCE { 
				sleLldpMedNetworkPolicyProfileIndex
					Integer32,
				sleLldpMedNetworkPolicyProfileName
					OCTET STRING
			 }

		sleLldpMedNetworkPolicyProfileIndex OBJECT-TYPE
			SYNTAX Integer32 (0..65535)
			MAX-ACCESS read-only
			STATUS current
			DESCRIPTION
				"network-policy profile index"
			::= { sleLldpMedNetworkPolicyProfileEntry 1 }

		
		sleLldpMedNetworkPolicyProfileName OBJECT-TYPE
			SYNTAX OCTET STRING
			MAX-ACCESS read-only
			STATUS current
			DESCRIPTION
				"network-policy profile name"
			::= { sleLldpMedNetworkPolicyProfileEntry 2 }

		
		sleLldpMedNetworkPolicyProfileControl OBJECT IDENTIFIER ::= { sleLldpMedNetworkPolicyProfile 2 }

		
		sleLldpMedNetworkPolicyProfileControlRequest OBJECT-TYPE
			SYNTAX INTEGER
				{
				addNetwrokPolicyProfile(1),
				delNetworkPolicyProfile(2),
				clearNetworkPolicyProfile(3)
				}
			MAX-ACCESS read-write
			STATUS current
			DESCRIPTION
				" The request of a user command"
			::= { sleLldpMedNetworkPolicyProfileControl 1 }

		
		sleLldpMedNetworkPolicyProfileControlStatus OBJECT-TYPE
			SYNTAX SleControlStatusType
			MAX-ACCESS read-only
			STATUS current
			DESCRIPTION
				" The status of user command"
			::= { sleLldpMedNetworkPolicyProfileControl 2 }

		
		sleLldpMedNetworkPolicyProfileControlTimer OBJECT-TYPE
			SYNTAX Gauge32
			MAX-ACCESS read-write
			STATUS current
			DESCRIPTION
				" The maximum time for the manager for a long running user command"
			::= { sleLldpMedNetworkPolicyProfileControl 3 }

		
		sleLldpMedNetworkPolicyProfileControlTimeStamp OBJECT-TYPE
			SYNTAX TimeTicks
			MAX-ACCESS read-only
			STATUS current
			DESCRIPTION
				" The time stamp of the last command(end of command)"
			::= { sleLldpMedNetworkPolicyProfileControl 4 }

		
		sleLldpMedNetworkPolicyProfileControlReqResult OBJECT-TYPE
			SYNTAX SleControlRequestResultType
			MAX-ACCESS read-only
			STATUS current
			DESCRIPTION
				" The result of the last user command"
			::= { sleLldpMedNetworkPolicyProfileControl 5 }

		
		sleLldpMedNetworkPolicyProfileControlIndex OBJECT-TYPE
			SYNTAX INTEGER (1..255)
			MAX-ACCESS read-write
			STATUS current
			DESCRIPTION
				"network-policy profile index"
			::= { sleLldpMedNetworkPolicyProfileControl 6 }

		
		sleLldpMedNetworkPolicyProfileControlName OBJECT-TYPE
			SYNTAX OCTET STRING
			MAX-ACCESS read-write
			STATUS current
			DESCRIPTION
				"network-policy profile name"
			::= { sleLldpMedNetworkPolicyProfileControl 7 }

		
		sleLldpMedNetworkPolicyProfileNotifications OBJECT IDENTIFIER ::= { sleLldpMedNetworkPolicyProfile 3 }

		
		sleLldpMedNetworkPolicyProfileCreated NOTIFICATION-TYPE
			OBJECTS { sleLldpMedNetworkPolicyProfileControlRequest, sleLldpMedNetworkPolicyProfileControlName, sleLldpMedNetworkPolicyProfileControlTimeStamp, sleLldpMedNetworkPolicyProfileControlReqResult }
			STATUS current
			DESCRIPTION 
				"Create new MFDB entry."
			::= { sleLldpMedNetworkPolicyProfileNotifications 1 }

		
		sleLldpMedNetworkPolicyProfileDestroyed NOTIFICATION-TYPE
			OBJECTS { sleLldpMedNetworkPolicyProfileControlRequest, sleLldpMedNetworkPolicyProfileControlIndex, sleLldpMedNetworkPolicyProfileControlTimeStamp, sleLldpMedNetworkPolicyProfileControlReqResult }
			STATUS current
			DESCRIPTION 
				"Create new MFDB entry."
			::= { sleLldpMedNetworkPolicyProfileNotifications 2 }

		
		sleLldpMedNetworkPolicyProfileCleared NOTIFICATION-TYPE
			OBJECTS { sleLldpMedNetworkPolicyProfileControlRequest, sleLldpMedNetworkPolicyProfileControlTimeStamp, sleLldpMedNetworkPolicyProfileControlReqResult }
			STATUS current
			DESCRIPTION 
				"Create new MFDB entry."
			::= { sleLldpMedNetworkPolicyProfileNotifications 3 }

		
		sleLldpMedNetworkPolicyProfilePolicy OBJECT IDENTIFIER ::= { sleLldpMed 2 }

		
		sleLldpMedNetworkPolicyProfilePolicyTable OBJECT-TYPE
			SYNTAX SEQUENCE OF SleLldpMedNetworkPolicyProfilePolicyEntry
			MAX-ACCESS not-accessible
			STATUS current
			DESCRIPTION
				"Description."
			::= { sleLldpMedNetworkPolicyProfilePolicy 1 }

		
		sleLldpMedNetworkPolicyProfilePolicyEntry OBJECT-TYPE
			SYNTAX SleLldpMedNetworkPolicyProfilePolicyEntry
			MAX-ACCESS not-accessible
			STATUS current
			DESCRIPTION
				"Description."
			INDEX { sleLldpMedNetworkPolicyProfileIndex, sleLldpMedNetworkPolicyProfilePolicyAppType }
			::= { sleLldpMedNetworkPolicyProfilePolicyTable 1 }

		
		SleLldpMedNetworkPolicyProfilePolicyEntry ::=
			SEQUENCE { 
				sleLldpMedNetworkPolicyProfilePolicyAppType
					INTEGER,
				sleLldpMedNetworkPolicyProfilePolicyVlanId
					Integer32,
				sleLldpMedNetworkPolicyProfilePolicyPriority
					Integer32,
				sleLldpMedNetworkPolicyProfilePolicyDscp
					Integer32,
				sleLldpMedNetworkPolicyProfilePolicyUnknown
					Boolean
			 }

		sleLldpMedNetworkPolicyProfilePolicyAppType OBJECT-TYPE
			SYNTAX INTEGER
				{
				voice(1),
				voiceSignal(2),
				guestVoice(3),
				guestVoiceSignal(4),
				softphoneVoice(5),
				videoConfrence(6),
				streamVideo(7),
				viceoSignal(8)
				}
			MAX-ACCESS read-only
			STATUS current
			DESCRIPTION
				"Information about the per port per policy type policy 
				information for a particular physical network connection."
			::= { sleLldpMedNetworkPolicyProfilePolicyEntry 1 }

		
		sleLldpMedNetworkPolicyProfilePolicyVlanId OBJECT-TYPE
			SYNTAX Integer32 (1..4094)
			MAX-ACCESS read-only
			STATUS current
			DESCRIPTION
				"An extension of the VLAN Identifier for the remote system
				connected to this port, as defined in IEEE 802.1P-1998.
				 
				A value of 1 through 4094 is used to define a valid PVID.
				 
				A value of 0 shall be used if the device is using priority tagged
				frames, meaning that only the 802.1p priority level is significant
				and the default VID of the ingress port is being used instead."
			::= { sleLldpMedNetworkPolicyProfilePolicyEntry 2 }

		
		sleLldpMedNetworkPolicyProfilePolicyPriority OBJECT-TYPE
			SYNTAX Integer32 (0..7)
			MAX-ACCESS read-only
			STATUS current
			DESCRIPTION
				"This object contains the value of the 802.1p priority
				which is associated with the remote system connected at
				given port."
			::= { sleLldpMedNetworkPolicyProfilePolicyEntry 3 }

		
		sleLldpMedNetworkPolicyProfilePolicyDscp OBJECT-TYPE
			SYNTAX Integer32 (0..63)
			MAX-ACCESS read-only
			STATUS current
			DESCRIPTION
				"This object contains the value of the Differentiated Service
				Code Point (DSCP) as defined in IETF RFC 2474 and RFC 2475
				which is associated with remote system connected at the port."
			::= { sleLldpMedNetworkPolicyProfilePolicyEntry 4 }

		
		sleLldpMedNetworkPolicyProfilePolicyUnknown OBJECT-TYPE
			SYNTAX Boolean
			MAX-ACCESS read-only
			STATUS current
			DESCRIPTION
				"This object contains the value of the Differentiated Service
				Code Point (DSCP) as defined in IETF RFC 2474 and RFC 2475
				which is associated with remote system connected at the port."
			::= { sleLldpMedNetworkPolicyProfilePolicyEntry 5 }

		
		sleLldpMedNetworkPolicyProfilePolicyControl OBJECT IDENTIFIER ::= { sleLldpMedNetworkPolicyProfilePolicy 2 }

		
		sleLldpMedNetworkPolicyProfilePolicyControlRequest OBJECT-TYPE
			SYNTAX INTEGER
				{
				setNetwrokPolicy(1),
				delNetworkPolicy(2)
				}
			MAX-ACCESS read-write
			STATUS current
			DESCRIPTION
				" The request of a user command"
			::= { sleLldpMedNetworkPolicyProfilePolicyControl 1 }

		
		sleLldpMedNetworkPolicyProfilePolicyControlStatus OBJECT-TYPE
			SYNTAX SleControlStatusType
			MAX-ACCESS read-only
			STATUS current
			DESCRIPTION
				" The status of user command"
			::= { sleLldpMedNetworkPolicyProfilePolicyControl 2 }

		
		sleLldpMedNetworkPolicyProfilePolicyControlTimer OBJECT-TYPE
			SYNTAX Gauge32
			MAX-ACCESS read-write
			STATUS current
			DESCRIPTION
				" The maximum time for the manager for a long running user command"
			::= { sleLldpMedNetworkPolicyProfilePolicyControl 3 }

		
		sleLldpMedNetworkPolicyProfilePolicyControlTimeStamp OBJECT-TYPE
			SYNTAX TimeTicks
			MAX-ACCESS read-only
			STATUS current
			DESCRIPTION
				" The time stamp of the last command(end of command)"
			::= { sleLldpMedNetworkPolicyProfilePolicyControl 4 }

		
		sleLldpMedNetworkPolicyProfilePolicyControlReqResult OBJECT-TYPE
			SYNTAX SleControlRequestResultType
			MAX-ACCESS read-only
			STATUS current
			DESCRIPTION
				" The result of the last user command"
			::= { sleLldpMedNetworkPolicyProfilePolicyControl 5 }

		
		sleLldpMedNetworkPolicyProfilePolicyControlProfileIndex OBJECT-TYPE
			SYNTAX INTEGER (1..255)
			MAX-ACCESS read-write
			STATUS current
			DESCRIPTION
				"network-policy profile index"
			::= { sleLldpMedNetworkPolicyProfilePolicyControl 6 }

		
		sleLldpMedNetworkPolicyProfilePolicyControlAppType OBJECT-TYPE
			SYNTAX INTEGER
				{
				voice(1),
				voiceSignal(2),
				guestVoice(3),
				guestVoiceSignal(4),
				softphoneVoice(5),
				videoConfrence(6),
				streamVideo(7),
				viceoSignal(8)
				}
			MAX-ACCESS read-write
			STATUS current
			DESCRIPTION
				"Information about the per port per policy type policy 
				information for a particular physical network connection."
			::= { sleLldpMedNetworkPolicyProfilePolicyControl 7 }

		
		sleLldpMedNetworkPolicyProfilePolicyControlVlanId OBJECT-TYPE
			SYNTAX Integer32 (1..4094)
			MAX-ACCESS read-write
			STATUS current
			DESCRIPTION
				"An extension of the VLAN Identifier for the remote system
				connected to this port, as defined in IEEE 802.1P-1998.
				 
				A value of 1 through 4094 is used to define a valid PVID.
				 
				A value of 0 shall be used if the device is using priority tagged
				frames, meaning that only the 802.1p priority level is significant
				and the default VID of the ingress port is being used instead."
			::= { sleLldpMedNetworkPolicyProfilePolicyControl 8 }

		
		sleLldpMedNetworkPolicyProfilePolicyControlPriority OBJECT-TYPE
			SYNTAX Integer32 (0..7)
			MAX-ACCESS read-write
			STATUS current
			DESCRIPTION
				"This object contains the value of the 802.1p priority
				which is associated with the remote system connected at
				given port"
			::= { sleLldpMedNetworkPolicyProfilePolicyControl 9 }

		
		sleLldpMedNetworkPolicyProfilePolicyControlDscp OBJECT-TYPE
			SYNTAX Integer32 (0..63)
			MAX-ACCESS read-write
			STATUS current
			DESCRIPTION
				"This object contains the value of the Differentiated Service
				Code Point (DSCP) as defined in IETF RFC 2474 and RFC 2475
				which is associated with remote system connected at the port."
			::= { sleLldpMedNetworkPolicyProfilePolicyControl 10 }

		
		sleLldpMedNetworkPolicyProfilePolicyControlUnknown OBJECT-TYPE
			SYNTAX Boolean
			MAX-ACCESS read-write
			STATUS current
			DESCRIPTION
				"A value of 'true' indicates that the network policy for the specified application type is 
				currently unknown. In this case, the VLAN ID, the layer 2 priority and the DSCP value fields are ignored.
				A value of 'false' indicates that this network policy is defined"
			::= { sleLldpMedNetworkPolicyProfilePolicyControl 11 }

		
		sleLldpMedNetworkPolicyProfilePolicyNotifications OBJECT IDENTIFIER ::= { sleLldpMedNetworkPolicyProfilePolicy 3 }

		
		sleLldpMedNetworkPolicyProfilePolicyChanged NOTIFICATION-TYPE
			OBJECTS { sleLldpMedNetworkPolicyProfilePolicyControlRequest, sleLldpMedNetworkPolicyProfilePolicyControlProfileIndex, sleLldpMedNetworkPolicyProfilePolicyControlAppType, sleLldpMedNetworkPolicyProfilePolicyControlVlanId, sleLldpMedNetworkPolicyProfilePolicyControlPriority, 
				sleLldpMedNetworkPolicyProfilePolicyControlDscp, sleLldpMedNetworkPolicyProfilePolicyControlUnknown, sleLldpMedNetworkPolicyProfilePolicyControlTimeStamp, sleLldpMedNetworkPolicyProfilePolicyControlReqResult }
			STATUS current
			DESCRIPTION 
				"Create new MFDB entry."
			::= { sleLldpMedNetworkPolicyProfilePolicyNotifications 1 }

		
		sleLldpMedNetworkPolicyProfilePolicyDeleted NOTIFICATION-TYPE
			OBJECTS { sleLldpMedNetworkPolicyProfilePolicyControlRequest, sleLldpMedNetworkPolicyProfilePolicyControlProfileIndex, sleLldpMedNetworkPolicyProfilePolicyControlAppType, sleLldpMedNetworkPolicyProfilePolicyControlTimeStamp, sleLldpMedNetworkPolicyProfilePolicyControlReqResult
				 }
			STATUS current
			DESCRIPTION 
				"Create new MFDB entry."
			::= { sleLldpMedNetworkPolicyProfilePolicyNotifications 2 }

		
		sleLldpMedRemote OBJECT IDENTIFIER ::= { sleLldpMed 3 }

		
		sleLldpMedRemoteNetworkPolicyTable OBJECT-TYPE
			SYNTAX SEQUENCE OF SleLldpMedRemoteNetworkPolicyEntry
			MAX-ACCESS not-accessible
			STATUS current
			DESCRIPTION
				"Description."
			::= { sleLldpMedRemote 1 }

		
		sleLldpMedRemoteNetworkPolicyEntry OBJECT-TYPE
			SYNTAX SleLldpMedRemoteNetworkPolicyEntry
			MAX-ACCESS not-accessible
			STATUS current
			DESCRIPTION
				"Description."
			INDEX { sleLldpPortIndex, sleLldpRemIndex }
			::= { sleLldpMedRemoteNetworkPolicyTable 1 }

		
		SleLldpMedRemoteNetworkPolicyEntry ::=
			SEQUENCE { 
				sleLldpMedRemoteNetworkPolicyAppType
					INTEGER,
				sleLldpMedRemoteNetworkPolicyVlanId
					Integer32,
				sleLldpMedRemoteNetworkPolicyPriority
					Integer32,
				sleLldpMedRemoteNetworkPolicyDscp
					Integer32,
				sleLldpMedRemoteNetworkPolicyUnknown
					Boolean,
				sleLldpMedRemoteNetworkPolicyTagged
					Boolean
			 }

		sleLldpMedRemoteNetworkPolicyAppType OBJECT-TYPE
			SYNTAX INTEGER
				{
				unknown(0),
				voice(1),
				voiceSignal(2),
				guestVoice(3),
				guestVoiceSignal(4),
				softphoneVoice(5),
				videoConfrence(6),
				streamVideo(7),
				viceoSignal(8)
				}
			MAX-ACCESS read-only
			STATUS current
			DESCRIPTION
				"Information about the per port per policy type policy 
				information for a particular physical network connection."
			::= { sleLldpMedRemoteNetworkPolicyEntry 1 }

		
		sleLldpMedRemoteNetworkPolicyVlanId OBJECT-TYPE
			SYNTAX Integer32 (0 | 1..4094 | 4095)
			MAX-ACCESS read-only
			STATUS current
			DESCRIPTION
				"An extension of the VLAN Identifier for the remote system
				connected to this port, as defined in IEEE 802.1P-1998.
				
				A value of 1 through 4094 is used to define a valid PVID.
				
				A value of 0 shall be used if the device is using priority tagged
				frames, meaning that only the 802.1p priority level is significant
				and the default VID of the ingress port is being used instead.
				
				A value of 4095 is reserved for implementation use."
			::= { sleLldpMedRemoteNetworkPolicyEntry 2 }

		
		sleLldpMedRemoteNetworkPolicyPriority OBJECT-TYPE
			SYNTAX Integer32 (0..7)
			MAX-ACCESS read-only
			STATUS current
			DESCRIPTION
				"This object contains the value of the 802.1p priority
				which is associated with the remote system connected at
				given port."
			::= { sleLldpMedRemoteNetworkPolicyEntry 3 }

		
		sleLldpMedRemoteNetworkPolicyDscp OBJECT-TYPE
			SYNTAX Integer32 (0..63)
			MAX-ACCESS read-only
			STATUS current
			DESCRIPTION
				"This object contains the value of the Differentiated Service
				Code Point (DSCP) as defined in IETF RFC 2474 and RFC 2475
				which is associated with remote system connected at the port."
			::= { sleLldpMedRemoteNetworkPolicyEntry 4 }

		
		sleLldpMedRemoteNetworkPolicyUnknown OBJECT-TYPE
			SYNTAX Boolean
			MAX-ACCESS read-only
			STATUS current
			DESCRIPTION
				"This object contains the value of the Differentiated Service
				Code Point (DSCP) as defined in IETF RFC 2474 and RFC 2475
				which is associated with remote system connected at the port."
			::= { sleLldpMedRemoteNetworkPolicyEntry 5 }

		
		sleLldpMedRemoteNetworkPolicyTagged OBJECT-TYPE
			SYNTAX Boolean
			MAX-ACCESS read-only
			STATUS current
			DESCRIPTION
				"description"
			::= { sleLldpMedRemoteNetworkPolicyEntry 6 }

		
		sleLldpMedRemoteLocationTable OBJECT-TYPE
			SYNTAX SEQUENCE OF SleLldpMedRemoteLocationEntry
			MAX-ACCESS not-accessible
			STATUS current
			DESCRIPTION
				"Description."
			::= { sleLldpMedRemote 2 }

		
		sleLldpMedRemoteLocationEntry OBJECT-TYPE
			SYNTAX SleLldpMedRemoteLocationEntry
			MAX-ACCESS not-accessible
			STATUS current
			DESCRIPTION
				"Description."
			INDEX { sleLldpPortIndex, sleLldpRemIndex }
			::= { sleLldpMedRemoteLocationTable 1 }

		
		SleLldpMedRemoteLocationEntry ::=
			SEQUENCE { 
				sleLldpMedRemoteLocationSubType
					INTEGER,
				sleLldpMedRemoteLocationInfo
					OCTET STRING
			 }

		sleLldpMedRemoteLocationSubType OBJECT-TYPE
			SYNTAX INTEGER
				{
				unknown(1),
				coordinateBased(2),
				civicAddress(3),
				elin(4)
				}
			MAX-ACCESS read-only
			STATUS current
			DESCRIPTION
				"The location subtype advertised by the remote endpoint."
			::= { sleLldpMedRemoteLocationEntry 1 }

		
		sleLldpMedRemoteLocationInfo OBJECT-TYPE
			SYNTAX OCTET STRING
			MAX-ACCESS read-only
			STATUS current
			DESCRIPTION
				"The location information advertised by the remote endpoint.
				Parsing of this information is dependent upon the location 
				subtype, as defined by the value of the corresponding
				lldpXMedRemLocationSubType object.
				
				A value of 4095 is reserved for implementation use."
			::= { sleLldpMedRemoteLocationEntry 2 }

		
		sleLldpMedRemoteInventoryTable OBJECT-TYPE
			SYNTAX SEQUENCE OF SleLldpMedRemoteInventoryEntry
			MAX-ACCESS not-accessible
			STATUS current
			DESCRIPTION
				"Description."
			::= { sleLldpMedRemote 3 }

		
		sleLldpMedRemoteInventoryEntry OBJECT-TYPE
			SYNTAX SleLldpMedRemoteInventoryEntry
			MAX-ACCESS not-accessible
			STATUS current
			DESCRIPTION
				"Description."
			INDEX { sleLldpPortIndex, sleLldpRemIndex }
			::= { sleLldpMedRemoteInventoryTable 1 }

		
		SleLldpMedRemoteInventoryEntry ::=
			SEQUENCE { 
				sleLldpMedRemoteHardwareRev
					OCTET STRING,
				sleLldpMedRemoteFirmwareWRev
					OCTET STRING,
				sleLldpMedRemoteSoftwareRev
					OCTET STRING,
				sleLldpMedRemoteSerialNum
					OCTET STRING,
				sleLldpMedRemoteMfgName
					OCTET STRING,
				sleLldpMedRemoteModelName
					OCTET STRING,
				sleLldpMedRemoteAssetID
					OCTET STRING
			 }

		sleLldpMedRemoteHardwareRev OBJECT-TYPE
			SYNTAX OCTET STRING
			MAX-ACCESS read-only
			STATUS current
			DESCRIPTION
				"The vendor-specific hardware revision string as advertised by the remote endpoint.."
			::= { sleLldpMedRemoteInventoryEntry 1 }

		
		sleLldpMedRemoteFirmwareWRev OBJECT-TYPE
			SYNTAX OCTET STRING
			MAX-ACCESS read-only
			STATUS current
			DESCRIPTION
				"The vendor-specific firmware revision string as advertised by the remote endpoint."
			::= { sleLldpMedRemoteInventoryEntry 2 }

		
		sleLldpMedRemoteSoftwareRev OBJECT-TYPE
			SYNTAX OCTET STRING
			MAX-ACCESS read-only
			STATUS current
			DESCRIPTION
				"The vendor-specific software revision string as advertised by the remote endpoint.."
			::= { sleLldpMedRemoteInventoryEntry 3 }

		
		sleLldpMedRemoteSerialNum OBJECT-TYPE
			SYNTAX OCTET STRING
			MAX-ACCESS read-only
			STATUS current
			DESCRIPTION
				"The vendor-specific serial number as advertised by the remote endpoint."
			::= { sleLldpMedRemoteInventoryEntry 4 }

		
		sleLldpMedRemoteMfgName OBJECT-TYPE
			SYNTAX OCTET STRING
			MAX-ACCESS read-only
			STATUS current
			DESCRIPTION
				"The vendor-specific manufacturer name as advertised by the remote endpoint."
			::= { sleLldpMedRemoteInventoryEntry 5 }

		
		sleLldpMedRemoteModelName OBJECT-TYPE
			SYNTAX OCTET STRING
			MAX-ACCESS read-only
			STATUS current
			DESCRIPTION
				"The vendor-specific model name as advertised by the remote endpoint."
			::= { sleLldpMedRemoteInventoryEntry 6 }

		
		sleLldpMedRemoteAssetID OBJECT-TYPE
			SYNTAX OCTET STRING
			MAX-ACCESS read-only
			STATUS current
			DESCRIPTION
				"The vendor-specific asset tracking identifier as advertised by the remote endpoint."
			::= { sleLldpMedRemoteInventoryEntry 7 }

		
		sleBridgeInterface OBJECT IDENTIFIER ::= { sleBridge 32 }

		
		sleBridgeInterfaceTable OBJECT-TYPE
			SYNTAX SEQUENCE OF SleBridgeInterfaceEntry
			MAX-ACCESS not-accessible
			STATUS current
			DESCRIPTION
				"Description."
			::= { sleBridgeInterface 1 }

		
		sleBridgeInterfaceEntry OBJECT-TYPE
			SYNTAX SleBridgeInterfaceEntry
			MAX-ACCESS not-accessible
			STATUS current
			DESCRIPTION
				"Description."
			INDEX { sleBridgeInterfaceIndex }
			::= { sleBridgeInterfaceTable 1 }

		
		SleBridgeInterfaceEntry ::=
			SEQUENCE { 
				sleBridgeInterfaceIndex
					Integer32,
				sleBridgeInterfaceName
					OCTET STRING,
				sleBridgeInterfaceType
					INTEGER,
				sleBridgeInterfaceMode
					INTEGER,
				sleBridgeInterfaceDefaultVlan
					Integer32,
				sleBridgeInterfacePvid
					Integer32,
				sleBridgeInterfaceIngressFilter
					INTEGER,
				sleBridgeInterfaceAllowedVlanFlags
					INTEGER,
				sleBridgeInterfaceAllowedVlan
					OCTET STRING,
				sleBridgeInterfaceNativeVlan
					Integer32,
				sleBridgeInterfaceChannelGroupAggrId
					Integer32,
				sleBridgeInterfaceChannelGroupMode
					INTEGER,
				sleBridgeInterfaceChannelGroupState
					INTEGER,
				sleBridgeInterfaceChannelGroupLacpAggrMode
					INTEGER,
				sleBridgeInterfaceChannelGroupAdminKey
					Integer32,
				sleBridgeInterfaceChannelGroupAggrType
					INTEGER,
				sleBridgeInterfaceChannelGroupPriority
					Integer32,
				sleBridgeInterfaceChannelGroupTimeOut
					INTEGER,
				sleBridgeInterfaceChannelGroupActiveLink
					Integer32,
				sleBridgeInterfaceChannelGroupDistMode
					INTEGER,
				sleBridgeInterfaceSubMode
					INTEGER,
				sleBridgeInterfaceAcceptableFramType
					INTEGER,
				sleBridgeInterfaceEgressTagged
					OCTET STRING,
				sleBridgeInterfaceVlanTranslation
					OCTET STRING,
				sleBridgeInterfaceCVlanRegistraionName
					OCTET STRING,
				sleBridgeInterfacePEVlanId
					OCTET STRING,
				sleBridgeInterfacePEDefaultVlanId
					OCTET STRING,
				sleBridgeInterfacePEUntaggedVlanId
					OCTET STRING,
				sleBridgeInterfaceDefaulSVlanId
					Integer32,
				sleBridgeInterfacePrivateVlanHostAssociationPrimaryVid
					Integer32,
				sleBridgeInterfacePrivateVlanHostAssociationPvid
					Integer32,
				sleBridgeInterfacePrivateVlanMappingPvid
					Integer32,
				sleBridgeInterfacePrivateVlanMappingSecondaryVid
					Integer32,
				sleBridgeInterfaceGroup
					Integer32,
				sleBridgeInterfaceGroupSpanningTree
					Integer32,
				sleBridgeInterfaceProviderNetworkEtherType
					INTEGER
			 }

		sleBridgeInterfaceIndex OBJECT-TYPE
			SYNTAX Integer32 (1..65535)
			MAX-ACCESS read-only
			STATUS current
			DESCRIPTION
				"The interface index."
			::= { sleBridgeInterfaceEntry 1 }

		
		sleBridgeInterfaceName OBJECT-TYPE
			SYNTAX OCTET STRING
			MAX-ACCESS read-only
			STATUS current
			DESCRIPTION
				"The interface name."
			::= { sleBridgeInterfaceEntry 2 }

		
		sleBridgeInterfaceType OBJECT-TYPE
			SYNTAX INTEGER
				{
				switchedPort(1),
				routedPort(2)
				}
			MAX-ACCESS read-only
			STATUS current
			DESCRIPTION
				"The interface type
				1:swtiched port 2:routed port"
			::= { sleBridgeInterfaceEntry 3 }

		
		sleBridgeInterfaceMode OBJECT-TYPE
			SYNTAX INTEGER
				{
				invalid(0),
				access(1),
				hybrid(2),
				trunk(3),
				ce(4),
				cn(5),
				pn(6),
				pe(7),
				cnp(8),
				vip(9),
				pip(10),
				cbp(11)
				}
			MAX-ACCESS read-only
			STATUS current
			DESCRIPTION
				"The interface mode"
			::= { sleBridgeInterfaceEntry 4 }

		
		sleBridgeInterfaceDefaultVlan OBJECT-TYPE
			SYNTAX Integer32 (1..4094)
			MAX-ACCESS read-only
			STATUS current
			DESCRIPTION
				"The default vlan"
			::= { sleBridgeInterfaceEntry 5 }

		
		sleBridgeInterfacePvid OBJECT-TYPE
			SYNTAX Integer32 (1..4094)
			MAX-ACCESS read-only
			STATUS current
			DESCRIPTION
				"The interface pvid"
			::= { sleBridgeInterfaceEntry 6 }

		
		sleBridgeInterfaceIngressFilter OBJECT-TYPE
			SYNTAX INTEGER
				{
				disable(0),
				enable(1)
				}
			MAX-ACCESS read-only
			STATUS current
			DESCRIPTION
				"The interface ingress filter"
			::= { sleBridgeInterfaceEntry 7 }

		
		sleBridgeInterfaceAllowedVlanFlags OBJECT-TYPE
			SYNTAX INTEGER
				{
				none(1),
				add(2),
				except(3),
				remove(4),
				all(255)
				}
			MAX-ACCESS read-only
			STATUS current
			DESCRIPTION
				"The allowed vlan flag"
			::= { sleBridgeInterfaceEntry 8 }

		
		sleBridgeInterfaceAllowedVlan OBJECT-TYPE
			SYNTAX OCTET STRING
			MAX-ACCESS read-only
			STATUS current
			DESCRIPTION
				"The allowed vlan."
			::= { sleBridgeInterfaceEntry 9 }

		
		sleBridgeInterfaceNativeVlan OBJECT-TYPE
			SYNTAX Integer32 (1..4094)
			MAX-ACCESS read-only
			STATUS current
			DESCRIPTION
				"The native vlan id."
			::= { sleBridgeInterfaceEntry 10 }

		
		sleBridgeInterfaceChannelGroupAggrId OBJECT-TYPE
			SYNTAX Integer32 (0..65535)
			MAX-ACCESS read-only
			STATUS current
			DESCRIPTION
				"The channel group LAG aggregation ID"
			::= { sleBridgeInterfaceEntry 11 }

		
		sleBridgeInterfaceChannelGroupMode OBJECT-TYPE
			SYNTAX INTEGER
				{
				inactive(0),
				static(1),
				lacp(2)
				}
			MAX-ACCESS read-only
			STATUS current
			DESCRIPTION
				"The channel group mode."
			::= { sleBridgeInterfaceEntry 12 }

		
		sleBridgeInterfaceChannelGroupState OBJECT-TYPE
			SYNTAX INTEGER
				{
				none(0),
				aggregated(1),
				aggregator(2)
				}
			MAX-ACCESS read-only
			STATUS current
			DESCRIPTION
				"The channel group state."
			::= { sleBridgeInterfaceEntry 13 }

		
		sleBridgeInterfaceChannelGroupLacpAggrMode OBJECT-TYPE
			SYNTAX INTEGER
				{
				active(1),
				passive(2)
				}
			MAX-ACCESS read-only
			STATUS current
			DESCRIPTION
				"The channel group LACP aggregation mode"
			::= { sleBridgeInterfaceEntry 14 }

		
		sleBridgeInterfaceChannelGroupAdminKey OBJECT-TYPE
			SYNTAX Integer32 (1..15)
			MAX-ACCESS read-only
			STATUS current
			DESCRIPTION
				"The channel group LACP admin key 
				default:1
				"
			::= { sleBridgeInterfaceEntry 15 }

		
		sleBridgeInterfaceChannelGroupAggrType OBJECT-TYPE
			SYNTAX INTEGER
				{
				aggregatable(1),
				individual(2)
				}
			MAX-ACCESS read-only
			STATUS current
			DESCRIPTION
				"The channel group LACP aggregatable type. 
				default: 0 aggregatable
				"
			::= { sleBridgeInterfaceEntry 16 }

		
		sleBridgeInterfaceChannelGroupPriority OBJECT-TYPE
			SYNTAX Integer32 (1..65535)
			MAX-ACCESS read-only
			STATUS current
			DESCRIPTION
				"The channel group priority (default:32768)"
			::= { sleBridgeInterfaceEntry 17 }

		
		sleBridgeInterfaceChannelGroupTimeOut OBJECT-TYPE
			SYNTAX INTEGER
				{
				long(0),
				short(1)
				}
			MAX-ACCESS read-only
			STATUS current
			DESCRIPTION
				"The channel group time out (default:0 long)"
			::= { sleBridgeInterfaceEntry 18 }

		
		sleBridgeInterfaceChannelGroupActiveLink OBJECT-TYPE
			SYNTAX Integer32 (1..8)
			MAX-ACCESS read-only
			STATUS current
			DESCRIPTION
				"The channel group interface active link (default: 1)"
			::= { sleBridgeInterfaceEntry 19 }

		
		sleBridgeInterfaceChannelGroupDistMode OBJECT-TYPE
			SYNTAX INTEGER
				{
				none(0),
				srcmac(1),
				dstmac(2),
				srcdstmac(3),
				srcip(4),
				dstip(5),
				srcdstip(6),
				srcdstl4(7),
				label(8),
				srcport(9),
				dstport(10),
				srcdstport(11),
				rtag7(12)
				}
			MAX-ACCESS read-only
			STATUS current
			DESCRIPTION
				"The channel group distribution method of aggregator mode. (default: 3 srcdstmac)"
			::= { sleBridgeInterfaceEntry 20 }

		
		sleBridgeInterfaceSubMode OBJECT-TYPE
			SYNTAX INTEGER
				{
				invalid(0),
				access(1),
				hybrid(2),
				trunk(3),
				ce(4),
				cn(5),
				pn(6),
				pe(7),
				cnp(8),
				vip(9),
				pip(10),
				cbp(11)
				}
			MAX-ACCESS read-only
			STATUS current
			DESCRIPTION
				"The interface mode"
			::= { sleBridgeInterfaceEntry 21 }

		
		sleBridgeInterfaceAcceptableFramType OBJECT-TYPE
			SYNTAX INTEGER
				{
				none(0),
				all(1),
				vlanTagged(2)
				}
			MAX-ACCESS read-only
			STATUS current
			DESCRIPTION
				"set the layer 2 interface acceptable frames types"
			::= { sleBridgeInterfaceEntry 22 }

		
		sleBridgeInterfaceEgressTagged OBJECT-TYPE
			SYNTAX OCTET STRING
			MAX-ACCESS read-only
			STATUS current
			DESCRIPTION
				"set the layer 2 interface acceptable egress tagges vlans"
			::= { sleBridgeInterfaceEntry 23 }

		
		sleBridgeInterfaceVlanTranslation OBJECT-TYPE
			SYNTAX OCTET STRING
			MAX-ACCESS read-only
			STATUS current
			DESCRIPTION
				"to configure a VLAN translation table for the interface	the vlan which should be translated
				FORMAT: From:To, From:To, ..."
			::= { sleBridgeInterfaceEntry 24 }

		
		sleBridgeInterfaceCVlanRegistraionName OBJECT-TYPE
			SYNTAX OCTET STRING
			MAX-ACCESS read-only
			STATUS current
			DESCRIPTION
				"to configure the VLAN registration"
			::= { sleBridgeInterfaceEntry 25 }

		
		sleBridgeInterfacePEVlanId OBJECT-TYPE
			SYNTAX OCTET STRING
			MAX-ACCESS read-only
			STATUS current
			DESCRIPTION
				"to configure the provider edge VLAN "
			::= { sleBridgeInterfaceEntry 26 }

		
		sleBridgeInterfacePEDefaultVlanId OBJECT-TYPE
			SYNTAX OCTET STRING
			MAX-ACCESS read-only
			STATUS current
			DESCRIPTION
				"to configure the provider edge default VLAN "
			::= { sleBridgeInterfaceEntry 27 }

		
		sleBridgeInterfacePEUntaggedVlanId OBJECT-TYPE
			SYNTAX OCTET STRING
			MAX-ACCESS read-only
			STATUS current
			DESCRIPTION
				"to configure the provider edge untagged VLAN "
			::= { sleBridgeInterfaceEntry 28 }

		
		sleBridgeInterfaceDefaulSVlanId OBJECT-TYPE
			SYNTAX Integer32 (1..4095)
			MAX-ACCESS read-only
			STATUS current
			DESCRIPTION
				"to configure the customer edge default Svlan for trunk and hybrid."
			::= { sleBridgeInterfaceEntry 29 }

		
		sleBridgeInterfacePrivateVlanHostAssociationPrimaryVid OBJECT-TYPE
			SYNTAX Integer32 (0 | 2..4094)
			MAX-ACCESS read-only
			STATUS current
			DESCRIPTION
				"Switchport Pvivate Vlan Host Association Primary Vid"
			::= { sleBridgeInterfaceEntry 30 }

		
		sleBridgeInterfacePrivateVlanHostAssociationPvid OBJECT-TYPE
			SYNTAX Integer32 (0 | 2..4094)
			MAX-ACCESS read-only
			STATUS current
			DESCRIPTION
				"Switchport Pvivate Vlan Host Association Pvid"
			::= { sleBridgeInterfaceEntry 31 }

		
		sleBridgeInterfacePrivateVlanMappingPvid OBJECT-TYPE
			SYNTAX Integer32 (0 | 2..4094)
			MAX-ACCESS read-only
			STATUS current
			DESCRIPTION
				"Switchport Pvivate Vlan Mapping Pvid"
			::= { sleBridgeInterfaceEntry 32 }

		
		sleBridgeInterfacePrivateVlanMappingSecondaryVid OBJECT-TYPE
			SYNTAX Integer32 (0 | 2..4094)
			MAX-ACCESS read-only
			STATUS current
			DESCRIPTION
				"Switchport Pvivate Vlan Mapping Secondary Vid"
			::= { sleBridgeInterfaceEntry 33 }

		
		sleBridgeInterfaceGroup OBJECT-TYPE
			SYNTAX Integer32
			MAX-ACCESS read-only
			STATUS current
			DESCRIPTION
				"Description."
			::= { sleBridgeInterfaceEntry 34 }

		
		sleBridgeInterfaceGroupSpanningTree OBJECT-TYPE
			SYNTAX Integer32
			MAX-ACCESS read-only
			STATUS current
			DESCRIPTION
				"Description."
			::= { sleBridgeInterfaceEntry 35 }

		
		sleBridgeInterfaceProviderNetworkEtherType OBJECT-TYPE
			SYNTAX INTEGER
				{
				none(-1),
				value0x88a8(0),
				value0x8100(1),
				value0x9100(2)
				}
			MAX-ACCESS read-only
			STATUS current
			DESCRIPTION
				"The ether-type for provider network mode. (default: value0x88a8)"
			::= { sleBridgeInterfaceEntry 36 }

		
		sleBridgeInterfaceControl OBJECT IDENTIFIER ::= { sleBridgeInterface 2 }

		
		sleBridgeInterfaceControlRequest OBJECT-TYPE
			SYNTAX INTEGER
				{
				setSwitchport(1),
				setSwitchportDefaultVlan(2),
				delSwitchportDefaultVlan(3),
				setSwitchportAllowedVlan(4),
				setSwitchportMode(5),
				setSwitchportModeIngressFilter(6),
				delSwitchportTrunk(7),
				setSwitchportTrunkNativeVlan(8),
				delSwitchportTrunkNativeVlan(9),
				setChannelGroup(10),
				delChannelGroup(11),
				setChannelGroupAdminKey(12),
				setChannelGroupAggrType(13),
				setChannelGroupPriority(14),
				setChannelGroupTimeOut(15),
				setChannelGroupActiveLink(16),
				setChannelGroupDistMode(17),
				setInterfacePvid(18),
				unsetBridgeIfSwitchStatus(19),
				setSwitchportCvlanRegistration(20),
				delSwitchportCvlanRegistration(21),
				setAcceptableFrameType(22),
				setProviderEdge(23),
				setVlanTranslation(24),
				unsetVlanTranslation(25),
				setSwitchportDefaultSVlan(26),
				unsetSwitchportDefaultSVlan(27),
				setSwitchportPrivateVlanHostAssociation(28),
				delSwitchportPrivateVlanHostAssociation(29),
				addSwitchportPrivateVlanMapping(30),
				removeSwitchportPrivateVlanMapping(31),
				setBridgeGroup(32),
				unsetBridgeGroup(33),
				setBridgeGroupSpanningTree(34),
				setProviderNetworkEtherType(35)
				}
			MAX-ACCESS read-write
			STATUS current
			DESCRIPTION
				" The request of a user command"
			::= { sleBridgeInterfaceControl 1 }

		
		sleBridgeInterfaceControlStatus OBJECT-TYPE
			SYNTAX SleControlStatusType
			MAX-ACCESS read-only
			STATUS current
			DESCRIPTION
				" The status of user command"
			::= { sleBridgeInterfaceControl 2 }

		
		sleBridgeInterfaceControlTimer OBJECT-TYPE
			SYNTAX Gauge32
			MAX-ACCESS read-write
			STATUS current
			DESCRIPTION
				" The maximum time for the manager for a long running user command"
			::= { sleBridgeInterfaceControl 3 }

		
		sleBridgeInterfaceControlTimeStamp OBJECT-TYPE
			SYNTAX TimeTicks
			MAX-ACCESS read-only
			STATUS current
			DESCRIPTION
				" The time stamp of the last command(end of command)"
			::= { sleBridgeInterfaceControl 4 }

		
		sleBridgeInterfaceControlReqResult OBJECT-TYPE
			SYNTAX SleControlRequestResultType
			MAX-ACCESS read-only
			STATUS current
			DESCRIPTION
				" The result of the last user command"
			::= { sleBridgeInterfaceControl 5 }

		
		sleBridgeInterfaceControlIndex OBJECT-TYPE
			SYNTAX Integer32 (1..65535)
			MAX-ACCESS read-write
			STATUS current
			DESCRIPTION
				"The interface index."
			::= { sleBridgeInterfaceControl 6 }

		
		sleBridgeInterfaceControlMode OBJECT-TYPE
			SYNTAX INTEGER
				{
				invalid(0),
				access(1),
				hybrid(2),
				trunk(3),
				ce(4),
				cn(5),
				pn(6),
				pe(7),
				cnp(8),
				vip(9),
				pip(10),
				cbp(11)
				}
			MAX-ACCESS read-write
			STATUS current
			DESCRIPTION
				"The interface mode"
			::= { sleBridgeInterfaceControl 7 }

		
		sleBridgeInterfaceControlDefaultVlan OBJECT-TYPE
			SYNTAX Integer32 (1..4094)
			MAX-ACCESS read-write
			STATUS current
			DESCRIPTION
				"The default vlan"
			::= { sleBridgeInterfaceControl 8 }

		
		sleBridgeInterfaceControlPvid OBJECT-TYPE
			SYNTAX Integer32 (1..4094)
			MAX-ACCESS read-write
			STATUS current
			DESCRIPTION
				"The interface pvid"
			::= { sleBridgeInterfaceControl 9 }

		
		sleBridgeInterfaceControlIngressFilter OBJECT-TYPE
			SYNTAX INTEGER
				{
				disable(0),
				enable(1)
				}
			MAX-ACCESS read-write
			STATUS current
			DESCRIPTION
				"The interface ingress filter"
			::= { sleBridgeInterfaceControl 10 }

		
		sleBridgeInterfaceControlAllowedVlanFlags OBJECT-TYPE
			SYNTAX INTEGER
				{
				none(1),
				add(2),
				except(3),
				remove(4),
				all(255)
				}
			MAX-ACCESS read-write
			STATUS current
			DESCRIPTION
				"The allowed vlan flag"
			::= { sleBridgeInterfaceControl 11 }

		
		sleBridgeInterfaceControlAllowedVlan OBJECT-TYPE
			SYNTAX OCTET STRING
			MAX-ACCESS read-write
			STATUS current
			DESCRIPTION
				"The allowed vlan."
			::= { sleBridgeInterfaceControl 12 }

		
		sleBridgeInterfaceControlNativeVlan OBJECT-TYPE
			SYNTAX Integer32 (1..4094)
			MAX-ACCESS read-write
			STATUS current
			DESCRIPTION
				"The native vlan id."
			::= { sleBridgeInterfaceControl 13 }

		
		sleBridgeInterfaceControlChannelGroupAggrId OBJECT-TYPE
			SYNTAX Integer32 (0..65535)
			MAX-ACCESS read-write
			STATUS current
			DESCRIPTION
				"The channel group LAG aggregation ID"
			::= { sleBridgeInterfaceControl 14 }

		
		sleBridgeInterfaceControlChannelGroupMode OBJECT-TYPE
			SYNTAX INTEGER
				{
				inactive(0),
				static(1),
				lacp(2)
				}
			MAX-ACCESS read-write
			STATUS current
			DESCRIPTION
				"The channel group mode."
			::= { sleBridgeInterfaceControl 15 }

		
		sleBridgeInterfaceControlChannelGroupLacpAggrMode OBJECT-TYPE
			SYNTAX INTEGER
				{
				active(1),
				passive(2)
				}
			MAX-ACCESS read-write
			STATUS current
			DESCRIPTION
				"The channel group LACP aggregation mode"
			::= { sleBridgeInterfaceControl 16 }

		
		sleBridgeInterfaceControlChannelGroupAdminKey OBJECT-TYPE
			SYNTAX Integer32 (1..15)
			MAX-ACCESS read-write
			STATUS current
			DESCRIPTION
				"The channel group admin key (default:1)"
			::= { sleBridgeInterfaceControl 17 }

		
		sleBridgeInterfaceControlChannelGroupAggrType OBJECT-TYPE
			SYNTAX INTEGER
				{
				aggregatable(0),
				individual(1)
				}
			MAX-ACCESS read-write
			STATUS current
			DESCRIPTION
				"The channel group aggregatable type. (default: 0 aggregatable)"
			::= { sleBridgeInterfaceControl 18 }

		
		sleBridgeInterfaceControlChannelGroupPriority OBJECT-TYPE
			SYNTAX Integer32 (1..65535)
			MAX-ACCESS read-write
			STATUS current
			DESCRIPTION
				"The channel group priority (default:32768)"
			::= { sleBridgeInterfaceControl 19 }

		
		sleBridgeInterfaceControlChannelGroupTimeOut OBJECT-TYPE
			SYNTAX INTEGER
				{
				long(0),
				short(1)
				}
			MAX-ACCESS read-write
			STATUS current
			DESCRIPTION
				"The channel group interface active link (default: 1)"
			::= { sleBridgeInterfaceControl 20 }

		
		sleBridgeInterfaceControlChannelGroupActiveLink OBJECT-TYPE
			SYNTAX Integer32 (1..8)
			MAX-ACCESS read-write
			STATUS current
			DESCRIPTION
				"The channel group time out (default:0 long)"
			::= { sleBridgeInterfaceControl 21 }

		
		sleBridgeInterfaceControlChannelGroupDistMode OBJECT-TYPE
			SYNTAX INTEGER
				{
				none(0),
				srcmac(1),
				dstmac(2),
				srcdstmac(3),
				srcip(4),
				dstip(5),
				srcdstip(6),
				srcdstl4(7),
				label(8),
				srcport(9),
				dstport(10),
				srcdstport(11),
				rtag7(12)
				}
			MAX-ACCESS read-write
			STATUS current
			DESCRIPTION
				"The channel group distribution method of aggregator mode. (default: 3 srcdstmac)"
			::= { sleBridgeInterfaceControl 22 }

		
		sleBridgeInterfaceControlSubMode OBJECT-TYPE
			SYNTAX INTEGER
				{
				invalid(0),
				access(1),
				hybrid(2),
				trunk(3)
				}
			MAX-ACCESS read-write
			STATUS current
			DESCRIPTION
				"The interface mode"
			::= { sleBridgeInterfaceControl 23 }

		
		sleBridgeInterfaceControlAcceptableFramType OBJECT-TYPE
			SYNTAX INTEGER
				{
				none(0),
				all(1),
				vlanTagged(2)
				}
			MAX-ACCESS read-write
			STATUS current
			DESCRIPTION
				"set the layer 2 interface acceptable frames types"
			::= { sleBridgeInterfaceControl 24 }

		
		sleBridgeInterfaceControlEgressTagged OBJECT-TYPE
			SYNTAX INTEGER
				{
				disable(0),
				enable(1)
				}
			MAX-ACCESS read-write
			STATUS current
			DESCRIPTION
				"set the layer 2 interface acceptable frames types"
			DEFVAL { 1 }
			::= { sleBridgeInterfaceControl 25 }

		
		sleBridgeInterfaceControlVlanTranslate OBJECT-TYPE
			SYNTAX INTEGER (0..4095)
			MAX-ACCESS read-write
			STATUS current
			DESCRIPTION
				"to configure a VLAN translation table for the interface
				the vlan which should be translated"
			::= { sleBridgeInterfaceControl 26 }

		
		sleBridgeInterfaceControlVlanToBeTranslated OBJECT-TYPE
			SYNTAX INTEGER (0..4095)
			MAX-ACCESS read-write
			STATUS current
			DESCRIPTION
				"to configure a VLAN translation table for the interface
				the vlan which is translated"
			::= { sleBridgeInterfaceControl 27 }

		
		sleBridgeInterfaceControlCVlanRegistraionName OBJECT-TYPE
			SYNTAX OCTET STRING
			MAX-ACCESS read-write
			STATUS current
			DESCRIPTION
				"to configure the VLAN registration"
			::= { sleBridgeInterfaceControl 28 }

		
		sleBridgeInterfaceControlPEVlanId OBJECT-TYPE
			SYNTAX INTEGER (0..4095)
			MAX-ACCESS read-write
			STATUS current
			DESCRIPTION
				"to configure a provider edge vlan"
			::= { sleBridgeInterfaceControl 29 }

		
		sleBridgeInterfaceControlPEDefaultVlanId OBJECT-TYPE
			SYNTAX INTEGER (0..4095)
			MAX-ACCESS read-write
			STATUS current
			DESCRIPTION
				"to configure a provider edge default vlan"
			::= { sleBridgeInterfaceControl 30 }

		
		sleBridgeInterfaceControlPEUntaggedVlanId OBJECT-TYPE
			SYNTAX INTEGER (0..4095)
			MAX-ACCESS read-write
			STATUS current
			DESCRIPTION
				"to configure a provider edge untagged vlan"
			::= { sleBridgeInterfaceControl 31 }

		
		sleBridgeInterfaceControlPrivateVlanHostAssociationPrimaryVid OBJECT-TYPE
			SYNTAX Integer32 (2..4094)
			MAX-ACCESS read-write
			STATUS current
			DESCRIPTION
				"Switchport Pvivate Vlan Host Association Primary Vid"
			::= { sleBridgeInterfaceControl 32 }

		
		sleBridgeInterfaceControlPrivateVlanHostAssociationPvid OBJECT-TYPE
			SYNTAX Integer32 (2..4094)
			MAX-ACCESS read-write
			STATUS current
			DESCRIPTION
				"Switchport Pvivate Vlan Host Association Pvid"
			::= { sleBridgeInterfaceControl 33 }

		
		sleBridgeInterfaceControlPrivateVlanMappingPvid OBJECT-TYPE
			SYNTAX Integer32 (2..4094)
			MAX-ACCESS read-write
			STATUS current
			DESCRIPTION
				"Switchport Pvivate Vlan Mapping Pvid"
			::= { sleBridgeInterfaceControl 34 }

		
		sleBridgeInterfaceControlPrivateVlanMappingSecondaryVid OBJECT-TYPE
			SYNTAX Integer32 (2..4094)
			MAX-ACCESS read-write
			STATUS current
			DESCRIPTION
				"Switchport Pvivate Vlan Mapping Secondary Vid"
			::= { sleBridgeInterfaceControl 35 }

		
		sleBridgeInterfaceControlGroup OBJECT-TYPE
			SYNTAX Integer32
			MAX-ACCESS read-write
			STATUS current
			DESCRIPTION
				"Description."
			::= { sleBridgeInterfaceControl 36 }

		
		sleBridgeInterfaceControlGroupSpanningTree OBJECT-TYPE
			SYNTAX Integer32
			MAX-ACCESS read-write
			STATUS current
			DESCRIPTION
				"Description."
			::= { sleBridgeInterfaceControl 37 }

		
		sleBridgeInterfaceControlProviderNetworkEtherType OBJECT-TYPE
			SYNTAX INTEGER
				{
				value0x88a8(0),
				value0x8100(1),
				value0x9100(2)
				}
			MAX-ACCESS read-write
			STATUS current
			DESCRIPTION
				"The ether-type for provider network mode. (default: value0x88a8)"
			::= { sleBridgeInterfaceControl 38 }

		
		sleBridgeInterfaceNotification OBJECT IDENTIFIER ::= { sleBridgeInterface 3 }

		
		sleBridgeInterfaceSwitchportChanged NOTIFICATION-TYPE
			OBJECTS { sleBridgeInterfaceControlRequest, sleBridgeInterfaceControlTimeStamp, sleBridgeInterfaceControlReqResult, sleBridgeInterfaceControlIndex }
			STATUS current
			DESCRIPTION 
				"setSwitchport"
			::= { sleBridgeInterfaceNotification 1 }

		
		sleBridgeInterfaceSwitchportDefaultVlanChanged NOTIFICATION-TYPE
			OBJECTS { sleBridgeInterfaceControlRequest, sleBridgeInterfaceControlTimeStamp, sleBridgeInterfaceControlReqResult, sleBridgeInterfaceControlIndex, sleBridgeInterfaceControlDefaultVlan
				 }
			STATUS current
			DESCRIPTION 
				"setSwitchportDefaultVlan"
			::= { sleBridgeInterfaceNotification 2 }

		
		sleBridgeInterfaceSwitchportDefaultVlanDeleted NOTIFICATION-TYPE
			OBJECTS { sleBridgeInterfaceControlRequest, sleBridgeInterfaceControlTimeStamp, sleBridgeInterfaceControlReqResult, sleBridgeInterfaceControlIndex }
			STATUS current
			DESCRIPTION 
				"delSwitchportDefaultVlan"
			::= { sleBridgeInterfaceNotification 3 }

		
		sleBridgeInterfaceSwitchportAllowedVlanChanged NOTIFICATION-TYPE
			OBJECTS { sleBridgeInterfaceControlRequest, sleBridgeInterfaceControlTimeStamp, sleBridgeInterfaceControlReqResult, sleBridgeInterfaceControlIndex, sleBridgeInterfaceControlAllowedVlanFlags, 
				sleBridgeInterfaceControlAllowedVlan }
			STATUS current
			DESCRIPTION 
				"setSwitchportAllowedVlan"
			::= { sleBridgeInterfaceNotification 4 }

		
		sleBridgeInterfaceSwitchportModeChanged NOTIFICATION-TYPE
			OBJECTS { sleBridgeInterfaceControlRequest, sleBridgeInterfaceControlTimeStamp, sleBridgeInterfaceControlReqResult, sleBridgeInterfaceControlIndex, sleBridgeInterfaceControlMode
				 }
			STATUS current
			DESCRIPTION 
				"setSwitchportMode"
			::= { sleBridgeInterfaceNotification 5 }

		
		sleBridgeInterfaceSwitchportModeIngressFilterChanged NOTIFICATION-TYPE
			OBJECTS { sleBridgeInterfaceControlRequest, sleBridgeInterfaceControlTimeStamp, sleBridgeInterfaceControlReqResult, sleBridgeInterfaceControlIndex, sleBridgeInterfaceControlMode, 
				sleBridgeInterfaceControlIngressFilter }
			STATUS current
			DESCRIPTION 
				"setSwitchportModeIngressFilter"
			::= { sleBridgeInterfaceNotification 6 }

		
		sleBridgeInterfaceSwitchportTrunkDeleted NOTIFICATION-TYPE
			OBJECTS { sleBridgeInterfaceControlRequest, sleBridgeInterfaceControlTimeStamp, sleBridgeInterfaceControlReqResult, sleBridgeInterfaceControlIndex }
			STATUS current
			DESCRIPTION 
				"delSwitchportTrunk"
			::= { sleBridgeInterfaceNotification 7 }

		
		sleBridgeInterfaceSwitchportTrunkNativeVlanChanged NOTIFICATION-TYPE
			OBJECTS { sleBridgeInterfaceControlRequest, sleBridgeInterfaceControlTimeStamp, sleBridgeInterfaceControlReqResult, sleBridgeInterfaceControlIndex, sleBridgeInterfaceControlNativeVlan
				 }
			STATUS current
			DESCRIPTION 
				"setSwitchportTrunkNativeVlan"
			::= { sleBridgeInterfaceNotification 8 }

		
		sleBridgeInterfaceSwitchportTrunkNativeVlanDeleted NOTIFICATION-TYPE
			OBJECTS { sleBridgeInterfaceControlRequest, sleBridgeInterfaceControlTimeStamp, sleBridgeInterfaceControlReqResult, sleBridgeInterfaceControlIndex }
			STATUS current
			DESCRIPTION 
				"delSwitchportTrunkNativeVlan"
			::= { sleBridgeInterfaceNotification 9 }

		
		sleBridgeInterfaceChannelGroupChanged NOTIFICATION-TYPE
			OBJECTS { sleBridgeInterfaceControlRequest, sleBridgeInterfaceControlTimeStamp, sleBridgeInterfaceControlReqResult, sleBridgeInterfaceControlIndex, sleBridgeInterfaceControlChannelGroupAggrId, 
				sleBridgeInterfaceControlChannelGroupMode, sleBridgeInterfaceControlChannelGroupLacpAggrMode }
			STATUS current
			DESCRIPTION 
				"setChannelGroup"
			::= { sleBridgeInterfaceNotification 10 }

		
		sleBridgeInterfaceChannelGroupDeleted NOTIFICATION-TYPE
			OBJECTS { sleBridgeInterfaceControlRequest, sleBridgeInterfaceControlTimeStamp, sleBridgeInterfaceControlReqResult, sleBridgeInterfaceControlIndex }
			STATUS current
			DESCRIPTION 
				"delChannelGroup"
			::= { sleBridgeInterfaceNotification 11 }

		
		sleBridgeInterfaceChannelGroupAdminKeyChanged NOTIFICATION-TYPE
			OBJECTS { sleBridgeInterfaceControlRequest, sleBridgeInterfaceControlTimeStamp, sleBridgeInterfaceControlReqResult, sleBridgeInterfaceControlIndex, sleBridgeInterfaceControlChannelGroupAdminKey
				 }
			STATUS current
			DESCRIPTION 
				"setChannelGroupAdminKey"
			::= { sleBridgeInterfaceNotification 12 }

		
		sleBridgeInterfaceChannelGroupAggrTypeChanged NOTIFICATION-TYPE
			OBJECTS { sleBridgeInterfaceControlRequest, sleBridgeInterfaceControlTimeStamp, sleBridgeInterfaceControlReqResult, sleBridgeInterfaceControlIndex, sleBridgeInterfaceControlChannelGroupAggrType
				 }
			STATUS current
			DESCRIPTION 
				"setChannelGroupAggrType"
			::= { sleBridgeInterfaceNotification 13 }

		
		sleBridgeInterfaceChannelGroupPriorityChanged NOTIFICATION-TYPE
			OBJECTS { sleBridgeInterfaceControlRequest, sleBridgeInterfaceControlTimeStamp, sleBridgeInterfaceControlReqResult, sleBridgeInterfaceControlIndex, sleBridgeInterfaceControlChannelGroupPriority
				 }
			STATUS current
			DESCRIPTION 
				"setChannelGroupPriority"
			::= { sleBridgeInterfaceNotification 14 }

		
		sleBridgeInterfaceChannelGroupTimeOutChanged NOTIFICATION-TYPE
			OBJECTS { sleBridgeInterfaceControlRequest, sleBridgeInterfaceControlTimeStamp, sleBridgeInterfaceControlReqResult, sleBridgeInterfaceControlIndex, sleBridgeInterfaceControlChannelGroupTimeOut
				 }
			STATUS current
			DESCRIPTION 
				"setChannelGroupTimeOut"
			::= { sleBridgeInterfaceNotification 15 }

		
		sleBridgeInterfaceChannelGroupActiveLinkChanged NOTIFICATION-TYPE
			OBJECTS { sleBridgeInterfaceControlRequest, sleBridgeInterfaceControlTimeStamp, sleBridgeInterfaceControlReqResult, sleBridgeInterfaceControlIndex, sleBridgeInterfaceControlChannelGroupActiveLink, 
				sleBridgeInterfaceControlChannelGroupDistMode }
			STATUS current
			DESCRIPTION 
				"setChannelGroupActiveLink"
			::= { sleBridgeInterfaceNotification 16 }

		
		sleBridgeInterfaceChannelGroupDistModeChanged NOTIFICATION-TYPE
			OBJECTS { sleBridgeInterfaceControlRequest, sleBridgeInterfaceControlTimeStamp, sleBridgeInterfaceControlReqResult, sleBridgeInterfaceControlIndex, sleBridgeInterfaceControlChannelGroupDistMode
				 }
			STATUS current
			DESCRIPTION 
				"setChannelGroupDistMode"
			::= { sleBridgeInterfaceNotification 17 }

		
		sleBridgeInterfaceVlanChanged NOTIFICATION-TYPE
			OBJECTS { sleBridgeInterfaceControlRequest, sleBridgeInterfaceControlTimeStamp, sleBridgeInterfaceControlReqResult, sleBridgeInterfaceControlIndex, sleBridgeInterfaceControlPvid
				 }
			STATUS current
			DESCRIPTION 
				"setInterfacePvid"
			::= { sleBridgeInterfaceNotification 18 }

		
		sleBridgeReservedVlan OBJECT IDENTIFIER ::= { sleBridge 33 }

		
		sleBridgeReservedVlanTable OBJECT-TYPE
			SYNTAX SEQUENCE OF SleBridgeReservedVlanEntry
			MAX-ACCESS not-accessible
			STATUS current
			DESCRIPTION
				"Description."
			::= { sleBridgeReservedVlan 1 }

		
		sleBridgeReservedVlanEntry OBJECT-TYPE
			SYNTAX SleBridgeReservedVlanEntry
			MAX-ACCESS not-accessible
			STATUS current
			DESCRIPTION
				"Description."
			INDEX { sleBridgeReservedVlanId }
			::= { sleBridgeReservedVlanTable 1 }

		
		SleBridgeReservedVlanEntry ::=
			SEQUENCE { 
				sleBridgeReservedVlanId
					Integer32,
				sleBridgeReservedVlanIsUsed
					INTEGER
			 }

		sleBridgeReservedVlanId OBJECT-TYPE
			SYNTAX Integer32 (0..4096)
			MAX-ACCESS read-only
			STATUS current
			DESCRIPTION
				"The reserved vlan ID."
			::= { sleBridgeReservedVlanEntry 1 }

		
		sleBridgeReservedVlanIsUsed OBJECT-TYPE
			SYNTAX INTEGER
				{
				none(0),
				used(1)
				}
			MAX-ACCESS read-only
			STATUS current
			DESCRIPTION
				"The status of reserved vlan."
			::= { sleBridgeReservedVlanEntry 2 }

		
		sleBridgeReservedVlanControl OBJECT IDENTIFIER ::= { sleBridgeReservedVlan 2 }

		
		sleBridgeReservedVlanControlRequest OBJECT-TYPE
			SYNTAX INTEGER
				{
				addReservedVlan(1),
				removeReservedVlan(2)
				}
			MAX-ACCESS read-write
			STATUS current
			DESCRIPTION
				" The request of a user command"
			::= { sleBridgeReservedVlanControl 1 }

		
		sleBridgeReservedVlanControlStatus OBJECT-TYPE
			SYNTAX SleControlStatusType
			MAX-ACCESS read-only
			STATUS current
			DESCRIPTION
				" The status of user command"
			::= { sleBridgeReservedVlanControl 2 }

		
		sleBridgeReservedVlanControlTimer OBJECT-TYPE
			SYNTAX Gauge32
			MAX-ACCESS read-write
			STATUS current
			DESCRIPTION
				" The maximum time for the manager for a long running user command"
			::= { sleBridgeReservedVlanControl 3 }

		
		sleBridgeReservedVlanControlTimeStamp OBJECT-TYPE
			SYNTAX TimeTicks
			MAX-ACCESS read-only
			STATUS current
			DESCRIPTION
				" The time stamp of the last command(end of command)"
			::= { sleBridgeReservedVlanControl 4 }

		
		sleBridgeReservedVlanControlReqResult OBJECT-TYPE
			SYNTAX SleControlRequestResultType
			MAX-ACCESS read-only
			STATUS current
			DESCRIPTION
				" The result of the last user command"
			::= { sleBridgeReservedVlanControl 5 }

		
		sleBridgeReservedVlanControlStartVlanId OBJECT-TYPE
			SYNTAX Integer32 (1..4096)
			MAX-ACCESS read-write
			STATUS current
			DESCRIPTION
				"The start vlan index."
			::= { sleBridgeReservedVlanControl 6 }

		
		sleBridgeReservedVlanControlEndVlanId OBJECT-TYPE
			SYNTAX Integer32 (1..4096)
			MAX-ACCESS read-write
			STATUS current
			DESCRIPTION
				"The end vlan index."
			::= { sleBridgeReservedVlanControl 7 }

		
		sleBridgeReservedVlanNotification OBJECT IDENTIFIER ::= { sleBridgeReservedVlan 3 }

		
		sleBridgeReservedVlanAdded NOTIFICATION-TYPE
			OBJECTS { sleBridgeReservedVlanControlRequest, sleBridgeReservedVlanControlTimeStamp, sleBridgeReservedVlanControlReqResult, sleBridgeReservedVlanControlStartVlanId, sleBridgeReservedVlanControlEndVlanId
				 }
			STATUS current
			DESCRIPTION 
				"addReservedVlan"
			::= { sleBridgeReservedVlanNotification 1 }

		
		sleBridgeReservedVlanRemoved NOTIFICATION-TYPE
			OBJECTS { sleBridgeReservedVlanControlRequest, sleBridgeReservedVlanControlTimeStamp, sleBridgeReservedVlanControlReqResult, sleBridgeReservedVlanControlStartVlanId, sleBridgeReservedVlanControlEndVlanId
				 }
			STATUS current
			DESCRIPTION 
				"removeReservedVlan"
			::= { sleBridgeReservedVlanNotification 2 }

		
		sleBridgeInternalVlanTable OBJECT-TYPE
			SYNTAX SEQUENCE OF SleBridgeInternalVlanEntry
			MAX-ACCESS not-accessible
			STATUS current
			DESCRIPTION
				"Description."
			::= { sleBridgeReservedVlan 4 }

		
		sleBridgeInternalVlanEntry OBJECT-TYPE
			SYNTAX SleBridgeInternalVlanEntry
			MAX-ACCESS not-accessible
			STATUS current
			DESCRIPTION
				"Description."
			INDEX { sleBridgeInternalVlanSlot, sleBridgeInternalVlanPort, sleBridgeInternalVlanRealVlanId }
			::= { sleBridgeInternalVlanTable 1 }

		
		SleBridgeInternalVlanEntry ::=
			SEQUENCE { 
				sleBridgeInternalVlanSlot
					Integer32,
				sleBridgeInternalVlanPort
					Integer32,
				sleBridgeInternalVlanRealVlanId
					Integer32,
				sleBridgeInternalVlanInternalVlanId
					Integer32
			 }

		sleBridgeInternalVlanSlot OBJECT-TYPE
			SYNTAX Integer32 (0..65535)
			MAX-ACCESS read-only
			STATUS current
			DESCRIPTION
				"The Internal vlan slot."
			::= { sleBridgeInternalVlanEntry 1 }

		
		sleBridgeInternalVlanPort OBJECT-TYPE
			SYNTAX Integer32 (1..65535)
			MAX-ACCESS read-only
			STATUS current
			DESCRIPTION
				"The Internal vlan port."
			::= { sleBridgeInternalVlanEntry 2 }

		
		sleBridgeInternalVlanRealVlanId OBJECT-TYPE
			SYNTAX Integer32 (1..4096)
			MAX-ACCESS read-only
			STATUS current
			DESCRIPTION
				"The Real VLAN ID."
			::= { sleBridgeInternalVlanEntry 3 }

		
		sleBridgeInternalVlanInternalVlanId OBJECT-TYPE
			SYNTAX Integer32 (1..4096)
			MAX-ACCESS read-only
			STATUS current
			DESCRIPTION
				"The internal VLAN ID."
			::= { sleBridgeInternalVlanEntry 4 }

		
		sleSubnetVlan6 OBJECT IDENTIFIER ::= { sleBridge 34 }

		
		sleSubnetVlan6Table OBJECT-TYPE
			SYNTAX SEQUENCE OF SleSubnetVlan6Entry
			MAX-ACCESS not-accessible
			STATUS current
			DESCRIPTION
				"Description."
			::= { sleSubnetVlan6 1 }

		
		sleSubnetVlan6Entry OBJECT-TYPE
			SYNTAX SleSubnetVlan6Entry
			MAX-ACCESS not-accessible
			STATUS current
			DESCRIPTION
				"Description."
			INDEX { sleSubnetVlan6Ip, sleSubnetVlan6Mask }
			::= { sleSubnetVlan6Table 1 }

		
		SleSubnetVlan6Entry ::=
			SEQUENCE { 
				sleSubnetVlan6Ip
					InetAddressIPv6,
				sleSubnetVlan6Mask
					Integer32,
				sleSubnetVlan6Vid
					Integer32
			 }

		sleSubnetVlan6Ip OBJECT-TYPE
			SYNTAX InetAddressIPv6
			MAX-ACCESS read-only
			STATUS current
			DESCRIPTION
				"Description."
			::= { sleSubnetVlan6Entry 1 }

		
		sleSubnetVlan6Mask OBJECT-TYPE
			SYNTAX Integer32 (1..64)
			MAX-ACCESS read-only
			STATUS current
			DESCRIPTION
				"Description."
			::= { sleSubnetVlan6Entry 2 }

		
		sleSubnetVlan6Vid OBJECT-TYPE
			SYNTAX Integer32 (1..4094)
			MAX-ACCESS read-only
			STATUS current
			DESCRIPTION
				"Description."
			::= { sleSubnetVlan6Entry 3 }

		
		sleSubnetVlan6Control OBJECT IDENTIFIER ::= { sleSubnetVlan6 2 }

		
		sleSubnetVlan6ControlRequest OBJECT-TYPE
			SYNTAX INTEGER
				{
				createSubnetVlan6(1),
				destroySubnetVlan6(2)
				}
			MAX-ACCESS read-write
			STATUS current
			DESCRIPTION
				"Description."
			::= { sleSubnetVlan6Control 1 }

		
		sleSubnetVlan6ControlStatus OBJECT-TYPE
			SYNTAX SleControlStatusType
			MAX-ACCESS read-write
			STATUS current
			DESCRIPTION
				"Description."
			::= { sleSubnetVlan6Control 2 }

		
		sleSubnetVlan6ControlTimer OBJECT-TYPE
			SYNTAX Gauge32
			MAX-ACCESS read-write
			STATUS current
			DESCRIPTION
				"Description."
			::= { sleSubnetVlan6Control 3 }

		
		sleSubnetVlan6ControlTimeStamp OBJECT-TYPE
			SYNTAX TimeTicks
			MAX-ACCESS read-write
			STATUS current
			DESCRIPTION
				"Description."
			::= { sleSubnetVlan6Control 4 }

		
		sleSubnetVlan6ControlReqResult OBJECT-TYPE
			SYNTAX SleControlRequestResultType
			MAX-ACCESS read-write
			STATUS current
			DESCRIPTION
				"Description."
			::= { sleSubnetVlan6Control 5 }

		
		sleSubnetVlan6ControlIp OBJECT-TYPE
			SYNTAX InetAddressIPv6
			MAX-ACCESS read-write
			STATUS current
			DESCRIPTION
				"Description."
			::= { sleSubnetVlan6Control 6 }

		
		sleSubnetVlan6ControlMask OBJECT-TYPE
			SYNTAX Integer32 (1..64)
			MAX-ACCESS read-write
			STATUS current
			DESCRIPTION
				"Description."
			::= { sleSubnetVlan6Control 7 }

		
		sleSubnetVlan6ControlVid OBJECT-TYPE
			SYNTAX Integer32 (1..4094)
			MAX-ACCESS read-write
			STATUS current
			DESCRIPTION
				"Description."
			::= { sleSubnetVlan6Control 8 }

		
		sleSubnetVlan6Notification OBJECT IDENTIFIER ::= { sleSubnetVlan6 3 }

		
		sleSubnetVlan6Created NOTIFICATION-TYPE
			OBJECTS { sleSubnetVlan6ControlRequest, sleSubnetVlan6ControlReqResult, sleSubnetVlan6ControlTimeStamp, sleSubnetVlan6Vid }
			STATUS current
			DESCRIPTION 
				"Description."
			::= { sleSubnetVlan6Notification 1 }

		
		sleSubnetVlan6Destroyed NOTIFICATION-TYPE
			OBJECTS { sleSubnetVlan6ControlRequest, sleSubnetVlan6ControlReqResult, sleSubnetVlan6ControlTimeStamp, sleSubnetVlan6Vid }
			STATUS current
			DESCRIPTION 
				"Description."
			::= { sleSubnetVlan6Notification 2 }

		
		sle2MacAddress OBJECT IDENTIFIER ::= { sleBridge 35 }

		
		sle2MacAddressTable OBJECT-TYPE
			SYNTAX SEQUENCE OF Sle2MacAddressEntry
			MAX-ACCESS not-accessible
			STATUS current
			DESCRIPTION
				"The table of MacAddress entries."
			::= { sle2MacAddress 1 }

		
		sle2MacAddressEntry OBJECT-TYPE
			SYNTAX Sle2MacAddressEntry
			MAX-ACCESS not-accessible
			STATUS current
			DESCRIPTION
				"The table entry of MacAddress table.
				key: sle2MacAddressEntryBridgeId, sle2MacAddressEntryMacAddress, sle2MacAddressEntryIfIndex, sle2MacAddressEntryVid"
			INDEX { sle2MacAddressEntryBridgeId, sle2MacAddressEntryMacAddress, sle2MacAddressEntryIfIndex, sle2MacAddressEntryVid }
			::= { sle2MacAddressTable 1 }

		
		Sle2MacAddressEntry ::=
			SEQUENCE { 
				sle2MacAddressEntryBridgeId
					INTEGER,
				sle2MacAddressEntryMacAddress
					MacAddress,
				sle2MacAddressEntryIfIndex
					Integer32,
				sle2MacAddressEntryVid
					INTEGER,
				sle2MacAddressEntrySVid
					INTEGER,
				sle2MacAddressEntryMode
					INTEGER,
				sle2MacAddressEntryPermission
					INTEGER,
				sle2MacAddressEntryElapsedTime
					Unsigned32
			 }

		sle2MacAddressEntryBridgeId OBJECT-TYPE
			SYNTAX INTEGER (1..32)
			MAX-ACCESS read-only
			STATUS current
			DESCRIPTION
				"Indicates bridgegroup id"
			::= { sle2MacAddressEntry 1 }

		
		sle2MacAddressEntryMacAddress OBJECT-TYPE
			SYNTAX MacAddress
			MAX-ACCESS read-only
			STATUS current
			DESCRIPTION
				"MAC Address"
			::= { sle2MacAddressEntry 2 }

		
		sle2MacAddressEntryIfIndex OBJECT-TYPE
			SYNTAX Integer32 (1..2147483647)
			MAX-ACCESS read-only
			STATUS current
			DESCRIPTION
				"Indcates the interface index."
			::= { sle2MacAddressEntry 3 }

		
		sle2MacAddressEntryVid OBJECT-TYPE
			SYNTAX INTEGER (1..4094)
			MAX-ACCESS read-only
			STATUS current
			DESCRIPTION
				"The Vlan ID"
			::= { sle2MacAddressEntry 4 }

		
		sle2MacAddressEntrySVid OBJECT-TYPE
			SYNTAX INTEGER (1..4094)
			MAX-ACCESS read-only
			STATUS current
			DESCRIPTION
				"The SVlan ID"
			::= { sle2MacAddressEntry 5 }

		
		sle2MacAddressEntryMode OBJECT-TYPE
			SYNTAX INTEGER
				{
				static(0),
				dynamic(1)
				}
			MAX-ACCESS read-only
			STATUS current
			DESCRIPTION
				"MacAdress Entry's mode"
			::= { sle2MacAddressEntry 6 }

		
		sle2MacAddressEntryPermission OBJECT-TYPE
			SYNTAX INTEGER
				{
				discard(0),
				forward(1)
				}
			MAX-ACCESS read-only
			STATUS current
			DESCRIPTION
				"Fowarding option"
			::= { sle2MacAddressEntry 7 }

		
		sle2MacAddressEntryElapsedTime OBJECT-TYPE
			SYNTAX Unsigned32
			MAX-ACCESS read-only
			STATUS current
			DESCRIPTION
				"Elapsed time after registered"
			::= { sle2MacAddressEntry 8 }

		
		sle2MacAddressControl OBJECT IDENTIFIER ::= { sle2MacAddress 2 }

		
		sle2MacAddressEntryControlRequest OBJECT-TYPE
			SYNTAX INTEGER
				{
				createMacAddressEntry(1),
				destoryMacAddressEntry(2),
				clearMacAddressTableEntries(3)
				}
			MAX-ACCESS read-write
			STATUS current
			DESCRIPTION
				"The request of a user command"
			::= { sle2MacAddressControl 1 }

		
		sle2MacAddressEntryControlStatus OBJECT-TYPE
			SYNTAX SleControlStatusType
			MAX-ACCESS read-only
			STATUS current
			DESCRIPTION
				"Control Status."
			::= { sle2MacAddressControl 2 }

		
		sle2MacAddressEntryControlTimer OBJECT-TYPE
			SYNTAX Gauge32
			MAX-ACCESS read-write
			STATUS current
			DESCRIPTION
				"Cotrol Timer."
			::= { sle2MacAddressControl 3 }

		
		sle2MacAddressEntryControlTimeStamp OBJECT-TYPE
			SYNTAX TimeTicks
			MAX-ACCESS read-only
			STATUS current
			DESCRIPTION
				" The time stamp of the last command(end of command)"
			::= { sle2MacAddressControl 4 }

		
		sle2MacAddressEntryControlReqResult OBJECT-TYPE
			SYNTAX SleControlRequestResultType
			MAX-ACCESS read-only
			STATUS current
			DESCRIPTION
				" The result of the last user command"
			::= { sle2MacAddressControl 5 }

		
		sle2MacAddressEntryControlBridgeId OBJECT-TYPE
			SYNTAX INTEGER (1..32)
			MAX-ACCESS read-write
			STATUS current
			DESCRIPTION
				"Indicates bridgegroup id
				1 : default bridge id"
			::= { sle2MacAddressControl 6 }

		
		sle2MacAddressEntryControlMacAddress OBJECT-TYPE
			SYNTAX MacAddress
			MAX-ACCESS read-write
			STATUS current
			DESCRIPTION
				"MAC Address"
			::= { sle2MacAddressControl 7 }

		
		sle2MacAddressEntryControlIfIndex OBJECT-TYPE
			SYNTAX Integer32
			MAX-ACCESS read-write
			STATUS current
			DESCRIPTION
				"Indicates interface index"
			::= { sle2MacAddressControl 8 }

		
		sle2MacAddressEntryControlVid OBJECT-TYPE
			SYNTAX INTEGER (1..4094)
			MAX-ACCESS read-write
			STATUS current
			DESCRIPTION
				"The Vlan ID"
			::= { sle2MacAddressControl 9 }

		
		sle2MacAddressEntryControlSVid OBJECT-TYPE
			SYNTAX INTEGER (1..4094)
			MAX-ACCESS read-write
			STATUS current
			DESCRIPTION
				"The SVlan ID"
			::= { sle2MacAddressControl 10 }

		
		sle2MacAddressEntryControlPermission OBJECT-TYPE
			SYNTAX INTEGER
				{
				discard(0),
				forward(1)
				}
			MAX-ACCESS read-write
			STATUS current
			DESCRIPTION
				"Fowarding option"
			::= { sle2MacAddressControl 11 }

		
		sle2MacAddressEntryControlCVid OBJECT-TYPE
			SYNTAX INTEGER (1..4094)
			MAX-ACCESS read-write
			STATUS current
			DESCRIPTION
				"The CVlan ID"
			::= { sle2MacAddressControl 12 }

		
		sle2MacAddressEntryControlInstance OBJECT-TYPE
			SYNTAX INTEGER (1..63)
			MAX-ACCESS read-write
			STATUS current
			DESCRIPTION
				"MSTP instance id"
			::= { sle2MacAddressControl 13 }

		
		sle2MacAddressEntryControlClearType OBJECT-TYPE
			SYNTAX INTEGER
				{
				dynamicAll(0),
				dynamicAddress(1),
				dynamicVlan(2),
				dynamicInterface(3),
				dynamicVlanInterface(4),
				dynamicCvlanSvlan(5),
				dynamicInstance(6),
				staticAll(7),
				staticAddress(8),
				staticVlan(9),
				staticInterface(10),
				staticVlanInterface(11),
				staticCvlanSvlan(12),
				staticInstance(13)
				}
			MAX-ACCESS read-write
			STATUS current
			DESCRIPTION
				"Type to clear MacAddress"
			::= { sle2MacAddressControl 14 }

		
		sle2MacAddressNotification OBJECT IDENTIFIER ::= { sle2MacAddress 3 }

		
		sle2MacAddressEntryCreated NOTIFICATION-TYPE
			OBJECTS { sle2MacAddressEntryControlRequest, sle2MacAddressEntryControlReqResult, sle2MacAddressEntryControlTimeStamp, sle2MacAddressEntryBridgeId, sle2MacAddressEntryMacAddress, 
				sle2MacAddressEntryIfIndex, sle2MacAddressEntryVid, sle2MacAddressEntrySVid, sle2MacAddressEntryPermission }
			STATUS current
			DESCRIPTION 
				"createMacAddressEntry"
			::= { sle2MacAddressNotification 1 }

		
		sle2MacAddressEntryDestroyed NOTIFICATION-TYPE
			OBJECTS { sle2MacAddressEntryControlRequest, sle2MacAddressEntryControlReqResult, sle2MacAddressEntryControlTimeStamp, sle2MacAddressEntryControlBridgeId, sle2MacAddressEntryControlMacAddress, 
				sle2MacAddressEntryControlIfIndex, sle2MacAddressEntryControlVid, sle2MacAddressEntryControlSVid, sle2MacAddressEntryControlPermission }
			STATUS current
			DESCRIPTION 
				"destroyMacAddressEntry "
			::= { sle2MacAddressNotification 2 }

		
		sle2MacAddressTableEntriesCleared NOTIFICATION-TYPE
			OBJECTS { sle2MacAddressEntryControlRequest, sle2MacAddressEntryControlReqResult, sle2MacAddressEntryControlTimeStamp, sle2MacAddressEntryControlBridgeId, sle2MacAddressEntryControlMacAddress, 
				sle2MacAddressEntryControlIfIndex, sle2MacAddressEntryControlVid, sle2MacAddressEntryControlSVid, sle2MacAddressEntryControlCVid, sle2MacAddressEntryControlInstance, 
				sle2MacAddressEntryControlClearType }
			STATUS current
			DESCRIPTION 
				"clearMacAddressTableEntries"
			::= { sle2MacAddressNotification 3 }

		
		sleCVlanRegistrationMap OBJECT IDENTIFIER ::= { sleBridge 36 }

		
		sleCVlanRegistrationMapTable OBJECT-TYPE
			SYNTAX SEQUENCE OF SleCVlanRegistrationMapEntry
			MAX-ACCESS not-accessible
			STATUS current
			DESCRIPTION
				" sle cvlan registration map table"
			::= { sleCVlanRegistrationMap 1 }

		
		sleCVlanRegistrationMapEntry OBJECT-TYPE
			SYNTAX SleCVlanRegistrationMapEntry
			MAX-ACCESS not-accessible
			STATUS current
			DESCRIPTION
				" key: sleVlanIndex"
			INDEX { sleCVlanRegIndex, sleCVlanIndex }
			::= { sleCVlanRegistrationMapTable 1 }

		
		SleCVlanRegistrationMapEntry ::=
			SEQUENCE { 
				sleCVlanRegIndex
					INTEGER,
				sleCVlanIndex
					Integer32,
				sleCVlanRegName
					OCTET STRING,
				sleSVlan
					Integer32,
				sleUntaggedMap
					Integer32
			 }

		sleCVlanRegIndex OBJECT-TYPE
			SYNTAX INTEGER (1..4094)
			MAX-ACCESS read-only
			STATUS current
			DESCRIPTION
				"The table index for cvlan registration"
			::= { sleCVlanRegistrationMapEntry 1 }

		
		sleCVlanIndex OBJECT-TYPE
			SYNTAX Integer32 (1..4095)
			MAX-ACCESS read-only
			STATUS current
			DESCRIPTION
				"The table index for the cvlan registration for the multiple cvlan id's
				the index itself is a cvlan-id "
			::= { sleCVlanRegistrationMapEntry 2 }

		
		sleCVlanRegName OBJECT-TYPE
			SYNTAX OCTET STRING
			MAX-ACCESS read-only
			STATUS current
			DESCRIPTION
				"A descriptional name for that vlan."
			::= { sleCVlanRegistrationMapEntry 3 }

		
		sleSVlan OBJECT-TYPE
			SYNTAX Integer32
			MAX-ACCESS read-only
			STATUS current
			DESCRIPTION
				" "
			::= { sleCVlanRegistrationMapEntry 4 }

		
		sleUntaggedMap OBJECT-TYPE
			SYNTAX Integer32
			MAX-ACCESS read-only
			STATUS current
			DESCRIPTION
				" "
			::= { sleCVlanRegistrationMapEntry 5 }

		
		sleCVlanRegistrationMapControl OBJECT IDENTIFIER ::= { sleCVlanRegistrationMap 2 }

		
		sleCVlanRegistrationMapControlRequest OBJECT-TYPE
			SYNTAX INTEGER
				{
				createCvlanRegistration(1),
				destroyCvlanRegistration(2),
				setSvlanId(3),
				unsetSvlanId(4)
				}
			MAX-ACCESS read-write
			STATUS current
			DESCRIPTION
				"Description."
			::= { sleCVlanRegistrationMapControl 1 }

		
		sleCVlanRegistrationMapControlStatus OBJECT-TYPE
			SYNTAX SleControlStatusType
			MAX-ACCESS read-write
			STATUS current
			DESCRIPTION
				"Description."
			::= { sleCVlanRegistrationMapControl 2 }

		
		sleCVlanRegistrationMapControlTimer OBJECT-TYPE
			SYNTAX Gauge32
			MAX-ACCESS read-write
			STATUS current
			DESCRIPTION
				"Description."
			::= { sleCVlanRegistrationMapControl 3 }

		
		sleCVlanRegistrationMapControlTimeStamp OBJECT-TYPE
			SYNTAX TimeTicks
			MAX-ACCESS read-write
			STATUS current
			DESCRIPTION
				"Description."
			::= { sleCVlanRegistrationMapControl 4 }

		
		sleCVlanRegistrationMapControlReqResult OBJECT-TYPE
			SYNTAX SleControlRequestResultType
			MAX-ACCESS read-write
			STATUS current
			DESCRIPTION
				"Description."
			::= { sleCVlanRegistrationMapControl 5 }

		
		sleCVlanRegistrationMapControlCVlanID OBJECT-TYPE
			SYNTAX Integer32 (1..4094)
			MAX-ACCESS read-write
			STATUS current
			DESCRIPTION
				"Description."
			::= { sleCVlanRegistrationMapControl 6 }

		
		sleCVlanRegistrationMapControlName OBJECT-TYPE
			SYNTAX OCTET STRING
			MAX-ACCESS read-write
			STATUS current
			DESCRIPTION
				"Description."
			::= { sleCVlanRegistrationMapControl 7 }

		
		sleCVlanRegistrationMapControlSVlan OBJECT-TYPE
			SYNTAX Integer32 (1..4094)
			MAX-ACCESS read-write
			STATUS current
			DESCRIPTION
				"Description."
			::= { sleCVlanRegistrationMapControl 8 }

		
		sleCVlanRegistrationMapControlFlagPort OBJECT-TYPE
			SYNTAX INTEGER
				{
				none(0),
				untaggedPep(1),
				untaggedCep(2),
				both(3)
				}
			MAX-ACCESS read-write
			STATUS current
			DESCRIPTION
				"Description."
			::= { sleCVlanRegistrationMapControl 9 }

		
		sleLacpBase OBJECT IDENTIFIER ::= { sleBridge 37 }

		
		sleLacpBaseInfo OBJECT IDENTIFIER ::= { sleLacpBase 1 }

		
		sleLacpSystemPriority OBJECT-TYPE
			SYNTAX Integer32 (1..65535)
			MAX-ACCESS read-only
			STATUS current
			DESCRIPTION
				"Description."
			DEFVAL { 32768 }
			::= { sleLacpBaseInfo 1 }

		
		sleLacpBaseControl OBJECT IDENTIFIER ::= { sleLacpBase 2 }

		
		sleLacpBaseControlRequest OBJECT-TYPE
			SYNTAX INTEGER
				{
				setLacpSystemPriority(1),
				clearLacpCounters(2)
				}
			MAX-ACCESS read-write
			STATUS current
			DESCRIPTION
				"Description."
			::= { sleLacpBaseControl 1 }

		
		sleLacpBaseControlStatus OBJECT-TYPE
			SYNTAX SleControlStatusType
			MAX-ACCESS read-write
			STATUS current
			DESCRIPTION
				"Description."
			::= { sleLacpBaseControl 2 }

		
		sleLacpBaseControlTimer OBJECT-TYPE
			SYNTAX Gauge32
			MAX-ACCESS read-write
			STATUS current
			DESCRIPTION
				"Description."
			::= { sleLacpBaseControl 3 }

		
		sleLacpBaseControlTimeStamp OBJECT-TYPE
			SYNTAX TimeTicks
			MAX-ACCESS read-write
			STATUS current
			DESCRIPTION
				"Description."
			::= { sleLacpBaseControl 4 }

		
		sleLacpBaseControlReqResult OBJECT-TYPE
			SYNTAX SleControlRequestResultType
			MAX-ACCESS read-write
			STATUS current
			DESCRIPTION
				"Description."
			::= { sleLacpBaseControl 5 }

		
		sleLacpBaseControlSystemPriority OBJECT-TYPE
			SYNTAX Integer32 (1..65535)
			MAX-ACCESS read-write
			STATUS current
			DESCRIPTION
				"Description."
			DEFVAL { 32768 }
			::= { sleLacpBaseControl 6 }

		
		sleLacpBaseControlAggregatorId OBJECT-TYPE
			SYNTAX Integer32 (0..65535)
			MAX-ACCESS read-write
			STATUS current
			DESCRIPTION
				"Description."
			::= { sleLacpBaseControl 7 }

		
		sleLacpInterface OBJECT IDENTIFIER ::= { sleBridge 38 }

		
		sleLacpInterfaceTable OBJECT-TYPE
			SYNTAX SEQUENCE OF SleLacpInterfaceEntry
			MAX-ACCESS not-accessible
			STATUS current
			DESCRIPTION
				"Description."
			::= { sleLacpInterface 1 }

		
		sleLacpInterfaceEntry OBJECT-TYPE
			SYNTAX SleLacpInterfaceEntry
			MAX-ACCESS not-accessible
			STATUS current
			DESCRIPTION
				"Description."
			INDEX { sleLacpInterfaceIndex }
			::= { sleLacpInterfaceTable 1 }

		
		SleLacpInterfaceEntry ::=
			SEQUENCE { 
				sleLacpInterfaceIndex
					InterfaceIndex,
				sleLacpInterfaceName
					OCTET STRING,
				sleLacpInterfaceActorPriority
					Integer32,
				sleLacpInterfaceActorAdminKey
					Integer32,
				sleLacpInterfaceActorAdminState
					BITS,
				sleLacpInterfaceDestinationMac
					INTEGER,
				sleLacpInterfaceDiscardWrongConversation
					INTEGER,
				sleLacpInterfaceTimeout
					INTEGER,
				sleLacpInterfaceActiveLink
					Integer32
			 }

		sleLacpInterfaceIndex OBJECT-TYPE
			SYNTAX InterfaceIndex
			MAX-ACCESS read-only
			STATUS current
			DESCRIPTION
				"Description."
			::= { sleLacpInterfaceEntry 1 }

		
		sleLacpInterfaceName OBJECT-TYPE
			SYNTAX OCTET STRING
			MAX-ACCESS read-only
			STATUS current
			DESCRIPTION
				"Description."
			::= { sleLacpInterfaceEntry 2 }

		
		sleLacpInterfaceActorPriority OBJECT-TYPE
			SYNTAX Integer32
			MAX-ACCESS read-write
			STATUS current
			DESCRIPTION
				"Description."
			::= { sleLacpInterfaceEntry 3 }

		
		sleLacpInterfaceActorAdminKey OBJECT-TYPE
			SYNTAX Integer32 (1..65535)
			MAX-ACCESS read-only
			STATUS current
			DESCRIPTION
				"Description."
			::= { sleLacpInterfaceEntry 4 }

		
		sleLacpInterfaceActorAdminState OBJECT-TYPE
			SYNTAX BITS
				{
				expired(0),
				defaulted(1),
				destributing(2),
				collecting(3),
				synchronization(4),
				aggregation(5),
				lacpTimeout(6),
				lacpActivity(7)
				}
			MAX-ACCESS read-only
			STATUS current
			DESCRIPTION
				"The Actor's administrable state variables for the port."
			::= { sleLacpInterfaceEntry 5 }

		
		sleLacpInterfaceDestinationMac OBJECT-TYPE
			SYNTAX INTEGER
				{
				none(0),
				customer(1),
				multicast(2),
				nonTmpr(3)
				}
			MAX-ACCESS read-only
			STATUS current
			DESCRIPTION
				"Description."
			::= { sleLacpInterfaceEntry 6 }

		
		sleLacpInterfaceDiscardWrongConversation OBJECT-TYPE
			SYNTAX INTEGER
				{
				disable(0),
				enable(1)
				}
			MAX-ACCESS read-only
			STATUS current
			DESCRIPTION
				"Description."
			::= { sleLacpInterfaceEntry 7 }

		
		sleLacpInterfaceTimeout OBJECT-TYPE
			SYNTAX INTEGER
				{
				short(1),
				long(2)
				}
			MAX-ACCESS read-only
			STATUS current
			DESCRIPTION
				"The LACP interface group timeout"
			::= { sleLacpInterfaceEntry 8 }

		
		sleLacpInterfaceActiveLink OBJECT-TYPE
			SYNTAX Integer32 (1..65535)
			MAX-ACCESS read-only
			STATUS current
			DESCRIPTION
				"LACP aggregator's active-link"
			::= { sleLacpInterfaceEntry 9 }

		
		sleLacpInterfaceControl OBJECT IDENTIFIER ::= { sleLacpInterface 2 }

		
		sleLacpInterfaceControlRequest OBJECT-TYPE
			SYNTAX INTEGER
				{
				setLacpPriority(1),
				setLacpTimeout(2),
				setLacpDestMac(3),
				setLacpDwc(4),
				setLacpActiveLink(5)
				}
			MAX-ACCESS read-write
			STATUS current
			DESCRIPTION
				"Description."
			::= { sleLacpInterfaceControl 1 }

		
		sleLacpInterfaceControlStatus OBJECT-TYPE
			SYNTAX SleControlStatusType
			MAX-ACCESS read-write
			STATUS current
			DESCRIPTION
				"Description."
			::= { sleLacpInterfaceControl 2 }

		
		sleLacpInterfaceControlTimer OBJECT-TYPE
			SYNTAX Gauge32
			MAX-ACCESS read-write
			STATUS current
			DESCRIPTION
				"Description."
			::= { sleLacpInterfaceControl 3 }

		
		sleLacpInterfaceControlTimeStamp OBJECT-TYPE
			SYNTAX TimeTicks
			MAX-ACCESS read-write
			STATUS current
			DESCRIPTION
				"Description."
			::= { sleLacpInterfaceControl 4 }

		
		sleLacpInterfaceControlReqResult OBJECT-TYPE
			SYNTAX SleControlRequestResultType
			MAX-ACCESS read-write
			STATUS current
			DESCRIPTION
				"Description."
			::= { sleLacpInterfaceControl 5 }

		
		sleLacpInterfaceControlIndex OBJECT-TYPE
			SYNTAX InterfaceIndex
			MAX-ACCESS read-write
			STATUS current
			DESCRIPTION
				"Description."
			::= { sleLacpInterfaceControl 6 }

		
		sleLacpInterfaceControlPriority OBJECT-TYPE
			SYNTAX Integer32 (1..65535)
			MAX-ACCESS read-write
			STATUS current
			DESCRIPTION
				"Description."
			DEFVAL { 32768 }
			::= { sleLacpInterfaceControl 7 }

		
		sleLacpInterfaceControlTimeout OBJECT-TYPE
			SYNTAX INTEGER
				{
				short(1),
				long(2)
				}
			MAX-ACCESS read-write
			STATUS current
			DESCRIPTION
				"Description."
			::= { sleLacpInterfaceControl 8 }

		
		sleLacpInterfaceControlDestinationMac OBJECT-TYPE
			SYNTAX INTEGER
				{
				customer(1),
				multicast(2),
				nonTmpr(3)
				}
			MAX-ACCESS read-write
			STATUS current
			DESCRIPTION
				"Description."
			::= { sleLacpInterfaceControl 9 }

		
		sleLacpInterfaceControlDiscardWrongConversation OBJECT-TYPE
			SYNTAX INTEGER
				{
				disable(0),
				enable(1)
				}
			MAX-ACCESS read-write
			STATUS current
			DESCRIPTION
				"Description."
			::= { sleLacpInterfaceControl 10 }

		
		sleLacpInterfaceControlActiveLink OBJECT-TYPE
			SYNTAX Integer32 (1..65535)
			MAX-ACCESS read-write
			STATUS current
			DESCRIPTION
				"LACP aggregator's active-link"
			::= { sleLacpInterfaceControl 11 }

		
		sle2LldpGlobal OBJECT IDENTIFIER ::= { sleBridge 39 }

		
		sle2LldpGlobalTable OBJECT-TYPE
			SYNTAX SEQUENCE OF Sle2LldpGlobalEntry
			MAX-ACCESS not-accessible
			STATUS current
			DESCRIPTION
				"Description."
			::= { sle2LldpGlobal 1 }

		
		sle2LldpGlobalEntry OBJECT-TYPE
			SYNTAX Sle2LldpGlobalEntry
			MAX-ACCESS not-accessible
			STATUS current
			DESCRIPTION
				"Description."
			INDEX { sle2LldpGlobalIfIndex }
			::= { sle2LldpGlobalTable 1 }

		
		Sle2LldpGlobalEntry ::=
			SEQUENCE { 
				sle2LldpGlobalIfIndex
					InterfaceIndex,
				sle2LldpGlobalAgtCircuitId
					OCTET STRING,
				sle2LldpGlobalMedDevType
					INTEGER,
				sle2LldpGlobalPortDescription
					OCTET STRING
			 }

		sle2LldpGlobalIfIndex OBJECT-TYPE
			SYNTAX InterfaceIndex
			MAX-ACCESS read-only
			STATUS current
			DESCRIPTION
				"LLDP Interface"
			::= { sle2LldpGlobalEntry 1 }

		
		sle2LldpGlobalAgtCircuitId OBJECT-TYPE
			SYNTAX OCTET STRING
			MAX-ACCESS read-only
			STATUS current
			DESCRIPTION
				"LLDP Global agent circuitid"
			::= { sle2LldpGlobalEntry 2 }

		
		sle2LldpGlobalMedDevType OBJECT-TYPE
			SYNTAX INTEGER
				{
				epclass1(1),
				epclass2(2),
				epclass3(3),
				netconnect(4)
				}
			MAX-ACCESS read-only
			STATUS current
			DESCRIPTION
				"Selection of MED device type"
			::= { sle2LldpGlobalEntry 3 }

		
		sle2LldpGlobalPortDescription OBJECT-TYPE
			SYNTAX OCTET STRING
			MAX-ACCESS read-only
			STATUS current
			DESCRIPTION
				"LLDP Global Port Description"
			::= { sle2LldpGlobalEntry 4 }

		
		sle2LldpGlobalControl OBJECT IDENTIFIER ::= { sle2LldpGlobal 2 }

		
		sle2LldpGlobalControlRequest OBJECT-TYPE
			SYNTAX INTEGER
				{
				setLldpGlobal(1),
				unsetLldpGlobalMedDevType(2)
				}
			MAX-ACCESS read-write
			STATUS current
			DESCRIPTION
				"The request of a user command"
			::= { sle2LldpGlobalControl 1 }

		
		sle2LldpGlobalControlStatus OBJECT-TYPE
			SYNTAX SleControlStatusType
			MAX-ACCESS read-only
			STATUS current
			DESCRIPTION
				"The status of a user command"
			::= { sle2LldpGlobalControl 2 }

		
		sle2LldpGlobalControlTimer OBJECT-TYPE
			SYNTAX Gauge32
			MAX-ACCESS read-write
			STATUS current
			DESCRIPTION
				"The maximum time for the manager for a long running user command"
			::= { sle2LldpGlobalControl 3 }

		
		sle2LldpGlobalControlTimeStamp OBJECT-TYPE
			SYNTAX TimeTicks
			MAX-ACCESS read-only
			STATUS current
			DESCRIPTION
				"The time stamp of the last command(end of command)"
			::= { sle2LldpGlobalControl 4 }

		
		sle2LldpGlobalControlReqResult OBJECT-TYPE
			SYNTAX SleControlRequestResultType
			MAX-ACCESS read-only
			STATUS current
			DESCRIPTION
				"Result of the last command."
			::= { sle2LldpGlobalControl 5 }

		
		sle2LldpGlobalControlIfIndex OBJECT-TYPE
			SYNTAX InterfaceIndex
			MAX-ACCESS read-write
			STATUS current
			DESCRIPTION
				"LLDP Interface"
			::= { sle2LldpGlobalControl 6 }

		
		sle2LldpGlobalControlAgtCircuitId OBJECT-TYPE
			SYNTAX OCTET STRING
			MAX-ACCESS read-write
			STATUS current
			DESCRIPTION
				"LLDP Global agent circuitid"
			::= { sle2LldpGlobalControl 7 }

		
		sle2LldpGlobalControlMedDevType OBJECT-TYPE
			SYNTAX INTEGER
				{
				epclass1(1),
				epclass2(2),
				epclass3(3),
				netconnect(4)
				}
			MAX-ACCESS read-write
			STATUS current
			DESCRIPTION
				"Selection of MED device type"
			::= { sle2LldpGlobalControl 8 }

		
		sle2LldpGlobalControlPortDescription OBJECT-TYPE
			SYNTAX OCTET STRING
			MAX-ACCESS read-write
			STATUS current
			DESCRIPTION
				"LLDP Global Port Description"
			::= { sle2LldpGlobalControl 9 }

		
		sle2LldpParameters OBJECT IDENTIFIER ::= { sleBridge 40 }

		
		sle2LldpParametersTable OBJECT-TYPE
			SYNTAX SEQUENCE OF Sle2LldpParametersEntry
			MAX-ACCESS not-accessible
			STATUS current
			DESCRIPTION
				"Description."
			::= { sle2LldpParameters 1 }

		
		sle2LldpParametersEntry OBJECT-TYPE
			SYNTAX Sle2LldpParametersEntry
			MAX-ACCESS not-accessible
			STATUS current
			DESCRIPTION
				"Description."
			INDEX { sle2LldpParamIfIndex, sle2LldpParamAgentMode }
			::= { sle2LldpParametersTable 1 }

		
		Sle2LldpParametersEntry ::=
			SEQUENCE { 
				sle2LldpParamIfIndex
					InterfaceIndex,
				sle2LldpParamAgentMode
					INTEGER,
				sle2LldpParamBacManagementAddress
					INTEGER,
				sle2LldpParamBacPortDescription
					INTEGER,
				sle2LldpParamBacSystemCapabilities
					INTEGER,
				sle2LldpParamBacSystemDescription
					INTEGER,
				sle2LldpParamBacSystemName
					INTEGER,
				sle2LldpParamI8021LinkAgg
					INTEGER,
				sle2LldpParamI8021MgmtVid
					INTEGER,
				sle2LldpParamI8021PortPtclVlanid
					INTEGER,
				sle2LldpParamI8021PortVlanid
					INTEGER,
				sle2LldpParamI8021PtclIdentity
					INTEGER,
				sle2LldpParamI8021VidDigest
					INTEGER,
				sle2LldpParamI8021VlanName
					INTEGER,
				sle2LldpParamI8023MacPhy
					INTEGER,
				sle2LldpParamI8023MaxMtuSize
					INTEGER,
				sle2LldpParamMedInventory
					INTEGER,
				sle2LldpParamMedLocation
					INTEGER,
				sle2LldpParamMedNetworkPolicy
					INTEGER,
				sle2LldpParamMedPower
					INTEGER
			 }

		sle2LldpParamIfIndex OBJECT-TYPE
			SYNTAX InterfaceIndex
			MAX-ACCESS read-only
			STATUS current
			DESCRIPTION
				"LLDP Interface"
			::= { sle2LldpParametersEntry 1 }

		
		sle2LldpParamAgentMode OBJECT-TYPE
			SYNTAX INTEGER
				{
				nearest(1),
				nontpmr(2),
				customer(3)
				}
			MAX-ACCESS read-only
			STATUS current
			DESCRIPTION
				"LLDP Agent Mode"
			::= { sle2LldpParametersEntry 2 }

		
		sle2LldpParamBacManagementAddress OBJECT-TYPE
			SYNTAX INTEGER
				{
				disable(0),
				enable(1)
				}
			MAX-ACCESS read-only
			STATUS current
			DESCRIPTION
				"management address Specific TLV"
			::= { sle2LldpParametersEntry 3 }

		
		sle2LldpParamBacPortDescription OBJECT-TYPE
			SYNTAX INTEGER
				{
				disable(0),
				enable(1)
				}
			MAX-ACCESS read-only
			STATUS current
			DESCRIPTION
				"port description Specific TLV"
			::= { sle2LldpParametersEntry 4 }

		
		sle2LldpParamBacSystemCapabilities OBJECT-TYPE
			SYNTAX INTEGER
				{
				disable(0),
				enable(1)
				}
			MAX-ACCESS read-only
			STATUS current
			DESCRIPTION
				"system capabilities Specific TLV"
			::= { sle2LldpParametersEntry 5 }

		
		sle2LldpParamBacSystemDescription OBJECT-TYPE
			SYNTAX INTEGER
				{
				disable(0),
				enable(1)
				}
			MAX-ACCESS read-only
			STATUS current
			DESCRIPTION
				"system description Specific TLV"
			::= { sle2LldpParametersEntry 6 }

		
		sle2LldpParamBacSystemName OBJECT-TYPE
			SYNTAX INTEGER
				{
				disable(0),
				enable(1)
				}
			MAX-ACCESS read-only
			STATUS current
			DESCRIPTION
				"system name Specific TLV"
			::= { sle2LldpParametersEntry 7 }

		
		sle2LldpParamI8021LinkAgg OBJECT-TYPE
			SYNTAX INTEGER
				{
				disable(0),
				enable(1)
				}
			MAX-ACCESS read-only
			STATUS current
			DESCRIPTION
				"link agg TLV"
			::= { sle2LldpParametersEntry 8 }

		
		sle2LldpParamI8021MgmtVid OBJECT-TYPE
			SYNTAX INTEGER
				{
				disable(0),
				enable(1)
				}
			MAX-ACCESS read-only
			STATUS current
			DESCRIPTION
				"Mgmt vid TLV"
			::= { sle2LldpParametersEntry 9 }

		
		sle2LldpParamI8021PortPtclVlanid OBJECT-TYPE
			SYNTAX INTEGER
				{
				disable(0),
				enable(1)
				}
			MAX-ACCESS read-only
			STATUS current
			DESCRIPTION
				"Port ptcl vlanid TLV"
			::= { sle2LldpParametersEntry 10 }

		
		sle2LldpParamI8021PortVlanid OBJECT-TYPE
			SYNTAX INTEGER
				{
				disable(0),
				enable(1)
				}
			MAX-ACCESS read-only
			STATUS current
			DESCRIPTION
				"Port vlanid TLV"
			::= { sle2LldpParametersEntry 11 }

		
		sle2LldpParamI8021PtclIdentity OBJECT-TYPE
			SYNTAX INTEGER
				{
				disable(0),
				enable(1)
				}
			MAX-ACCESS read-only
			STATUS current
			DESCRIPTION
				"Ptcl identity TLV"
			::= { sle2LldpParametersEntry 12 }

		
		sle2LldpParamI8021VidDigest OBJECT-TYPE
			SYNTAX INTEGER
				{
				disable(0),
				enable(1)
				}
			MAX-ACCESS read-only
			STATUS current
			DESCRIPTION
				"Vid digest TLV"
			::= { sle2LldpParametersEntry 13 }

		
		sle2LldpParamI8021VlanName OBJECT-TYPE
			SYNTAX INTEGER
				{
				disable(0),
				enable(1)
				}
			MAX-ACCESS read-only
			STATUS current
			DESCRIPTION
				"Vlan name TLV"
			::= { sle2LldpParametersEntry 14 }

		
		sle2LldpParamI8023MacPhy OBJECT-TYPE
			SYNTAX INTEGER
				{
				disable(0),
				enable(1)
				}
			MAX-ACCESS read-only
			STATUS current
			DESCRIPTION
				"mac phy TLV"
			::= { sle2LldpParametersEntry 15 }

		
		sle2LldpParamI8023MaxMtuSize OBJECT-TYPE
			SYNTAX INTEGER
				{
				disable(0),
				enable(1)
				}
			MAX-ACCESS read-only
			STATUS current
			DESCRIPTION
				"Max mtu size TLV"
			::= { sle2LldpParametersEntry 16 }

		
		sle2LldpParamMedInventory OBJECT-TYPE
			SYNTAX INTEGER
				{
				disable(0),
				enable(1)
				}
			MAX-ACCESS read-only
			STATUS current
			DESCRIPTION
				"Inventory"
			::= { sle2LldpParametersEntry 17 }

		
		sle2LldpParamMedLocation OBJECT-TYPE
			SYNTAX INTEGER
				{
				disable(0),
				enable(1)
				}
			MAX-ACCESS read-only
			STATUS current
			DESCRIPTION
				"Location"
			::= { sle2LldpParametersEntry 18 }

		
		sle2LldpParamMedNetworkPolicy OBJECT-TYPE
			SYNTAX INTEGER
				{
				disable(0),
				enable(1)
				}
			MAX-ACCESS read-only
			STATUS current
			DESCRIPTION
				"Network policy"
			::= { sle2LldpParametersEntry 19 }

		
		sle2LldpParamMedPower OBJECT-TYPE
			SYNTAX INTEGER
				{
				disable(0),
				enable(1)
				}
			MAX-ACCESS read-only
			STATUS current
			DESCRIPTION
				"Power"
			::= { sle2LldpParametersEntry 20 }

		
		sle2LldpParametersControl OBJECT IDENTIFIER ::= { sle2LldpParameters 2 }

		
		sle2LldpParamControlRequest OBJECT-TYPE
			SYNTAX INTEGER { setLldpParam(1) }
			MAX-ACCESS read-write
			STATUS current
			DESCRIPTION
				"The request of a user command"
			::= { sle2LldpParametersControl 1 }

		
		sle2LldpParamControlStatus OBJECT-TYPE
			SYNTAX SleControlStatusType
			MAX-ACCESS read-only
			STATUS current
			DESCRIPTION
				"The status of a user command"
			::= { sle2LldpParametersControl 2 }

		
		sle2LldpParamControlTimer OBJECT-TYPE
			SYNTAX Gauge32
			MAX-ACCESS read-write
			STATUS current
			DESCRIPTION
				"The maximum time for the manager for a long running user command"
			::= { sle2LldpParametersControl 3 }

		
		sle2LldpParamControlTimeStamp OBJECT-TYPE
			SYNTAX TimeTicks
			MAX-ACCESS read-only
			STATUS current
			DESCRIPTION
				"The time stamp of the last command(end of command)"
			::= { sle2LldpParametersControl 4 }

		
		sle2LldpParamControlReqResult OBJECT-TYPE
			SYNTAX SleControlRequestResultType
			MAX-ACCESS read-only
			STATUS current
			DESCRIPTION
				"Result of the last command."
			::= { sle2LldpParametersControl 5 }

		
		sle2LldpParamControlIfIndex OBJECT-TYPE
			SYNTAX InterfaceIndex
			MAX-ACCESS read-write
			STATUS current
			DESCRIPTION
				"LLDP Interface"
			::= { sle2LldpParametersControl 6 }

		
		sle2LldpParamControlAgentMode OBJECT-TYPE
			SYNTAX INTEGER
				{
				nearest(1),
				nontpmr(2),
				customer(3)
				}
			MAX-ACCESS read-write
			STATUS current
			DESCRIPTION
				"LLDP Agent Mode"
			::= { sle2LldpParametersControl 7 }

		
		sle2LldpParamControlBacManagementAddress OBJECT-TYPE
			SYNTAX INTEGER
				{
				disable(0),
				enable(1)
				}
			MAX-ACCESS read-write
			STATUS current
			DESCRIPTION
				"Management address Specific TLV"
			::= { sle2LldpParametersControl 8 }

		
		sle2LldpParamControlBacPortDescription OBJECT-TYPE
			SYNTAX INTEGER
				{
				disable(0),
				enable(1)
				}
			MAX-ACCESS read-write
			STATUS current
			DESCRIPTION
				"Port description Specific TLV"
			::= { sle2LldpParametersControl 9 }

		
		sle2LldpParamControlBacSystemCapabilities OBJECT-TYPE
			SYNTAX INTEGER
				{
				disable(0),
				enable(1)
				}
			MAX-ACCESS read-write
			STATUS current
			DESCRIPTION
				"System capabilities Specific TLV"
			::= { sle2LldpParametersControl 10 }

		
		sle2LldpParamControlBacSystemDescription OBJECT-TYPE
			SYNTAX INTEGER
				{
				disable(0),
				enable(1)
				}
			MAX-ACCESS read-write
			STATUS current
			DESCRIPTION
				"System description Specific TLV"
			::= { sle2LldpParametersControl 11 }

		
		sle2LldpParamControlBacSystemName OBJECT-TYPE
			SYNTAX INTEGER
				{
				disable(0),
				enable(1)
				}
			MAX-ACCESS read-write
			STATUS current
			DESCRIPTION
				"System name Specific TLV"
			::= { sle2LldpParametersControl 12 }

		
		sle2LldpParamControlI8021LinkAgg OBJECT-TYPE
			SYNTAX INTEGER
				{
				disable(0),
				enable(1)
				}
			MAX-ACCESS read-write
			STATUS current
			DESCRIPTION
				"Link agg TLV"
			::= { sle2LldpParametersControl 13 }

		
		sle2LldpParamControlI8021MgmtVid OBJECT-TYPE
			SYNTAX INTEGER
				{
				disable(0),
				enable(1)
				}
			MAX-ACCESS read-write
			STATUS current
			DESCRIPTION
				"Mgmt vid TLV"
			::= { sle2LldpParametersControl 14 }

		
		sle2LldpParamControlI8021PortPtclVlanid OBJECT-TYPE
			SYNTAX INTEGER
				{
				disable(0),
				enable(1)
				}
			MAX-ACCESS read-write
			STATUS current
			DESCRIPTION
				"Port ptcl vlanid TLV"
			::= { sle2LldpParametersControl 15 }

		
		sle2LldpParamControlI8021PortVlanid OBJECT-TYPE
			SYNTAX INTEGER
				{
				disable(0),
				enable(1)
				}
			MAX-ACCESS read-write
			STATUS current
			DESCRIPTION
				"Port vlanid TLV"
			::= { sle2LldpParametersControl 16 }

		
		sle2LldpParamControlI8021PtclIdentity OBJECT-TYPE
			SYNTAX INTEGER
				{
				disable(0),
				enable(1)
				}
			MAX-ACCESS read-write
			STATUS current
			DESCRIPTION
				"Ptcl identity TLV"
			::= { sle2LldpParametersControl 17 }

		
		sle2LldpParamControlI8021VidDigest OBJECT-TYPE
			SYNTAX INTEGER
				{
				disable(0),
				enable(1)
				}
			MAX-ACCESS read-write
			STATUS current
			DESCRIPTION
				"Vid digest TLV"
			::= { sle2LldpParametersControl 18 }

		
		sle2LldpParamControlI8021VlanName OBJECT-TYPE
			SYNTAX INTEGER
				{
				disable(0),
				enable(1)
				}
			MAX-ACCESS read-write
			STATUS current
			DESCRIPTION
				"Vlan name TLV"
			::= { sle2LldpParametersControl 19 }

		
		sle2LldpParamControlI8023MacPhy OBJECT-TYPE
			SYNTAX INTEGER
				{
				disable(0),
				enable(1)
				}
			MAX-ACCESS read-write
			STATUS current
			DESCRIPTION
				"Mac phy TLV"
			::= { sle2LldpParametersControl 20 }

		
		sle2LldpParamControlI8023MaxMtuSize OBJECT-TYPE
			SYNTAX INTEGER
				{
				disable(0),
				enable(1)
				}
			MAX-ACCESS read-write
			STATUS current
			DESCRIPTION
				"Max mtu size TLV"
			::= { sle2LldpParametersControl 21 }

		
		sle2LldpParamControlMedInventory OBJECT-TYPE
			SYNTAX INTEGER
				{
				disable(0),
				enable(1)
				}
			MAX-ACCESS read-write
			STATUS current
			DESCRIPTION
				"Inventory"
			::= { sle2LldpParametersControl 22 }

		
		sle2LldpParamControlMedLocation OBJECT-TYPE
			SYNTAX INTEGER
				{
				disable(0),
				enable(1)
				}
			MAX-ACCESS read-write
			STATUS current
			DESCRIPTION
				"Location"
			::= { sle2LldpParametersControl 23 }

		
		sle2LldpParamControlMedNetworkPolicy OBJECT-TYPE
			SYNTAX INTEGER
				{
				disable(0),
				enable(1)
				}
			MAX-ACCESS read-write
			STATUS current
			DESCRIPTION
				"Network policy"
			::= { sle2LldpParametersControl 24 }

		
		sle2LldpParamControlMedPower OBJECT-TYPE
			SYNTAX INTEGER
				{
				disable(0),
				enable(1)
				}
			MAX-ACCESS read-write
			STATUS current
			DESCRIPTION
				"Power"
			::= { sle2LldpParametersControl 25 }

		
		sle2LldpAgent OBJECT IDENTIFIER ::= { sleBridge 41 }

		
		sle2LldpAgentTable OBJECT-TYPE
			SYNTAX SEQUENCE OF Sle2LldpAgentEntry
			MAX-ACCESS not-accessible
			STATUS current
			DESCRIPTION
				"Description."
			::= { sle2LldpAgent 1 }

		
		sle2LldpAgentEntry OBJECT-TYPE
			SYNTAX Sle2LldpAgentEntry
			MAX-ACCESS not-accessible
			STATUS current
			DESCRIPTION
				"Description."
			INDEX { sle2LldpAgentIfIndex, sle2LldpAgentMode }
			::= { sle2LldpAgentTable 1 }

		
		Sle2LldpAgentEntry ::=
			SEQUENCE { 
				sle2LldpAgentIfIndex
					InterfaceIndex,
				sle2LldpAgentMode
					INTEGER,
				sle2LldpAgentChassisIdTlv
					INTEGER,
				sle2LldpAgentAdminStatus
					INTEGER,
				sle2LldpAgentLocallyAssigned
					OCTET STRING,
				sle2LldpAgentManagementAddressTlv
					INTEGER,
				sle2LldpAgentMsgTxHold
					Integer32,
				sle2LldpAgentPortIdTlv
					INTEGER,
				sle2LldpAgentTimerMsgFastTx
					Integer32,
				sle2LldpAgentTimerMsgTxInterval
					Integer32,
				sle2LldpAgentTimerReinitDelay
					Integer32,
				sle2LldpAgentTimerTxDelay
					Integer32,
				sle2LldpAgentTMNlimit
					Integer32,
				sle2LldpAgentTMNInfoType
					INTEGER,
				sle2LldpAgentTMNMac
					MacAddress,
				sle2LldpAgentTMNTimer
					Integer32,
				sle2LldpAgentTxFastInit
					Integer32,
				sle2LldpAgentTxMaxCredit
					Integer32
			 }

		sle2LldpAgentIfIndex OBJECT-TYPE
			SYNTAX InterfaceIndex
			MAX-ACCESS read-only
			STATUS current
			DESCRIPTION
				"LLDP Interface"
			::= { sle2LldpAgentEntry 1 }

		
		sle2LldpAgentMode OBJECT-TYPE
			SYNTAX INTEGER
				{
				nearest(1),
				nontpmr(2),
				customer(3)
				}
			MAX-ACCESS read-only
			STATUS current
			DESCRIPTION
				"LLDP Agent Mode"
			::= { sle2LldpAgentEntry 2 }

		
		sle2LldpAgentChassisIdTlv OBJECT-TYPE
			SYNTAX INTEGER
				{
				ifalias(1),
				ifname(2),
				ipaddress(3),
				locallyassigned(4),
				macaddress(5)
				}
			MAX-ACCESS read-only
			STATUS current
			DESCRIPTION
				"chassis ID sub type"
			::= { sle2LldpAgentEntry 3 }

		
		sle2LldpAgentAdminStatus OBJECT-TYPE
			SYNTAX INTEGER
				{
				txOnly(1),
				rxOnly(2),
				txAndRx(3),
				disabled(4)
				}
			MAX-ACCESS read-only
			STATUS current
			DESCRIPTION
				"LLDP Status"
			::= { sle2LldpAgentEntry 4 }

		
		sle2LldpAgentLocallyAssigned OBJECT-TYPE
			SYNTAX OCTET STRING
			MAX-ACCESS read-only
			STATUS current
			DESCRIPTION
				"Locally assigned"
			::= { sle2LldpAgentEntry 5 }

		
		sle2LldpAgentManagementAddressTlv OBJECT-TYPE
			SYNTAX INTEGER
				{
				ipaddress(1),
				macaddress(2)
				}
			MAX-ACCESS read-only
			STATUS current
			DESCRIPTION
				"Management Address sub type"
			::= { sle2LldpAgentEntry 6 }

		
		sle2LldpAgentMsgTxHold OBJECT-TYPE
			SYNTAX Integer32 (1..100)
			MAX-ACCESS read-only
			STATUS current
			DESCRIPTION
				"MsgTxHold Value"
			::= { sle2LldpAgentEntry 7 }

		
		sle2LldpAgentPortIdTlv OBJECT-TYPE
			SYNTAX INTEGER
				{
				agtcircuitid(1),
				ifalias(2),
				ifname(3),
				ipaddress(4),
				locallyassigned(5),
				macaddress(6)
				}
			MAX-ACCESS read-only
			STATUS current
			DESCRIPTION
				"Port ID sub type"
			::= { sle2LldpAgentEntry 8 }

		
		sle2LldpAgentTimerMsgFastTx OBJECT-TYPE
			SYNTAX Integer32 (1..3600)
			MAX-ACCESS read-only
			STATUS current
			DESCRIPTION
				"Msg fast tx"
			::= { sle2LldpAgentEntry 9 }

		
		sle2LldpAgentTimerMsgTxInterval OBJECT-TYPE
			SYNTAX Integer32 (5..3600)
			MAX-ACCESS read-only
			STATUS current
			DESCRIPTION
				"Message Transmit Interval"
			::= { sle2LldpAgentEntry 10 }

		
		sle2LldpAgentTimerReinitDelay OBJECT-TYPE
			SYNTAX Integer32 (1..10)
			MAX-ACCESS read-only
			STATUS current
			DESCRIPTION
				"Reinitialization Delay"
			::= { sle2LldpAgentEntry 11 }

		
		sle2LldpAgentTimerTxDelay OBJECT-TYPE
			SYNTAX Integer32 (1..8)
			MAX-ACCESS read-only
			STATUS current
			DESCRIPTION
				"Transmit Delay"
			::= { sle2LldpAgentEntry 12 }

		
		sle2LldpAgentTMNlimit OBJECT-TYPE
			SYNTAX Integer32 (1..65535)
			MAX-ACCESS read-only
			STATUS current
			DESCRIPTION
				"Upper limit for the no. of Remote LLDP Information"
			::= { sle2LldpAgentEntry 13 }

		
		sle2LldpAgentTMNInfoType OBJECT-TYPE
			SYNTAX INTEGER
				{
				existing(1),
				received(2)
				}
			MAX-ACCESS read-only
			STATUS current
			DESCRIPTION
				"LLDP TMN Info Type"
			::= { sle2LldpAgentEntry 14 }

		
		sle2LldpAgentTMNMac OBJECT-TYPE
			SYNTAX MacAddress
			MAX-ACCESS read-only
			STATUS current
			DESCRIPTION
				"MAC Address of the Remate LLDP Agent"
			::= { sle2LldpAgentEntry 15 }

		
		sle2LldpAgentTMNTimer OBJECT-TYPE
			SYNTAX Integer32 (1..65535)
			MAX-ACCESS read-only
			STATUS current
			DESCRIPTION
				"Timer"
			::= { sle2LldpAgentEntry 16 }

		
		sle2LldpAgentTxFastInit OBJECT-TYPE
			SYNTAX Integer32 (1..8)
			MAX-ACCESS read-only
			STATUS current
			DESCRIPTION
				"Tx fast init"
			::= { sle2LldpAgentEntry 17 }

		
		sle2LldpAgentTxMaxCredit OBJECT-TYPE
			SYNTAX Integer32 (1..10)
			MAX-ACCESS read-only
			STATUS current
			DESCRIPTION
				"Tx max credit"
			::= { sle2LldpAgentEntry 18 }

		
		sle2LldpAgentControl OBJECT IDENTIFIER ::= { sle2LldpAgent 2 }

		
		sle2LldpAgentControlRequest OBJECT-TYPE
			SYNTAX INTEGER
				{
				setLldpAgent(1),
				clearLldpAgent(2)
				}
			MAX-ACCESS read-write
			STATUS current
			DESCRIPTION
				"The request of a user command"
			::= { sle2LldpAgentControl 1 }

		
		sle2LldpAgentControlStatus OBJECT-TYPE
			SYNTAX SleControlStatusType
			MAX-ACCESS read-only
			STATUS current
			DESCRIPTION
				"The status of a user command"
			::= { sle2LldpAgentControl 2 }

		
		sle2LldpAgentControlTimer OBJECT-TYPE
			SYNTAX Gauge32
			MAX-ACCESS read-write
			STATUS current
			DESCRIPTION
				"The maximum time for the manager for a long running user command"
			::= { sle2LldpAgentControl 3 }

		
		sle2LldpAgentControlTimeStamp OBJECT-TYPE
			SYNTAX TimeTicks
			MAX-ACCESS read-only
			STATUS current
			DESCRIPTION
				"The time stamp of the last command(end of command)"
			::= { sle2LldpAgentControl 4 }

		
		sle2LldpAgentControlReqResult OBJECT-TYPE
			SYNTAX SleControlRequestResultType
			MAX-ACCESS read-only
			STATUS current
			DESCRIPTION
				"Result of the last command."
			::= { sle2LldpAgentControl 5 }

		
		sle2LldpAgentControlIfIndex OBJECT-TYPE
			SYNTAX InterfaceIndex
			MAX-ACCESS read-write
			STATUS current
			DESCRIPTION
				"LLDP Interface"
			::= { sle2LldpAgentControl 6 }

		
		sle2LldpAgentControlMode OBJECT-TYPE
			SYNTAX INTEGER
				{
				nearest(1),
				nontpmr(2),
				customer(3)
				}
			MAX-ACCESS read-write
			STATUS current
			DESCRIPTION
				"LLDP Agent Mode"
			::= { sle2LldpAgentControl 7 }

		
		sle2LldpAgentControlChassisIdTlv OBJECT-TYPE
			SYNTAX INTEGER
				{
				ifalias(1),
				ifname(2),
				ipaddress(3),
				locallyassigned(4),
				macaddress(5)
				}
			MAX-ACCESS read-write
			STATUS current
			DESCRIPTION
				"chassis ID sub type"
			::= { sle2LldpAgentControl 8 }

		
		sle2LldpAgentControlAdminStatus OBJECT-TYPE
			SYNTAX INTEGER
				{
				txOnly(1),
				rxOnly(2),
				txAndRx(3)
				}
			MAX-ACCESS read-write
			STATUS current
			DESCRIPTION
				"LLDP Status"
			::= { sle2LldpAgentControl 9 }

		
		sle2LldpAgentControlLocallyAssigned OBJECT-TYPE
			SYNTAX OCTET STRING
			MAX-ACCESS read-write
			STATUS current
			DESCRIPTION
				"Locally assigned"
			::= { sle2LldpAgentControl 10 }

		
		sle2LldpAgentControlManagementAddressTlv OBJECT-TYPE
			SYNTAX INTEGER
				{
				ipaddress(1),
				macaddress(2)
				}
			MAX-ACCESS read-write
			STATUS current
			DESCRIPTION
				"Management Address sub type"
			::= { sle2LldpAgentControl 11 }

		
		sle2LldpAgentControlMsgTxHold OBJECT-TYPE
			SYNTAX Integer32 (1..100)
			MAX-ACCESS read-write
			STATUS current
			DESCRIPTION
				"MsgTxHold Value"
			::= { sle2LldpAgentControl 12 }

		
		sle2LldpAgentControlPortIdTlv OBJECT-TYPE
			SYNTAX INTEGER
				{
				agtcircuitid(1),
				ifalias(2),
				ifname(3),
				ipaddress(4),
				locallyassigned(5),
				macaddress(6)
				}
			MAX-ACCESS read-write
			STATUS current
			DESCRIPTION
				"Port ID sub type"
			::= { sle2LldpAgentControl 13 }

		
		sle2LldpAgentControlTimerMsgFastTx OBJECT-TYPE
			SYNTAX Integer32 (1..3600)
			MAX-ACCESS read-write
			STATUS current
			DESCRIPTION
				"Msg fast tx"
			::= { sle2LldpAgentControl 14 }

		
		sle2LldpAgentControlTimerMsgTxInterval OBJECT-TYPE
			SYNTAX Integer32 (5..3600)
			MAX-ACCESS read-write
			STATUS current
			DESCRIPTION
				"Message Transmit Interval"
			::= { sle2LldpAgentControl 15 }

		
		sle2LldpAgentControlTimerReinitDelay OBJECT-TYPE
			SYNTAX Integer32 (1..10)
			MAX-ACCESS read-write
			STATUS current
			DESCRIPTION
				"Reinitialization Delay"
			::= { sle2LldpAgentControl 16 }

		
		sle2LldpAgentControlTimerTxDelay OBJECT-TYPE
			SYNTAX Integer32 (1..8)
			MAX-ACCESS read-write
			STATUS current
			DESCRIPTION
				"Transmit Delay"
			::= { sle2LldpAgentControl 17 }

		
		sle2LldpAgentControlTMNlimit OBJECT-TYPE
			SYNTAX Integer32 (1..65535)
			MAX-ACCESS read-write
			STATUS current
			DESCRIPTION
				"Upper limit for the no. of Remote LLDP Information"
			::= { sle2LldpAgentControl 18 }

		
		sle2LldpAgentControlTMNInfoType OBJECT-TYPE
			SYNTAX INTEGER
				{
				existing(1),
				received(2)
				}
			MAX-ACCESS read-write
			STATUS current
			DESCRIPTION
				"LLDP TMN Info Type"
			::= { sle2LldpAgentControl 19 }

		
		sle2LldpAgentControlTMNMac OBJECT-TYPE
			SYNTAX MacAddress
			MAX-ACCESS read-write
			STATUS current
			DESCRIPTION
				"MAC Address of the Remate LLDP Agent"
			::= { sle2LldpAgentControl 20 }

		
		sle2LldpAgentControlTMNTimer OBJECT-TYPE
			SYNTAX Integer32 (1..65535)
			MAX-ACCESS read-write
			STATUS current
			DESCRIPTION
				"Timer"
			::= { sle2LldpAgentControl 21 }

		
		sle2LldpAgentControlTxFastInit OBJECT-TYPE
			SYNTAX Integer32 (1..8)
			MAX-ACCESS read-write
			STATUS current
			DESCRIPTION
				"Tx fast init"
			::= { sle2LldpAgentControl 22 }

		
		sle2LldpAgentControlTxMaxCredit OBJECT-TYPE
			SYNTAX Integer32 (1..10)
			MAX-ACCESS read-write
			STATUS current
			DESCRIPTION
				"Tx max credit"
			::= { sle2LldpAgentControl 23 }

		
		sle2LldpStatistics OBJECT IDENTIFIER ::= { sleBridge 42 }

		
		sle2LldpStatisticsTable OBJECT-TYPE
			SYNTAX SEQUENCE OF Sle2LldpStatisticsEntry
			MAX-ACCESS not-accessible
			STATUS current
			DESCRIPTION
				"Description."
			::= { sle2LldpStatistics 1 }

		
		sle2LldpStatisticsEntry OBJECT-TYPE
			SYNTAX Sle2LldpStatisticsEntry
			MAX-ACCESS not-accessible
			STATUS current
			DESCRIPTION
				"Description."
			INDEX { sle2LldpStatsIfIndex, sle2LldpStatsAgentMode }
			::= { sle2LldpStatisticsTable 1 }

		
		Sle2LldpStatisticsEntry ::=
			SEQUENCE { 
				sle2LldpStatsIfIndex
					InterfaceIndex,
				sle2LldpStatsAgentMode
					INTEGER,
				sle2LldpStatsTransmittedFramesTotal
					Integer32,
				sle2LldpStatsAgedEntriesTotal
					Integer32,
				sle2LldpStatsReceivedFramesTotal
					Integer32,
				sle2LldpStatsReceivedFramesError
					Integer32,
				sle2LldpStatsDiscardedFramesTotal
					Integer32,
				sle2LldpStatsTLVDiscardTotal
					Integer32,
				sle2LldpStatsTLVUnrecognisedTotal
					Integer32
			 }

		sle2LldpStatsIfIndex OBJECT-TYPE
			SYNTAX InterfaceIndex
			MAX-ACCESS read-only
			STATUS current
			DESCRIPTION
				"LLDP Interface"
			::= { sle2LldpStatisticsEntry 1 }

		
		sle2LldpStatsAgentMode OBJECT-TYPE
			SYNTAX INTEGER
				{
				nearest(1),
				nontpmr(2),
				customer(3)
				}
			MAX-ACCESS read-only
			STATUS current
			DESCRIPTION
				"LLDP Agent Mode"
			::= { sle2LldpStatisticsEntry 2 }

		
		sle2LldpStatsTransmittedFramesTotal OBJECT-TYPE
			SYNTAX Integer32
			MAX-ACCESS read-only
			STATUS current
			DESCRIPTION
				"Total frames transmitted"
			::= { sle2LldpStatisticsEntry 3 }

		
		sle2LldpStatsAgedEntriesTotal OBJECT-TYPE
			SYNTAX Integer32
			MAX-ACCESS read-only
			STATUS current
			DESCRIPTION
				"Total entries aged"
			::= { sle2LldpStatisticsEntry 4 }

		
		sle2LldpStatsReceivedFramesTotal OBJECT-TYPE
			SYNTAX Integer32
			MAX-ACCESS read-only
			STATUS current
			DESCRIPTION
				"Total frames received"
			::= { sle2LldpStatisticsEntry 5 }

		
		sle2LldpStatsReceivedFramesError OBJECT-TYPE
			SYNTAX Integer32
			MAX-ACCESS read-only
			STATUS current
			DESCRIPTION
				"Total frames received in error"
			::= { sle2LldpStatisticsEntry 6 }

		
		sle2LldpStatsDiscardedFramesTotal OBJECT-TYPE
			SYNTAX Integer32
			MAX-ACCESS read-only
			STATUS current
			DESCRIPTION
				"Total frames discarded"
			::= { sle2LldpStatisticsEntry 7 }

		
		sle2LldpStatsTLVDiscardTotal OBJECT-TYPE
			SYNTAX Integer32
			MAX-ACCESS read-only
			STATUS current
			DESCRIPTION
				"Total discarded TLVs"
			::= { sle2LldpStatisticsEntry 8 }

		
		sle2LldpStatsTLVUnrecognisedTotal OBJECT-TYPE
			SYNTAX Integer32
			MAX-ACCESS read-only
			STATUS current
			DESCRIPTION
				"Total unrecognised TLVs"
			::= { sle2LldpStatisticsEntry 9 }

		
		sle2LldpStatisticsControl OBJECT IDENTIFIER ::= { sle2LldpStatistics 2 }

		
		sle2LldpStatsControlRequest OBJECT-TYPE
			SYNTAX INTEGER { clearLldpStats(1) }
			MAX-ACCESS read-write
			STATUS current
			DESCRIPTION
				"The request of a user command"
			::= { sle2LldpStatisticsControl 1 }

		
		sle2LldpStatsControlStatus OBJECT-TYPE
			SYNTAX SleControlStatusType
			MAX-ACCESS read-only
			STATUS current
			DESCRIPTION
				"The status of a user command"
			::= { sle2LldpStatisticsControl 2 }

		
		sle2LldpStatsControlTimer OBJECT-TYPE
			SYNTAX Gauge32
			MAX-ACCESS read-write
			STATUS current
			DESCRIPTION
				"The maximum time for the manager for a long running user command"
			::= { sle2LldpStatisticsControl 3 }

		
		sle2LldpStatsControlTimeStamp OBJECT-TYPE
			SYNTAX TimeTicks
			MAX-ACCESS read-only
			STATUS current
			DESCRIPTION
				"The time stamp of the last command(end of command)"
			::= { sle2LldpStatisticsControl 4 }

		
		sle2LldpStatsControlReqResult OBJECT-TYPE
			SYNTAX SleControlRequestResultType
			MAX-ACCESS read-only
			STATUS current
			DESCRIPTION
				"Result of the last command."
			::= { sle2LldpStatisticsControl 5 }

		
		sle2LldpRemote OBJECT IDENTIFIER ::= { sleBridge 43 }

		
		sle2LldpRemoteTable OBJECT-TYPE
			SYNTAX SEQUENCE OF Sle2LldpRemoteEntry
			MAX-ACCESS not-accessible
			STATUS current
			DESCRIPTION
				"Description."
			::= { sle2LldpRemote 1 }

		
		sle2LldpRemoteEntry OBJECT-TYPE
			SYNTAX Sle2LldpRemoteEntry
			MAX-ACCESS not-accessible
			STATUS current
			DESCRIPTION
				"Description."
			INDEX { sle2LldpRemoteIfIndex, sle2LldpRemoteAgentMode }
			::= { sle2LldpRemoteTable 1 }

		
		Sle2LldpRemoteEntry ::=
			SEQUENCE { 
				sle2LldpRemoteIfIndex
					InterfaceIndex,
				sle2LldpRemoteAgentMode
					INTEGER,
				sle2LldpRemoteSysName
					OCTET STRING,
				sle2LldpRemoteSysDescr
					OCTET STRING,
				sle2LldpRemotePortDescr
					OCTET STRING,
				sle2LldpRemoteRxTtl
					Integer32,
				sle2LldpRemoteSysCapability
					OCTET STRING,
				sle2LldpRemoteIfNumbering
					Integer32,
				sle2LldpRemoteIfNumber
					Integer32,
				sle2LldpRemoteOid
					OCTET STRING,
				sle2LldpRemoteMgmtAddrSubType
					INTEGER,
				sle2LldpRemoteMgmtAddr
					OCTET STRING,
				sle2LldpRemoteChassisIdType
					INTEGER,
				sle2LldpRemoteChassisId
					OCTET STRING,
				sle2LldpRemotePortIdType
					INTEGER,
				sle2LldpRemotePortId
					OCTET STRING,
				sle2LldpRemotePortVlanId
					Integer32,
				sle2LldpRemotePPVlanId
					Integer32,
				sle2LldpRemoteProtocols
					BITS,
				sle2LldpRemoteVidUsageDigest
					Integer32,
				sle2LldpRemoteMgmtVlan
					Integer32,
				sle2LldpRemoteLinkAggrStatus
					INTEGER,
				sle2LldpRemoteLinkAggrPortId
					Integer32,
				sle2LldpRemoteAutonegoSupport
					BITS,
				sle2LldpRemoteAutonegoCapability
					Integer32,
				sle2LldpRemoteOperMauType
					Integer32,
				sle2LldpRemoteMaxFrameSize
					Integer32,
				sle2LldpRemoteMedCapability
					BITS,
				sle2LldpRemoteMedCapabilityDevType
					OCTET STRING,
				sle2LldpRemoteMedNwPlcyAppType
					OCTET STRING,
				sle2LldpRemoteMedNwPlcyVlanId
					Integer32,
				sle2LldpRemoteMedNwPlcyTagged
					INTEGER,
				sle2LldpRemoteMedNwPlcyL2Prio
					Integer32,
				sle2LldpRemoteMedNwPlcyDscp
					Integer32,
				sle2LldpRemoteMedLocDataFormat
					OCTET STRING,
				sle2LldpRemoteMedLocLatitudeRes
					Integer32,
				sle2LldpRemoteMedLocLatitude
					Counter64,
				sle2LldpRemoteMedLocLongitudeRes
					Integer32,
				sle2LldpRemoteMedLocLongitude
					Counter64,
				sle2LldpRemoteMedLocAt
					Integer32,
				sle2LldpRemoteMedLocAltitudeRes
					Integer32,
				sle2LldpRemoteMedLocAltitude
					Integer32,
				sle2LldpRemoteMedLocDatum
					Integer32,
				sle2LldpRemoteMedLocLciLength
					Integer32,
				sle2LldpRemoteMedLocWhat
					Integer32,
				sle2LldpRemoteMedLocCountryCode
					Integer32,
				sle2LldpRemoteMedLocCaType
					Integer32,
				sle2LldpRemoteMedLocCaLen
					Integer32
			 }

		sle2LldpRemoteIfIndex OBJECT-TYPE
			SYNTAX InterfaceIndex
			MAX-ACCESS read-only
			STATUS current
			DESCRIPTION
				"LLDP Interface"
			::= { sle2LldpRemoteEntry 1 }

		
		sle2LldpRemoteAgentMode OBJECT-TYPE
			SYNTAX INTEGER
				{
				nearest(1),
				nontpmr(2),
				customer(3)
				}
			MAX-ACCESS read-only
			STATUS current
			DESCRIPTION
				"LLDP Agent Mode"
			::= { sle2LldpRemoteEntry 2 }

		
		sle2LldpRemoteSysName OBJECT-TYPE
			SYNTAX OCTET STRING
			MAX-ACCESS read-only
			STATUS current
			DESCRIPTION
				" "
			::= { sle2LldpRemoteEntry 3 }

		
		sle2LldpRemoteSysDescr OBJECT-TYPE
			SYNTAX OCTET STRING
			MAX-ACCESS read-only
			STATUS current
			DESCRIPTION
				" "
			::= { sle2LldpRemoteEntry 4 }

		
		sle2LldpRemotePortDescr OBJECT-TYPE
			SYNTAX OCTET STRING
			MAX-ACCESS read-only
			STATUS current
			DESCRIPTION
				" "
			::= { sle2LldpRemoteEntry 5 }

		
		sle2LldpRemoteRxTtl OBJECT-TYPE
			SYNTAX Integer32
			MAX-ACCESS read-only
			STATUS current
			DESCRIPTION
				" "
			::= { sle2LldpRemoteEntry 6 }

		
		sle2LldpRemoteSysCapability OBJECT-TYPE
			SYNTAX OCTET STRING
			MAX-ACCESS read-only
			STATUS current
			DESCRIPTION
				" "
			::= { sle2LldpRemoteEntry 7 }

		
		sle2LldpRemoteIfNumbering OBJECT-TYPE
			SYNTAX Integer32
			MAX-ACCESS read-only
			STATUS current
			DESCRIPTION
				" "
			::= { sle2LldpRemoteEntry 8 }

		
		sle2LldpRemoteIfNumber OBJECT-TYPE
			SYNTAX Integer32
			MAX-ACCESS read-only
			STATUS current
			DESCRIPTION
				" "
			::= { sle2LldpRemoteEntry 9 }

		
		sle2LldpRemoteOid OBJECT-TYPE
			SYNTAX OCTET STRING
			MAX-ACCESS read-only
			STATUS current
			DESCRIPTION
				" "
			::= { sle2LldpRemoteEntry 10 }

		
		sle2LldpRemoteMgmtAddrSubType OBJECT-TYPE
			SYNTAX INTEGER
				{
				mac(1),
				ip(2)
				}
			MAX-ACCESS read-only
			STATUS current
			DESCRIPTION
				" "
			::= { sle2LldpRemoteEntry 11 }

		
		sle2LldpRemoteMgmtAddr OBJECT-TYPE
			SYNTAX OCTET STRING
			MAX-ACCESS read-only
			STATUS current
			DESCRIPTION
				" "
			::= { sle2LldpRemoteEntry 12 }

		
		sle2LldpRemoteChassisIdType OBJECT-TYPE
			SYNTAX INTEGER
				{
				chassisComponent(1),
				interfaceAlias(2),
				portComponent(3),
				macAddress(4),
				ipAddress(5),
				interfaceName(6),
				locallyAssigned(7)
				}
			MAX-ACCESS read-only
			STATUS current
			DESCRIPTION
				" "
			::= { sle2LldpRemoteEntry 13 }

		
		sle2LldpRemoteChassisId OBJECT-TYPE
			SYNTAX OCTET STRING
			MAX-ACCESS read-only
			STATUS current
			DESCRIPTION
				" "
			::= { sle2LldpRemoteEntry 14 }

		
		sle2LldpRemotePortIdType OBJECT-TYPE
			SYNTAX INTEGER
				{
				interfaceAlias(1),
				portComponent(2),
				macAddress(3),
				ipAddress(4),
				ifName(5),
				agentCircuitId(6),
				locallyAssigned(7)
				}
			MAX-ACCESS read-only
			STATUS current
			DESCRIPTION
				" "
			::= { sle2LldpRemoteEntry 15 }

		
		sle2LldpRemotePortId OBJECT-TYPE
			SYNTAX OCTET STRING
			MAX-ACCESS read-only
			STATUS current
			DESCRIPTION
				" "
			::= { sle2LldpRemoteEntry 16 }

		
		sle2LldpRemotePortVlanId OBJECT-TYPE
			SYNTAX Integer32
			MAX-ACCESS read-only
			STATUS current
			DESCRIPTION
				" "
			::= { sle2LldpRemoteEntry 17 }

		
		sle2LldpRemotePPVlanId OBJECT-TYPE
			SYNTAX Integer32
			MAX-ACCESS read-only
			STATUS current
			DESCRIPTION
				" "
			::= { sle2LldpRemoteEntry 18 }

		
		sle2LldpRemoteProtocols OBJECT-TYPE
			SYNTAX BITS
				{
				stp(0),
				rstp(1),
				mstp(2),
				gmrp(3),
				mmrp(4),
				gvrp(5),
				mvrp(6),
				lacp(7),
				dot1x(8),
				efmoam(9)
				}
			MAX-ACCESS read-only
			STATUS current
			DESCRIPTION
				" "
			::= { sle2LldpRemoteEntry 19 }

		
		sle2LldpRemoteVidUsageDigest OBJECT-TYPE
			SYNTAX Integer32
			MAX-ACCESS read-only
			STATUS current
			DESCRIPTION
				" "
			::= { sle2LldpRemoteEntry 20 }

		
		sle2LldpRemoteMgmtVlan OBJECT-TYPE
			SYNTAX Integer32
			MAX-ACCESS read-only
			STATUS current
			DESCRIPTION
				" "
			::= { sle2LldpRemoteEntry 21 }

		
		sle2LldpRemoteLinkAggrStatus OBJECT-TYPE
			SYNTAX INTEGER
				{
				disabled(0),
				enabled(1)
				}
			MAX-ACCESS read-only
			STATUS current
			DESCRIPTION
				" "
			::= { sle2LldpRemoteEntry 22 }

		
		sle2LldpRemoteLinkAggrPortId OBJECT-TYPE
			SYNTAX Integer32
			MAX-ACCESS read-only
			STATUS current
			DESCRIPTION
				" "
			::= { sle2LldpRemoteEntry 23 }

		
		sle2LldpRemoteAutonegoSupport OBJECT-TYPE
			SYNTAX BITS
				{
				supported(0),
				enabled(1)
				}
			MAX-ACCESS read-only
			STATUS current
			DESCRIPTION
				" "
			::= { sle2LldpRemoteEntry 24 }

		
		sle2LldpRemoteAutonegoCapability OBJECT-TYPE
			SYNTAX Integer32
			MAX-ACCESS read-only
			STATUS current
			DESCRIPTION
				" "
			::= { sle2LldpRemoteEntry 25 }

		
		sle2LldpRemoteOperMauType OBJECT-TYPE
			SYNTAX Integer32
			MAX-ACCESS read-only
			STATUS current
			DESCRIPTION
				" "
			::= { sle2LldpRemoteEntry 26 }

		
		sle2LldpRemoteMaxFrameSize OBJECT-TYPE
			SYNTAX Integer32
			MAX-ACCESS read-only
			STATUS current
			DESCRIPTION
				" "
			::= { sle2LldpRemoteEntry 27 }

		
		sle2LldpRemoteMedCapability OBJECT-TYPE
			SYNTAX BITS
				{
				capabilities(0),
				networkPolicy(1),
				locationIdentification(2),
				extendedPowerMDIPSE(3),
				extendedPowerMDIPD(4),
				medInventory(5),
				reserved(6)
				}
			MAX-ACCESS read-only
			STATUS current
			DESCRIPTION
				" "
			::= { sle2LldpRemoteEntry 28 }

		
		sle2LldpRemoteMedCapabilityDevType OBJECT-TYPE
			SYNTAX OCTET STRING
			MAX-ACCESS read-only
			STATUS current
			DESCRIPTION
				" "
			::= { sle2LldpRemoteEntry 29 }

		
		sle2LldpRemoteMedNwPlcyAppType OBJECT-TYPE
			SYNTAX OCTET STRING
			MAX-ACCESS read-only
			STATUS current
			DESCRIPTION
				" "
			::= { sle2LldpRemoteEntry 30 }

		
		sle2LldpRemoteMedNwPlcyVlanId OBJECT-TYPE
			SYNTAX Integer32
			MAX-ACCESS read-only
			STATUS current
			DESCRIPTION
				" "
			::= { sle2LldpRemoteEntry 31 }

		
		sle2LldpRemoteMedNwPlcyTagged OBJECT-TYPE
			SYNTAX INTEGER
				{
				tagged(1),
				untagged(2)
				}
			MAX-ACCESS read-only
			STATUS current
			DESCRIPTION
				" "
			::= { sle2LldpRemoteEntry 32 }

		
		sle2LldpRemoteMedNwPlcyL2Prio OBJECT-TYPE
			SYNTAX Integer32
			MAX-ACCESS read-only
			STATUS current
			DESCRIPTION
				" "
			::= { sle2LldpRemoteEntry 33 }

		
		sle2LldpRemoteMedNwPlcyDscp OBJECT-TYPE
			SYNTAX Integer32
			MAX-ACCESS read-only
			STATUS current
			DESCRIPTION
				" "
			::= { sle2LldpRemoteEntry 34 }

		
		sle2LldpRemoteMedLocDataFormat OBJECT-TYPE
			SYNTAX OCTET STRING
			MAX-ACCESS read-only
			STATUS current
			DESCRIPTION
				" "
			::= { sle2LldpRemoteEntry 35 }

		
		sle2LldpRemoteMedLocLatitudeRes OBJECT-TYPE
			SYNTAX Integer32
			MAX-ACCESS read-only
			STATUS current
			DESCRIPTION
				" "
			::= { sle2LldpRemoteEntry 36 }

		
		sle2LldpRemoteMedLocLatitude OBJECT-TYPE
			SYNTAX Counter64
			MAX-ACCESS read-only
			STATUS current
			DESCRIPTION
				" "
			::= { sle2LldpRemoteEntry 37 }

		
		sle2LldpRemoteMedLocLongitudeRes OBJECT-TYPE
			SYNTAX Integer32
			MAX-ACCESS read-only
			STATUS current
			DESCRIPTION
				" "
			::= { sle2LldpRemoteEntry 38 }

		
		sle2LldpRemoteMedLocLongitude OBJECT-TYPE
			SYNTAX Counter64
			MAX-ACCESS read-only
			STATUS current
			DESCRIPTION
				" "
			::= { sle2LldpRemoteEntry 39 }

		
		sle2LldpRemoteMedLocAt OBJECT-TYPE
			SYNTAX Integer32
			MAX-ACCESS read-only
			STATUS current
			DESCRIPTION
				" "
			::= { sle2LldpRemoteEntry 40 }

		
		sle2LldpRemoteMedLocAltitudeRes OBJECT-TYPE
			SYNTAX Integer32
			MAX-ACCESS read-only
			STATUS current
			DESCRIPTION
				" "
			::= { sle2LldpRemoteEntry 41 }

		
		sle2LldpRemoteMedLocAltitude OBJECT-TYPE
			SYNTAX Integer32
			MAX-ACCESS read-only
			STATUS current
			DESCRIPTION
				" "
			::= { sle2LldpRemoteEntry 42 }

		
		sle2LldpRemoteMedLocDatum OBJECT-TYPE
			SYNTAX Integer32
			MAX-ACCESS read-only
			STATUS current
			DESCRIPTION
				" "
			::= { sle2LldpRemoteEntry 43 }

		
		sle2LldpRemoteMedLocLciLength OBJECT-TYPE
			SYNTAX Integer32
			MAX-ACCESS read-only
			STATUS current
			DESCRIPTION
				" "
			::= { sle2LldpRemoteEntry 44 }

		
		sle2LldpRemoteMedLocWhat OBJECT-TYPE
			SYNTAX Integer32
			MAX-ACCESS read-only
			STATUS current
			DESCRIPTION
				" "
			::= { sle2LldpRemoteEntry 45 }

		
		sle2LldpRemoteMedLocCountryCode OBJECT-TYPE
			SYNTAX Integer32
			MAX-ACCESS read-only
			STATUS current
			DESCRIPTION
				" "
			::= { sle2LldpRemoteEntry 46 }

		
		sle2LldpRemoteMedLocCaType OBJECT-TYPE
			SYNTAX Integer32
			MAX-ACCESS read-only
			STATUS current
			DESCRIPTION
				" "
			::= { sle2LldpRemoteEntry 47 }

		
		sle2LldpRemoteMedLocCaLen OBJECT-TYPE
			SYNTAX Integer32
			MAX-ACCESS read-only
			STATUS current
			DESCRIPTION
				" "
			::= { sle2LldpRemoteEntry 48 }

		
		sle2LldpRemoteVlan OBJECT IDENTIFIER ::= { sleBridge 44 }

		
		sle2LldpRemoteVlanTable OBJECT-TYPE
			SYNTAX SEQUENCE OF Sle2LldpRemoteVlanEntry
			MAX-ACCESS not-accessible
			STATUS current
			DESCRIPTION
				"Description."
			::= { sle2LldpRemoteVlan 1 }

		
		sle2LldpRemoteVlanEntry OBJECT-TYPE
			SYNTAX Sle2LldpRemoteVlanEntry
			MAX-ACCESS not-accessible
			STATUS current
			DESCRIPTION
				"Description."
			INDEX { sle2LldpRemoteVlanIfIndex, sle2LldpRemoteVlanAgentMode, sle2LldpRemoteVlanId }
			::= { sle2LldpRemoteVlanTable 1 }

		
		Sle2LldpRemoteVlanEntry ::=
			SEQUENCE { 
				sle2LldpRemoteVlanIfIndex
					InterfaceIndex,
				sle2LldpRemoteVlanAgentMode
					INTEGER,
				sle2LldpRemoteVlanId
					Integer32,
				sle2LldpRemoteVlanName
					OCTET STRING
			 }

		sle2LldpRemoteVlanIfIndex OBJECT-TYPE
			SYNTAX InterfaceIndex
			MAX-ACCESS read-only
			STATUS current
			DESCRIPTION
				"LLDP Interface"
			::= { sle2LldpRemoteVlanEntry 1 }

		
		sle2LldpRemoteVlanAgentMode OBJECT-TYPE
			SYNTAX INTEGER
				{
				nearest(1),
				nontpmr(2),
				customer(3)
				}
			MAX-ACCESS read-only
			STATUS current
			DESCRIPTION
				"LLDP Agent Mode"
			::= { sle2LldpRemoteVlanEntry 2 }

		
		sle2LldpRemoteVlanId OBJECT-TYPE
			SYNTAX Integer32 (1..4094)
			MAX-ACCESS read-only
			STATUS current
			DESCRIPTION
				" "
			::= { sle2LldpRemoteVlanEntry 3 }

		
		sle2LldpRemoteVlanName OBJECT-TYPE
			SYNTAX OCTET STRING
			MAX-ACCESS read-only
			STATUS current
			DESCRIPTION
				" "
			::= { sle2LldpRemoteVlanEntry 4 }

		
		sle2LldpBase OBJECT IDENTIFIER ::= { sleBridge 45 }

		
		sle2LldpBaseInfo OBJECT IDENTIFIER ::= { sle2LldpBase 1 }

		
		sle2LldpBaseSystemDescription OBJECT-TYPE
			SYNTAX OCTET STRING
			MAX-ACCESS read-only
			STATUS current
			DESCRIPTION
				"LLDP Global System Description"
			::= { sle2LldpBaseInfo 1 }

		
		sle2LldpBaseSystemName OBJECT-TYPE
			SYNTAX OCTET STRING
			MAX-ACCESS read-only
			STATUS current
			DESCRIPTION
				"LLDP Global System Name"
			::= { sle2LldpBaseInfo 2 }

		
		sle2LldpBaseControl OBJECT IDENTIFIER ::= { sle2LldpBase 2 }

		
		sle2LldpBaseControlRequest OBJECT-TYPE
			SYNTAX INTEGER { setLldpBase(1) }
			MAX-ACCESS read-write
			STATUS current
			DESCRIPTION
				"The request of a user command"
			::= { sle2LldpBaseControl 1 }

		
		sle2LldpBaseControlStatus OBJECT-TYPE
			SYNTAX SleControlStatusType
			MAX-ACCESS read-only
			STATUS current
			DESCRIPTION
				"The status of a user command"
			::= { sle2LldpBaseControl 2 }

		
		sle2LldpBaseControlTimer OBJECT-TYPE
			SYNTAX Gauge32
			MAX-ACCESS read-write
			STATUS current
			DESCRIPTION
				"The maximum time for the manager for a long running user command"
			::= { sle2LldpBaseControl 3 }

		
		sle2LldpBaseControlTimeStamp OBJECT-TYPE
			SYNTAX TimeTicks
			MAX-ACCESS read-only
			STATUS current
			DESCRIPTION
				"The time stamp of the last command(end of command)"
			::= { sle2LldpBaseControl 4 }

		
		sle2LldpBaseControlReqResult OBJECT-TYPE
			SYNTAX SleControlRequestResultType
			MAX-ACCESS read-only
			STATUS current
			DESCRIPTION
				"Result of the last command."
			::= { sle2LldpBaseControl 5 }

		
		sle2LldpBaseControlSystemDescription OBJECT-TYPE
			SYNTAX OCTET STRING
			MAX-ACCESS read-write
			STATUS current
			DESCRIPTION
				"LLDP Global System Description"
			::= { sle2LldpBaseControl 6 }

		
		sle2LldpBaseControlSystemName OBJECT-TYPE
			SYNTAX OCTET STRING
			MAX-ACCESS read-write
			STATUS current
			DESCRIPTION
				"LLDP Global System Name"
			::= { sle2LldpBaseControl 7 }

		
		sleMllcf OBJECT IDENTIFIER ::= { sleBridge 46 }

		
		sleMllcfInfo OBJECT IDENTIFIER ::= { sleMllcf 1 }

		
		sleMllcfPortsA OBJECT-TYPE
			SYNTAX OCTET STRING
			MAX-ACCESS read-only
			STATUS current
			DESCRIPTION
				"Member ports in PORTS_A"
			::= { sleMllcfInfo 1 }

		
		sleMllcfPortsB OBJECT-TYPE
			SYNTAX OCTET STRING
			MAX-ACCESS read-only
			STATUS current
			DESCRIPTION
				"Member ports in PORTS_B"
			::= { sleMllcfInfo 2 }

		
		sleMllcfPortsALinkDownStatus OBJECT-TYPE
			SYNTAX OCTET STRING
			MAX-ACCESS read-only
			STATUS current
			DESCRIPTION
				"Port(s) in PORTS_A down because of Link-down"
			::= { sleMllcfInfo 3 }

		
		sleMllcfPortsAAdminDownStatus OBJECT-TYPE
			SYNTAX OCTET STRING
			MAX-ACCESS read-only
			STATUS current
			DESCRIPTION
				"Port(s) in PORTS_A down because of Admin-down"
			::= { sleMllcfInfo 4 }

		
		sleMllcfPortsBStatus OBJECT-TYPE
			SYNTAX INTEGER
				{
				none(0),
				up(1),
				forceToDown(2)
				}
			MAX-ACCESS read-only
			STATUS current
			DESCRIPTION
				"Status of ports in PORTS_B
				Value
				0. none
				1. up
				2. force-to-down"
			::= { sleMllcfInfo 5 }

		
		sleMllcfHoldTime OBJECT-TYPE
			SYNTAX INTEGER (0..10)
			MAX-ACCESS read-only
			STATUS current
			DESCRIPTION
				"Holddown interval"
			::= { sleMllcfInfo 6 }

		
		sleMllcfControl OBJECT IDENTIFIER ::= { sleMllcf 2 }

		
		sleMllcfControlRequest OBJECT-TYPE
			SYNTAX INTEGER
				{
				setMllcfControlPorts(1),
				setMllcfControlHoldTime(2),
				delMllcfControlPorts(3)
				}
			MAX-ACCESS read-write
			STATUS current
			DESCRIPTION
				"The request of a user command"
			::= { sleMllcfControl 1 }

		
		sleMllcfControlStatus OBJECT-TYPE
			SYNTAX SleControlStatusType
			MAX-ACCESS read-only
			STATUS current
			DESCRIPTION
				"The status of a user command"
			::= { sleMllcfControl 2 }

		
		sleMllcfControlTimer OBJECT-TYPE
			SYNTAX Gauge32
			MAX-ACCESS read-write
			STATUS current
			DESCRIPTION
				"The maximum time for the manager for a long running user command"
			::= { sleMllcfControl 3 }

		
		sleMllcfControlTimeStamp OBJECT-TYPE
			SYNTAX TimeTicks
			MAX-ACCESS read-only
			STATUS current
			DESCRIPTION
				"The time stamp of the last command(end of command)"
			::= { sleMllcfControl 4 }

		
		sleMllcfControlReqResult OBJECT-TYPE
			SYNTAX SleControlRequestResultType
			MAX-ACCESS read-only
			STATUS current
			DESCRIPTION
				"Result of the last command."
			::= { sleMllcfControl 5 }

		
		sleMllcfControlPortsA OBJECT-TYPE
			SYNTAX OCTET STRING
			MAX-ACCESS read-write
			STATUS current
			DESCRIPTION
				"Set member for PORTS_A"
			::= { sleMllcfControl 6 }

		
		sleMllcfControlPortsB OBJECT-TYPE
			SYNTAX OCTET STRING
			MAX-ACCESS read-write
			STATUS current
			DESCRIPTION
				"Set member for PORTS_B"
			::= { sleMllcfControl 7 }

		
		sleMllcfControlHoldTime OBJECT-TYPE
			SYNTAX Integer32 (0..10)
			MAX-ACCESS read-write
			STATUS current
			DESCRIPTION
				"Set holdtime"
			::= { sleMllcfControl 8 }

		
		sleBridgeGroup OBJECT-GROUP
			OBJECTS { sleBridgeMacAddress, sleBridgePortNum, sleBridgeLagMaxId, sleBridgeLacpActivity, sleBridgeLacpPriority, 
				sleBridgeVlanSupportMode, sleBridgeVlanMaxNum, sleBridgeDoubleTagProtoId, sleBridgeMirrorMode, sleBridgeMirrorMonitorPortId, 
				sleBridgeMirroredIngressPorts, sleBridgeMirroredEgressPorts, sleBridgeMaxLearnPerUnit, sleBridgeFdbAgeingTime, sleBridgeFdbMaxEntries, 
				sleBridgeFdbCurrentEntries, sleBridgeStackMode, sleBridgeStackDeviceName, sleBridgeStackNodeId, sleBridgeLldpMessageTxInterval, 
				sleBridgeLldpTxHoldMultiplier, sleBridgeLldpReinitDelay, sleBridgeLldpTxDelay, sleBridgeLldpNotificationInterval, sleBridgeLldpStatsRemTablesLastChangeTime, 
				sleBridgeLldpStatsRemTablesInserts, sleBridgeLldpStatsRemTablesDeletes, sleBridgeLldpStatsRemTablesDrops, sleBridgeLldpStatsRemTablesAgeouts, sleBridgeLldpLocalChassisIdSubtype, 
				sleBridgeLldpLocalChassisId, sleBridgeLldpLocalSysName, sleBridgeLldpLocalSysDes, sleBridgeLldpLocalSysCapSupported, sleBridgeLldpLocalSysCapEnabled, 
				sleBridgeStpActivity, sleBridgeStpSelfLoop, sleBridgePvlanOnePromPortEnable, sleBridgeTcpSyncookie, sleBridgeTcpIgnoreRstUnknown, 
				sleBridgeControlRequest, sleBridgeControlStatus, sleBridgeControlTimer, sleBridgeControlTimeStamp, sleBridgeControlReqResult, 
				sleBridgeControlLacpActivity, sleBridgeControlLacpPriority, sleBridgeControlDoubleTagProtoId, sleBridgeControlMirrorMode, sleBridgeControlMirrorMonitorPortId, 
				sleBridgeControlMaxLearnPerUnit, sleBridgeControlFdbAgeingTime, sleBridgeControlStackMode, sleBridgeControlStackDeviceName, sleBridgeControlLldpMessageTxInterval, 
				sleBridgeControlLldpTxHoldMultiplier, sleBridgeControlLldpReinitDelay, sleBridgeControlLldpTxDelay, sleBridgeControlLldpNotificationInterval, sleBridgeControlStpActivity, 
				sleBridgeControlStpSelfLoop, sleBridgeControlTcpSyncookie, sleBridgeControlTcpIgnoreRstUnknown, sleBridgePortIndex, sleBridgePortIfIndex, 
				sleBridgePortPVid, sleBridgePortMaxHosts, sleBridgePortCurrentHosts, sleBridgePortMaxLearnPerUnit, sleBridgePortMACFilterPermission, 
				sleBridgePortIngMirrorStatus, sleBridgePortEgMirrorStatus, sleBridgePortBcastThreshold, sleBridgePortMcastThreshold, sleBridgePortDlfThreshold, 
				sleBridgePortQinQStatus, sleBridgePortAdminLinktype, sleBridgePortAdminEdgemode, sleBridgePortOperLinktype, sleBridgePortOperEdgemode, 
				sleBridgePortStpBpduFilter, sleBridgePortPvlanIsolatedStatus, sleBridgePortPvlanPromPorts, sleBridgePortControlRequest, sleBridgePortControlStatus, 
				sleBridgePortControlTimer, sleBridgePortControlTimeStamp, sleBridgePortControlReqResult, sleBridgePortControlIndex, sleBridgePortControlPVid, 
				sleBridgePortControlMaxHosts, sleBridgePortControlMaxLearnPerUnit, sleBridgePortControlMACFilterPermission, sleBridgePortControlIngMirrorStatus, sleBridgePortControlEgMirrorStatus, 
				sleBridgePortControlBcastThreshold, sleBridgePortControlMcastThreshold, sleBridgePortControlDlfThreshold, sleBridgePortControlQinQStatus, sleBridgePortControlAdminLinktype, 
				sleBridgePortControlAdminEdgemode, sleBridgePortControlStpBpduFilter, sleBridgePortControlPvlanIsolatedStatus, sleBridgePortControlPvlanPromPort, sleBridgePortControlStpBpduGuardErrRcv, 
				sleVlanIndex, sleVlanIfIndex, sleVlanName, sleVlanStatus, sleVlanEgressPorts, 
				sleVlanUnTaggedPorts, sleVlanCreationTime, sleVlanAgeingTime, sleVlanControlRequest, sleVlanControlStatus, 
				sleVlanControlTimer, sleVlanControlTimeStamp, sleVlanControlReqResult, sleVlanControlIndex, sleVlanControlName, 
				sleVlanControlEgressPorts, sleVlanControlUnTaggedPorts, sleVlanControlAgeingTime, sleVlanMapFid, sleVlanMapStpId, 
				sleVlanMapErpDomainId, sleVlanMapControlRequest, sleVlanMapControlStatus, sleVlanMapControlTimer, sleVlanMapControlTimeStamp, 
				sleVlanMapControlReqResult, sleVlanMapControlIndex, sleVlanMapControlFid, sleVlanMapControlStpId, sleVlanMapControlErpDomainId, 
				sleStpOperationMode, sleStpFormatSelector, sleStpConfigureName, sleStpRevisionLevel, sleStpFwdDelay, 
				sleStpHelloTime, sleStpMaxAge, sleStpMaxHops, sleStpExtRootBridgeId, sleStpExtPathcost, 
				sleStpBpduGuardMode, sleStpBpduGuardAutoRcvMode, sleStpBpduGuardAutoRcvTime, sleStpControlRequest, sleStpControlStatus, 
				sleStpControlTimer, sleStpControlTimeStamp, sleStpControlReqResult, sleStpControlOperationMode, sleStpControlConfigureName, 
				sleStpControlRevisionLevel, sleStpControlFwdDelay, sleStpControlHelloTime, sleStpControlMaxAge, sleStpControlMaxHops, 
				sleStpControlBpduGuardMode, sleStpControlBpduGuardAutoRcvMode, sleStpControlBpduGuardAutoRcvTime, sleStpInstanceIndex, sleStpInstanceEnable, 
				sleStpInstancePriority, sleStpInstanceRootBridgeId, sleStpInstanceRootPathcost, sleStpInstanceDesignatedBridgeId, sleStpInstanceDesignatedPortId, 
				sleStpInstanceRootPortId, sleStpInstanceFwdDelay, sleStpInstanceHelloTime, sleStpInstanceMaxAge, sleStpInstanceRemainHops, 
				sleStpInstanceBrFwdDelay, sleStpInstanceBrHelloTime, sleStpInstanceBrMaxAge, sleStpInstanceControlRequest, sleStpInstanceControlStatus, 
				sleStpInstanceControlTimer, sleStpInstanceControlTimeStamp, sleStpInstanceControlReqResult, sleStpInstanceControlIndex, sleStpInstanceControlEnable, 
				sleStpInstanceControlPriority, sleStpInstanceControlBrFwdDelay, sleStpInstanceControlBrHelloTime, sleStpInstanceControlBrMaxAge, sleStpInstancePortIndex, 
				sleStpInstancePortPathcost, sleStpInstancePortPriority, sleStpInstancePortRole, sleStpInstancePortState, sleStpInstancePortRootBridgeId, 
				sleStpInstancePortRootPathcost, sleStpInstancePortDesignateBridgeId, sleStpInstancePortDesignatePortId, sleStpInstancePortRootGuardMode, sleStpInstancePortControlRequest, 
				sleStpInstancePortControlStatus, sleStpInstancePortControlTimer, sleStpInstancePortControlTimeStamp, sleStpInstancePortControlReqResult, sleStpInstancePortControlIndex, 
				sleStpInstancePortControlInstanceId, sleStpInstancePortControlPathcost, sleStpInstancePortControlPriority, sleStpInstancePortControlRootGuardMode, sleSubnetVlanIp, 
				sleSubnetVlanMask, sleSubnetVlanVid, sleSubnetVlanControlRequest, sleSubnetVlanControlStatus, sleSubnetVlanControlTimer, 
				sleSubnetVlanControlTimeStamp, sleSubnetVlanControlReqResult, sleSubnetVlanControlIp, sleSubnetVlanControlMask, sleSubnetVlanControlVid, 
				sleProtocolVlanEtype, sleProtocolVlanVid, sleProtocolVlanControlRequest, sleProtocolVlanControlStatus, sleProtocolVlanControlTimer, 
				sleProtocolVlanControlTimeStamp, sleProtocolVlanControlReqResult, sleProtocolVlanControlPortIndex, sleProtocolVlanControlEtype, sleProtocolVlanControlVid, 
				sleLagIndex, sleLagPortId, sleLagDistMode, sleLagPortMap, sleLagMode, 
				sleLagControlRequest, sleLagControlStatus, sleLagControlTimer, sleLagControlTimeStamp, sleLagControlReqResult, 
				sleLagControlIndex, sleLagControlDistMode, sleLagControlPortMap, sleLagControlMode, sleLagLacpIndex, 
				sleLagLacpActorAggregatorKey, sleLagLacpActorSystemMAC, sleLagLacpPartnerSystemMAC, sleLagLacpPartnerSystemPriority, sleLagLacpPartnerAggregatorKey, 
				sleLagLacpPortIndex, sleLagLacpPortActivity, sleLagLacpPortActorPriority, sleLagLacpPortActorAggregatorId, sleLagLacpPortActorAdminKey, 
				sleLagLacpPortActorAdminState, sleLagLacpPortActorOperKey, sleLagLacpPortActorOperState, sleLagLacpPortPartnerAdminSystemMAC, sleLagLacpPortPartnerAdminSystemPriority, 
				sleLagLacpPortPartnerAdminKey, sleLagLacpPortPartnerAdminNum, sleLagLacpPortPartnerAdminPriority, sleLagLacpPortPartnerAdminState, sleLagLacpPortPartnerOperSystemMAC, 
				sleLagLacpPortPartnerOperSystemPriority, sleLagLacpPortPartnerOperKey, sleLagLacpPortPartnerOperNum, sleLagLacpPortPartnerOperPriority, sleLagLacpPortPartnerOperState, 
				sleLagLacpPortControlRequest, sleLagLacpPortControlStatus, sleLagLacpPortControlTimer, sleLagLacpPortControlTimeStamp, sleLagLacpPortControlReqResult, 
				sleLagLacpPortControlIndex, sleLagLacpPortControlActivity, sleLagLacpPortControlMode, sleLagLacpPortControlAdminKey, sleLagLacpPortControlAggregation, 
				sleLagLacpPortControlPriority, sleLagLacpPortControlTimeout, sleFdbEntryFid, sleFdbEntryPort, sleFdbEntryMacAddress, 
				sleFdbEntryVid, sleFdbEntryMode, sleFdbEntryPermission, sleFdbEntryElapsedTime, sleFdbEntryControlRequest, 
				sleFdbEntryControlStatus, sleFdbEntryControlTimer, sleFdbEntryControlTImeStamp, sleFdbEntryControlReqResult, sleFdbEntryControlFid, 
				sleFdbEntryControlPort, sleFdbEntryControlMacAddress, sleIgmpConfVlanIndex, sleIgmpConfEnable, sleIgmpConfMulticastFilter, 
				sleIgmpConfOutmostVlan, sleIgmpConfSnoopEnable, sleIgmpConfSnoopJoinDelay, sleIgmpConfSnoopQueryDelay, sleIgmpConfSnoopMrouter, 
				sleIgmpConfSnoopFastLeave, sleIgmpConfSnoopQuerier, sleIgmpConfControlRequest, sleIgmpConfControlStatus, sleIgmpConfControlTimer, 
				sleIgmpConfControlReqResult, sleIgmpConfControlTimeStamp, sleIgmpConfControlVlanIndex, sleIgmpConfControlEnable, sleIgmpConfControlMulticastFilter, 
				sleIgmpConfControlOutmostVlan, sleIgmpConfControlSnoopEnable, sleIgmpConfControlSnoopJoinDelay, sleIgmpConfControlSnoopQueryDelay, sleIgmpConfControlSnoopMrouter, 
				sleIgmpConfControlSnoopFastLeave, sleIgmpConfControlSnoopQuerier, sleIgmpMcastVlanIndex, sleIgmpMcastIPAddress, sleIgmpMcastPortIndex, 
				sleIgmpMcastType, sleIgmpMcastExpireTime, sleIgmpMcastControlReqest, sleIgmpMcastControlStatus, sleIgmpMcastControlTimer, 
				sleIgmpMcastControlTimeStamp, sleIgmpMcastControlReqResult, sleIgmpMcastControlVlanIndex, sleIgmpMcastControlIPAddress, sleIgmpMcastControlPortIndex, 
				sleStackDeviceMacAddress, sleStackDeviceNodeId, sleStackDeviceDescriptor, sleStackDeviceMode, sleStackDeviceStatus, 
				sleStackDeviceType, sleStackDeviceHostName, sleStackDevicePortNum, sleStackDeviceControlRequest, sleStackDeviceControlStatus, 
				sleStackDeviceControlTimer, sleStackDeviceControlTImeStamp, sleStackDeviceControlReqResult, sleStackDeviceControlMacAddress, sleStackDeviceControlDescriptor, 
				sleErpDomainIndex, sleErpDomainName, sleErpDomainPrimaryPort, sleErpDomainSecondaryPort, sleErpDomainBridgeRole, 
				sleErpDomainProtectionActivation, sleErpDomainOperatorRequest, sleErpDomainWaitToRestoreTime, sleErpDomainTestPacketInterval, sleErpDomainLearningDisabledTime, 
				sleErpDomainNodeStatus, sleErpDomainRingStatus, sleErpDomainLotp, sleErpDomainULotp, sleErpDomainMultipleRM, 
				sleErpDomainRMNodeReacheablility, sleErpDomainControlRequest, sleErpDomainControlStatus, sleErpDomainControlTimer, sleErpDomainControlTImeStamp, 
				sleErpDomainControlReqResult, sleErpDomainControlIndex, sleErpDomainControlName, sleErpDomainControlPrimaryPort, sleErpDomainControlSecondaryPort, 
				sleErpDomainControlBridgeRole, sleErpDomainControlProtectionActivation, sleErpDomainControlOperatorRequest, sleErpDomainControlWaitToRestoreTime, sleErpDomainControlTestPacketInterval, 
				sleErpDomainControlLearningDisabledTime, sleLldpPortIndex, sleLldpPortActivity, sleLldpPortAdminStatus, sleLldpPortNotificationEnable, 
				sleLldpPortTLVsTxEnable, sleLldpPortMgmtTxEnable, sleLldpPortMgmtAddress, sleLldpPortControlRequest, sleLldpPortControlStatus, 
				sleLldpPortControlTimer, sleLldpPortControlTimeStamp, sleLldpPortControlReqResult, sleLldpPortControlIndex, sleLldpPortControlActivity, 
				sleLldpPortControlAdminstatus, sleLldpPortControlNotificationEnable, sleLldpPortControlTLVsTxEnable, sleLldpPortControlMgmtTxEnable, sleLldpPortControlMgmtAddress, 
				sleLldpRemIndex, sleLldpRemTimeMark, sleLldpRemChassisIdSubtype, sleLldpRemChassisId, sleLldpRemPortIdSubtype, 
				sleLldpRemPortId, sleLldpRemPortDesc, sleLldpRemSysName, sleLldpRemSysDesc, sleLldpRemSysCapSupported, 
				sleLldpRemSysCapEnabled, sleLldpStatsTxPortFramesTotal, sleLldpStatsRxPortFramesDiscardedTotal, sleLldpStatsRxPortFramesErrors, sleLldpStatsRxPortFramesTotal, 
				sleLldpStatsRxPortTLVsDiscardedTotal, sleLldpStatsRxPortTLVsUnrecognizedTotal, sleLldpStatsRxPortAgeoutsTotal, sleLldpStatsControlRequest, sleLldpStatsControlStatus, 
				sleLldpStatsControlTimer, sleLldpStatsControlTimeStamp, sleLldpStatsControlReqResult, sleLldpStatsControlPortIndex, sleBridgePSIndex, 
				sleBridgePSStatus, sleBridgePSMaxCount, sleBridgePSCurrCount, sleBridgePSAgingType, sleBridgePSAgingTimer, 
				sleBridgePSAgingStatic, sleBridgePSViolation, sleBridgePSControlRequest, sleBridgePSControlStatus, sleBridgePSControlTimer, 
				sleBridgePSControlTimeStamp, sleBridgePSControlReqResult, sleBridgePSControlIndex, sleBridgePSControlPSStatus, sleBridgePSControlMaxCount, 
				sleBridgePSControlAgingType, sleBridgePSControlAgingTimer, sleBridgePSControlAgingStatic, sleBridgePScontrolViolation, sleBridgePSFdbPort, 
				sleBridgePSFdbVid, sleBridgePSFdbMacAddress, sleBridgePSFdbMode, sleBridgePSFdbElapsedTime, sleBridgePSFdbControlRequest, 
				sleBridgePSFdbControlStatus, sleBridgePSFdbControlTimer, sleBridgePSFdbControlTimeStamp, sleBridgePSFdbControlReqResult, sleBridgePSFdbControlPort, 
				sleBridgePSFdbControlVid, sleErpDomainControlRingPriority, sleErpDomainHoldOffTime, sleErpDomainRingPriority, sleErpDomainControlHoldOffTime, 
				sleErpDomainControlLotp, sleErpDomainControlULotp, sleErpDomainControlMultipleRM, sleErpDomainControlRMNodeReacheablility, sleBridgeFGBaseControlRequest, 
				sleBridgeFGBaseSfgdEnabled, sleBridgeFGBaseMfgdEnabled, sleBridgeFGBaseCfgdEnabled, sleBridgePSFdbControlMacAddress, sleBridgePortDhcpFilterServer, 
				sleBridgePortControlDhcpFilterServer, sleBridgeFGBaseControlStatus, sleBridgeFGBaseControlTimer, sleBridgeFGBaseControlTimeStamp, sleBridgeFGBaseControlReqResult, 
				sleBridgeFGBaseControlCfgdEnable, sleBridgeFGBaseControlSfgdEnable, sleBridgeFGPortControlRequest, sleBridgeFGPortControlStatus, sleBridgeFGPortControlTimer, 
				sleBridgeFGPortControlTimeStamp, sleBridgeFGPortControlReqResult, sleBridgeFGPortControlIndex, sleBridgeFGPortType, sleBridgeFGPortFrame, 
				sleBridgeFGPortBlocked, sleBridgeFGPortTimer, sleBridgeFGPortControlFrame, sleBridgeFGPortFrameType, sleBridgeFGPortControlBlock, 
				sleBridgeAutoInterfaceActivation, sleBridgeControlAutoInterfaceActivation, sleBridgeLoopDetectStatus, sleBridgeLoopDetectPacketType, sleBridgeControlLoopDetectStatus, 
				sleBridgeControlLoopDetectPacketType, sleBridgePortLoopDetectStatus, sleBridgePortLoopDetectBlock, sleBridgePortLoopDetectPeriod, sleBridgePortLoopDetectTimer, 
				sleBridgePortLoopDetectBlockStatus, sleBridgePortControlLoopDetectStatus, sleBridgePortControlLoopDetectBlock, sleBridgePortControlLoopDetectPeriod, sleBridgePortControlLoopDetectTimer, 
				sleBridgePvlanPromSelectMode, sleBridgePvlanPromiscuousPorts, sleBridgeControlPvlanPromSelectMode, sleBridgeControlPvlanPromiscuousPorts, sleBridgeVTServiceId, 
				sleBridgeVTSubscriberId, sleBridgeVTRuleMac, sleBridgeVTRuleVid, sleBridgeVTRuleRDirVid, sleBridgeVTRuleRDirPort, 
				sleBridgeVTRuleStatus, sleBridgeVTControlRequest, sleBridgeVTControlStatus, sleBridgeVTControlTimer, sleBridgeVTControlTimeStamp, 
				sleBridgeVTControlServerId, sleBridgeVTControlClientId, sleBridgeGvrpStatus, sleBridgeGmrpStatus, sleBridgeGarpTimerJoin, 
				sleBridgeGarpTimerLeave, sleBridgeGarpTimerLeaveAll, sleBridgeGarpBaseControlRequest, sleBridgeGarpBaseControlStatus, sleBridgeGarpBaseControlTimer, 
				sleBridgeGarpBaseControlTimeStamp, sleBridgeGarpBaseControlReqResult, sleBridgeGarpBaseControlGvrpStatus, sleBridgeGarpBaseControlGmrpStatus, sleBridgeGarpBaseControlTimerJoin, 
				sleBridgeGarpBaseControlTimerLeave, sleBridgeGarpBaseControlTimerLeaveAll, sleBridgeGarpAppPortIndex, sleBridgeGarpAppPortType, sleBridgeGarpAppPortStatus, 
				sleBridgeGarpAppPortFailedRegistrations, sleBridgeGarpAppPortLastPduOrigin, sleBridgeGarpAppPortRegistration, sleBridgeGarpAppPortApplicant, sleBridgeGarpAppPortFwdAll, 
				sleBridgeGarpAppPortTimerJoin, sleBridgeGarpAppPortTimerLeave, sleBridgeGarpAppPortTimerLeaveAll, sleBridgeGarpAppPortControlRequest, sleBridgeGarpAppPortControlStatus, 
				sleBridgeGarpAppPortControlTimer, sleBridgeGarpAppPortControlTimeStamp, sleBridgeGarpAppPortControlReqResult, sleBridgeGarpAppPortControlIndex, sleBridgeGarpAppPortControlType, 
				sleBridgeGarpAppPortControlPortStatus, sleBridgeGarpAppPortControlRegistration, sleBridgeGarpAppPortControlApplicant, sleBridgeGarpAppPortControlFwdAll, sleBridgeGarpAppPortControlTimerJoin, 
				sleBridgeGarpAppPortControlTimerLeave, sleBridgeGarpAppPortControlTimerLeaveAll, sleBridgeGarpStatsJoinEmptyReceived, sleBridgeGarpStatsJoinInReceived, sleBridgeGarpStatsLeaveInReceived, 
				sleBridgeGarpStatsLeaveEmptyReceived, sleBridgeGarpStatsLeaveAllReceived, sleBridgeGarpStatsJoinInTransmitted, sleBridgeGarpStatsEmptyTransmitted, sleBridgeGarpStatsLeaveInTransmitted, 
				sleBridgeGarpStatsLeaveEmptyTransmitted, sleBridgeGarpStatsControlRequest, sleBridgeGarpStatstControlStatus, sleBridgeGarpStatsControlTimer, sleBridgeGarpStatsControlTimeStamp, 
				sleBridgeGarpStatsControlReqResult, sleBridgeGarpStatsControlIndex, sleBridgeGarpStatsControlType, sleBridgeGmrpStaticVid, sleBridgeGmrpStaticPort, 
				sleBridgeGmrpStaticGmac, sleBridgeGmrpStaticControlRequest, sleBridgeGmrpStaticControlStatus, sleBridgeGmrpStaticControlTimer, sleBridgeGmrpStaticControlTimeStamp, 
				sleBridgeGmrpStaticControlReqResult, sleBridgeGmrpStaticControlVid, sleBridgeGmrpStaticControlPort, sleBridgeGmrpStaticControlGmac, sleBridgePortNetBIOSFilter, 
				sleBridgePortControlNetBIOSFilter, sleBridgePortPopInnertag, sleBridgePortInnertag, sleBridgePortPriority, sleBridgePortControlPushInnertag, 
				sleBridgePortControlPopInnertag, sleBridgePortControlInnertag, sleBridgePortControlPriority, sleBridgePortPushInnertag, sleVlanInboundTagPortIndex, 
				sleVlanInboundTagVlanIndex, sleVlanInboundTagOuterVid, sleVlanInboundTagControlRequest, sleVlanInboundTagControlStatus, sleVlanInboundTagControlTimer, 
				sleVlanInboundTagControlTimeStamp, sleVlanInboundTagControlReqResult, sleVlanInboundTagControlPortIndex, sleVlanInboundTagControlVlanIndex, sleVlanInboundTagControlOuterVid, 
				sleVlanOutboundTagPortIndex, sleVlanOutboundTagControlRequest, sleVlanOutboundTagControlStatus, sleVlanOutboundTagControlTimer, sleVlanOutboundTagControlTimeStamp, 
				sleVlanOutboundTagControlReqResult, sleVlanOutboundTagControlPortIndex, sleVlanOutboundTagControlOuterVid, sleVlanOutboundTagVlanIndex, sleBridgePortInner2outerVid, 
				sleBridgePortInner2outerPri, sleBridgeFGPortControlFrameType, sleBridgeFGPortControlType, sleBridgeFGPortControlSetTimer, sleBridgeGarpStatsEmptyReceived, 
				sleBridgeGarpStatsJoinEmptyTransmitted, sleIgmpMcastCounterInfoGroupCount, sleIgmpMcastCounterInfoSnoopingCount, sleMcastMrouteJoinedCount, sleBridgePortLinkUpCnt, 
				sleBridgePortLinkDownCnt, sleBridgePortLinkUpTime, sleBridgePortElapsedTimeAfterClearStats, sleVlanTagTxCounter, sleBridgePortMACLearningStatus, 
				sleBridgePortPortBridgeStatus, sleBridgePortControlMACLearningStatus, sleBridgePortControlPortBridgeStatus, sleBridgeInBoundVTPortIndex, sleBridgeInBoundVTNewVid, 
				sleBridgeInBoundVTControlRequest, sleBridgeInBoundVTControlStatus, sleBridgeInBoundVTControlTimer, sleBridgeInBoundVTControlTimeStamp, sleBridgeInBoundVTControlReqResult, 
				sleBridgeInBoundVTControlPortIndex, sleBridgeInBoundVTControlNewVid, sleBridgeGarpStatsLeaveAllTransmitted, sleBridgePortControlInner2outerPri, sleBridgeInBoundVTVlanIndex, 
				sleBridgeInBoundVTOperStatus, sleBridgeInBoundVTControlVlanIndex, sleVlanInboundTagOperStatus, sleVlanOutboundTagOperStatus, sleVlanRangeInboundTagOperStatus, 
				sleVlanControlIndexTo, sleBridgeUnknownMcastBlockAllPorts, sleBridgeControlUnknownMcastBlockAllPorts, sleBridgePortUnknownMcastBlock, sleBridgePortControlUnknownMcastBlock, 
				sleBridgeEcmpHashType, sleBridgeControlEcmpHashType, sleBridgeTcpSynguard, sleBridgeControlTcpSynguard, sleBridgePortDescription, 
				sleBridgePortHoldTime, sleBridgePortControlDescription, sleBridgePortControlHoldTime, sleLagLacpStatsPduReceived, sleLagLacpStatsPduReceivedErrrors, 
				sleLagLacpStatsPduSent, sleLagLacpStatsPduSentError, sleLagLacpStatsMarkerReceived, sleLagLacpStatsMarkerSent, sleLagLacpStatsMarkerSentError, 
				sleLagLacpControlRequest, sleLagLacpControlStatus, sleLagLacpControlTimer, sleLagLacpControlTimeStamp, sleLagLacpControlReqResult, 
				sleBridgeOuterTagProtoId, sleBridgeControlOuterTagProtoId, sleBridgeOutBoundVTPortIndex, sleBridgeOutBoundVTVlanIndex, sleBridgeOutBoundVTNewVid, 
				sleBridgeOutBoundVTOperStatus, sleBridgeOutBoundVTControlRequest, sleBridgeOutBoundVTControlStatus, sleBridgeOutBoundVTControlTimer, sleBridgeOutBoundVTControlTimeStamp, 
				sleBridgeOutBoundVTControlReqResult, sleBridgeOutBoundVTControlPortIndex, sleBridgeOutBoundVTControlVlanIndex, sleBridgeOutBoundVTControlNewVid, sleBridgeMacAntiSpoofing, 
				sleBridgeMacReplace, sleBridgeControlMacAntiSpoofing, sleBridgeControlMacReplace, sleBridgePortMacAntiSpoofing, sleBridgePortControlMacAntiSpoofing, 
				sleVlanProtoIdVid, sleVlanProtoIdOuterProtoId, sleVlanProtoIdControlRequest, sleVlanProtoIdControlStatus, sleVlanProtoIdControlTimer, 
				sleVlanProtoIdControlTimeStamp, sleVlanProtoIdControlReqResult, sleVlanProtoIdControlVid, sleVlanProtoIdControlOuterProtoId, sleBridgeStormControlBcast, 
				sleBridgeStormControlDLF, sleBridgeStormControlMulticast, sleBridgeControlStormControlBcast, sleBridgeControlStormControlDLF, sleBridgeControlStormControlMulticast, 
				sleVlanMappingIndex, sleVlanMappingPortId, sleVlanMappingOriVlanId, sleVlanMappingTransVlanId, sleVlanMappingMode, 
				sleVlanMappingMatchCos, sleVlanMappingMatchDscp, sleVlanMappingMatchEthType, sleVlanMappingMatchIPPrecedence, sleVlanMappingMatchTos, 
				sleVlanMappingRateLimit, sleVlanMappingCos, sleVlanMappingDscp, sleVlanMappingControlRequest, sleVlanMappingControlStatus, 
				sleVlanMappingControlTimer, sleVlanMappingControlTimeStamp, sleVlanMappingControlReqResult, sleVlanMappingControlPortId, sleVlanMappingControlOriVlanId, 
				sleVlanMappingControlTransVlanID, sleVlanMappingControlMode, sleVlanMappingControlMatchCos, sleVlanMappingControlMatchDscp, sleVlanMappingControlMatchEthType, 
				sleVlanMappingControlMatchIPPrecedence, sleVlanMappingControlMatchTos, sleVlanMappingControlRateLimit, sleVlanMappingControlCos, sleVlanMappingControlDscp, 
				sleVlanMappingControlIndex, sleBridgeMacLearningMode, sleBridgeControlMacLearningMode, sleLldpRemManAddrSubType, sleLldpRemManAddr, 
				sleLldpRemManAddrIfSubType, sleLldpRemManAddrIfId, sleLldpRemAddrOid, sleBridgeLagGlobalDistMode, sleBridgeControlLagGlobalDistMode, 
				sleVlanDescription, sleVlanControlDescription, sleVlanElineEnable, sleVlanControlElineEnable, sleBridgePortSwitchType, 
				sleBridgePortSwitchState, sleBridgePortSwitchMode, sleBridgePortSwitchSubMode, sleBridgePortSwitchDefaultVlan, sleBridgePortSwitchIngressFilter, 
				sleBridgePortSwitchAccFrameType, sleBridgePortSwitchNativeVid, sleBridgePortSwitchAllowedVlan, sleBridgePortSwitchAllowedVlanEtag, sleBridgePortControlSwitchStatus, 
				sleBridgePortControlSwitchMode, sleBridgePortControlSwitchSubMode, sleBridgePortControlSwitchDefaultVlan, sleBridgePortControlSwitchIngressFilter, sleBridgePortControlSwitchAccFrameType, 
				sleBridgePortControlSwitchNativeVid, sleBridgePortControlSwitchAllowedVlan, sleBridgePortControlSwitchAllowedVlanEtag, sleBridgePortControlInner2outerVid, sleBridgeInnerTagProtoId, 
				sleBridgeControlInnerTagProtoId, sleBridgeVTControlReqResult, sleVlanRangeInboundTagPortIndex, sleVlanRangeInboundTagMinVlanIndex, sleVlanRangeInboundTagMaxVlanIndex, 
				sleVlanRangeInboundTagOuterVid, sleVlanRangeInboundTagControlRequest, sleVlanRangeInboundTagControlStatus, sleVlanRangeInboundTagControlTimer, sleVlanRangeInboundTagControlTimeStamp, 
				sleVlanRangeInboundTagControlReqResult, sleVlanRangeInboundTagControlPortIndex, sleVlanRangeInboundTagControlMinVlanIndex, sleVlanRangeInboundTagControlMaxVlanIndex, sleBridgeMultiPortLlcfPortAStatus, 
				sleBridgeMultiPortLlcfPortBStatus, sleVlanRangeInboundTagControlOuterVid, sleBridgeMultiPortLlcfPortA, sleBridgeMultiPortLlcfPortB, sleBridgeMultiPortLlcfTimer, 
				sleBridgeControlMultiPortLlcfPortA, sleBridgeControlMultiPortLlcfPortB, sleBridgeControlMultiPortLlcfPortC, sleVlanOperStatus, sleVlanMtu, 
				sleVlanControlOperStatus, sleVlanControlMtu, sleBridgePortSwitchChannelType, sleBridgePortSwitchStaticChannelGroup, sleBridgePortSwitchChannelLoadbalance, 
				sleBridgePortControlSwitchStaticChannelGroup, sleBridgePortControlSwitchChannelLoadbalance, sleVlanInboundTagVlanPriority, sleVlanInboundTagOuterVlanPriority, sleVlanInboundTagControlVlanPriority, 
				sleVlanInboundTagControlOuterVlanPriority, slePowerInlinePortIndex, slePowerInlineAdminStatus, slePowerInlinePortStatus, slePowerInlineDetectionStatus, 
				slePowerInlinePortClass, slePowerInlinePortMaxPow, slePowerInlinePortLegacy, slePowerInlinePortPriority, slePowerInlinePortPower, 
				slePowerInlinePortCurrent, slePowerInlinePortVoltage, slePowerInlinePortTemperture, slePowerInlineControlRequest, slePowerInlineControlStatus, 
				slePowerInlineControlTimer, slePowerInlineControlTimeStamp, slePowerInlineControlReqResult, slePowerInlineControlPortIndex, slePowerInlineControlPortStatus, 
				slePowerInlineControlPortClass, slePowerInlineControlPortMaxPower, slePowerInlineControlPortLegacy, slePowerInlineControlPriority, slePowerInlineControlAdminStatus, 
				sleLagLeastActive, sleLagControlLeastActive, sleMfdbOldMacAddress, sleMfdbOldEntryPermission, sleMfdbOldVlanIndex, 
				sleMfdbOldPorts, sleMfdbOldControlRequest, sleMfdbOldControlStatus, sleMfdbOldControlTimer, sleMfdbOldControlTimeStamp, 
				sleMfdbOldControlReqResult, sleMfdbOldControlMacAddress, sleMfdbOldControlEntryPermission, sleMfdbOldControlVlanIndex, sleMfdbOldControlPorts, 
				sleMfdbMacAddress, sleMfdbEntryPermission, sleMfdbVlanIndex, sleMfdbPorts, sleMfdbControlRequest, 
				sleMfdbControlStatus, sleMfdbControlTimer, sleMfdbControlTimeStamp, sleMfdbControlReqResult, sleMfdbControlMacAddress, 
				sleMfdbControlEntryPermission, sleMfdbControlVlanIndex, sleMfdbControlPorts, sleBridgePortLoopDetectPeriodMs, sleBridgePortControlLoopDetectPeriodMs, 
				sleLldpPortTLVsTxNetworkPolciyProfile, sleLldpPortControlTLVsTxNetworkPolicyProfile, sleLldpMedNetworkPolicyProfileIndex, sleLldpMedNetworkPolicyProfileName, sleLldpMedNetworkPolicyProfileControlRequest, 
				sleLldpMedNetworkPolicyProfileControlStatus, sleLldpMedNetworkPolicyProfileControlTimer, sleLldpMedNetworkPolicyProfileControlTimeStamp, sleLldpMedNetworkPolicyProfileControlReqResult, sleLldpMedNetworkPolicyProfileControlIndex, 
				sleLldpMedNetworkPolicyProfileControlName, sleLldpMedNetworkPolicyProfilePolicyAppType, sleLldpMedNetworkPolicyProfilePolicyVlanId, sleLldpMedNetworkPolicyProfilePolicyPriority, sleLldpMedNetworkPolicyProfilePolicyDscp, 
				sleLldpMedNetworkPolicyProfilePolicyUnknown, sleLldpMedNetworkPolicyProfilePolicyControlRequest, sleLldpMedNetworkPolicyProfilePolicyControlStatus, sleLldpMedNetworkPolicyProfilePolicyControlTimer, sleLldpMedNetworkPolicyProfilePolicyControlTimeStamp, 
				sleLldpMedNetworkPolicyProfilePolicyControlReqResult, sleLldpMedNetworkPolicyProfilePolicyControlProfileIndex, sleLldpMedNetworkPolicyProfilePolicyControlAppType, sleLldpMedNetworkPolicyProfilePolicyControlVlanId, sleLldpMedNetworkPolicyProfilePolicyControlPriority, 
				sleLldpMedNetworkPolicyProfilePolicyControlDscp, sleLldpMedNetworkPolicyProfilePolicyControlUnknown, sleLldpMedRemoteNetworkPolicyAppType, sleLldpMedRemoteNetworkPolicyVlanId, sleLldpMedRemoteNetworkPolicyPriority, 
				sleLldpMedRemoteNetworkPolicyDscp, sleLldpMedRemoteNetworkPolicyUnknown, sleLldpMedRemoteNetworkPolicyTagged, sleLldpMedRemoteLocationSubType, sleLldpMedRemoteLocationInfo, 
				sleLldpMedRemoteHardwareRev, sleLldpMedRemoteFirmwareWRev, sleLldpMedRemoteSoftwareRev, sleLldpMedRemoteSerialNum, sleLldpMedRemoteMfgName, 
				sleLldpMedRemoteModelName, sleLldpMedRemoteAssetID, sleBridgePortLoopDetectVlan, sleBridgePortControlLoopDetectVlan, sleLldpPortMgmtIPType, 
				sleLldpPortMgmtIPAddress, sleLldpPortControlMgmtIPType, sleLldpPortControlMgmtIPAddress, sleBridgePortSwitchAggrType, sleBridgePortSwitchAggrId, 
				sleBridgePortSwitchAggrMode, sleBridgePortControlSwitchAggrType, sleBridgePortControlSwitchAggrId, sleBridgePortControlSwitchAggrMode, sleBridgeInterfaceIndex, 
				sleBridgeInterfaceName, sleBridgeInterfaceType, sleBridgeInterfaceMode, sleBridgeInterfacePvid, sleBridgeInterfaceIngressFilter, 
				sleBridgeInterfaceAllowedVlanFlags, sleBridgeInterfaceAllowedVlan, sleBridgeInterfaceControlRequest, sleBridgeInterfaceControlStatus, sleBridgeInterfaceControlTimer, 
				sleBridgeInterfaceControlTimeStamp, sleBridgeInterfaceControlReqResult, sleBridgeInterfaceControlIndex, sleBridgeInterfaceControlMode, sleBridgeInterfaceControlPvid, 
				sleBridgeInterfaceControlIngressFilter, sleBridgeInterfaceControlAllowedVlanFlags, sleBridgeInterfaceControlAllowedVlan, sleLagLacpPortActorAdminAggregatorId, sleLagLacpPortControlAdminAggregatorId, 
				sleBridgeReservedVlanId, sleBridgeReservedVlanIsUsed, sleBridgeReservedVlanControlRequest, sleBridgeReservedVlanControlStatus, sleBridgeReservedVlanControlTimer, 
				sleBridgeReservedVlanControlTimeStamp, sleBridgeReservedVlanControlReqResult, sleBridgeReservedVlanControlStartVlanId, sleBridgeReservedVlanControlEndVlanId, sleBridgeInternalVlanSlot, 
				sleBridgeInternalVlanPort, sleBridgeInternalVlanRealVlanId, sleBridgeInternalVlanInternalVlanId, sleBridgeChannelGroupLacpMaxBundle, sleBridgeChannelGroupSystemPriority, 
				sleBridgeControlChannelGroupLacpMaxBundle, sleBridgeControlChannelGroupSystemPriority, sleBridgeInterfaceChannelGroupAdminKey, sleBridgeInterfaceChannelGroupAggrType, sleBridgeInterfaceChannelGroupLacpAggrMode, 
				sleBridgeInterfaceChannelGroupPriority, sleBridgeInterfaceChannelGroupTimeOut, sleBridgeInterfaceChannelGroupActiveLink, sleBridgeInterfaceChannelGroupDistMode, sleBridgeInterfaceControlChannelGroupAdminKey, 
				sleBridgeInterfaceControlChannelGroupAggrType, sleBridgeInterfaceControlChannelGroupLacpAggrMode, sleBridgeInterfaceControlChannelGroupPriority, sleBridgeInterfaceControlChannelGroupTimeOut, sleBridgeInterfaceControlChannelGroupActiveLink, 
				sleBridgeInterfaceControlChannelGroupDistMode, sleBridgeControlMultiPortLlcfTimer, sleBridgeMultiPortLlcfUpPortC, sleBridgeMultiPortLlcfDownPortC, sleBridgeMultiPortLlcfUpPortCStatus, 
				sleBridgeMultiPortLlcfDownPortCStatus, sleBridgePortLoopDetectAdminCount, sleBridgePortLoopDetectOperCount, sleBridgePortLoopDetectDetectedCount, sleBridgePortControlLoopDetectAdminCount, 
				sleBridgeInterfaceNativeVlan, sleBridgePortBandwidth, sleBridgePortControlBandwidth, sleSubnetVlan6Ip, sleSubnetVlan6Mask, 
				sleSubnetVlan6Vid, sleSubnetVlan6ControlRequest, sleSubnetVlan6ControlStatus, sleSubnetVlan6ControlTimer, sleSubnetVlan6ControlTimeStamp, 
				sleSubnetVlan6ControlReqResult, sleSubnetVlan6ControlIp, sleSubnetVlan6ControlMask, sleSubnetVlan6ControlVid, sleBridgeInterfaceControlNativeVlan, 
				sleBridgePortMaxNewHosts, sleBridgePortStpStatus, sleBridgePortStpBpduGuard, sleBridgePortOuterTpid, sleBridgePortMirrorMonitor, 
				sleBridgePortControlMaxNewHosts, sleBridgePortControlStpStatus, sleBridgePortControlStpBpduGuard, sleBridgePortControlOuterTpid, sleBridgePortControlMirrorMonitor, 
				sleBridgeInterfaceChannelGroupAggrId, sleBridgeInterfaceChannelGroupMode, sleBridgeInterfaceChannelGroupState, sleBridgeInterfaceControlChannelGroupAggrId, sleBridgePortAlias, 
				sleBridgePortControlAlias, sle2MacAddressEntryBridgeId, sle2MacAddressEntryMacAddress, sle2MacAddressEntryIfIndex, sle2MacAddressEntryVid, 
				sle2MacAddressEntrySVid, sle2MacAddressEntryMode, sle2MacAddressEntryPermission, sle2MacAddressEntryElapsedTime, sle2MacAddressEntryControlRequest, 
				sle2MacAddressEntryControlStatus, sle2MacAddressEntryControlTimer, sle2MacAddressEntryControlTimeStamp, sle2MacAddressEntryControlReqResult, sle2MacAddressEntryControlBridgeId, 
				sle2MacAddressEntryControlMacAddress, sle2MacAddressEntryControlIfIndex, sle2MacAddressEntryControlVid, sle2MacAddressEntryControlSVid, sle2MacAddressEntryControlPermission, 
				sle2MacAddressEntryControlCVid, sle2MacAddressEntryControlInstance, sle2MacAddressEntryControlClearType, sleVlanType, sleVlanControlType, 
				sleVlanControlServiceType, sleServiceVlanIndex, sleServiceVlanName, sleServiceVlanDescription, sleServiceVlanOperStatus, 
				sleServiceVlanMtu, sleServiceVlanStatus, sleServiceVlanType, sleServiceVlanSeviceType, sleBridgeInterfaceSubMode, 
				sleBridgeInterfaceAcceptableFramType, sleBridgeInterfaceEgressTagged, sleBridgeInterfaceCVlanRegistraionName, sleBridgeInterfacePEVlanId, sleBridgeInterfacePEDefaultVlanId, 
				sleBridgeInterfacePEUntaggedVlanId, sleBridgeInterfaceControlSubMode, sleBridgeInterfaceControlAcceptableFramType, sleBridgeInterfaceControlEgressTagged, sleBridgeInterfaceControlCVlanRegistraionName, 
				sleBridgeInterfaceControlPEVlanId, sleBridgeInterfaceControlPEDefaultVlanId, sleBridgeInterfaceControlPEUntaggedVlanId, sleCVlanRegName, sleSVlan, 
				sleUntaggedMap, sleCVlanRegistrationMapControlRequest, sleCVlanRegistrationMapControlStatus, sleCVlanRegistrationMapControlTimer, sleCVlanRegistrationMapControlTimeStamp, 
				sleCVlanRegistrationMapControlReqResult, sleCVlanRegistrationMapControlCVlanID, sleCVlanRegistrationMapControlName, sleCVlanRegistrationMapControlSVlan, sleCVlanRegistrationMapControlFlagPort, 
				sleBridgeInterfaceControlChannelGroupMode, sleBridgeInterfaceDefaultVlan, sleLacpSystemPriority, sleLacpBaseControlRequest, sleLacpBaseControlStatus, 
				sleLacpBaseControlTimer, sleLacpBaseControlTimeStamp, sleLacpBaseControlReqResult, sleLacpBaseControlSystemPriority, sleLacpBaseControlAggregatorId, 
				sleLacpInterfaceIndex, sleLacpInterfaceName, sleLacpInterfaceActorPriority, sleLacpInterfaceActorAdminKey, sleLacpInterfaceActorAdminState, 
				sleLacpInterfaceDestinationMac, sleLacpInterfaceDiscardWrongConversation, sleLacpInterfaceControlRequest, sleLacpInterfaceControlStatus, sleLacpInterfaceControlTimer, 
				sleLacpInterfaceControlTimeStamp, sleLacpInterfaceControlReqResult, sleLacpInterfaceControlIndex, sleLacpInterfaceControlPriority, sleLacpInterfaceControlTimeout, 
				sleLacpInterfaceControlDestinationMac, sleLacpInterfaceControlDiscardWrongConversation, sle2LldpGlobalIfIndex, sle2LldpGlobalAgtCircuitId, sle2LldpGlobalMedDevType, 
				sle2LldpGlobalPortDescription, sle2LldpGlobalControlRequest, sle2LldpGlobalControlStatus, sle2LldpGlobalControlTimer, sle2LldpGlobalControlTimeStamp, 
				sle2LldpGlobalControlReqResult, sle2LldpGlobalControlIfIndex, sle2LldpGlobalControlAgtCircuitId, sle2LldpGlobalControlMedDevType, sle2LldpGlobalControlPortDescription, 
				sle2LldpParamIfIndex, sle2LldpParamAgentMode, sle2LldpParamBacManagementAddress, sle2LldpParamBacPortDescription, sle2LldpParamBacSystemCapabilities, 
				sle2LldpParamBacSystemDescription, sle2LldpParamBacSystemName, sle2LldpParamI8021LinkAgg, sle2LldpParamI8021MgmtVid, sle2LldpParamI8021PortPtclVlanid, 
				sle2LldpParamI8021PortVlanid, sle2LldpParamI8021PtclIdentity, sle2LldpParamI8021VidDigest, sle2LldpParamI8021VlanName, sle2LldpParamI8023MacPhy, 
				sle2LldpParamI8023MaxMtuSize, sle2LldpParamMedInventory, sle2LldpParamMedLocation, sle2LldpParamMedNetworkPolicy, sle2LldpParamMedPower, 
				sle2LldpParamControlRequest, sle2LldpParamControlStatus, sle2LldpParamControlTimer, sle2LldpParamControlTimeStamp, sle2LldpParamControlReqResult, 
				sle2LldpParamControlIfIndex, sle2LldpParamControlAgentMode, sle2LldpParamControlBacManagementAddress, sle2LldpParamControlBacPortDescription, sle2LldpParamControlBacSystemCapabilities, 
				sle2LldpParamControlBacSystemDescription, sle2LldpParamControlBacSystemName, sle2LldpParamControlI8021LinkAgg, sle2LldpParamControlI8021MgmtVid, sle2LldpParamControlI8021PortPtclVlanid, 
				sle2LldpParamControlI8021PortVlanid, sle2LldpParamControlI8021PtclIdentity, sle2LldpParamControlI8021VidDigest, sle2LldpParamControlI8021VlanName, sle2LldpParamControlI8023MacPhy, 
				sle2LldpParamControlI8023MaxMtuSize, sle2LldpParamControlMedInventory, sle2LldpParamControlMedLocation, sle2LldpParamControlMedNetworkPolicy, sle2LldpParamControlMedPower, 
				sle2LldpAgentIfIndex, sle2LldpAgentMode, sle2LldpAgentChassisIdTlv, sle2LldpAgentAdminStatus, sle2LldpAgentLocallyAssigned, 
				sle2LldpAgentManagementAddressTlv, sle2LldpAgentMsgTxHold, sle2LldpAgentPortIdTlv, sle2LldpAgentTimerMsgFastTx, sle2LldpAgentTimerMsgTxInterval, 
				sle2LldpAgentTimerReinitDelay, sle2LldpAgentTimerTxDelay, sle2LldpAgentTMNlimit, sle2LldpAgentTMNInfoType, sle2LldpAgentTMNMac, 
				sle2LldpAgentTMNTimer, sle2LldpAgentTxFastInit, sle2LldpAgentTxMaxCredit, sle2LldpAgentControlRequest, sle2LldpAgentControlStatus, 
				sle2LldpAgentControlTimer, sle2LldpAgentControlTimeStamp, sle2LldpAgentControlReqResult, sle2LldpAgentControlIfIndex, sle2LldpAgentControlMode, 
				sle2LldpAgentControlChassisIdTlv, sle2LldpAgentControlAdminStatus, sle2LldpAgentControlLocallyAssigned, sle2LldpAgentControlManagementAddressTlv, sle2LldpAgentControlMsgTxHold, 
				sle2LldpAgentControlPortIdTlv, sle2LldpAgentControlTimerMsgFastTx, sle2LldpAgentControlTimerMsgTxInterval, sle2LldpAgentControlTimerReinitDelay, sle2LldpAgentControlTimerTxDelay, 
				sle2LldpAgentControlTMNlimit, sle2LldpAgentControlTMNInfoType, sle2LldpAgentControlTMNMac, sle2LldpAgentControlTMNTimer, sle2LldpAgentControlTxFastInit, 
				sle2LldpAgentControlTxMaxCredit, sle2LldpStatsIfIndex, sle2LldpStatsAgentMode, sle2LldpStatsTransmittedFramesTotal, sle2LldpStatsAgedEntriesTotal, 
				sle2LldpStatsReceivedFramesTotal, sle2LldpStatsReceivedFramesError, sle2LldpStatsDiscardedFramesTotal, sle2LldpStatsTLVDiscardTotal, sle2LldpStatsTLVUnrecognisedTotal, 
				sle2LldpStatsControlRequest, sle2LldpStatsControlStatus, sle2LldpStatsControlTimer, sle2LldpStatsControlTimeStamp, sle2LldpStatsControlReqResult, 
				sle2LldpRemoteIfIndex, sle2LldpRemoteAgentMode, sle2LldpRemoteSysName, sle2LldpRemoteSysDescr, sle2LldpRemotePortDescr, 
				sle2LldpRemoteRxTtl, sle2LldpRemoteSysCapability, sle2LldpRemoteIfNumbering, sle2LldpRemoteIfNumber, sle2LldpRemoteOid, 
				sle2LldpRemoteMgmtAddrSubType, sle2LldpRemoteMgmtAddr, sle2LldpRemoteChassisIdType, sle2LldpRemoteChassisId, sle2LldpRemotePortIdType, 
				sle2LldpRemotePortId, sle2LldpRemotePortVlanId, sle2LldpRemotePPVlanId, sle2LldpRemoteProtocols, sle2LldpRemoteVidUsageDigest, 
				sle2LldpRemoteMgmtVlan, sle2LldpRemoteLinkAggrStatus, sle2LldpRemoteLinkAggrPortId, sle2LldpRemoteAutonegoSupport, sle2LldpRemoteAutonegoCapability, 
				sle2LldpRemoteOperMauType, sle2LldpRemoteMaxFrameSize, sle2LldpRemoteMedCapability, sle2LldpRemoteMedCapabilityDevType, sle2LldpRemoteMedNwPlcyAppType, 
				sle2LldpRemoteMedNwPlcyVlanId, sle2LldpRemoteMedNwPlcyTagged, sle2LldpRemoteMedNwPlcyL2Prio, sle2LldpRemoteMedLocDataFormat, sle2LldpRemoteMedLocLatitudeRes, 
				sle2LldpRemoteMedLocLatitude, sle2LldpRemoteMedLocLongitudeRes, sle2LldpRemoteMedLocLongitude, sle2LldpRemoteMedLocAt, sle2LldpRemoteMedLocAltitudeRes, 
				sle2LldpRemoteMedLocAltitude, sle2LldpRemoteMedLocDatum, sle2LldpRemoteMedLocLciLength, sle2LldpRemoteMedLocWhat, sle2LldpRemoteMedLocCountryCode, 
				sle2LldpRemoteMedLocCaType, sle2LldpRemoteMedLocCaLen, sleCVlanRegIndex, sleCVlanIndex, sleMllcfControlHoldTime, 
				sleMllcfControlPortsB, sleMllcfControlPortsA, sleMllcfControlReqResult, sleMllcfControlTimeStamp, sleMllcfControlTimer, 
				sleMllcfControlStatus, sleMllcfControlRequest, sleMllcfHoldTime, sleMllcfPortsBStatus, sleMllcfPortsAAdminDownStatus, 
				sleMllcfPortsALinkDownStatus, sleMllcfPortsB, sleMllcfPortsA, sleBridgeInterfacePrivateVlanHostAssociationPvid, sleBridgeInterfacePrivateVlanMappingPvid, 
				sleBridgeInterfaceControlPrivateVlanHostAssociationPvid, sleBridgeInterfaceControlPrivateVlanMappingPvid, sleBridgeInterfaceControlDefaultVlan, sleBridgeInterfaceVlanTranslation, sleBridgeInterfaceDefaulSVlanId, 
				sleBridgeInterfaceControlVlanTranslate, sleBridgeInterfaceControlVlanToBeTranslated, sle2LldpRemoteMedNwPlcyDscp, sle2LldpRemoteVlanIfIndex, sle2LldpRemoteVlanAgentMode, 
				sle2LldpRemoteVlanId, sle2LldpRemoteVlanName, sle2LldpBaseSystemDescription, sle2LldpBaseSystemName, sle2LldpBaseControlRequest, 
				sle2LldpBaseControlStatus, sle2LldpBaseControlTimer, sle2LldpBaseControlTimeStamp, sle2LldpBaseControlReqResult, sle2LldpBaseControlSystemDescription, 
				sleBridgeInterfaceGroup, sleBridgeInterfaceGroupSpanningTree, sleBridgeInterfaceControlGroup, sleBridgeInterfaceControlGroupSpanningTree, sleBridgeInterfaceProviderNetworkEtherType, 
				sleBridgeInterfaceControlProviderNetworkEtherType, sleBridgePortMulticast, sleBridgePortFloodBlock, sleBridgePortControlMulticast, sleBridgePortControlFloodBlock, 
				sleLacpInterfaceTimeout, sleBridgeId, sleBridgeProtocol, sleBridgeControlId, sleBridgeControlProtocol, 
				sleLacpInterfaceActiveLink, sleLacpInterfaceControlActiveLink, sle2LldpBaseControlSystemName, sleBridgeInterfacePrivateVlanHostAssociationPrimaryVid, sleBridgeInterfacePrivateVlanMappingSecondaryVid, 
				sleBridgeInterfaceControlPrivateVlanHostAssociationPrimaryVid, sleBridgeInterfaceControlPrivateVlanMappingSecondaryVid }
			STATUS current
			DESCRIPTION 
				"Description."
			::= { sleBridge 47 }

		
		sleBridgeNotificationGroup NOTIFICATION-GROUP
			NOTIFICATIONS { sleBridgeLacpProfileChanged, sleBridgeDoubleTagProtoIdChanged, sleBridgeMirrorProfileChanged, sleBridgeMaxLearnPerUnitChanged, sleBridgeFdbAgeingTimeChanged, 
				sleBridgeStackProfileChanged, sleBridgeLldpProfileChanged, sleBridgeTcpSyncookieChanged, sleBridgeTcpIgnoreRstUnknownChanged, sleBridgePortPVidChanged, 
				sleBridgePortMaxHostsChanged, sleBridgePortMaxLearnPerUnitChanged, sleBridgePortMACFilterPermissionChanged, sleBridgePortMirrorProfileChanged, sleBridgePortBcscThresholdProfileChanged, 
				sleBridgePortQinQStatusChanged, sleBridgePortLinktypeChanged, sleBridgePortEdgemodeChanged, sleBridgePortStpBpduFilterChanged, sleBridgePortPvlanIsolatedStatusChanged, 
				sleVlanCreated, sleVlanDestroyed, sleVlanPortProfileChanged, sleVlanAgeingTimeChanged, sleVlanMapFidChanged, 
				sleVlanMapStpIdChanged, sleVlanMapErpDomainIdChanged, sleStpOperationModeChanged, sleStpConfigureProfileChanged, sleStpTimerProfileChanged, 
				sleStpBpduGuardProfileChanged, sleStpInstanceEnableChanged, sleStpInstanceConfigProfileChanged, sleStpInstancePortProfileChanged, sleSubnetVlanCreated, 
				sleSubnetVlanDestroyed, sleProtocolVlanCreated, sleProtocolVlanDestroyed, sleLagProfileChanged, sleLagLacpPortProfileChanged, 
				sleFdbEntryCreated, sleFdbEntryDestoryed, sleFdbTableEntriesCleared, sleMfdbEntryCreated, sleMfdbEntryDestoryed, 
				sleMfdbEntryPermissionChanged, sleMfdbEntryTableCleared, sleIgmpConfProfileChanged, sleIgmpStaticMcastCreated, sleIgmpStaticMcastDestroyed, 
				sleStackDeviceCreated, sleStackDeviceDestoryed, sleErpDomainCreated, sleErpDomainDestroyed, sleErpDomainProfileChanged, 
				sleErpProtectionActivationChanged, sleLldpPortProfileChanged, sleLldpStatisticsCleared, sleBridgePSStatusChanged, sleBridgePSMaxCountChanged, 
				sleBridgePSProfileChanged, sleBridgePSFdbEntryCreated, sleBridgePSFdbEntryDestroyed, sleBridgePortStpBpduGuardErrRcvChanged, sleErpHoldOffTimeChanged, 
				sleErpRingPriorityChanged, sleErpTrapChanged, sleBridgeFGBaseCfgdStatusChanged, sleBridgeAutoInterfaceActivationChanged, sleBridgeFGPortUnblockChanged, 
				sleBridgeFGPortProfileChanged, sleBridgeLoopDetectProfileChanged, sleBridgePortLoopDetectProfileChanged, sleBridgePortLoopDetectUnblock, sleBridgePvlanPormSelectModeChanged, 
				sleBridgeVTSet, sleBridgeVTClear, sleBridgeGarpStatusChanged, sleBridgeGarpTimerChanged, sleBridgeGarpAppPortStatusChanged, 
				sleBridgeGarpAppPortProfileChanged, sleBridgeGarpStatisticsCleared, sleBridgeGmrpStaticAdded, sleBridgeGmrpStaticDeleted, sleBridgePortNetBIOSFilterChanged, 
				sleBridgePortPriorityChanged, sleBridgePortInnertagChanged, sleBridgePortPopInnertagChanged, sleBridgePortPushInnertagChanged, sleVlanInboundTagChanged, 
				sleVlanOutboundTagSet, sleVlanOutboundTagClear, sleBridgePortInner2outerVidChanged, sleBridgePortInner2outerPriChanged, sleBridgePSFdbEntryCleared, 
				sleBridgePortDhcpFilterServerChanged, sleBridgePortMACLearningStatusChanged, sleBridgePortPortBridgeStatusChanged, sleBridgeInBoundVTSet, sleBridgeInBoundVTClear, 
				sleBridgeInnerTagProtoIdChanged, sleVlanInboundTagCleared, sleVlanRangeInboundTagChanged, sleVlanRangeInboundTagCleared, sleVlanRangeCreated, 
				sleBridgeUnknownMcastBlockAllPortsChanged, sleBridgePortUnknownMcastBlockChanged, sleBridgeEcmpHashTypeChanged, sleBridgeTcpSynguardChanged, sleBridgePortDescriptionChanged, 
				sleBridgePortHoldTimeChanged, sleLagLacpStatsCleared, sleBridgeOuterTagProtoIdChanged, sleBridgeOutBoundVTSet, sleBridgeOutBoundVTClear, 
				sleBridgeMacAntiSpoofingChanged, sleBridgeMacReplaceChanged, sleBridgePortMacAntiSpoofChanged, sleVlanProtoIdOuterProtoIdChanged, sleBridgeStormControlChanged, 
				sleVlanMappingCreated, sleVlanMappingDeleted, sleBridgeMacLearningModeChanged, sleBridgeLagGlobalDistModeChanged, sleVlanDescriptionChanged, 
				sleVlanElineVlanCreated, sleBridgePortSwitchStatusChanged, sleBridgePortSwitchModeChanged, sleBridgePortSwitchDefaultVlanChanged, sleBridgePortSwitchNativeVlanChanged, 
				sleBridgePortSwitchAccFramTypeChanged, sleBridgePortSwitchAllowdVlanAdded, sleBridgePortSwitchAllowdVlanDeleted, sleVlanOperStatusChagned, sleVlanMtuChagned, 
				sleBridgePortSwitchStaticChannelChanged, sleBridgePortSwitchChannelLoadbalanceChanged, slePowerInlineEnableChanged, slePowerInlineDisableChanged, slePowerInlineResetChanged, 
				slePowerInlineLegacyChanged, slePowerInlinePriorityChanged, slePowerInlineClassChanged, slePowerInlinePowerChanged, sleMfdbOldEntryCreated, 
				sleMfdbOldEntryDestoryed, sleMfdbOldEntryPermissionChanged, sleMfdbOldEntryTableCleared, sleBridgePortLoopDetectPeriodMsChanged, sleLagProfileActiveLinkChanged, 
				sleLldpPortNetworkPolicyProfileChanged, sleLldpMedNetworkPolicyProfileCreated, sleLldpMedNetworkPolicyProfileDestroyed, sleLldpMedNetworkPolicyProfileCleared, sleLldpMedNetworkPolicyProfilePolicyChanged, 
				sleLldpMedNetworkPolicyProfilePolicyDeleted, sleBridgePortLoopDetectLoopingCountChanged, sleBridgePortPortLinkCntChanged, sleBridgePortLoopDetectVlanChanged, sleBridgePortLoopDetectVlanDeleted, 
				sleBridgePortSwitchChannelProfileChanged, sleBridgePortSwitchChannelProfileDeleted, sleLagLacpPortAggrChanged, sleBridgeReservedVlanAdded, sleBridgeReservedVlanRemoved, 
				sleBridgeInterfaceSwitchportChanged, sleBridgeInterfaceSwitchportAllowedVlanChanged, sleBridgeInterfaceSwitchportModeChanged, sleBridgeInterfaceSwitchportModeIngressFilterChanged, sleBridgeInterfaceSwitchportTrunkDeleted, 
				sleBridgeInterfaceSwitchportTrunkNativeVlanChanged, sleBridgeInterfaceSwitchportTrunkNativeVlanDeleted, sleBridgeChannelGroupLacpMaxBundleChanged, sleBridgeChannelGroupLacpMaxBundleDeleted, sleBridgeChannelGroupSystemPriorityChanged, 
				sleBridgeChannelGroupSystemPriorityDeleted, sleBridgeInterfaceChannelGroupAdminKeyChanged, sleBridgeInterfaceChannelGroupAggrTypeChanged, sleBridgeInterfaceChannelGroupPriorityChanged, sleBridgeInterfaceChannelGroupTimeOutChanged, 
				sleBridgeInterfaceChannelGroupDeleted, sleBridgeInterfaceChannelGroupActiveLinkChanged, sleBridgeInterfaceChannelGroupDistModeChanged, sleBridgePortBandwidthChanged, sleSubnetVlan6Created, 
				sleSubnetVlan6Destroyed, sleBridgePortAliasSet, sleBridgePortAliasUnset, sleBridgeFGBaseSfgdStatusChanged, sleBridgeStpProfileChanged, 
				sleBridgeMultiPortLlcfChanged, sleBridgeMultiPortLlcfDeleted, sleBridgeMultiPortLlcfTimerChanged, sleBridgePortMaxNewHostsChanged, sleBridgePortSpanningTreeDetectedProtocolsCleared, 
				sleBridgePortStpStatusChanged, sleBridgePortStpBpduGuardChanged, sleBridgePortOuterTpidChanged, sleBridgePortMirrorMonitorChanged, sle2MacAddressEntryCreated, 
				sle2MacAddressEntryDestroyed, sle2MacAddressTableEntriesCleared, sleBridgePortFloodBlockChanged, sleBridgePortMulticastChanged, sleBridgeInterfaceChannelGroupChanged, 
				sleBridgeInterfaceSwitchportDefaultVlanChanged, sleBridgeInterfaceSwitchportDefaultVlanDeleted, sleBridgeInterfaceVlanChanged }
			STATUS current
			DESCRIPTION 
				"Description."
			::= { sleBridge 48 }

		
	
	END

--
-- sle-bridge-mib.mib
--
