-- *****************************************************************************
-- Unisphere-Data-SLEP-CONF
--
-- SNMP Agent Capabilities definitions for the SLEP MIB.
--
-- Copyright (c) 2001 Unisphere Networks, Inc.  All rights reserved.
-- *****************************************************************************

Unisphere-Data-SLEP-CONF DEFINITIONS ::= BEGIN

IMPORTS
    MODULE-IDENTITY
        FROM SNMPv2-SMI
    AGENT-CAPABILITIES
        FROM SNMPv2-CONF
    usDataAgents
        FROM Unisphere-Data-Agents
    usdSlepGroup
        FROM Unisphere-Data-SLEP-MIB;

usdSlepAgent MODULE-IDENTITY
    LAST-UPDATED "200103301415Z"  -- 30-Mar-01 09:15 AM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Serial Line Encapsulation
        Protocol (SLEP) component of the SNMP agent in the Unisphere Data
        Routing Switch family of products."
    -- Revision History
    REVISION    "200103301415Z"  -- 30-Mar-01 09:15 AM EST  - RX 3.2
    DESCRIPTION
        "The initial release of this management information module."
    ::= { usDataAgents 38 }

usdSlepAgentV1 AGENT-CAPABILITIES
    PRODUCT-RELEASE
        "Version 1 of the SLEP component of the Unisphere Routing Switch SNMP
        agent.  This version of the SLEP component is supported in the Unisphere
        RX 1.3 and subsequent system releases."
    STATUS      current
    DESCRIPTION
        "The MIB supported by the SNMP agent for the SLEP application in the
        Unisphere Routing Switch."

    SUPPORTS        Unisphere-Data-SLEP-MIB
        INCLUDES  { usdSlepGroup }

    ::= { usdSlepAgent 1 }

END
