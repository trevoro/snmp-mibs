--*********************************************************************
-- Copyright: Ericsson Telecom AB 1997
-- Doc no: 72/190 55-CAA 134 74 Uen
--
--
-- NAME ANS-ALARM-MIB.mib
-- 
-- DESCRIPTION
--
-- This MIB module defines objects for controlling the distribution and 
-- logging of events, assigning alarm severities and keeping track of 
-- currently active alarms in ANS. The managed objects for this are 
-- described through the following groups:
--
--         - the Event group
--	   - the Log Group
--         - the Alarm Severity Assignment group
--	   - the Current Alarm group
--
-- It also contains variable definitions to be used in alarm traps.
--
-- REVISION HISTORY
--
-- Old revision history is found in clearcase.
-- Use the 'ct lshistory' command to view it, or
-- use the program '/vobs/tools/bin/cc_mp' program to print
-- the file with the revision information.
-- REV     Date    Name       Reason
-- PA2    970528   etxtsun    Trap references deleted.
-- PA3    970619   etxtsun    currentAlarmIndex only an integer.
-- PA4	  970821   etxtpet    logEventGenObjString and currentAlarmObjString
--			      removed. The display string is from now on
-- PA5	  980701   etxtpet    Size defined for all display strings.
-- PA6	  981228   etxkake    The variable discriminateNtEvents added.
-- PA7	  011015   teigaba    Changed branch.

ANS-ALARM-MIB DEFINITIONS ::= BEGIN

IMPORTS
        OBJECT-TYPE
                FROM SNMPv2-SMI
	DisplayString
		FROM RFC1213-MIB
	RowStatus, DateAndTime, mlpmpR115
		FROM ANS-COMMON-MIB;

eventAndAlarm		OBJECT IDENTIFIER ::= {mlpmpR115 2}
event			OBJECT IDENTIFIER ::= {eventAndAlarm 1}
log			OBJECT IDENTIFIER ::= {eventAndAlarm 2}
alarmSeverityAssignment	OBJECT IDENTIFIER ::= {eventAndAlarm 3}
currentAlarm		OBJECT IDENTIFIER ::= {eventAndAlarm 4}

AlarmSeverity ::=
	INTEGER {
		indeterminate (0),
		critical (1),
		major (2),
		minor (3),
		warning (4),
		cleared (5)
	}

AlarmType ::=
	INTEGER {
		undefined (0),
		communications (1),
		qos (2),		-- Quality of service
		processing (3),
		equipment (4),
		environmental (5)
	}


-- *****************************************************************************
--        Textual conventions
-- *****************************************************************************

InstancePointer ::= OBJECT IDENTIFIER  
          
-- A pointer to either a specific instance of a MIB object or
-- a conceptual row of a MIB table in the managed device.  In
-- the latter case, by convention, it is the name of the
-- particular instance of the first accessible columnar object
-- in the conceptual row. If the instance is represented by a
-- group of variables, such as the System group in MIB-II, the 
-- first accessible variable in that group would be pointed at, 
-- i.e. the sysDescr variable in this example.


-- *****************************************************************************
--        Event group
-- *****************************************************************************
--
-- The Event Table controls the treatment of events generated by the network
-- element. Each entry in the eventTable describes an event or an alarm.
-- By setting the desired treatment it is possible to control whether an event 
-- shall be logged, sent as a trap, or be discarded. The community string
-- indicates to whom the traps shall be sent. The traps associated with the 
-- events are defined in other MIBs, normally in the MIBs containing the event 
-- generating object.

eventTable OBJECT-TYPE 
	SYNTAX	SEQUENCE OF EventEntry
	ACCESS	not-accessible
	STATUS	mandatory
	DESCRIPTION
		"A list of events that may be generated by the agent.
		Entries is a set of parameters that describe an event to be
		generated when certain conditions are met"
	::= { event 1 }

eventEntry OBJECT-TYPE 
	SYNTAX	EventEntry
	ACCESS	not-accessible
	STATUS	mandatory
	DESCRIPTION ""
	INDEX {eventIndex}
	::= { eventTable 1 }

EventEntry ::= SEQUENCE {
	eventIndex	INTEGER,
	eventName	DisplayString (SIZE (0..127)),
	eventTreatment	INTEGER,
	eventCommunity	DisplayString (SIZE (0..127)),
	eventLastTimeSent	DateAndTime,
	eventOwner	DisplayString (SIZE (0..127))
}

eventIndex OBJECT-TYPE
	SYNTAX	INTEGER(1..65535)
	ACCESS	read-only
	STATUS	mandatory
	DESCRIPTION
		"An index that uniquely identifies an entry in the
		event table.  Each such entry defines one event that
		is to be generated when the appropriate conditions
		occur."
	::= { eventEntry 1 }

eventName OBJECT-TYPE
	SYNTAX	DisplayString(SIZE(0..127))
	ACCESS	read-only
	STATUS	mandatory
	DESCRIPTION
		"The name of the associated event, normally the
		name of the associated trap."
	::= { eventEntry 2 }

eventTreatment OBJECT-TYPE
	SYNTAX	INTEGER{
			none(1),
			log(2),
			snmp-trap(3),
			log-and-trap(4)
		}
	ACCESS	read-write
	STATUS	mandatory
	DESCRIPTION
		"Defines how the system shall treat this event.
		In the case of log, an entry is made in the log table 
		for each event.  In the case of snmp-trap, an SNMP 
		trap is sent to one or more management stations."
	::= { eventEntry 3 }

eventCommunity OBJECT-TYPE
	SYNTAX	DisplayString(SIZE(0..127))
	ACCESS	read-write
	STATUS	mandatory
	DESCRIPTION
		"If an SNMP trap is to be sent, it will be sent to
		the SNMP community specified by this octet string."
	::= { eventEntry 4 }

eventLastTimeSent OBJECT-TYPE
	SYNTAX	DateAndTime
	ACCESS	read-only
	STATUS	mandatory
	DESCRIPTION
		"The value of sysUpTime at the time this event
		entry last generated an event.  If this entry has
		not generated any events, this value will be zero."
	::= { eventEntry 5 }

eventOwner OBJECT-TYPE
	SYNTAX	DisplayString(SIZE (0..127))
	ACCESS	read-write
	STATUS	mandatory
	DESCRIPTION
		"The entity that configured this entry and is therefore
		responsible for its contents. This variable is suggested
		to contain one or more of the following:
		IP address, management station name, network manager's
		name, location, or phone number.
		In some cases the agent system itself will be the owner 
		of an entry (e.g. prior to a manual configuration of an
		entry). In these cases, this string shall be set
		to a string starting with 'monitor'. Note that this
		variable will only act as a voluntary access control.
		It does not prevent uncooperative parties from changing
		an entry of another owner."
	::= { eventEntry 6 }

discriminateNtEvents OBJECT-TYPE
	SYNTAX INTEGER {
			include (1),
			exclude (2)
			}
	ACCESS read-write
	STATUS mandatory
	DESCRIPTION
		"Indicates whether events generated by an NT shall
		be discarded or not. include means that NT events shall
		be shown. exclude means that NT events are hidden when
		displaying the event log, the current alarm list, and
		when sending traps."
	::= { event 2 }


-- *****************************************************************************
--        Log Group
-- *****************************************************************************
-- The logTable contains logged events and alarms. The log works in a 
-- wrap-around mode i.e. when the log has reached its maximum size the oldest 
-- entry will be removed when a new entry is added. For alarms, additional 
-- information can be found in the logAlarmType and logAlarmSeverity attributes,
-- for non alarm entry the attributes are undefined.

-- It is possible to globally turn on and off the logging of all events and 
-- alarms via the logAdminStatus, and to set the maximum size of the log.

logAdminStatus OBJECT-TYPE
	SYNTAX INTEGER {
			up (1),
			down (2)
			}
	ACCESS read-write
	STATUS mandatory
	DESCRIPTION
		"The administrative status of the log as a whole. Up
		means that logging shall take place of all events that
		are to be logged. Down means that no logging of events
		shall take place."
	::= { log 1 }

logSize OBJECT-TYPE
	SYNTAX INTEGER
	ACCESS read-write
	STATUS mandatory
	DESCRIPTION
		"A configurable maximum size of the log."
	::= { log 2 }

-- The Log Table


logTable OBJECT-TYPE 
	SYNTAX	SEQUENCE OF LogEntry
	ACCESS	not-accessible
	STATUS	mandatory
	DESCRIPTION
		"A list of events that have been logged."
	::= { log 3 }

logEntry OBJECT-TYPE 
	SYNTAX	LogEntry
	ACCESS	not-accessible
	STATUS	mandatory
	DESCRIPTION ""
	INDEX {logIndex}
	::= { logTable 1 }

LogEntry ::= SEQUENCE {
	logIndex			INTEGER,
	logEventIndex			INTEGER,
	logEventName			DisplayString (SIZE (0..127)),
	logEventGeneratingObject	InstancePointer,
	logTime				DateAndTime,
	logEventInformation		DisplayString (SIZE (0..255)),
	logEventType			INTEGER,
	logAlarmType			AlarmType,
	logAlarmSeverity		AlarmSeverity
}

logIndex OBJECT-TYPE
	SYNTAX	INTEGER
	ACCESS	read-only
	STATUS	mandatory
	DESCRIPTION
		"An index that uniquely identifies an entry
		in the log table. The association between a
		particular event and its logIndex shall remain 
		constant for the life-time of the event in the 
		log."
	::= { logEntry 1 }

logEventIndex OBJECT-TYPE
	SYNTAX	INTEGER(1..65535)
	ACCESS	read-only
	STATUS	mandatory
	DESCRIPTION
		"The event entry that generated this log
		entry.  The log identified by a particular
		value of this index is associated with the same
		eventEntry as identified by the same value
		of eventIndex."
	::= { logEntry 2 }

logEventName OBJECT-TYPE
	SYNTAX	DisplayString(SIZE (0..127))
	ACCESS	read-only
	STATUS	mandatory
	DESCRIPTION
		"The name of the logged event."
	::= { logEntry 3 }

logEventGeneratingObject OBJECT-TYPE
	SYNTAX	InstancePointer
	ACCESS	read-only
	STATUS	mandatory
	DESCRIPTION
		"The event generating object. Identifies either 
		a variable in the group of variables belonging
		to the object, or a row in a table representing
		the object."
	::= { logEntry 4 }

logTime OBJECT-TYPE
	SYNTAX	DateAndTime
	ACCESS	read-only
	STATUS	mandatory
	DESCRIPTION
		"The time this log entry was created."
	::= { logEntry 5 }

logEventInformation OBJECT-TYPE
	SYNTAX	DisplayString(SIZE(0..255))
	ACCESS	read-only
	STATUS	mandatory
	DESCRIPTION
		"Additional information pin-pointing the cause or 
		origin of the event. For alarms this will contain 
		the same information as the alarmInformation variable 
		of the corresponding alarm trap. For other events the
		contents of this object is implementation-specific."
	::= { logEntry 6 }

logEventType OBJECT-TYPE
	SYNTAX	INTEGER{
			alarm(1),
			other(2)
		}
	ACCESS	read-only
	STATUS	mandatory
	DESCRIPTION
		"Identifies the type of the event, which may be
		an alarm event or a regular event. In case of an
		alarm event additional information can be found
		in the logAlarmType and logAlarmSeverity."
	::= { logEntry 7 }

logAlarmType OBJECT-TYPE
	SYNTAX	AlarmType
	ACCESS	read-only
	STATUS	mandatory
	DESCRIPTION
		"The type of alarm for the logged alarm event."
	::= { logEntry 8 }

logAlarmSeverity OBJECT-TYPE
	SYNTAX	AlarmSeverity
	ACCESS	read-only
	STATUS	mandatory
	DESCRIPTION
		"The perceived severity of the logged alarm event."
	::= { logEntry 9 }


-- *****************************************************************************
--        Alarm Severity Assignment Group
-- *****************************************************************************

-- alarmSeverityAssignmentTable
-- The Alarm Severity Assignment table allows assignment of the perceived 
-- severity of alarms in the system.


alarmSeverityAssignmentTable OBJECT-TYPE 
	SYNTAX	SEQUENCE OF AlarmSeverityAssignmentEntry
	ACCESS	not-accessible
	STATUS	mandatory
	DESCRIPTION
		"Contains entries for alarm severity assignment."
	::= { alarmSeverityAssignment 1 }

alarmSeverityAssignmentEntry OBJECT-TYPE 
	SYNTAX	AlarmSeverityAssignmentEntry
	ACCESS	not-accessible
	STATUS	mandatory
	DESCRIPTION ""
	INDEX { alarmSeverityIndex }
	::= { alarmSeverityAssignmentTable 1 }

AlarmSeverityAssignmentEntry ::= SEQUENCE {
	alarmSeverityIndex	INTEGER,
	alarmSeverityAlarmName	DisplayString (SIZE (0..127)),
	alarmSeverityPerceivedSeverity	AlarmSeverity
}

alarmSeverityIndex OBJECT-TYPE
	SYNTAX	INTEGER(1..65535)
	ACCESS	read-only
	STATUS	mandatory
	DESCRIPTION
		"An index that uniquely identifies an entry in the
		alarmSeverityAssignmentTable."
	::= { alarmSeverityAssignmentEntry 1 }

alarmSeverityAlarmName OBJECT-TYPE
	SYNTAX	DisplayString(SIZE (0..127))
	ACCESS	read-only
	STATUS	mandatory
	DESCRIPTION
		"The name of the alarm this entry applies to (also
		indicates the probable cause of the alarm). The same
		as the name of the associated alarm trap."
	::= { alarmSeverityAssignmentEntry 2 }

alarmSeverityPerceivedSeverity OBJECT-TYPE
	SYNTAX	AlarmSeverity
	ACCESS	read-write
	STATUS	mandatory
	DESCRIPTION
		"The perceived severity that shall apply to the 
		associated alarms."
	::= { alarmSeverityAssignmentEntry 3 }


-- *****************************************************************************
--        Current Alarm Group 
-- *****************************************************************************

-- The Current Alarm Table
-- The current alarm table contains all alarms that are currently active in the 
-- system. When a fault condition ceases the corresponding entry in the table is
-- removed automatically.

numberOfCurrentAlarms OBJECT-TYPE
	SYNTAX INTEGER
	ACCESS read-only
	STATUS mandatory
	DESCRIPTION
		"Number of currently active alarms in the ANS."
	::= { currentAlarm 1 }

currentAlarmTable OBJECT-TYPE 
	SYNTAX	SEQUENCE OF CurrentAlarmEntry
	ACCESS	not-accessible
	STATUS	mandatory
	DESCRIPTION
		"A list of currently active alarms in the ANS."
	::= { currentAlarm 2 }

currentAlarmEntry OBJECT-TYPE 
	SYNTAX	CurrentAlarmEntry
	ACCESS	not-accessible
	STATUS	mandatory
	DESCRIPTION ""
	INDEX {currentAlarmIndex}
	::= { currentAlarmTable 1 }

CurrentAlarmEntry ::= SEQUENCE {
	currentAlarmIndex	INTEGER,
	currentAlarmName	DisplayString (SIZE (0..127)),
	currentAlarmObject	InstancePointer,
	currentAlarmType	AlarmType,
	currentAlarmSeverity	AlarmSeverity,
	currentAlarmTime	DateAndTime,
	currentAlarmInformation	DisplayString (SIZE (0..255))
}

currentAlarmIndex OBJECT-TYPE
	SYNTAX	INTEGER
	ACCESS	read-only
	STATUS	mandatory
	DESCRIPTION
		"An index that uniquely identifies an
		entry in the current alarm table."
	::= { currentAlarmEntry 1 }

currentAlarmName OBJECT-TYPE
	SYNTAX	DisplayString(SIZE (0..127))
	ACCESS	read-only
	STATUS	mandatory
	DESCRIPTION
		"The name of the alarm. Also indicates
		the probable cause of the alarm."
	::= { currentAlarmEntry 2 }

currentAlarmObject OBJECT-TYPE
	SYNTAX	InstancePointer
	ACCESS	read-only
	STATUS	mandatory
	DESCRIPTION
		"The alarming object. Identifies either a
		variable in the group of variables belonging to
		the alarming object, or a row in a table
		representing the alarming object."
	::= { currentAlarmEntry 3 }

currentAlarmType OBJECT-TYPE
	SYNTAX	AlarmType
	ACCESS	read-only
	STATUS	mandatory
	DESCRIPTION
		"The type of alarm."
	::= { currentAlarmEntry 4 }

currentAlarmSeverity OBJECT-TYPE
	SYNTAX	AlarmSeverity
	ACCESS	read-only
	STATUS	mandatory
	DESCRIPTION
		"The perceived severity of the fault."
	::= { currentAlarmEntry 5 }

currentAlarmTime OBJECT-TYPE
	SYNTAX	DateAndTime
	ACCESS	read-only
	STATUS	mandatory
	DESCRIPTION
		"The time the fault was detected."
	::= { currentAlarmEntry 6 }

currentAlarmInformation OBJECT-TYPE
	SYNTAX	DisplayString(SIZE (0..255))
	ACCESS	read-only
	STATUS	mandatory
	DESCRIPTION
		"Additional information pin-pointing the problem.
		May be a string of zero length."
	::= { currentAlarmEntry 7 }

END
