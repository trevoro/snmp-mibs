---------------------------------------------------------------------------
-- hippiSwitchMIB MODULE-IDENTITY
--    LAST-UPDATED   "9809181100Z"
--    ORGANIZATION	 "Essential/ODS Inc."
--    CONTACT-INFO   "Essential/ODS support.  E-mail support@esscom.com"
--    DESCRIPTION    "HIPPI EPS-16 16 port switch MIB"
--
-- REVISION "9809181100Z"
-- DESCRIPTION "v1.03d The comments at the beginning were modified to 
--    immitate the SNMP v2 REVISION format.  The DESCRIPTION, ORGANIZATION,
--    and CONTACT-INFO fields in the comments were modified. 
--    Added 1 save/restore variable for the src/destination routes, 
--    and 1 save/restore variable for hunt groups."
--
-- REVISION "9709161000Z"
-- DESCRIPTION "v1.03c This is the first official release of this MIB."
--
---------------------------------------------------------------------------

ESSENTIAL-COMMUNICATIONS-HIPPI-SWITCH DEFINITIONS ::= BEGIN

IMPORTS
   DisplayString
      FROM RFC1213-MIB
   Gauge,enterprises
      FROM RFC1155-SMI
   OBJECT-TYPE
      FROM RFC-1212
   ecExperimental
      FROM ESSENTIAL-COMMUNICATIONS-GLOBAL-REG;


---------------------------------------------------------------------------
--Main branches of the MIB.
---------------------------------------------------------------------------
essentialCommunications OBJECT IDENTIFIER ::= { enterprises essCom(2159) }
ecRoot                  OBJECT IDENTIFIER ::= { essentialCommunications 1 }
ecProducts              OBJECT IDENTIFIER ::= { ecRoot 3 } 
ecExperimental          OBJECT IDENTIFIER ::= { ecRoot 6 } 
hippiSwitchMIB          OBJECT IDENTIFIER ::= { ecExperimental 1 }
hippiSwitchMIBv103      OBJECT IDENTIFIER ::= { ecProducts 1 }
switchObjs              OBJECT IDENTIFIER ::= { hippiSwitchMIBv103 1 }
--switchEvents            OBJECT IDENTIFIER ::= { hippiSwitchMIBv103 2 } 
--switchConformance       OBJECT IDENTIFIER ::= { hippiSwitchMIBv103 3 } 
--switchGroups            OBJECT IDENTIFIER ::= { switchConformance 1 }
--switchCompliance        OBJECT IDENTIFIER ::= { switchConformance 2 }

---------------------------------------------------------------------------
---------------------------------------------------------------------------
--First branch of this MIB containing the switch objects.
---------------------------------------------------------------------------
---------------------------------------------------------------------------

switchDescription OBJECT-TYPE
   SYNTAX      DisplayString
   ACCESS      read-only
   STATUS      mandatory
   DESCRIPTION "Returns the description, vendor, 
                and version numbers of the switch."
   ::= { switchObjs 1 } 

switchNumOfPorts OBJECT-TYPE
   SYNTAX      Gauge
   ACCESS      read-only
   STATUS      mandatory
   DESCRIPTION   "The number of slots in this switch. 
            (Max number of media access cards)."
   ::= { switchObjs 2 } 

sccDescription OBJECT-TYPE
   SYNTAX      DisplayString
   ACCESS      read-only
   STATUS       mandatory
   DESCRIPTION   "The model, vendor, and version number 
                of the switch control card."
   ::= { switchObjs 3 }

sccDateTime OBJECT-TYPE
   SYNTAX      DisplayString
   ACCESS      read-write
   STATUS      mandatory
   DESCRIPTION   "The date/time in the real time clock. 
                Format: yyyymmddhhmmss."
   ::= { switchObjs 4 }

sccAdminStatus OBJECT-TYPE
   SYNTAX      INTEGER { up(1), reset(2) }
   ACCESS      read-write
   STATUS      mandatory
   DESCRIPTION "The desired state of the switch." 
   ::= { switchObjs 5 } 

sccOperStatus OBJECT-TYPE
   SYNTAX      INTEGER { up(1), reseting(2), busy(3) }
   ACCESS      read-only
   STATUS      mandatory
   DESCRIPTION "The current state of the switch.
            SNMP operations can not occur when the switch is busy.
            SNMP operations can not occur when the switch is resetting."
   ::= { switchObjs 6 } 

---------------------------------------------------------------------------
--The backplane hardware description.
---------------------------------------------------------------------------
backPlaneTable    OBJECT-TYPE
   SYNTAX      SEQUENCE OF BackPlaneEntry
   ACCESS      not-accessible
   STATUS      mandatory
   DESCRIPTION
            "This table represent all of the slots in a HIPPI switch. 
            None of the rows can be added to or deleted by the user."
   ::= { switchObjs 7 }

backPlaneEntry OBJECT-TYPE
   SYNTAX       BackPlaneEntry
   ACCESS       not-accessible
   STATUS      mandatory
   DESCRIPTION
            "A row in the table describing one slot in the switch backplane. "
   INDEX      { backPlaneIndex } --Identifies a row in the slot table.
   ::= { backPlaneTable 1 } 

BackPlaneEntry ::= SEQUENCE 
{
   backPlaneIndex            Gauge,
   backPlaneNumber            Gauge,     
   backPlaneCard            INTEGER,
   mICPowerUpInitError       Gauge,
   mICHippiParityBurstError    Gauge,
   mICLinkReady             Gauge,
   mICSourceInterconnect       Gauge,
   mICSourceRequest          Gauge,
   mICSourceConnect          Gauge,
   mICSourceLastConnectAttempt Gauge,
   mICDestinationInterconnect   Gauge,
   mICDestinationRequest      Gauge,
   mICDestinationConnect       Gauge,
   mICByteCounterOverflow      Gauge,
   mICNumberOfBytes          Gauge,
   mICNumberOfPackets          Gauge,
   mICConnectsSuccessful      Gauge
}
   
backPlaneIndex OBJECT-TYPE
   SYNTAX      Gauge
   ACCESS      not-accessible
   STATUS      mandatory
   DESCRIPTION   "The table index for this slot on the backplane."
   ::= { backPlaneEntry 1 }

backPlaneNumber   OBJECT-TYPE
   SYNTAX      Gauge
   ACCESS      read-only
   STATUS       mandatory
   DESCRIPTION   "The slot number as seen printed on the switch 
            (backPlaneIndex + 1)"
   ::= { backPlaneEntry 2 }

backPlaneCard OBJECT-TYPE
   SYNTAX      INTEGER {none(0),unknown(1),parallel(2),serial(3)}
   ACCESS      read-only
   STATUS      mandatory
   DESCRIPTION   "The type of MIC present in this slot of the backplane on 
            the switch"
   ::= { backPlaneEntry 3 }

mICPowerUpInitError OBJECT-TYPE
   SYNTAX      Gauge
   ACCESS      read-only
   STATUS      mandatory
   DESCRIPTION "True if error detected by MIC on start-up."
   ::= { backPlaneEntry 4 }

mICHippiParityBurstError OBJECT-TYPE
   SYNTAX       Gauge    -- { None(0), XDeMux(1), XMux(2), XError(3) }
   ACCESS      read-only
   STATUS      mandatory
   DESCRIPTION "Valid the SMIC only. Type of parity error."
   ::= { backPlaneEntry 5 }

mICLinkReady OBJECT-TYPE
   SYNTAX      Gauge
   ACCESS      read-only
   STATUS      mandatory
   DESCRIPTION "Valid the SMIC only. True if link ready asserted."
   ::= { backPlaneEntry 6 }

mICSourceInterconnect OBJECT-TYPE
    SYNTAX      Gauge
   ACCESS      read-only
   STATUS      mandatory
   DESCRIPTION "Source interconnect is valid for the PMIC only."
   ::= { backPlaneEntry 7 }

mICSourceRequest OBJECT-TYPE
   SYNTAX      Gauge
   ACCESS      read-only
   STATUS      mandatory
   DESCRIPTION "True if source request is asserted."
   ::= { backPlaneEntry 8 }

mICSourceConnect OBJECT-TYPE
   SYNTAX      Gauge
   ACCESS      read-only
   STATUS      mandatory
   DESCRIPTION "True if source connect is asserted."
   ::= { backPlaneEntry 9 }

mICSourceLastConnectAttempt OBJECT-TYPE
   SYNTAX      Gauge
   ACCESS      read-only
   STATUS      mandatory
   DESCRIPTION "True if last source request was successful."
   ::= { backPlaneEntry 10 }

mICDestinationInterconnect OBJECT-TYPE
   SYNTAX      Gauge
   ACCESS      read-only
   STATUS      mandatory
   DESCRIPTION "True if destination interconnect is asserted."
   ::= { backPlaneEntry 11 }

mICDestinationRequest OBJECT-TYPE
   SYNTAX      Gauge
   ACCESS      read-only
   STATUS      mandatory
   DESCRIPTION "True if destination request is asserted."
   ::= { backPlaneEntry 12 }

mICDestinationConnect OBJECT-TYPE
   SYNTAX      Gauge
   ACCESS      read-only
   STATUS      mandatory
   DESCRIPTION "True if destination connect is asserted."
   ::= { backPlaneEntry 13 }

mICByteCounterOverflow OBJECT-TYPE
   SYNTAX      Gauge
   ACCESS      read-only
   STATUS      mandatory
   DESCRIPTION "The number of times the byte counter has over-flowed."
   ::= { backPlaneEntry 14 }

mICNumberOfBytes OBJECT-TYPE
   SYNTAX      Gauge
   ACCESS      read-only
   STATUS      mandatory
   DESCRIPTION "The number of bytes that have passed through the MIC."
   ::= { backPlaneEntry 15 }

mICNumberOfPackets OBJECT-TYPE
   SYNTAX      Gauge
   ACCESS      read-only
   STATUS      mandatory
   DESCRIPTION "The number of times packets has been asserted."
   ::= { backPlaneEntry 16 }

mICConnectsSuccessful OBJECT-TYPE
   SYNTAX      Gauge
   ACCESS      read-only
   STATUS      mandatory
   DESCRIPTION "The number of times this MIC has connected since reset."
   ::= { backPlaneEntry 17 }

---------------------------------------------------------------------------
--Source Route Table.
--A table that contains the enable/disable information for each input port-
--output port pair.
---------------------------------------------------------------------------
sourceRouteTable OBJECT-TYPE
   SYNTAX      SEQUENCE OF SourceRouteEntry
   ACCESS       not-accessible
   STATUS       mandatory
   DESCRIPTION "This table holds all of the source routes for this switch.
            FORMAT: OutputPort InputPortList Status.
            Output port is 0 to 15
            Input  port is 0 to 15
            List is NUMBER or NUMBER1-NUMBER2 where NUMBER1 < NUMBER2.
            Status is 0 (disabled) or 1 (enabled)"
   ::= { switchObjs 8 } 

sourceRouteEntry OBJECT-TYPE
   SYNTAX      SourceRouteEntry
   ACCESS       not-accessible
   STATUS       mandatory
   DESCRIPTION "One row in the source route table."
   INDEX      { srcIndex }
   ::= { sourceRouteTable 1 }

SourceRouteEntry ::= SEQUENCE
{
   srcIndex      Gauge,
   srcRoute      DisplayString(1..80)
}

srcIndex OBJECT-TYPE
   SYNTAX      Gauge
   ACCESS      read-only
   STATUS      mandatory
   DESCRIPTION "The row number for this row of the table."
   ::= { sourceRouteEntry 1 } 

srcRoute OBJECT-TYPE
   SYNTAX      DisplayString
   ACCESS      read-only
   STATUS      mandatory
   DESCRIPTION "One source route.
            FORMAT: OutputPort InputPortList Status.
            Output port is 0 to 15
            Input  port is 0 to 15
            List is NUMBER or NUMBER1-NUMBER2 where NUMBER1 < NUMBER2.
            Status is 0 (disabled) or 1 (enabled)"
   ::= { sourceRouteEntry 2 } 

srcWriteRow      OBJECT-TYPE
   SYNTAX      DisplayString 
   ACCESS      read-write
   STATUS      mandatory
   DESCRIPTION "Setting this variable alters source routes.
            FORMAT: OutputPortList InputPortList Status.
            Output port is 0 to 15
            Input  port is 0 to 15
            List is NUMBER or NUMBER1-NUMBER2 where NUMBER1 < NUMBER2.
            Status is 0 (disabled) or 1 (enabled)"
   ::= { switchObjs 9 } 

---------------------------------------------------------------------------
--The destination routing table contains the huntgroup number 
--(if any) for each defined logical address and input port pair.
--tabel max is 4kx16. f(la,inport) = HG
---------------------------------------------------------------------------
--destRouteTable OBJECT IDENTIFIER ::= { scc 8 }
destRouteTable OBJECT-TYPE
   SYNTAX      SEQUENCE OF DestRouteEntry
   ACCESS       not-accessible
   STATUS       mandatory
   DESCRIPTION "This table holds all of destination routes (logical
            address routes) for this switch.
            FORMAT: LogicalAddress InputPortList Huntgroup.
            LogicalAddress is 0 to 4095.
            Input  port is 0 to 15
            Huntgroup is 0 to 31.
            List is NUMBER or NUMBER1-NUMBER2 where NUMBER1 < NUMBER2."
   ::= { switchObjs 10 } 

destRouteEntry OBJECT-TYPE
   SYNTAX      DestRouteEntry
   ACCESS       not-accessible
   STATUS       mandatory
   DESCRIPTION "A row in the destination route table."
   INDEX      { destIndex }
   ::= { destRouteTable 1 }

DestRouteEntry ::= SEQUENCE
{
   destIndex       Gauge,
   destRoute      DisplayString(1..80)
}

destIndex OBJECT-TYPE
   SYNTAX      Gauge
   ACCESS      read-only
   STATUS      mandatory
   DESCRIPTION "The index for this row of the table."
   ::= { destRouteEntry 1 } 

destRoute OBJECT-TYPE
   SYNTAX      DisplayString
   ACCESS      read-only
   STATUS      mandatory
   DESCRIPTION "One Destination Route.
            FORMAT: LogicalAddress InputPortList Huntgroup.
            LogicalAddress is 0 to 4095.
            Input  port is 0 to 15.
            Huntgroup is 0 to 31.
            List is NUMBER or NUMBER1-NUMBER2 where NUMBER1 < NUMBER2."
   ::= { destRouteEntry 2 } 

destWriteRow OBJECT-TYPE
   SYNTAX      DisplayString 
   ACCESS      read-write
   STATUS      mandatory
   DESCRIPTION "Setting this variable will alter the desitination routes.
            FORMAT: LogicalAddressList Huntgroup InputPortList.
            LogicalAddress is 0 to 4095.
            Huntgroup is 0 to 31. 31 will disable this route.
            Input port is 0 to 15.
            List is NUMBER or NUMBER1-NUMBER2 where NUMBER1 < NUMBER2."
   ::= { switchObjs 11 } 

---------------------------------------------------------------------------
--Hunt Group Table (Output port sets).    
--The huntgroup table defines which output ports are in each huntgroup set.
---------------------------------------------------------------------------
huntGroupTable OBJECT-TYPE
   SYNTAX      SEQUENCE OF HuntGroupEntry
   ACCESS       not-accessible
   STATUS       mandatory
   DESCRIPTION "This table holds all of the huntgroups for this  switch.
            FORMAT: Huntgroup ( OutportList )
            Huntgroup is 0 to 31.
            OutportList is an orderd list of output ports in Huntgroup."
   ::= { switchObjs 12 } 

huntGroupEntry OBJECT-TYPE
   SYNTAX      HuntGroupEntry
   ACCESS       not-accessible
   STATUS       mandatory
   DESCRIPTION "A row in the huntgroup table."
   INDEX      { hg }
   ::= { huntGroupTable 1 }

HuntGroupEntry ::= SEQUENCE
{
   --hgIndex      Gauge,
   hg            Gauge,         
   hgOutPortList   DisplayString (1..80)
   --hgWriteRow   Gauge
}

hg OBJECT-TYPE
   SYNTAX      Gauge
   ACCESS      read-only
   STATUS      mandatory
   DESCRIPTION "The huntgroup number." 
   ::= { huntGroupEntry 1 } 

hgOutPortList OBJECT-TYPE
   SYNTAX      DisplayString 
   ACCESS      read-only
   STATUS      mandatory
   DESCRIPTION "The definition of one Huntgroup.
            FORMAT: Huntgroup ( OutportList )
            Huntgroup is 0 to 31.
            OutportList is an orderd list of output ports in Huntgroup."
   ::= { huntGroupEntry 2 } 

hgLWriteRow OBJECT-TYPE
   SYNTAX      DisplayString 
   ACCESS      read-write
   STATUS      mandatory
   DESCRIPTION "Setting this variable will alter the huntgroup table by
            setting every huntgroup in list to include outPortList.
            FORMAT: HuntgroupList OutportList
            Huntgroup is 0 to 31.
            Outport is 0 to 15 and 16. 16 will clear the huntgroup.
            List is NUMBER or NUMBER1-NUMBER2 where NUMBER1 < NUMBER2."
   ::= { switchObjs 13 } 

---------------------------------------------------------------------------
--Hunt Group Order. A table that contains that the huntgroups are processed
--in when more that 1 huntgroup contends for the same output port.
--table 16x32. f(outPort) = hgList.
---------------------------------------------------------------------------
huntGroupOrderTable OBJECT-TYPE
   SYNTAX      SEQUENCE OF HuntGroupOrderEntry
   ACCESS       not-accessible
   STATUS       mandatory
   DESCRIPTION "This table holds all of the huntgroup order information
            for this  switch. i.e. The order huntgroups are processed 
            in when more than one huntgroup contends for the same output 
            port. 
            FORMAT: OutputPort HuntGroupList
            OutputPort is 0 to 15.
            Huntgroup is 0 to 31.
            List is an ordered list of huntgroups."
   ::= { switchObjs 14 } 

huntGroupOrderEntry OBJECT-TYPE
   SYNTAX      HuntGroupOrderEntry
   ACCESS       not-accessible
   STATUS       mandatory
   DESCRIPTION "One record on an output port's huntgroup priority."
   INDEX      { hg }
   ::= { huntGroupOrderTable 1 }

HuntGroupOrderEntry ::= SEQUENCE
{
   hgOrderIndex   Gauge,         
   hgOrderList      DisplayString (1..80)
}

hgOrderIndex OBJECT-TYPE
   SYNTAX      Gauge
   ACCESS      read-only
   STATUS      mandatory
   DESCRIPTION "The backplane slot number containing output port." 
   ::= { huntGroupOrderEntry 1 } 

hgOrderList OBJECT-TYPE
   SYNTAX      DisplayString 
   ACCESS      read-only
   STATUS      mandatory
   DESCRIPTION "An ordered list of an output port's huntgroup priority.
            FORMAT: OutputPort HuntGroupList
            OutputPort is 0 to 15.
            Huntgroup is 0 to 31.
            List is an ordered list of huntgroups."
   ::= { huntGroupOrderEntry 2 } 

hgOWriteRow OBJECT-TYPE
   SYNTAX      DisplayString 
   ACCESS      read-write
   STATUS      mandatory
   DESCRIPTION "Setting this variable will alter the huntgroup order table. 
   FORMAT: OutputPort HuntGroupList
   Output port is 0 to 15.
   Huntgroup is 0 to 31. Huntgroup must contain output port in its output port list.
   List is NUMBER or NUMBER1-NUMBER2 where NUMBER1 < NUMBER2."
   ::= { switchObjs 15 } 

hgSaveRestore OBJECT-TYPE
   SYNTAX      INTEGER { save(1), restore(2) }
   ACCESS      read-write
   STATUS      mandatory
   DESCRIPTION "
   Writting a 1 saves    all hunt group information on the switch.
   Writting a 2 restores all hunt group information on the switch."
   ::= { switchObjs 16 } 

routesSaveRestore OBJECT-TYPE
   SYNTAX      INTEGER { save(1), restore(2) }
   ACCESS      read-write
   STATUS      mandatory
   DESCRIPTION "
   Writting a 1 saves    all source/destination routes on the switch.
   Writting a 2 restores all source/destination routes on the switch."
   ::= { switchObjs 17 } 

---------------------------------------------------------------------------
---------------------------------------------------------------------------
--The second branch of this MIB that contains the events.
--This is here to easily translate SNMPv1 traps.
---------------------------------------------------------------------------
---------------------------------------------------------------------------
--switchEventsV2       OBJECT IDENTIFIER ::= { switchEvents 0 }
--Sample event
--switchHeapBad    NOTIFICATION-TYPE
--  OBJECTS { }
--   STATUS      mandatory
--   DESCRIPTION "The memory heap in the SCC EEMM is corrupted."
--   ::= { switchEvents 1 }

---------------------------------------------------------------------------
---------------------------------------------------------------------------
--The third branch of this MIB that contains the conformance information 
--in the compliance and group branches. Wait till the MIB is done.
---------------------------------------------------------------------------
---------------------------------------------------------------------------

END
