PANDATEL-FXG-MODEM-MIB DEFINITIONS ::= BEGIN

 -- This is the private mib group section for the FX-G modems.
 -- Because these modems must be installed in the PANDATEL modem rack
 -- the PANDATEL-MODEM-MIB also applies.


 -- Ver.1.00    Oct.17.2000

        IMPORTS
                enterprises
                        FROM RFC1155-SMI
                DisplayString
                        FROM RFC1213-MIB
                OBJECT-TYPE
                        FROM RFC-1212
                mdmSpecifics, device-id
                        FROM PANDATEL-MODEM-MIB;

-- ********************** THE MDM-FXG SUBTREE ******************************

-- the specific identifier is identical to the modem type integer
-- of the FX-G modem entries in the PANDATEL-MODEM-MIB mdmModemTable.

fxg-modem      OBJECT IDENTIFIER ::= { device-id 506 }     -- chassis-mib

fxg            OBJECT IDENTIFIER ::= { mdmSpecifics 506 }  -- this subtree

fxgModemTable OBJECT-TYPE
        SYNTAX  SEQUENCE OF FxgTableEntry
        ACCESS  not-accessible
        STATUS  mandatory
        DESCRIPTION
                "The table of all FX-G modems in this housing."
        ::= { fxg 1 }

fxgTableEntry OBJECT-TYPE
        SYNTAX  FxgTableEntry
        ACCESS  not-accessible
        STATUS  mandatory
        DESCRIPTION
                "The index of the table."
        INDEX   { mdmRack, mdmModem, mdmPosition }
        ::= { fxgModemTable 1 }

FxgTableEntry ::= SEQUENCE {
        mdmRack
                INTEGER,
        mdmModem
                INTEGER,
        mdmPosition
                INTEGER,
        mdmModemName
                DisplayString,
        mdmAlarm
                INTEGER,
        mdmRemoteAccessMode
                INTEGER,
        mdmForcedRemoteAccess
                INTEGER,
        mdmClockRecovery
                INTEGER,
        mdmOperationMode
                INTEGER,
        mdmInterfaceAlarmCondition
                INTEGER,
        mdmLineAlarmCondition
                INTEGER
        }

mdmRack OBJECT-TYPE
        SYNTAX  INTEGER
        ACCESS  read-only
        STATUS  mandatory
        DESCRIPTION
                "The index of the rack where the modem is installed."
        ::= { fxgTableEntry 1 }

mdmModem OBJECT-TYPE
        SYNTAX  INTEGER
        ACCESS  read-only
        STATUS  mandatory
        DESCRIPTION
                "This variable displays the slot number where the
                 corresponding modem is installed in the rack."
        ::= { fxgTableEntry 2 }

mdmPosition OBJECT-TYPE
        SYNTAX  INTEGER {
                local  (1),
                remote (2)
        }
        ACCESS  read-only
        STATUS  mandatory
        DESCRIPTION
                "This variable displays the location of the corresponding
                 modem: 'local' or 'remote'.
                 The modem which is plugged into a managed rack is 'local',
                 the counterpart is 'remote'."
        ::= { fxgTableEntry 3 }

mdmModemName OBJECT-TYPE
        SYNTAX  DisplayString
        ACCESS  read-only
        STATUS  mandatory
        DESCRIPTION
                "A verbal name of this modem."
        ::= { fxgTableEntry 5 }

mdmAlarm OBJECT-TYPE
        SYNTAX  INTEGER {
                other (1),
                off   (2),
                on    (3)
        }
        ACCESS  read-only
        STATUS  mandatory
        DESCRIPTION
                "The status of local alarm: 'off' or 'on'."
        ::= { fxgTableEntry 15 }

mdmRemoteAccessMode OBJECT-TYPE
        SYNTAX  INTEGER {
                other                    (1),
                enable                   (5),
                disable-local            (8),
                disable-local-and-remote (9)
        }
        ACCESS  read-write
        STATUS  mandatory
        DESCRIPTION
               "The possibility of remote management: 'enabled', 'disabled local' 
               or 'disable local and remote'. 
               Once disabled management at local and remote unit, it is not possible 
               to enable it at the remote unit again."
        ::= { fxgTableEntry 64 }

mdmForcedRemoteAccess OBJECT-TYPE
        SYNTAX  INTEGER {
                off (1),
                on  (2)
        }
        ACCESS  read-write
        STATUS  mandatory
        DESCRIPTION
                "Activation of remote management: 'on' or 'off'.
                 Status 'on' enables management of remote unit. During this
                 process the link is restricted to management data. The
                 transmission of user data is interrupted.
                 Status 'off' disables management of remote unit. The link
                 transmits user data."
        ::= { fxgTableEntry 65 }

mdmClockRecovery OBJECT-TYPE
        SYNTAX  INTEGER {
                other                 (1),
                disable               (2),
                gigabit-Ethernet-1250 (6),
                fibre-Channel-1062    (7),
                not-available       (100)
        }
        ACCESS  read-write
        STATUS  mandatory
        DESCRIPTION
                "The clock recovery and data retiming at interface and line port.
                 The remote unit's configuration changes simultaneously."
        ::= { fxgTableEntry 70 }

------------------------------- OperationMode: variable in the agent and modem is 'ConverterMode', 
------------------------------- only the visual part is OperationMode.
mdmOperationMode OBJECT-TYPE
        SYNTAX  INTEGER {
                other          (1),
                modem-mode     (2),
                converter-mode (3)
        }
        ACCESS  read-write
        STATUS  mandatory
        DESCRIPTION
                "The possibility of operation mode: 'converter mode' or 'modem mode'."
        ::= { fxgTableEntry 72 }

mdmInterfaceAlarmCondition OBJECT-TYPE
        SYNTAX  INTEGER {
                other                        (1),
                disable                      (2),
                no-link-signal               (3),
                not-available                (100)
        }
        ACCESS  read-write
        STATUS  mandatory
        DESCRIPTION
                "The alarm trigger mode at interface port: 'disable', i.e. no alarm
                 is triggered, 'no-link-signal', i.e. an alarm is triggered if
                 the link is down."
        ::= { fxgTableEntry 98 }

mdmLineAlarmCondition OBJECT-TYPE
        SYNTAX  INTEGER {
                other                          (1),
                disable                        (2),
                no-link-signal                 (3),
                not-available                  (100)
        }
        ACCESS  read-write
        STATUS  mandatory
        DESCRIPTION
                "The alarm trigger mode at line port: 'disable', i.e. no alarm
                 is triggered, 'no-link-signal', i.e. an alarm is triggered if
                 the link is down."
        ::= { fxgTableEntry 99 }


END
