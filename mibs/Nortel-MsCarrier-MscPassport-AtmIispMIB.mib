Nortel-MsCarrier-MscPassport-AtmIispMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Gauge32,
      Integer32,
      Unsigned32
   FROM Nortel-MsCarrier-MscPassport-StandardTextualConventionsMIB

      Hex,
      NonReplicated,
      HexString,
      AsciiStringIndex
   FROM Nortel-MsCarrier-MscPassport-TextualConventionsMIB

      mscAtmIf,
      mscAtmIfVptIndex,
      mscAtmIfVpt,
      mscAtmIfIndex
   FROM Nortel-MsCarrier-MscPassport-AtmCoreMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     AtmIisp Enterprise MIB."

atmIispMIB OBJECT IDENTIFIER ::= { mscPassportMIBs 70 }










-- AtmIf/n Iisp
-- This component represents an ATM Interim Inter-switch Signaling 
-- Protocol (IISP) interface. If this component is provisioned, the Uni 
-- component can not be provisioned under the same AtmIf 
-- component. If this component is deleted, then all associated Vcc 
-- components are deleted.

mscAtmIfIisp OBJECT IDENTIFIER ::= { mscAtmIf 7 }



mscAtmIfIispRowStatusTable OBJECT-TYPE
   SYNTAX     SEQUENCE OF MscAtmIfIispRowStatusEntry
   ACCESS     not-accessible
   STATUS     mandatory
   DESCRIPTION
     "This entry controls the addition and deletion of 
      mscAtmIfIisp components."
::= { mscAtmIfIisp 1 }

mscAtmIfIispRowStatusEntry OBJECT-TYPE
   SYNTAX     MscAtmIfIispRowStatusEntry
   ACCESS     not-accessible
   STATUS     mandatory
   DESCRIPTION
     "A single entry in the table represents a single 
      mscAtmIfIisp component."
   INDEX {
      mscAtmIfIndex,
      mscAtmIfIispIndex }
::= { mscAtmIfIispRowStatusTable 1 }

MscAtmIfIispRowStatusEntry ::= SEQUENCE {
   mscAtmIfIispRowStatus
      RowStatus,
   mscAtmIfIispComponentName
      DisplayString,
   mscAtmIfIispStorageType
      StorageType,
   mscAtmIfIispIndex
      NonReplicated }

mscAtmIfIispRowStatus OBJECT-TYPE
   SYNTAX     RowStatus 
   ACCESS     read-write
   STATUS     mandatory
   DESCRIPTION
     "This variable is used as the basis for SNMP naming of
      mscAtmIfIisp components.
      These components can be added and deleted."
::= { mscAtmIfIispRowStatusEntry 1 }

mscAtmIfIispComponentName OBJECT-TYPE
   SYNTAX     DisplayString 
   ACCESS     read-only
   STATUS     mandatory
   DESCRIPTION
     "This variable provides the component's string name for
      use with the ASCII Console Interface"
::= { mscAtmIfIispRowStatusEntry 2 }

mscAtmIfIispStorageType OBJECT-TYPE
   SYNTAX     StorageType 
   ACCESS     read-only
   STATUS     mandatory
   DESCRIPTION
     "This variable represents the storage type value for the
      mscAtmIfIisp tables."
::= { mscAtmIfIispRowStatusEntry 4 }

mscAtmIfIispIndex OBJECT-TYPE
   SYNTAX     NonReplicated 
   ACCESS     not-accessible
   STATUS     mandatory
   DESCRIPTION
     "This variable represents the index for the mscAtmIfIisp tables."
::= { mscAtmIfIispRowStatusEntry 10 }

mscAtmIfIispProvTable OBJECT-TYPE
   SYNTAX     SEQUENCE OF MscAtmIfIispProvEntry
   ACCESS     not-accessible
   STATUS     mandatory
   DESCRIPTION
     "This group contains the provisionable attributes for the Iisp 
      component."
::= { mscAtmIfIisp 10 }

mscAtmIfIispProvEntry OBJECT-TYPE
   SYNTAX     MscAtmIfIispProvEntry
   ACCESS     not-accessible
   STATUS     mandatory
   DESCRIPTION
     "An entry in the mscAtmIfIispProvTable."
   INDEX {
      mscAtmIfIndex,
      mscAtmIfIispIndex }
::= { mscAtmIfIispProvTable 1 }

MscAtmIfIispProvEntry ::= SEQUENCE {
   mscAtmIfIispVersion
      INTEGER,
   mscAtmIfIispSide
      INTEGER,
   mscAtmIfIispSoftPvcRetryPeriod
      Unsigned32,
   mscAtmIfIispSoftPvpAndPvcRetryPeriod
      Unsigned32,
   mscAtmIfIispSoftPvpAndPvcHoldOffTime
      Unsigned32 }

mscAtmIfIispVersion OBJECT-TYPE
   SYNTAX     INTEGER  {
                 iisp10Sig30(2),
                 iisp10Sig31(3) }
   ACCESS     read-write
   STATUS     mandatory
   DESCRIPTION
     "This attribute indicates which specification the IISP interface 
      complies with. The options are iisp10Sig30 which refers to IISP 
      version 1.0 with 3.0 signalling and iisp10Sig31 which refers to IISP 
      version 1.0 with 3.1 signalling. If this attribute is changed, all 
      switched Vcc components in this interface are cleared due to the 
      fact that the two versions are incompatible."
   DEFVAL     { iisp10Sig31 }
::= { mscAtmIfIispProvEntry 1 }

mscAtmIfIispSide OBJECT-TYPE
   SYNTAX     INTEGER  {
                 networkSide(0),
                 userSide(1) }
   ACCESS     read-write
   STATUS     mandatory
   DESCRIPTION
     "This attribute indicates which side the interface is, user or network."
   DEFVAL     { networkSide }
::= { mscAtmIfIispProvEntry 2 }

mscAtmIfIispSoftPvcRetryPeriod OBJECT-TYPE
   SYNTAX     Unsigned32 (20..999999)
   ACCESS     read-write
   STATUS     obsolete
   DESCRIPTION
     "This attribute specifies the time to wait between call set up retries. 
      The resolution is to the nearest 10 seconds.
      This attribute has been obsoleted and is replaced by the 
      softPvpAndPvcRetryPeriod attribute."
   DEFVAL     { 60 }
::= { mscAtmIfIispProvEntry 3 }

mscAtmIfIispSoftPvpAndPvcRetryPeriod OBJECT-TYPE
   SYNTAX     Unsigned32 (20..999999)
   ACCESS     read-write
   STATUS     mandatory
   DESCRIPTION
     "This attribute specifies the time to wait between soft PVP or soft 
      PVC call setup retries. The resolution is to the nearest 10 seconds."
   DEFVAL     { 60 }
::= { mscAtmIfIispProvEntry 4 }

mscAtmIfIispSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { mscAtmIfIispProvEntry 5 }

mscAtmIfIispAcctOptTable OBJECT-TYPE
   SYNTAX     SEQUENCE OF MscAtmIfIispAcctOptEntry
   ACCESS     not-accessible
   STATUS     mandatory
   DESCRIPTION
     "This group contains the provisionable attributes for accounting."
::= { mscAtmIfIisp 11 }

mscAtmIfIispAcctOptEntry OBJECT-TYPE
   SYNTAX     MscAtmIfIispAcctOptEntry
   ACCESS     not-accessible
   STATUS     mandatory
   DESCRIPTION
     "An entry in the mscAtmIfIispAcctOptTable."
   INDEX {
      mscAtmIfIndex,
      mscAtmIfIispIndex }
::= { mscAtmIfIispAcctOptTable 1 }

MscAtmIfIispAcctOptEntry ::= SEQUENCE {
   mscAtmIfIispAccountCollection
      OCTET STRING,
   mscAtmIfIispAccountConnectionType
      INTEGER,
   mscAtmIfIispAccountClass
      Unsigned32,
   mscAtmIfIispServiceExchange
      Unsigned32 }

mscAtmIfIispAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit, or force.
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { mscAtmIfIispAcctOptEntry 1 }

mscAtmIfIispAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { intermediate }
::= { mscAtmIfIispAcctOptEntry 2 }

mscAtmIfIispAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { mscAtmIfIispAcctOptEntry 3 }

mscAtmIfIispServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { mscAtmIfIispAcctOptEntry 4 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

mscAtmIfIispSig OBJECT IDENTIFIER ::= { mscAtmIfIisp 3 }



mscAtmIfIispSigRowStatusTable OBJECT-TYPE
   SYNTAX     SEQUENCE OF MscAtmIfIispSigRowStatusEntry
   ACCESS     not-accessible
   STATUS     mandatory
   DESCRIPTION
     "This entry controls the addition and deletion of 
      mscAtmIfIispSig components."
::= { mscAtmIfIispSig 1 }

mscAtmIfIispSigRowStatusEntry OBJECT-TYPE
   SYNTAX     MscAtmIfIispSigRowStatusEntry
   ACCESS     not-accessible
   STATUS     mandatory
   DESCRIPTION
     "A single entry in the table represents a single 
      mscAtmIfIispSig component."
   INDEX {
      mscAtmIfIndex,
      mscAtmIfIispIndex,
      mscAtmIfIispSigIndex }
::= { mscAtmIfIispSigRowStatusTable 1 }

MscAtmIfIispSigRowStatusEntry ::= SEQUENCE {
   mscAtmIfIispSigRowStatus
      RowStatus,
   mscAtmIfIispSigComponentName
      DisplayString,
   mscAtmIfIispSigStorageType
      StorageType,
   mscAtmIfIispSigIndex
      NonReplicated }

mscAtmIfIispSigRowStatus OBJECT-TYPE
   SYNTAX     RowStatus 
   ACCESS     read-only
   STATUS     mandatory
   DESCRIPTION
     "This variable is used as the basis for SNMP naming of
      mscAtmIfIispSig components.
      These components cannot be added nor deleted."
::= { mscAtmIfIispSigRowStatusEntry 1 }

mscAtmIfIispSigComponentName OBJECT-TYPE
   SYNTAX     DisplayString 
   ACCESS     read-only
   STATUS     mandatory
   DESCRIPTION
     "This variable provides the component's string name for
      use with the ASCII Console Interface"
::= { mscAtmIfIispSigRowStatusEntry 2 }

mscAtmIfIispSigStorageType OBJECT-TYPE
   SYNTAX     StorageType 
   ACCESS     read-only
   STATUS     mandatory
   DESCRIPTION
     "This variable represents the storage type value for the
      mscAtmIfIispSig tables."
::= { mscAtmIfIispSigRowStatusEntry 4 }

mscAtmIfIispSigIndex OBJECT-TYPE
   SYNTAX     NonReplicated 
   ACCESS     not-accessible
   STATUS     mandatory
   DESCRIPTION
     "This variable represents the index for the mscAtmIfIispSig tables."
::= { mscAtmIfIispSigRowStatusEntry 10 }

mscAtmIfIispSigProvTable OBJECT-TYPE
   SYNTAX     SEQUENCE OF MscAtmIfIispSigProvEntry
   ACCESS     not-accessible
   STATUS     mandatory
   DESCRIPTION
     "This attribute group contains the provisionable attributes for the 
      Signalling component."
::= { mscAtmIfIispSig 10 }

mscAtmIfIispSigProvEntry OBJECT-TYPE
   SYNTAX     MscAtmIfIispSigProvEntry
   ACCESS     not-accessible
   STATUS     mandatory
   DESCRIPTION
     "An entry in the mscAtmIfIispSigProvTable."
   INDEX {
      mscAtmIfIndex,
      mscAtmIfIispIndex,
      mscAtmIfIispSigIndex }
::= { mscAtmIfIispSigProvTable 1 }

MscAtmIfIispSigProvEntry ::= SEQUENCE {
   mscAtmIfIispSigVci
      Unsigned32,
   mscAtmIfIispSigAddressConversion
      INTEGER,
   mscAtmIfIispSigOperatingMode
      INTEGER }

mscAtmIfIispSigVci OBJECT-TYPE
   SYNTAX     Unsigned32 (0..65535)
   ACCESS     read-write
   STATUS     mandatory
   DESCRIPTION
     "This attribute specifies the signalling channel number."
   DEFVAL     { 5 }
::= { mscAtmIfIispSigProvEntry 1 }

mscAtmIfIispSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { mscAtmIfIispSigProvEntry 2 }

mscAtmIfIispSigOperatingMode OBJECT-TYPE
   SYNTAX     INTEGER  {
                 normal(0),
                 provisionedOnly(1) }
   ACCESS     read-write
   STATUS     mandatory
   DESCRIPTION
     "This attribute specifies the operating mode of the signaling channel. 				
      provisionedOnly indicates that only SPVCs and SPVPs are 
      supported on the interface and SVCs are not supported. This value 
      is permitted only on UNI interfaces.
      normal indicates that SVCs, SPVCs, and SPVPs are supported on 
      the interface."
   DEFVAL     { normal }
::= { mscAtmIfIispSigProvEntry 3 }

mscAtmIfIispSigStateTable OBJECT-TYPE
   SYNTAX     SEQUENCE OF MscAtmIfIispSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmIfIispSig 11 }

mscAtmIfIispSigStateEntry OBJECT-TYPE
   SYNTAX     MscAtmIfIispSigStateEntry
   ACCESS     not-accessible
   STATUS     mandatory
   DESCRIPTION
     "An entry in the mscAtmIfIispSigStateTable."
   INDEX {
      mscAtmIfIndex,
      mscAtmIfIispIndex,
      mscAtmIfIispSigIndex }
::= { mscAtmIfIispSigStateTable 1 }

MscAtmIfIispSigStateEntry ::= SEQUENCE {
   mscAtmIfIispSigAdminState
      INTEGER,
   mscAtmIfIispSigOperationalState
      INTEGER,
   mscAtmIfIispSigUsageState
      INTEGER }

mscAtmIfIispSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfIispSigStateEntry 1 }

mscAtmIfIispSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfIispSigStateEntry 2 }

mscAtmIfIispSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfIispSigStateEntry 3 }

mscAtmIfIispSigOperTable OBJECT-TYPE
   SYNTAX     SEQUENCE OF MscAtmIfIispSigOperEntry
   ACCESS     not-accessible
   STATUS     mandatory
   DESCRIPTION
     "This attribute contains the operational attributes for the 
      AtmSignalling component."
::= { mscAtmIfIispSig 12 }

mscAtmIfIispSigOperEntry OBJECT-TYPE
   SYNTAX     MscAtmIfIispSigOperEntry
   ACCESS     not-accessible
   STATUS     mandatory
   DESCRIPTION
     "An entry in the mscAtmIfIispSigOperTable."
   INDEX {
      mscAtmIfIndex,
      mscAtmIfIispIndex,
      mscAtmIfIispSigIndex }
::= { mscAtmIfIispSigOperTable 1 }

MscAtmIfIispSigOperEntry ::= SEQUENCE {
   mscAtmIfIispSigLastTxCauseCode
      Unsigned32,
   mscAtmIfIispSigLastTxDiagCode
      Hex,
   mscAtmIfIispSigLastRxCauseCode
      Unsigned32,
   mscAtmIfIispSigLastRxDiagCode
      Hex }

mscAtmIfIispSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { mscAtmIfIispSigOperEntry 1 }

mscAtmIfIispSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfIispSigOperEntry 2 }

mscAtmIfIispSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { mscAtmIfIispSigOperEntry 3 }

mscAtmIfIispSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfIispSigOperEntry 4 }

mscAtmIfIispSigStatsTable OBJECT-TYPE
   SYNTAX     SEQUENCE OF MscAtmIfIispSigStatsEntry
   ACCESS     not-accessible
   STATUS     mandatory
   DESCRIPTION
     "This attribute group contains the statistics associated with the 
      AtmSignalling component."
::= { mscAtmIfIispSig 13 }

mscAtmIfIispSigStatsEntry OBJECT-TYPE
   SYNTAX     MscAtmIfIispSigStatsEntry
   ACCESS     not-accessible
   STATUS     mandatory
   DESCRIPTION
     "An entry in the mscAtmIfIispSigStatsTable."
   INDEX {
      mscAtmIfIndex,
      mscAtmIfIispIndex,
      mscAtmIfIispSigIndex }
::= { mscAtmIfIispSigStatsTable 1 }

MscAtmIfIispSigStatsEntry ::= SEQUENCE {
   mscAtmIfIispSigCurrentConnections
      Counter32,
   mscAtmIfIispSigPeakConnections
      Gauge32,
   mscAtmIfIispSigSuccessfulConnections
      Counter32,
   mscAtmIfIispSigFailedConnections
      Counter32,
   mscAtmIfIispSigTxPdus
      Counter32,
   mscAtmIfIispSigRxPdus
      Counter32,
   mscAtmIfIispSigCurrentPmpConnections
      Gauge32,
   mscAtmIfIispSigPeakPmpConnections
      Gauge32,
   mscAtmIfIispSigSuccessfulPmpConnections
      Counter32,
   mscAtmIfIispSigFailedPmpConnections
      Counter32,
   mscAtmIfIispSigNewCurrentConnections
      Gauge32 }

mscAtmIfIispSigCurrentConnections OBJECT-TYPE
   SYNTAX     Counter32 
   ACCESS     read-only
   STATUS     obsolete
   DESCRIPTION
     "This attribute indicates the total number of currently active 
      connections."
::= { mscAtmIfIispSigStatsEntry 1 }

mscAtmIfIispSigPeakConnections OBJECT-TYPE
   SYNTAX     Gauge32 (0..4294967295)
   ACCESS     read-only
   STATUS     mandatory
   DESCRIPTION
     "This attribute indicates the high water mark of active point-to-
      point and point-to-multipoint connections."
::= { mscAtmIfIispSigStatsEntry 2 }

mscAtmIfIispSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { mscAtmIfIispSigStatsEntry 3 }

mscAtmIfIispSigFailedConnections OBJECT-TYPE
   SYNTAX     Counter32 
   ACCESS     read-only
   STATUS     mandatory
   DESCRIPTION
     "This attribute counts the total number of switched connections that 
      were not successfully established.The counter wraps to 0 when the 
      maximum value is exceeded."
::= { mscAtmIfIispSigStatsEntry 4 }

mscAtmIfIispSigTxPdus OBJECT-TYPE
   SYNTAX     Counter32 
   ACCESS     read-only
   STATUS     mandatory
   DESCRIPTION
     "This attribute counts the number of transmitted signalling 
      PDUs.The counter wraps to 0 when the maximum value is 
      exceeded."
::= { mscAtmIfIispSigStatsEntry 5 }

mscAtmIfIispSigRxPdus OBJECT-TYPE
   SYNTAX     Counter32 
   ACCESS     read-only
   STATUS     mandatory
   DESCRIPTION
     "This attribute counts the number of received signalling PDUs.The 
      counter wraps to 0 when the maximum value is exceeded."
::= { mscAtmIfIispSigStatsEntry 6 }

mscAtmIfIispSigCurrentPmpConnections OBJECT-TYPE
   SYNTAX     Gauge32 (0..4294967295)
   ACCESS     read-only
   STATUS     mandatory
   DESCRIPTION
     "This attribute indicates the number of currently active point-to-
      multipoint connections."
::= { mscAtmIfIispSigStatsEntry 7 }

mscAtmIfIispSigPeakPmpConnections OBJECT-TYPE
   SYNTAX     Gauge32 (0..4294967295)
   ACCESS     read-only
   STATUS     mandatory
   DESCRIPTION
     "This attribute indicates the high water mark of active point-to-
      multipoint connections."
::= { mscAtmIfIispSigStatsEntry 8 }

mscAtmIfIispSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { mscAtmIfIispSigStatsEntry 9 }

mscAtmIfIispSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { mscAtmIfIispSigStatsEntry 10 }

mscAtmIfIispSigNewCurrentConnections OBJECT-TYPE
   SYNTAX     Gauge32 (0..4294967295)
   ACCESS     read-only
   STATUS     mandatory
   DESCRIPTION
     "This attribute indicates the total number of currently active point-to-
      point and point-to-multipoint connections."
::= { mscAtmIfIispSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

mscAtmIfIispSigVcd OBJECT IDENTIFIER ::= { mscAtmIfIispSig 2 }



mscAtmIfIispSigVcdRowStatusTable OBJECT-TYPE
   SYNTAX     SEQUENCE OF MscAtmIfIispSigVcdRowStatusEntry
   ACCESS     not-accessible
   STATUS     mandatory
   DESCRIPTION
     "This entry controls the addition and deletion of 
      mscAtmIfIispSigVcd components."
::= { mscAtmIfIispSigVcd 1 }

mscAtmIfIispSigVcdRowStatusEntry OBJECT-TYPE
   SYNTAX     MscAtmIfIispSigVcdRowStatusEntry
   ACCESS     not-accessible
   STATUS     mandatory
   DESCRIPTION
     "A single entry in the table represents a single 
      mscAtmIfIispSigVcd component."
   INDEX {
      mscAtmIfIndex,
      mscAtmIfIispIndex,
      mscAtmIfIispSigIndex,
      mscAtmIfIispSigVcdIndex }
::= { mscAtmIfIispSigVcdRowStatusTable 1 }

MscAtmIfIispSigVcdRowStatusEntry ::= SEQUENCE {
   mscAtmIfIispSigVcdRowStatus
      RowStatus,
   mscAtmIfIispSigVcdComponentName
      DisplayString,
   mscAtmIfIispSigVcdStorageType
      StorageType,
   mscAtmIfIispSigVcdIndex
      NonReplicated }

mscAtmIfIispSigVcdRowStatus OBJECT-TYPE
   SYNTAX     RowStatus 
   ACCESS     read-write
   STATUS     mandatory
   DESCRIPTION
     "This variable is used as the basis for SNMP naming of
      mscAtmIfIispSigVcd components.
      These components can be added and deleted."
::= { mscAtmIfIispSigVcdRowStatusEntry 1 }

mscAtmIfIispSigVcdComponentName OBJECT-TYPE
   SYNTAX     DisplayString 
   ACCESS     read-only
   STATUS     mandatory
   DESCRIPTION
     "This variable provides the component's string name for
      use with the ASCII Console Interface"
::= { mscAtmIfIispSigVcdRowStatusEntry 2 }

mscAtmIfIispSigVcdStorageType OBJECT-TYPE
   SYNTAX     StorageType 
   ACCESS     read-only
   STATUS     mandatory
   DESCRIPTION
     "This variable represents the storage type value for the
      mscAtmIfIispSigVcd tables."
::= { mscAtmIfIispSigVcdRowStatusEntry 4 }

mscAtmIfIispSigVcdIndex OBJECT-TYPE
   SYNTAX     NonReplicated 
   ACCESS     not-accessible
   STATUS     mandatory
   DESCRIPTION
     "This variable represents the index for the mscAtmIfIispSigVcd tables."
::= { mscAtmIfIispSigVcdRowStatusEntry 10 }

mscAtmIfIispSigVcdProvTable OBJECT-TYPE
   SYNTAX     SEQUENCE OF MscAtmIfIispSigVcdProvEntry
   ACCESS     not-accessible
   STATUS     mandatory
   DESCRIPTION
     "This group contains the provisionable traffic attributes for a control 
      channel."
::= { mscAtmIfIispSigVcd 10 }

mscAtmIfIispSigVcdProvEntry OBJECT-TYPE
   SYNTAX     MscAtmIfIispSigVcdProvEntry
   ACCESS     not-accessible
   STATUS     mandatory
   DESCRIPTION
     "An entry in the mscAtmIfIispSigVcdProvTable."
   INDEX {
      mscAtmIfIndex,
      mscAtmIfIispIndex,
      mscAtmIfIispSigIndex,
      mscAtmIfIispSigVcdIndex }
::= { mscAtmIfIispSigVcdProvTable 1 }

MscAtmIfIispSigVcdProvEntry ::= SEQUENCE {
   mscAtmIfIispSigVcdTrafficDescType
      INTEGER,
   mscAtmIfIispSigVcdAtmServiceCategory
      INTEGER,
   mscAtmIfIispSigVcdWeight
      Unsigned32,
   mscAtmIfIispSigVcdQosClass
      INTEGER,
   mscAtmIfIispSigVcdTrafficShaping
      INTEGER,
   mscAtmIfIispSigVcdUnshapedTransmitQueueing
      INTEGER,
   mscAtmIfIispSigVcdUsageParameterControl
      INTEGER }

mscAtmIfIispSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { mscAtmIfIispSigVcdProvEntry 1 }

mscAtmIfIispSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { mscAtmIfIispSigVcdProvEntry 3 }

mscAtmIfIispSigVcdWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic VPTs. 
      
      When the value is set to sameAsCa, the weight is determined by the 
      weight policy attribute under the CA service category component 
      for all but standard VPT VCCs. For standard VPT VCCs, the 
      weight is determined by the VCC's service category, when the value 
      is set to sameAsCa.
      
      When this attribute is set to a value from 1 to 4095, that value is 
      used for the weight policy of this connection relative to other 
      connections. For all but standard VPT VCCs, weight policy 
      determines the proportion of transit cell opportunities which are 
      allocated to this connection, compared to other connections in the 
      same service category. For standard VPT VCCs, weight policy 
      determines the proportion of transmit cell opportunities which are 
      allocated to this connection, compared to other connections 
      associated with the VPT.
      
      When the value is set to upToQueueLimit, the weight policy is 
      limited only by the txQueueLimit.

      VALUES (

      0 = upToQueueLimit

      65535 = sameAsCa

      )"
   DEFVAL     { 65535 }
::= { mscAtmIfIispSigVcdProvEntry 4 }

mscAtmIfIispSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { mscAtmIfIispSigVcdProvEntry 21 }

mscAtmIfIispSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { mscAtmIfIispSigVcdProvEntry 50 }

mscAtmIfIispSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { mscAtmIfIispSigVcdProvEntry 60 }

mscAtmIfIispSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { mscAtmIfIispSigVcdProvEntry 70 }

mscAtmIfIispSigVcdTdpTable OBJECT-TYPE
   SYNTAX     SEQUENCE OF MscAtmIfIispSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { mscAtmIfIispSigVcd 387 }

mscAtmIfIispSigVcdTdpEntry OBJECT-TYPE
   SYNTAX     MscAtmIfIispSigVcdTdpEntry
   ACCESS     not-accessible
   STATUS     mandatory
   DESCRIPTION
     "An entry in the mscAtmIfIispSigVcdTdpTable."
   INDEX {
      mscAtmIfIndex,
      mscAtmIfIispIndex,
      mscAtmIfIispSigIndex,
      mscAtmIfIispSigVcdIndex,
      mscAtmIfIispSigVcdTdpIndex }
::= { mscAtmIfIispSigVcdTdpTable 1 }

MscAtmIfIispSigVcdTdpEntry ::= SEQUENCE {
   mscAtmIfIispSigVcdTdpIndex
      Integer32,
   mscAtmIfIispSigVcdTdpValue
      Unsigned32 }

mscAtmIfIispSigVcdTdpIndex OBJECT-TYPE
   SYNTAX     Integer32 (1..5)
   ACCESS     not-accessible
   STATUS     mandatory
   DESCRIPTION
     "This variable represents the mscAtmIfIispSigVcdTdpTable
      specific index for the mscAtmIfIispSigVcdTdpTable."
::= { mscAtmIfIispSigVcdTdpEntry 1 }

mscAtmIfIispSigVcdTdpValue OBJECT-TYPE
   SYNTAX     Unsigned32 (0..2147483647)
   ACCESS     read-write
   STATUS     mandatory
   DESCRIPTION
     "This variable represents an individual value for the
      mscAtmIfIispSigVcdTdpTable."
::= { mscAtmIfIispSigVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

mscAtmIfIispAddr OBJECT IDENTIFIER ::= { mscAtmIfIisp 4 }



mscAtmIfIispAddrRowStatusTable OBJECT-TYPE
   SYNTAX     SEQUENCE OF MscAtmIfIispAddrRowStatusEntry
   ACCESS     not-accessible
   STATUS     mandatory
   DESCRIPTION
     "This entry controls the addition and deletion of 
      mscAtmIfIispAddr components."
::= { mscAtmIfIispAddr 1 }

mscAtmIfIispAddrRowStatusEntry OBJECT-TYPE
   SYNTAX     MscAtmIfIispAddrRowStatusEntry
   ACCESS     not-accessible
   STATUS     mandatory
   DESCRIPTION
     "A single entry in the table represents a single 
      mscAtmIfIispAddr component."
   INDEX {
      mscAtmIfIndex,
      mscAtmIfIispIndex,
      mscAtmIfIispAddrAddressIndex,
      mscAtmIfIispAddrAddressTypeIndex }
::= { mscAtmIfIispAddrRowStatusTable 1 }

MscAtmIfIispAddrRowStatusEntry ::= SEQUENCE {
   mscAtmIfIispAddrRowStatus
      RowStatus,
   mscAtmIfIispAddrComponentName
      DisplayString,
   mscAtmIfIispAddrStorageType
      StorageType,
   mscAtmIfIispAddrAddressIndex
      AsciiStringIndex,
   mscAtmIfIispAddrAddressTypeIndex
      INTEGER }

mscAtmIfIispAddrRowStatus OBJECT-TYPE
   SYNTAX     RowStatus 
   ACCESS     read-write
   STATUS     mandatory
   DESCRIPTION
     "This variable is used as the basis for SNMP naming of
      mscAtmIfIispAddr components.
      These components can be added and deleted."
::= { mscAtmIfIispAddrRowStatusEntry 1 }

mscAtmIfIispAddrComponentName OBJECT-TYPE
   SYNTAX     DisplayString 
   ACCESS     read-only
   STATUS     mandatory
   DESCRIPTION
     "This variable provides the component's string name for
      use with the ASCII Console Interface"
::= { mscAtmIfIispAddrRowStatusEntry 2 }

mscAtmIfIispAddrStorageType OBJECT-TYPE
   SYNTAX     StorageType 
   ACCESS     read-only
   STATUS     mandatory
   DESCRIPTION
     "This variable represents the storage type value for the
      mscAtmIfIispAddr tables."
::= { mscAtmIfIispAddrRowStatusEntry 4 }

mscAtmIfIispAddrAddressIndex OBJECT-TYPE
   SYNTAX     AsciiStringIndex (SIZE (1..40))
   ACCESS     not-accessible
   STATUS     mandatory
   DESCRIPTION
     "This variable represents an index for the mscAtmIfIispAddr tables."
::= { mscAtmIfIispAddrRowStatusEntry 10 }

mscAtmIfIispAddrAddressTypeIndex OBJECT-TYPE
   SYNTAX     INTEGER  {
                 primary(0),
                 alternate(1),
                 default(3) }
   ACCESS     not-accessible
   STATUS     mandatory
   DESCRIPTION
     "This variable represents an index for the mscAtmIfIispAddr tables."
::= { mscAtmIfIispAddrRowStatusEntry 11 }

mscAtmIfIispAddrOperTable OBJECT-TYPE
   SYNTAX     SEQUENCE OF MscAtmIfIispAddrOperEntry
   ACCESS     not-accessible
   STATUS     mandatory
   DESCRIPTION
     "This attribute group contains the operational attributes for the 
      Address component."
::= { mscAtmIfIispAddr 10 }

mscAtmIfIispAddrOperEntry OBJECT-TYPE
   SYNTAX     MscAtmIfIispAddrOperEntry
   ACCESS     not-accessible
   STATUS     mandatory
   DESCRIPTION
     "An entry in the mscAtmIfIispAddrOperTable."
   INDEX {
      mscAtmIfIndex,
      mscAtmIfIispIndex,
      mscAtmIfIispAddrAddressIndex,
      mscAtmIfIispAddrAddressTypeIndex }
::= { mscAtmIfIispAddrOperTable 1 }

MscAtmIfIispAddrOperEntry ::= SEQUENCE {
   mscAtmIfIispAddrScope
      INTEGER,
   mscAtmIfIispAddrReachability
      INTEGER }

mscAtmIfIispAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { mscAtmIfIispAddrOperEntry 1 }

mscAtmIfIispAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { mscAtmIfIispAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

mscAtmIfIispAddrTermSP OBJECT IDENTIFIER ::= { mscAtmIfIispAddr 2 }



mscAtmIfIispAddrTermSPRowStatusTable OBJECT-TYPE
   SYNTAX     SEQUENCE OF MscAtmIfIispAddrTermSPRowStatusEntry
   ACCESS     not-accessible
   STATUS     mandatory
   DESCRIPTION
     "This entry controls the addition and deletion of 
      mscAtmIfIispAddrTermSP components."
::= { mscAtmIfIispAddrTermSP 1 }

mscAtmIfIispAddrTermSPRowStatusEntry OBJECT-TYPE
   SYNTAX     MscAtmIfIispAddrTermSPRowStatusEntry
   ACCESS     not-accessible
   STATUS     mandatory
   DESCRIPTION
     "A single entry in the table represents a single 
      mscAtmIfIispAddrTermSP component."
   INDEX {
      mscAtmIfIndex,
      mscAtmIfIispIndex,
      mscAtmIfIispAddrAddressIndex,
      mscAtmIfIispAddrAddressTypeIndex,
      mscAtmIfIispAddrTermSPIndex }
::= { mscAtmIfIispAddrTermSPRowStatusTable 1 }

MscAtmIfIispAddrTermSPRowStatusEntry ::= SEQUENCE {
   mscAtmIfIispAddrTermSPRowStatus
      RowStatus,
   mscAtmIfIispAddrTermSPComponentName
      DisplayString,
   mscAtmIfIispAddrTermSPStorageType
      StorageType,
   mscAtmIfIispAddrTermSPIndex
      NonReplicated }

mscAtmIfIispAddrTermSPRowStatus OBJECT-TYPE
   SYNTAX     RowStatus 
   ACCESS     read-write
   STATUS     mandatory
   DESCRIPTION
     "This variable is used as the basis for SNMP naming of
      mscAtmIfIispAddrTermSP components.
      These components can be added and deleted."
::= { mscAtmIfIispAddrTermSPRowStatusEntry 1 }

mscAtmIfIispAddrTermSPComponentName OBJECT-TYPE
   SYNTAX     DisplayString 
   ACCESS     read-only
   STATUS     mandatory
   DESCRIPTION
     "This variable provides the component's string name for
      use with the ASCII Console Interface"
::= { mscAtmIfIispAddrTermSPRowStatusEntry 2 }

mscAtmIfIispAddrTermSPStorageType OBJECT-TYPE
   SYNTAX     StorageType 
   ACCESS     read-only
   STATUS     mandatory
   DESCRIPTION
     "This variable represents the storage type value for the
      mscAtmIfIispAddrTermSP tables."
::= { mscAtmIfIispAddrTermSPRowStatusEntry 4 }

mscAtmIfIispAddrTermSPIndex OBJECT-TYPE
   SYNTAX     NonReplicated 
   ACCESS     not-accessible
   STATUS     mandatory
   DESCRIPTION
     "This variable represents the index for the mscAtmIfIispAddrTermSP tables."
::= { mscAtmIfIispAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

mscAtmIfIispAddrPnniInfo OBJECT IDENTIFIER ::= { mscAtmIfIispAddr 3 }



mscAtmIfIispAddrPnniInfoRowStatusTable OBJECT-TYPE
   SYNTAX     SEQUENCE OF MscAtmIfIispAddrPnniInfoRowStatusEntry
   ACCESS     not-accessible
   STATUS     mandatory
   DESCRIPTION
     "This entry controls the addition and deletion of 
      mscAtmIfIispAddrPnniInfo components."
::= { mscAtmIfIispAddrPnniInfo 1 }

mscAtmIfIispAddrPnniInfoRowStatusEntry OBJECT-TYPE
   SYNTAX     MscAtmIfIispAddrPnniInfoRowStatusEntry
   ACCESS     not-accessible
   STATUS     mandatory
   DESCRIPTION
     "A single entry in the table represents a single 
      mscAtmIfIispAddrPnniInfo component."
   INDEX {
      mscAtmIfIndex,
      mscAtmIfIispIndex,
      mscAtmIfIispAddrAddressIndex,
      mscAtmIfIispAddrAddressTypeIndex,
      mscAtmIfIispAddrPnniInfoIndex }
::= { mscAtmIfIispAddrPnniInfoRowStatusTable 1 }

MscAtmIfIispAddrPnniInfoRowStatusEntry ::= SEQUENCE {
   mscAtmIfIispAddrPnniInfoRowStatus
      RowStatus,
   mscAtmIfIispAddrPnniInfoComponentName
      DisplayString,
   mscAtmIfIispAddrPnniInfoStorageType
      StorageType,
   mscAtmIfIispAddrPnniInfoIndex
      NonReplicated }

mscAtmIfIispAddrPnniInfoRowStatus OBJECT-TYPE
   SYNTAX     RowStatus 
   ACCESS     read-write
   STATUS     mandatory
   DESCRIPTION
     "This variable is used as the basis for SNMP naming of
      mscAtmIfIispAddrPnniInfo components.
      These components can be added and deleted."
::= { mscAtmIfIispAddrPnniInfoRowStatusEntry 1 }

mscAtmIfIispAddrPnniInfoComponentName OBJECT-TYPE
   SYNTAX     DisplayString 
   ACCESS     read-only
   STATUS     mandatory
   DESCRIPTION
     "This variable provides the component's string name for
      use with the ASCII Console Interface"
::= { mscAtmIfIispAddrPnniInfoRowStatusEntry 2 }

mscAtmIfIispAddrPnniInfoStorageType OBJECT-TYPE
   SYNTAX     StorageType 
   ACCESS     read-only
   STATUS     mandatory
   DESCRIPTION
     "This variable represents the storage type value for the
      mscAtmIfIispAddrPnniInfo tables."
::= { mscAtmIfIispAddrPnniInfoRowStatusEntry 4 }

mscAtmIfIispAddrPnniInfoIndex OBJECT-TYPE
   SYNTAX     NonReplicated 
   ACCESS     not-accessible
   STATUS     mandatory
   DESCRIPTION
     "This variable represents the index for the mscAtmIfIispAddrPnniInfo tables."
::= { mscAtmIfIispAddrPnniInfoRowStatusEntry 10 }

mscAtmIfIispAddrPnniInfoProvTable OBJECT-TYPE
   SYNTAX     SEQUENCE OF MscAtmIfIispAddrPnniInfoProvEntry
   ACCESS     not-accessible
   STATUS     mandatory
   DESCRIPTION
     "This attribute group contains the provisioned attributes relating to 
      PNNI for a PnniInfo component."
::= { mscAtmIfIispAddrPnniInfo 10 }

mscAtmIfIispAddrPnniInfoProvEntry OBJECT-TYPE
   SYNTAX     MscAtmIfIispAddrPnniInfoProvEntry
   ACCESS     not-accessible
   STATUS     mandatory
   DESCRIPTION
     "An entry in the mscAtmIfIispAddrPnniInfoProvTable."
   INDEX {
      mscAtmIfIndex,
      mscAtmIfIispIndex,
      mscAtmIfIispAddrAddressIndex,
      mscAtmIfIispAddrAddressTypeIndex,
      mscAtmIfIispAddrPnniInfoIndex }
::= { mscAtmIfIispAddrPnniInfoProvTable 1 }

MscAtmIfIispAddrPnniInfoProvEntry ::= SEQUENCE {
   mscAtmIfIispAddrPnniInfoScope
      INTEGER,
   mscAtmIfIispAddrPnniInfoReachability
      INTEGER }

mscAtmIfIispAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { mscAtmIfIispAddrPnniInfoProvEntry 1 }

mscAtmIfIispAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { mscAtmIfIispAddrPnniInfoProvEntry 2 }


-- AtmIf/n Uni CallingAddressScreening
-- AtmIf/n Iisp CallingAddressScreening
-- This component represents the screening of incoming ATM SVC 
-- call requests against provisioned ATM calling addresses (that is, 
-- screening SVC calls coming from specific addresses). If this 
-- component is not provisioned, all call requests are accepted and no 
-- calling address screening takes place. 

mscAtmIfIispCallingAScr OBJECT IDENTIFIER ::= { mscAtmIfIisp 5 }



mscAtmIfIispCallingAScrRowStatusTable OBJECT-TYPE
   SYNTAX     SEQUENCE OF MscAtmIfIispCallingAScrRowStatusEntry
   ACCESS     not-accessible
   STATUS     mandatory
   DESCRIPTION
     "This entry controls the addition and deletion of 
      mscAtmIfIispCallingAScr components."
::= { mscAtmIfIispCallingAScr 1 }

mscAtmIfIispCallingAScrRowStatusEntry OBJECT-TYPE
   SYNTAX     MscAtmIfIispCallingAScrRowStatusEntry
   ACCESS     not-accessible
   STATUS     mandatory
   DESCRIPTION
     "A single entry in the table represents a single 
      mscAtmIfIispCallingAScr component."
   INDEX {
      mscAtmIfIndex,
      mscAtmIfIispIndex,
      mscAtmIfIispCallingAScrIndex }
::= { mscAtmIfIispCallingAScrRowStatusTable 1 }

MscAtmIfIispCallingAScrRowStatusEntry ::= SEQUENCE {
   mscAtmIfIispCallingAScrRowStatus
      RowStatus,
   mscAtmIfIispCallingAScrComponentName
      DisplayString,
   mscAtmIfIispCallingAScrStorageType
      StorageType,
   mscAtmIfIispCallingAScrIndex
      NonReplicated }

mscAtmIfIispCallingAScrRowStatus OBJECT-TYPE
   SYNTAX     RowStatus 
   ACCESS     read-write
   STATUS     mandatory
   DESCRIPTION
     "This variable is used as the basis for SNMP naming of
      mscAtmIfIispCallingAScr components.
      These components can be added and deleted."
::= { mscAtmIfIispCallingAScrRowStatusEntry 1 }

mscAtmIfIispCallingAScrComponentName OBJECT-TYPE
   SYNTAX     DisplayString 
   ACCESS     read-only
   STATUS     mandatory
   DESCRIPTION
     "This variable provides the component's string name for
      use with the ASCII Console Interface"
::= { mscAtmIfIispCallingAScrRowStatusEntry 2 }

mscAtmIfIispCallingAScrStorageType OBJECT-TYPE
   SYNTAX     StorageType 
   ACCESS     read-only
   STATUS     mandatory
   DESCRIPTION
     "This variable represents the storage type value for the
      mscAtmIfIispCallingAScr tables."
::= { mscAtmIfIispCallingAScrRowStatusEntry 4 }

mscAtmIfIispCallingAScrIndex OBJECT-TYPE
   SYNTAX     NonReplicated 
   ACCESS     not-accessible
   STATUS     mandatory
   DESCRIPTION
     "This variable represents the index for the mscAtmIfIispCallingAScr tables."
::= { mscAtmIfIispCallingAScrRowStatusEntry 10 }

mscAtmIfIispCallingAScrProvTable OBJECT-TYPE
   SYNTAX     SEQUENCE OF MscAtmIfIispCallingAScrProvEntry
   ACCESS     not-accessible
   STATUS     mandatory
   DESCRIPTION
     "This attribute group contains the provisionable attributes for the 
      CallingAScr component."
::= { mscAtmIfIispCallingAScr 10 }

mscAtmIfIispCallingAScrProvEntry OBJECT-TYPE
   SYNTAX     MscAtmIfIispCallingAScrProvEntry
   ACCESS     not-accessible
   STATUS     mandatory
   DESCRIPTION
     "An entry in the mscAtmIfIispCallingAScrProvTable."
   INDEX {
      mscAtmIfIndex,
      mscAtmIfIispIndex,
      mscAtmIfIispCallingAScrIndex }
::= { mscAtmIfIispCallingAScrProvTable 1 }

MscAtmIfIispCallingAScrProvEntry ::= SEQUENCE {
   mscAtmIfIispCallingAScrAdminStatus
      INTEGER,
   mscAtmIfIispCallingAScrDefaultInsertionAddress
      HexString }

mscAtmIfIispCallingAScrAdminStatus OBJECT-TYPE
   SYNTAX     INTEGER  {
                 enabled(0),
                 disabled(1) }
   ACCESS     read-write
   STATUS     mandatory
   DESCRIPTION
     "This attribute specifies whether the calling address screening feature 
      is enabled or disabled. 
      
      If enabled, incoming SVC calls are screened against provisioned 
      addresses. If enabled and the calling address in the ATM SVC call 
      request is provisioned to be accepted, the call is accepted or rejected 
      according to the action specified for that address. If the value is 
      enabled, and the calling address in the address request is not 
      provisioned, the call is rejected
      
      If the value is disabled, no calling address screening is performed."
   DEFVAL     { disabled }
::= { mscAtmIfIispCallingAScrProvEntry 1 }

mscAtmIfIispCallingAScrDefaultInsertionAddress OBJECT-TYPE
   SYNTAX     HexString (SIZE (0..20))
   ACCESS     read-write
   STATUS     mandatory
   DESCRIPTION
     "This attribute specifies the address to be inserted into the SVC 
      connection request if adminStatus is enabled and the connection 
      request does not contain a calling address. If the adminStatus 
      attribute is enabled and this attribute is empty, all incoming SVC 
      calls which do not contain a calling address are rejected."
   DEFVAL     { ''H }  -- ""
::= { mscAtmIfIispCallingAScrProvEntry 2 }

mscAtmIfIispCallingAScrStatTable OBJECT-TYPE
   SYNTAX     SEQUENCE OF MscAtmIfIispCallingAScrStatEntry
   ACCESS     not-accessible
   STATUS     mandatory
   DESCRIPTION
     "This attribute group contains statistics related to the incoming SVC 
      call requests received while the adminStatus attribute is set to 
      enabled."
::= { mscAtmIfIispCallingAScr 11 }

mscAtmIfIispCallingAScrStatEntry OBJECT-TYPE
   SYNTAX     MscAtmIfIispCallingAScrStatEntry
   ACCESS     not-accessible
   STATUS     mandatory
   DESCRIPTION
     "An entry in the mscAtmIfIispCallingAScrStatTable."
   INDEX {
      mscAtmIfIndex,
      mscAtmIfIispIndex,
      mscAtmIfIispCallingAScrIndex }
::= { mscAtmIfIispCallingAScrStatTable 1 }

MscAtmIfIispCallingAScrStatEntry ::= SEQUENCE {
   mscAtmIfIispCallingAScrAcceptedCalls
      Counter32,
   mscAtmIfIispCallingAScrRejectedCalls
      Counter32,
   mscAtmIfIispCallingAScrUnmatchedCalls
      Counter32 }

mscAtmIfIispCallingAScrAcceptedCalls OBJECT-TYPE
   SYNTAX     Counter32 
   ACCESS     read-only
   STATUS     mandatory
   DESCRIPTION
     "This attribute counts the incoming SVC calls which were accepted 
      because the address specified in the call request matched a 
      provisioned ATM address and the associated action was accept.
      When the counter exceeds the maximum, it wraps to 0."
::= { mscAtmIfIispCallingAScrStatEntry 1 }

mscAtmIfIispCallingAScrRejectedCalls OBJECT-TYPE
   SYNTAX     Counter32 
   ACCESS     read-only
   STATUS     mandatory
   DESCRIPTION
     "This attribute counts the incoming SVC calls which were rejected 
      because the address specified in the call request matched a 
      provisioned ATM address, but the associated action was reject. 
      When the counter exceeds the maximum, it wraps to 0."
::= { mscAtmIfIispCallingAScrStatEntry 2 }

mscAtmIfIispCallingAScrUnmatchedCalls OBJECT-TYPE
   SYNTAX     Counter32 
   ACCESS     read-only
   STATUS     mandatory
   DESCRIPTION
     "This attribute counts the incoming SVC calls which were rejected 
      because none of the provisioned ATM addresses matched the 
      applicable address in the incoming SVC call request.
      When the counter exceeds the maximum, it wraps to 0."
::= { mscAtmIfIispCallingAScrStatEntry 3 }


-- AtmIf/n Uni CallingAScr Address/addr,action
-- AtmIf/n Iisp CallingAScr Address/addr,action 
-- AtmIf/n Uni CalledAScr Address/addr,action 
-- AtmIf/n Iisp CalledAScr Address/addr,action 
-- This component specifies a calling (or called) address with an 
-- action to accept or reject a connection request which contains a 
-- matching calling (or called) address.
-- For the Calling Address Screening feature, if the specified action is 
-- accept, any call whose calling address matches that address is 
-- accepted. If the specified action is reject, any call whose calling 
-- address matches that address is rejected.
-- For the Called Address Screening feature, if the specified action is 
-- accept, any call whose called address matches that address, is 
-- accepted. If the specified action is reject, any call whose called 
-- address matches that address is rejected.
-- For both features, the incoming SVC call request is rejected if the 
-- address is not provisioned and the feature is enabled.

mscAtmIfIispCallingAScrAddr OBJECT IDENTIFIER ::= { mscAtmIfIispCallingAScr 2 }



mscAtmIfIispCallingAScrAddrRowStatusTable OBJECT-TYPE
   SYNTAX     SEQUENCE OF MscAtmIfIispCallingAScrAddrRowStatusEntry
   ACCESS     not-accessible
   STATUS     mandatory
   DESCRIPTION
     "This entry controls the addition and deletion of 
      mscAtmIfIispCallingAScrAddr components."
::= { mscAtmIfIispCallingAScrAddr 1 }

mscAtmIfIispCallingAScrAddrRowStatusEntry OBJECT-TYPE
   SYNTAX     MscAtmIfIispCallingAScrAddrRowStatusEntry
   ACCESS     not-accessible
   STATUS     mandatory
   DESCRIPTION
     "A single entry in the table represents a single 
      mscAtmIfIispCallingAScrAddr component."
   INDEX {
      mscAtmIfIndex,
      mscAtmIfIispIndex,
      mscAtmIfIispCallingAScrIndex,
      mscAtmIfIispCallingAScrAddrAddressIndex,
      mscAtmIfIispCallingAScrAddrAddressActionIndex }
::= { mscAtmIfIispCallingAScrAddrRowStatusTable 1 }

MscAtmIfIispCallingAScrAddrRowStatusEntry ::= SEQUENCE {
   mscAtmIfIispCallingAScrAddrRowStatus
      RowStatus,
   mscAtmIfIispCallingAScrAddrComponentName
      DisplayString,
   mscAtmIfIispCallingAScrAddrStorageType
      StorageType,
   mscAtmIfIispCallingAScrAddrAddressIndex
      AsciiStringIndex,
   mscAtmIfIispCallingAScrAddrAddressActionIndex
      INTEGER }

mscAtmIfIispCallingAScrAddrRowStatus OBJECT-TYPE
   SYNTAX     RowStatus 
   ACCESS     read-write
   STATUS     mandatory
   DESCRIPTION
     "This variable is used as the basis for SNMP naming of
      mscAtmIfIispCallingAScrAddr components.
      These components can be added and deleted."
::= { mscAtmIfIispCallingAScrAddrRowStatusEntry 1 }

mscAtmIfIispCallingAScrAddrComponentName OBJECT-TYPE
   SYNTAX     DisplayString 
   ACCESS     read-only
   STATUS     mandatory
   DESCRIPTION
     "This variable provides the component's string name for
      use with the ASCII Console Interface"
::= { mscAtmIfIispCallingAScrAddrRowStatusEntry 2 }

mscAtmIfIispCallingAScrAddrStorageType OBJECT-TYPE
   SYNTAX     StorageType 
   ACCESS     read-only
   STATUS     mandatory
   DESCRIPTION
     "This variable represents the storage type value for the
      mscAtmIfIispCallingAScrAddr tables."
::= { mscAtmIfIispCallingAScrAddrRowStatusEntry 4 }

mscAtmIfIispCallingAScrAddrAddressIndex OBJECT-TYPE
   SYNTAX     AsciiStringIndex (SIZE (1..40))
   ACCESS     not-accessible
   STATUS     mandatory
   DESCRIPTION
     "This variable represents an index for the mscAtmIfIispCallingAScrAddr tables."
::= { mscAtmIfIispCallingAScrAddrRowStatusEntry 10 }

mscAtmIfIispCallingAScrAddrAddressActionIndex OBJECT-TYPE
   SYNTAX     INTEGER  {
                 accept(0),
                 reject(1) }
   ACCESS     not-accessible
   STATUS     mandatory
   DESCRIPTION
     "This variable represents an index for the mscAtmIfIispCallingAScrAddr tables."
::= { mscAtmIfIispCallingAScrAddrRowStatusEntry 11 }


-- AtmIf/n Uni CalledAddressScreening
-- AtmIf/n Iisp CalledAddressScreening
-- This component represents the screening of incoming ATM SVC 
-- call requests against provisioned ATM called addresses (that is, 
-- going to specific destinations). If this component is not provisioned, 
-- all call requests are accepted and no called address screening takes 
-- place.

mscAtmIfIispCalledAScr OBJECT IDENTIFIER ::= { mscAtmIfIisp 6 }



mscAtmIfIispCalledAScrRowStatusTable OBJECT-TYPE
   SYNTAX     SEQUENCE OF MscAtmIfIispCalledAScrRowStatusEntry
   ACCESS     not-accessible
   STATUS     mandatory
   DESCRIPTION
     "This entry controls the addition and deletion of 
      mscAtmIfIispCalledAScr components."
::= { mscAtmIfIispCalledAScr 1 }

mscAtmIfIispCalledAScrRowStatusEntry OBJECT-TYPE
   SYNTAX     MscAtmIfIispCalledAScrRowStatusEntry
   ACCESS     not-accessible
   STATUS     mandatory
   DESCRIPTION
     "A single entry in the table represents a single 
      mscAtmIfIispCalledAScr component."
   INDEX {
      mscAtmIfIndex,
      mscAtmIfIispIndex,
      mscAtmIfIispCalledAScrIndex }
::= { mscAtmIfIispCalledAScrRowStatusTable 1 }

MscAtmIfIispCalledAScrRowStatusEntry ::= SEQUENCE {
   mscAtmIfIispCalledAScrRowStatus
      RowStatus,
   mscAtmIfIispCalledAScrComponentName
      DisplayString,
   mscAtmIfIispCalledAScrStorageType
      StorageType,
   mscAtmIfIispCalledAScrIndex
      NonReplicated }

mscAtmIfIispCalledAScrRowStatus OBJECT-TYPE
   SYNTAX     RowStatus 
   ACCESS     read-write
   STATUS     mandatory
   DESCRIPTION
     "This variable is used as the basis for SNMP naming of
      mscAtmIfIispCalledAScr components.
      These components can be added and deleted."
::= { mscAtmIfIispCalledAScrRowStatusEntry 1 }

mscAtmIfIispCalledAScrComponentName OBJECT-TYPE
   SYNTAX     DisplayString 
   ACCESS     read-only
   STATUS     mandatory
   DESCRIPTION
     "This variable provides the component's string name for
      use with the ASCII Console Interface"
::= { mscAtmIfIispCalledAScrRowStatusEntry 2 }

mscAtmIfIispCalledAScrStorageType OBJECT-TYPE
   SYNTAX     StorageType 
   ACCESS     read-only
   STATUS     mandatory
   DESCRIPTION
     "This variable represents the storage type value for the
      mscAtmIfIispCalledAScr tables."
::= { mscAtmIfIispCalledAScrRowStatusEntry 4 }

mscAtmIfIispCalledAScrIndex OBJECT-TYPE
   SYNTAX     NonReplicated 
   ACCESS     not-accessible
   STATUS     mandatory
   DESCRIPTION
     "This variable represents the index for the mscAtmIfIispCalledAScr tables."
::= { mscAtmIfIispCalledAScrRowStatusEntry 10 }

mscAtmIfIispCalledAScrProvTable OBJECT-TYPE
   SYNTAX     SEQUENCE OF MscAtmIfIispCalledAScrProvEntry
   ACCESS     not-accessible
   STATUS     mandatory
   DESCRIPTION
     "This attribute group contains the provisionable attributes for the 
      CalledAScr component."
::= { mscAtmIfIispCalledAScr 10 }

mscAtmIfIispCalledAScrProvEntry OBJECT-TYPE
   SYNTAX     MscAtmIfIispCalledAScrProvEntry
   ACCESS     not-accessible
   STATUS     mandatory
   DESCRIPTION
     "An entry in the mscAtmIfIispCalledAScrProvTable."
   INDEX {
      mscAtmIfIndex,
      mscAtmIfIispIndex,
      mscAtmIfIispCalledAScrIndex }
::= { mscAtmIfIispCalledAScrProvTable 1 }

MscAtmIfIispCalledAScrProvEntry ::= SEQUENCE {
   mscAtmIfIispCalledAScrAdminStatus
      INTEGER }

mscAtmIfIispCalledAScrAdminStatus OBJECT-TYPE
   SYNTAX     INTEGER  {
                 enabled(0),
                 disabled(1) }
   ACCESS     read-write
   STATUS     mandatory
   DESCRIPTION
     "This attribute specifies whether the called address screening feature 
      is enabled or disabled.
      If the value is enabled, incoming SVC calls will be screened against 
      provisioned called addresses. If the value is enabled and the called 
      address in the ATM SVC call request has been provisioned, the call 
      is accepted or rejected according to the action specified for that 
      address. If the value is enabled and the called address in the call 
      request is not provisioned, the call is rejected.
      If the value is disabled, no called address screening is performed."
   DEFVAL     { disabled }
::= { mscAtmIfIispCalledAScrProvEntry 1 }

mscAtmIfIispCalledAScrStatTable OBJECT-TYPE
   SYNTAX     SEQUENCE OF MscAtmIfIispCalledAScrStatEntry
   ACCESS     not-accessible
   STATUS     mandatory
   DESCRIPTION
     "This attribute group contains statistics related to the incoming SVC 
      call requests received while the adminStatus attribute is set to 
      enabled."
::= { mscAtmIfIispCalledAScr 11 }

mscAtmIfIispCalledAScrStatEntry OBJECT-TYPE
   SYNTAX     MscAtmIfIispCalledAScrStatEntry
   ACCESS     not-accessible
   STATUS     mandatory
   DESCRIPTION
     "An entry in the mscAtmIfIispCalledAScrStatTable."
   INDEX {
      mscAtmIfIndex,
      mscAtmIfIispIndex,
      mscAtmIfIispCalledAScrIndex }
::= { mscAtmIfIispCalledAScrStatTable 1 }

MscAtmIfIispCalledAScrStatEntry ::= SEQUENCE {
   mscAtmIfIispCalledAScrAcceptedCalls
      Counter32,
   mscAtmIfIispCalledAScrRejectedCalls
      Counter32,
   mscAtmIfIispCalledAScrUnmatchedCalls
      Counter32 }

mscAtmIfIispCalledAScrAcceptedCalls OBJECT-TYPE
   SYNTAX     Counter32 
   ACCESS     read-only
   STATUS     mandatory
   DESCRIPTION
     "This attribute counts the incoming SVC calls which were accepted 
      because the address specified in the call request matched a 
      provisioned ATM address and the associated action was accept.
      When the counter exceeds the maximum, it wraps to 0."
::= { mscAtmIfIispCalledAScrStatEntry 1 }

mscAtmIfIispCalledAScrRejectedCalls OBJECT-TYPE
   SYNTAX     Counter32 
   ACCESS     read-only
   STATUS     mandatory
   DESCRIPTION
     "This attribute counts the incoming SVC calls which were rejected 
      because the address specified in the call request matched a 
      provisioned ATM address, but the associated action was reject. 
      When the counter exceeds the maximum, it wraps to 0."
::= { mscAtmIfIispCalledAScrStatEntry 2 }

mscAtmIfIispCalledAScrUnmatchedCalls OBJECT-TYPE
   SYNTAX     Counter32 
   ACCESS     read-only
   STATUS     mandatory
   DESCRIPTION
     "This attribute counts the incoming SVC calls which were rejected 
      because none of the provisioned ATM addresses matched the 
      applicable address in the incoming SVC call request.
      When the counter exceeds the maximum, it wraps to 0."
::= { mscAtmIfIispCalledAScrStatEntry 3 }


-- AtmIf/n Uni CallingAScr Address/addr,action
-- AtmIf/n Iisp CallingAScr Address/addr,action 
-- AtmIf/n Uni CalledAScr Address/addr,action 
-- AtmIf/n Iisp CalledAScr Address/addr,action 
-- This component specifies a calling (or called) address with an 
-- action to accept or reject a connection request which contains a 
-- matching calling (or called) address.
-- For the Calling Address Screening feature, if the specified action is 
-- accept, any call whose calling address matches that address is 
-- accepted. If the specified action is reject, any call whose calling 
-- address matches that address is rejected.
-- For the Called Address Screening feature, if the specified action is 
-- accept, any call whose called address matches that address, is 
-- accepted. If the specified action is reject, any call whose called 
-- address matches that address is rejected.
-- For both features, the incoming SVC call request is rejected if the 
-- address is not provisioned and the feature is enabled.

mscAtmIfIispCalledAScrAddr OBJECT IDENTIFIER ::= { mscAtmIfIispCalledAScr 2 }



mscAtmIfIispCalledAScrAddrRowStatusTable OBJECT-TYPE
   SYNTAX     SEQUENCE OF MscAtmIfIispCalledAScrAddrRowStatusEntry
   ACCESS     not-accessible
   STATUS     mandatory
   DESCRIPTION
     "This entry controls the addition and deletion of 
      mscAtmIfIispCalledAScrAddr components."
::= { mscAtmIfIispCalledAScrAddr 1 }

mscAtmIfIispCalledAScrAddrRowStatusEntry OBJECT-TYPE
   SYNTAX     MscAtmIfIispCalledAScrAddrRowStatusEntry
   ACCESS     not-accessible
   STATUS     mandatory
   DESCRIPTION
     "A single entry in the table represents a single 
      mscAtmIfIispCalledAScrAddr component."
   INDEX {
      mscAtmIfIndex,
      mscAtmIfIispIndex,
      mscAtmIfIispCalledAScrIndex,
      mscAtmIfIispCalledAScrAddrAddressIndex,
      mscAtmIfIispCalledAScrAddrAddressActionIndex }
::= { mscAtmIfIispCalledAScrAddrRowStatusTable 1 }

MscAtmIfIispCalledAScrAddrRowStatusEntry ::= SEQUENCE {
   mscAtmIfIispCalledAScrAddrRowStatus
      RowStatus,
   mscAtmIfIispCalledAScrAddrComponentName
      DisplayString,
   mscAtmIfIispCalledAScrAddrStorageType
      StorageType,
   mscAtmIfIispCalledAScrAddrAddressIndex
      AsciiStringIndex,
   mscAtmIfIispCalledAScrAddrAddressActionIndex
      INTEGER }

mscAtmIfIispCalledAScrAddrRowStatus OBJECT-TYPE
   SYNTAX     RowStatus 
   ACCESS     read-write
   STATUS     mandatory
   DESCRIPTION
     "This variable is used as the basis for SNMP naming of
      mscAtmIfIispCalledAScrAddr components.
      These components can be added and deleted."
::= { mscAtmIfIispCalledAScrAddrRowStatusEntry 1 }

mscAtmIfIispCalledAScrAddrComponentName OBJECT-TYPE
   SYNTAX     DisplayString 
   ACCESS     read-only
   STATUS     mandatory
   DESCRIPTION
     "This variable provides the component's string name for
      use with the ASCII Console Interface"
::= { mscAtmIfIispCalledAScrAddrRowStatusEntry 2 }

mscAtmIfIispCalledAScrAddrStorageType OBJECT-TYPE
   SYNTAX     StorageType 
   ACCESS     read-only
   STATUS     mandatory
   DESCRIPTION
     "This variable represents the storage type value for the
      mscAtmIfIispCalledAScrAddr tables."
::= { mscAtmIfIispCalledAScrAddrRowStatusEntry 4 }

mscAtmIfIispCalledAScrAddrAddressIndex OBJECT-TYPE
   SYNTAX     AsciiStringIndex (SIZE (1..40))
   ACCESS     not-accessible
   STATUS     mandatory
   DESCRIPTION
     "This variable represents an index for the mscAtmIfIispCalledAScrAddr tables."
::= { mscAtmIfIispCalledAScrAddrRowStatusEntry 10 }

mscAtmIfIispCalledAScrAddrAddressActionIndex OBJECT-TYPE
   SYNTAX     INTEGER  {
                 accept(0),
                 reject(1) }
   ACCESS     not-accessible
   STATUS     mandatory
   DESCRIPTION
     "This variable represents an index for the mscAtmIfIispCalledAScrAddr tables."
::= { mscAtmIfIispCalledAScrAddrRowStatusEntry 11 }


-- AtmIf/n VirtualPathTerminator/m Iisp
-- This component represents a virtual ATM Interim Inter-switch 
-- Signaling Protocol (IISP) interface. If this component is 
-- provisioned, neither a Uni component nor a Pnni component can be 
-- provisioned under the same Vpt component. If this component is 
-- deleted, then all associated Vcc components are deleted.

mscAtmIfVptIisp OBJECT IDENTIFIER ::= { mscAtmIfVpt 6 }



mscAtmIfVptIispRowStatusTable OBJECT-TYPE
   SYNTAX     SEQUENCE OF MscAtmIfVptIispRowStatusEntry
   ACCESS     not-accessible
   STATUS     mandatory
   DESCRIPTION
     "This entry controls the addition and deletion of 
      mscAtmIfVptIisp components."
::= { mscAtmIfVptIisp 1 }

mscAtmIfVptIispRowStatusEntry OBJECT-TYPE
   SYNTAX     MscAtmIfVptIispRowStatusEntry
   ACCESS     not-accessible
   STATUS     mandatory
   DESCRIPTION
     "A single entry in the table represents a single 
      mscAtmIfVptIisp component."
   INDEX {
      mscAtmIfIndex,
      mscAtmIfVptIndex,
      mscAtmIfVptIispIndex }
::= { mscAtmIfVptIispRowStatusTable 1 }

MscAtmIfVptIispRowStatusEntry ::= SEQUENCE {
   mscAtmIfVptIispRowStatus
      RowStatus,
   mscAtmIfVptIispComponentName
      DisplayString,
   mscAtmIfVptIispStorageType
      StorageType,
   mscAtmIfVptIispIndex
      NonReplicated }

mscAtmIfVptIispRowStatus OBJECT-TYPE
   SYNTAX     RowStatus 
   ACCESS     read-write
   STATUS     mandatory
   DESCRIPTION
     "This variable is used as the basis for SNMP naming of
      mscAtmIfVptIisp components.
      These components can be added and deleted."
::= { mscAtmIfVptIispRowStatusEntry 1 }

mscAtmIfVptIispComponentName OBJECT-TYPE
   SYNTAX     DisplayString 
   ACCESS     read-only
   STATUS     mandatory
   DESCRIPTION
     "This variable provides the component's string name for
      use with the ASCII Console Interface"
::= { mscAtmIfVptIispRowStatusEntry 2 }

mscAtmIfVptIispStorageType OBJECT-TYPE
   SYNTAX     StorageType 
   ACCESS     read-only
   STATUS     mandatory
   DESCRIPTION
     "This variable represents the storage type value for the
      mscAtmIfVptIisp tables."
::= { mscAtmIfVptIispRowStatusEntry 4 }

mscAtmIfVptIispIndex OBJECT-TYPE
   SYNTAX     NonReplicated 
   ACCESS     not-accessible
   STATUS     mandatory
   DESCRIPTION
     "This variable represents the index for the mscAtmIfVptIisp tables."
::= { mscAtmIfVptIispRowStatusEntry 10 }

mscAtmIfVptIispProvTable OBJECT-TYPE
   SYNTAX     SEQUENCE OF MscAtmIfVptIispProvEntry
   ACCESS     not-accessible
   STATUS     mandatory
   DESCRIPTION
     "This group contains the provisionable attributes for the Iisp 
      component."
::= { mscAtmIfVptIisp 10 }

mscAtmIfVptIispProvEntry OBJECT-TYPE
   SYNTAX     MscAtmIfVptIispProvEntry
   ACCESS     not-accessible
   STATUS     mandatory
   DESCRIPTION
     "An entry in the mscAtmIfVptIispProvTable."
   INDEX {
      mscAtmIfIndex,
      mscAtmIfVptIndex,
      mscAtmIfVptIispIndex }
::= { mscAtmIfVptIispProvTable 1 }

MscAtmIfVptIispProvEntry ::= SEQUENCE {
   mscAtmIfVptIispVersion
      INTEGER,
   mscAtmIfVptIispSide
      INTEGER,
   mscAtmIfVptIispSoftPvcRetryPeriod
      Unsigned32,
   mscAtmIfVptIispSoftPvpAndPvcRetryPeriod
      Unsigned32,
   mscAtmIfVptIispSoftPvpAndPvcHoldOffTime
      Unsigned32 }

mscAtmIfVptIispVersion OBJECT-TYPE
   SYNTAX     INTEGER  {
                 iisp10Sig30(2),
                 iisp10Sig31(3) }
   ACCESS     read-write
   STATUS     mandatory
   DESCRIPTION
     "This attribute indicates which specification the IISP interface 
      complies with. The options are iisp10Sig30 which refers to IISP 
      version 1.0 with 3.0 signalling and iisp10Sig31 which refers to IISP 
      version 1.0 with 3.1 signalling. If this attribute is changed, all 
      switched Vcc components in this interface are cleared due to the 
      fact that the two versions are incompatible."
   DEFVAL     { iisp10Sig31 }
::= { mscAtmIfVptIispProvEntry 1 }

mscAtmIfVptIispSide OBJECT-TYPE
   SYNTAX     INTEGER  {
                 networkSide(0),
                 userSide(1) }
   ACCESS     read-write
   STATUS     mandatory
   DESCRIPTION
     "This attribute indicates which side the interface is, user or network."
   DEFVAL     { networkSide }
::= { mscAtmIfVptIispProvEntry 2 }

mscAtmIfVptIispSoftPvcRetryPeriod OBJECT-TYPE
   SYNTAX     Unsigned32 (20..999999)
   ACCESS     read-write
   STATUS     obsolete
   DESCRIPTION
     "This attribute specifies the time to wait between call set up retries. 
      The resolution is to the nearest 10 seconds.
      This attribute has been obsoleted and is replaced by the 
      softPvpAndPvcRetryPeriod attribute."
   DEFVAL     { 60 }
::= { mscAtmIfVptIispProvEntry 3 }

mscAtmIfVptIispSoftPvpAndPvcRetryPeriod OBJECT-TYPE
   SYNTAX     Unsigned32 (20..999999)
   ACCESS     read-write
   STATUS     mandatory
   DESCRIPTION
     "This attribute specifies the time to wait between soft PVP or soft 
      PVC call setup retries. The resolution is to the nearest 10 seconds."
   DEFVAL     { 60 }
::= { mscAtmIfVptIispProvEntry 4 }

mscAtmIfVptIispSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { mscAtmIfVptIispProvEntry 5 }

mscAtmIfVptIispAcctOptTable OBJECT-TYPE
   SYNTAX     SEQUENCE OF MscAtmIfVptIispAcctOptEntry
   ACCESS     not-accessible
   STATUS     mandatory
   DESCRIPTION
     "This group contains the provisionable attributes for accounting."
::= { mscAtmIfVptIisp 11 }

mscAtmIfVptIispAcctOptEntry OBJECT-TYPE
   SYNTAX     MscAtmIfVptIispAcctOptEntry
   ACCESS     not-accessible
   STATUS     mandatory
   DESCRIPTION
     "An entry in the mscAtmIfVptIispAcctOptTable."
   INDEX {
      mscAtmIfIndex,
      mscAtmIfVptIndex,
      mscAtmIfVptIispIndex }
::= { mscAtmIfVptIispAcctOptTable 1 }

MscAtmIfVptIispAcctOptEntry ::= SEQUENCE {
   mscAtmIfVptIispAccountCollection
      OCTET STRING,
   mscAtmIfVptIispAccountConnectionType
      INTEGER,
   mscAtmIfVptIispAccountClass
      Unsigned32,
   mscAtmIfVptIispServiceExchange
      Unsigned32 }

mscAtmIfVptIispAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit, or force.
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { mscAtmIfVptIispAcctOptEntry 1 }

mscAtmIfVptIispAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { intermediate }
::= { mscAtmIfVptIispAcctOptEntry 2 }

mscAtmIfVptIispAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { mscAtmIfVptIispAcctOptEntry 3 }

mscAtmIfVptIispServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { mscAtmIfVptIispAcctOptEntry 4 }

mscAtmIfVptIispVProvTable OBJECT-TYPE
   SYNTAX     SEQUENCE OF MscAtmIfVptIispVProvEntry
   ACCESS     not-accessible
   STATUS     mandatory
   DESCRIPTION
     "This group contains the provisionable attributes for the Iisp 
      component which are specific to virtual IISP interfaces."
::= { mscAtmIfVptIisp 12 }

mscAtmIfVptIispVProvEntry OBJECT-TYPE
   SYNTAX     MscAtmIfVptIispVProvEntry
   ACCESS     not-accessible
   STATUS     mandatory
   DESCRIPTION
     "An entry in the mscAtmIfVptIispVProvTable."
   INDEX {
      mscAtmIfIndex,
      mscAtmIfVptIndex,
      mscAtmIfVptIispIndex }
::= { mscAtmIfVptIispVProvTable 1 }

MscAtmIfVptIispVProvEntry ::= SEQUENCE {
   mscAtmIfVptIispVpci
      Unsigned32 }

mscAtmIfVptIispVpci OBJECT-TYPE
   SYNTAX     Unsigned32 (0..255)
   ACCESS     read-write
   STATUS     mandatory
   DESCRIPTION
     "This attribute specifies the Virtual Path Connection Identifier 
      (VPCI) to be used between this signalling entity and its peer. The 
      VPCI of the peer virtual IISP must have the same value for 
      switched connections to be set up across the interface."
   DEFVAL     { 0 }
::= { mscAtmIfVptIispVProvEntry 1 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

mscAtmIfVptIispSig OBJECT IDENTIFIER ::= { mscAtmIfVptIisp 3 }



mscAtmIfVptIispSigRowStatusTable OBJECT-TYPE
   SYNTAX     SEQUENCE OF MscAtmIfVptIispSigRowStatusEntry
   ACCESS     not-accessible
   STATUS     mandatory
   DESCRIPTION
     "This entry controls the addition and deletion of 
      mscAtmIfVptIispSig components."
::= { mscAtmIfVptIispSig 1 }

mscAtmIfVptIispSigRowStatusEntry OBJECT-TYPE
   SYNTAX     MscAtmIfVptIispSigRowStatusEntry
   ACCESS     not-accessible
   STATUS     mandatory
   DESCRIPTION
     "A single entry in the table represents a single 
      mscAtmIfVptIispSig component."
   INDEX {
      mscAtmIfIndex,
      mscAtmIfVptIndex,
      mscAtmIfVptIispIndex,
      mscAtmIfVptIispSigIndex }
::= { mscAtmIfVptIispSigRowStatusTable 1 }

MscAtmIfVptIispSigRowStatusEntry ::= SEQUENCE {
   mscAtmIfVptIispSigRowStatus
      RowStatus,
   mscAtmIfVptIispSigComponentName
      DisplayString,
   mscAtmIfVptIispSigStorageType
      StorageType,
   mscAtmIfVptIispSigIndex
      NonReplicated }

mscAtmIfVptIispSigRowStatus OBJECT-TYPE
   SYNTAX     RowStatus 
   ACCESS     read-only
   STATUS     mandatory
   DESCRIPTION
     "This variable is used as the basis for SNMP naming of
      mscAtmIfVptIispSig components.
      These components cannot be added nor deleted."
::= { mscAtmIfVptIispSigRowStatusEntry 1 }

mscAtmIfVptIispSigComponentName OBJECT-TYPE
   SYNTAX     DisplayString 
   ACCESS     read-only
   STATUS     mandatory
   DESCRIPTION
     "This variable provides the component's string name for
      use with the ASCII Console Interface"
::= { mscAtmIfVptIispSigRowStatusEntry 2 }

mscAtmIfVptIispSigStorageType OBJECT-TYPE
   SYNTAX     StorageType 
   ACCESS     read-only
   STATUS     mandatory
   DESCRIPTION
     "This variable represents the storage type value for the
      mscAtmIfVptIispSig tables."
::= { mscAtmIfVptIispSigRowStatusEntry 4 }

mscAtmIfVptIispSigIndex OBJECT-TYPE
   SYNTAX     NonReplicated 
   ACCESS     not-accessible
   STATUS     mandatory
   DESCRIPTION
     "This variable represents the index for the mscAtmIfVptIispSig tables."
::= { mscAtmIfVptIispSigRowStatusEntry 10 }

mscAtmIfVptIispSigProvTable OBJECT-TYPE
   SYNTAX     SEQUENCE OF MscAtmIfVptIispSigProvEntry
   ACCESS     not-accessible
   STATUS     mandatory
   DESCRIPTION
     "This attribute group contains the provisionable attributes for the 
      Signalling component."
::= { mscAtmIfVptIispSig 10 }

mscAtmIfVptIispSigProvEntry OBJECT-TYPE
   SYNTAX     MscAtmIfVptIispSigProvEntry
   ACCESS     not-accessible
   STATUS     mandatory
   DESCRIPTION
     "An entry in the mscAtmIfVptIispSigProvTable."
   INDEX {
      mscAtmIfIndex,
      mscAtmIfVptIndex,
      mscAtmIfVptIispIndex,
      mscAtmIfVptIispSigIndex }
::= { mscAtmIfVptIispSigProvTable 1 }

MscAtmIfVptIispSigProvEntry ::= SEQUENCE {
   mscAtmIfVptIispSigVci
      Unsigned32,
   mscAtmIfVptIispSigAddressConversion
      INTEGER,
   mscAtmIfVptIispSigOperatingMode
      INTEGER }

mscAtmIfVptIispSigVci OBJECT-TYPE
   SYNTAX     Unsigned32 (0..65535)
   ACCESS     read-write
   STATUS     mandatory
   DESCRIPTION
     "This attribute specifies the signalling channel number."
   DEFVAL     { 5 }
::= { mscAtmIfVptIispSigProvEntry 1 }

mscAtmIfVptIispSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { mscAtmIfVptIispSigProvEntry 2 }

mscAtmIfVptIispSigOperatingMode OBJECT-TYPE
   SYNTAX     INTEGER  {
                 normal(0),
                 provisionedOnly(1) }
   ACCESS     read-write
   STATUS     mandatory
   DESCRIPTION
     "This attribute specifies the operating mode of the signaling channel. 				
      provisionedOnly indicates that only SPVCs and SPVPs are 
      supported on the interface and SVCs are not supported. This value 
      is permitted only on UNI interfaces.
      normal indicates that SVCs, SPVCs, and SPVPs are supported on 
      the interface."
   DEFVAL     { normal }
::= { mscAtmIfVptIispSigProvEntry 3 }

mscAtmIfVptIispSigStateTable OBJECT-TYPE
   SYNTAX     SEQUENCE OF MscAtmIfVptIispSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAtmIfVptIispSig 11 }

mscAtmIfVptIispSigStateEntry OBJECT-TYPE
   SYNTAX     MscAtmIfVptIispSigStateEntry
   ACCESS     not-accessible
   STATUS     mandatory
   DESCRIPTION
     "An entry in the mscAtmIfVptIispSigStateTable."
   INDEX {
      mscAtmIfIndex,
      mscAtmIfVptIndex,
      mscAtmIfVptIispIndex,
      mscAtmIfVptIispSigIndex }
::= { mscAtmIfVptIispSigStateTable 1 }

MscAtmIfVptIispSigStateEntry ::= SEQUENCE {
   mscAtmIfVptIispSigAdminState
      INTEGER,
   mscAtmIfVptIispSigOperationalState
      INTEGER,
   mscAtmIfVptIispSigUsageState
      INTEGER }

mscAtmIfVptIispSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAtmIfVptIispSigStateEntry 1 }

mscAtmIfVptIispSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAtmIfVptIispSigStateEntry 2 }

mscAtmIfVptIispSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAtmIfVptIispSigStateEntry 3 }

mscAtmIfVptIispSigOperTable OBJECT-TYPE
   SYNTAX     SEQUENCE OF MscAtmIfVptIispSigOperEntry
   ACCESS     not-accessible
   STATUS     mandatory
   DESCRIPTION
     "This attribute contains the operational attributes for the 
      AtmSignalling component."
::= { mscAtmIfVptIispSig 12 }

mscAtmIfVptIispSigOperEntry OBJECT-TYPE
   SYNTAX     MscAtmIfVptIispSigOperEntry
   ACCESS     not-accessible
   STATUS     mandatory
   DESCRIPTION
     "An entry in the mscAtmIfVptIispSigOperTable."
   INDEX {
      mscAtmIfIndex,
      mscAtmIfVptIndex,
      mscAtmIfVptIispIndex,
      mscAtmIfVptIispSigIndex }
::= { mscAtmIfVptIispSigOperTable 1 }

MscAtmIfVptIispSigOperEntry ::= SEQUENCE {
   mscAtmIfVptIispSigLastTxCauseCode
      Unsigned32,
   mscAtmIfVptIispSigLastTxDiagCode
      Hex,
   mscAtmIfVptIispSigLastRxCauseCode
      Unsigned32,
   mscAtmIfVptIispSigLastRxDiagCode
      Hex }

mscAtmIfVptIispSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { mscAtmIfVptIispSigOperEntry 1 }

mscAtmIfVptIispSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfVptIispSigOperEntry 2 }

mscAtmIfVptIispSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { mscAtmIfVptIispSigOperEntry 3 }

mscAtmIfVptIispSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { mscAtmIfVptIispSigOperEntry 4 }

mscAtmIfVptIispSigStatsTable OBJECT-TYPE
   SYNTAX     SEQUENCE OF MscAtmIfVptIispSigStatsEntry
   ACCESS     not-accessible
   STATUS     mandatory
   DESCRIPTION
     "This attribute group contains the statistics associated with the 
      AtmSignalling component."
::= { mscAtmIfVptIispSig 13 }

mscAtmIfVptIispSigStatsEntry OBJECT-TYPE
   SYNTAX     MscAtmIfVptIispSigStatsEntry
   ACCESS     not-accessible
   STATUS     mandatory
   DESCRIPTION
     "An entry in the mscAtmIfVptIispSigStatsTable."
   INDEX {
      mscAtmIfIndex,
      mscAtmIfVptIndex,
      mscAtmIfVptIispIndex,
      mscAtmIfVptIispSigIndex }
::= { mscAtmIfVptIispSigStatsTable 1 }

MscAtmIfVptIispSigStatsEntry ::= SEQUENCE {
   mscAtmIfVptIispSigCurrentConnections
      Counter32,
   mscAtmIfVptIispSigPeakConnections
      Gauge32,
   mscAtmIfVptIispSigSuccessfulConnections
      Counter32,
   mscAtmIfVptIispSigFailedConnections
      Counter32,
   mscAtmIfVptIispSigTxPdus
      Counter32,
   mscAtmIfVptIispSigRxPdus
      Counter32,
   mscAtmIfVptIispSigCurrentPmpConnections
      Gauge32,
   mscAtmIfVptIispSigPeakPmpConnections
      Gauge32,
   mscAtmIfVptIispSigSuccessfulPmpConnections
      Counter32,
   mscAtmIfVptIispSigFailedPmpConnections
      Counter32,
   mscAtmIfVptIispSigNewCurrentConnections
      Gauge32 }

mscAtmIfVptIispSigCurrentConnections OBJECT-TYPE
   SYNTAX     Counter32 
   ACCESS     read-only
   STATUS     obsolete
   DESCRIPTION
     "This attribute indicates the total number of currently active 
      connections."
::= { mscAtmIfVptIispSigStatsEntry 1 }

mscAtmIfVptIispSigPeakConnections OBJECT-TYPE
   SYNTAX     Gauge32 (0..4294967295)
   ACCESS     read-only
   STATUS     mandatory
   DESCRIPTION
     "This attribute indicates the high water mark of active point-to-
      point and point-to-multipoint connections."
::= { mscAtmIfVptIispSigStatsEntry 2 }

mscAtmIfVptIispSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { mscAtmIfVptIispSigStatsEntry 3 }

mscAtmIfVptIispSigFailedConnections OBJECT-TYPE
   SYNTAX     Counter32 
   ACCESS     read-only
   STATUS     mandatory
   DESCRIPTION
     "This attribute counts the total number of switched connections that 
      were not successfully established.The counter wraps to 0 when the 
      maximum value is exceeded."
::= { mscAtmIfVptIispSigStatsEntry 4 }

mscAtmIfVptIispSigTxPdus OBJECT-TYPE
   SYNTAX     Counter32 
   ACCESS     read-only
   STATUS     mandatory
   DESCRIPTION
     "This attribute counts the number of transmitted signalling 
      PDUs.The counter wraps to 0 when the maximum value is 
      exceeded."
::= { mscAtmIfVptIispSigStatsEntry 5 }

mscAtmIfVptIispSigRxPdus OBJECT-TYPE
   SYNTAX     Counter32 
   ACCESS     read-only
   STATUS     mandatory
   DESCRIPTION
     "This attribute counts the number of received signalling PDUs.The 
      counter wraps to 0 when the maximum value is exceeded."
::= { mscAtmIfVptIispSigStatsEntry 6 }

mscAtmIfVptIispSigCurrentPmpConnections OBJECT-TYPE
   SYNTAX     Gauge32 (0..4294967295)
   ACCESS     read-only
   STATUS     mandatory
   DESCRIPTION
     "This attribute indicates the number of currently active point-to-
      multipoint connections."
::= { mscAtmIfVptIispSigStatsEntry 7 }

mscAtmIfVptIispSigPeakPmpConnections OBJECT-TYPE
   SYNTAX     Gauge32 (0..4294967295)
   ACCESS     read-only
   STATUS     mandatory
   DESCRIPTION
     "This attribute indicates the high water mark of active point-to-
      multipoint connections."
::= { mscAtmIfVptIispSigStatsEntry 8 }

mscAtmIfVptIispSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { mscAtmIfVptIispSigStatsEntry 9 }

mscAtmIfVptIispSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { mscAtmIfVptIispSigStatsEntry 10 }

mscAtmIfVptIispSigNewCurrentConnections OBJECT-TYPE
   SYNTAX     Gauge32 (0..4294967295)
   ACCESS     read-only
   STATUS     mandatory
   DESCRIPTION
     "This attribute indicates the total number of currently active point-to-
      point and point-to-multipoint connections."
::= { mscAtmIfVptIispSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

mscAtmIfVptIispSigVcd OBJECT IDENTIFIER ::= { mscAtmIfVptIispSig 2 }



mscAtmIfVptIispSigVcdRowStatusTable OBJECT-TYPE
   SYNTAX     SEQUENCE OF MscAtmIfVptIispSigVcdRowStatusEntry
   ACCESS     not-accessible
   STATUS     mandatory
   DESCRIPTION
     "This entry controls the addition and deletion of 
      mscAtmIfVptIispSigVcd components."
::= { mscAtmIfVptIispSigVcd 1 }

mscAtmIfVptIispSigVcdRowStatusEntry OBJECT-TYPE
   SYNTAX     MscAtmIfVptIispSigVcdRowStatusEntry
   ACCESS     not-accessible
   STATUS     mandatory
   DESCRIPTION
     "A single entry in the table represents a single 
      mscAtmIfVptIispSigVcd component."
   INDEX {
      mscAtmIfIndex,
      mscAtmIfVptIndex,
      mscAtmIfVptIispIndex,
      mscAtmIfVptIispSigIndex,
      mscAtmIfVptIispSigVcdIndex }
::= { mscAtmIfVptIispSigVcdRowStatusTable 1 }

MscAtmIfVptIispSigVcdRowStatusEntry ::= SEQUENCE {
   mscAtmIfVptIispSigVcdRowStatus
      RowStatus,
   mscAtmIfVptIispSigVcdComponentName
      DisplayString,
   mscAtmIfVptIispSigVcdStorageType
      StorageType,
   mscAtmIfVptIispSigVcdIndex
      NonReplicated }

mscAtmIfVptIispSigVcdRowStatus OBJECT-TYPE
   SYNTAX     RowStatus 
   ACCESS     read-write
   STATUS     mandatory
   DESCRIPTION
     "This variable is used as the basis for SNMP naming of
      mscAtmIfVptIispSigVcd components.
      These components can be added and deleted."
::= { mscAtmIfVptIispSigVcdRowStatusEntry 1 }

mscAtmIfVptIispSigVcdComponentName OBJECT-TYPE
   SYNTAX     DisplayString 
   ACCESS     read-only
   STATUS     mandatory
   DESCRIPTION
     "This variable provides the component's string name for
      use with the ASCII Console Interface"
::= { mscAtmIfVptIispSigVcdRowStatusEntry 2 }

mscAtmIfVptIispSigVcdStorageType OBJECT-TYPE
   SYNTAX     StorageType 
   ACCESS     read-only
   STATUS     mandatory
   DESCRIPTION
     "This variable represents the storage type value for the
      mscAtmIfVptIispSigVcd tables."
::= { mscAtmIfVptIispSigVcdRowStatusEntry 4 }

mscAtmIfVptIispSigVcdIndex OBJECT-TYPE
   SYNTAX     NonReplicated 
   ACCESS     not-accessible
   STATUS     mandatory
   DESCRIPTION
     "This variable represents the index for the mscAtmIfVptIispSigVcd tables."
::= { mscAtmIfVptIispSigVcdRowStatusEntry 10 }

mscAtmIfVptIispSigVcdProvTable OBJECT-TYPE
   SYNTAX     SEQUENCE OF MscAtmIfVptIispSigVcdProvEntry
   ACCESS     not-accessible
   STATUS     mandatory
   DESCRIPTION
     "This group contains the provisionable traffic attributes for a control 
      channel."
::= { mscAtmIfVptIispSigVcd 10 }

mscAtmIfVptIispSigVcdProvEntry OBJECT-TYPE
   SYNTAX     MscAtmIfVptIispSigVcdProvEntry
   ACCESS     not-accessible
   STATUS     mandatory
   DESCRIPTION
     "An entry in the mscAtmIfVptIispSigVcdProvTable."
   INDEX {
      mscAtmIfIndex,
      mscAtmIfVptIndex,
      mscAtmIfVptIispIndex,
      mscAtmIfVptIispSigIndex,
      mscAtmIfVptIispSigVcdIndex }
::= { mscAtmIfVptIispSigVcdProvTable 1 }

MscAtmIfVptIispSigVcdProvEntry ::= SEQUENCE {
   mscAtmIfVptIispSigVcdTrafficDescType
      INTEGER,
   mscAtmIfVptIispSigVcdAtmServiceCategory
      INTEGER,
   mscAtmIfVptIispSigVcdWeight
      Unsigned32,
   mscAtmIfVptIispSigVcdQosClass
      INTEGER,
   mscAtmIfVptIispSigVcdTrafficShaping
      INTEGER,
   mscAtmIfVptIispSigVcdUnshapedTransmitQueueing
      INTEGER,
   mscAtmIfVptIispSigVcdUsageParameterControl
      INTEGER }

mscAtmIfVptIispSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { mscAtmIfVptIispSigVcdProvEntry 1 }

mscAtmIfVptIispSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { mscAtmIfVptIispSigVcdProvEntry 3 }

mscAtmIfVptIispSigVcdWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP and 
      basic VPTs. 
      
      When the value is set to sameAsCa, the weight is determined by the 
      weight policy attribute under the CA service category component 
      for all but standard VPT VCCs. For standard VPT VCCs, the 
      weight is determined by the VCC's service category, when the value 
      is set to sameAsCa.
      
      When this attribute is set to a value from 1 to 4095, that value is 
      used for the weight policy of this connection relative to other 
      connections. For all but standard VPT VCCs, weight policy 
      determines the proportion of transit cell opportunities which are 
      allocated to this connection, compared to other connections in the 
      same service category. For standard VPT VCCs, weight policy 
      determines the proportion of transmit cell opportunities which are 
      allocated to this connection, compared to other connections 
      associated with the VPT.
      
      When the value is set to upToQueueLimit, the weight policy is 
      limited only by the txQueueLimit.

      VALUES (

      0 = upToQueueLimit

      65535 = sameAsCa

      )"
   DEFVAL     { 65535 }
::= { mscAtmIfVptIispSigVcdProvEntry 4 }

mscAtmIfVptIispSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { mscAtmIfVptIispSigVcdProvEntry 21 }

mscAtmIfVptIispSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { mscAtmIfVptIispSigVcdProvEntry 50 }

mscAtmIfVptIispSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { mscAtmIfVptIispSigVcdProvEntry 60 }

mscAtmIfVptIispSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { mscAtmIfVptIispSigVcdProvEntry 70 }

mscAtmIfVptIispSigVcdTdpTable OBJECT-TYPE
   SYNTAX     SEQUENCE OF MscAtmIfVptIispSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { mscAtmIfVptIispSigVcd 387 }

mscAtmIfVptIispSigVcdTdpEntry OBJECT-TYPE
   SYNTAX     MscAtmIfVptIispSigVcdTdpEntry
   ACCESS     not-accessible
   STATUS     mandatory
   DESCRIPTION
     "An entry in the mscAtmIfVptIispSigVcdTdpTable."
   INDEX {
      mscAtmIfIndex,
      mscAtmIfVptIndex,
      mscAtmIfVptIispIndex,
      mscAtmIfVptIispSigIndex,
      mscAtmIfVptIispSigVcdIndex,
      mscAtmIfVptIispSigVcdTdpIndex }
::= { mscAtmIfVptIispSigVcdTdpTable 1 }

MscAtmIfVptIispSigVcdTdpEntry ::= SEQUENCE {
   mscAtmIfVptIispSigVcdTdpIndex
      Integer32,
   mscAtmIfVptIispSigVcdTdpValue
      Unsigned32 }

mscAtmIfVptIispSigVcdTdpIndex OBJECT-TYPE
   SYNTAX     Integer32 (1..5)
   ACCESS     not-accessible
   STATUS     mandatory
   DESCRIPTION
     "This variable represents the mscAtmIfVptIispSigVcdTdpTable
      specific index for the mscAtmIfVptIispSigVcdTdpTable."
::= { mscAtmIfVptIispSigVcdTdpEntry 1 }

mscAtmIfVptIispSigVcdTdpValue OBJECT-TYPE
   SYNTAX     Unsigned32 (0..2147483647)
   ACCESS     read-write
   STATUS     mandatory
   DESCRIPTION
     "This variable represents an individual value for the
      mscAtmIfVptIispSigVcdTdpTable."
::= { mscAtmIfVptIispSigVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

mscAtmIfVptIispAddr OBJECT IDENTIFIER ::= { mscAtmIfVptIisp 4 }



mscAtmIfVptIispAddrRowStatusTable OBJECT-TYPE
   SYNTAX     SEQUENCE OF MscAtmIfVptIispAddrRowStatusEntry
   ACCESS     not-accessible
   STATUS     mandatory
   DESCRIPTION
     "This entry controls the addition and deletion of 
      mscAtmIfVptIispAddr components."
::= { mscAtmIfVptIispAddr 1 }

mscAtmIfVptIispAddrRowStatusEntry OBJECT-TYPE
   SYNTAX     MscAtmIfVptIispAddrRowStatusEntry
   ACCESS     not-accessible
   STATUS     mandatory
   DESCRIPTION
     "A single entry in the table represents a single 
      mscAtmIfVptIispAddr component."
   INDEX {
      mscAtmIfIndex,
      mscAtmIfVptIndex,
      mscAtmIfVptIispIndex,
      mscAtmIfVptIispAddrAddressIndex,
      mscAtmIfVptIispAddrAddressTypeIndex }
::= { mscAtmIfVptIispAddrRowStatusTable 1 }

MscAtmIfVptIispAddrRowStatusEntry ::= SEQUENCE {
   mscAtmIfVptIispAddrRowStatus
      RowStatus,
   mscAtmIfVptIispAddrComponentName
      DisplayString,
   mscAtmIfVptIispAddrStorageType
      StorageType,
   mscAtmIfVptIispAddrAddressIndex
      AsciiStringIndex,
   mscAtmIfVptIispAddrAddressTypeIndex
      INTEGER }

mscAtmIfVptIispAddrRowStatus OBJECT-TYPE
   SYNTAX     RowStatus 
   ACCESS     read-write
   STATUS     mandatory
   DESCRIPTION
     "This variable is used as the basis for SNMP naming of
      mscAtmIfVptIispAddr components.
      These components can be added and deleted."
::= { mscAtmIfVptIispAddrRowStatusEntry 1 }

mscAtmIfVptIispAddrComponentName OBJECT-TYPE
   SYNTAX     DisplayString 
   ACCESS     read-only
   STATUS     mandatory
   DESCRIPTION
     "This variable provides the component's string name for
      use with the ASCII Console Interface"
::= { mscAtmIfVptIispAddrRowStatusEntry 2 }

mscAtmIfVptIispAddrStorageType OBJECT-TYPE
   SYNTAX     StorageType 
   ACCESS     read-only
   STATUS     mandatory
   DESCRIPTION
     "This variable represents the storage type value for the
      mscAtmIfVptIispAddr tables."
::= { mscAtmIfVptIispAddrRowStatusEntry 4 }

mscAtmIfVptIispAddrAddressIndex OBJECT-TYPE
   SYNTAX     AsciiStringIndex (SIZE (1..40))
   ACCESS     not-accessible
   STATUS     mandatory
   DESCRIPTION
     "This variable represents an index for the mscAtmIfVptIispAddr tables."
::= { mscAtmIfVptIispAddrRowStatusEntry 10 }

mscAtmIfVptIispAddrAddressTypeIndex OBJECT-TYPE
   SYNTAX     INTEGER  {
                 primary(0),
                 alternate(1),
                 default(3) }
   ACCESS     not-accessible
   STATUS     mandatory
   DESCRIPTION
     "This variable represents an index for the mscAtmIfVptIispAddr tables."
::= { mscAtmIfVptIispAddrRowStatusEntry 11 }

mscAtmIfVptIispAddrOperTable OBJECT-TYPE
   SYNTAX     SEQUENCE OF MscAtmIfVptIispAddrOperEntry
   ACCESS     not-accessible
   STATUS     mandatory
   DESCRIPTION
     "This attribute group contains the operational attributes for the 
      Address component."
::= { mscAtmIfVptIispAddr 10 }

mscAtmIfVptIispAddrOperEntry OBJECT-TYPE
   SYNTAX     MscAtmIfVptIispAddrOperEntry
   ACCESS     not-accessible
   STATUS     mandatory
   DESCRIPTION
     "An entry in the mscAtmIfVptIispAddrOperTable."
   INDEX {
      mscAtmIfIndex,
      mscAtmIfVptIndex,
      mscAtmIfVptIispIndex,
      mscAtmIfVptIispAddrAddressIndex,
      mscAtmIfVptIispAddrAddressTypeIndex }
::= { mscAtmIfVptIispAddrOperTable 1 }

MscAtmIfVptIispAddrOperEntry ::= SEQUENCE {
   mscAtmIfVptIispAddrScope
      INTEGER,
   mscAtmIfVptIispAddrReachability
      INTEGER }

mscAtmIfVptIispAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { mscAtmIfVptIispAddrOperEntry 1 }

mscAtmIfVptIispAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { mscAtmIfVptIispAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

mscAtmIfVptIispAddrTermSP OBJECT IDENTIFIER ::= { mscAtmIfVptIispAddr 2 }



mscAtmIfVptIispAddrTermSPRowStatusTable OBJECT-TYPE
   SYNTAX     SEQUENCE OF MscAtmIfVptIispAddrTermSPRowStatusEntry
   ACCESS     not-accessible
   STATUS     mandatory
   DESCRIPTION
     "This entry controls the addition and deletion of 
      mscAtmIfVptIispAddrTermSP components."
::= { mscAtmIfVptIispAddrTermSP 1 }

mscAtmIfVptIispAddrTermSPRowStatusEntry OBJECT-TYPE
   SYNTAX     MscAtmIfVptIispAddrTermSPRowStatusEntry
   ACCESS     not-accessible
   STATUS     mandatory
   DESCRIPTION
     "A single entry in the table represents a single 
      mscAtmIfVptIispAddrTermSP component."
   INDEX {
      mscAtmIfIndex,
      mscAtmIfVptIndex,
      mscAtmIfVptIispIndex,
      mscAtmIfVptIispAddrAddressIndex,
      mscAtmIfVptIispAddrAddressTypeIndex,
      mscAtmIfVptIispAddrTermSPIndex }
::= { mscAtmIfVptIispAddrTermSPRowStatusTable 1 }

MscAtmIfVptIispAddrTermSPRowStatusEntry ::= SEQUENCE {
   mscAtmIfVptIispAddrTermSPRowStatus
      RowStatus,
   mscAtmIfVptIispAddrTermSPComponentName
      DisplayString,
   mscAtmIfVptIispAddrTermSPStorageType
      StorageType,
   mscAtmIfVptIispAddrTermSPIndex
      NonReplicated }

mscAtmIfVptIispAddrTermSPRowStatus OBJECT-TYPE
   SYNTAX     RowStatus 
   ACCESS     read-write
   STATUS     mandatory
   DESCRIPTION
     "This variable is used as the basis for SNMP naming of
      mscAtmIfVptIispAddrTermSP components.
      These components can be added and deleted."
::= { mscAtmIfVptIispAddrTermSPRowStatusEntry 1 }

mscAtmIfVptIispAddrTermSPComponentName OBJECT-TYPE
   SYNTAX     DisplayString 
   ACCESS     read-only
   STATUS     mandatory
   DESCRIPTION
     "This variable provides the component's string name for
      use with the ASCII Console Interface"
::= { mscAtmIfVptIispAddrTermSPRowStatusEntry 2 }

mscAtmIfVptIispAddrTermSPStorageType OBJECT-TYPE
   SYNTAX     StorageType 
   ACCESS     read-only
   STATUS     mandatory
   DESCRIPTION
     "This variable represents the storage type value for the
      mscAtmIfVptIispAddrTermSP tables."
::= { mscAtmIfVptIispAddrTermSPRowStatusEntry 4 }

mscAtmIfVptIispAddrTermSPIndex OBJECT-TYPE
   SYNTAX     NonReplicated 
   ACCESS     not-accessible
   STATUS     mandatory
   DESCRIPTION
     "This variable represents the index for the mscAtmIfVptIispAddrTermSP tables."
::= { mscAtmIfVptIispAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

mscAtmIfVptIispAddrPnniInfo OBJECT IDENTIFIER ::= { mscAtmIfVptIispAddr 3 }



mscAtmIfVptIispAddrPnniInfoRowStatusTable OBJECT-TYPE
   SYNTAX     SEQUENCE OF MscAtmIfVptIispAddrPnniInfoRowStatusEntry
   ACCESS     not-accessible
   STATUS     mandatory
   DESCRIPTION
     "This entry controls the addition and deletion of 
      mscAtmIfVptIispAddrPnniInfo components."
::= { mscAtmIfVptIispAddrPnniInfo 1 }

mscAtmIfVptIispAddrPnniInfoRowStatusEntry OBJECT-TYPE
   SYNTAX     MscAtmIfVptIispAddrPnniInfoRowStatusEntry
   ACCESS     not-accessible
   STATUS     mandatory
   DESCRIPTION
     "A single entry in the table represents a single 
      mscAtmIfVptIispAddrPnniInfo component."
   INDEX {
      mscAtmIfIndex,
      mscAtmIfVptIndex,
      mscAtmIfVptIispIndex,
      mscAtmIfVptIispAddrAddressIndex,
      mscAtmIfVptIispAddrAddressTypeIndex,
      mscAtmIfVptIispAddrPnniInfoIndex }
::= { mscAtmIfVptIispAddrPnniInfoRowStatusTable 1 }

MscAtmIfVptIispAddrPnniInfoRowStatusEntry ::= SEQUENCE {
   mscAtmIfVptIispAddrPnniInfoRowStatus
      RowStatus,
   mscAtmIfVptIispAddrPnniInfoComponentName
      DisplayString,
   mscAtmIfVptIispAddrPnniInfoStorageType
      StorageType,
   mscAtmIfVptIispAddrPnniInfoIndex
      NonReplicated }

mscAtmIfVptIispAddrPnniInfoRowStatus OBJECT-TYPE
   SYNTAX     RowStatus 
   ACCESS     read-write
   STATUS     mandatory
   DESCRIPTION
     "This variable is used as the basis for SNMP naming of
      mscAtmIfVptIispAddrPnniInfo components.
      These components can be added and deleted."
::= { mscAtmIfVptIispAddrPnniInfoRowStatusEntry 1 }

mscAtmIfVptIispAddrPnniInfoComponentName OBJECT-TYPE
   SYNTAX     DisplayString 
   ACCESS     read-only
   STATUS     mandatory
   DESCRIPTION
     "This variable provides the component's string name for
      use with the ASCII Console Interface"
::= { mscAtmIfVptIispAddrPnniInfoRowStatusEntry 2 }

mscAtmIfVptIispAddrPnniInfoStorageType OBJECT-TYPE
   SYNTAX     StorageType 
   ACCESS     read-only
   STATUS     mandatory
   DESCRIPTION
     "This variable represents the storage type value for the
      mscAtmIfVptIispAddrPnniInfo tables."
::= { mscAtmIfVptIispAddrPnniInfoRowStatusEntry 4 }

mscAtmIfVptIispAddrPnniInfoIndex OBJECT-TYPE
   SYNTAX     NonReplicated 
   ACCESS     not-accessible
   STATUS     mandatory
   DESCRIPTION
     "This variable represents the index for the mscAtmIfVptIispAddrPnniInfo tables."
::= { mscAtmIfVptIispAddrPnniInfoRowStatusEntry 10 }

mscAtmIfVptIispAddrPnniInfoProvTable OBJECT-TYPE
   SYNTAX     SEQUENCE OF MscAtmIfVptIispAddrPnniInfoProvEntry
   ACCESS     not-accessible
   STATUS     mandatory
   DESCRIPTION
     "This attribute group contains the provisioned attributes relating to 
      PNNI for a PnniInfo component."
::= { mscAtmIfVptIispAddrPnniInfo 10 }

mscAtmIfVptIispAddrPnniInfoProvEntry OBJECT-TYPE
   SYNTAX     MscAtmIfVptIispAddrPnniInfoProvEntry
   ACCESS     not-accessible
   STATUS     mandatory
   DESCRIPTION
     "An entry in the mscAtmIfVptIispAddrPnniInfoProvTable."
   INDEX {
      mscAtmIfIndex,
      mscAtmIfVptIndex,
      mscAtmIfVptIispIndex,
      mscAtmIfVptIispAddrAddressIndex,
      mscAtmIfVptIispAddrAddressTypeIndex,
      mscAtmIfVptIispAddrPnniInfoIndex }
::= { mscAtmIfVptIispAddrPnniInfoProvTable 1 }

MscAtmIfVptIispAddrPnniInfoProvEntry ::= SEQUENCE {
   mscAtmIfVptIispAddrPnniInfoScope
      INTEGER,
   mscAtmIfVptIispAddrPnniInfoReachability
      INTEGER }

mscAtmIfVptIispAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { mscAtmIfVptIispAddrPnniInfoProvEntry 1 }

mscAtmIfVptIispAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { mscAtmIfVptIispAddrPnniInfoProvEntry 2 }


-- AtmIf/n Uni CallingAddressScreening
-- AtmIf/n Iisp CallingAddressScreening
-- This component represents the screening of incoming ATM SVC 
-- call requests against provisioned ATM calling addresses (that is, 
-- screening SVC calls coming from specific addresses). If this 
-- component is not provisioned, all call requests are accepted and no 
-- calling address screening takes place. 

mscAtmIfVptIispCallingAScr OBJECT IDENTIFIER ::= { mscAtmIfVptIisp 5 }



mscAtmIfVptIispCallingAScrRowStatusTable OBJECT-TYPE
   SYNTAX     SEQUENCE OF MscAtmIfVptIispCallingAScrRowStatusEntry
   ACCESS     not-accessible
   STATUS     mandatory
   DESCRIPTION
     "This entry controls the addition and deletion of 
      mscAtmIfVptIispCallingAScr components."
::= { mscAtmIfVptIispCallingAScr 1 }

mscAtmIfVptIispCallingAScrRowStatusEntry OBJECT-TYPE
   SYNTAX     MscAtmIfVptIispCallingAScrRowStatusEntry
   ACCESS     not-accessible
   STATUS     mandatory
   DESCRIPTION
     "A single entry in the table represents a single 
      mscAtmIfVptIispCallingAScr component."
   INDEX {
      mscAtmIfIndex,
      mscAtmIfVptIndex,
      mscAtmIfVptIispIndex,
      mscAtmIfVptIispCallingAScrIndex }
::= { mscAtmIfVptIispCallingAScrRowStatusTable 1 }

MscAtmIfVptIispCallingAScrRowStatusEntry ::= SEQUENCE {
   mscAtmIfVptIispCallingAScrRowStatus
      RowStatus,
   mscAtmIfVptIispCallingAScrComponentName
      DisplayString,
   mscAtmIfVptIispCallingAScrStorageType
      StorageType,
   mscAtmIfVptIispCallingAScrIndex
      NonReplicated }

mscAtmIfVptIispCallingAScrRowStatus OBJECT-TYPE
   SYNTAX     RowStatus 
   ACCESS     read-write
   STATUS     mandatory
   DESCRIPTION
     "This variable is used as the basis for SNMP naming of
      mscAtmIfVptIispCallingAScr components.
      These components can be added and deleted."
::= { mscAtmIfVptIispCallingAScrRowStatusEntry 1 }

mscAtmIfVptIispCallingAScrComponentName OBJECT-TYPE
   SYNTAX     DisplayString 
   ACCESS     read-only
   STATUS     mandatory
   DESCRIPTION
     "This variable provides the component's string name for
      use with the ASCII Console Interface"
::= { mscAtmIfVptIispCallingAScrRowStatusEntry 2 }

mscAtmIfVptIispCallingAScrStorageType OBJECT-TYPE
   SYNTAX     StorageType 
   ACCESS     read-only
   STATUS     mandatory
   DESCRIPTION
     "This variable represents the storage type value for the
      mscAtmIfVptIispCallingAScr tables."
::= { mscAtmIfVptIispCallingAScrRowStatusEntry 4 }

mscAtmIfVptIispCallingAScrIndex OBJECT-TYPE
   SYNTAX     NonReplicated 
   ACCESS     not-accessible
   STATUS     mandatory
   DESCRIPTION
     "This variable represents the index for the mscAtmIfVptIispCallingAScr tables."
::= { mscAtmIfVptIispCallingAScrRowStatusEntry 10 }

mscAtmIfVptIispCallingAScrProvTable OBJECT-TYPE
   SYNTAX     SEQUENCE OF MscAtmIfVptIispCallingAScrProvEntry
   ACCESS     not-accessible
   STATUS     mandatory
   DESCRIPTION
     "This attribute group contains the provisionable attributes for the 
      CallingAScr component."
::= { mscAtmIfVptIispCallingAScr 10 }

mscAtmIfVptIispCallingAScrProvEntry OBJECT-TYPE
   SYNTAX     MscAtmIfVptIispCallingAScrProvEntry
   ACCESS     not-accessible
   STATUS     mandatory
   DESCRIPTION
     "An entry in the mscAtmIfVptIispCallingAScrProvTable."
   INDEX {
      mscAtmIfIndex,
      mscAtmIfVptIndex,
      mscAtmIfVptIispIndex,
      mscAtmIfVptIispCallingAScrIndex }
::= { mscAtmIfVptIispCallingAScrProvTable 1 }

MscAtmIfVptIispCallingAScrProvEntry ::= SEQUENCE {
   mscAtmIfVptIispCallingAScrAdminStatus
      INTEGER,
   mscAtmIfVptIispCallingAScrDefaultInsertionAddress
      HexString }

mscAtmIfVptIispCallingAScrAdminStatus OBJECT-TYPE
   SYNTAX     INTEGER  {
                 enabled(0),
                 disabled(1) }
   ACCESS     read-write
   STATUS     mandatory
   DESCRIPTION
     "This attribute specifies whether the calling address screening feature 
      is enabled or disabled. 
      
      If enabled, incoming SVC calls are screened against provisioned 
      addresses. If enabled and the calling address in the ATM SVC call 
      request is provisioned to be accepted, the call is accepted or rejected 
      according to the action specified for that address. If the value is 
      enabled, and the calling address in the address request is not 
      provisioned, the call is rejected
      
      If the value is disabled, no calling address screening is performed."
   DEFVAL     { disabled }
::= { mscAtmIfVptIispCallingAScrProvEntry 1 }

mscAtmIfVptIispCallingAScrDefaultInsertionAddress OBJECT-TYPE
   SYNTAX     HexString (SIZE (0..20))
   ACCESS     read-write
   STATUS     mandatory
   DESCRIPTION
     "This attribute specifies the address to be inserted into the SVC 
      connection request if adminStatus is enabled and the connection 
      request does not contain a calling address. If the adminStatus 
      attribute is enabled and this attribute is empty, all incoming SVC 
      calls which do not contain a calling address are rejected."
   DEFVAL     { ''H }  -- ""
::= { mscAtmIfVptIispCallingAScrProvEntry 2 }

mscAtmIfVptIispCallingAScrStatTable OBJECT-TYPE
   SYNTAX     SEQUENCE OF MscAtmIfVptIispCallingAScrStatEntry
   ACCESS     not-accessible
   STATUS     mandatory
   DESCRIPTION
     "This attribute group contains statistics related to the incoming SVC 
      call requests received while the adminStatus attribute is set to 
      enabled."
::= { mscAtmIfVptIispCallingAScr 11 }

mscAtmIfVptIispCallingAScrStatEntry OBJECT-TYPE
   SYNTAX     MscAtmIfVptIispCallingAScrStatEntry
   ACCESS     not-accessible
   STATUS     mandatory
   DESCRIPTION
     "An entry in the mscAtmIfVptIispCallingAScrStatTable."
   INDEX {
      mscAtmIfIndex,
      mscAtmIfVptIndex,
      mscAtmIfVptIispIndex,
      mscAtmIfVptIispCallingAScrIndex }
::= { mscAtmIfVptIispCallingAScrStatTable 1 }

MscAtmIfVptIispCallingAScrStatEntry ::= SEQUENCE {
   mscAtmIfVptIispCallingAScrAcceptedCalls
      Counter32,
   mscAtmIfVptIispCallingAScrRejectedCalls
      Counter32,
   mscAtmIfVptIispCallingAScrUnmatchedCalls
      Counter32 }

mscAtmIfVptIispCallingAScrAcceptedCalls OBJECT-TYPE
   SYNTAX     Counter32 
   ACCESS     read-only
   STATUS     mandatory
   DESCRIPTION
     "This attribute counts the incoming SVC calls which were accepted 
      because the address specified in the call request matched a 
      provisioned ATM address and the associated action was accept.
      When the counter exceeds the maximum, it wraps to 0."
::= { mscAtmIfVptIispCallingAScrStatEntry 1 }

mscAtmIfVptIispCallingAScrRejectedCalls OBJECT-TYPE
   SYNTAX     Counter32 
   ACCESS     read-only
   STATUS     mandatory
   DESCRIPTION
     "This attribute counts the incoming SVC calls which were rejected 
      because the address specified in the call request matched a 
      provisioned ATM address, but the associated action was reject. 
      When the counter exceeds the maximum, it wraps to 0."
::= { mscAtmIfVptIispCallingAScrStatEntry 2 }

mscAtmIfVptIispCallingAScrUnmatchedCalls OBJECT-TYPE
   SYNTAX     Counter32 
   ACCESS     read-only
   STATUS     mandatory
   DESCRIPTION
     "This attribute counts the incoming SVC calls which were rejected 
      because none of the provisioned ATM addresses matched the 
      applicable address in the incoming SVC call request.
      When the counter exceeds the maximum, it wraps to 0."
::= { mscAtmIfVptIispCallingAScrStatEntry 3 }


-- AtmIf/n Uni CallingAScr Address/addr,action
-- AtmIf/n Iisp CallingAScr Address/addr,action 
-- AtmIf/n Uni CalledAScr Address/addr,action 
-- AtmIf/n Iisp CalledAScr Address/addr,action 
-- This component specifies a calling (or called) address with an 
-- action to accept or reject a connection request which contains a 
-- matching calling (or called) address.
-- For the Calling Address Screening feature, if the specified action is 
-- accept, any call whose calling address matches that address is 
-- accepted. If the specified action is reject, any call whose calling 
-- address matches that address is rejected.
-- For the Called Address Screening feature, if the specified action is 
-- accept, any call whose called address matches that address, is 
-- accepted. If the specified action is reject, any call whose called 
-- address matches that address is rejected.
-- For both features, the incoming SVC call request is rejected if the 
-- address is not provisioned and the feature is enabled.

mscAtmIfVptIispCallingAScrAddr OBJECT IDENTIFIER ::= { mscAtmIfVptIispCallingAScr 2 }



mscAtmIfVptIispCallingAScrAddrRowStatusTable OBJECT-TYPE
   SYNTAX     SEQUENCE OF MscAtmIfVptIispCallingAScrAddrRowStatusEntry
   ACCESS     not-accessible
   STATUS     mandatory
   DESCRIPTION
     "This entry controls the addition and deletion of 
      mscAtmIfVptIispCallingAScrAddr components."
::= { mscAtmIfVptIispCallingAScrAddr 1 }

mscAtmIfVptIispCallingAScrAddrRowStatusEntry OBJECT-TYPE
   SYNTAX     MscAtmIfVptIispCallingAScrAddrRowStatusEntry
   ACCESS     not-accessible
   STATUS     mandatory
   DESCRIPTION
     "A single entry in the table represents a single 
      mscAtmIfVptIispCallingAScrAddr component."
   INDEX {
      mscAtmIfIndex,
      mscAtmIfVptIndex,
      mscAtmIfVptIispIndex,
      mscAtmIfVptIispCallingAScrIndex,
      mscAtmIfVptIispCallingAScrAddrAddressIndex,
      mscAtmIfVptIispCallingAScrAddrAddressActionIndex }
::= { mscAtmIfVptIispCallingAScrAddrRowStatusTable 1 }

MscAtmIfVptIispCallingAScrAddrRowStatusEntry ::= SEQUENCE {
   mscAtmIfVptIispCallingAScrAddrRowStatus
      RowStatus,
   mscAtmIfVptIispCallingAScrAddrComponentName
      DisplayString,
   mscAtmIfVptIispCallingAScrAddrStorageType
      StorageType,
   mscAtmIfVptIispCallingAScrAddrAddressIndex
      AsciiStringIndex,
   mscAtmIfVptIispCallingAScrAddrAddressActionIndex
      INTEGER }

mscAtmIfVptIispCallingAScrAddrRowStatus OBJECT-TYPE
   SYNTAX     RowStatus 
   ACCESS     read-write
   STATUS     mandatory
   DESCRIPTION
     "This variable is used as the basis for SNMP naming of
      mscAtmIfVptIispCallingAScrAddr components.
      These components can be added and deleted."
::= { mscAtmIfVptIispCallingAScrAddrRowStatusEntry 1 }

mscAtmIfVptIispCallingAScrAddrComponentName OBJECT-TYPE
   SYNTAX     DisplayString 
   ACCESS     read-only
   STATUS     mandatory
   DESCRIPTION
     "This variable provides the component's string name for
      use with the ASCII Console Interface"
::= { mscAtmIfVptIispCallingAScrAddrRowStatusEntry 2 }

mscAtmIfVptIispCallingAScrAddrStorageType OBJECT-TYPE
   SYNTAX     StorageType 
   ACCESS     read-only
   STATUS     mandatory
   DESCRIPTION
     "This variable represents the storage type value for the
      mscAtmIfVptIispCallingAScrAddr tables."
::= { mscAtmIfVptIispCallingAScrAddrRowStatusEntry 4 }

mscAtmIfVptIispCallingAScrAddrAddressIndex OBJECT-TYPE
   SYNTAX     AsciiStringIndex (SIZE (1..40))
   ACCESS     not-accessible
   STATUS     mandatory
   DESCRIPTION
     "This variable represents an index for the mscAtmIfVptIispCallingAScrAddr tables."
::= { mscAtmIfVptIispCallingAScrAddrRowStatusEntry 10 }

mscAtmIfVptIispCallingAScrAddrAddressActionIndex OBJECT-TYPE
   SYNTAX     INTEGER  {
                 accept(0),
                 reject(1) }
   ACCESS     not-accessible
   STATUS     mandatory
   DESCRIPTION
     "This variable represents an index for the mscAtmIfVptIispCallingAScrAddr tables."
::= { mscAtmIfVptIispCallingAScrAddrRowStatusEntry 11 }


-- AtmIf/n Uni CalledAddressScreening
-- AtmIf/n Iisp CalledAddressScreening
-- This component represents the screening of incoming ATM SVC 
-- call requests against provisioned ATM called addresses (that is, 
-- going to specific destinations). If this component is not provisioned, 
-- all call requests are accepted and no called address screening takes 
-- place.

mscAtmIfVptIispCalledAScr OBJECT IDENTIFIER ::= { mscAtmIfVptIisp 6 }



mscAtmIfVptIispCalledAScrRowStatusTable OBJECT-TYPE
   SYNTAX     SEQUENCE OF MscAtmIfVptIispCalledAScrRowStatusEntry
   ACCESS     not-accessible
   STATUS     mandatory
   DESCRIPTION
     "This entry controls the addition and deletion of 
      mscAtmIfVptIispCalledAScr components."
::= { mscAtmIfVptIispCalledAScr 1 }

mscAtmIfVptIispCalledAScrRowStatusEntry OBJECT-TYPE
   SYNTAX     MscAtmIfVptIispCalledAScrRowStatusEntry
   ACCESS     not-accessible
   STATUS     mandatory
   DESCRIPTION
     "A single entry in the table represents a single 
      mscAtmIfVptIispCalledAScr component."
   INDEX {
      mscAtmIfIndex,
      mscAtmIfVptIndex,
      mscAtmIfVptIispIndex,
      mscAtmIfVptIispCalledAScrIndex }
::= { mscAtmIfVptIispCalledAScrRowStatusTable 1 }

MscAtmIfVptIispCalledAScrRowStatusEntry ::= SEQUENCE {
   mscAtmIfVptIispCalledAScrRowStatus
      RowStatus,
   mscAtmIfVptIispCalledAScrComponentName
      DisplayString,
   mscAtmIfVptIispCalledAScrStorageType
      StorageType,
   mscAtmIfVptIispCalledAScrIndex
      NonReplicated }

mscAtmIfVptIispCalledAScrRowStatus OBJECT-TYPE
   SYNTAX     RowStatus 
   ACCESS     read-write
   STATUS     mandatory
   DESCRIPTION
     "This variable is used as the basis for SNMP naming of
      mscAtmIfVptIispCalledAScr components.
      These components can be added and deleted."
::= { mscAtmIfVptIispCalledAScrRowStatusEntry 1 }

mscAtmIfVptIispCalledAScrComponentName OBJECT-TYPE
   SYNTAX     DisplayString 
   ACCESS     read-only
   STATUS     mandatory
   DESCRIPTION
     "This variable provides the component's string name for
      use with the ASCII Console Interface"
::= { mscAtmIfVptIispCalledAScrRowStatusEntry 2 }

mscAtmIfVptIispCalledAScrStorageType OBJECT-TYPE
   SYNTAX     StorageType 
   ACCESS     read-only
   STATUS     mandatory
   DESCRIPTION
     "This variable represents the storage type value for the
      mscAtmIfVptIispCalledAScr tables."
::= { mscAtmIfVptIispCalledAScrRowStatusEntry 4 }

mscAtmIfVptIispCalledAScrIndex OBJECT-TYPE
   SYNTAX     NonReplicated 
   ACCESS     not-accessible
   STATUS     mandatory
   DESCRIPTION
     "This variable represents the index for the mscAtmIfVptIispCalledAScr tables."
::= { mscAtmIfVptIispCalledAScrRowStatusEntry 10 }

mscAtmIfVptIispCalledAScrProvTable OBJECT-TYPE
   SYNTAX     SEQUENCE OF MscAtmIfVptIispCalledAScrProvEntry
   ACCESS     not-accessible
   STATUS     mandatory
   DESCRIPTION
     "This attribute group contains the provisionable attributes for the 
      CalledAScr component."
::= { mscAtmIfVptIispCalledAScr 10 }

mscAtmIfVptIispCalledAScrProvEntry OBJECT-TYPE
   SYNTAX     MscAtmIfVptIispCalledAScrProvEntry
   ACCESS     not-accessible
   STATUS     mandatory
   DESCRIPTION
     "An entry in the mscAtmIfVptIispCalledAScrProvTable."
   INDEX {
      mscAtmIfIndex,
      mscAtmIfVptIndex,
      mscAtmIfVptIispIndex,
      mscAtmIfVptIispCalledAScrIndex }
::= { mscAtmIfVptIispCalledAScrProvTable 1 }

MscAtmIfVptIispCalledAScrProvEntry ::= SEQUENCE {
   mscAtmIfVptIispCalledAScrAdminStatus
      INTEGER }

mscAtmIfVptIispCalledAScrAdminStatus OBJECT-TYPE
   SYNTAX     INTEGER  {
                 enabled(0),
                 disabled(1) }
   ACCESS     read-write
   STATUS     mandatory
   DESCRIPTION
     "This attribute specifies whether the called address screening feature 
      is enabled or disabled.
      If the value is enabled, incoming SVC calls will be screened against 
      provisioned called addresses. If the value is enabled and the called 
      address in the ATM SVC call request has been provisioned, the call 
      is accepted or rejected according to the action specified for that 
      address. If the value is enabled and the called address in the call 
      request is not provisioned, the call is rejected.
      If the value is disabled, no called address screening is performed."
   DEFVAL     { disabled }
::= { mscAtmIfVptIispCalledAScrProvEntry 1 }

mscAtmIfVptIispCalledAScrStatTable OBJECT-TYPE
   SYNTAX     SEQUENCE OF MscAtmIfVptIispCalledAScrStatEntry
   ACCESS     not-accessible
   STATUS     mandatory
   DESCRIPTION
     "This attribute group contains statistics related to the incoming SVC 
      call requests received while the adminStatus attribute is set to 
      enabled."
::= { mscAtmIfVptIispCalledAScr 11 }

mscAtmIfVptIispCalledAScrStatEntry OBJECT-TYPE
   SYNTAX     MscAtmIfVptIispCalledAScrStatEntry
   ACCESS     not-accessible
   STATUS     mandatory
   DESCRIPTION
     "An entry in the mscAtmIfVptIispCalledAScrStatTable."
   INDEX {
      mscAtmIfIndex,
      mscAtmIfVptIndex,
      mscAtmIfVptIispIndex,
      mscAtmIfVptIispCalledAScrIndex }
::= { mscAtmIfVptIispCalledAScrStatTable 1 }

MscAtmIfVptIispCalledAScrStatEntry ::= SEQUENCE {
   mscAtmIfVptIispCalledAScrAcceptedCalls
      Counter32,
   mscAtmIfVptIispCalledAScrRejectedCalls
      Counter32,
   mscAtmIfVptIispCalledAScrUnmatchedCalls
      Counter32 }

mscAtmIfVptIispCalledAScrAcceptedCalls OBJECT-TYPE
   SYNTAX     Counter32 
   ACCESS     read-only
   STATUS     mandatory
   DESCRIPTION
     "This attribute counts the incoming SVC calls which were accepted 
      because the address specified in the call request matched a 
      provisioned ATM address and the associated action was accept.
      When the counter exceeds the maximum, it wraps to 0."
::= { mscAtmIfVptIispCalledAScrStatEntry 1 }

mscAtmIfVptIispCalledAScrRejectedCalls OBJECT-TYPE
   SYNTAX     Counter32 
   ACCESS     read-only
   STATUS     mandatory
   DESCRIPTION
     "This attribute counts the incoming SVC calls which were rejected 
      because the address specified in the call request matched a 
      provisioned ATM address, but the associated action was reject. 
      When the counter exceeds the maximum, it wraps to 0."
::= { mscAtmIfVptIispCalledAScrStatEntry 2 }

mscAtmIfVptIispCalledAScrUnmatchedCalls OBJECT-TYPE
   SYNTAX     Counter32 
   ACCESS     read-only
   STATUS     mandatory
   DESCRIPTION
     "This attribute counts the incoming SVC calls which were rejected 
      because none of the provisioned ATM addresses matched the 
      applicable address in the incoming SVC call request.
      When the counter exceeds the maximum, it wraps to 0."
::= { mscAtmIfVptIispCalledAScrStatEntry 3 }


-- AtmIf/n Uni CallingAScr Address/addr,action
-- AtmIf/n Iisp CallingAScr Address/addr,action 
-- AtmIf/n Uni CalledAScr Address/addr,action 
-- AtmIf/n Iisp CalledAScr Address/addr,action 
-- This component specifies a calling (or called) address with an 
-- action to accept or reject a connection request which contains a 
-- matching calling (or called) address.
-- For the Calling Address Screening feature, if the specified action is 
-- accept, any call whose calling address matches that address is 
-- accepted. If the specified action is reject, any call whose calling 
-- address matches that address is rejected.
-- For the Called Address Screening feature, if the specified action is 
-- accept, any call whose called address matches that address, is 
-- accepted. If the specified action is reject, any call whose called 
-- address matches that address is rejected.
-- For both features, the incoming SVC call request is rejected if the 
-- address is not provisioned and the feature is enabled.

mscAtmIfVptIispCalledAScrAddr OBJECT IDENTIFIER ::= { mscAtmIfVptIispCalledAScr 2 }



mscAtmIfVptIispCalledAScrAddrRowStatusTable OBJECT-TYPE
   SYNTAX     SEQUENCE OF MscAtmIfVptIispCalledAScrAddrRowStatusEntry
   ACCESS     not-accessible
   STATUS     mandatory
   DESCRIPTION
     "This entry controls the addition and deletion of 
      mscAtmIfVptIispCalledAScrAddr components."
::= { mscAtmIfVptIispCalledAScrAddr 1 }

mscAtmIfVptIispCalledAScrAddrRowStatusEntry OBJECT-TYPE
   SYNTAX     MscAtmIfVptIispCalledAScrAddrRowStatusEntry
   ACCESS     not-accessible
   STATUS     mandatory
   DESCRIPTION
     "A single entry in the table represents a single 
      mscAtmIfVptIispCalledAScrAddr component."
   INDEX {
      mscAtmIfIndex,
      mscAtmIfVptIndex,
      mscAtmIfVptIispIndex,
      mscAtmIfVptIispCalledAScrIndex,
      mscAtmIfVptIispCalledAScrAddrAddressIndex,
      mscAtmIfVptIispCalledAScrAddrAddressActionIndex }
::= { mscAtmIfVptIispCalledAScrAddrRowStatusTable 1 }

MscAtmIfVptIispCalledAScrAddrRowStatusEntry ::= SEQUENCE {
   mscAtmIfVptIispCalledAScrAddrRowStatus
      RowStatus,
   mscAtmIfVptIispCalledAScrAddrComponentName
      DisplayString,
   mscAtmIfVptIispCalledAScrAddrStorageType
      StorageType,
   mscAtmIfVptIispCalledAScrAddrAddressIndex
      AsciiStringIndex,
   mscAtmIfVptIispCalledAScrAddrAddressActionIndex
      INTEGER }

mscAtmIfVptIispCalledAScrAddrRowStatus OBJECT-TYPE
   SYNTAX     RowStatus 
   ACCESS     read-write
   STATUS     mandatory
   DESCRIPTION
     "This variable is used as the basis for SNMP naming of
      mscAtmIfVptIispCalledAScrAddr components.
      These components can be added and deleted."
::= { mscAtmIfVptIispCalledAScrAddrRowStatusEntry 1 }

mscAtmIfVptIispCalledAScrAddrComponentName OBJECT-TYPE
   SYNTAX     DisplayString 
   ACCESS     read-only
   STATUS     mandatory
   DESCRIPTION
     "This variable provides the component's string name for
      use with the ASCII Console Interface"
::= { mscAtmIfVptIispCalledAScrAddrRowStatusEntry 2 }

mscAtmIfVptIispCalledAScrAddrStorageType OBJECT-TYPE
   SYNTAX     StorageType 
   ACCESS     read-only
   STATUS     mandatory
   DESCRIPTION
     "This variable represents the storage type value for the
      mscAtmIfVptIispCalledAScrAddr tables."
::= { mscAtmIfVptIispCalledAScrAddrRowStatusEntry 4 }

mscAtmIfVptIispCalledAScrAddrAddressIndex OBJECT-TYPE
   SYNTAX     AsciiStringIndex (SIZE (1..40))
   ACCESS     not-accessible
   STATUS     mandatory
   DESCRIPTION
     "This variable represents an index for the mscAtmIfVptIispCalledAScrAddr tables."
::= { mscAtmIfVptIispCalledAScrAddrRowStatusEntry 10 }

mscAtmIfVptIispCalledAScrAddrAddressActionIndex OBJECT-TYPE
   SYNTAX     INTEGER  {
                 accept(0),
                 reject(1) }
   ACCESS     not-accessible
   STATUS     mandatory
   DESCRIPTION
     "This variable represents an index for the mscAtmIfVptIispCalledAScrAddr tables."
::= { mscAtmIfVptIispCalledAScrAddrRowStatusEntry 11 }




-- 
-- Version and Compliance statements
-- 



-- Object-Group Statement:
-- A list of all current accessible leaf objects.

-- OBJECTS { mscAtmIfVptIispSoftPvpAndPvcRetryPeriod,
--           mscAtmIfIispVersion,
--           mscAtmIfVptIispSigVcdAtmServiceCategory,
--           mscAtmIfIispAddrPnniInfoReachability,
--           mscAtmIfIispSigCurrentPmpConnections,
--           mscAtmIfVptIispServiceExchange,
--           mscAtmIfIispSigNewCurrentConnections,
--           mscAtmIfVptIispCallingAScrAcceptedCalls,
--           mscAtmIfVptIispAddrPnniInfoRowStatus,
--           mscAtmIfIispAddrRowStatus,
--           mscAtmIfVptIispSigAdminState,
--           mscAtmIfIispCalledAScrAcceptedCalls,
--           mscAtmIfIispCalledAScrAddrStorageType,
--           mscAtmIfIispSide,
--           mscAtmIfIispSigAddressConversion,
--           mscAtmIfIispComponentName,
--           mscAtmIfVptIispSigRowStatus,
--           mscAtmIfIispCalledAScrRejectedCalls,
--           mscAtmIfVptIispCallingAScrAddrStorageType,
--           mscAtmIfIispAddrTermSPStorageType,
--           mscAtmIfVptIispSigVcdTrafficShaping,
--           mscAtmIfIispSigVcdStorageType,
--           mscAtmIfVptIispCallingAScrRowStatus,
--           mscAtmIfVptIispSigOperatingMode,
--           mscAtmIfIispAccountConnectionType,
--           mscAtmIfVptIispCalledAScrAddrComponentName,
--           mscAtmIfIispAddrPnniInfoStorageType,
--           mscAtmIfIispSigFailedPmpConnections,
--           mscAtmIfVptIispSigSuccessfulConnections,
--           mscAtmIfVptIispCalledAScrRejectedCalls,
--           mscAtmIfIispSigPeakPmpConnections,
--           mscAtmIfIispSigRowStatus,
--           mscAtmIfVptIispAddrRowStatus,
--           mscAtmIfIispSigVci,
--           mscAtmIfIispCalledAScrRowStatus,
--           mscAtmIfIispCalledAScrUnmatchedCalls,
--           mscAtmIfVptIispCallingAScrStorageType,
--           mscAtmIfIispAddrScope,
--           mscAtmIfVptIispSigVcdQosClass,
--           mscAtmIfVptIispAddrComponentName,
--           mscAtmIfIispSigVcdUnshapedTransmitQueueing,
--           mscAtmIfIispAddrTermSPRowStatus,
--           mscAtmIfIispSigComponentName,
--           mscAtmIfIispSigVcdRowStatus,
--           mscAtmIfVptIispSigFailedConnections,
--           mscAtmIfVptIispSigCurrentPmpConnections,
--           mscAtmIfVptIispCalledAScrAdminStatus,
--           mscAtmIfIispCallingAScrComponentName,
--           mscAtmIfVptIispSigVcdWeight,
--           mscAtmIfVptIispSigVcdStorageType,
--           mscAtmIfVptIispSigLastRxCauseCode,
--           mscAtmIfVptIispAddrPnniInfoStorageType,
--           mscAtmIfIispAddrPnniInfoRowStatus,
--           mscAtmIfIispSigSuccessfulConnections,
--           mscAtmIfIispSigOperatingMode,
--           mscAtmIfVptIispSigAddressConversion,
--           mscAtmIfVptIispCalledAScrStorageType,
--           mscAtmIfVptIispCalledAScrAddrRowStatus,
--           mscAtmIfVptIispAddrPnniInfoComponentName,
--           mscAtmIfVptIispCallingAScrAddrRowStatus,
--           mscAtmIfIispAccountCollection,
--           mscAtmIfVptIispSigRxPdus,
--           mscAtmIfVptIispAddrTermSPStorageType,
--           mscAtmIfVptIispSide,
--           mscAtmIfIispAddrStorageType,
--           mscAtmIfIispStorageType,
--           mscAtmIfVptIispAddrPnniInfoReachability,
--           mscAtmIfIispSigRxPdus,
--           mscAtmIfVptIispSigLastRxDiagCode,
--           mscAtmIfVptIispCalledAScrUnmatchedCalls,
--           mscAtmIfVptIispSigLastTxCauseCode,
--           mscAtmIfVptIispSigPeakPmpConnections,
--           mscAtmIfIispSigSuccessfulPmpConnections,
--           mscAtmIfIispSigLastTxDiagCode,
--           mscAtmIfIispAddrReachability,
--           mscAtmIfVptIispVersion,
--           mscAtmIfIispSigFailedConnections,
--           mscAtmIfVptIispSigVcdTdpValue,
--           mscAtmIfVptIispSigVcdTrafficDescType,
--           mscAtmIfVptIispSigNewCurrentConnections,
--           mscAtmIfIispCallingAScrAddrComponentName,
--           mscAtmIfIispSigVcdUsageParameterControl,
--           mscAtmIfIispRowStatus,
--           mscAtmIfVptIispSigOperationalState,
--           mscAtmIfVptIispCallingAScrComponentName,
--           mscAtmIfIispCalledAScrStorageType,
--           mscAtmIfIispCallingAScrAdminStatus,
--           mscAtmIfIispSigStorageType,
--           mscAtmIfIispSoftPvpAndPvcHoldOffTime,
--           mscAtmIfIispCallingAScrAcceptedCalls,
--           mscAtmIfIispCallingAScrDefaultInsertionAddress,
--           mscAtmIfVptIispComponentName,
--           mscAtmIfVptIispAccountClass,
--           mscAtmIfIispSoftPvpAndPvcRetryPeriod,
--           mscAtmIfVptIispVpci,
--           mscAtmIfIispSigVcdAtmServiceCategory,
--           mscAtmIfIispAddrPnniInfoScope,
--           mscAtmIfVptIispCalledAScrComponentName,
--           mscAtmIfVptIispCallingAScrRejectedCalls,
--           mscAtmIfIispServiceExchange,
--           mscAtmIfVptIispAccountConnectionType,
--           mscAtmIfVptIispAddrPnniInfoScope,
--           mscAtmIfIispSigAdminState,
--           mscAtmIfVptIispSigFailedPmpConnections,
--           mscAtmIfVptIispAddrTermSPComponentName,
--           mscAtmIfIispAccountClass,
--           mscAtmIfIispCallingAScrUnmatchedCalls,
--           mscAtmIfIispSigVcdTdpValue,
--           mscAtmIfVptIispSigVci,
--           mscAtmIfVptIispCalledAScrRowStatus,
--           mscAtmIfVptIispSigSuccessfulPmpConnections,
--           mscAtmIfIispSigVcdTrafficDescType,
--           mscAtmIfVptIispCallingAScrAddrComponentName,
--           mscAtmIfVptIispSigVcdUnshapedTransmitQueueing,
--           mscAtmIfVptIispAddrTermSPRowStatus,
--           mscAtmIfVptIispSigComponentName,
--           mscAtmIfVptIispSigVcdRowStatus,
--           mscAtmIfIispAddrComponentName,
--           mscAtmIfIispSigUsageState,
--           mscAtmIfVptIispSigPeakConnections,
--           mscAtmIfIispCalledAScrAddrRowStatus,
--           mscAtmIfIispSigVcdWeight,
--           mscAtmIfVptIispAddrScope,
--           mscAtmIfVptIispSigTxPdus,
--           mscAtmIfIispSigTxPdus,
--           mscAtmIfIispSigLastRxCauseCode,
--           mscAtmIfIispCallingAScrAddrStorageType,
--           mscAtmIfIispCallingAScrStorageType,
--           mscAtmIfVptIispSigVcdComponentName,
--           mscAtmIfIispSigVcdQosClass,
--           mscAtmIfVptIispSigUsageState,
--           mscAtmIfVptIispAccountCollection,
--           mscAtmIfIispCallingAScrRejectedCalls,
--           mscAtmIfIispCalledAScrAddrComponentName,
--           mscAtmIfIispSigOperationalState,
--           mscAtmIfVptIispCallingAScrUnmatchedCalls,
--           mscAtmIfVptIispAddrStorageType,
--           mscAtmIfVptIispStorageType,
--           mscAtmIfIispCalledAScrComponentName,
--           mscAtmIfIispCalledAScrAdminStatus,
--           mscAtmIfVptIispCalledAScrAcceptedCalls,
--           mscAtmIfIispAddrTermSPComponentName,
--           mscAtmIfIispSigVcdComponentName,
--           mscAtmIfIispSigPeakConnections,
--           mscAtmIfVptIispSigVcdUsageParameterControl,
--           mscAtmIfVptIispAddrReachability,
--           mscAtmIfIispAddrPnniInfoComponentName,
--           mscAtmIfVptIispCalledAScrAddrStorageType,
--           mscAtmIfIispCallingAScrAddrRowStatus,
--           mscAtmIfIispCallingAScrRowStatus,
--           mscAtmIfIispSigVcdTrafficShaping,
--           mscAtmIfVptIispSigLastTxDiagCode,
--           mscAtmIfIispSigLastRxDiagCode,
--           mscAtmIfVptIispRowStatus,
--           mscAtmIfVptIispCallingAScrAdminStatus,
--           mscAtmIfIispSigLastTxCauseCode,
--           mscAtmIfVptIispSigStorageType,
--           mscAtmIfVptIispSoftPvpAndPvcHoldOffTime,
--           mscAtmIfVptIispCallingAScrDefaultInsertionAddress }
-- STATUS  mandatory
-- DESCRIPTION
--   "A list of all current accessible leaf objects."

atmIispGroup OBJECT IDENTIFIER ::= { atmIispMIB 1 }
atmIispGroupCA OBJECT IDENTIFIER ::= { atmIispGroup 1 }
atmIispGroupCA02 OBJECT IDENTIFIER ::= { atmIispGroupCA 3 }
atmIispGroupCA02A OBJECT IDENTIFIER ::= { atmIispGroupCA02 2 }



-- Agent-Capabilities Statement:

-- PRODUCT-RELEASE "MscPassport Release 1.2 AtmIisp."
-- STATUS          mandatory
-- DESCRIPTION     "Carrier Passport AtmIisp MIB: MIB Version CA02A,
--                  Software Version CA02S9C."
-- SUPPORTS        Nortel-MsCarrier-MscPassport-AtmIispMIB
--    INCLUDES     { atmIispGroupCA02A }

atmIispCapabilities OBJECT IDENTIFIER ::= { atmIispMIB 3 }
atmIispCapabilitiesCA OBJECT IDENTIFIER ::= { atmIispCapabilities 1 }
atmIispCapabilitiesCA02 OBJECT IDENTIFIER ::= { atmIispCapabilitiesCA 3 }
atmIispCapabilitiesCA02A OBJECT IDENTIFIER ::= { atmIispCapabilitiesCA02 2 }





END
