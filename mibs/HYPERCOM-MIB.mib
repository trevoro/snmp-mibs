-- hypercom MIB
    -- Request for Comments: Draft             Hypercom Inc.


       HYPERCOM-MIB DEFINITIONS ::= BEGIN


    -- Title:      Hypercom Concise MIB



    -- Rev  :      R2.0.0    24 APR. 1992
    --      :      R2.0.1    08 SEP. 1992
    --      :      R2.0.2    10 FEB. 1993
    --      :      R2.0.3    07 OCT. 1993
    --      :      R2.0.4    10 NOV. 1993
    --      :      R2.0.5    07 JAN. 1994
    --      :      R2.0.6    27 JAN. 1994
    --      :      R2.0.7    02 SEP. 1994
    --      :      R2.0.8    02 JUN. 1995
    --      :      R2.0.9    10 SEP  1995
    --      :      R2.1.0    03 OCT. 1995
	--		:	   R2.1.1	 30 SEP. 2002
	--      :      R2.1.2    06 NOV. 2002



       IMPORTS
           OBJECT-TYPE
               FROM RFC-1212
           enterprises, Counter, TimeTicks, NetworkAddress, Gauge
               FROM RFC1155-SMI
           mib-2
               FROM RFC1213-MIB
           MacAddress, DisplayString
               FROM SNMPv2-TC
           TRAP-TYPE
               FROM RFC-1215;



    --   MacAddress ::= OCTET STRING (SIZE (6))     (see RFC1286)


        hypercom           OBJECT IDENTIFIER ::= { enterprises 626 }
        hypercomIEN        OBJECT IDENTIFIER ::= { hypercom 2 }
        hypIenMib             OBJECT IDENTIFIER ::= { hypercomIEN 1 }

        hypSystem             OBJECT IDENTIFIER ::= { hypIenMib 1  }
        hypIp                 OBJECT IDENTIFIER ::= { hypIenMib 2  }
        hypIcmp               OBJECT IDENTIFIER ::= { hypIenMib 3  }
        hypTcp                OBJECT IDENTIFIER ::= { hypIenMib 4  }
        hypUdp                OBJECT IDENTIFIER ::= { hypIenMib 5  }
        hypIpx                OBJECT IDENTIFIER ::= { hypIenMib 6  }

        hypHdlc               OBJECT IDENTIFIER ::= { hypIenMib 7  }
        hypSdlc               OBJECT IDENTIFIER ::= { hypIenMib 8  }
        hypRtm                OBJECT IDENTIFIER ::= { hypIenMib 9  }
        hypX25                OBJECT IDENTIFIER ::= { hypIenMib 10 }
        hypX28                OBJECT IDENTIFIER ::= { hypIenMib 11 }
        hypSna                OBJECT IDENTIFIER ::= { hypIenMib 12 }

        hypFRelayMib          OBJECT IDENTIFIER ::= { hypIenMib 13 }
        hypDs1Mib             OBJECT IDENTIFIER ::= { hypIenMib 14 }
        hypLanBridgeRouter    OBJECT IDENTIFIER ::= { hypIenMib 15 }
        hypLanStatistics      OBJECT IDENTIFIER ::= { hypIenMib 16 }
        hypBridgeStations     OBJECT IDENTIFIER ::= { hypIenMib 17 }
        hypIpRemoteSubnets    OBJECT IDENTIFIER ::= { hypIenMib 18 }
        hypTokenRingIf        OBJECT IDENTIFIER ::= { hypIenMib 19 }
        hypRemoteLanSegList   OBJECT IDENTIFIER ::= { hypIenMib 20 }
        hypAlarmSystem        OBJECT IDENTIFIER ::= { hypIenMib 21 }
        hypAdmin              OBJECT IDENTIFIER ::= { hypIenMib 22 }

    -- NOTE: Hypercom TRAP's use  hypercomAlarmSystem for the
    --       ENTERPRISE keyword




    -- Future version of this Hypercom private MIB may contain the following:
    --
    -- (p45) IEN Node Port MEMORY access for retrieval, load, copy  (add to system group)
    -- (p31) Stat Threshold Parameters, also reset to default
    -- (p34) Reset NetView Alarm Counters
    -- (p38) DownLoad tables and configuration data
    -- (p53) Bus activity Statistics (incl clear counters)
    --
    -- (p54) VRU (Voice Rec) statistics
    -- (p56) Port Dial Out request and status (status may be a TRAP)
    -- (p60) High Speed Modem status
    -- Modem Eye Pattern Data Monitor
    -- IEN Node DCP/CAS related commands
    -- Test commands
    -- X.25 call establishment
    -- Downloadable system cfg, x.25/SNA  and HDLC/X.28
    -- CIM program download






    -- This is the Private MIB module for Hypercom IEN Systems.
    -- The following groups describe the variables within the Hypercom
    -- product lines. Specific groups may or may not be present
    -- depending on the actual installed card types and the software
    -- options present in the managed IEN device.




    --Table of hypIpTable
    --hypIpTable description (Table format)
    hypSysTableTable OBJECT-TYPE
        SYNTAX   SEQUENCE OF HypSysTableEntry
        ACCESS   not-accessible
        STATUS   mandatory
        DESCRIPTION
        "A table containing information about
         the Hypercom System"
        ::= { hypSystem 1 }

        hypSysTableEntry OBJECT-TYPE
        SYNTAX   HypSysTableEntry
        ACCESS   not-accessible
        STATUS   mandatory
        DESCRIPTION
        "Hypercom System Table"
        INDEX { hypSysTableIndex }
        ::= { hypSysTableTable 1 }

        HypSysTableEntry ::=
        SEQUENCE {
            hypSysBusAddr
                INTEGER,
            hypSysSwName
                DisplayString,
            hypPortMode
                DisplayString,
            hypSysStatus
                DisplayString,
            hypSysCuAddress
                INTEGER,
            hypSysModeSwitch1
                INTEGER,
            hypSysModeSwitch2
                INTEGER,
            hypSysUpTime
                INTEGER,
            hypSysDownTime
                INTEGER,
            hypSysRestart
                INTEGER
            }


    -- The SYSTEM Group
    -- Implementation of this group is mandatory for all
    -- Hypercom IEN Systems although some specific members
    -- may or may not apply to all Hypercom IEN devices.

    hypSysBusAddr  OBJECT-TYPE
        SYNTAX INTEGER
        ACCESS read-only
        STATUS mandatory
        DESCRIPTION
        "Card BUS Address switch setting"
        ::= { hypSysTableEntry 1 }

    hypSysSwName  OBJECT-TYPE
        SYNTAX DisplayString
        ACCESS read-only
        STATUS mandatory
        DESCRIPTION
        "Name and version number of the SW module  (SIZE (0..20)"
        ::= { hypSysTableEntry 2 }

    hypPortMode  OBJECT-TYPE
        SYNTAX DisplayString
        ACCESS read-only
        STATUS mandatory
        DESCRIPTION
        "Port Card Operating mode ('E'=EPROM, 'R'=RAM)"
        ::= { hypSysTableEntry 3 }

    hypSysStatus  OBJECT-TYPE
        SYNTAX DisplayString
        ACCESS read-only
        STATUS mandatory
        DESCRIPTION
        "Card Display status display values"
        ::= { hypSysTableEntry 4 }

    hypSysCuAddress  OBJECT-TYPE
        SYNTAX INTEGER
        ACCESS read-only
        STATUS mandatory
        DESCRIPTION
        "Card CU Address switch setting"
        ::= { hypSysTableEntry 5 }

    hypSysModeSwitch1  OBJECT-TYPE
        SYNTAX INTEGER
        ACCESS read-only
        STATUS mandatory
        DESCRIPTION
        "Card Mode switch 1 setting"
        ::= { hypSysTableEntry 6 }

    hypSysModeSwitch2  OBJECT-TYPE
        SYNTAX INTEGER
        ACCESS read-only
        STATUS mandatory
        DESCRIPTION
        "Card Mode switch 2 setting"
        ::= { hypSysTableEntry 7 }

    hypSysUpTime  OBJECT-TYPE
        SYNTAX INTEGER
        ACCESS read-only
        STATUS mandatory
        DESCRIPTION
        "System Up time in minutes"
        ::= { hypSysTableEntry 8 }

    hypSysDownTime  OBJECT-TYPE
        SYNTAX INTEGER
        ACCESS read-only
        STATUS mandatory
        DESCRIPTION
        "System Down time in minutes"
        ::= { hypSysTableEntry 9 }

    hypSysRestart  OBJECT-TYPE
        SYNTAX INTEGER
        ACCESS read-only
        STATUS mandatory
        DESCRIPTION
        "System Restart"
        ::= { hypSysTableEntry 10 }




    -- The IP Group
    -- The IP Group contains information about the IP
    -- in a Hypercom IEN.
    -- For clearing counters see the hypSystem group object hypClearStatCounters



    --Table of hypIpTable
    --hypIpTable description (Table format)
    hypIpTableTable OBJECT-TYPE
        SYNTAX   SEQUENCE OF HypIpTableEntry
        ACCESS   not-accessible
        STATUS   mandatory
        DESCRIPTION
        "A table containing information about
         IP Table"
        ::= { hypIp 1 }

        hypIpTableEntry OBJECT-TYPE
        SYNTAX   HypIpTableEntry
        ACCESS   not-accessible
        STATUS   mandatory
        DESCRIPTION
        "IP Table"
        INDEX { hypIpTableIndex }
        ::= { hypIpTableTable 1 }

        HypIpTableEntry ::=
        SEQUENCE {
            hypIpIfIndex
                INTEGER,
            hypIpIn
                Counter,
            hypIpOut
                Counter,
            hypIpAverage
                Gauge,
            hypIpInSec
                Gauge,
            hypIpInMax
                Gauge,
            hypUnknownFrame
                Counter,
            hypTimeToLive
                INTEGER,
            hypMsgIn
                Counter,
            hypMsgOut
                Counter,
            hypUnreachIn
                Counter,
            hypUnreachOut
                Counter,
            hypPingIn
                Counter,
            hypPingOut
                Counter,
            hypDataIn
                Counter,
            hypDataOut
                Counter,
            hypBadFrames
                Counter,
            hypUnknownPort
                Counter
            }

        hypIpIfIndex  OBJECT-TYPE
        SYNTAX INTEGER
        ACCESS read-only
        STATUS mandatory
        DESCRIPTION
        "The ifIndex  (IP Interface Instance)"
        ::= { hypIpTableEntry 1 }

        hypIpIn  OBJECT-TYPE
        SYNTAX Counter
        ACCESS read-only
        STATUS mandatory
        DESCRIPTION
        "The number of IP packet received since last reset"
        ::= { hypIpTableEntry 2 }

        hypIpOut  OBJECT-TYPE
        SYNTAX Counter
        ACCESS read-only
        STATUS mandatory
        DESCRIPTION
        "The number of IP packet sent since last reset"
        ::= { hypIpTableEntry 3 }

        hypIpAverage  OBJECT-TYPE
        SYNTAX Gauge
        ACCESS read-only
        STATUS mandatory
        DESCRIPTION
        "Average number of IP frame received/sec since last reset"
        ::= { hypIpTableEntry 4 }

        hypIpInSec  OBJECT-TYPE
        SYNTAX Gauge
        ACCESS read-only
        STATUS mandatory
        DESCRIPTION
        "Currently number of IP frame received/sec"
        ::= { hypIpTableEntry 5 }

        hypIpInMax  OBJECT-TYPE
        SYNTAX Gauge
        ACCESS read-only
        STATUS mandatory
        DESCRIPTION
        "Maximum number of IP frame received/sec since last reset"
        ::= { hypIpTableEntry 6 }

        hypUnknownFrame  OBJECT-TYPE
        SYNTAX Counter
        ACCESS read-only
        STATUS mandatory
        DESCRIPTION
        "Unknown protocol frame received"
        ::= { hypIpTableEntry 7 }

        hypTimeToLive  OBJECT-TYPE
        SYNTAX INTEGER
        ACCESS read-only
        STATUS mandatory
        DESCRIPTION
        "IP Time To Live (TTL) value"
        ::= { hypIpTableEntry 8 }

    hypMsgIn  OBJECT-TYPE
        SYNTAX Counter
        ACCESS read-only
        STATUS mandatory
        DESCRIPTION
        "Messages received"
        ::= { hypIpTableEntry 9 }

    hypMsgOut  OBJECT-TYPE
        SYNTAX Counter
        ACCESS read-only
        STATUS mandatory
        DESCRIPTION
        "Messages sent"
        ::= { hypIpTableEntry 10 }

    hypUnreachIn  OBJECT-TYPE
        SYNTAX Counter
        ACCESS read-only
        STATUS mandatory
        DESCRIPTION
        "Destination unreachable received"
        ::= { hypIpTableEntry 11 }

    hypUnreachOut  OBJECT-TYPE
        SYNTAX Counter
        ACCESS read-only
        STATUS mandatory
        DESCRIPTION
        "Destination unreachable sent"
        ::= { hypIpTableEntry 12 }

    hypPingIn  OBJECT-TYPE
        SYNTAX Counter
        ACCESS read-only
        STATUS mandatory
        DESCRIPTION
        "Pings received"
        ::= { hypIpTableEntry 13 }

    hypPingOut  OBJECT-TYPE
        SYNTAX Counter
        ACCESS read-only
        STATUS mandatory
        DESCRIPTION
        "Pings sent"
        ::= { hypIpTableEntry 14 }

    hypDataIn  OBJECT-TYPE
        SYNTAX Counter
        ACCESS read-only
        STATUS mandatory
        DESCRIPTION
        "Datagrams in"
        ::= { hypIpTableEntry 15 }

    hypDataOut  OBJECT-TYPE
        SYNTAX Counter
        ACCESS read-only
        STATUS mandatory
        DESCRIPTION
        "Datagrams out"
        ::= { hypIpTableEntry 16 }

    hypBadFrames  OBJECT-TYPE
        SYNTAX Counter
        ACCESS read-only
        STATUS mandatory
        DESCRIPTION
        "Bad frames in"
        ::= { hypIpTableEntry 17 }

    hypUnknownPort  OBJECT-TYPE
        SYNTAX Counter
        ACCESS read-only
        STATUS mandatory
        DESCRIPTION
        "Unknown port received"
        ::= { hypIpTableEntry 18 }

    --End of Table hypIpTable  IP Table




    -- The IPX Group
    -- The IPX Group contains information about the IPX
    -- in a Hypercom IEN.
    -- For clearing counters see the hypSystem group object hypClearStatCounters



    --Table of hypIpTable
    --hypIpTable description (Table format)
    hypIpxTableTable OBJECT-TYPE
        SYNTAX   SEQUENCE OF HypIpxTableEntry
        ACCESS   not-accessible
        STATUS   mandatory
        DESCRIPTION
        "A table containing information about
         IPX Table"
        ::= { hypIpx 1 }

        hypIpxTableEntry OBJECT-TYPE
        SYNTAX   HypIpxTableEntry
        ACCESS   not-accessible
        STATUS   mandatory
        DESCRIPTION
        "IPX Table"
        INDEX { hypIpxTableIndex }
        ::= { hypIpxTableTable 1 }

        HypIpxTableEntry ::=
        SEQUENCE {
            hypIpxIfIndex
                INTEGER,
            hypIpx8023pkt
                Counter,
            hypIpxEthIIpkt
                Counter,
            hypIpxSNAPpkt
                Counter,
            hypIpx8022pkt
                Counter,
            hypIpxIn
                Counter,
            hypIpxOut
                Counter,
            hypIpxAlErrs
                Counter,
            hypIpxCrcErrs
                Counter,
            hypIpxRxOvRun
                Counter,
            hypIpxColl
                Counter,
            hypIpxRipSup
                Counter,
            hypIpxRipReqRcv
                Counter,
            hypIpxRipReqSent
                Counter,
            hypIpxRipRspRcved
                Counter,
            hypIpxRipRspSent
                Counter,
            hypIpxSapSup
                Counter,
            hypIpxSapReqRcved
                Counter,
            hypIpxSapReqSent
                Counter,
            hypIpxSapRspRcved
                Counter,
            hypIpxSapRspSent
                Counter
            }
        hypIpxIfIndex  OBJECT-TYPE
        SYNTAX INTEGER
        ACCESS read-only
        STATUS mandatory
        DESCRIPTION
        "The ifIndex  (IPX Interface Instance)"
        ::= { hypIpxTableEntry 1 }

        hypIpx8023pkt  OBJECT-TYPE
        SYNTAX Counter
        ACCESS read-only
        STATUS mandatory
        DESCRIPTION
        "The number of 802.3 packets"
        ::= { hypIpxTableEntry 2 }

        hypIpxEthIIpkt  OBJECT-TYPE
        SYNTAX Counter
        ACCESS read-only
        STATUS mandatory
        DESCRIPTION
        "The number of Ethernet II packets"
        ::= { hypIpxTableEntry 3 }

        hypIpxSNAP  OBJECT-TYPE
        SYNTAX Counter
        ACCESS read-only
        STATUS mandatory
        DESCRIPTION
        "The number of SNAP packets"
        ::= { hypIpxTableEntry 4 }

        hypIpx8022pkt  OBJECT-TYPE
        SYNTAX Counter
        ACCESS read-only
        STATUS mandatory
        DESCRIPTION
        "The number of 802.2 packets"
        ::= { hypIpxTableEntry 5 }

        hypIpxIn  OBJECT-TYPE
        SYNTAX Counter
        ACCESS read-only
        STATUS mandatory
        DESCRIPTION
        "The number of IPX packet received since last reset"
        ::= { hypIpxTableEntry 6 }

        hypIpxOut  OBJECT-TYPE
        SYNTAX Counter
        ACCESS read-only
        STATUS mandatory
        DESCRIPTION
        "The number of IPX packet sent since last reset"
        ::= { hypIpxTableEntry 7 }

        hypIpxAlErrs OBJECT-TYPE
        SYNTAX Counter
        ACCESS read-only
        STATUS mandatory
        DESCRIPTION
        "The number of IPX packet Alignment Errors "
        ::= { hypIpxTableEntry 8 }

        hypIpxCrcErrs  OBJECT-TYPE
        SYNTAX Counter
        ACCESS read-only
        STATUS mandatory
        DESCRIPTION
        "The number of IPX packet CRC Errors "
        ::= { hypIpxTableEntry 9 }

        hypIpxRxOvRun  OBJECT-TYPE
        SYNTAX Counter
        ACCESS read-only
        STATUS mandatory
        DESCRIPTION
        "The number of IPX packet Receiver Overrun Errors "
        ::= { hypIpxTableEntry 10 }

        hypIpxColl  OBJECT-TYPE
        SYNTAX Counter
        ACCESS read-only
        STATUS mandatory
        DESCRIPTION
        "The number of IPX packet Collisions "
        ::= { hypIpxTableEntry 11 }

        hypIpxRipSup  OBJECT-TYPE
        SYNTAX Counter
        ACCESS read-only
        STATUS mandatory
        DESCRIPTION
        "The number of IPX packet RIP Supplier "
        ::= { hypIpxTableEntry 12 }

        hypIpxRipReqRcv OBJECT-TYPE
        SYNTAX Counter
        ACCESS read-only
        STATUS mandatory
        DESCRIPTION
        "The number of IPX packet RIP Requests Received "
        ::= { hypIpxTableEntry 13 }

        hypIpxRipReqSent OBJECT-TYPE
        SYNTAX Counter
        ACCESS read-only
        STATUS mandatory
        DESCRIPTION
        "The number of IPX packet RIP Requests Sent "
        ::= { hypIpxTableEntry 14 }

        hypIpxRipRspRcved  OBJECT-TYPE
        SYNTAX Counter
        ACCESS read-only
        STATUS mandatory
        DESCRIPTION
        "The number of IPX packet Responses Received "
        ::= { hypIpxTableEntry 15 }

        hypIpxRipRspSent  OBJECT-TYPE
        SYNTAX Counter
        ACCESS read-only
        STATUS mandatory
        DESCRIPTION
        "The number of IPX packet Responses Sent "
        ::= { hypIpxTableEntry 16 }

        hypIpxSapSup  OBJECT-TYPE
        SYNTAX Counter
        ACCESS read-only
        STATUS mandatory
        DESCRIPTION
        "The number of IPX packet SAP Supplier"
        ::= { hypIpxTableEntry 17 }

        hypIpxSapReqRcved OBJECT-TYPE
        SYNTAX Counter
        ACCESS read-only
        STATUS mandatory
        DESCRIPTION
        "The number of IPX packet SAP Requests Received"
        ::= { hypIpxTableEntry 18 }

        hypIpxSapReqSent  OBJECT-TYPE
        SYNTAX Counter
        ACCESS read-only
        STATUS mandatory
        DESCRIPTION
        "The number of IPX packet SAP Requests Sent"
        ::= { hypIpxTableEntry 19 }

        hypIpxSapRspRcved OBJECT-TYPE
        SYNTAX Counter
        ACCESS read-only
        STATUS mandatory
        DESCRIPTION
        "The number of IPX packet SAP Responses Received"
        ::= { hypIpxTableEntry 20 }

        hypIpxSapRspSent OBJECT-TYPE
        SYNTAX Counter
        ACCESS read-only
        STATUS mandatory
        DESCRIPTION
        "The number of IPX packet SAP Responses Sent"
        ::= { hypIpxTableEntry 21 }



    --End of Table hypIpTable  IPX Table



    -- The icmp Group
    -- The icmp Group contains information about the
    -- icmp Parameters in a Hypercom IEN.

    hypMsgIn  OBJECT-TYPE
        SYNTAX Counter
        ACCESS read-only
        STATUS mandatory
        DESCRIPTION
        "Messages received"
        ::= { hypIcmp 1 }

    hypMsgOut  OBJECT-TYPE
        SYNTAX Counter
        ACCESS read-only
        STATUS mandatory
        DESCRIPTION
        "Messages sent"
        ::= { hypIcmp 2 }

    hypUnreachIn  OBJECT-TYPE
        SYNTAX Counter
        ACCESS read-only
        STATUS mandatory
        DESCRIPTION
        "Destination unreachable received"
        ::= { hypIcmp 3 }

    hypUnreachOut  OBJECT-TYPE
        SYNTAX Counter
        ACCESS read-only
        STATUS mandatory
        DESCRIPTION
        "Destination unreachable sent"
        ::= { hypIcmp 4 }

    hypPingIn  OBJECT-TYPE
        SYNTAX Counter
        ACCESS read-only
        STATUS mandatory
        DESCRIPTION
        "Pings received"
        ::= { hypIcmp 5 }

    hypPingOut  OBJECT-TYPE
        SYNTAX Counter
        ACCESS read-only
        STATUS mandatory
        DESCRIPTION
        "Pings sent"
        ::= { hypIcmp 6 }






    -- The tcp Group
    -- The tcp Group contains information about the
    -- tcp Parameters in a Hypercom IEN.

    hypCntConnections  OBJECT-TYPE
        SYNTAX Counter
        ACCESS read-only
        STATUS mandatory
        DESCRIPTION
        "number of active TCP connections"
        ::= { hypTcp 1 }



    --Table of hypTcpConnections
    --hypTcpConnections description (Table format)
    hypTcpConnectionsTable OBJECT-TYPE
        SYNTAX   SEQUENCE OF HypTcpConnectionsEntry
        ACCESS   not-accessible
        STATUS   mandatory
        DESCRIPTION
        "A table containing information about
         "
        ::= { hypTcp 2 }

        hypTcpConnectionsEntry OBJECT-TYPE
        SYNTAX   HypTcpConnectionsEntry
        ACCESS   not-accessible
        STATUS   mandatory
        DESCRIPTION
        ""
        INDEX { hypTcpConnectionsIndex }
        ::= { hypTcpConnectionsTable 1 }

        HypTcpConnectionsEntry ::=
        SEQUENCE {
            hypTcpConnectionsIndex
                INTEGER,
            hypFramesIn
                Counter,
            hypFramesOut
                Counter,
            hypTcpPort
                INTEGER,
            hypTcpStatus
                INTEGER,
            hypIpAddr
                NetworkAddress
            }

        hypTcpConnectionsIndex  OBJECT-TYPE
        SYNTAX INTEGER
        ACCESS read-only
        STATUS mandatory
        DESCRIPTION
        "The ifIndex Value of the corresponding ifEntry."
        ::= { hypTcpConnectionsEntry 1 }

        hypFramesIn  OBJECT-TYPE
        SYNTAX Counter
        ACCESS read-only
        STATUS mandatory
        DESCRIPTION
        "Frames received"
        ::= { hypTcpConnectionsEntry 2 }

        hypFramesOut  OBJECT-TYPE
        SYNTAX Counter
        ACCESS read-only
        STATUS mandatory
        DESCRIPTION
        "Frames sent"
        ::= { hypTcpConnectionsEntry 3 }

        hypTcpPort  OBJECT-TYPE
        SYNTAX INTEGER
        ACCESS read-only
        STATUS mandatory
        DESCRIPTION
        "TCP port number"
        ::= { hypTcpConnectionsEntry 4 }

        hypTcpStatus  OBJECT-TYPE
        SYNTAX INTEGER
        ACCESS read-only
        STATUS mandatory
        DESCRIPTION
        "Connection status: Idle(0), ARPsent(1), SYNsent(2), Active(3)"
        ::= { hypTcpConnectionsEntry 5 }

        hypIpAddr  OBJECT-TYPE
        SYNTAX NetworkAddress
        ACCESS read-write
        STATUS mandatory
        DESCRIPTION
        "Remote IP address"
        ::= { hypTcpConnectionsEntry 6 }




    --End of Table hypTcpConnections






    -- The udp Group
    -- The udp Group contains information about the
    -- udp Parameters in a Hypercom IEN.

    hypDataIn  OBJECT-TYPE
        SYNTAX Counter
        ACCESS read-only
        STATUS mandatory
        DESCRIPTION
        "Datagrams in"
        ::= { hypUdp 1 }

    hypDataOut  OBJECT-TYPE
        SYNTAX Counter
        ACCESS read-only
        STATUS mandatory
        DESCRIPTION
        "Datagrams out"
        ::= { hypUdp 2 }

    hypBadFrames  OBJECT-TYPE
        SYNTAX Counter
        ACCESS read-only
        STATUS mandatory
        DESCRIPTION
        "Bad frames in"
        ::= { hypUdp 3 }

    hypUnknownPort  OBJECT-TYPE
        SYNTAX Counter
        ACCESS read-only
        STATUS mandatory
        DESCRIPTION
        "Unknown port received"
        ::= { hypUdp 4 }





    -- The hdlc Group
    -- The hdlc Group contains information about the
    -- hdlc line driver port including the extended hdlc
    -- and hdlc lan driver port
    -- parameters in a Hypercom IEN.



    hypHdlcPortOperMode  OBJECT-TYPE
        SYNTAX INTEGER
        ACCESS read-only
        STATUS mandatory
        DESCRIPTION
        "Port operating mode"
        ::= { hypHdlc 1 }

    -- 00 = hdlc leased line multipoint
    -- 01 = hdlc dial=up mode
    -- 02 = hdlc/visa combined interface
    -- 03 = visa only dial-up mode
    -- 0B = token ring interface


    -- Port Availability Statistics
    hypHdlcBuffMax  OBJECT-TYPE
        SYNTAX INTEGER
        ACCESS read-only
        STATUS mandatory
        DESCRIPTION
        "Maximum number of buffers allocated"
        ::= { hypHdlc 2 }

    hypHdlcBuffThreshold  OBJECT-TYPE
        SYNTAX Counter
        ACCESS read-only
        STATUS mandatory
        DESCRIPTION
        "Number of times the buffer threshold was reached"
        ::= { hypHdlc 3 }

    hypHdlcBuffAllocFail  OBJECT-TYPE
        SYNTAX Counter
        ACCESS read-only
        STATUS mandatory
        DESCRIPTION
        "Number of buffer allocation failures"
        ::= { hypHdlc 4 }

    hypHdlcMemoryMode  OBJECT-TYPE
        SYNTAX Counter
        ACCESS read-only
        STATUS mandatory
        DESCRIPTION
        "Memory mode, 'E' = EPROM,   'R' = RAM mode"
        ::= { hypHdlc 5 }

    hypHdlcAlarmMode  OBJECT-TYPE
        SYNTAX Counter
        ACCESS read-only
        STATUS mandatory
        DESCRIPTION
        "Alarm mode, 'N' = No Minor TRAP's, 'Y' = All Alarms"
        ::= { hypHdlc 6 }


    -- HDLC Call Processing Statistics
    hypHdlcSeizures  OBJECT-TYPE
        SYNTAX Counter
        ACCESS read-only
        STATUS mandatory
        DESCRIPTION
        "Incoming call seizures."
        ::= { hypHdlc 7 }

    hypHdlcLostSeizures  OBJECT-TYPE
        SYNTAX Counter
        ACCESS read-only
        STATUS mandatory
        DESCRIPTION
        "aborts due to lost seizure."
        ::= { hypHdlc 8 }

    hypHdlcLostCarrier  OBJECT-TYPE
        SYNTAX Counter
        ACCESS read-only
        STATUS mandatory
        DESCRIPTION
        "aborts due to lost carrier."
        ::= { hypHdlc 9 }

    hypHdlcNoTrain  OBJECT-TYPE
        SYNTAX Counter
        ACCESS read-only
        STATUS mandatory
        DESCRIPTION
        "aborts due to can't train modem."
        ::= { hypHdlc 10 }

    hypHdlcCompleted  OBJECT-TYPE
        SYNTAX Counter
        ACCESS read-only
        STATUS mandatory
        DESCRIPTION
        "completed calls."
        ::= { hypHdlc 11 }

    hypHdlcVisa300  OBJECT-TYPE
        SYNTAX Counter
        ACCESS read-only
        STATUS mandatory
        DESCRIPTION
        "Completed VISA 300 BPS calls."
        ::= { hypHdlc 12 }

    hypHdlcVisa1200  OBJECT-TYPE
        SYNTAX Counter
        ACCESS read-only
        STATUS mandatory
        DESCRIPTION
        "Completed VISA 1200 BPS calls."
        ::= { hypHdlc 13 }

    hypHdlcVisa2400  OBJECT-TYPE
        SYNTAX Counter
        ACCESS read-only
        STATUS mandatory
        DESCRIPTION
        "Completed VISA 2400 BPS calls."
        ::= { hypHdlc 14 }

    hypHdlcSdlc1200  OBJECT-TYPE
        SYNTAX Counter
        ACCESS read-only
        STATUS mandatory
        DESCRIPTION
        "Completed SDLC 1200 BPS calls."
        ::= { hypHdlc 15 }

    hypHdlcSdlc2400  OBJECT-TYPE
        SYNTAX Counter
        ACCESS read-only
        STATUS mandatory
        DESCRIPTION
        "Completed SDLC 2400 BPS calls."
        ::= { hypHdlc 16 }

    hypHdlcCommErrs  OBJECT-TYPE
        SYNTAX Counter
        ACCESS read-only
        STATUS mandatory
        DESCRIPTION
        "Aborts due to communication errors."
        ::= { hypHdlc 17 }

    hypHdlcSeizeTime  OBJECT-TYPE
        SYNTAX Counter
        ACCESS read-only
        STATUS mandatory
        DESCRIPTION
        "Total seized time."
        ::= { hypHdlc 18 }

    hypHdlcBillableTime  OBJECT-TYPE
        SYNTAX Counter
        ACCESS read-only
        STATUS mandatory
        DESCRIPTION
        "Total billable time."
        ::= { hypHdlc 19 }

    hypHdlcReleaseTime  OBJECT-TYPE
        SYNTAX Counter
        ACCESS read-only
        STATUS mandatory
        DESCRIPTION
        "Total seizure release time."
        ::= { hypHdlc 20 }

    hypHdlcHangups  OBJECT-TYPE
        SYNTAX Counter
        ACCESS read-only
        STATUS mandatory
        DESCRIPTION
        "Answer/Hangups"
        ::= { hypHdlc 21 }



    -- HDLC Level 2 (HDLC/NRM) statistics
    hypHdlcRexmits  OBJECT-TYPE
        SYNTAX Counter
        ACCESS read-only
        STATUS mandatory
        DESCRIPTION
        "Retransmits counter"
        ::= { hypHdlc 22 }

    hypHdlcFrameErrs  OBJECT-TYPE
        SYNTAX Counter
        ACCESS read-only
        STATUS mandatory
        DESCRIPTION
        "Receive framing errors counter"
        ::= { hypHdlc 23 }

    hypHdlcInSnrm  OBJECT-TYPE
        SYNTAX Counter
        ACCESS read-only
        STATUS mandatory
        DESCRIPTION
        "Incomming SNRM counters"
        ::= { hypHdlc 24 }

    hypHdlcOutSnrm  OBJECT-TYPE
        SYNTAX Counter
        ACCESS read-only
        STATUS mandatory
        DESCRIPTION
        "Outgoing  SNRM counters"
        ::= { hypHdlc 25 }

    hypHdlcInRnrs  OBJECT-TYPE
        SYNTAX Counter
        ACCESS read-only
        STATUS mandatory
        DESCRIPTION
        "Incomming RNR counters"
        ::= { hypHdlc 26 }

    hypHdlcOutRnrs  OBJECT-TYPE
        SYNTAX Counter
        ACCESS read-only
        STATUS mandatory
        DESCRIPTION
        "Outgoing  RNR counters"
        ::= { hypHdlc 27 }

    hypHdlcInTestFrames  OBJECT-TYPE
        SYNTAX Counter
        ACCESS read-only
        STATUS mandatory
        DESCRIPTION
        "Incomming Test frames counters"
        ::= { hypHdlc 28 }

    hypHdlcOutTestFrames  OBJECT-TYPE
        SYNTAX Counter
        ACCESS read-only
        STATUS mandatory
        DESCRIPTION
        "Outgoing  Test frames counters"
        ::= { hypHdlc 29 }

    hypHdlcInDm  OBJECT-TYPE
        SYNTAX Counter
        ACCESS read-only
        STATUS mandatory
        DESCRIPTION
        "Incomming DM counters"
        ::= { hypHdlc 30 }

    hypHdlcOutDm  OBJECT-TYPE
        SYNTAX Counter
        ACCESS read-only
        STATUS mandatory
        DESCRIPTION
        "Outgoing  DM counters"
        ::= { hypHdlc 31 }

    hypHdlcInUa  OBJECT-TYPE
        SYNTAX Counter
        ACCESS read-only
        STATUS mandatory
        DESCRIPTION
        "Incomming UA counters"
        ::= { hypHdlc 32 }

    hypHdlcOutUa  OBJECT-TYPE
        SYNTAX Counter
        ACCESS read-only
        STATUS mandatory
        DESCRIPTION
        "Outgoing  UA counters"
        ::= { hypHdlc 33 }

    hypHdlcInFrmr  OBJECT-TYPE
        SYNTAX Counter
        ACCESS read-only
        STATUS mandatory
        DESCRIPTION
        "Incomming FRMR counters"
        ::= { hypHdlc 34 }

    hypHdlcOutFrmr  OBJECT-TYPE
        SYNTAX Counter
        ACCESS read-only
        STATUS mandatory
        DESCRIPTION
        "Outgoing  FRMR counters"
        ::= { hypHdlc 35 }



    -- V.24 interface lead status
    hypHdlcV24Ch1DTR  OBJECT-TYPE
        SYNTAX INTEGER
        ACCESS read-only
        STATUS mandatory
        DESCRIPTION
        "V.24/V.35 Channel 1 DTR lead status (0=inactive)"
        ::= { hypHdlc 36 }

    hypHdlcV24Ch1DSR  OBJECT-TYPE
        SYNTAX INTEGER
        ACCESS read-only
        STATUS mandatory
        DESCRIPTION
        "V.24/V.35 Channel 1 DSR lead status (0=inactive)"
        ::= { hypHdlc 37 }

    hypHdlcV24Ch1DCD  OBJECT-TYPE
        SYNTAX INTEGER
        ACCESS read-only
        STATUS mandatory
        DESCRIPTION
        "V.24/V.35 Channel 1 DCD lead status (0=inactive)"
        ::= { hypHdlc 38 }

    hypHdlcV24Ch1CTS  OBJECT-TYPE
        SYNTAX INTEGER
        ACCESS read-only
        STATUS mandatory
        DESCRIPTION
        "V.24/V.35 Channel 1 CTS lead status (0=inactive)"
        ::= { hypHdlc 39 }

    hypHdlcV24Ch1RTS  OBJECT-TYPE
        SYNTAX INTEGER
        ACCESS read-only
        STATUS mandatory
        DESCRIPTION
        "V.24/V.35 Channel 1 RTS lead status (0=inactive)"
        ::= { hypHdlc 40 }



    hypHdlcV24Ch2DTR  OBJECT-TYPE
        SYNTAX INTEGER
        ACCESS read-only
        STATUS mandatory
        DESCRIPTION
        "V.24/V.35 Channel 2 DTR lead status (0=inactive)"
        ::= { hypHdlc 41 }

    hypHdlcV24Ch2DSR  OBJECT-TYPE
        SYNTAX INTEGER
        ACCESS read-only
        STATUS mandatory
        DESCRIPTION
        "V.24/V.35 Channel 2 DSR lead status (0=inactive)"
        ::= { hypHdlc 42 }

    hypHdlcV24Ch2DCD  OBJECT-TYPE
        SYNTAX INTEGER
        ACCESS read-only
        STATUS mandatory
        DESCRIPTION
        "V.24/V.35 Channel 2 DCD lead status (0=inactive)"
        ::= { hypHdlc 43 }

    hypHdlcV24Ch2CTS  OBJECT-TYPE
        SYNTAX INTEGER
        ACCESS read-only
        STATUS mandatory
        DESCRIPTION
        "V.24/V.35 Channel 2 CTS lead status (0=inactive)"
        ::= { hypHdlc 44 }

    hypHdlcV24Ch2RTS  OBJECT-TYPE
        SYNTAX INTEGER
        ACCESS read-only
        STATUS mandatory
        DESCRIPTION
        "V.24/V.35 Channel 2 RTS lead status (0=inactive)"
        ::= { hypHdlc 45 }



    hypHdlcV24Ch3DTR  OBJECT-TYPE
        SYNTAX INTEGER
        ACCESS read-only
        STATUS mandatory
        DESCRIPTION
        "V.24/V.35 Channel 3 DTR lead status (0=inactive)"
        ::= { hypHdlc 46 }

    hypHdlcV24Ch3DSR  OBJECT-TYPE
        SYNTAX INTEGER
        ACCESS read-only
        STATUS mandatory
        DESCRIPTION
        "V.24/V.35 Channel 3 DSR lead status (0=inactive)"
        ::= { hypHdlc 47 }

    hypHdlcV24Ch3DCD  OBJECT-TYPE
        SYNTAX INTEGER
        ACCESS read-only
        STATUS mandatory
        DESCRIPTION
        "V.24/V.35 Channel 3 DCD lead status (0=inactive)"
        ::= { hypHdlc 48 }

    hypHdlcV24Ch3CTS  OBJECT-TYPE
        SYNTAX INTEGER
        ACCESS read-only
        STATUS mandatory
        DESCRIPTION
        "V.24/V.35 Channel 3 CTS lead status (0=inactive)"
        ::= { hypHdlc 49 }

    hypHdlcV24Ch3RTS  OBJECT-TYPE
        SYNTAX INTEGER
        ACCESS read-only
        STATUS mandatory
        DESCRIPTION
        "V.24/V.35 Channel 3 RTS lead status (0=inactive)"
        ::= { hypHdlc 50 }


    hypCntHdlcDropStatus  OBJECT-TYPE
        SYNTAX Counter
        ACCESS read-only
        STATUS mandatory
        DESCRIPTION
        "Number of drop status fields"
        ::= { hypHdlc 51 }



    --Table of hypHldcDropStatus
    --hypHldcDropStatus description (Table format)
    hypHldcDropStatusTable OBJECT-TYPE
        SYNTAX   SEQUENCE OF HypHldcDropStatusEntry
        ACCESS   not-accessible
        STATUS   mandatory
        DESCRIPTION
        "A table containing information about
         drop status"
        ::= { hypHdlc 52 }

        hypHldcDropStatusEntry OBJECT-TYPE
        SYNTAX   HypHldcDropStatusEntry
        ACCESS   not-accessible
        STATUS   mandatory
        DESCRIPTION
        "drop status"
        INDEX { hypHldcDropStatusIndex }
        ::= { hypHldcDropStatusTable 1 }

        HypHldcDropStatusEntry ::=
        SEQUENCE {
            hypHldcDropStatusIndex
                INTEGER,
            hypHldcDropHdlcAddress
                INTEGER,
            hypHldcDropControlStatus
                INTEGER,
            hypHldcDropMsgIn
                Counter,
            hypHldcDropMsgOut
                Counter
            }

        hypHldcDropStatusIndex  OBJECT-TYPE
        SYNTAX INTEGER
        ACCESS read-only
        STATUS mandatory
        DESCRIPTION
        "The ifIndex Value of the corresponding ifEntry."
        ::= { hypHldcDropStatusEntry 1 }

        hypHldcDropHdlcAddress  OBJECT-TYPE
        SYNTAX INTEGER
        ACCESS read-only
        STATUS mandatory
        DESCRIPTION
        "HDLC controller address"
        ::= { hypHldcDropStatusEntry 2 }

        hypHldcDropControlStatus  OBJECT-TYPE
        SYNTAX INTEGER
        ACCESS read-only
        STATUS mandatory
        DESCRIPTION
        "Controller status"
        ::= { hypHldcDropStatusEntry 3 }

        hypHldcDropMsgIn  OBJECT-TYPE
        SYNTAX Counter
        ACCESS read-only
        STATUS mandatory
        DESCRIPTION
        "Count of incomming messages"
        ::= { hypHldcDropStatusEntry 4 }

        hypHldcDropMsgOut  OBJECT-TYPE
        SYNTAX Counter
        ACCESS read-only
        STATUS mandatory
        DESCRIPTION
        "Count of outgoing messages"
        ::= { hypHldcDropStatusEntry 5 }




    --End of Table hypHldcDropStatus  drop status


    -- The sdlc Group
    -- The sdlc Group contains information about the
    -- sdlc Parameters in a Hypercom IEN.

    hypSdlcTableTable OBJECT-TYPE
        SYNTAX   SEQUENCE OF HypSdlcTableEntry
        ACCESS   not-accessible
        STATUS   mandatory
        DESCRIPTION
        "A table containing information about
         SDLC Table"
        ::= { hypSdlc 1 }

        hypSdlcTableEntry OBJECT-TYPE
        SYNTAX   HypSdlcTableEntry
        ACCESS   not-accessible
        STATUS   mandatory
        DESCRIPTION
        "SDLC Table"
        INDEX { hypSdlcTableIndex }
        ::= { hypSdlcTableTable 1 }

        HypSdlcTableEntry ::=
        SEQUENCE {
            hypSdlcIfIndex
                Counter,
            hypSdlcRexmits
                Counter,
            hypSdlcFrameErrs
                Counter,
            hypSdlcInSnrm
                Counter,
            hypSdlcOutSnrp
                Counter,
            hypSdlcInRnrs
                Counter,
            hypSdlcOutRnrs
                Counter,
            hypSdlcInTestFrames
                Counter,
            hypSdlcOutTestFrames
                Counter,
            hypSdlcInDm
                Counter,
            hypSdlcOutDm
                Counter,
            hypSdlcInUa
                Counter,
            hypSdlcOutUa
                Counter,
            hypSdlcInFrmr
                Counter,
            hypSdlcOutFrmr
                Counter
            }


    -- The SDLC Group
    -- Implementation of this group is mandatory for all
    -- Hypercom IEN Systems although some specific members
    -- may or may not apply to all Hypercom IEN devices.

    hypSdlcIfIndex  OBJECT-TYPE
        SYNTAX Counter
        ACCESS read-only
        STATUS mandatory
        DESCRIPTION
        "Sdlc Interface Instance"
        ::= { hypSdlcTableEntry 1 }

    hypSdlcRexmits  OBJECT-TYPE
        SYNTAX Counter
        ACCESS read-only
        STATUS mandatory
        DESCRIPTION
        "Retransmits counter"
        ::= { hypSdlcTableEntry 2 }

    hypSdlcFrameErrs  OBJECT-TYPE
        SYNTAX Counter
        ACCESS read-only
        STATUS mandatory
        DESCRIPTION
        "Receive framing errors counter"
        ::= { hypSdlcTableEntry 3 }

    hypSdlcInSnrm  OBJECT-TYPE
        SYNTAX Counter
        ACCESS read-only
        STATUS mandatory
        DESCRIPTION
        "Incomming SNRM counters"
        ::= { hypSdlcTableEntry 4 }

    hypSdlcOutSnrm  OBJECT-TYPE
        SYNTAX Counter
        ACCESS read-only
        STATUS mandatory
        DESCRIPTION
        "Outgoing  SNRM counters"
        ::= { hypSdlcTableEntry 5 }

    hypSdlcInRnrs  OBJECT-TYPE
        SYNTAX Counter
        ACCESS read-only
        STATUS mandatory
        DESCRIPTION
        "Incomming RNR counters"
        ::= { hypSdlcTableEntry 6 }

    hypSdlcOutRnrs  OBJECT-TYPE
        SYNTAX Counter
        ACCESS read-only
        STATUS mandatory
        DESCRIPTION
        "Outgoing  RNR counters"
        ::= { hypSdlcTableEntry 7 }

    hypSdlcInTestFrames  OBJECT-TYPE
        SYNTAX Counter
        ACCESS read-only
        STATUS mandatory
        DESCRIPTION
        "Incomming Test frames counters"
        ::= { hypSdlcTableEntry 8 }

    hypSdlcOutTestFrames  OBJECT-TYPE
        SYNTAX Counter
        ACCESS read-only
        STATUS mandatory
        DESCRIPTION
        "Outgoing  Test frames counters"
        ::= { hypSdlcTableEntry 9 }

    hypSdlcInDm  OBJECT-TYPE
        SYNTAX Counter
        ACCESS read-only
        STATUS mandatory
        DESCRIPTION
        "Incomming DM counters"
        ::= { hypSdlcTableEntry 10 }

    hypSdlcOutDm  OBJECT-TYPE
        SYNTAX Counter
        ACCESS read-only
        STATUS mandatory
        DESCRIPTION
        "Outgoing  DM counters"
        ::= { hypSdlcTableEntry 11 }

    hypSdlcInUa  OBJECT-TYPE
        SYNTAX Counter
        ACCESS read-only
        STATUS mandatory
        DESCRIPTION
        "Incomming UA counters"
        ::= { hypSdlcTableEntry 12 }

    hypSdlcOutUa  OBJECT-TYPE
        SYNTAX Counter
        ACCESS read-only
        STATUS mandatory
        DESCRIPTION
        "Outgoing  UA counters"
        ::= { hypSdlcTableEntry 13 }

    hypSdlcInFrmr  OBJECT-TYPE
        SYNTAX Counter
        ACCESS read-only
        STATUS mandatory
        DESCRIPTION
        "Incomming FRMR counters"
        ::= { hypSdlcTableEntry 14 }

    hypSdlcOutFrmr  OBJECT-TYPE
        SYNTAX Counter
        ACCESS read-only
        STATUS mandatory
        DESCRIPTION
        "Outgoing  FRMR counters"
        ::= { hypSdlcTableEntry 15 }

    -- End of the sdlc Group






    -- The rtm Group
    -- The rtm Group contains information about the
    -- rtm Parameters in a Hypercom IEN.

    hypRtmSetBoundary1  OBJECT-TYPE
        SYNTAX INTEGER
        ACCESS read-only
        STATUS mandatory
        DESCRIPTION
        "RTM boundary 1 setting in 100 ms units"
        ::= { hypRtm 1 }

    hypRtmSetBoundary2  OBJECT-TYPE
        SYNTAX INTEGER
        ACCESS read-only
        STATUS mandatory
        DESCRIPTION
        "RTM boundary 2 setting in 100 ms units"
        ::= { hypRtm 2 }

    hypRtmSetBoundary3  OBJECT-TYPE
        SYNTAX INTEGER
        ACCESS read-only
        STATUS mandatory
        DESCRIPTION
        "RTM boundary 3 setting in 100 ms units"
        ::= { hypRtm 3 }

    hypRtmSetBoundary4  OBJECT-TYPE
        SYNTAX INTEGER
        ACCESS read-only
        STATUS mandatory
        DESCRIPTION
        "RTM boundary 4 setting in 100 ms units"
        ::= { hypRtm 4 }

    hypRtmCntBoundary1  OBJECT-TYPE
        SYNTAX Counter
        ACCESS read-only
        STATUS mandatory
        DESCRIPTION
        "RTM boundary 1 transaction count"
        ::= { hypRtm 5 }

    hypRtmCntBoundary2  OBJECT-TYPE
        SYNTAX Counter
        ACCESS read-only
        STATUS mandatory
        DESCRIPTION
        "RTM boundary 2 transaction count"
        ::= { hypRtm 6 }

    hypRtmCntBoundary3  OBJECT-TYPE
        SYNTAX Counter
        ACCESS read-only
        STATUS mandatory
        DESCRIPTION
        "RTM boundary 3 transaction count"
        ::= { hypRtm 7 }

    hypRtmCntBoundary4  OBJECT-TYPE
        SYNTAX Counter
        ACCESS read-only
        STATUS mandatory
        DESCRIPTION
        "RTM boundary 4 transaction count"
        ::= { hypRtm 8 }


    hypRtmOverflowBuc  OBJECT-TYPE
        SYNTAX Counter
        ACCESS read-only
        STATUS mandatory
        DESCRIPTION
        "Overflow bucket - transaction count"
        ::= { hypRtm 9 }

    hypRtmTotalTrans  OBJECT-TYPE
        SYNTAX Counter
        ACCESS read-only
        STATUS mandatory
        DESCRIPTION
        "Total transaction count"
        ::= { hypRtm 10 }

    hypRtmLastResTime  OBJECT-TYPE
        SYNTAX INTEGER
        ACCESS read-only
        STATUS mandatory
        DESCRIPTION
        "Last transaction response time in 100 ms units"
        ::= { hypRtm 11 }





    -- The x25 Group
    -- The x25 Group contains information about the x25
    -- functionality in a Hypercom IEN.

    hypX25PortStatus  OBJECT-TYPE
        SYNTAX INTEGER
        ACCESS read-only
        STATUS mandatory
        DESCRIPTION
        "X25 port status"
        ::= { hypX25 1 }

    hypX25LogChHi  OBJECT-TYPE
        SYNTAX INTEGER
        ACCESS read-only
        STATUS mandatory
        DESCRIPTION
        "Logical Channel HI defined"
        ::= { hypX25 2 }

    hypX25LogChLow  OBJECT-TYPE
        SYNTAX INTEGER
        ACCESS read-only
        STATUS mandatory
        DESCRIPTION
        "Logical Channel LOW defined"
        ::= { hypX25 3 }


    -- X25 Level 3 [Packet level] Statistics
    hypX25L3Restart  OBJECT-TYPE
        SYNTAX Counter
        ACCESS read-only
        STATUS mandatory
        DESCRIPTION
        "X25 Level 3 restarts counter"
        ::= { hypX25 4 }

    hypX25L3IncCalls  OBJECT-TYPE
        SYNTAX Counter
        ACCESS read-only
        STATUS mandatory
        DESCRIPTION
        "X25 Level 3 incoming calls counter"
        ::= { hypX25 5 }

    hypX25L3OutCalls  OBJECT-TYPE
        SYNTAX Counter
        ACCESS read-only
        STATUS mandatory
        DESCRIPTION
        "X25 Level 3 outgoing calls counter"
        ::= { hypX25 6 }

    hypX25L3IncClears  OBJECT-TYPE
        SYNTAX Counter
        ACCESS read-only
        STATUS mandatory
        DESCRIPTION
        "X25 Level 3 incoming clears counter"
        ::= { hypX25 7 }

    hypX25L3OutClears  OBJECT-TYPE
        SYNTAX Counter
        ACCESS read-only
        STATUS mandatory
        DESCRIPTION
        "X25 Level 3 outgoing clears counter"
        ::= { hypX25 8 }

    hypX25L3IncData  OBJECT-TYPE
        SYNTAX Counter
        ACCESS read-only
        STATUS mandatory
        DESCRIPTION
        "X25 Level 3 incoming data packets"
        ::= { hypX25 9 }

    hypX25L3OutData  OBJECT-TYPE
        SYNTAX Counter
        ACCESS read-only
        STATUS mandatory
        DESCRIPTION
        "X25 Level 3 outgoing data packets"
        ::= { hypX25 10 }

    hypX25L3IncRNR  OBJECT-TYPE
        SYNTAX Counter
        ACCESS read-only
        STATUS mandatory
        DESCRIPTION
        "X25 Level 3 incoming RNR count"
        ::= { hypX25 11 }

    hypX25L3OutRNR  OBJECT-TYPE
        SYNTAX Counter
        ACCESS read-only
        STATUS mandatory
        DESCRIPTION
        "X25 Level 3 outgoing RNR count"
        ::= { hypX25 12 }

    hypX25L3IncReset  OBJECT-TYPE
        SYNTAX Counter
        ACCESS read-only
        STATUS mandatory
        DESCRIPTION
        "X25 Level 3 incoming reset count"
        ::= { hypX25 13 }

    hypX25L3OutReset  OBJECT-TYPE
        SYNTAX Counter
        ACCESS read-only
        STATUS mandatory
        DESCRIPTION
        "X25 Level 3 outgoing reset count"
        ::= { hypX25 14 }

    hypX25L3IncReject  OBJECT-TYPE
        SYNTAX Counter
        ACCESS read-only
        STATUS mandatory
        DESCRIPTION
        "X25 Level 3 incoming reject packet count"
        ::= { hypX25 15 }

    hypX25L3OutReject  OBJECT-TYPE
        SYNTAX Counter
        ACCESS read-only
        STATUS mandatory
        DESCRIPTION
        "X25 Level 3 outgoing reject packet count"
        ::= { hypX25 16 }



    --- LEVEL 2  [HDLC/LAPB] STATISTICS
    hypX25CarrierLoss  OBJECT-TYPE
        SYNTAX Counter
        ACCESS read-only
        STATUS mandatory
        DESCRIPTION
        "X25 Level 2 carrier loss count"
        ::= { hypX25 17 }

    hypX25Retransmitt  OBJECT-TYPE
        SYNTAX Counter
        ACCESS read-only
        STATUS mandatory
        DESCRIPTION
        "X25 Level 2 retransmitt count"
        ::= { hypX25 18 }

    hypX25ReceiveFrame  OBJECT-TYPE
        SYNTAX Counter
        ACCESS read-only
        STATUS mandatory
        DESCRIPTION
        "X25 Level 2 receive framing errors"
        ::= { hypX25 19 }

    hypX25IncSABM  OBJECT-TYPE
        SYNTAX Counter
        ACCESS read-only
        STATUS mandatory
        DESCRIPTION
        "X25 Level 2 incoming SABM count"
        ::= { hypX25 20 }

    hypX25OutSABM  OBJECT-TYPE
        SYNTAX Counter
        ACCESS read-only
        STATUS mandatory
        DESCRIPTION
        "X25 Level 2 outgoing SABM count"
        ::= { hypX25 21 }

    hypX25IncRNR  OBJECT-TYPE
        SYNTAX Counter
        ACCESS read-only
        STATUS mandatory
        DESCRIPTION
        "X25 Level 2 incoming RNR count"
        ::= { hypX25 22 }

    hypX25OutRNR  OBJECT-TYPE
        SYNTAX Counter
        ACCESS read-only
        STATUS mandatory
        DESCRIPTION
        "X25 Level 2 outgoing RNR count"
        ::= { hypX25 23 }

    hypX25IncREJ  OBJECT-TYPE
        SYNTAX Counter
        ACCESS read-only
        STATUS mandatory
        DESCRIPTION
        "X25 Level 2 incoming REJ count"
        ::= { hypX25 24 }

    hypX25OutREJ  OBJECT-TYPE
        SYNTAX Counter
        ACCESS read-only
        STATUS mandatory
        DESCRIPTION
        "X25 Level 2 outgoing REJ count"
        ::= { hypX25 25 }

    hypX25IncDM  OBJECT-TYPE
        SYNTAX Counter
        ACCESS read-only
        STATUS mandatory
        DESCRIPTION
        "X25 Level 2 incoming DM count"
        ::= { hypX25 26 }

    hypX25OutDM  OBJECT-TYPE
        SYNTAX Counter
        ACCESS read-only
        STATUS mandatory
        DESCRIPTION
        "X25 Level 2 outgoing DM count"
        ::= { hypX25 27 }

    hypX25IncUA  OBJECT-TYPE
        SYNTAX Counter
        ACCESS read-only
        STATUS mandatory
        DESCRIPTION
        "X25 Level 2 incoming UA count"
        ::= { hypX25 28 }

    hypX25OutUA  OBJECT-TYPE
        SYNTAX Counter
        ACCESS read-only
        STATUS mandatory
        DESCRIPTION
        "X25 Level 2 outgoing UA count"
        ::= { hypX25 29 }

    hypX25IncFRMR  OBJECT-TYPE
        SYNTAX Counter
        ACCESS read-only
        STATUS mandatory
        DESCRIPTION
        "X25 Level 2 incoming FRMR count"
        ::= { hypX25 30 }

    hypX25OutFRMR  OBJECT-TYPE
        SYNTAX Counter
        ACCESS read-only
        STATUS mandatory
        DESCRIPTION
        "X25 Level 2 outgoing FRMR count"
        ::= { hypX25 31 }





    -- Port Availability Statistics
    hypX25BuffMax  OBJECT-TYPE
        SYNTAX INTEGER
        ACCESS read-only
        STATUS mandatory
        DESCRIPTION
        "Maximum number of buffers allocated"
        ::= { hypX25 32 }

    hypX25BuffThreshold  OBJECT-TYPE
        SYNTAX Counter
        ACCESS read-only
        STATUS mandatory
        DESCRIPTION
        "Number of times the buffer threshold was reached"
        ::= { hypX25 33 }

    hypX25BuffAllocFail  OBJECT-TYPE
        SYNTAX Counter
        ACCESS read-only
        STATUS mandatory
        DESCRIPTION
        "Number of buffer allocation failures"
        ::= { hypX25 34 }

    hypX25MemoryMode  OBJECT-TYPE
        SYNTAX Counter
        ACCESS read-only
        STATUS mandatory
        DESCRIPTION
        "Memory mode, 'E' = EPROM,   'R' = RAM mode"
        ::= { hypX25 35 }

    hypX25AlarmMode  OBJECT-TYPE
        SYNTAX Counter
        ACCESS read-only
        STATUS mandatory
        DESCRIPTION
        "Alarm mode, 'N' = No Minor TRAP's, 'Y' = All Alarms"
        ::= { hypX25 36 }

    hypX25SwitchDCP  OBJECT-TYPE
        SYNTAX Counter
        ACCESS read-only
        STATUS mandatory
        DESCRIPTION
        "Switched to DCP mode count"
        ::= { hypX25 37 }

    hypX25TimeDCP  OBJECT-TYPE
        SYNTAX INTEGER
        ACCESS read-only
        STATUS mandatory
        DESCRIPTION
        "Total time in DCP mode"
        ::= { hypX25 38 }



    --  X25 Logical Channel Status
    hypX25CntLogStatus  OBJECT-TYPE
        SYNTAX INTEGER
        ACCESS read-only
        STATUS mandatory
        DESCRIPTION
        "Count of X25 Logical Channel status"
        ::= { hypX25 39 }



    --Table of hypX25LogChanStatus
    --hypX25LogChanStatus description (Table format)
    hypX25LogChanStatusTable OBJECT-TYPE
        SYNTAX   SEQUENCE OF HypX25LogChanStatusEntry
        ACCESS   not-accessible
        STATUS   mandatory
        DESCRIPTION
        "A table containing information about
         x25 Logical Channel status fields"
        ::= { hypX25 40 }

        hypX25LogChanStatusEntry OBJECT-TYPE
        SYNTAX   HypX25LogChanStatusEntry
        ACCESS   not-accessible
        STATUS   mandatory
        DESCRIPTION
        "x25 Logical Channel status fields"
        INDEX { hypX25LogChanStatusIndex }
        ::= { hypX25LogChanStatusTable 1 }

        HypX25LogChanStatusEntry ::=
        SEQUENCE {
            hypX25LogChanStatusIndex
                INTEGER,
            hypX25LogChanStatus
                INTEGER
            }

        hypX25LogChanStatusIndex  OBJECT-TYPE
        SYNTAX INTEGER
        ACCESS read-only
        STATUS mandatory
        DESCRIPTION
        "The ifIndex Value of the corresponding ifEntry."
        ::= { hypX25LogChanStatusEntry 1 }

        hypX25LogChanStatus  OBJECT-TYPE
        SYNTAX INTEGER
        ACCESS read-only
        STATUS mandatory
        DESCRIPTION
        "x25 Logical Channel status"
        ::= { hypX25LogChanStatusEntry 2 }

    -- x25LogChanStatus Status value:
    --    00 - LCN connected
    --    01 - LCN not conected
    --    02 - LCN not defined



    --End of Table hypX25LogChanStatus  x25 Logical Channel status fields





    -- The x28 Group
    -- The x28 Group contains information about the x28
    -- functionality in a Hypercom IEN.

    hypX28PortStat  OBJECT-TYPE
        SYNTAX INTEGER
        ACCESS read-only
        STATUS mandatory
        DESCRIPTION
        "X28 Port Status 0=Com, 01=Cleared, xx=other"
        ::= { hypX28 1 }

    hypX28LastClearDn  OBJECT-TYPE
        SYNTAX INTEGER
        ACCESS read-only
        STATUS mandatory
        DESCRIPTION
        "X28 Last Clear Down Code (Hex 00-FF)"
        ::= { hypX28 2 }

    --  X28 Last Clear Down Codes are as follows:
    --    0XX = X.25 NETWORK ORIGINATED CLEAR CODES
    --    000 = REMOTE DTE INITIATED CLEAR DOWN
    --    2XX = IEN Node INTERNAL ERROR
    --    222 = PORT NEVER ACTIVE
    --    232 = IEN Node LINE STOPPED BY NMS
    --    237 = TERMINAL DISCONNECTED (BY CARRIER DROP)
    --    242 = TERMINAL ATTEMPTED TO CONNECT WHILE
    --          X.25 RESTART IN PROGRESS






    hypX28CntConnAttem  OBJECT-TYPE
        SYNTAX Counter
        ACCESS read-only
        STATUS mandatory
        DESCRIPTION
        "X28 Total number of connection attempts"
        ::= { hypX28 3 }

    hypX28CntConn  OBJECT-TYPE
        SYNTAX Counter
        ACCESS read-only
        STATUS mandatory
        DESCRIPTION
        "X28 Total number of connections"
        ::= { hypX28 4 }

    hypX28CntCommAttem  OBJECT-TYPE
        SYNTAX Counter
        ACCESS read-only
        STATUS mandatory
        DESCRIPTION
        "X28 Total number of connection attempts"
        ::= { hypX28 5 }

    hypX28CntFromLine  OBJECT-TYPE
        SYNTAX Counter
        ACCESS read-only
        STATUS mandatory
        DESCRIPTION
        "X28 Total number messages from line"
        ::= { hypX28 6 }

    hypX28CntToLine  OBJECT-TYPE
        SYNTAX Counter
        ACCESS read-only
        STATUS mandatory
        DESCRIPTION
        "X28 Total number messages to line"
        ::= { hypX28 7 }



    -- Port Availability Statistics
    hypX28BuffMax  OBJECT-TYPE
        SYNTAX INTEGER
        ACCESS read-only
        STATUS mandatory
        DESCRIPTION
        "Maximum number of Buffers allocated"
        ::= { hypX28 8 }

    hypX28BuffThreshold  OBJECT-TYPE
        SYNTAX Counter
        ACCESS read-only
        STATUS mandatory
        DESCRIPTION
        "Number of times the buffer threshold was reached"
        ::= { hypX28 9 }

    hypX28BuffAllocFail  OBJECT-TYPE
        SYNTAX Counter
        ACCESS read-only
        STATUS mandatory
        DESCRIPTION
        "Number of buffer allocation failures"
        ::= { hypX28 10 }

    hypX28CntRecovery  OBJECT-TYPE
        SYNTAX Counter
        ACCESS read-only
        STATUS mandatory
        DESCRIPTION
        "Count of recovery error restarts"
        ::= { hypX28 11 }

    hypX28CntFailure  OBJECT-TYPE
        SYNTAX Counter
        ACCESS read-only
        STATUS mandatory
        DESCRIPTION
        "Message delivery count failure due to rem control down"
        ::= { hypX28 12 }

    hypX28MemoryMode  OBJECT-TYPE
        SYNTAX Counter
        ACCESS read-only
        STATUS mandatory
        DESCRIPTION
        "Memory mode, 'E' = EPROM,   'R' = RAM mode"
        ::= { hypX28 13 }

    hypX28AlarmMode  OBJECT-TYPE
        SYNTAX Counter
        ACCESS read-only
        STATUS mandatory
        DESCRIPTION
        "Alarm mode, 'N' = No Minor TRAP's, 'Y' = All Alarms"
        ::= { hypX28 14 }




    -- The sna Group
    -- The sna Group contains information about the sna
    -- functionality in a Hypercom IEN.

    hypSnaPortStatus  OBJECT-TYPE
        SYNTAX INTEGER
        ACCESS read-only
        STATUS mandatory
        DESCRIPTION
        "SNA port status"
        ::= { hypSna 1 }

    hypSnaLogChHi  OBJECT-TYPE
        SYNTAX INTEGER
        ACCESS read-only
        STATUS mandatory
        DESCRIPTION
        "Logical Unit HI defined"
        ::= { hypSna 2 }

    hypSnaLogChLow  OBJECT-TYPE
        SYNTAX INTEGER
        ACCESS read-only
        STATUS mandatory
        DESCRIPTION
        "Logical Unit LOW defined"
        ::= { hypSna 3 }



    -- Level 3 [SNA  LEVEL] statistics
    hypSnaL3Restart  OBJECT-TYPE
        SYNTAX Counter
        ACCESS read-only
        STATUS mandatory
        DESCRIPTION
        "SNA Level 3 incoming active PU"
        ::= { hypSna 4 }

    hypSnaL3IncCalls  OBJECT-TYPE
        SYNTAX Counter
        ACCESS read-only
        STATUS mandatory
        DESCRIPTION
        "SNA Level 3 incoming bind counter"
        ::= { hypSna 5 }

    hypSnaL3OutCalls  OBJECT-TYPE
        SYNTAX Counter
        ACCESS read-only
        STATUS mandatory
        DESCRIPTION
        "SNA Level 3 outgoing init-self [3650 only]"
        ::= { hypSna 6 }

    hypSnaL3IncClears  OBJECT-TYPE
        SYNTAX Counter
        ACCESS read-only
        STATUS mandatory
        DESCRIPTION
        "SNA Level 3 incoming unbind counter"
        ::= { hypSna 7 }

    hypSnaL3OutClears  OBJECT-TYPE
        SYNTAX Counter
        ACCESS read-only
        STATUS mandatory
        DESCRIPTION
        "SNA Level 3 outgoing term-self [3650 only]"
        ::= { hypSna 8 }



    hypSnaL3IncFrame  OBJECT-TYPE
        SYNTAX Counter
        ACCESS read-only
        STATUS mandatory
        DESCRIPTION
        "SNA Level 3 incoming data frames"
        ::= { hypSna 9 }

    hypSnaL3OutFrame  OBJECT-TYPE
        SYNTAX Counter
        ACCESS read-only
        STATUS mandatory
        DESCRIPTION
        "SNA Level 3 outgoing data frames"
        ::= { hypSna 10 }

    hypSnaL3IncRNR  OBJECT-TYPE
        SYNTAX Counter
        ACCESS read-only
        STATUS mandatory
        DESCRIPTION
        "SNA Level 3 incoming Neg responses"
        ::= { hypSna 11 }

    hypSnaL3OutRNR  OBJECT-TYPE
        SYNTAX Counter
        ACCESS read-only
        STATUS mandatory
        DESCRIPTION
        "SNA Level 3 outgoing Neg responses"
        ::= { hypSna 12 }

    hypSnaL3IncReset  OBJECT-TYPE
        SYNTAX Counter
        ACCESS read-only
        STATUS mandatory
        DESCRIPTION
        "SNA Level 3 incoming reset count"
        ::= { hypSna 13 }

    hypSnaL3OutReset  OBJECT-TYPE
        SYNTAX Counter
        ACCESS read-only
        STATUS mandatory
        DESCRIPTION
        "SNA Level 3 outgoing reset count"
        ::= { hypSna 14 }

    hypSnaL3IncReject  OBJECT-TYPE
        SYNTAX Counter
        ACCESS read-only
        STATUS mandatory
        DESCRIPTION
        "SNA Level 3 incoming reject packet count"
        ::= { hypSna 15 }

    hypSnaL3OutReject  OBJECT-TYPE
        SYNTAX Counter
        ACCESS read-only
        STATUS mandatory
        DESCRIPTION
        "SNA Level 3 outgoing reject packet count"
        ::= { hypSna 16 }




    -- Level 2 [SDLC] statistics
    hypSnaCarrierLoss  OBJECT-TYPE
        SYNTAX Counter
        ACCESS read-only
        STATUS mandatory
        DESCRIPTION
        "SNA Level 2 carrier loss count"
        ::= { hypSna 17 }

    hypSnaRetransmitt  OBJECT-TYPE
        SYNTAX Counter
        ACCESS read-only
        STATUS mandatory
        DESCRIPTION
        "SNA Level 2 retransmitt count"
        ::= { hypSna 18 }

    hypSnaReceiveFrame  OBJECT-TYPE
        SYNTAX Counter
        ACCESS read-only
        STATUS mandatory
        DESCRIPTION
        "SNA Level 2 receive framing errors"
        ::= { hypSna 19 }

    hypSnaIncSABM  OBJECT-TYPE
        SYNTAX Counter
        ACCESS read-only
        STATUS mandatory
        DESCRIPTION
        "SNA Level 2 incoming SABM count"
        ::= { hypSna 20 }

    hypSnaOutSABM  OBJECT-TYPE
        SYNTAX Counter
        ACCESS read-only
        STATUS mandatory
        DESCRIPTION
        "SNA Level 2 outgoing SABM count"
        ::= { hypSna 21 }

    hypSnaIncRNR  OBJECT-TYPE
        SYNTAX Counter
        ACCESS read-only
        STATUS mandatory
        DESCRIPTION
        "SNA Level 2 incoming RNR count"
        ::= { hypSna 22 }

    hypSnaOutRNR  OBJECT-TYPE
        SYNTAX Counter
        ACCESS read-only
        STATUS mandatory
        DESCRIPTION
        "SNA Level 2 outgoing RNR count"
        ::= { hypSna 23 }

    hypSnaIncREJ  OBJECT-TYPE
        SYNTAX Counter
        ACCESS read-only
        STATUS mandatory
        DESCRIPTION
        "SNA Level 2 incoming REJ count"
        ::= { hypSna 24 }

    hypSnaOutREJ  OBJECT-TYPE
        SYNTAX Counter
        ACCESS read-only
        STATUS mandatory
        DESCRIPTION
        "SNA Level 2 outgoing REJ count"
        ::= { hypSna 25 }

    hypSnaIncDM  OBJECT-TYPE
        SYNTAX Counter
        ACCESS read-only
        STATUS mandatory
        DESCRIPTION
        "SNA Level 2 incoming DM count"
        ::= { hypSna 26 }

    hypSnaOutDM  OBJECT-TYPE
        SYNTAX Counter
        ACCESS read-only
        STATUS mandatory
        DESCRIPTION
        "SNA Level 2 outgoing DM count"
        ::= { hypSna 27 }

    hypSnaIncUA  OBJECT-TYPE
        SYNTAX Counter
        ACCESS read-only
        STATUS mandatory
        DESCRIPTION
        "SNA Level 2 incoming UA count"
        ::= { hypSna 28 }

    hypSnaOutUA  OBJECT-TYPE
        SYNTAX Counter
        ACCESS read-only
        STATUS mandatory
        DESCRIPTION
        "SNA Level 2 outgoing UA count"
        ::= { hypSna 29 }

    hypSnaIncFRMR  OBJECT-TYPE
        SYNTAX Counter
        ACCESS read-only
        STATUS mandatory
        DESCRIPTION
        "SNA Level 2 incoming FRMR count"
        ::= { hypSna 30 }

    hypSnaOutFRMR  OBJECT-TYPE
        SYNTAX Counter
        ACCESS read-only
        STATUS mandatory
        DESCRIPTION
        "SNA Level 2 outgoing FRMR count"
        ::= { hypSna 31 }


    -- Port Availability Statistics
    hypSnaBuffMax  OBJECT-TYPE
        SYNTAX INTEGER
        ACCESS read-only
        STATUS mandatory
        DESCRIPTION
        "Maximum number of buffers allocated"
        ::= { hypSna 32 }

    hypSnaBuffThreshold  OBJECT-TYPE
        SYNTAX Counter
        ACCESS read-only
        STATUS mandatory
        DESCRIPTION
        "Number of times the buffer threshold was reached"
        ::= { hypSna 33 }

    hypSnaBuffAllocFail  OBJECT-TYPE
        SYNTAX Counter
        ACCESS read-only
        STATUS mandatory
        DESCRIPTION
        "Number of buffer allocation failures"
        ::= { hypSna 34 }

    hypSnaCntRecovery  OBJECT-TYPE
        SYNTAX Counter
        ACCESS read-only
        STATUS mandatory
        DESCRIPTION
        "Count of recovery error restarts"
        ::= { hypSna 35 }

    hypSnaCntFailure  OBJECT-TYPE
        SYNTAX Counter
        ACCESS read-only
        STATUS mandatory
        DESCRIPTION
        "Message delivery count failure due to rem control down"
        ::= { hypSna 36 }

    hypSnaMemoryMode  OBJECT-TYPE
        SYNTAX Counter
        ACCESS read-only
        STATUS mandatory
        DESCRIPTION
        "Memory mode, 'E' = EPROM,   'R' = RAM mode"
        ::= { hypSna 37 }

    hypSnaAlarmMode  OBJECT-TYPE
        SYNTAX Counter
        ACCESS read-only
        STATUS mandatory
        DESCRIPTION
        "Alarm mode, 'N' = No Minor TRAP's, 'Y' = All Alarms"
        ::= { hypSna 38 }



    --  sna Logical Channel Status
    hypSnaCntLUStat  OBJECT-TYPE
        SYNTAX INTEGER
        ACCESS read-only
        STATUS mandatory
        DESCRIPTION
        "Count of SNA Logical Unit status"
        ::= { hypSna 39 }



    --Table of hypSnaLUStatus
    --hypSnaLUStatus description (Table format)
    hypSnaLUStatusTable OBJECT-TYPE
        SYNTAX   SEQUENCE OF HypSnaLUStatusEntry
        ACCESS   not-accessible
        STATUS   mandatory
        DESCRIPTION
        "A table containing information about
         port status fields"
        ::= { hypSna 40 }

        hypSnaLUStatusEntry OBJECT-TYPE
        SYNTAX   HypSnaLUStatusEntry
        ACCESS   not-accessible
        STATUS   mandatory
        DESCRIPTION
        "port status fields"
        INDEX { hypSnaLUStatusIndex }
        ::= { hypSnaLUStatusTable 1 }

        HypSnaLUStatusEntry ::=
        SEQUENCE {
            hypSnaLUStatusIndex
                INTEGER,
            hypSnaLUStatus
                INTEGER
            }

        hypSnaLUStatusIndex  OBJECT-TYPE
        SYNTAX INTEGER
        ACCESS read-only
        STATUS mandatory
        DESCRIPTION
        "The ifIndex Value of the corresponding ifEntry."
        ::= { hypSnaLUStatusEntry 1 }

        hypSnaLUStatus  OBJECT-TYPE
        SYNTAX INTEGER
        ACCESS read-only
        STATUS mandatory
        DESCRIPTION
        "SNA Logical Unit status"
        ::= { hypSnaLUStatusEntry 2 }




    --End of Table hypSnaLUStatus  port status fields
    -- snaLUStatus Status value:
    --    X0 - LU  acquired [in session]
    --    X1 - LU  released [no session]
    --    X2 - LU  inactive [no ACTLU]
    --    0X - LU  remote connected
    --    1X - LU  remote not connected
    --    2X - LU  remote not defined



    -- end of sna Group



    -- The FRAME RELAY Group
    -- from  RFC 1315 adopted for Hypercom Private MIB
    -- Frame Relay Interface


    -- Frame Relay Data Link Connection


    --Table of hypFrDLConn
    --hypFrDLConn description (Table format)
    hypFrDLConnTable OBJECT-TYPE
        SYNTAX   SEQUENCE OF HypFrDLConnEntry
        ACCESS   not-accessible
        STATUS   mandatory
        DESCRIPTION
        "A table containing information about
         Frame Relay Data Link Connection"
        ::= { hypFRelayMib 1 }

        hypFrDLConnEntry OBJECT-TYPE
        SYNTAX   HypFrDLConnEntry
        ACCESS   not-accessible
        STATUS   mandatory
        DESCRIPTION
        "Frame Relay Data Link Connection"
        INDEX { hypFrDLConnIndex }
        ::= { hypFrDLConnTable 1 }

        HypFrDLConnEntry ::=
        SEQUENCE {
            hypFrDLCIfIndex
                INTEGER,
            hypFrT1PollInterval
                INTEGER,
            hypFrT2PollVerification
                INTEGER,
            hypFrT3MsgFrequenctTimer
                INTEGER,
            hypFrN1PollStatusCnt
                Counter,
            hypFrN2ErrorThreshold
                Counter,
            hypFrN3MonitorEventCnt
                Counter,
            hypFrN4MsgFrequencyCnt
                Counter,
            hypFrMgtType
                INTEGER,
            hypFrAddrFmt
                INTEGER,
            hypFrFramesReceived
                Counter,
            hypFrFramesSent
                Counter,
            hypFrCntFECN
                Counter,
            hypFrCntBECN
                Counter,
            hypFrLmiSent
                INTEGER,
            hypFrLmiRecv
                INTEGER,
            hypFrPhyIf
                INTEGER
            }

        hypFrDLCIfIndex  OBJECT-TYPE
        SYNTAX INTEGER
        ACCESS read-only
        STATUS mandatory
        DESCRIPTION
        "The ifIndex  (FR Card Instance)"
        ::= { hypFrDLConnEntry 1 }

        hypFrT1PollInterval  OBJECT-TYPE
        SYNTAX INTEGER
        ACCESS read-only
        STATUS mandatory
        DESCRIPTION
        "T1 poll interval in seconds."
        ::= { hypFrDLConnEntry 2 }

        hypFrT2PollVerification  OBJECT-TYPE
        SYNTAX INTEGER
        ACCESS read-only
        STATUS mandatory
        DESCRIPTION
        "T2 poll verification in seconds."
        ::= { hypFrDLConnEntry 3 }

        hypFrT3MsgFrequenctTimer  OBJECT-TYPE
        SYNTAX INTEGER
        ACCESS read-only
        STATUS mandatory
        DESCRIPTION
        "T3 message frequency timer in seconds."
        ::= { hypFrDLConnEntry 4 }

        hypFrN1PollStatusCnt  OBJECT-TYPE
        SYNTAX Counter
        ACCESS read-only
        STATUS mandatory
        DESCRIPTION
        "N1 poll status count."
        ::= { hypFrDLConnEntry 5 }

        hypFrN2ErrorThreshold  OBJECT-TYPE
        SYNTAX Counter
        ACCESS read-only
        STATUS mandatory
        DESCRIPTION
        "N2 error threshold."
        ::= { hypFrDLConnEntry 6 }

        hypFrN3MonitorEventCnt  OBJECT-TYPE
        SYNTAX Counter
        ACCESS read-only
        STATUS mandatory
        DESCRIPTION
        "N3 monitored events count."
        ::= { hypFrDLConnEntry 7 }

        hypFrN4MsgFrequencyCnt  OBJECT-TYPE
        SYNTAX Counter
        ACCESS read-only
        STATUS mandatory
        DESCRIPTION
        "N4 message frequency count."
        ::= { hypFrDLConnEntry 8 }

        hypFrMgtType  OBJECT-TYPE
        SYNTAX INTEGER
        ACCESS read-only
        STATUS mandatory
        DESCRIPTION
        "Management type  { LMI (0), ANSI_AnnexD (1) }"
        ::= { hypFrDLConnEntry 9 }

        hypFrAddrFmt  OBJECT-TYPE
        SYNTAX INTEGER
        ACCESS read-only
        STATUS mandatory
        DESCRIPTION
        "Address format (2..4-byte format)   ( 2..4 )"
        ::= { hypFrDLConnEntry 10 }

        hypFrFramesReceived  OBJECT-TYPE
        SYNTAX Counter
        ACCESS read-only
        STATUS mandatory
        DESCRIPTION
        "Total frame received."
        ::= { hypFrDLConnEntry 11 }

        hypFrFramesSent  OBJECT-TYPE
        SYNTAX Counter
        ACCESS read-only
        STATUS mandatory
        DESCRIPTION
        "Total Frame sent."
        ::= { hypFrDLConnEntry 12 }

        hypFrCntFECN  OBJECT-TYPE
        SYNTAX Counter
        ACCESS read-only
        STATUS mandatory
        DESCRIPTION
        "Frame count with FECN"
        ::= { hypFrDLConnEntry 13 }

        hypFrCntBECN  OBJECT-TYPE
        SYNTAX Counter
        ACCESS read-only
        STATUS mandatory
        DESCRIPTION
        "Frame count with BECN"
        ::= { hypFrDLConnEntry 14 }

        hypFrLmiSent  OBJECT-TYPE
        SYNTAX INTEGER
        ACCESS read-only
        STATUS mandatory
        DESCRIPTION
        "Total LMI polls sent"
        ::= { hypFrDLConnEntry 15 }

        hypFrLmiRecv  OBJECT-TYPE
        SYNTAX INTEGER
        ACCESS read-only
        STATUS mandatory
        DESCRIPTION
        "Total LMI responses received"
        ::= { hypFrDLConnEntry 16 }

        hypFrPhyIf  OBJECT-TYPE
        SYNTAX INTEGER
        ACCESS read-only
        STATUS mandatory
        DESCRIPTION
        "Physical interface status"
        ::= { hypFrDLConnEntry 17 }

    --   NotConnected (1),
    --   Connected    (2),
    --   Loopback     (3),
    --   PortStopped  (4)  port stopped by NMS



    --End of Table hypFrDLConn  Frame Relay Data Link Connection


    -- Frame Relay Circuits


    --Table of hypFrPVCirStatus
    --hypFrPVCirStatus description (Table format)
    hypFrPVCirStatusTable OBJECT-TYPE
        SYNTAX   SEQUENCE OF HypFrPVCirStatusEntry
        ACCESS   not-accessible
        STATUS   mandatory
        DESCRIPTION
        "A table containing information about
         Frame Relay PVC interface"
        ::= { hypFRelayMib 2 }

        hypFrPVCirStatusEntry OBJECT-TYPE
        SYNTAX   HypFrPVCirStatusEntry
        ACCESS   not-accessible
        STATUS   mandatory
        DESCRIPTION
        "Frame Relay PVC interface"
        INDEX { hypFrPVCirStatusIndex }
        ::= { hypFrPVCirStatusTable 1 }

        HypFrPVCirStatusEntry ::=
        SEQUENCE {
            hypFrPVCIfIndex
                INTEGER,
            hypFrPVCDLCINumber
                INTEGER,
            hypFrPVCStatus
                INTEGER,
            hypFrPVCframesReceived
                Counter,
            hypFrPVCframesSent
                Counter
            }

        hypFrPVCIfIndex  OBJECT-TYPE
        SYNTAX INTEGER
        ACCESS read-only
        STATUS mandatory
        DESCRIPTION
        "The ifIndex  (FR Card Instance)"
        ::= { hypFrPVCirStatusEntry 1 }

        hypFrPVCDLCINumber  OBJECT-TYPE
        SYNTAX INTEGER
        ACCESS read-only
        STATUS mandatory
        DESCRIPTION
        "PVC DLCI number 0001-1023  (DLCI number on card)"
        ::= { hypFrPVCirStatusEntry 2 }

        hypFrPVCStatus  OBJECT-TYPE
        SYNTAX INTEGER
        ACCESS read-only
        STATUS mandatory
        DESCRIPTION
        "PVC status, 00=idle, 01=active  { idle (0), active (1) }"
        ::= { hypFrPVCirStatusEntry 3 }

        hypFrPVCframesReceived  OBJECT-TYPE
        SYNTAX Counter
        ACCESS read-only
        STATUS mandatory
        DESCRIPTION
        "frames received"
        ::= { hypFrPVCirStatusEntry 4 }

        hypFrPVCframesSent  OBJECT-TYPE
        SYNTAX Counter
        ACCESS read-only
        STATUS mandatory
        DESCRIPTION
        "frames sent"
        ::= { hypFrPVCirStatusEntry 5 }




    --End of Table hypFrPVCirStatus  Frame Relay PVC interface
    -- End of Frame Relay



    -- The lanBridgeRouter Group
    -- The lanBridgeRouter Group contains information about the
    -- LAN Bridge configuration Parameters in a Hypercom IEN.

    hypIpNac  OBJECT-TYPE
        SYNTAX NetworkAddress
        ACCESS read-write
        STATUS mandatory
        DESCRIPTION
        "NAC IP address"
        ::= { hypLanBridgeRouter 1 }

    hypHardwareAddr  OBJECT-TYPE
        SYNTAX MacAddress
        ACCESS read-write
        STATUS mandatory
        DESCRIPTION
        "NAC hardware address"
        ::= { hypLanBridgeRouter 2 }

    hypRmtHardwareAddr  OBJECT-TYPE
        SYNTAX MacAddress
        ACCESS read-write
        STATUS mandatory
        DESCRIPTION
        "NAC remote hardware address"
        ::= { hypLanBridgeRouter 3 }

    hypLclSegAddr  OBJECT-TYPE
        SYNTAX NetworkAddress
        ACCESS read-write
        STATUS mandatory
        DESCRIPTION
        "NAC local LAN segment address"
        ::= { hypLanBridgeRouter 4 }

    hypRmtLanAddr  OBJECT-TYPE
        SYNTAX NetworkAddress
        ACCESS read-write
        STATUS mandatory
        DESCRIPTION
        "NAC remote LAN segment address"
        ::= { hypLanBridgeRouter 5 }

    hypRmtBridge  OBJECT-TYPE
        SYNTAX INTEGER
        ACCESS read-write
        STATUS mandatory
        DESCRIPTION
        "NAC remote bridge number"
        ::= { hypLanBridgeRouter 6 }

    hypNHop  OBJECT-TYPE
        SYNTAX Counter
        ACCESS read-write
        STATUS mandatory
        DESCRIPTION
        "Hop count"
        ::= { hypLanBridgeRouter 7 }

    hypFilterOptions  OBJECT-TYPE
        SYNTAX INTEGER
        ACCESS read-write
        STATUS mandatory
        DESCRIPTION
        "Filter options"
        ::= { hypLanBridgeRouter 8 }

    hypBRouterMode  OBJECT-TYPE
        SYNTAX INTEGER
        ACCESS read-write
        STATUS mandatory
        DESCRIPTION
        "Router mode (0 = static, 1 = dynamic)"
        ::= { hypLanBridgeRouter 9 }

    hypProtocol  OBJECT-TYPE
        SYNTAX INTEGER
        ACCESS read-write
        STATUS mandatory
        DESCRIPTION
        "Protocol (0 = RIP, 01=OSPF)"
        ::= { hypLanBridgeRouter 10 }

    hypIpGateway  OBJECT-TYPE
        SYNTAX NetworkAddress
        ACCESS read-write
        STATUS mandatory
        DESCRIPTION
        "Gateway IP address"
        ::= { hypLanBridgeRouter 11 }





    -- The lanStatistics Group
    -- The lanStatistics Group contains information about the
    -- Bridge performance stats in a Hypercom IEN.

    hypLanType  OBJECT-TYPE
        SYNTAX INTEGER
        ACCESS read-only
        STATUS mandatory
        DESCRIPTION
        "LAN type (00 = token ring, 01=Ethernet)"
        ::= { hypLanStatistics 1 }

    hypLanSpeed  OBJECT-TYPE
        SYNTAX INTEGER
        ACCESS read-only
        STATUS mandatory
        DESCRIPTION
        "LAN speed (04-4Mbps, 0A-10Mbps, 10-16Mbps)"
        ::= { hypLanStatistics 2 }

    hypLanStatus  OBJECT-TYPE
        SYNTAX INTEGER
        ACCESS read-only
        STATUS mandatory
        DESCRIPTION
        "LAN status (0 = connected, 1=disconnected)"
        ::= { hypLanStatistics 3 }

    hypLanPortStatus  OBJECT-TYPE
        SYNTAX INTEGER
        ACCESS read-only
        STATUS mandatory
        DESCRIPTION
        "Port status (0=active, 1=idle)"
        ::= { hypLanStatistics 4 }

    hypBcastFrames  OBJECT-TYPE
        SYNTAX Counter
        ACCESS read-only
        STATUS mandatory
        DESCRIPTION
        "broadcast frames"
        ::= { hypLanStatistics 5 }

    hypBcastBytes  OBJECT-TYPE
        SYNTAX Counter
        ACCESS read-only
        STATUS mandatory
        DESCRIPTION
        "broadcast bytes"
        ::= { hypLanStatistics 6 }

    hypFrames  OBJECT-TYPE
        SYNTAX Counter
        ACCESS read-only
        STATUS mandatory
        DESCRIPTION
        "non-broadcast frames"
        ::= { hypLanStatistics 7 }

    hypBytes  OBJECT-TYPE
        SYNTAX Counter
        ACCESS read-only
        STATUS mandatory
        DESCRIPTION
        "non-broadcast bytes"
        ::= { hypLanStatistics 8 }

    hypSingleRouteBcast  OBJECT-TYPE
        SYNTAX INTEGER
        ACCESS read-only
        STATUS mandatory
        DESCRIPTION
        "single route broadcast (00=no, 01=yes)"
        ::= { hypLanStatistics 9 }

    hypFramesDiscarded  OBJECT-TYPE
        SYNTAX Counter
        ACCESS read-only
        STATUS mandatory
        DESCRIPTION
        "frames discarded"
        ::= { hypLanStatistics 10 }

    hypFramesNotReceived  OBJECT-TYPE
        SYNTAX Counter
        ACCESS read-only
        STATUS mandatory
        DESCRIPTION
        "frames not received"
        ::= { hypLanStatistics 11 }

    hypFramesNotForwarded  OBJECT-TYPE
        SYNTAX Counter
        ACCESS read-only
        STATUS mandatory
        DESCRIPTION
        "frames not forwarded"
        ::= { hypLanStatistics 12 }



    -- The bridgeStations Group
    -- The bridgeStations Group contains information about the
    -- LAN Bridge Router stations list in a Hypercom IEN.

    hypLanBrCntLanStations  OBJECT-TYPE
        SYNTAX INTEGER
        ACCESS read-only
        STATUS mandatory
        DESCRIPTION
        "Number of lan stations"
        ::= { hypBridgeStations 1 }



    --Table of hypLanStation
    --hypLanStation description (Table format)
    hypLanStationTable OBJECT-TYPE
        SYNTAX   SEQUENCE OF HypLanStationEntry
        ACCESS   not-accessible
        STATUS   mandatory
        DESCRIPTION
        "A table containing information about
         LAN stations"
        ::= { hypBridgeStations 2 }

        hypLanStationEntry OBJECT-TYPE
        SYNTAX   HypLanStationEntry
        ACCESS   not-accessible
        STATUS   mandatory
        DESCRIPTION
        "LAN stations"
        INDEX { hypLanStationIndex }
        ::= { hypLanStationTable 1 }

        HypLanStationEntry ::=
        SEQUENCE {
            hypLanStationIndex
                INTEGER,
            hypHwAddr
                MacAddress,
            hypLanBrStatus
                INTEGER,
            hypFeature
                INTEGER
            }

        hypLanStationIndex  OBJECT-TYPE
        SYNTAX INTEGER
        ACCESS read-only
        STATUS mandatory
        DESCRIPTION
        "The ifIndex Value of the corresponding ifEntry."
        ::= { hypLanStationEntry 1 }

        hypHwAddr  OBJECT-TYPE
        SYNTAX MacAddress
        ACCESS read-only
        STATUS mandatory
        DESCRIPTION
        "hardware address"
        ::= { hypLanStationEntry 2 }

        hypLanBrStatus  OBJECT-TYPE
        SYNTAX INTEGER
        ACCESS read-only
        STATUS mandatory
        DESCRIPTION
        "status (0 = good, non-zero=error)"
        ::= { hypLanStationEntry 3 }

        hypFeature  OBJECT-TYPE
        SYNTAX INTEGER
        ACCESS read-only
        STATUS mandatory
        DESCRIPTION
        "station feature"
        ::= { hypLanStationEntry 4 }




    --End of Table hypLanStation  LAN stations
    --       Station Feature
    --               0x011B = bridge/REM/RPS
    --               0x0100 = bridge/router
    --               0x0000 = LAN station



    -- The ipRemoteSubnets Group
    -- The ipRemoteSubnets Group contains information about the
    -- ip Remote Subnets in a Hypercom IEN.

    hypCntRemoteSubnets  OBJECT-TYPE
        SYNTAX INTEGER
        ACCESS read-only
        STATUS mandatory
        DESCRIPTION
        "number of IP Remote Subnets (max 16)"
        ::= { hypIpRemoteSubnets 1 }



    --Table of hypRemoteSubnets
    --hypRemoteSubnets description (Table format)
    hypRemoteSubnetsTable OBJECT-TYPE
        SYNTAX   SEQUENCE OF HypRemoteSubnetsEntry
        ACCESS   not-accessible
        STATUS   mandatory
        DESCRIPTION
        "A table containing information about
         IP Remote Subnets"
        ::= { hypIpRemoteSubnets 2 }

        hypRemoteSubnetsEntry OBJECT-TYPE
        SYNTAX   HypRemoteSubnetsEntry
        ACCESS   not-accessible
        STATUS   mandatory
        DESCRIPTION
        "IP Remote Subnets"
        INDEX { hypRemoteSubnetsIndex }
        ::= { hypRemoteSubnetsTable 1 }

        HypRemoteSubnetsEntry ::=
        SEQUENCE {
            hypRemoteSubnetsIndex
                INTEGER,
            hypIpSubnetAddress
                MacAddress
            }

        hypRemoteSubnetsIndex  OBJECT-TYPE
        SYNTAX INTEGER
        ACCESS read-only
        STATUS mandatory
        DESCRIPTION
        "The ifIndex Value of the corresponding ifEntry."
        ::= { hypRemoteSubnetsEntry 1 }

        hypIpSubnetAddress  OBJECT-TYPE
        SYNTAX MacAddress
        ACCESS read-only
        STATUS mandatory
        DESCRIPTION
        "IP Subnet Address"
        ::= { hypRemoteSubnetsEntry 2 }




    --End of Table hypRemoteSubnets  IP Remote Subnets
    hypRemSubCntLanStations  OBJECT-TYPE
        SYNTAX INTEGER
        ACCESS read-only
        STATUS mandatory
        DESCRIPTION
        "number of LAN Stations (max 16)"
        ::= { hypIpRemoteSubnets 3 }



    --Table of hypLanStationsTable
    --hypLanStationsTable description (Table format)
    hypLanStationsTableTable OBJECT-TYPE
        SYNTAX   SEQUENCE OF HypLanStationsTableEntry
        ACCESS   not-accessible
        STATUS   mandatory
        DESCRIPTION
        "A table containing information about
         Lan stations"
        ::= { hypIpRemoteSubnets 4 }

        hypLanStationsTableEntry OBJECT-TYPE
        SYNTAX   HypLanStationsTableEntry
        ACCESS   not-accessible
        STATUS   mandatory
        DESCRIPTION
        "Lan stations"
        INDEX { hypLanStationsTableIndex }
        ::= { hypLanStationsTableTable 1 }

        HypLanStationsTableEntry ::=
        SEQUENCE {
            hypLanStationsIndex
                INTEGER,
            hypRemSubIpAddress
                NetworkAddress,
            hypRemSumMacAddress
                MacAddress,
            hypIp
                INTEGER,
            hypIpx
                INTEGER,
            hypSR
                INTEGER,
            hypRouter
                INTEGER,
            hypIpRemSubStatus
                INTEGER
            }

        hypLanStationsIndex  OBJECT-TYPE
        SYNTAX INTEGER
        ACCESS read-only
        STATUS mandatory
        DESCRIPTION
        "The ifIndex Value of the corresponding ifEntry."
        ::= { hypLanStationsTableEntry 1 }

        hypRemSubIpAddress  OBJECT-TYPE
        SYNTAX NetworkAddress
        ACCESS read-only
        STATUS mandatory
        DESCRIPTION
        "IP Address"
        ::= { hypLanStationsTableEntry 2 }

        hypRemSumMacAddress  OBJECT-TYPE
        SYNTAX MacAddress
        ACCESS read-only
        STATUS mandatory
        DESCRIPTION
        "MAC Address"
        ::= { hypLanStationsTableEntry 3 }

        hypIp  OBJECT-TYPE
        SYNTAX INTEGER
        ACCESS read-only
        STATUS mandatory
        DESCRIPTION
        "Status of ip,     0 =not enabled"
        ::= { hypLanStationsTableEntry 4 }

        hypIpx  OBJECT-TYPE
        SYNTAX INTEGER
        ACCESS read-only
        STATUS mandatory
        DESCRIPTION
        "Status of ipx,    0 =not enabled"
        ::= { hypLanStationsTableEntry 5 }

        hypSR  OBJECT-TYPE
        SYNTAX INTEGER
        ACCESS read-only
        STATUS mandatory
        DESCRIPTION
        "Status of SR,     0 =not enabled"
        ::= { hypLanStationsTableEntry 6 }

        hypRouter  OBJECT-TYPE
        SYNTAX INTEGER
        ACCESS read-only
        STATUS mandatory
        DESCRIPTION
        "Status of router, 0 =not enabled"
        ::= { hypLanStationsTableEntry 7 }

        hypIpRemSubStatus  OBJECT-TYPE
        SYNTAX INTEGER
        ACCESS read-only
        STATUS mandatory
        DESCRIPTION
        "Status, 0=active, non-zero=error"
        ::= { hypLanStationsTableEntry 8 }




    --End of Table hypLanStationsTable  Lan stations




    -- The tokenRingIf Group
    -- The tokenRingIf Group contains information about the
    -- Token Ring Interface Parameters in a Hypercom IEN.

    hypTokenLanType  OBJECT-TYPE
        SYNTAX INTEGER
        ACCESS read-only
        STATUS mandatory
        DESCRIPTION
        "LAN type 0=Eth, 1=4M TR, 2=16M TR"
        ::= { hypTokenRingIf 1 }

    hypTokenUtilNow  OBJECT-TYPE
        SYNTAX Gauge
        ACCESS read-only
        STATUS mandatory
        DESCRIPTION
        "LAN utilization - Now in frames/second"
        ::= { hypTokenRingIf 2 }

    hypTokenUtilAvg  OBJECT-TYPE
        SYNTAX Gauge
        ACCESS read-only
        STATUS mandatory
        DESCRIPTION
        "LAN utilization - Average in frames/second since last reset"
        ::= { hypTokenRingIf 3 }

    hypTokenUtilPeak  OBJECT-TYPE
        SYNTAX Gauge
        ACCESS read-only
        STATUS mandatory
        DESCRIPTION
        "LAN utilization - Peak in frames/second since last reset"
        ::= { hypTokenRingIf 4 }





    -- The remoteLanSegList Group
    -- The remoteLanSegList Group contains information about the
    -- Remote Lan Segment/bridge numbers in a Hypercom IEN.

    hypLocalLanNumber  OBJECT-TYPE
        SYNTAX INTEGER
        ACCESS read-only
        STATUS mandatory
        DESCRIPTION
        "Local LAN segment/bridge number"
        ::= { hypRemoteLanSegList 1 }

    hypCntRemoteLanSeg  OBJECT-TYPE
        SYNTAX INTEGER
        ACCESS read-only
        STATUS mandatory
        DESCRIPTION
        "number of Remote LAN segment/bridge numbers (max 32)"
        ::= { hypRemoteLanSegList 2 }



    --Table of hypRemoteLanSeg
    --hypRemoteLanSeg description (Table format)
    hypRemoteLanSegTable OBJECT-TYPE
        SYNTAX   SEQUENCE OF HypRemoteLanSegEntry
        ACCESS   not-accessible
        STATUS   mandatory
        DESCRIPTION
        "A table containing information about
         Remote LAN segments"
        ::= { hypRemoteLanSegList 3 }

        hypRemoteLanSegEntry OBJECT-TYPE
        SYNTAX   HypRemoteLanSegEntry
        ACCESS   not-accessible
        STATUS   mandatory
        DESCRIPTION
        "Remote LAN segments"
        INDEX { hypRemoteLanSegIndex }
        ::= { hypRemoteLanSegTable 1 }

        HypRemoteLanSegEntry ::=
        SEQUENCE {
            hypRemoteLanSegIndex
                INTEGER,
            hypRemoteLanSegBrg
                MacAddress
            }

        hypRemoteLanSegIndex  OBJECT-TYPE
        SYNTAX INTEGER
        ACCESS read-only
        STATUS mandatory
        DESCRIPTION
        "The ifIndex Value of the corresponding ifEntry."
        ::= { hypRemoteLanSegEntry 1 }

        hypRemoteLanSegBrg  OBJECT-TYPE
        SYNTAX MacAddress
        ACCESS read-only
        STATUS mandatory
        DESCRIPTION
        "Remote LAN segment/bridge number"
        ::= { hypRemoteLanSegEntry 2 }




    --End of Table hypRemoteLanSeg  Remote LAN segments




    -- The DS1 Group
    -- The DS1 Group contains information about the T1
    -- module of a Hypercom IEN.

    hypDs1In  OBJECT-TYPE
        SYNTAX Counter
        ACCESS read-only
        STATUS mandatory
        DESCRIPTION
        "The number of T1 packet received"
        ::= { hypDs1Mib 1 }

    hypDs1Out  OBJECT-TYPE
        SYNTAX Counter
        ACCESS read-only
        STATUS mandatory
        DESCRIPTION
        "The number of T1 packet sent."
        ::= { hypDs1Mib 2 }





    -- The Admin Group
    -- The Admin Group contains the Alarm log text description



    hypTrapLogText  OBJECT-TYPE
        SYNTAX OCTET STRING (SIZE (255))
        ACCESS read-only
        STATUS mandatory
        DESCRIPTION
        "Alarm log text description in NMS proxy agent  (SIZE (0..255))"
        ::= { hypAdmin 1 }





    --  beginning of Hypercom TRAP's based on Hypercom IEN Alarms

    hypTrap03 TRAP-TYPE
        ENTERPRISE  hypAlarmSystem
         -- VARIABLES { hypTrapLogText }
        DESCRIPTION
            "Port Stopped by IENView
             NMS alarm: 03(h), severity: alarm"
        ::= 3

    hypTrap08 TRAP-TYPE
        ENTERPRISE  hypAlarmSystem
         -- VARIABLES { hypTrapLogText }
        DESCRIPTION
            "Loopback Set by IENView
             NMS alarm: 08(h), severity: alarm"
        ::= 8

    hypTrap09 TRAP-TYPE
        ENTERPRISE  hypAlarmSystem
         -- VARIABLES { hypTrapLogText }
        DESCRIPTION
            "Loopback Detected From TELCO
             NMS alarm: 09(h), severity: alarm"
        ::= 9

    hypTrap10 TRAP-TYPE
        ENTERPRISE  hypAlarmSystem
         -- VARIABLES { hypTrapLogText }
        DESCRIPTION
            "Port Not Installed
             NMS alarm: 10(h), severity: alarm"
        ::= 16

    hypTrap20 TRAP-TYPE
        ENTERPRISE  hypAlarmSystem
         -- VARIABLES { hypTrapLogText }
        DESCRIPTION
            "Hardware Memory Error
             NMS alarm: 20(h), severity: alarm"
        ::= 32

    hypTrap21 TRAP-TYPE
        ENTERPRISE  hypAlarmSystem
         -- VARIABLES { hypTrapLogText }
        DESCRIPTION
            "Hardware Circuit I/O Error
             NMS alarm: 21(h), severity: alarm"
        ::= 33

    hypTrap22 TRAP-TYPE
        ENTERPRISE  hypAlarmSystem
         -- VARIABLES { hypTrapLogText }
        DESCRIPTION
            "Hardware Configuration Error
             NMS alarm: 22(h), severity: alarm"
        ::= 34

    hypTrap23 TRAP-TYPE
        ENTERPRISE  hypAlarmSystem
         -- VARIABLES { hypTrapLogText }
        DESCRIPTION
            "Self-Diagnostic Failure at IPL
             NMS alarm: 23(h), severity: alarm"
        ::= 35

    hypTrap24 TRAP-TYPE
        ENTERPRISE  hypAlarmSystem
         -- VARIABLES { hypTrapLogText }
        DESCRIPTION
            "Power Supply Failure
             NMS alarm: 24(h), severity: alarm"
        ::= 36

    hypTrap25 TRAP-TYPE
        ENTERPRISE  hypAlarmSystem
         -- VARIABLES { hypTrapLogText }
        DESCRIPTION
            "Port Lost
             NMS alarm: 25(h), severity: alarm"
        ::= 37

    hypTrap26 TRAP-TYPE
        ENTERPRISE  hypAlarmSystem
         -- VARIABLES { hypTrapLogText }
        DESCRIPTION
            "Port Reset
             NMS alarm: 26(h), severity: alarm"
        ::= 38

    hypTrap30 TRAP-TYPE
        ENTERPRISE  hypAlarmSystem
         -- VARIABLES { hypTrapLogText }
        DESCRIPTION
            "Invalid Port Configuration
             NMS alarm: 30(h), severity: alarm"
        ::= 48

    hypTrap31 TRAP-TYPE
        ENTERPRISE  hypAlarmSystem
         -- VARIABLES { hypTrapLogText }
        DESCRIPTION
            "No Poll Response on Link
             NMS alarm: 31(h), severity: alarm"
        ::= 49

    hypTrap32 TRAP-TYPE
        ENTERPRISE  hypAlarmSystem
         -- VARIABLES { hypTrapLogText }
        DESCRIPTION
            "Constant Half Duplex Carrier
             NMS alarm: 32(h), severity: alarm"
        ::= 50

    hypTrap33 TRAP-TYPE
        ENTERPRISE  hypAlarmSystem
         -- VARIABLES { hypTrapLogText }
        DESCRIPTION
            "Lost Full Duplex Carrier
             NMS alarm: 33(h), severity: alarm"
        ::= 51

    hypTrap34 TRAP-TYPE
        ENTERPRISE  hypAlarmSystem
         -- VARIABLES { hypTrapLogText }
        DESCRIPTION
            "Restored Full Duplex Carrier
             NMS alarm: 34(h), severity: alarm"
        ::= 52

    hypTrap35 TRAP-TYPE
        ENTERPRISE  hypAlarmSystem
         -- VARIABLES { hypTrapLogText }
        DESCRIPTION
            "No DSR Signal
             NMS alarm: 35(h), severity: alarm"
        ::= 53

    hypTrap36 TRAP-TYPE
        ENTERPRISE  hypAlarmSystem
         -- VARIABLES { hypTrapLogText }
        DESCRIPTION
            "Alarm Generated
             NMS alarm: 36(h), severity: alarm"
        ::= 54

    hypTrap37 TRAP-TYPE
        ENTERPRISE  hypAlarmSystem
         -- VARIABLES { hypTrapLogText }
        DESCRIPTION
            "Poll Response on Link Resumed
             NMS alarm: 37(h), severity: alarm"
        ::= 55

    hypTrap38 TRAP-TYPE
        ENTERPRISE  hypAlarmSystem
         -- VARIABLES { hypTrapLogText }
        DESCRIPTION
            "ISDN Dial: Manually Initiated
             NMS alarm: 38(h), severity: information"
        ::= 56

    hypTrap39 TRAP-TYPE
        ENTERPRISE  hypAlarmSystem
         -- VARIABLES { hypTrapLogText }
        DESCRIPTION
            "ISDN Dial: Application Trigger
             NMS alarm: 39(h), severity: information"
        ::= 57

    hypTrap3A TRAP-TYPE
        ENTERPRISE  hypAlarmSystem
         -- VARIABLES { hypTrapLogText }
        DESCRIPTION
            "ISDN Dial: Dial Overflow
             NMS alarm: 3A(h), severity: information"
        ::= 58

    hypTrap3B TRAP-TYPE
        ENTERPRISE  hypAlarmSystem
         -- VARIABLES { hypTrapLogText }
        DESCRIPTION
            "ISDN Dial: Primary Link Failure
             NMS alarm: 3B(h), severity: information"
        ::= 59

    hypTrap3C TRAP-TYPE
        ENTERPRISE  hypAlarmSystem
         -- VARIABLES { hypTrapLogText }
        DESCRIPTION
            "ISDN Dial: Call Disconnected
             NMS alarm: 3C(h), severity: information"
        ::= 60

    hypTrap3D TRAP-TYPE
        ENTERPRISE  hypAlarmSystem
         -- VARIABLES { hypTrapLogText }
        DESCRIPTION
            "ISDN Data Link Lost
             NMS alarm: 3D(h), severity: error"
        ::= 61

    hypTrap3E TRAP-TYPE
        ENTERPRISE  hypAlarmSystem
         -- VARIABLES { hypTrapLogText }
        DESCRIPTION
            "ISDN Data Link Restored
             NMS alarm: 3E(h), severity: error"
        ::= 62

    hypTrap40 TRAP-TYPE
        ENTERPRISE  hypAlarmSystem
         -- VARIABLES { hypTrapLogText }
        DESCRIPTION
            "Communication Line Buffer Overflow
             NMS alarm: 40(h), severity: alarm"
        ::= 64

    hypTrap41 TRAP-TYPE
        ENTERPRISE  hypAlarmSystem
         -- VARIABLES { hypTrapLogText }
        DESCRIPTION
            "Communication Bus Buffer Overflow
             NMS alarm: 41(h), severity: alarm"
        ::= 65

    hypTrap42 TRAP-TYPE
        ENTERPRISE  hypAlarmSystem
         -- VARIABLES { hypTrapLogText }
        DESCRIPTION
            "Message Lost - Unrecoverable Protocol Error
             NMS alarm: 42(h), severity: alarm"
        ::= 66

    hypTrap44 TRAP-TYPE
        ENTERPRISE  hypAlarmSystem
         -- VARIABLES { hypTrapLogText }
        DESCRIPTION
            "Retransmit Threshold Exceeded
             NMS alarm: 44(h), severity: alarm"
        ::= 68

    hypTrap45 TRAP-TYPE
        ENTERPRISE  hypAlarmSystem
         -- VARIABLES { hypTrapLogText }
        DESCRIPTION
            "Messages Lost - Communication Bus Buffer Overflow
             NMS alarm: 45(h), severity: alarm"
        ::= 69

    hypTrap46 TRAP-TYPE
        ENTERPRISE  hypAlarmSystem
         -- VARIABLES { hypTrapLogText }
        DESCRIPTION
            "Framing Error Threshold Exceeded
             NMS alarm: 46(h), severity: alarm"
        ::= 70

    hypTrap47 TRAP-TYPE
        ENTERPRISE  hypAlarmSystem
         -- VARIABLES { hypTrapLogText }
        DESCRIPTION
            "Communication Bus Buffer Threshold Reached
             NMS alarm: 47(h), severity: alarm"
        ::= 71

    hypTrap48 TRAP-TYPE
        ENTERPRISE  hypAlarmSystem
         -- VARIABLES { hypTrapLogText }
        DESCRIPTION
            "Communication Line Buffer Threshold Reached
             NMS alarm: 48(h), severity: alarm"
        ::= 72

    hypTrap49 TRAP-TYPE
        ENTERPRISE  hypAlarmSystem
         -- VARIABLES { hypTrapLogText }
        DESCRIPTION
            "Uplink Retransmit Threshold Exceeded
             NMS alarm: 49(h), severity: alarm"
        ::= 73

    hypTrap4A TRAP-TYPE
        ENTERPRISE  hypAlarmSystem
         -- VARIABLES { hypTrapLogText }
        DESCRIPTION
            "Duplicate Bus Address
             NMS alarm: 4A(h), severity: alarm"
        ::= 74

    hypTrap4B TRAP-TYPE
        ENTERPRISE  hypAlarmSystem
         -- VARIABLES { hypTrapLogText }
        DESCRIPTION
            "Message Sent Through Alternate Route
             NMS alarm: 4B(h), severity: alarm"
        ::= 75

    hypTrap4C TRAP-TYPE
        ENTERPRISE  hypAlarmSystem
         -- VARIABLES { hypTrapLogText }
        DESCRIPTION
            "Frame Size Exceeded
             NMS alarm: 4C(h), severity: information"
        ::= 76

    hypTrap4D TRAP-TYPE
        ENTERPRISE  hypAlarmSystem
         -- VARIABLES { hypTrapLogText }
        DESCRIPTION
            "Frame-Relay CIR Exceeded
             NMS alarm: 4D(h), severity: error"
        ::= 77

    hypTrap4E TRAP-TYPE
        ENTERPRISE  hypAlarmSystem
         -- VARIABLES { hypTrapLogText }
        DESCRIPTION
            "Incorrect Service Profile ID (SPID) Specified
             NMS alarm: 4E(h), severity: alarm"
        ::= 78

    hypTrap4F TRAP-TYPE
        ENTERPRISE  hypAlarmSystem
         -- VARIABLES { hypTrapLogText }
        DESCRIPTION
            "Table Download Requested
             NMS alarm: 4F(h), severity: information"
        ::= 79

    hypTrap50 TRAP-TYPE
        ENTERPRISE  hypAlarmSystem
         -- VARIABLES { hypTrapLogText }
        DESCRIPTION
            "Port Initialization Required
             NMS alarm: 50(h), severity: alarm"
        ::= 80

    hypTrap51 TRAP-TYPE
        ENTERPRISE  hypAlarmSystem
         -- VARIABLES { hypTrapLogText }
        DESCRIPTION
            "Port Upload Requested
             NMS alarm: 51(h), severity: alarm"
        ::= 81

    hypTrap52 TRAP-TYPE
        ENTERPRISE  hypAlarmSystem
         -- VARIABLES { hypTrapLogText }
        DESCRIPTION
            "NII Table Download Required
             NMS alarm: 52(h), severity: information"
        ::= 82

    hypTrap53 TRAP-TYPE
        ENTERPRISE  hypAlarmSystem
         -- VARIABLES { hypTrapLogText }
        DESCRIPTION
            "DTC Routing Table Download Required
             NMS alarm: 53(h), severity: information"
        ::= 83

    hypTrap56 TRAP-TYPE
        ENTERPRISE  hypAlarmSystem
         -- VARIABLES { hypTrapLogText }
        DESCRIPTION
            "PPP Async Table Download Required
             NMS alarm: 56(h), severity: information"
        ::= 86

    hypTrap57 TRAP-TYPE
        ENTERPRISE  hypAlarmSystem
         -- VARIABLES { hypTrapLogText }
        DESCRIPTION
            "DCM Routing Table Download Required
             NMS alarm: 57(h), severity: information"
        ::= 87

    hypTrap58 TRAP-TYPE
        ENTERPRISE  hypAlarmSystem
         -- VARIABLES { hypTrapLogText }
        DESCRIPTION
            "Internet Application Table Download Required
             NMS alarm: 58(h), severity: information"
        ::= 88

    hypTrap59 TRAP-TYPE
        ENTERPRISE  hypAlarmSystem
         -- VARIABLES { hypTrapLogText }
        DESCRIPTION
            "Master Encryption Key Download Required
             NMS alarm: 59(h), severity: alarm"
        ::= 89

    hypTrap5A TRAP-TYPE
        ENTERPRISE  hypAlarmSystem
         -- VARIABLES { hypTrapLogText }
        DESCRIPTION
            "IP Configuration Table Download Required
             NMS alarm: 5A(h), severity: information"
        ::= 90

    hypTrap5B TRAP-TYPE
        ENTERPRISE  hypAlarmSystem
         -- VARIABLES { hypTrapLogText }
        DESCRIPTION
            "LAT Async Configuration Table Download Required
             NMS alarm: 5B(h), severity: information"
        ::= 91

    hypTrap5C TRAP-TYPE
        ENTERPRISE  hypAlarmSystem
         -- VARIABLES { hypTrapLogText }
        DESCRIPTION
            "NII Table Download Required
             NMS alarm: 5C(h), severity: information"
        ::= 92

    hypTrap5D TRAP-TYPE
        ENTERPRISE  hypAlarmSystem
         -- VARIABLES { hypTrapLogText }
        DESCRIPTION
            "Configuration Download Required
             NMS alarm: 5D(h), severity: information"
        ::= 93

    hypTrap5E TRAP-TYPE
        ENTERPRISE  hypAlarmSystem
         -- VARIABLES { hypTrapLogText }
        DESCRIPTION
            "Virtual Circuit Table Load Required
             NMS alarm: 5E(h), severity: information"
        ::= 94

    hypTrap5F TRAP-TYPE
        ENTERPRISE  hypAlarmSystem
         -- VARIABLES { hypTrapLogText }
        DESCRIPTION
            "Configuration Download Required
             NMS alarm: 5F(h), severity: alarm"
        ::= 95

    hypTrap60 TRAP-TYPE
        ENTERPRISE  hypAlarmSystem
         -- VARIABLES { hypTrapLogText }
        DESCRIPTION
            "Dial Connection Established
             NMS alarm: 60(h), severity: error"
        ::= 96

    hypTrap61 TRAP-TYPE
        ENTERPRISE  hypAlarmSystem
         -- VARIABLES { hypTrapLogText }
        DESCRIPTION
            "Dial Connection Lost
             NMS alarm: 61(h), severity: alarm"
        ::= 97

    hypTrap62 TRAP-TYPE
        ENTERPRISE  hypAlarmSystem
         -- VARIABLES { hypTrapLogText }
        DESCRIPTION
            "IPX Configuration Table Download Required
             NMS alarm: 62(h), severity: information"
        ::= 98

    hypTrap63 TRAP-TYPE
        ENTERPRISE  hypAlarmSystem
         -- VARIABLES { hypTrapLogText }
        DESCRIPTION
            "SNMP Configuration Table Download Required
             NMS alarm: 63(h), severity: information"
        ::= 99

    hypTrap64 TRAP-TYPE
        ENTERPRISE  hypAlarmSystem
         -- VARIABLES { hypTrapLogText }
        DESCRIPTION
            "Dial Backup Table Download Required
             NMS alarm: 64(h), severity: information"
        ::= 100

    hypTrap65 TRAP-TYPE
        ENTERPRISE  hypAlarmSystem
         -- VARIABLES { hypTrapLogText }
        DESCRIPTION
            "Protocol Priorities Table Download Required
             NMS alarm: 65(h), severity: information"
        ::= 101

    hypTrap66 TRAP-TYPE
        ENTERPRISE  hypAlarmSystem
         -- VARIABLES { hypTrapLogText }
        DESCRIPTION
            "Modem AT Commands Download Required
             NMS alarm: 66(h), severity: information"
        ::= 102

    hypTrap67 TRAP-TYPE
        ENTERPRISE  hypAlarmSystem
         -- VARIABLES { hypTrapLogText }
        DESCRIPTION
            "HTSP Configuration Table Load Required
             NMS alarm: 67(h), severity: information"
        ::= 103

    hypTrap68 TRAP-TYPE
        ENTERPRISE  hypAlarmSystem
         -- VARIABLES { hypTrapLogText }
        DESCRIPTION
            "Duplicate Drop
             NMS alarm: 68(h), severity: alarm"
        ::= 104

    hypTrap69 TRAP-TYPE
        ENTERPRISE  hypAlarmSystem
         -- VARIABLES { hypTrapLogText }
        DESCRIPTION
            "Extended Dial Backup Table Download Required
             NMS alarm: 69(h), severity: information"
        ::= 105

    hypTrap6A TRAP-TYPE
        ENTERPRISE  hypAlarmSystem
         -- VARIABLES { hypTrapLogText }
        DESCRIPTION
            "X.3 PAD Profile Request
             NMS alarm: 6A(h), severity: information"
        ::= 106

    hypTrap6B TRAP-TYPE
        ENTERPRISE  hypAlarmSystem
         -- VARIABLES { hypTrapLogText }
        DESCRIPTION
            "PVC Table Load Download Required
             NMS alarm: 6B(h), severity: information"
        ::= 107

    hypTrap6C TRAP-TYPE
        ENTERPRISE  hypAlarmSystem
         -- VARIABLES { hypTrapLogText }
        DESCRIPTION
            "End-to-End Configuration Table Load Required
             NMS alarm: 6C(h), severity: information"
        ::= 108

    hypTrap6D TRAP-TYPE
        ENTERPRISE  hypAlarmSystem
         -- VARIABLES { hypTrapLogText }
        DESCRIPTION
            "LAN LAT Server Configuration Table Download Required
             NMS alarm: 6D(h), severity: information"
        ::= 109

    hypTrap6E TRAP-TYPE
        ENTERPRISE  hypAlarmSystem
         -- VARIABLES { hypTrapLogText }
        DESCRIPTION
            "Node to Node Connected
             NMS alarm: 6E(h), severity: information"
        ::= 110

    hypTrap6F TRAP-TYPE
        ENTERPRISE  hypAlarmSystem
         -- VARIABLES { hypTrapLogText }
        DESCRIPTION
            "Node to Node Disconnected
             NMS alarm: 6F(h), severity: alarm"
        ::= 111

    hypTrap70 TRAP-TYPE
        ENTERPRISE  hypAlarmSystem
         -- VARIABLES { hypTrapLogText }
        DESCRIPTION
            "Communication Error Threshold Exceeded
             NMS alarm: 70(h), severity: alarm"
        ::= 112

    hypTrap71 TRAP-TYPE
        ENTERPRISE  hypAlarmSystem
         -- VARIABLES { hypTrapLogText }
        DESCRIPTION
            "No Incoming Calls on Port
             NMS alarm: 71(h), severity: alarm"
        ::= 113

    hypTrap72 TRAP-TYPE
        ENTERPRISE  hypAlarmSystem
         -- VARIABLES { hypTrapLogText }
        DESCRIPTION
            "Call Abandoned Threshold Reached
             NMS alarm: 72(h), severity: alarm"
        ::= 114

    hypTrap73 TRAP-TYPE
        ENTERPRISE  hypAlarmSystem
         -- VARIABLES { hypTrapLogText }
        DESCRIPTION
            "Host Response Time Threshold Exceeded
             NMS alarm: 73(h), severity: alarm"
        ::= 115

    hypTrap74 TRAP-TYPE
        ENTERPRISE  hypAlarmSystem
         -- VARIABLES { hypTrapLogText }
        DESCRIPTION
            "No Incoming Calls on Any Port
             NMS alarm: 74(h), severity: alarm"
        ::= 116

    hypTrap75 TRAP-TYPE
        ENTERPRISE  hypAlarmSystem
         -- VARIABLES { hypTrapLogText }
        DESCRIPTION
            "Permanent Dial Line Seizure
             NMS alarm: 75(h), severity: alarm"
        ::= 117

    hypTrap76 TRAP-TYPE
        ENTERPRISE  hypAlarmSystem
         -- VARIABLES { hypTrapLogText }
        DESCRIPTION
            "Line Disconnect Max Call Length Time Threshold Exceeded
             NMS alarm: 76(h), severity: alarm"
        ::= 118

    hypTrap77 TRAP-TYPE
        ENTERPRISE  hypAlarmSystem
         -- VARIABLES { hypTrapLogText }
        DESCRIPTION
            "Hardware Restart Threshold Exceeded
             NMS alarm: 77(h), severity: alarm"
        ::= 119

    hypTrap78 TRAP-TYPE
        ENTERPRISE  hypAlarmSystem
         -- VARIABLES { hypTrapLogText }
        DESCRIPTION
            "Statistics Overflow
             NMS alarm: 78(h), severity: information"
        ::= 120

    hypTrap79 TRAP-TYPE
        ENTERPRISE  hypAlarmSystem
         -- VARIABLES { hypTrapLogText }
        DESCRIPTION
            "No Response From Host on Port
             NMS alarm: 79(h), severity: alarm"
        ::= 121

    hypTrap7A TRAP-TYPE
        ENTERPRISE  hypAlarmSystem
         -- VARIABLES { hypTrapLogText }
        DESCRIPTION
            "Bus Buffer Allocation Warning
             NMS alarm: 7A(h), severity: information"
        ::= 122

    hypTrap7B TRAP-TYPE
        ENTERPRISE  hypAlarmSystem
         -- VARIABLES { hypTrapLogText }
        DESCRIPTION
            "No Data Encryption Hardware Detected
             NMS alarm: 7B(h), severity: error"
        ::= 123

    hypTrap7C TRAP-TYPE
        ENTERPRISE  hypAlarmSystem
         -- VARIABLES { hypTrapLogText }
        DESCRIPTION
            "High Speed Bus Disabled
             NMS alarm: 7C(h), severity: alarm"
        ::= 124

    hypTrap7D TRAP-TYPE
        ENTERPRISE  hypAlarmSystem
         -- VARIABLES { hypTrapLogText }
        DESCRIPTION
            "IP Access Filter Table Download Required
             NMS alarm: 7D(h), severity: information"
        ::= 125

    hypTrap7E TRAP-TYPE
        ENTERPRISE  hypAlarmSystem
         -- VARIABLES { hypTrapLogText }
        DESCRIPTION
            "IPX Access Filter Table Download Required
             NMS alarm: 7E(h), severity: information"
        ::= 126

    hypTrap7F TRAP-TYPE
        ENTERPRISE  hypAlarmSystem
         -- VARIABLES { hypTrapLogText }
        DESCRIPTION
            "IP Routing Protocol Config Table Download Required
             NMS alarm: 7F(h), severity: information"
        ::= 127

    hypTrap80 TRAP-TYPE
        ENTERPRISE  hypAlarmSystem
         -- VARIABLES { hypTrapLogText }
        DESCRIPTION
            "No Data Uplink Session
             NMS alarm: 80(h), severity: alarm"
        ::= 128

    hypTrap81 TRAP-TYPE
        ENTERPRISE  hypAlarmSystem
         -- VARIABLES { hypTrapLogText }
        DESCRIPTION
            "No IENView Uplink Session
             NMS alarm: 81(h), severity: alarm"
        ::= 129

    hypTrap82 TRAP-TYPE
        ENTERPRISE  hypAlarmSystem
         -- VARIABLES { hypTrapLogText }
        DESCRIPTION
            "X.25 Data Uplink Session Restored
             NMS alarm: 82(h), severity: alarm"
        ::= 130

    hypTrap83 TRAP-TYPE
        ENTERPRISE  hypAlarmSystem
         -- VARIABLES { hypTrapLogText }
        DESCRIPTION
            "IENView Uplink Session Restored
             NMS alarm: 83(h), severity: alarm"
        ::= 131

    hypTrap84 TRAP-TYPE
        ENTERPRISE  hypAlarmSystem
         -- VARIABLES { hypTrapLogText }
        DESCRIPTION
            "Port Hardware Error Corrected
             NMS alarm: 84(h), severity: alarm"
        ::= 132

    hypTrapB0 TRAP-TYPE
        ENTERPRISE  hypAlarmSystem
         -- VARIABLES { hypTrapLogText }
        DESCRIPTION
            "No Transaction Reply From Host
             NMS alarm: B0(h), severity: alarm"
        ::= 176

    hypTrapB1 TRAP-TYPE
        ENTERPRISE  hypAlarmSystem
         -- VARIABLES { hypTrapLogText }
        DESCRIPTION
            "RTM Overflow
             NMS alarm: B1(h), severity: alarm"
        ::= 177

    hypTrapB2 TRAP-TYPE
        ENTERPRISE  hypAlarmSystem
         -- VARIABLES { hypTrapLogText }
        DESCRIPTION
            "Excessive X.25 Restarts
             NMS alarm: B2(h), severity: alarm"
        ::= 178

    hypTrapB3 TRAP-TYPE
        ENTERPRISE  hypAlarmSystem
         -- VARIABLES { hypTrapLogText }
        DESCRIPTION
            "DS1 Link Lost
             NMS alarm: B3(h), severity: alarm"
        ::= 179

    hypTrapB4 TRAP-TYPE
        ENTERPRISE  hypAlarmSystem
         -- VARIABLES { hypTrapLogText }
        DESCRIPTION
            "Yellow Alarm
             NMS alarm: B4(h), severity: alarm"
        ::= 180

    hypTrapB5 TRAP-TYPE
        ENTERPRISE  hypAlarmSystem
         -- VARIABLES { hypTrapLogText }
        DESCRIPTION
            "Blue Alarm
             NMS alarm: B5(h), severity: alarm"
        ::= 181

    hypTrapB6 TRAP-TYPE
        ENTERPRISE  hypAlarmSystem
         -- VARIABLES { hypTrapLogText }
        DESCRIPTION
            "DS1 Link Restored
             NMS alarm: B6(h), severity: alarm"
        ::= 182

    hypTrapB7 TRAP-TYPE
        ENTERPRISE  hypAlarmSystem
         -- VARIABLES { hypTrapLogText }
        DESCRIPTION
            "Bipolar Violation Threshold Exceeded
             NMS alarm: B7(h), severity: alarm"
        ::= 183

    hypTrapB8 TRAP-TYPE
        ENTERPRISE  hypAlarmSystem
         -- VARIABLES { hypTrapLogText }
        DESCRIPTION
            "CRC Violation Threshold Exceeded
             NMS alarm: B8(h), severity: alarm"
        ::= 184

    hypTrapB9 TRAP-TYPE
        ENTERPRISE  hypAlarmSystem
         -- VARIABLES { hypTrapLogText }
        DESCRIPTION
            "No Signal Duration Threshold Exceeded
             NMS alarm: B9(h), severity: alarm"
        ::= 185

    hypTrapBA TRAP-TYPE
        ENTERPRISE  hypAlarmSystem
         -- VARIABLES { hypTrapLogText }
        DESCRIPTION
            "Transmit Frame Error Threshold Exceeded
             NMS alarm: BA(h), severity: alarm"
        ::= 186

    hypTrapBB TRAP-TYPE
        ENTERPRISE  hypAlarmSystem
         -- VARIABLES { hypTrapLogText }
        DESCRIPTION
            "SLIP Violation Threshold Exceeded
             NMS alarm: BB(h), severity: alarm"
        ::= 187

    hypTrapBC TRAP-TYPE
        ENTERPRISE  hypAlarmSystem
         -- VARIABLES { hypTrapLogText }
        DESCRIPTION
            "Compressed Voice Options Request
             NMS alarm: BC(h), severity: information"
        ::= 188

    hypTrapBD TRAP-TYPE
        ENTERPRISE  hypAlarmSystem
         -- VARIABLES { hypTrapLogText }
        DESCRIPTION
            "Call Plan Table Request
             NMS alarm: BD(h), severity: information"
        ::= 189

    hypTrapBE TRAP-TYPE
        ENTERPRISE  hypAlarmSystem
         -- VARIABLES { hypTrapLogText }
        DESCRIPTION
            "Bulk Link Up Alarm
             NMS alarm: BE(h), severity: information"
        ::= 190

    hypTrapBF TRAP-TYPE
        ENTERPRISE  hypAlarmSystem
         -- VARIABLES { hypTrapLogText }
        DESCRIPTION
            "IEN 100 Central Node Active
             NMS alarm: BF(h), severity: information"
        ::= 191

    hypTrapE0 TRAP-TYPE
        ENTERPRISE  hypAlarmSystem
         -- VARIABLES { hypTrapLogText }
        DESCRIPTION
            "Token Ring Signal Lost
             NMS alarm: E0(h), severity: alarm"
        ::= 224

    hypTrapE1 TRAP-TYPE
        ENTERPRISE  hypAlarmSystem
         -- VARIABLES { hypTrapLogText }
        DESCRIPTION
            "Single Token Ring Station
             NMS alarm: E1(h), severity: alarm"
        ::= 225

    hypTrapE2 TRAP-TYPE
        ENTERPRISE  hypAlarmSystem
         -- VARIABLES { hypTrapLogText }
        DESCRIPTION
            "Token Ring Lobe Wiring Fault
             NMS alarm: E2(h), severity: alarm"
        ::= 226

    hypTrapE3 TRAP-TYPE
        ENTERPRISE  hypAlarmSystem
         -- VARIABLES { hypTrapLogText }
        DESCRIPTION
            "Token Ring Beaconing
             NMS alarm: E3(h), severity: alarm"
        ::= 227

    hypTrapE4 TRAP-TYPE
        ENTERPRISE  hypAlarmSystem
         -- VARIABLES { hypTrapLogText }
        DESCRIPTION
            "Hub / Mau Error
             NMS alarm: E4(h), severity: alarm"
        ::= 228

    hypTrapE5 TRAP-TYPE
        ENTERPRISE  hypAlarmSystem
         -- VARIABLES { hypTrapLogText }
        DESCRIPTION
            "Token Ring Bridge Configuration Error
             NMS alarm: E5(h), severity: alarm"
        ::= 229

    hypTrapE7 TRAP-TYPE
        ENTERPRISE  hypAlarmSystem
         -- VARIABLES { hypTrapLogText }
        DESCRIPTION
            "Duplicate MAC Address
             NMS alarm: E7(h), severity: alarm"
        ::= 231

    hypTrapE8 TRAP-TYPE
        ENTERPRISE  hypAlarmSystem
         -- VARIABLES { hypTrapLogText }
        DESCRIPTION
            "Excessive Router Traffic
             NMS alarm: E8(h), severity: alarm"
        ::= 232

    hypTrapE9 TRAP-TYPE
        ENTERPRISE  hypAlarmSystem
         -- VARIABLES { hypTrapLogText }
        DESCRIPTION
            "Invalid IPX Network Number
             NMS alarm: E9(h), severity: alarm"
        ::= 233

    hypTrapEA TRAP-TYPE
        ENTERPRISE  hypAlarmSystem
         -- VARIABLES { hypTrapLogText }
        DESCRIPTION
            "Invalid IP Network Number
             NMS alarm: EA(h), severity: alarm"
        ::= 234

    hypTrapEC TRAP-TYPE
        ENTERPRISE  hypAlarmSystem
         -- VARIABLES { hypTrapLogText }
        DESCRIPTION
            "Voice Directory Download Required
             NMS alarm: EC(h), severity: information"
        ::= 236

    hypTrapF1 TRAP-TYPE
        ENTERPRISE  hypAlarmSystem
         -- VARIABLES { hypTrapLogText }
        DESCRIPTION
            "General Alarm
             NMS alarm: F1(h), severity: alarm"
        ::= 241

    hypTrapF2 TRAP-TYPE
        ENTERPRISE  hypAlarmSystem
         -- VARIABLES { hypTrapLogText }
        DESCRIPTION
            "Program Verification Request
             NMS alarm: F2(h), severity: information"
        ::= 242

    hypTrapF3 TRAP-TYPE
        ENTERPRISE  hypAlarmSystem
         -- VARIABLES { hypTrapLogText }
        DESCRIPTION
            "Encryption Hardware Error
             NMS alarm: F3(h), severity: error"
        ::= 243

    hypTrapF4 TRAP-TYPE
        ENTERPRISE  hypAlarmSystem
         -- VARIABLES { hypTrapLogText }
        DESCRIPTION
            "Link is not secure
             NMS alarm: F4(h), severity: error"
        ::= 244

    hypTrapF5 TRAP-TYPE
        ENTERPRISE  hypAlarmSystem
         -- VARIABLES { hypTrapLogText }
        DESCRIPTION
            "Link is secure
             NMS alarm: F5(h), severity: information"
        ::= 245

    hypTrapF6 TRAP-TYPE
        ENTERPRISE  hypAlarmSystem
         -- VARIABLES { hypTrapLogText }
        DESCRIPTION
            "Compression Hardware Error
             NMS alarm: F6(h), severity: error"
        ::= 246

    hypTrapF7 TRAP-TYPE
        ENTERPRISE  hypAlarmSystem
         -- VARIABLES { hypTrapLogText }
        DESCRIPTION
            "Link is compressed
             NMS alarm: F7(h), severity: information"
        ::= 247

    hypTrapF8 TRAP-TYPE
        ENTERPRISE  hypAlarmSystem
         -- VARIABLES { hypTrapLogText }
        DESCRIPTION
            "Multiple sub-types subsystem alarms
             NMS alarm: F8(h), severity: alarm"
        ::= 248

    hypTrapF9 TRAP-TYPE
        ENTERPRISE  hypAlarmSystem
         -- VARIABLES { hypTrapLogText }
        DESCRIPTION
            "Multiple sub-types subsystem errors
             NMS error: F9(h), severity: error"
        ::= 249

    hypTrapFA TRAP-TYPE
        ENTERPRISE  hypAlarmSystem
         -- VARIABLES { hypTrapLogText }
        DESCRIPTION
            "Multiple sub-types subsystem information
             NMS info: FA(h), severity: information"
        ::= 250

    hypLogInfo  TRAP-TYPE
        ENTERPRISE  hypAlarmSystem
         -- VARIABLES { hypTrapLogText }
        DESCRIPTION
            " Info message in NMS Alarm log
             NMS alarm: f01(h), flag: 00(h), type: (8) Test Mode"
        ::= 3841

    hypLogError  TRAP-TYPE
        ENTERPRISE  hypAlarmSystem
         -- VARIABLES { hypTrapLogText }
        DESCRIPTION
            " Error message in NMS Alarm log
             NMS alarm: f02(h), flag: 00(h), type: (8) Test Mode"
        ::= 3842

    hypLogAlarm  TRAP-TYPE
        ENTERPRISE  hypAlarmSystem
         -- VARIABLES { hypTrapLogText }
        DESCRIPTION
            " Alarm message in NMS Alarm log
             NMS alarm: f03(h), flag: 00(h), type: (8) Test Mode"
        ::= 3843

    hypTrapF811 TRAP-TYPE
        ENTERPRISE  hypAlarmSystem
         -- VARIABLES { hypTrapLogText }
        DESCRIPTION
            "VC Cleared by Operator Action
             NMS info: f811(h), severity: information"
        ::= 63505

    hypTrapF812 TRAP-TYPE
        ENTERPRISE  hypAlarmSystem
         -- VARIABLES { hypTrapLogText }
        DESCRIPTION
            "Unrecognized Packet Format
             NMS info: f812(h), severity: error"
        ::= 63506

    hypTrapF813 TRAP-TYPE
        ENTERPRISE  hypAlarmSystem
         -- VARIABLES { hypTrapLogText }
        DESCRIPTION
            "Time out on Receive From Device (DCE)
             NMS info: f813(h), severity: error"
        ::= 63507

    hypTrapF814 TRAP-TYPE
        ENTERPRISE  hypAlarmSystem
         -- VARIABLES { hypTrapLogText }
        DESCRIPTION
            "Time out on Receive From Device (DTE)
             NMS info: f814(h), severity: error"
        ::= 63508

    hypTrapF815 TRAP-TYPE
        ENTERPRISE  hypAlarmSystem
         -- VARIABLES { hypTrapLogText }
        DESCRIPTION
            "Clear Request to Reset Indication
             NMS info: f815(h), severity: information"
        ::= 63509

    hypTrapF816 TRAP-TYPE
        ENTERPRISE  hypAlarmSystem
         -- VARIABLES { hypTrapLogText }
        DESCRIPTION
            "Dataset Signals Drop (DCE)
             NMS info: f816(h), severity: alarm"
        ::= 63510

    hypTrapF817 TRAP-TYPE
        ENTERPRISE  hypAlarmSystem
         -- VARIABLES { hypTrapLogText }
        DESCRIPTION
            "Dataset Signals Drop (DTE)
             NMS info: f817(h), severity: alarm"
        ::= 63511

    hypTrapF818 TRAP-TYPE
        ENTERPRISE  hypAlarmSystem
         -- VARIABLES { hypTrapLogText }
        DESCRIPTION
            "Host Sent Transparent Text to Non-transparent Device
             NMS info: f818(h), severity: error"
        ::= 63512

    hypTrapF819 TRAP-TYPE
        ENTERPRISE  hypAlarmSystem
         -- VARIABLES { hypTrapLogText }
        DESCRIPTION
            "VC Cleared LLC End to End Circuit Failure
             NMS info: f819(h), severity: alarm"
        ::= 63513

    hypTrapF821 TRAP-TYPE
        ENTERPRISE  hypAlarmSystem
         -- VARIABLES { hypTrapLogText }
        DESCRIPTION
            "VC Terminated Refer to Vendor Documentation
             NMS info: f821(h), severity: error"
        ::= 63521

    hypTrapF831 TRAP-TYPE
        ENTERPRISE  hypAlarmSystem
         -- VARIABLES { hypTrapLogText }
        DESCRIPTION
            "VC Established
             NMS info: f831(h), severity: information"
        ::= 63537

    hypTrapF841 TRAP-TYPE
        ENTERPRISE  hypAlarmSystem
         -- VARIABLES { hypTrapLogText }
        DESCRIPTION
            "No Dataset Signal (DSR)
             NMS info: f841(h), severity: alarm"
        ::= 63553

    hypTrapF842 TRAP-TYPE
        ENTERPRISE  hypAlarmSystem
         -- VARIABLES { hypTrapLogText }
        DESCRIPTION
            "No Dataset Signal (DTR)
             NMS info: f842(h), severity: alarm"
        ::= 63554

    hypTrapF843 TRAP-TYPE
        ENTERPRISE  hypAlarmSystem
         -- VARIABLES { hypTrapLogText }
        DESCRIPTION
            "Disconnect Received
             NMS info: f843(h), severity: alarm"
        ::= 63555

    hypTrapF844 TRAP-TYPE
        ENTERPRISE  hypAlarmSystem
         -- VARIABLES { hypTrapLogText }
        DESCRIPTION
            "N2 Retransmissions Exceeded
             NMS info: f844(h), severity: alarm"
        ::= 63556

    hypTrapF845 TRAP-TYPE
        ENTERPRISE  hypAlarmSystem
         -- VARIABLES { hypTrapLogText }
        DESCRIPTION
            "No Flags Received
             NMS info: f845(h), severity: alarm"
        ::= 63557

    hypTrapF846 TRAP-TYPE
        ENTERPRISE  hypAlarmSystem
         -- VARIABLES { hypTrapLogText }
        DESCRIPTION
            "No Clock
             NMS info: f846(h), severity: alarm"
        ::= 63558

    hypTrapF847 TRAP-TYPE
        ENTERPRISE  hypAlarmSystem
         -- VARIABLES { hypTrapLogText }
        DESCRIPTION
            "Disconnect Mode Received
             NMS info: f847(h), severity: alarm"
        ::= 63559

    hypTrapF848 TRAP-TYPE
        ENTERPRISE  hypAlarmSystem
         -- VARIABLES { hypTrapLogText }
        DESCRIPTION
            "Disconnect Sent
             NMS info: f848(h), severity: alarm"
        ::= 63560

    hypTrapF849 TRAP-TYPE
        ENTERPRISE  hypAlarmSystem
         -- VARIABLES { hypTrapLogText }
        DESCRIPTION
            "No Dataset Signal (DCD)
             NMS info: f849(h), severity: alarm"
        ::= 63561

    hypTrapF851 TRAP-TYPE
        ENTERPRISE  hypAlarmSystem
         -- VARIABLES { hypTrapLogText }
        DESCRIPTION
            "Line Up
             NMS info: f851(h), severity: information"
        ::= 63569

    hypTrapF860 TRAP-TYPE
        ENTERPRISE  hypAlarmSystem
         -- VARIABLES { hypTrapLogText }
        DESCRIPTION
            "SPSVC Cleared By Host
             NMS info: f860(h), severity: alarm"
        ::= 63584

    hypTrapF861 TRAP-TYPE
        ENTERPRISE  hypAlarmSystem
         -- VARIABLES { hypTrapLogText }
        DESCRIPTION
            "LCN Pool Exhausted
             NMS info: f861(h), severity: alarm"
        ::= 63585

    hypTrapF862 TRAP-TYPE
        ENTERPRISE  hypAlarmSystem
         -- VARIABLES { hypTrapLogText }
        DESCRIPTION
            "PRI D-Channel Lost
             NMS info: f862(h), severity: alarm"
        ::= 63586

    hypTrapF863 TRAP-TYPE
        ENTERPRISE  hypAlarmSystem
         -- VARIABLES { hypTrapLogText }
        DESCRIPTION
            "PRI D-Channel Restored
             NMS info: f863(h), severity: information"
        ::= 63587

    hypTrapF864 TRAP-TYPE
        ENTERPRISE  hypAlarmSystem
         -- VARIABLES { hypTrapLogText }
        DESCRIPTION
            "No NII Routes Available
             NMS info: f864(h), severity: alarm"
        ::= 63588

    hypTrapF865 TRAP-TYPE
        ENTERPRISE  hypAlarmSystem
         -- VARIABLES { hypTrapLogText }
        DESCRIPTION
            "NII Routes Restored
             NMS info: f865(h), severity: information"
        ::= 63589

    hypTrapF866 TRAP-TYPE
        ENTERPRISE  hypAlarmSystem
         -- VARIABLES { hypTrapLogText }
        DESCRIPTION
            "T1/E1 Link Lost
             NMS info: f866(h), severity: alarm"
        ::= 63590

    hypTrapF867 TRAP-TYPE
        ENTERPRISE  hypAlarmSystem
         -- VARIABLES { hypTrapLogText }
        DESCRIPTION
            "T1/E1 Link Restored
             NMS info: f867(h), severity: information"
        ::= 63591

    hypTrapF870 TRAP-TYPE
        ENTERPRISE  hypAlarmSystem
         -- VARIABLES { hypTrapLogText }
        DESCRIPTION
            "No NUA from Terminal
             NMS info: f870(h), severity: alarm"
        ::= 63600

    hypTrapF871 TRAP-TYPE
        ENTERPRISE  hypAlarmSystem
         -- VARIABLES { hypTrapLogText }
        DESCRIPTION
            "Unknown NUA from Terminal
             NMS info: f871(h), severity: alarm"
        ::= 63601

    hypTrapF872 TRAP-TYPE
        ENTERPRISE  hypAlarmSystem
         -- VARIABLES { hypTrapLogText }
        DESCRIPTION
            "No NII Route for NUA from Terminal
             NMS info: f872(h), severity: alarm"
        ::= 63602

    hypTrapF873 TRAP-TYPE
        ENTERPRISE  hypAlarmSystem
         -- VARIABLES { hypTrapLogText }
        DESCRIPTION
            "No Message Received from Terminal
             NMS info: f873(h), severity: alarm"
        ::= 63603

    hypTrapF874 TRAP-TYPE
        ENTERPRISE  hypAlarmSystem
         -- VARIABLES { hypTrapLogText }
        DESCRIPTION
            "No Host Available
             NMS info: f874(h), severity: alarm"
        ::= 63604

    hypTrapF875 TRAP-TYPE
        ENTERPRISE  hypAlarmSystem
         -- VARIABLES { hypTrapLogText }
        DESCRIPTION
            "No Host Response
             NMS info: f875(h), severity: alarm"
        ::= 63605

    hypTrapF876 TRAP-TYPE
        ENTERPRISE  hypAlarmSystem
         -- VARIABLES { hypTrapLogText }
        DESCRIPTION
            "No DLE/EOT from Terminal
             NMS info: f876(h), severity: error"
        ::= 63606

    hypTrapF877 TRAP-TYPE
        ENTERPRISE  hypAlarmSystem
         -- VARIABLES { hypTrapLogText }
        DESCRIPTION
            "No UA from Terminal
             NMS info: f877(h), severity: alarm"
        ::= 63607

    hypTrapF878 TRAP-TYPE
        ENTERPRISE  hypAlarmSystem
         -- VARIABLES { hypTrapLogText }
        DESCRIPTION
            "No Call Request from Terminal
             NMS info: f878(h), severity: alarm"
        ::= 63608

    hypTrapF879 TRAP-TYPE
        ENTERPRISE  hypAlarmSystem
         -- VARIABLES { hypTrapLogText }
        DESCRIPTION
            "Unknown NUI Received from Terminal
             NMS info: f879(h), severity: alarm"
        ::= 63609

    hypTrapF87A TRAP-TYPE
        ENTERPRISE  hypAlarmSystem
         -- VARIABLES { hypTrapLogText }
        DESCRIPTION
            "No Packet Restart Confirmation from Terminal
             NMS info: f87a(h), severity: error"
        ::= 63610

    hypTrapF87B TRAP-TYPE
        ENTERPRISE  hypAlarmSystem
         -- VARIABLES { hypTrapLogText }
        DESCRIPTION
            "No NII Route for NUI from Terminal
             NMS info: f87b(h), severity: alarm"
        ::= 63611

    hypTrapF87C TRAP-TYPE
        ENTERPRISE  hypAlarmSystem
         -- VARIABLES { hypTrapLogText }
        DESCRIPTION
            "ISDN Call not Dropped by Terminal, Call Terminated
             NMS info: f87c(h), severity: error"
        ::= 63612

    hypTrapF87D TRAP-TYPE
        ENTERPRISE  hypAlarmSystem
         -- VARIABLES { hypTrapLogText }
        DESCRIPTION
            "Unexpected Host Disconnect
             NMS info: f87d(h), severity: error"
        ::= 63613

    hypTrapF87E TRAP-TYPE
        ENTERPRISE  hypAlarmSystem
         -- VARIABLES { hypTrapLogText }
        DESCRIPTION
            "No Carrier from Terminal
             NMS info: f87e(h), severity: alarm"
        ::= 63614

    hypTrapF87F TRAP-TYPE
        ENTERPRISE  hypAlarmSystem
         -- VARIABLES { hypTrapLogText }
        DESCRIPTION
            "Comms Error Threshold Exceeded
             NMS info: f87f(h), severity: error"
        ::= 63615

    hypTrapF880 TRAP-TYPE
        ENTERPRISE  hypAlarmSystem
         -- VARIABLES { hypTrapLogText }
        DESCRIPTION
            "B-Channel Resource Unavailable
             NMS info: f880(h), severity: alarm"
        ::= 63616

    hypTrapF881 TRAP-TYPE
        ENTERPRISE  hypAlarmSystem
         -- VARIABLES { hypTrapLogText }
        DESCRIPTION
            "B-Channel Resource Available
             NMS info: f881(h), severity: information"
        ::= 63617

    END
