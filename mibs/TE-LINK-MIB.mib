-- extracted from draft-ietf-mpls-telink-mib-01.txt
-- at Thu May  1 06:12:55 2003

TE-LINK-MIB DEFINITIONS ::= BEGIN

IMPORTS
   MODULE-IDENTITY, OBJECT-TYPE, NOTIFICATION-TYPE,
   mib-2, Unsigned32
      FROM SNMPv2-SMI

   MODULE-COMPLIANCE, OBJECT-GROUP, NOTIFICATION-GROUP
      FROM SNMPv2-CONF

   TEXTUAL-CONVENTION, TruthValue, RowStatus, StorageType
      FROM SNMPv2-TC

   InterfaceIndexOrZero, ifIndex
      FROM IF-MIB

   InetAddressType, InetAddress
      FROM INET-ADDRESS-MIB;


teLinkMIB MODULE-IDENTITY
   LAST-UPDATED "200304291200Z"  -- 29 April 2003 12:00:00 EST
   ORGANIZATION "Multiprotocol Label Switching (MPLS) Working Group"
   CONTACT-INFO
       "        Martin Dubuc
        Email:  dubuc.consulting@rogers.com

                Sudheer Dharanikota
        Email:  sudheer@avici.com

                Thomas D. Nadeau
        Email:  tnadeau@cisco.com

                Jonathan P. Lang
        Email:  jplang@ieee.org

        Comments about this document should be emailed directly to
        the MPLS working group mailing list at mpls@uu.net."

   DESCRIPTION
       "Copyright (C) 2003 The Internet Society. This version of
        this MIB module is part of RFCXXXX; see the RFC
        itself for full legal notices.

        This MIB module contains managed object definitions for
        MPLS traffic engineering links as defined in
        'Link Bundling in MPLS Traffic Engineering'."

   -- Revision history.
   REVISION
       "200304291200Z"  -- 29 April 2003 12:00:00 EST
   DESCRIPTION
       "Initial version published as RFC xxxx (to be assigned by RFC Editor)"
   ::= { mib-2 1 } -- To be assigned by IANA (experimental 114 can be used
                     -- in the interim)


-- Textual Conventions
Priority ::= TEXTUAL-CONVENTION
   DISPLAY-HINT "d"
   STATUS       current
   DESCRIPTION
       "This type is used to represent a priority. Each connection is
        assigned a priority. This priority is used when accounting for
        bandwidth on TE links or component links, for resource allocation
        and for rerouting purposes. Value 0 is the highest priority.
        Value 7 is the lowest priority."
   SYNTAX       Unsigned32 (0..7)

LinkProtection ::= TEXTUAL-CONVENTION
   STATUS       current
   DESCRIPTION
       "Link protection."
   SYNTAX       INTEGER {
                    primary(1),
                    secondary(2)
                }

SwitchingCapability ::= TEXTUAL-CONVENTION
   STATUS       current
   DESCRIPTION
       "Switching capability as specified in the 'OSPF Extensions in
        Support of Generalized MPLS' document. The values specified in
        this document are not contiguous."
   SYNTAX       INTEGER {
                    packetSwitch1(1),
                    packetSwitch2(2),
                    packetSwitch3(3),
                    packetSwitch4(4),
                    layer2Switch(51),
                    tdm(100),
                    lambdaSwitch(150),
                    fiberSwitch(200)
                }

LinkEncodingType ::= TEXTUAL-CONVENTION
   STATUS       current
   DESCRIPTION
       "Link encoding type as specified in 'GMPLS Signaling Functional
        Description' document. The values specified in this document are
        not contiguous."
   SYNTAX       INTEGER {
                    packet(1),
                    ethernet(2),
                    ansiEtsiPdh(3),
                    sdhItuSonetAnsi(5),
                    digitalWrapper(7),
                    lambda(8),
                    fiber(9),
                    fiberChannel(11)
                }

-- Top level components of this MIB module

-- Notifications
teLinkNotifications OBJECT IDENTIFIER ::= { teLinkMIB 0 }
-- Tables, Scalars
teLinkObjects       OBJECT IDENTIFIER ::= { teLinkMIB 1 }
-- Conformance
teLinkConformance   OBJECT IDENTIFIER ::= { teLinkMIB 2 }

-- TE Link Table

teLinkTable OBJECT-TYPE
   SYNTAX        SEQUENCE OF TeLinkEntry
   MAX-ACCESS    not-accessible
   STATUS        current
   DESCRIPTION
       "This table specifies the grouping of component links into
        TE links and grouping of TE links into bundled links."
   ::= { teLinkObjects 1 }

teLinkEntry OBJECT-TYPE
   SYNTAX        TeLinkEntry
   MAX-ACCESS    not-accessible
   STATUS        current
   DESCRIPTION
       "An entry in this table exists for each ifEntry with an
        ifType of teLink(200), i.e. for every TE link. An ifEntry
        in the ifTable must exist before a teLinkEntry is created with
        the corresponding ifIndex. If a TE link entry in the ifTable is
        destroyed, then so is the corresponding entry in the
        teLinkTable. The administrative and operational status values
        are controlled from the ifEntry."
   INDEX         { ifIndex }
   ::= { teLinkTable 1 }

TeLinkEntry ::= SEQUENCE {
  teLinkAddressType            InetAddressType,
  teLinkLocalIpAddr            InetAddress,
  teLinkRemoteIpAddr           InetAddress,
  teLinkMetric                 Unsigned32,
  teLinkMuxCapability          SwitchingCapability,
  teLinkProtectionType         INTEGER,
  teLinkWorkingPriority        Priority,
  teLinkResourceClass          Unsigned32,
  teLinkIncomingIfId           InterfaceIndexOrZero,
  teLinkOutgoingIfId           InterfaceIndexOrZero,
  teLinkRowStatus              RowStatus,
  teLinkStorageType            StorageType
}

teLinkAddressType OBJECT-TYPE
   SYNTAX        InetAddressType
   MAX-ACCESS    read-create
   STATUS        current
   DESCRIPTION
       "The type of Internet address for the TE link. Only IPv4,
        IPv6 and unknown (for unnumbered links) need to be supported."
   ::= { teLinkEntry 1 }

teLinkLocalIpAddr OBJECT-TYPE
   SYNTAX        InetAddress
   MAX-ACCESS    read-create
   STATUS        current
   DESCRIPTION
       "For IPv4 and IPv6 numbered links, this object represents the
        local IP address associated with the TE link. For unnumbered
        link, the local address is not stored in this object, but
        rather in the teLinkOutgoingIfId object."
   ::= { teLinkEntry 2 }

teLinkRemoteIpAddr OBJECT-TYPE
   SYNTAX        InetAddress
   MAX-ACCESS    read-create
   STATUS        current
   DESCRIPTION
       "The remote IP address associated with the TE link (IPv4 and
        IPv6 numbered links). For unnumbered links, the remote address
        is not stored in this object, but rather in the
        teLinkIncomingIfId object."
   ::= { teLinkEntry 3 }

teLinkMetric OBJECT-TYPE
   SYNTAX        Unsigned32
   MAX-ACCESS    read-create
   STATUS        current
   DESCRIPTION
       "The traffic engineering metric for the TE link is
        derived from its component links. All component links
        within the TE link must have the same traffic
        engineering metric."

   REFERENCE
       "Link Bundling in MPLS Traffic Engineering, RFC xxxx"
       -- RFC Editor to fill in RFC number that will be assigned to
       -- [BUNDLING]
   ::= { teLinkEntry 4 }

teLinkMuxCapability OBJECT-TYPE
   SYNTAX        SwitchingCapability
   MAX-ACCESS    read-create
   STATUS        current
   DESCRIPTION
       "This attribute specifies link multiplex capability of the
        TE link, which is derived from its component links. All
        component links within the same TE link must have the
        same link multiplex capability."
   REFERENCE
       "OSPF Extensions in Support of Generalized MPLS, RFC xxxx"
       -- RFC Editor to fill in RFC number that will be assigned to
       -- [GMPLS-OSPF]
   ::= { teLinkEntry 5 }

teLinkProtectionType OBJECT-TYPE
   SYNTAX        INTEGER {
                     extraTraffic(1),
                     unprotected(2),
                     shared(3),
                     dedicated1For1(4),
                     dedicated1Plus1(5),
                     enhanced(6)
                 }
   MAX-ACCESS    read-create
   STATUS        current
   DESCRIPTION
       "This attribute specifies link protection type of the
        TE link. Description of the different protection types can be
        found in the 'Routing Extensions in Support of Generalized
        MPLS' document."
   REFERENCE
       "OSPF Extensions in Support of Generalized MPLS, RFC xxxx and
        Routing Extensions in Support of Generalized MPLS, RFC xxxx"
       -- RFC Editor to fill in RFC number that will be assigned to
       -- [GMPLS-OSPF] and [ROUTING]
   ::= { teLinkEntry 6 }

teLinkWorkingPriority OBJECT-TYPE
   SYNTAX        Priority
   MAX-ACCESS    read-create
   STATUS        current
   DESCRIPTION
       "This object represents a priority value such that a new
        connection with a higher priority, i.e. numerically lower than
        this value, is guaranteed to be setup on a primary link and
        not on a secondary link."
   REFERENCE
       "OSPF Extensions in Support of Generalized MPLS, RFC xxxx"
       -- RFC Editor to fill in RFC number that will be assigned to
       -- [GMPLS-OSPF]
   ::= { teLinkEntry 7 }

teLinkResourceClass OBJECT-TYPE
   SYNTAX        Unsigned32
   MAX-ACCESS    read-create
   STATUS        current
   DESCRIPTION
       "This attribute specifies the TE link resource class.
        The resource class is a 32 bit bitfield. The resource class for
        a link bundle is derived from the resource class of its
        TE links. All TE links within a link bundle must have the
        same resource class. Encoding of the resource class is described
        in the 'Traffic Engineering Extensions to OSPF Version 2'
        document."
   REFERENCE
       "Link Bundling in MPLS Traffic Engineering, RFC xxxx and
        Traffic Engineering Extensions to OSPF Version 2, RFC xxxx"
       -- RFC Editor to fill in RFC number that will be assigned to
       -- [BUNDLING] and [OSPF]
   ::= { teLinkEntry 8 }

teLinkIncomingIfId OBJECT-TYPE
   SYNTAX        InterfaceIndexOrZero
   MAX-ACCESS    read-create
   STATUS        current
   DESCRIPTION
       "For unnumbered links, the incoming interface is set to the
        outgoing interface identifier chosen by the neighboring LSR
        for the reverse link corresponding to this TE link. For
        numbered links, the address is stored in the teLinkRemoteIpAddr
        instead."
   REFERENCE
       "Link Bundling in MPLS Traffic Engineering, RFC xxxx"
       -- RFC Editor to fill in RFC number that will be assigned to
       -- [BUNDLING]
   ::= { teLinkEntry 9 }

teLinkOutgoingIfId OBJECT-TYPE
   SYNTAX        InterfaceIndexOrZero
   MAX-ACCESS    read-create
   STATUS        current
   DESCRIPTION
       "If the link is unnumbered, the outgoing interface identifier is
        set to the outgoing interface identifier chosen for the TE link
        by the advertising LSR. For numbered links, the address is
        stored in the teLinkLocalIpAddr instead."
   REFERENCE
       "Link Bundling in MPLS Traffic Engineering, RFC xxxx"
       -- RFC Editor to fill in RFC number that will be assigned to
       -- [BUNDLING]
   ::= { teLinkEntry 10 }

teLinkRowStatus OBJECT-TYPE
   SYNTAX        RowStatus
   MAX-ACCESS    read-create
   STATUS        current
   DESCRIPTION
       "This variable is used to create, modify, and/or
        delete a row in this table. All read-create objects
        can only be changed when teLinkRowStatus is notInService(2)
        or notReady(3)."
   ::= { teLinkEntry 11 }

teLinkStorageType OBJECT-TYPE
   SYNTAX        StorageType
   MAX-ACCESS    read-create
   STATUS        current
   DESCRIPTION
       "The storage type for this conceptual row in the
        teLinkTable. Conceptual rows having the value
        'permanent' need not allow write-access to any
        columnar object in the row."
   ::= { teLinkEntry 12 }

-- End of teLinkTable


-- TE Link Descriptor Table

teLinkDescriptorTable OBJECT-TYPE
   SYNTAX        SEQUENCE OF TeLinkDescriptorEntry
   MAX-ACCESS    not-accessible
   STATUS        current
   DESCRIPTION
       "This table specifies the link descriptors associated with the
        TE links."
   ::= { teLinkObjects 2 }

teLinkDescriptorEntry OBJECT-TYPE
   SYNTAX        TeLinkDescriptorEntry
   MAX-ACCESS    not-accessible
   STATUS        current
   DESCRIPTION
       "An entry in this table is created for every TE link descriptor.
        An ifEntry in the ifTable must exist before a
        teLinkDescriptorEntry using the same ifIndex is created.
        ifType of ifEntry must be teLink(200).
        If a TE link entry in the ifTable is destroyed, then so are all
        entries in the teLinkDescriptorTable that use the ifIndex of
        this TE link."
   INDEX         { ifIndex, teLinkDescriptorId }
   ::= { teLinkDescriptorTable 1 }

TeLinkDescriptorEntry ::= SEQUENCE {
  teLinkDescriptorId           Unsigned32,
  teLinkDescrEncodingType      LinkEncodingType,
  teLinkDescrPriority          Priority,
  teLinkDescrMinResBandwidth   Unsigned32,
  teLinkDescrMaxResBandwidth   Unsigned32,
  teLinkDescrRowStatus         RowStatus,
  teLinkDescrStorageType       StorageType
}

teLinkDescriptorId OBJECT-TYPE
   SYNTAX        Unsigned32 (1..4294967295)
   MAX-ACCESS    not-accessible
   STATUS        current
   DESCRIPTION
       "This object specifies the link descriptor identifier."
   ::= { teLinkDescriptorEntry 1 }

teLinkDescrEncodingType OBJECT-TYPE
   SYNTAX        LinkEncodingType
   MAX-ACCESS    read-create
   STATUS        current
   DESCRIPTION
       "This attribute specifies the TE link encoding type."
   REFERENCE
       "Generalized MPLS Signaling Functional Description, RFC 3471"
   ::= { teLinkDescriptorEntry 2 }

teLinkDescrPriority OBJECT-TYPE
   SYNTAX        Priority
   MAX-ACCESS    read-create
   STATUS        current
   DESCRIPTION
       "This object specifies the lowest priority at which that link
        encoding type is available."
   REFERENCE
       "OSPF Extensions in Support of Generalized MPLS, RFC xxxx"
       -- RFC Editor to fill in RFC number that will be assigned to
       -- [GMPLS-OSPF]
   ::= { teLinkDescriptorEntry 3 }

teLinkDescrMinResBandwidth OBJECT-TYPE
   SYNTAX        Unsigned32
   UNITS         "thousand bps"
   MAX-ACCESS    read-create
   STATUS        current
   DESCRIPTION
       "This attribute specifies the minimum reservable bandwidth on
        the TE link. This is derived from the union of the
        minimum reservable bandwidth of all the component links
        associated with the TE link that can be used to carry
        live traffic. This value is an estimate in units of 1,000 bits
        per second."
   REFERENCE
       "OSPF Extensions in Support of Generalized MPLS, RFC xxxx"
       -- RFC Editor to fill in RFC number that will be assigned to
       -- [GMPLS-OSPF]
   ::= { teLinkDescriptorEntry 4 }

teLinkDescrMaxResBandwidth OBJECT-TYPE
   SYNTAX        Unsigned32
   UNITS         "thousand bps"
   MAX-ACCESS    read-create
   STATUS        current
   DESCRIPTION
       "This attribute specifies the maximum reservable bandwidth on
        the TE link. This is the union of the maximum reservable
        bandwidth of all the component links within the
        TE link that can be used to carry live traffic. This value
        is an estimate in units of 1,000 bits per second."
   REFERENCE
       "OSPF Extensions in Support of Generalized MPLS, RFC xxxx"
       -- RFC Editor to fill in RFC number that will be assigned to
       -- [GMPLS-OSPF]
   ::= { teLinkDescriptorEntry 5 }

teLinkDescrRowStatus OBJECT-TYPE
   SYNTAX        RowStatus
   MAX-ACCESS    read-create
   STATUS        current
   DESCRIPTION
       "This variable is used to create, modify, and/or
        delete a row in this table. No read-create object
        can changed if teLinkDescrRowStatus is in active(1) state."
   ::= { teLinkDescriptorEntry 6 }

teLinkDescrStorageType OBJECT-TYPE
   SYNTAX        StorageType
   MAX-ACCESS    read-create
   STATUS        current
   DESCRIPTION
       "The storage type for this conceptual row in the
        teLinkDescriptorTable. Conceptual rows having the value
        'permanent' need not allow write-access to any
        columnar object in the row."
   ::= { teLinkDescriptorEntry 7 }

-- End of teLinkDescriptorTable


-- TE Link Shared Risk Link Group Table

teLinkSrlgTable OBJECT-TYPE
   SYNTAX        SEQUENCE OF TeLinkSrlgEntry
   MAX-ACCESS    not-accessible
   STATUS        current
   DESCRIPTION
       "This table specifies the SRLGs associated with TE links."
   ::= { teLinkObjects 3 }

teLinkSrlgEntry OBJECT-TYPE
   SYNTAX        TeLinkSrlgEntry
   MAX-ACCESS    not-accessible
   STATUS        current
   DESCRIPTION
       "An entry in this table contains information about a
        SRLG associated with a TE link.
        An ifEntry in the ifTable must exist before a
        teLinkSrlgEntry using the same ifIndex is created.
        ifType of ifEntry must be teLink(200).
        If a TE link entry in the ifTable is destroyed, then so are all
        entries in the teLinkSrlgTable that use the ifIndex of
        this TE link."
   INDEX         { ifIndex, srlg }
   ::= { teLinkSrlgTable 1 }

TeLinkSrlgEntry ::= SEQUENCE {
  srlg            Unsigned32,
  srlgRowStatus   RowStatus,
  srlgStorageType StorageType
}

srlg OBJECT-TYPE
   SYNTAX        Unsigned32 (0..4294967295)
   MAX-ACCESS    not-accessible
   STATUS        current
   DESCRIPTION
       "This identifies a SRLG supported by the TE link. An SRLG is
        identified with a 32 bit number that is unique within an IGP
        domain. Zero is a valid SRLG number."
   REFERENCE
       "OSPF Extensions in Support of Generalized MPLS, RFC xxxx"
       -- RFC Editor to fill in RFC number that will be assigned to
       -- [GMPLS-OSPF]
   ::= { teLinkSrlgEntry 1 }

srlgRowStatus OBJECT-TYPE
   SYNTAX        RowStatus
   MAX-ACCESS    read-create
   STATUS        current
   DESCRIPTION
       "This variable is used to create, modify, and/or
        delete a row in this table. No read-create object can
        be modified if srlgRowStatus is active(1)."
   ::= { teLinkSrlgEntry 2 }

srlgStorageType OBJECT-TYPE
   SYNTAX        StorageType
   MAX-ACCESS    read-create
   STATUS        current
   DESCRIPTION
       "The storage type for this conceptual row in the
        teLinkSrlgTable. Conceptual rows having the value
        'permanent' need not allow write-access to any
        columnar object in the row."
   ::= { teLinkSrlgEntry 3 }

-- End of teLinkSrlgTable


-- TE Link Bandwidth Table

teLinkBandwidthTable OBJECT-TYPE
   SYNTAX        SEQUENCE OF TeLinkBandwidthEntry
   MAX-ACCESS    not-accessible
   STATUS        current
   DESCRIPTION
       "This table specifies the priority-based bandwidth table
        for TE links."
   ::= { teLinkObjects 4 }

teLinkBandwidthEntry OBJECT-TYPE
   SYNTAX        TeLinkBandwidthEntry
   MAX-ACCESS    not-accessible
   STATUS        current
   DESCRIPTION
       "An entry in this table contains information about
        the priority-based bandwidth of TE links. An ifEntry in the
        ifTable must exist before a teLinkBandwidthEntry using the
        same ifIndex is created. ifType of ifEntry must be teLink(200).
        If a TE link entry in the ifTable is destroyed, then so are
        all entries in the teLinkBandwidthTable that use the ifIndex of
        this TE link."
   INDEX         { ifIndex, teLinkPriority }
   ::= { teLinkBandwidthTable 1 }

TeLinkBandwidthEntry ::= SEQUENCE {
  teLinkPriority             Priority,
  teLinkUnreservedBandwidth  Unsigned32,
  teLinkMaximumLspBandwidth  Unsigned32,
  teLinkBandwidthRowStatus   RowStatus,
  teLinkBandwidthStorageType StorageType
}

teLinkPriority OBJECT-TYPE
   SYNTAX        Priority
   MAX-ACCESS    not-accessible
   STATUS        current
   DESCRIPTION
       "This attribute specifies the priority. A value of 0 is valid
        as specified in the 'Traffic Engineering Extensions to OSPF
        Version 2' document."
   REFERENCE
       "OSPF Extensions in Support of Generalized MPLS, RFC xxxx and
        Traffic Engineering Extensions to OSPF Version 2, RFC xxxx"
       -- RFC Editor to fill in RFC number that will be assigned to
       -- [GMPLS-OSPF] and [OSPF]
   ::= { teLinkBandwidthEntry 1 }

teLinkUnreservedBandwidth OBJECT-TYPE
   SYNTAX        Unsigned32
   UNITS         "thousand bps"
   MAX-ACCESS    read-only
   STATUS        current
   DESCRIPTION
       "This attribute specifies the TE link unreserved
        bandwidth at priority p. It is the sum of the unreserved
        bandwidths at priority p of all component links associated
        with the TE link (excludes all links that are strictly
        used as protecting links). This value is an estimate in units
        of 1,000 bits per second."
   REFERENCE
       "Link Bundling in MPLS Traffic Engineering, RFC xxxx"
       -- RFC Editor to fill in RFC number that will be assigned to
       -- [BUNDLING]
   ::= { teLinkBandwidthEntry 2 }

teLinkMaximumLspBandwidth OBJECT-TYPE
   SYNTAX        Unsigned32
   UNITS         "thousand bps"
   MAX-ACCESS    read-create
   STATUS        current
   DESCRIPTION
       "This attribute specifies the TE link maximum
        LSP bandwidth at priority p. It is the maximum of all
        maximum LSP bandwidth at priority p of the component links
        associated with the TE link (excludes all links that are
        strictly used as protecting links). This value is an estimate
        in units of 1,000 bits per second."
   REFERENCE
       "Link Bundling in MPLS Traffic Engineering, RFC xxxx"
       -- RFC Editor to fill in RFC number that will be assigned to
       -- [BUNDLING]
   ::= { teLinkBandwidthEntry 3 }

teLinkBandwidthRowStatus OBJECT-TYPE
   SYNTAX        RowStatus
   MAX-ACCESS    read-create
   STATUS        current
   DESCRIPTION
       "This variable is used to create, modify, and/or
        delete a row in this table. No read-create object
        can be modified when teLinkBandwidthRowStatus is active(1)."
   ::= { teLinkBandwidthEntry 4 }

teLinkBandwidthStorageType OBJECT-TYPE
   SYNTAX        StorageType
   MAX-ACCESS    read-create
   STATUS        current
   DESCRIPTION
       "The storage type for this conceptual row in the
        teLinkBandwidthTable. Conceptual rows having the value
        'permanent' need not allow write-access to any
        columnar object in the row."
   ::= { teLinkBandwidthEntry 5 }

-- End of teLinkBandwidthTable


-- Component Link Table

componentLinkTable  OBJECT-TYPE
   SYNTAX        SEQUENCE OF ComponentLinkEntry
   MAX-ACCESS    not-accessible
   STATUS        current
   DESCRIPTION
       "This table specifies the component link parameters."
   ::= { teLinkObjects 5 }

componentLinkEntry  OBJECT-TYPE
   SYNTAX        ComponentLinkEntry
   MAX-ACCESS    not-accessible
   STATUS        current
   DESCRIPTION
       "An entry in this table exists for each ifEntry that represents
        a component link. An ifEntry must exist in the ifTable
        before a componentLinkEntry is created with the
        corresponding ifIndex. ifEntry's ifType can be
        of any interface type which has been defined for TE Link
        interworking. Examples include ATM, Frame Relay, Ethernet, etc.
        If an entry representing a component link is destroyed in the
        ifTable, then so is the corresponding entry in the
        componentLinkTable. The administrative and operational status
        values are controlled from the ifEntry."
   INDEX         { ifIndex }
   ::= { componentLinkTable 1 }

ComponentLinkEntry ::= SEQUENCE {
  componentLinkMuxCapability       SwitchingCapability,
  componentLinkPreferredProtection LinkProtection,
  componentLinkCurrentProtection   LinkProtection,
  componentLinkRowStatus           RowStatus,
  componentLinkStorageType         StorageType
}

componentLinkMuxCapability OBJECT-TYPE
   SYNTAX        SwitchingCapability
   MAX-ACCESS    read-create
   STATUS        current
   DESCRIPTION
       "This attribute specifies link multiplexing capabilities of the
        component link."
   REFERENCE
       "OSPF Extensions in Support of Generalized MPLS, RFC xxxx"
       -- RFC Editor to fill in RFC number that will be assigned to
       -- [GMPLS-OSPF]
   ::= { componentLinkEntry 1 }

componentLinkPreferredProtection OBJECT-TYPE
   SYNTAX        LinkProtection
   MAX-ACCESS    read-create
   STATUS        current
   DESCRIPTION
       "This attribute specifies whether this component link is
        a primary or secondary entity."
   ::= { componentLinkEntry 2 }

componentLinkCurrentProtection OBJECT-TYPE
   SYNTAX        LinkProtection
   MAX-ACCESS    read-only
   STATUS        current
   DESCRIPTION
       "This attribute specifies whether this component link is
        currently used as primary or secondary link."
   ::= { componentLinkEntry 3 }

componentLinkRowStatus OBJECT-TYPE
   SYNTAX        RowStatus
   MAX-ACCESS    read-create
   STATUS        current
   DESCRIPTION
       "This variable is used to create, modify, and/or
        delete a row in this table. No read-create object
        can be modified when componentLinkRowStatus is active(1)."
   ::= { componentLinkEntry 4 }

componentLinkStorageType OBJECT-TYPE
   SYNTAX        StorageType
   MAX-ACCESS    read-create
   STATUS        current
   DESCRIPTION
       "The storage type for this conceptual row in the
        componentLinkTable. Conceptual rows having the value
        'permanent' need not allow write-access to any
        columnar object in the row."
   ::= { componentLinkEntry 5 }

-- End of componentLinkTable
-- Component Link Descriptor Table

componentLinkDescriptorTable OBJECT-TYPE
   SYNTAX        SEQUENCE OF ComponentLinkDescriptorEntry
   MAX-ACCESS    not-accessible
   STATUS        current
   DESCRIPTION
       "This table specifies the link descriptors associated with the
        component links."
   ::= { teLinkObjects 6 }

componentLinkDescriptorEntry OBJECT-TYPE
   SYNTAX        ComponentLinkDescriptorEntry
   MAX-ACCESS    not-accessible
   STATUS        current
   DESCRIPTION
       "An entry in this table is created for every component link
        descriptor. An ifEntry in the ifTable must exist before a
        componentLinkDescriptorEntry using the same ifIndex is created.
        ifEntry's ifType can be of any interface type which has been
        defined for TE Link interworking. Examples include ATM, Frame
        Relay, Ethernet, etc. If a component link entry in the ifTable
        is destroyed, then so are all entries in the
        componentLinkDescriptorTable that use the ifIndex of this
        component link."
   INDEX         { ifIndex, componentLinkDescrId }
   ::= { componentLinkDescriptorTable 1 }

ComponentLinkDescriptorEntry ::= SEQUENCE {
  componentLinkDescrId            Unsigned32,
  componentLinkDescrEncodingType  LinkEncodingType,
  componentLinkDescrPriority      Priority,
  componentLinkDescrMinBandwidth  Unsigned32,
  componentLinkDescrMaxBandwidth  Unsigned32,
  componentLinkDescrRowStatus     RowStatus,
  componentLinkDescrStorageType   StorageType
}

componentLinkDescrId OBJECT-TYPE
   SYNTAX        Unsigned32 (1..4294967295)
   MAX-ACCESS    not-accessible
   STATUS        current
   DESCRIPTION
       "This object specifies the link descriptor identifier."
   ::= { componentLinkDescriptorEntry 1 }

componentLinkDescrEncodingType OBJECT-TYPE
   SYNTAX        LinkEncodingType
   MAX-ACCESS    read-create
   STATUS        current
   DESCRIPTION
       "This attribute specifies the component link encoding type."
   REFERENCE
       "Generalized MPLS Signaling Functional Description, RFC 3471"
   ::= { componentLinkDescriptorEntry 2 }

componentLinkDescrPriority OBJECT-TYPE
   SYNTAX        Priority
   MAX-ACCESS    read-create
   STATUS        current
   DESCRIPTION
       "This object specifies the lowest priority at which that link
        encoding type is available for the component link."
   REFERENCE
       "OSPF Extensions in Support of Generalized MPLS, RFC xxxx"
       -- RFC Editor to fill in RFC number that will be assigned to
       -- [GMPLS-OSPF]
   ::= { componentLinkDescriptorEntry 3 }

componentLinkDescrMinBandwidth OBJECT-TYPE
   SYNTAX        Unsigned32
   UNITS         "thousand bps"
   MAX-ACCESS    read-create
   STATUS        current
   DESCRIPTION
       "This attribute specifies the minimum reservable bandwidth on
        the component link. This value is an estimate
        in units of 1,000 bits per second."
   REFERENCE
       "OSPF Extensions in Support of Generalized MPLS, RFC xxxx"
       -- RFC Editor to fill in RFC number that will be assigned to
       -- [GMPLS-OSPF]
   ::= { componentLinkDescriptorEntry 4 }

componentLinkDescrMaxBandwidth OBJECT-TYPE
   SYNTAX        Unsigned32
   UNITS         "thousand bps"
   MAX-ACCESS    read-create
   STATUS        current
   DESCRIPTION
       "This attribute specifies the maximum reservable bandwidth on
        the component link. This value is an estimate
        in units of 1,000 bits per second."
   REFERENCE
       "OSPF Extensions in Support of Generalized MPLS, RFC xxxx"
       -- RFC Editor to fill in RFC number that will be assigned to
       -- [GMPLS-OSPF]
   ::= { componentLinkDescriptorEntry 5 }

componentLinkDescrRowStatus OBJECT-TYPE
   SYNTAX        RowStatus
   MAX-ACCESS    read-create
   STATUS        current
   DESCRIPTION
       "This variable is used to create, modify, and/or
        delete a row in this table. No read-create object
        can be modified when componentLinkDescrRowStatus
        is active(1)."
   ::= { componentLinkDescriptorEntry 6 }

componentLinkDescrStorageType OBJECT-TYPE
   SYNTAX        StorageType
   MAX-ACCESS    read-create
   STATUS        current
   DESCRIPTION
       "The storage type for this conceptual row in the
        componentLinkDescriptorTable. Conceptual rows
        having the value 'permanent' need not allow write-access
        to any columnar object in the row."
   ::= { componentLinkDescriptorEntry 7 }

-- End of componentLinkDescriptorTable


-- Component Link Bandwidth Table

componentLinkBandwidthTable OBJECT-TYPE
   SYNTAX        SEQUENCE OF ComponentLinkBandwidthEntry
   MAX-ACCESS    not-accessible
   STATUS        current
   DESCRIPTION
       "This table specifies the priority-based bandwidth
        for component links."
   ::= { teLinkObjects 7 }

componentLinkBandwidthEntry OBJECT-TYPE
   SYNTAX        ComponentLinkBandwidthEntry
   MAX-ACCESS    not-accessible
   STATUS        current
   DESCRIPTION
       "An entry in this table contains information about
        the priority-based bandwidth on component links.
        An ifEntry in the ifTable must exist before a
        componentLinkBandwidthEntry using the same ifIndex is
        created. ifEntry's ifType can be of any interface type which
        has been defined for TE Link interworking. Examples include
        ATM, Frame Relay, Ethernet, etc. If a component link entry in
        the ifTable is destroyed, then so are all entries in the
        componentLinkBandwidthTable that use the ifIndex of
        this component link."
   INDEX         { ifIndex, componentLinkPriority }
   ::= { componentLinkBandwidthTable 1 }

ComponentLinkBandwidthEntry ::= SEQUENCE {
  componentLinkPriority            Priority,
  componentLinkUnreservedBandwidth Unsigned32,
  componentLinkMaximumLspBandwidth Unsigned32,
  componentLinkBandwidthRowStatus  RowStatus,
  componentLinkBwStorageType       StorageType
}

componentLinkPriority OBJECT-TYPE
   SYNTAX        Priority
   MAX-ACCESS    not-accessible
   STATUS        current
   DESCRIPTION
       "This attribute specifies the priority. A value of 0 is valid
        as specified in the 'Traffic Engineering Extensions to OSPF
        Version 2' document."
   REFERENCE
       "OSPF Extensions in Support of Generalized MPLS, RFC xxxx and
        Traffic Engineering Extensions to OSPF Version 2, RFC xxxx"
       -- RFC Editor to fill in RFC number that will be assigned to
       -- [GMPLS-OSPF] and [OSPF]
   ::= { componentLinkBandwidthEntry 1 }

componentLinkUnreservedBandwidth OBJECT-TYPE
   SYNTAX        Unsigned32
   UNITS         "thousand bps"
   MAX-ACCESS    read-only
   STATUS        current
   DESCRIPTION
       "This attribute specifies the component link unreserved
        bandwidth at priority p. This value is an estimate
        in units of 1,000 bits per second."
   REFERENCE
       "OSPF Extensions in Support of Generalized MPLS, RFC xxxx"
       -- RFC Editor to fill in RFC number that will be assigned to
       -- [GMPLS-OSPF]
   ::= { componentLinkBandwidthEntry 2 }

componentLinkMaximumLspBandwidth OBJECT-TYPE
   SYNTAX        Unsigned32
   UNITS         "thousand bps"
   MAX-ACCESS    read-create
   STATUS        current
   DESCRIPTION
       "This attribute specifies the component link maximum
        LSP bandwidth at priority p. This value is an estimate
        in units of 1,000 bits per second."
   REFERENCE
       "OSPF Extensions in Support of Generalized MPLS, RFC xxxx"
       -- RFC Editor to fill in RFC number that will be assigned to
       -- [GMPLS-OSPF]
   ::= { componentLinkBandwidthEntry 3 }

componentLinkBandwidthRowStatus OBJECT-TYPE
   SYNTAX        RowStatus
   MAX-ACCESS    read-create
   STATUS        current
   DESCRIPTION
       "This variable is used to create, modify, and/or
        delete a row in this table. No read-create object can
        be modified when componentLinkBandwidthRowStatus is
        active(1)."
   ::= { componentLinkBandwidthEntry 4 }

componentLinkBwStorageType OBJECT-TYPE
   SYNTAX        StorageType
   MAX-ACCESS    read-create
   STATUS        current
   DESCRIPTION
       "The storage type for this conceptual row in the
        componentLinkBandwidthTable. Conceptual rows
        having the value 'permanent' need not allow write-access
        to any columnar object in the row."
   ::= { componentLinkBandwidthEntry 5 }

-- End of componentLinkBandwidthTable


-- Notification Configuration

teLinkNotificationsEnabled OBJECT-TYPE
   SYNTAX        TruthValue
   MAX-ACCESS    read-write
   STATUS        current
   DESCRIPTION
       "If this object is true, then it enables the
        generation of the TE link notifications,
        otherwise these notifications are not emitted."
   DEFVAL        { false }
   ::= { teLinkObjects 8 }


-- Notifications


-- TE Link Notifications

linkBundleMismatch NOTIFICATION-TYPE
   OBJECTS       { teLinkAddressType,
                   teLinkLocalIpAddr, teLinkRemoteIpAddr,
                   teLinkIncomingIfId, teLinkOutgoingIfId }
   STATUS        current
   DESCRIPTION
       "This notification is generated when a mismatch is found on a
        bundled link. Such mismatch can be detected for instance if one
        of the traffic engineering parameters is not consistent across
        all TE links within a bundled link (resource class, etc.)."
   ::= { teLinkNotifications 1 }

-- End of notifications


-- Module compliance

teLinkGroups
   OBJECT IDENTIFIER ::= { teLinkConformance 1 }

teLinkCompliances
   OBJECT IDENTIFIER ::= { teLinkConformance 2 }

teLinkModuleFullCompliance MODULE-COMPLIANCE
   STATUS current
   DESCRIPTION
       "Compliance statement for agents that support the
        configuration and monitoring of TE Link MIB module."
   MODULE -- this module

      -- The mandatory groups have to be implemented
      -- by all devices supporting TE links. However, they may all
      -- be supported as read-only objects in the case where automatic
      -- configuration is supported.

      MANDATORY-GROUPS    { teLinkGroup,
                            teLinkBandwidthGroup,
                            componentLinkBandwidthGroup }

      GROUP teLinkSrlgGroup
      DESCRIPTION
          "This group is mandatory for G-MPLS enabled devices."

      GROUP teLinkNotificationGroup
      DESCRIPTION
          "This group is mandatory for equipment that support
           TE link notifications."

      -- teLinkTable

      OBJECT      teLinkAddressType
      SYNTAX      INTEGER { unknown(0), ipv4(1), ipv6(2) }
      DESCRIPTION
          "Only ipv4(1) and ipv6(2) address types need to be
           supported for numbered links. For unnumbered links, the
           unknown(0) address type needs to be supported."

      OBJECT      teLinkLocalIpAddr
      SYNTAX      InetAddress (SIZE(0|4|16))
      DESCRIPTION
          "Size of TE link IP address depends on type of TE link.
           TE link IP address size is zero if link is unnumbered,
           four if link IP address is IPv4 and sixteen if link IP
           address is IPv6."

      OBJECT      teLinkRemoteIpAddr
      SYNTAX      InetAddress (SIZE(0|4|16))
      DESCRIPTION
          "Size of TE link IP address depends on type of TE link.
           TE link IP address size is zero if link is unnumbered,
           four if link IP address is IPv4 and sixteen if link IP
           address is IPv6."

      OBJECT      teLinkRowStatus
      SYNTAX      INTEGER { active(1), notInService(2),
                            createAndGo(4), destroy(6) }
      DESCRIPTION
          "The notReady(3) and createAndWait(5) states need
           not be supported."

      -- teLinkDescriptorTable

      OBJECT      teLinkDescrRowStatus
      SYNTAX      INTEGER { active(1), notInService(2),
                            createAndGo(4), destroy(6) }
      DESCRIPTION
          "The notReady(3) and createAndWait(5) states need
           not be supported."

      OBJECT      teLinkDescrStorageType
      MIN-ACCESS  read-only
      DESCRIPTION
          "Write access is not required."

      -- teLinkSrlgTable

      OBJECT      srlgRowStatus
      SYNTAX      INTEGER { active(1), notInService(2),
                            createAndGo(4), destroy(6) }
      DESCRIPTION
          "The notReady(3) and createAndWait(5) states need
           not be supported."

      -- teLinkBandwidthTable

      OBJECT      teLinkBandwidthRowStatus
      SYNTAX      INTEGER { active(1), notInService(2),
                            createAndGo(4), destroy(6) }
      DESCRIPTION
          "The notReady(3) and createAndWait(5) states need
           not be supported."

      -- componentLinkTable

      OBJECT      componentLinkRowStatus
      SYNTAX      INTEGER { active(1), notInService(2),
                            createAndGo(4), destroy(6) }
      DESCRIPTION
          "The notReady(3) and createAndWait(5) states need
           not be supported."

      -- componentLinkDescriptorTable

      OBJECT      componentLinkDescrRowStatus
      SYNTAX      INTEGER { active(1), notInService(2),
                            createAndGo(4), destroy(6) }
      DESCRIPTION
          "The notReady(3) and createAndWait(5) states need
           not be supported."

      -- componentLinkBandwidthTable

      OBJECT      componentLinkBandwidthRowStatus
      SYNTAX      INTEGER { active(1), notInService(2),
                            createAndGo(4), destroy(6) }

      DESCRIPTION
          "The notReady(3) and createAndWait(5) states need
           not be supported."

   ::= { teLinkCompliances 1 }

teLinkModuleReadOnlyCompliance MODULE-COMPLIANCE
   STATUS current
   DESCRIPTION
       "Compliance statement for agents that support the
        monitoring of TE link MIB module."
   MODULE -- this module

      -- The mandatory groups have to be implemented
      -- by all devices supporting TE links. However, they may all
      -- be supported as read-only objects in the case where manual
      -- configuration is unsupported.

      MANDATORY-GROUPS    { teLinkGroup,
                            teLinkBandwidthGroup,
                            componentLinkBandwidthGroup }

      GROUP teLinkSrlgGroup
      DESCRIPTION
          "This group is mandatory for G-MPLS enabled devices."

      GROUP teLinkNotificationGroup
      DESCRIPTION
          "This group is optional."

      -- teLinkTable

      OBJECT      teLinkAddressType
      SYNTAX      INTEGER { unknown(0), ipv4(1), ipv6(2) }
      MIN-ACCESS  read-only
      DESCRIPTION
          "Only ipv4(1) and ipv6(2) address types need to be
           supported for numbered links. For unnumbered links, the
           unknown(0) address type needs to be supported."

      OBJECT      teLinkLocalIpAddr
      SYNTAX      InetAddress (SIZE(0|4|16))
      MIN-ACCESS  read-only
      DESCRIPTION
          "Size of TE link IP address depends on type of TE link.
           TE link IP address size is zero if link is unnumbered,
           four if link IP address is IPv4 and sixteen if link IP
           address is IPv6."

      OBJECT      teLinkRemoteIpAddr
      SYNTAX      InetAddress (SIZE(0|4|16))
      MIN-ACCESS  read-only
      DESCRIPTION
          "Size of TE link IP address depends on type of TE link.
           TE link IP address size is zero if link is unnumbered,
           four if link IP address is IPv4 and sixteen if link IP
           address is IPv6."

      OBJECT      teLinkMuxCapability
      MIN-ACCESS  read-only
      DESCRIPTION
          "Write access is not required."

      OBJECT      teLinkProtectionType
      MIN-ACCESS  read-only
      DESCRIPTION
          "Write access is not required."

      OBJECT      teLinkWorkingPriority
      MIN-ACCESS  read-only
      DESCRIPTION
          "Write access is not required."

      OBJECT      teLinkRowStatus
      SYNTAX      INTEGER { active(1) }
      MIN-ACCESS  read-only
      DESCRIPTION
          "Write access is not required and active(1) is the
           only status that needs to be supported."

      OBJECT      teLinkStorageType
      MIN-ACCESS  read-only
      DESCRIPTION
          "Write access is not required."

      -- teLinkDescriptorTable

      OBJECT      teLinkDescrEncodingType
      MIN-ACCESS  read-only
      DESCRIPTION
          "Write access is not required."

      OBJECT      teLinkDescrPriority
      MIN-ACCESS  read-only
      DESCRIPTION
          "Write access is not required."

      OBJECT      teLinkDescrMinResBandwidth
      MIN-ACCESS  read-only
      DESCRIPTION
          "Write access is not required."

      OBJECT      teLinkDescrMaxResBandwidth
      MIN-ACCESS  read-only
      DESCRIPTION
          "Write access is not required."

      OBJECT      teLinkDescrRowStatus
      SYNTAX      INTEGER { active(1) }
      MIN-ACCESS  read-only
      DESCRIPTION
          "Write access is not required and active(1) is the
           only status that needs to be supported."

      OBJECT      teLinkDescrStorageType
      MIN-ACCESS  read-only
      DESCRIPTION
          "Write access is not required."

      -- teLinkSrlgTable

      OBJECT      srlgRowStatus
      SYNTAX      INTEGER { active(1) }
      MIN-ACCESS  read-only
      DESCRIPTION
          "Write access is not required and active(1) is the
           only status that needs to be supported."

      OBJECT      srlgStorageType
      MIN-ACCESS  read-only
      DESCRIPTION
          "Write access is not required."

      -- teLinkBandwidthTable

      OBJECT      teLinkMaximumLspBandwidth
      MIN-ACCESS  read-only
      DESCRIPTION
          "Write access is not required."

      OBJECT      teLinkBandwidthRowStatus
      SYNTAX      INTEGER { active(1) }
      MIN-ACCESS  read-only
      DESCRIPTION
          "Write access is not required and active(1) is the
           only status that needs to be supported."

      OBJECT      teLinkBandwidthStorageType
      MIN-ACCESS  read-only
      DESCRIPTION
          "Write access is not required."

      -- componentLinkTable

      OBJECT      componentLinkMuxCapability
      MIN-ACCESS  read-only
      DESCRIPTION
          "Write access is not required."

      OBJECT      componentLinkPreferredProtection
      MIN-ACCESS  read-only
      DESCRIPTION
          "Write access is not required."

      OBJECT      componentLinkRowStatus
      SYNTAX      INTEGER { active(1) }
      MIN-ACCESS  read-only
      DESCRIPTION
          "Write access is not required and active(1) is the
           only status that needs to be supported."

      OBJECT      componentLinkStorageType
      MIN-ACCESS  read-only
      DESCRIPTION
          "Write access is not required."

      -- componentLinkDescriptorTable

      OBJECT      componentLinkDescrEncodingType
      MIN-ACCESS  read-only
      DESCRIPTION
          "Write access is not required."

      OBJECT      componentLinkDescrPriority
      MIN-ACCESS  read-only
      DESCRIPTION
          "Write access is not required."

      OBJECT      componentLinkDescrMinBandwidth
      MIN-ACCESS  read-only
      DESCRIPTION
          "Write access is not required."

      OBJECT      componentLinkDescrMaxBandwidth
      MIN-ACCESS  read-only
      DESCRIPTION
          "Write access is not required."

      OBJECT      componentLinkDescrRowStatus
      SYNTAX      INTEGER { active(1) }
      MIN-ACCESS  read-only
      DESCRIPTION
          "Write access is not required and active(1) is the
           only status that needs to be supported."

      OBJECT      componentLinkDescrStorageType
      MIN-ACCESS  read-only
      DESCRIPTION
          "Write access is not required."

      -- componentLinkBandwidthTable

      OBJECT      componentLinkMaximumLspBandwidth
      MIN-ACCESS  read-only
      DESCRIPTION
          "Write access is not required."

      OBJECT      componentLinkBandwidthRowStatus
      SYNTAX      INTEGER { active(1) }
      MIN-ACCESS  read-only
      DESCRIPTION
          "Write access is not required and active(1) is the
           only status that needs to be supported."

      OBJECT      componentLinkBwStorageType
      MIN-ACCESS  read-only
      DESCRIPTION
          "Write access is not required."

   ::= { teLinkCompliances 2 }

-- Units of conformance

teLinkGroup OBJECT-GROUP
   OBJECTS { teLinkAddressType,
             teLinkLocalIpAddr,
             teLinkRemoteIpAddr,
             teLinkMetric,
             teLinkMuxCapability,
             teLinkProtectionType,
             teLinkWorkingPriority,
             teLinkResourceClass,
             teLinkIncomingIfId,
             teLinkOutgoingIfId,
             teLinkRowStatus,
             teLinkStorageType,
             teLinkDescrEncodingType,
             teLinkDescrPriority,
             teLinkDescrMinResBandwidth,
             teLinkDescrMaxResBandwidth,
             teLinkDescrRowStatus,
             teLinkDescrStorageType,
             componentLinkMuxCapability,
             componentLinkPreferredProtection,
             componentLinkCurrentProtection,
             componentLinkRowStatus,
             componentLinkStorageType,
             teLinkNotificationsEnabled
           }

   STATUS  current
   DESCRIPTION
          "Collection of objects needed for the monitoring of
           resources associated with TE links."
   ::= { teLinkGroups 1 }

teLinkSrlgGroup OBJECT-GROUP
   OBJECTS { srlgRowStatus,
             srlgStorageType
           }

   STATUS  current
   DESCRIPTION
          "Collection of objects needed for the monitoring of
           SRLG resources associated with TE links."
   ::= { teLinkGroups 2 }

teLinkBandwidthGroup OBJECT-GROUP
   OBJECTS { teLinkUnreservedBandwidth,
             teLinkMaximumLspBandwidth,
             teLinkBandwidthRowStatus,
             teLinkBandwidthStorageType
           }

   STATUS  current
   DESCRIPTION
          "Collection of objects needed for the monitoring of
           the priority-based bandwidth resources associated with
           TE links and component links."
   ::= { teLinkGroups 3 }

componentLinkBandwidthGroup OBJECT-GROUP
   OBJECTS { componentLinkDescrEncodingType,
             componentLinkDescrPriority,
             componentLinkDescrMinBandwidth,
             componentLinkDescrMaxBandwidth,
             componentLinkDescrRowStatus,
             componentLinkDescrStorageType,
             componentLinkUnreservedBandwidth,
             componentLinkMaximumLspBandwidth,
             componentLinkBandwidthRowStatus,
             componentLinkBwStorageType
           }

   STATUS  current
   DESCRIPTION
          "Collection of objects needed for the monitoring of
           bandwidth parameters associated with component links."
   ::= { teLinkGroups 4 }

teLinkNotificationGroup NOTIFICATION-GROUP
   NOTIFICATIONS { linkBundleMismatch }
   STATUS  current
   DESCRIPTION
          "Set of notifications implemented in this module.
           None is mandatory."
   ::= { teLinkGroups 5 }

-- End of TE-LINK-MIB
END

-- 
-- 
--    Copyright (C) The Internet Society (2003). All Rights Reserved.
-- 
--    This document and translations of it may be copied and furnished to
--    others, and derivative works that comment on or otherwise explain it
--    or assist in its implementation may be prepared, copied, published
--    and distributed, in whole or in part, without restriction of any
--    kind, provided that the above copyright notice and this paragraph are
--    included on all such copies and derivative works. However, this docu-
--    ment itself may not be modified in any way, such as by removing the
--    copyright notice or references to the Internet Society or other
--    Internet organizations, except as needed for the purpose of develop-
--    ing Internet standards in which case the procedures for copyrights
--    defined in the Internet Standards process must be followed, or as
--    required to translate it into languages other than English.
-- 
--    The limited permissions granted above are perpetual and will not be
--    revoked by the Internet Society or its successors or assigns.  This
--    document and the information contained herein is provided on an "AS
--    IS" basis and THE INTERNET SOCIETY AND THE INTERNET ENGINEERING TASK
--    FORCE DISCLAIMS ALL WARRANTIES, EXPRESS OR IMPLIED, INCLUDING BUT NOT
--    LIMITED TO ANY WARRANTY THAT THE USE OF THE INFORMATION HEREIN WILL
--    NOT INFRINGE ANY RIGHTS OR ANY IMPLIED WARRANTIES OF MERCHANTABILITY
--    OR FITNESS FOR A PARTICULAR PURPOSE.
