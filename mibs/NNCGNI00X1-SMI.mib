-- @(#)Newbridge.mib	9.1 10/16/98
--------------------------------------------------------------------------------
-- file: Newbridge.mib
--
-- contents:
--	This file contains the basic definitions for the Newbridge MIB 
--	extensions.
--
-- history:
--	0.1 / 92.08.25 / J. Watt / Creation
--	0.2 / 92.08.26 / J. Watt / Added nncExtSyncDataCct
--
-- Copyright 1992 Newbridge Networks Corporation.  All Rights Reserved
--------------------------------------------------------------------------------
NNCGNI00X1-SMI	DEFINITIONS ::= BEGIN
	
	IMPORTS	
		enterprises
			FROM RFC1155-SMI;
		
	newbridge     		 OBJECT IDENTIFIER ::= { enterprises 123 }
        nncDeviceIDs   		 OBJECT IDENTIFIER ::= { newbridge 1 }
        nncInterimMib		 OBJECT IDENTIFIER ::= { newbridge 2 }
	nncExtensions		 OBJECT IDENTIFIER ::= { newbridge 3 }
		
	nncStandalone  		 OBJECT IDENTIFIER ::= { nncDeviceIDs 1  }
        nnc8230        		 OBJECT IDENTIFIER ::= { nncStandalone 1 }
        nnc3604        		 OBJECT IDENTIFIER ::= { nncStandalone 2 }
        nnc8231        		 OBJECT IDENTIFIER ::= { nncStandalone 3 }
        nnc8251        		 OBJECT IDENTIFIER ::= { nncStandalone 4 }
        nnc3601        		 OBJECT IDENTIFIER ::= { nncStandalone 5 }

        nncIntegral    		 OBJECT IDENTIFIER ::= { nncDeviceIDs 2 }
        nncITB         		 OBJECT IDENTIFIER ::= { nncIntegral 1  }
		
		
	nncExtSystem		OBJECT IDENTIFIER ::= { nncExtensions 1 }
	nncExtEnvironmental	OBJECT IDENTIFIER ::= { nncExtensions 2 }
	nncExtRestart		OBJECT IDENTIFIER ::= { nncExtensions 3 }
	nncExtCodeSpace		OBJECT IDENTIFIER ::= { nncExtensions 4 }
	nncExtNVM		OBJECT IDENTIFIER ::= { nncExtensions 5 }
	nncExtAlarm		OBJECT IDENTIFIER ::= { nncExtensions 6 }
	nncExtNetSynch		OBJECT IDENTIFIER ::= { nncExtensions 7 }
	nncExtPosition		OBJECT IDENTIFIER ::= { nncExtensions 8 }
	nncExtDevice		OBJECT IDENTIFIER ::= { nncExtensions 9 }
	nncExtDs1		OBJECT IDENTIFIER ::= { nncExtensions 10 }
	nncExtRptr		OBJECT IDENTIFIER ::= { nncExtensions 11 }
	nncExtProbe		OBJECT IDENTIFIER ::= { nncExtensions 12 }
	nncExtDiag		OBJECT IDENTIFIER ::= { nncExtensions 13 }
	nncExtSyncDataCct	OBJECT IDENTIFIER ::= { nncExtensions 14 }
	
END
