-- *****************************************************************************
-- Unisphere-Data-PPP-CONF
--
-- SNMP Agent Capabilities definitions for the PPP MIBs.
--
-- Copyright (c) 2001, 2002 Unisphere Networks, Inc.  All rights reserved.
-- *****************************************************************************

Unisphere-Data-PPP-CONF DEFINITIONS ::= BEGIN

IMPORTS
    MODULE-IDENTITY, OBJECT-IDENTITY
        FROM SNMPv2-SMI
    AGENT-CAPABILITIES
        FROM SNMPv2-CONF
    usDataAgents
        FROM Unisphere-Data-Agents
    pppLinkStatusEntry, pppLinkConfigEntry, pppLqrEntry, pppLqrConfigEntry,
    pppLqrExtnsEntry
        FROM PPP-LCP-MIB
    pppIpEntry, pppIpConfigEntry
        FROM PPP-IP-NCP-MIB
    usdPppLcpGroup3, usdPppIpGroup2, usdPppOsiGroup2, usdPppSessionGroup,
    usdPppMlPppGroup, usdPppSummaryGroup, usdPppSummaryBasicGroup,
    usdPppSummaryLinkGroup, usdPppSummaryNetworkGroup, usdPppLcpGroup4,
    usdPppIpGroup3, usdPppMlPppGroup2
        FROM Unisphere-Data-PPP-MIB;

usdPppAgent MODULE-IDENTITY
    LAST-UPDATED "200205092103Z"  -- 09-May-02 05:03 PM EDT
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the point-to-point protocol
        (PPP) component of the SNMP agent in the Unisphere Data Routing Switch
        family of products."
    -- Revision History
    REVISION    "200205092103Z"  -- 09-May-02 05:03 PM EDT  - RX 4.0
    DESCRIPTION
        "Added new objects to the LCP, IP and multi-link groups in the
        Unisphere-Data-PPP-MIB."
    REVISION    "200205082025Z"  -- 08-May-02 04:25 PM EDT  - RX 3.3
    DESCRIPTION
        "Created separate capabilities for multi-link PPP."
    REVISION    "200104101823Z"  -- 10-Apr-01 02:23 PM EDT  - RX 3.2
    DESCRIPTION
        "The initial release of this management information module."
    ::= { usDataAgents 32 }


-- *****************************************************************************
-- The inclusive PPP agent capabilities.
-- *****************************************************************************
usdPppAgentV1 AGENT-CAPABILITIES
    PRODUCT-RELEASE
        "Version 1 of the PPP component of the Unisphere Routing Switch SNMP
        agent.  This version of the PPP component was supported in the Unisphere
        RX 2.4 thru 3.2 system releases."
    STATUS      obsolete
    DESCRIPTION
        "The MIBs supported by the SNMP agent for the PPP application in the
        Unisphere Routing Switch.  These capabilities became obsolete when the
        multilink capabilities were separated out."
    SUPPORTS    PPP-LCP-MIB
    --  The PPP-LCP-MIB is based on SMIv1 and has no conformance groups.
    --  Therefore, capabilities are identified by OID subtree "groups".
        INCLUDES  {
            pppLinkStatusEntry,
            pppLinkConfigEntry,
            pppLqrEntry,
            pppLqrConfigEntry,
            pppLqrExtnsEntry }
    SUPPORTS    PPP-IP-NCP-MIB
    --  The PPP-IP-NCP-MIB is based on SMIv1 and has no conformance groups.
    --  Therefore, capabilities are identified by OID subtree "groups".
        INCLUDES  {
            pppIpEntry,
            pppIpConfigEntry }
    SUPPORTS    Unisphere-Data-PPP-MIB
        INCLUDES  {
            usdPppLcpGroup3,
            usdPppIpGroup2,
            usdPppOsiGroup2,
            usdPppSessionGroup,
            usdPppMlPppGroup,
            usdPppSummaryGroup }
    ::= { usdPppAgent 1 }


-- *****************************************************************************
-- The general PPP interface agent capabilities.
-- *****************************************************************************
usdPppGeneralAgent OBJECT-IDENTITY
    STATUS      current
    DESCRIPTION
        "The registration group of agent capabilities for the general
        functionality of the PPP application which provides management support
        for basic (non-multi-link) PPP interfaces via SNMP."
    ::= { usdPppAgent 2 }

usdPppGeneralAgentV1 AGENT-CAPABILITIES
    PRODUCT-RELEASE
        "Version 1 of the general PPP component of the Unisphere Routing Switch
        SNMP agent.  This version of the PPP component was supported in the
        Unisphere RX 3.3 and subsequent 3.x system releases."
    STATUS      obsolete
    DESCRIPTION
        "The MIBs supported by the SNMP agent for the basic PPP application in
        the Unisphere Routing Switch.  These capabilities became obsolete when
        new LCP and IP objects were added to the Unisphere-Data-PPP-MIB."
    SUPPORTS    PPP-LCP-MIB
    --  The PPP-LCP-MIB is based on SMIv1 and has no conformance groups.
    --  Therefore, capabilities are identified by OID subtree "groups".
        INCLUDES  {
            pppLinkStatusEntry,
            pppLinkConfigEntry,
            pppLqrEntry,
            pppLqrConfigEntry,
            pppLqrExtnsEntry }
    SUPPORTS    PPP-IP-NCP-MIB
    --  The PPP-IP-NCP-MIB is based on SMIv1 and has no conformance groups.
    --  Therefore, capabilities are identified by OID subtree "groups".
        INCLUDES  {
            pppIpEntry,
            pppIpConfigEntry }
    SUPPORTS    Unisphere-Data-PPP-MIB
        INCLUDES  {
            usdPppLcpGroup3,
            usdPppIpGroup2,
            usdPppOsiGroup2,
            usdPppSessionGroup,
            usdPppSummaryBasicGroup }
    ::= { usdPppGeneralAgent 1 }

usdPppGeneralAgentV2 AGENT-CAPABILITIES
    PRODUCT-RELEASE
        "Version 2 of the general PPP component of the Unisphere Routing Switch
        SNMP agent.  This version of the PPP component is supported in the
        Unisphere RX 4.0 and subsequent system releases."
    STATUS      current
    DESCRIPTION
        "The MIBs supported by the SNMP agent for the basic PPP application in
        the Unisphere Routing Switch."
    SUPPORTS    PPP-LCP-MIB
    --  The PPP-LCP-MIB is based on SMIv1 and has no conformance groups.
    --  Therefore, capabilities are identified by OID subtree "groups".
        INCLUDES  {
            pppLinkStatusEntry,
            pppLinkConfigEntry,
            pppLqrEntry,
            pppLqrConfigEntry,
            pppLqrExtnsEntry }
    SUPPORTS    PPP-IP-NCP-MIB
    --  The PPP-IP-NCP-MIB is based on SMIv1 and has no conformance groups.
    --  Therefore, capabilities are identified by OID subtree "groups".
        INCLUDES  {
            pppIpEntry,
            pppIpConfigEntry }
    SUPPORTS    Unisphere-Data-PPP-MIB
        INCLUDES  {
            usdPppLcpGroup4,
            usdPppIpGroup3,
            usdPppOsiGroup2,
            usdPppSessionGroup,
            usdPppSummaryBasicGroup }
    ::= { usdPppGeneralAgent 2 }


-- *****************************************************************************
-- The multi-link PPP interface agent capabilities.
-- *****************************************************************************
usdPppMultiLinkAgent OBJECT-IDENTITY
    STATUS      current
    DESCRIPTION
        "The registration group of agent capabilities for the multi-link
        functionality of the PPP application which provides management support
        for multi-link PPP interfaces via SNMP."
    ::= { usdPppAgent 3 }

usdPppMultiLinkAgentV1 AGENT-CAPABILITIES
    PRODUCT-RELEASE
        "Version 1 of the multi-link PPP component of the Unisphere Routing
        Switch SNMP agent.  This version of the PPP component was supported in
        the Unisphere RX 3.3 and subsequent 3.x system releases."
    STATUS      obsolete
    DESCRIPTION
        "The MIB groups supported by the SNMP agent for the PPP application in
        the Unisphere Routing Switch..  These capabilities became obsolete when
        new multi-link objects were added to the Unisphere-Data-PPP-MIB"
    SUPPORTS    Unisphere-Data-PPP-MIB
        INCLUDES  {
            usdPppMlPppGroup,
            usdPppSummaryLinkGroup,
            usdPppSummaryNetworkGroup }
    ::= { usdPppMultiLinkAgent 1 }

usdPppMultiLinkAgentV2 AGENT-CAPABILITIES
    PRODUCT-RELEASE
        "Version 2 of the multi-link PPP component of the Unisphere Routing
        Switch SNMP agent.  This version of the PPP component is supported in
        the Unisphere RX 4.0 and subsequent system releases."
    STATUS      current
    DESCRIPTION
        "The MIB groups supported by the SNMP agent for the PPP application in
        the Unisphere Routing Switch."
    SUPPORTS    Unisphere-Data-PPP-MIB
        INCLUDES  {
            usdPppMlPppGroup2,
            usdPppSummaryLinkGroup,
            usdPppSummaryNetworkGroup }
    ::= { usdPppMultiLinkAgent 2 }

END
