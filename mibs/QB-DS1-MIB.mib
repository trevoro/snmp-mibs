--	Quantum Bridge DS1/E1 Management Information Base
--	Version 1.0.0
--	March 14, 2001
--
--	Quantum Bridge Corporation
--	Two Tech Drive
--	Andover, MA 01810
--	(978) 983-2617
--
----------------------------------------------------------------------------------------
--  03/14/2001 - mvaysman    	Original version
--
----------------------------------------------------------------------------------------
--
	QB-DS1-MIB DEFINITIONS ::= BEGIN
	IMPORTS 
	MODULE-IDENTITY, OBJECT-TYPE,  Counter32, Integer32
	FROM SNMPv2-SMI
	TEXTUAL-CONVENTION
        FROM SNMPv2-TC
	ifIndex
        FROM IF-MIB
	dsx1ConfigEntry
	FROM DS1-MIB
	MODULE-COMPLIANCE, OBJECT-GROUP
        FROM SNMPv2-CONF
        qbMibs
        FROM QUANTUMBRIDGE-REG
    ;    

    qbDs1MIB MODULE-IDENTITY
	LAST-UPDATED "0103140000Z" -- March 14, 2001
	ORGANIZATION "Quantum Bridge Corp."
	CONTACT-INFO
		"mvaysman@quantumbridge.com"
	DESCRIPTION
		"This module defines additional objects for management of DS1 
		links in Quantum Bridge devices, above and beyond what is defined in the
		standard DS1 mib, and proposed drafts."
    ::= { qbMibs 10 }

    -- Top-level organization of the MIB

    qbDs1Objects          OBJECT IDENTIFIER ::= { qbDs1MIB 1 }
    qbDs1Tables           OBJECT IDENTIFIER ::= { qbDs1MIB 2 }
    qbDs1Conformance      OBJECT IDENTIFIER ::= { qbDs1MIB 3 }

    -- Textual Conventions


-- ***************************************
-- Extensions to the DS1 'Config' Table
-- ***************************************
   qbDsx1ConfigTable        OBJECT-TYPE
	SYNTAX      SEQUENCE OF QbDsx1ConfigEntry
	MAX-ACCESS  not-accessible
	STATUS      current
	DESCRIPTION
            "The Quantum Bridge DS1 Config table contains extensions to
             the DS1 Config table."
	::= { qbDs1Tables 1 }

    qbDsx1ConfigEntry        OBJECT-TYPE
	SYNTAX      QbDsx1ConfigEntry
	MAX-ACCESS  not-accessible
	STATUS      current
	DESCRIPTION
            "An entry in the Quantum Build DS1 Config table."
	AUGMENTS    { dsx1ConfigEntry }
	::= { qbDsx1ConfigTable 1 }

    QbDsx1ConfigEntry ::=
	SEQUENCE {
		qbdsx1ClockMode		INTEGER
    }

   qbdsx1ClockMode OBJECT-TYPE
	 SYNTAX      INTEGER {
		srts(2),
		adaptive(3)
	}
	MAX-ACCESS  read-write
	STATUS      current
	DESCRIPTION
		"Define if DSx/Ex service clocking mode."
	DEFVAL     { adaptive }
    ::= { qbDsx1ConfigEntry 1 }

-- ***************************************
-- DS1 port Statistics Table 
-- ***************************************
    qbDsx1StatTable        OBJECT-TYPE
	SYNTAX      SEQUENCE OF QbDsx1StatEntry
	MAX-ACCESS  not-accessible
	STATUS      current
	DESCRIPTION
            "The Quantum Bridge DS1 Config table contains extensions to
             the DS1 Config table."
	::= { qbDs1Tables 2 }

    qbDsx1StatEnry   OBJECT-TYPE
	SYNTAX      QbDsx1StatEntry
	MAX-ACCESS  not-accessible
	STATUS      current
	DESCRIPTION
            "An entry in the Quantum Build DS1 Config table."
	INDEX    { ifIndex }
	::= { qbDsx1StatTable 1 }

    QbDsx1StatEntry ::=
	SEQUENCE {
		qbDsx1StatBPVs	Counter32
	}

   qbDsx1StatBPVs OBJECT-TYPE
	SYNTAX		Counter32
	MAX-ACCESS	read-only
	STATUS		current
	DESCRIPTION
		"The number of Bipolar Violations."
    ::= {  qbDsx1StatEnry 1 }

-- ****************************************************************
-- Conformance Information
-- ****************************************************************

   qbDs1Compliances OBJECT IDENTIFIER ::= { qbDs1Conformance 1 }
   qbDs1Groups      OBJECT IDENTIFIER ::= { qbDs1Conformance 2 }

--
-- Compliance Statements
--

   qbDs1Compliance MODULE-COMPLIANCE
	 STATUS      current
	DESCRIPTION
		"The compliance statement for all agents that support this
		MIB. A compliant agent implements all objects defined in this
		MIB."
    MODULE  -- this module
    MANDATORY-GROUPS {
        qbDs1AllGroup
    }
    ::= { qbDs1Compliances 1 }

--
-- All Object Groups
--
   qbDs1AllGroup OBJECT-GROUP
    OBJECTS {
	    qbdsx1ClockMode
    }
    STATUS      current
    DESCRIPTION
        "The set of all accessible objects in this MIB."
    ::= { qbDs1Groups 1 }

END
