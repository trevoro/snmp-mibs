------------------------------------------------------------
-- $Workfile:   pgsyslog.my  $
--   pg chassis mid
-- $Archive:   S:\DSLAM\swdev\snmp14.2.1.16\mibs\common\pgsyslog.myv  $
-- $Revision:   1.4  $
-- $Date:   19 Jan 2000 17:02:18  $
-- $Author:   ngov  $
------------------------------------------------------------

-- Release 1.0
-- Revision 10/1/98
-- Printed

-- Copyright 1998 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain's intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.


PAIRGAIN-SYS-LOG-MIB DEFINITIONS ::= BEGIN

-- SECTION 1: Top Level Definitions

IMPORTS
        OBJECT-TYPE
            FROM RFC-1212
--        TimeStamp
--            FROM SNMPv2-TC
        pgainSysLog
            FROM PAIRGAIN-COMMON-HD-MIB
	TimeSeconds
	    FROM PAIRGAIN-DSLAM-CHASSIS-MIB;


-- Textual Conventions

    DisplayString ::= OCTET STRING

--
-- System Log type
--

    PgSysLogType ::=
        INTEGER {
                unknown(1),
                error(2),
                alarm(3),
                clralarm(4),
                trap(5),
                info(6),
                bintrace(7),
                txttrace(8),
                debug(9)
        }

-- SECTION 2: PairGain System Log Table

pgSystemLogTable OBJECT-TYPE
        SYNTAX  SEQUENCE OF PgSystemLogEntry
        ACCESS  not-accessible
        STATUS  mandatory
        DESCRIPTION
                "The system log table."
        ::= { pgainSysLog 1 }

pgSystemLogEntry OBJECT-TYPE
        SYNTAX  PgSystemLogEntry
        ACCESS  not-accessible
        STATUS  mandatory
        DESCRIPTION
                "Entry in the system log table."
        INDEX   { pgSystemLogId}
        ::= { pgSystemLogTable 1 }

PgSystemLogEntry ::= SEQUENCE {
        pgSystemLogId
                INTEGER,
        pgSystemLogTimeStamp
                TimeSeconds,
        pgSystemLogType
                PgSysLogType,
        pgSystemLogSlotId
                INTEGER,
        pgSystemLogDescription
                DisplayString
}

pgSystemLogId OBJECT-TYPE
        SYNTAX  INTEGER
        ACCESS  read-only
        STATUS  mandatory
        DESCRIPTION
                "The ID of the current log entry, with pgSystemLogId equals 1
                 represents the most current LOG, 2 represents the prior
                 log entry, and etc.
                "
        ::= { pgSystemLogEntry 1 }

pgSystemLogTimeStamp  OBJECT-TYPE
        SYNTAX  TimeSeconds
        ACCESS  read-only
        STATUS  mandatory
        DESCRIPTION
                "The time stamp of the log entry .
                "
        ::= { pgSystemLogEntry 2 }

pgSystemLogType  OBJECT-TYPE
        SYNTAX  PgSysLogType
        ACCESS  read-only
        STATUS  mandatory
        DESCRIPTION
                "The (PgSystemLogType) type of the log entry.
                "
        ::= { pgSystemLogEntry 3 }

pgSystemLogSlotId OBJECT-TYPE
        SYNTAX  INTEGER
        ACCESS  read-only
        STATUS  mandatory
        DESCRIPTION
                "The slot ID that the log message is orignated.
                "
        ::= { pgSystemLogEntry 4 }

pgSystemLogDescription  OBJECT-TYPE
        SYNTAX  DisplayString
        ACCESS  read-only
        STATUS  mandatory
        DESCRIPTION
                "The description of the log entry.
                "
        ::= { pgSystemLogEntry 5 }


END
