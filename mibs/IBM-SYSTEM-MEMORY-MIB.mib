IBM-SYSTEM-MEMORY-MIB DEFINITIONS ::= BEGIN

IMPORTS
   OBJECT-TYPE
        FROM RFC-1212

   TRAP-TYPE
        FROM RFC-1215

   ibmSystemMemory,
   Boolean, Uint8, Sint8, Uint16, Sint16, Uint32,
   Sint32, Uint64, Sint64, Real32, Real64, String, Datetime
      FROM IBM-SYSTEM-MIB;
      
ibmSystemPhysicalMemoryTable OBJECT-TYPE
   SYNTAX         SEQUENCE OF IbmSystemPhysicalMemoryEntry
   ACCESS         not-accessible
   STATUS         mandatory
   DESCRIPTION    "The IBMPSG_PhysicalMemory class represents an IBM managed Memory Array."
   REFERENCE      "IBMPSG_PhysicalMemory"
::= { ibmSystemMemory 1 }

ibmSystemPhysicalMemoryEntry OBJECT-TYPE
   SYNTAX         IbmSystemPhysicalMemoryEntry
   ACCESS         not-accessible
   STATUS         mandatory
   DESCRIPTION    "This class defines an entry for each IBMPSG_PhysicalMemory
                    instance. Each instance of the IBMPSG_PhysicalMemory class 
                    contains status and descriptive information for each memory 
                    bank recognized by the operating system."
   INDEX          { ibmSystemPhysicalMemoryKeyIndex }
::= { ibmSystemPhysicalMemoryTable 1 }

IbmSystemPhysicalMemoryEntry ::= SEQUENCE
{
   ibmSystemPhysicalMemoryKeyIndex String,   
   ibmSystemPhysicalMemoryIsActive Boolean,
   ibmSystemPhysicalMemoryHasError Boolean,
   ibmSystemPhysicalMemoryPoweredOn Boolean,
   ibmSystemPhysicalMemoryTotalWidth Uint16,
   ibmSystemPhysicalMemoryDataWidth Uint16,
   ibmSystemPhysicalMemoryFormFactor Uint16,
   ibmSystemPhysicalMemoryMemoryType Uint16,
   ibmSystemPhysicalMemoryTypeDetail Uint16,
   ibmSystemPhysicalMemorySpeed Uint32,
   ibmSystemPhysicalMemoryCapacity Uint64,
   ibmSystemPhysicalMemoryBankLabel String,
   ibmSystemPhysicalMemoryDeviceLocator String,
   ibmSystemPhysicalMemoryManufacturer String,
   ibmSystemPhysicalMemoryPartNumber String,
   ibmSystemPhysicalMemorySerialNumber String,
   ibmSystemPhysicalMemoryStatus String
}

ibmSystemPhysicalMemoryKeyIndex OBJECT-TYPE
   SYNTAX         String
   ACCESS         read-only
   STATUS         mandatory
   DESCRIPTION    "The index used by this table."
   REFERENCE      "IBMPSG_PhysicalMemory.KeyIndex"
::= { ibmSystemPhysicalMemoryEntry 1 }

ibmSystemPhysicalMemoryIsActive OBJECT-TYPE
   SYNTAX         Boolean
   ACCESS         read-only
   STATUS         mandatory
   DESCRIPTION    "Indicates whether memory is active
                   1 - is active
                   0 - is not active."
   REFERENCE      "IBMPSG_PhysicalMemory.IsActive"
::= { ibmSystemPhysicalMemoryEntry 2 }

ibmSystemPhysicalMemoryHasError OBJECT-TYPE
   SYNTAX         Boolean
   ACCESS         read-only
   STATUS         mandatory
   DESCRIPTION    "Indicates whether memory has error 
                   1 - has error
                   0 - does not have error."
   REFERENCE      "IBMPSG_PhysicalMemory.NominalReading"
::= { ibmSystemPhysicalMemoryEntry 3 }

ibmSystemPhysicalMemoryPoweredOn OBJECT-TYPE
   SYNTAX         Boolean
   ACCESS         read-only
   STATUS         mandatory
   DESCRIPTION    "Indicates whether memory is powered on
                   1 - powered on
                   0 - powered off."
   REFERENCE      "IBMPSG_PhysicalMemory.PoweredOn"
::= { ibmSystemPhysicalMemoryEntry 4 }

ibmSystemPhysicalMemoryTotalWidth OBJECT-TYPE
   SYNTAX         Uint16
   ACCESS         read-only
   STATUS         mandatory
   DESCRIPTION    "Total width, in bits, of the PhysicalMemory, including check
                   or error correction bits. If there are no error correction bits, 
                   the value in this property should match that specified for DataWidth."
   REFERENCE      "IBMPSG_PhysicalMemory.TotalWidth"
::= { ibmSystemPhysicalMemoryEntry 5 }

ibmSystemPhysicalMemoryDataWidth OBJECT-TYPE
   SYNTAX         Uint16
   ACCESS         read-only
   STATUS         mandatory
   DESCRIPTION    "Data width of the PhysicalMemory, in bits. A data width 
                   of 0 and a TotalWidth of 8 would indicate that the Memory 
                   is solely used to provide error correction bits."
   REFERENCE      "IBMPSG_PhysicalMemory.DataWidth"
::= { ibmSystemPhysicalMemoryEntry 6 }

ibmSystemPhysicalMemoryFormFactor OBJECT-TYPE
   SYNTAX         Uint16
   ACCESS         read-only
   STATUS         mandatory
   DESCRIPTION    "Refers to the physical packaging of the memory
                   examples - DIMM,SIMM,Chip."
   REFERENCE      "IBMPSG_PhysicalMemory.FormFactor"
::= { ibmSystemPhysicalMemoryEntry 7 }

ibmSystemPhysicalMemoryMemoryType OBJECT-TYPE
   SYNTAX         Uint16
   ACCESS         read-only
   STATUS         mandatory
   DESCRIPTION    "The type of PhysicalMemory."
   REFERENCE      "IBMPSG_PhysicalMemory.MemoryType"
::= { ibmSystemPhysicalMemoryEntry 8 }

ibmSystemPhysicalMemoryTypeDetail OBJECT-TYPE
   SYNTAX         Uint16
   ACCESS         read-only
   STATUS         mandatory
   DESCRIPTION    "Further Details about memory type
                   examples - Fast-paged,static column,window DRAM."
   REFERENCE      "IBMPSG_PhysicalMemory.TypeDetail"
::= { ibmSystemPhysicalMemoryEntry 9 }

ibmSystemPhysicalMemorySpeed OBJECT-TYPE
   SYNTAX         Uint32
   ACCESS         read-only
   STATUS         mandatory
   DESCRIPTION    "The speed of the PhysicalMemory, in nanoseconds."
   REFERENCE      "IBMPSG_PhysicalMemory.Speed"
::= { ibmSystemPhysicalMemoryEntry 10 }

ibmSystemPhysicalMemoryCapacity OBJECT-TYPE
   SYNTAX         Uint64
   ACCESS         read-only
   STATUS         mandatory
   DESCRIPTION    "The total capacity of this PhysicalMemory, in bytes."
   REFERENCE      "IBMPSG_PhysicalMemory.Capacity"
::= { ibmSystemPhysicalMemoryEntry 11 }

ibmSystemPhysicalMemoryBankLabel OBJECT-TYPE
   SYNTAX         String
   ACCESS         read-only
   STATUS         mandatory
   DESCRIPTION    "A string identifying the physically labeled bank where 
                   the Memory is located - for example, 'Bank 0' or 'Bank A'."
   REFERENCE      "IBMPSG_PhysicalMemory.BankLabel"
::= { ibmSystemPhysicalMemoryEntry 12 }

ibmSystemPhysicalMemoryDeviceLocator OBJECT-TYPE
   SYNTAX         String
   ACCESS         read-only
   STATUS         mandatory
   DESCRIPTION    "The physically labeled socket or board position where the 
                   memory device is located."
   REFERENCE      "IBMPSG_PhysicalMemory.DeviceLocator"
::= { ibmSystemPhysicalMemoryEntry 13 }

ibmSystemPhysicalMemoryManufacturer OBJECT-TYPE
   SYNTAX         String
   ACCESS         read-only
   STATUS         mandatory
   DESCRIPTION    "The name of the organization responsible for producing this Memory."
   REFERENCE      "IBMPSG_PhysicalMemory.Manufacturer"
::= { ibmSystemPhysicalMemoryEntry 14 }

ibmSystemPhysicalMemoryPartNumber OBJECT-TYPE
   SYNTAX         String
   ACCESS         read-only
   STATUS         mandatory
   DESCRIPTION    "The part number for this memory device."
   REFERENCE      "IBMPSG_PhysicalMemory.PartNumber"
::= { ibmSystemPhysicalMemoryEntry 15 }

ibmSystemPhysicalMemorySerialNumber OBJECT-TYPE
   SYNTAX         String
   ACCESS         read-only
   STATUS         mandatory
   DESCRIPTION    "A manufacturer-allocated number used to identify the Memory."
   REFERENCE      "IBMPSG_PhysicalMemory.SerialNumber"
::= { ibmSystemPhysicalMemoryEntry 16 }

ibmSystemPhysicalMemoryStatus OBJECT-TYPE
   SYNTAX         String
   ACCESS         read-only
   STATUS         mandatory
   DESCRIPTION    "The current Status of the Memory."
   REFERENCE      "IBMPSG_PhysicalMemory.Status"
::= { ibmSystemPhysicalMemoryEntry 17 }

END
