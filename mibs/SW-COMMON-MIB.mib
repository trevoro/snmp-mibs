-- Revision 1.0.0
-- Copyright 1999 D-Link, Inc.
-- All rights reserved.

SW-COMMON-MIB   DEFINITIONS ::= BEGIN
    IMPORTS
        OBJECT-TYPE     FROM RFC-1212
        enterprises     FROM RFC1155-SMI;
        
    marconi     OBJECT IDENTIFIER ::= { enterprises 326 }
    systems     OBJECT IDENTIFIER ::= { marconi 2 }
    external    OBJECT IDENTIFIER ::= { systems 20 }
    dlink       OBJECT IDENTIFIER ::= { external 1 }

    dlinkcommon OBJECT IDENTIFIER ::= { dlink 1 }

    golf        OBJECT IDENTIFIER ::= { dlink 2 }
    golfproducts        OBJECT IDENTIFIER ::= { golf 1 }
    es2000              OBJECT IDENTIFIER ::= { golfproducts 3 }

    golfcommon          OBJECT IDENTIFIER ::= { golf 2 }

    marconi-mgmt    OBJECT IDENTIFIER ::= { golfcommon 2 }        

    es2000Mgmt      OBJECT IDENTIFIER ::= { marconi-mgmt 28 }

    swL2Mgmt        OBJECT IDENTIFIER ::= { es2000Mgmt 2 }

    swL2DevMgmt     OBJECT IDENTIFIER ::= { swL2Mgmt 1 }

-- *****************************************************************************
--  swL2DevCtrl
-- *****************************************************************************
    swL2DevCtrl     OBJECT IDENTIFIER ::= { swL2DevMgmt 1 }

    swL2DevCtrlStpState OBJECT-TYPE
        SYNTAX  INTEGER {
            other(1),
            disabled(2),
            enabled(3),
            notAvailable(4)
        }
        ACCESS  read-write
        STATUS  mandatory
        DESCRIPTION
            "This object can be enabled or disabled spanning tree algorithm
             during runtime of the system."
        ::= { swL2DevCtrl 1 }

    swL2DevCtrlPartitionModeState OBJECT-TYPE
        SYNTAX  INTEGER {
            other(1),
            disabled(2),
            enabled(3),
            notAvailable(4)
        }
        ACCESS  read-write
        STATUS  mandatory
        DESCRIPTION
            "This object used to enable or disable port auto partition. When the
             object apply for all ports of the device."
        ::= { swL2DevCtrl 2 }

    swL2DevCtrlTableLockState OBJECT-TYPE
        SYNTAX  INTEGER {
            other(1),
            disabled(2),
            enabled(3),
            notAvailable(4)
        }
        ACCESS  read-write
        STATUS  mandatory
        DESCRIPTION
            "This object indicates whether the address table is locked.
             In other words, the address table doesn't learn any more new address.
             The aging timer is suspended when the address table is locked.
             As long as the table is locked, all of the frames are dropped if the
             destination can not be found in the address."
        ::= { swL2DevCtrl 3 }

    swL2DevCtrlHOLState OBJECT-TYPE
        SYNTAX  INTEGER {
            other(1),
            disabled(2),
            enabled(3),
            notAvailable(4)
        }
        ACCESS  read-write
        STATUS  mandatory
        DESCRIPTION
            "The object provides a way to prevent HOL (Head Of Line) blocking
             between ports. HOL protection may prevent forwarding a packet to
             a blocking port. The idea relies on the assumption that it is
             better to discard packets destined to blocking ports, then to let
             them consume more and more buffers in the input-port's Rx-counters
             because eventually these input ports may become totally blocked.
             The meanings of the values are:

             other(1) - this entry is currently in use but the conditions under
                        which it will remain so are different from each of the
                        following values.
             disabled(2) - HOL function disable for device.
             enabled(3) - HOL function enable for device."
        ::= { swL2DevCtrl 4 }

-- + added by Jemy 10/12/99
    swL2DevCtrlAddrLookupModesAndHitRate OBJECT-TYPE
        SYNTAX  INTEGER {
            level0(1),
            level1(2),
            level2(3),
            level3(4),
            level4(5),
            level5(6),
            level6(7),
            level7(8)
        }
        ACCESS  read-write
        STATUS  mandatory
        DESCRIPTION
            "According to the differnet address looke mode setting, to enlarge the
             address table size is possible in device. But there is side effect
             as the higher level you have, the lower thorughput device has. That
             means Level 0 get the smallest table size, but get better performace.
             We recommand the user use the Level 1 as defualt setting."
        ::= { swL2DevCtrl 5 }

-- +added by Jemy 2000/1/25 05:45PM
    swL2DevCtrlBuzzerState OBJECT-TYPE
        SYNTAX  INTEGER {
            other(1),
            disabled(2),
            enabled(3)
        }
        ACCESS  read-write
        STATUS  mandatory
        DESCRIPTION
            " Controls buzzer state to be disabled or enabled."
        ::= { swL2DevCtrl 6 }

-- +updated by Jemy 2000/1/29 06:36PM
    swL2DevCtrlBuzzerTest OBJECT-TYPE
        SYNTAX  INTEGER
        ACCESS  write-only
        STATUS  mandatory
        DESCRIPTION
            " Tests buzzer to bibi. First of all, any unsigned integer can be used to set."
        ::= { swL2DevCtrl 7 }
-- -        
-- -        

-- *****************************************************************************
--  swL2DevAlarm
-- *****************************************************************************
    swL2DevAlarm    OBJECT IDENTIFIER ::= { swL2DevMgmt 2 }

    swL2DevAlarmPartition OBJECT-TYPE
        SYNTAX  INTEGER {
            other(1),
            disabled(2),
            enabled(3),
            notAvailable(4)
        }
        ACCESS  read-write
        STATUS  mandatory
        DESCRIPTION
            "Depending on this object, the device send a trap or not when
             any one of the device's ports was partitioned."
        ::= { swL2DevAlarm 1 }

    swL2DevAlarmNewRoot OBJECT-TYPE
        SYNTAX  INTEGER {
            other(1),
            disabled(2),
            enabled(3),
            notAvailable(4)
        }
        ACCESS  read-write
        STATUS  mandatory
        DESCRIPTION
            "When the device has become the new root of the Spanning Tree, this
             object decide whether to send a new root trap."
        ::= { swL2DevAlarm 2 }

    swL2DevAlarmTopChange OBJECT-TYPE
        SYNTAX  INTEGER {
            other(1),
            disabled(2),
            enabled(3),
            notAvailable(4)
        }
        ACCESS  read-write
        STATUS  mandatory
        DESCRIPTION
            "This object determines to send a trap or not when the switch topology
             was changed. If the object is enabled(3), the topologyChange trap is
             sent by the device when any of its configured ports transitions from
             the Learning state to the Forwarding state, or from the Forwarding
             state to the Blocking state. For the same port tranition, the device
             doesn't send the trap if this object value is disabled or other."
        ::= { swL2DevAlarm 3 }

    swL2DevAlarmLinkChange OBJECT-TYPE
        SYNTAX  INTEGER {
            other(1),
            disabled(2),
            enabled(3),
            notAvailable(4)
        }
        ACCESS  read-write
        STATUS  mandatory
        DESCRIPTION
            "This object determines to send a trap or not when the link was changed.
             If the object is enabled(3), the Link Change trap is sent by the
             device when any of its ports link change. The device doesn't send
             the trap if this object value is disabled or other."
        ::= { swL2DevAlarm 4 }

-- *****************************************************************************
--  swL2DevAlarmPowerTable
-- *****************************************************************************
-- +added by Jemy 2000/2/2 02:28PM B13
    swL2DevAlarmPowerTable OBJECT-TYPE
        SYNTAX  SEQUENCE OF SwL2DevAlarmPowerEntry
        ACCESS  not-accessible
        STATUS  mandatory
        DESCRIPTION
            "A table that controls error state to bibi about power module."
        ::= { swL2DevAlarm 5 }

    swL2DevAlarmPowerEntry OBJECT-TYPE
        SYNTAX  SwL2DevAlarmPowerEntry
        ACCESS  not-accessible
        STATUS  mandatory
        DESCRIPTION
            "A list of controlling informations for power module."
        INDEX   { swL2DevAlarmPowerIndex }
        ::= { swL2DevAlarmPowerTable 1 }

    SwL2DevAlarmPowerEntry ::=
        SEQUENCE {
            swL2DevAlarmPowerIndex
                INTEGER,
            swL2DevAlarmPowerTemperature
                INTEGER,
            swL2DevAlarmPowerVolt
                INTEGER,
            swL2DevAlarmPowerCurrent
                INTEGER,
            swL2DevAlarmPowerFan
                INTEGER
        }

    swL2DevAlarmPowerIndex OBJECT-TYPE
        SYNTAX  INTEGER
        ACCESS  read-only
        STATUS  mandatory
        DESCRIPTION
            "ID of the power module."
        ::= { swL2DevAlarmPowerEntry 1 }
        
    swL2DevAlarmPowerTemperature OBJECT-TYPE
        SYNTAX  INTEGER {
            other(1),
            disabled(2),
            enabled(3),
            notAvailable(4)
        }
        ACCESS  read-write
        STATUS  mandatory
        DESCRIPTION
            "Controls temperature error state in power module."
        ::= { swL2DevAlarmPowerEntry 2 }
        
    swL2DevAlarmPowerVolt OBJECT-TYPE
        SYNTAX  INTEGER {
            other(1),
            disabled(2),
            enabled(3),
            notAvailable(4)
        }
        ACCESS  read-write
        STATUS  mandatory
        DESCRIPTION
            "Controls volt error state in power module."
        ::= { swL2DevAlarmPowerEntry 3 }
        
    swL2DevAlarmPowerCurrent OBJECT-TYPE
        SYNTAX  INTEGER {
            other(1),
            disabled(2),
            enabled(3),
            notAvailable(4)
        }
        ACCESS  read-write
        STATUS  mandatory
        DESCRIPTION
            "Controls current error state in power module."
        ::= { swL2DevAlarmPowerEntry 4 }        
        
    swL2DevAlarmPowerFan OBJECT-TYPE
        SYNTAX  INTEGER {
            other(1),
            disabled(2),
            enabled(3),
            notAvailable(4)
        }
        ACCESS  read-write
        STATUS  mandatory
        DESCRIPTION
            "Controls fan error state in power module."
        ::= { swL2DevAlarmPowerEntry 5 }        

-- *****************************************************************************
--  swL2DevAlarmSystemFanTable
-- *****************************************************************************
-- +added by Jemy 2000/2/2 02:28PM B13
    swL2DevAlarmSystemFanTable OBJECT-TYPE
        SYNTAX  SEQUENCE OF SwL2DevAlarmSystemFanEntry
        ACCESS  not-accessible
        STATUS  mandatory
        DESCRIPTION
            "A table that controls error state to bibi about system fans."
        ::= { swL2DevAlarm 6 }

    swL2DevAlarmSystemFanEntry OBJECT-TYPE
        SYNTAX  SwL2DevAlarmSystemFanEntry
        ACCESS  not-accessible
        STATUS  mandatory
        DESCRIPTION
            "A list of controlling informations for system fans."
        INDEX   { swL2DevAlarmSystemFanIndex }
        ::= { swL2DevAlarmSystemFanTable 1 }

    SwL2DevAlarmSystemFanEntry ::=
        SEQUENCE {
            swL2DevAlarmSystemFanIndex
                INTEGER,
            swL2DevAlarmSystemFanState
                INTEGER
        }

    swL2DevAlarmSystemFanIndex OBJECT-TYPE
        SYNTAX  INTEGER
        ACCESS  read-only
        STATUS  mandatory
        DESCRIPTION
            "ID of the system fans."
        ::= { swL2DevAlarmSystemFanEntry 1 }
        
    swL2DevAlarmSystemFanState OBJECT-TYPE
        SYNTAX  INTEGER {
            other(1),
            disabled(2),
            enabled(3),
            notAvailable(4)
        }
        ACCESS  read-write
        STATUS  mandatory
        DESCRIPTION
            "Controls system fan error state."
        ::= { swL2DevAlarmSystemFanEntry 2 }        
                
END
