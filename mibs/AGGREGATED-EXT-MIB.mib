-- 
-- AGGREGATED-EXT-MIB module definition  
--
-- The definitions in this module specify a "superMIB", which 
-- represents our aggrated Styx view, and it will support SNMP
-- protocol on behalf of all devices that are part of this 
-- aggregated view.
-- 
--

AGGREGATED-EXT-MIB DEFINITIONS ::= BEGIN
IMPORTS
    IpAddress, enterprises, Counter
        FROM RFC1155-SMI
    OBJECT-TYPE
        FROM RFC-1212
    DisplayString
        FROM RFC1213-MIB
    MODULE-IDENTITY, ObjectName, Integer32, Counter32, snmpModules
        FROM SNMPv2-SMI
    TruthValue, DisplayString, TestAndIncr, TimeStamp, RowStatus
        FROM SNMPv2-TC;

    lucent			OBJECT IDENTIFIER  ::=  {  enterprises  1751  }
    products		OBJECT IDENTIFIER  ::=  {  lucent  1  }
    excel			OBJECT IDENTIFIER  ::=  {  products 67  }
    excel1			OBJECT IDENTIFIER  ::=  {  excel 1 }
    excel2			OBJECT IDENTIFIER  ::=  {  excel 2 }
    excel3			OBJECT IDENTIFIER  ::=  {  excel 3 }
    excel4			OBJECT IDENTIFIER  ::=  {  excel 4 }

softSwitch   MODULE-IDENTITY    
        LAST-UPDATED "240701"
        ORGANIZATION "Lucent Technologies"    
        CONTACT-INFO 
                ""    
        DESCRIPTION
                "The MIB module for entities implementing the xxxx
                protocol."  

::=  {  products 1198  }

--    callCoordinator		OBJECT IDENTIFIER  ::=  {  softSwitch 1 }
--    ss7DeviceServer		OBJECT IDENTIFIER  ::=  {  softSwitch 2 }
    h323DeviceServer	OBJECT IDENTIFIER  ::=  {  softSwitch 3 }
    resourceMonitor		OBJECT IDENTIFIER  ::=  {  softSwitch 4 }
    sipDeviceServer	 	OBJECT IDENTIFIER  ::=  {  softSwitch 5 } 
    psaxDeviceServer	OBJECT IDENTIFIER  ::=  {  softSwitch 6 } 
    cdrDeviceServer	 	OBJECT IDENTIFIER  ::=  {  softSwitch 7 }
    spinsDeviceServer	OBJECT IDENTIFIER  ::=  {  softSwitch 8 }
    fcDeviceServer	    OBJECT IDENTIFIER  ::=  {  softSwitch 9 }
    softswitchTraps     OBJECT IDENTIFIER  ::=  {  softSwitch 10 }
    mantraAdmin	        OBJECT IDENTIFIER  ::=  {  softSwitch 99 } 
    mantraTrapVars      OBJECT IDENTIFIER ::= { softswitchTraps 1 }
    h323TrapVariables   OBJECT IDENTIFIER ::= { softswitchTraps 2 }
    rmTrapVariables     OBJECT IDENTIFIER ::= { softswitchTraps 3 } 
    fcTrapVariables     OBJECT IDENTIFIER ::= { softswitchTraps 4 } 
    mantraTraps         OBJECT IDENTIFIER ::= { mantraAdmin 0 }

h323DS1	OBJECT IDENTIFIER 	        ::=  { h323DeviceServer  1 }
h323DS2	OBJECT IDENTIFIER 	        ::=  { h323DeviceServer  2 }

sipDS1	OBJECT IDENTIFIER 	        ::=  { sipDeviceServer  1 }
sipDS2	OBJECT IDENTIFIER 	        ::=  { sipDeviceServer  2 }

cdrDS1	OBJECT IDENTIFIER 	        ::=  { cdrDeviceServer  1 }
cdrDS2	OBJECT IDENTIFIER 	        ::=  { cdrDeviceServer  2 }

spinsDS1 OBJECT IDENTIFIER 	        ::=  { spinsDeviceServer  1 }
spinsDS2 OBJECT IDENTIFIER 	        ::=  { spinsDeviceServer  2 }

fcDS1 OBJECT IDENTIFIER 	        ::=  { fcDeviceServer  1 }
fcDS2 OBJECT IDENTIFIER 	        ::=  { fcDeviceServer  2 }

psaxDS1	OBJECT IDENTIFIER 	        ::=  { psaxDeviceServer  1 }
psaxDS2	OBJECT IDENTIFIER 	        ::=  { psaxDeviceServer  2 }

rm1	OBJECT IDENTIFIER  		::=  {  resourceMonitor  1  }
rm2	OBJECT IDENTIFIER  		::=  {  resourceMonitor  2  }
rm3	OBJECT IDENTIFIER  		::=  {  resourceMonitor  3  }
rm4	OBJECT IDENTIFIER  		::=  {  resourceMonitor  4  }

pepName OBJECT-TYPE
    SYNTAX DisplayString
    MAX-ACCESS accessible-for-notify
    STATUS current
    DESCRIPTION
        "Name of the pep the action has occurred on."

    ::= { mantraTrapVars 1 }

devName OBJECT-TYPE
    SYNTAX DisplayString
    MAX-ACCESS accessible-for-notify
    STATUS current
    DESCRIPTION
        "Name of the deviceServer the action has occurred on."

    ::= { mantraTrapVars 2 }

file OBJECT-TYPE
    SYNTAX DisplayString
    MAX-ACCESS accessible-for-notify
    STATUS current
    DESCRIPTION
        "Name of the file the action has occurred on."

    ::= { mantraTrapVars 3 }

host OBJECT-TYPE
    SYNTAX DisplayString
    MAX-ACCESS accessible-for-notify
    STATUS current
    DESCRIPTION
        "Name of the host the action has occurred on."

    ::= { mantraTrapVars 4 }

port OBJECT-TYPE
    SYNTAX INTEGER ( 1024..32565 )
    MAX-ACCESS accessible-for-notify
    STATUS current
    DESCRIPTION
        "Port number associated with the pep the action has occurred on."

    ::= { mantraTrapVars 5 }

oldFile OBJECT-TYPE
    SYNTAX DisplayString
    MAX-ACCESS accessible-for-notify
    STATUS current
    DESCRIPTION
        "Name of the file the action has occurred on."

    ::= { mantraTrapVars 6 }

newFile OBJECT-TYPE
    SYNTAX DisplayString
    MAX-ACCESS accessible-for-notify
    STATUS current
    DESCRIPTION
        "Name of the file the action has occurred on."

    ::= { mantraTrapVars 7 }

minutes OBJECT-TYPE
    SYNTAX DisplayString
    MAX-ACCESS accessible-for-notify
    STATUS current
    DESCRIPTION
        "Name of the file the action has occurred on."

    ::= { mantraTrapVars 8 }

result OBJECT-TYPE
    SYNTAX DisplayString
    MAX-ACCESS accessible-for-notify
    STATUS current
    DESCRIPTION
        "Result of the action taken."

    ::= { mantraTrapVars 9 }

reason OBJECT-TYPE
    SYNTAX DisplayString
    MAX-ACCESS accessible-for-notify
    STATUS current
    DESCRIPTION
        "The reason the action was taken."

    ::= { mantraTrapVars 10 }

snName  OBJECT-TYPE
    SYNTAX DisplayString
    MAX-ACCESS accessible-for-notify
    STATUS current
    DESCRIPTION
        "The reason the action was taken."

    ::= { mantraTrapVars 11 }

myHost OBJECT-TYPE
    SYNTAX DisplayString
    MAX-ACCESS accessible-for-notify
    STATUS current
    DESCRIPTION
        "Name of the host the action has occurred on."

    ::= { mantraTrapVars 12 }

myPort OBJECT-TYPE
    SYNTAX INTEGER ( 1024..32565 )
    MAX-ACCESS accessible-for-notify
    STATUS current
    DESCRIPTION
        "Port number associated with the pep the action has occurred on."

    ::= { mantraTrapVars 13 }

mateHost OBJECT-TYPE
    SYNTAX DisplayString
    MAX-ACCESS accessible-for-notify
    STATUS current
    DESCRIPTION
        "Name of the host the action has occurred on."

    ::= { mantraTrapVars 14 }

matePort OBJECT-TYPE
    SYNTAX INTEGER ( 1024..32565 )
    MAX-ACCESS accessible-for-notify
    STATUS current
    DESCRIPTION
        "Port number associated with the pep the action has occurred on."

    ::= { mantraTrapVars 15 }

deviceType OBJECT-TYPE
    SYNTAX DisplayString
    MAX-ACCESS accessible-for-notify
    STATUS current
    DESCRIPTION
        "This is either CC, H323, SS7 or EBGen (the various modules in SARAS)"

    ::= { mantraTrapVars 16 }

domain OBJECT-TYPE
    SYNTAX DisplayString
    MAX-ACCESS accessible-for-notify
    STATUS current
    DESCRIPTION
        "Name of the domain the action has occurred on."

    ::= { mantraTrapVars 17 }

group OBJECT-TYPE
    SYNTAX DisplayString
    MAX-ACCESS accessible-for-notify
    STATUS current
    DESCRIPTION
        "Name of the group the action has occurred on."

    ::= { mantraTrapVars 18 }

name OBJECT-TYPE
    SYNTAX DisplayString
    MAX-ACCESS accessible-for-notify
    STATUS current
    DESCRIPTION
        "Name of the process the action has occurred on."

    ::= { mantraTrapVars 19 }

runStatus OBJECT-TYPE
    SYNTAX INTEGER ( 1..5 )
    MAX-ACCESS accessible-for-notify
    STATUS current
    DESCRIPTION
        "A short summary of the status of the mantra software modules."

    ::= { mantraTrapVars 20 }


timeOccurred OBJECT-TYPE
    SYNTAX  DisplayString 
    MAX-ACCESS  accessible-for-notify
    STATUS  current
    DESCRIPTION
		""

	    ::= { h323TrapVariables 1 }

code OBJECT-TYPE
    SYNTAX  INTEGER ( 1..1024 )
    MAX-ACCESS  accessible-for-notify
    STATUS  current
    DESCRIPTION
		""

	    ::= { h323TrapVariables 2 }

csID OBJECT-TYPE
    SYNTAX  INTEGER ( 1..1024 )
    MAX-ACCESS  accessible-for-notify
    STATUS  current
    DESCRIPTION
		""

	    ::= { h323TrapVariables 3 }

csType OBJECT-TYPE
    SYNTAX  DisplayString 
    MAX-ACCESS  accessible-for-notify
    STATUS  current
    DESCRIPTION
		""

	    ::= { h323TrapVariables 4 }

registrationStatus OBJECT-TYPE
    SYNTAX  DisplayString 
    MAX-ACCESS  accessible-for-notify
    STATUS  current
    DESCRIPTION
		""

	    ::= { h323TrapVariables 5 }

comment OBJECT-TYPE
    SYNTAX  DisplayString 
    MAX-ACCESS  accessible-for-notify
    STATUS  current
    DESCRIPTION
		""

	    ::= { h323TrapVariables 6 }

gwID OBJECT-TYPE
    SYNTAX  DisplayString 
    MAX-ACCESS  accessible-for-notify
    STATUS  current
    DESCRIPTION
		"Gateway ID"

	    ::= { h323TrapVariables 7 }

moduleID OBJECT-TYPE
    SYNTAX  INTEGER ( 1..1024 ) 
    MAX-ACCESS  accessible-for-notify
    STATUS  current
    DESCRIPTION
		"Gateway ID"

	    ::= { h323TrapVariables 8 }

percent OBJECT-TYPE
    SYNTAX  INTEGER ( 0..100 )
    MAX-ACCESS  accessible-for-notify
    STATUS  current
    DESCRIPTION
		"Gateway ID"

	    ::= { h323TrapVariables 9 }

gwIP OBJECT-TYPE
    SYNTAX  IpAddress
    MAX-ACCESS  accessible-for-notify
    STATUS  current
    DESCRIPTION
		"Gateway ip address"

	    ::= { h323TrapVariables 10 }

gwType OBJECT-TYPE
    SYNTAX  INTEGER ( 1..1024 ) 
    MAX-ACCESS  accessible-for-notify
    STATUS  current
    DESCRIPTION
		"Gateway type"

	    ::= { h323TrapVariables 11 }

percentage OBJECT-TYPE
    SYNTAX  INTEGER ( 1..1024 ) 
    MAX-ACCESS  accessible-for-notify
    STATUS  current
    DESCRIPTION
		"Gateway type"

	    ::= { rmTrapVariables 1 }

status OBJECT-TYPE
    SYNTAX  INTEGER ( 1..1024 ) 
    MAX-ACCESS  accessible-for-notify
    STATUS  current
    DESCRIPTION
		"Gateway type"

	    ::= { rmTrapVariables 2 }

load OBJECT-TYPE
    SYNTAX  INTEGER ( 1..1024 ) 
    MAX-ACCESS  accessible-for-notify
    STATUS  current
    DESCRIPTION
		"Gateway type"

	    ::= { rmTrapVariables 3 }

disk OBJECT-TYPE
    SYNTAX  DisplayString 
    MAX-ACCESS  accessible-for-notify
    STATUS  current
    DESCRIPTION
		"Gateway type"

	    ::= { rmTrapVariables 4 }

curSize OBJECT-TYPE
    SYNTAX  INTEGER ( 1..1024 ) 
    MAX-ACCESS  accessible-for-notify
    STATUS  current
    DESCRIPTION
		"Gateway type"

	    ::= { rmTrapVariables 5 }

maxSize OBJECT-TYPE
    SYNTAX  INTEGER ( 1..1024 ) 
    MAX-ACCESS  accessible-for-notify
    STATUS  current
    DESCRIPTION
		"Gateway type"

	    ::= { rmTrapVariables 6 }

processName OBJECT-TYPE
    SYNTAX  DisplayString
    MAX-ACCESS  accessible-for-notify
    STATUS  current
    DESCRIPTION
		"Gateway type"

	    ::= { rmTrapVariables 7 }

processID OBJECT-TYPE
    SYNTAX  INTEGER ( 1..65535 ) 
    MAX-ACCESS  accessible-for-notify
    STATUS  current
    DESCRIPTION
		"processID"

	    ::= { rmTrapVariables 8 }

cpuUsage OBJECT-TYPE
    SYNTAX  INTEGER ( 1..99 ) 
    MAX-ACCESS  accessible-for-notify
    STATUS  current
    DESCRIPTION
		"CPU usage percentage"

	    ::= { rmTrapVariables 9 }

memUsage OBJECT-TYPE
    SYNTAX  INTEGER ( 1..99 ) 
    MAX-ACCESS  accessible-for-notify
    STATUS  current
    DESCRIPTION
		"CPU usage percentage"

    ::= { rmTrapVariables 10 }

sbProducerHost OBJECT-TYPE
    SYNTAX DisplayString
    MAX-ACCESS accessible-for-notify
    STATUS current
    DESCRIPTION
        "Socket based producer host name"

    ::= { fcTrapVariables 1 }

sbProducerPort OBJECT-TYPE
    SYNTAX INTEGER ( 1024..65535 )
    MAX-ACCESS accessible-for-notify
    STATUS current
    DESCRIPTION
        "Socket based producer name"

    ::= { fcTrapVariables 2 }

unknownDeviceTrapContents OBJECT-TYPE
    SYNTAX  DisplayString
    MAX-ACCESS  read-only
    STATUS  current
    DESCRIPTION
	    "This is a string field (just to have a legal oid)
	    for traps generated neither from SS7 nor from the CC."

    ::= { softSwitch 98 }

lastAggNode OBJECT-TYPE
    SYNTAX  DisplayString
    MAX-ACCESS  read-only
    STATUS  current
    DESCRIPTION
	    "This is a flag variable, kept to indicate the 
	    end of aggregated mib during a snmpwalk.
	    It always returns the following string:
		Reached the End of Aggregated MIB"

    ::= { softSwitch 100 }

END
