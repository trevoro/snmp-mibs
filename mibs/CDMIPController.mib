--
-- CDMIPController.my
-- MIB generated by MG-SOFT Visual MIB Builder Version 2.1 Build 199
-- Monday, February 13, 2006 at 13:33:32
--

	CDMIPController DEFINITIONS ::= BEGIN

		IMPORTS 
			comtechEFData			
				FROM ComtechEFData			
			OBJECT-GROUP, MODULE-COMPLIANCE			
				FROM SNMPv2-CONF			
			IpAddress, Integer32, Counter32, OBJECT-TYPE, MODULE-IDENTITY			
				FROM SNMPv2-SMI			
			DisplayString			
				FROM SNMPv2-TC;
	
	
		cdmipController MODULE-IDENTITY
			LAST-UPDATED "200407121700Z"
			ORGANIZATION
				"Comtech EF Data"
			CONTACT-INFO
				"2114 West 7th Street Tempe, AZ  85281 USA"
			DESCRIPTION
				"CDMIP IP Controller"
			REVISION "200302231100Z"
			DESCRIPTION
				"Added QoS Rules Table."
			REVISION "200310231546Z"
			DESCRIPTION
				"Added V2 Conformance (Groups and Compliance)"
			REVISION "200402191653Z"
			DESCRIPTION
				"Added more WAN statistics."
			REVISION "200407121039Z"
			DESCRIPTION
				"Updates for 4.2 Maint. Release"
			REVISION "200512061455Z"
			DESCRIPTION
				"Updated for 1.5.3 Maint. Release"
			::= { comtechEFData 4 }
		
	
--
-- Type definitions
--
	
		Availability ::= INTEGER
			{
			unavailable(0),
			available(1)
			}
		
		EnableDisable ::= INTEGER
			{
			disable(0),
			enable(1)
			}
		
	
	
--
-- Node definitions
--
	
-- cdmipAdministration starts at child number "2"
		cdmipAdministration OBJECT IDENTIFIER ::= { cdmipController 2 }
		
		cdmipMibVersion OBJECT-TYPE
			SYNTAX INTEGER (1..256)
			MAX-ACCESS read-only
			STATUS current
			DESCRIPTION
				"/*****************************************************************************/
				/* 
				 * CDM-IP MIB Version Information
				 * 
				 * Date                 App Release             MIB Version
				 * ========             ===========             ===========
				 * 03/14/02             1.0                     1
				 *
				 * 04/23/02             internal                2
				 * 
				 * 07/31/02             1.1                     3
				 * 
				 * 10/15/02             1.2                     4
				 *
				 * 11/25/02             2.1                     5
				 *
				 * 02/19/04             4.0                     6
				 * 
				 * 07/12/04             4.2                     7
				 * 
				 * 12/31/05             5.3                     8
				 */
				/*****************************************************************************/
				"
			::= { cdmipAdministration 1 }
		
-- cdmipAccessList starts at child number "4"
		cdmipAccessLists OBJECT IDENTIFIER ::= { cdmipAdministration 4 }
		
		cdmipAccessIpAddress1 OBJECT-TYPE
			SYNTAX IpAddress
			MAX-ACCESS read-write
			STATUS current
			DESCRIPTION
				"Access IP Address #1:
				Used to restrict modem management through Web, Telnet, or SNMP
				to specific IP Addresses. "
			::= { cdmipAccessLists 1 }
		
		cdmipAccessSubnetMaskLen1 OBJECT-TYPE
			SYNTAX INTEGER (0 | 8..32)
			MAX-ACCESS read-write
			STATUS current
			DESCRIPTION
				"Subnet Mask Length for Access IP Address #1."
			::= { cdmipAccessLists 2 }
		
		cdmipAccessIpAddress2 OBJECT-TYPE
			SYNTAX IpAddress
			MAX-ACCESS read-write
			STATUS current
			DESCRIPTION
				"Access IP Address #2
				Used to restrict modem management through Web, Telnet, or SNMP
				to specific IP Addresses. "
			::= { cdmipAccessLists 3 }
		
		cdmipAccessSubnetMaskLen2 OBJECT-TYPE
			SYNTAX INTEGER (0 | 8..32)
			MAX-ACCESS read-write
			STATUS current
			DESCRIPTION
				"Subnet Mask Length for Access IP Address #2."
			::= { cdmipAccessLists 4 }
		
		cdmipAccessIpAddress3 OBJECT-TYPE
			SYNTAX IpAddress
			MAX-ACCESS read-write
			STATUS current
			DESCRIPTION
				"Access IP Address #3:
				Used to restrict modem management through Web, Telnet, or SNMP
				to specific IP Addresses."
			::= { cdmipAccessLists 5 }
		
		cdmipAccessSubnetMaskLen3 OBJECT-TYPE
			SYNTAX INTEGER (0 | 8..32)
			MAX-ACCESS read-write
			STATUS current
			DESCRIPTION
				"Subnet Mask Length for Access IP Addres #3."
			::= { cdmipAccessLists 6 }
		
		cdmipAccessIpAddress4 OBJECT-TYPE
			SYNTAX IpAddress
			MAX-ACCESS read-write
			STATUS current
			DESCRIPTION
				"Access IP Address #4:
				Used to restrict modem management through Web, Telnet, or SNMP
				to specific IP Addresses. "
			::= { cdmipAccessLists 7 }
		
		cdmipAccessSubnetMaskLen4 OBJECT-TYPE
			SYNTAX INTEGER (0 | 8..32)
			MAX-ACCESS read-write
			STATUS current
			DESCRIPTION
				"Subnet Mask Length for Access IP Address #4."
			::= { cdmipAccessLists 8 }
		
		cdmipAccessListEnforcement OBJECT-TYPE
			SYNTAX INTEGER
				{
				disabled(0),
				enforced(1)
				}
			MAX-ACCESS read-write
			STATUS current
			DESCRIPTION
				"Access List Enforcement
				
				Note: Be sure that you have added the SNMP browser's/manager's 
				IP Address to the access list before enabling access list filtering.
				Otherwise, the SNMP browser/manager will no longer be able to gain
				access to the SNMP agent."
			::= { cdmipAccessLists 9 }
		
		cdmipFeaturesAvailability OBJECT IDENTIFIER ::= { cdmipAdministration 5 }
		
		cdmipQosOption OBJECT-TYPE
			SYNTAX Availability
			MAX-ACCESS read-only
			STATUS current
			DESCRIPTION
				"Quality of Server (QoS) FAST Option."
			::= { cdmipFeaturesAvailability 3 }
		
		cdmipEncryptionOption OBJECT-TYPE
			SYNTAX Availability
			MAX-ACCESS read-only
			STATUS current
			DESCRIPTION
				"Triple DES Encryption FAST Option."
			::= { cdmipFeaturesAvailability 6 }
		
		cdmipIgmpOption OBJECT-TYPE
			SYNTAX Availability
			MAX-ACCESS read-only
			STATUS current
			DESCRIPTION
				"IGMP FAST Option."
			::= { cdmipFeaturesAvailability 7 }
		
		cdmipHeaderCompressionOption OBJECT-TYPE
			SYNTAX Availability
			MAX-ACCESS read-only
			STATUS current
			DESCRIPTION
				"IP Header Compression FAST Option."
			::= { cdmipFeaturesAvailability 8 }
		
		cdmipPayloadCompressionOption OBJECT-TYPE
			SYNTAX Availability
			MAX-ACCESS read-only
			STATUS current
			DESCRIPTION
				"IP Payload Compression FAST Option."
			::= { cdmipFeaturesAvailability 9 }
		
		cdmipFeaturesConfig OBJECT IDENTIFIER ::= { cdmipAdministration 6 }
		
		cdmipTelnetFeature OBJECT-TYPE
			SYNTAX EnableDisable
			MAX-ACCESS read-write
			STATUS current
			DESCRIPTION
				"Enable or disable Telnet access for managing the modem."
			::= { cdmipFeaturesConfig 2 }
		
		cdmipPingReplyFeature OBJECT-TYPE
			SYNTAX EnableDisable
			MAX-ACCESS read-write
			STATUS current
			DESCRIPTION
				"Enable or disable ICMP Ping Reply from the modem."
			::= { cdmipFeaturesConfig 3 }
		
		cdmipDownlinkRouteMulticastFeature OBJECT-TYPE
			SYNTAX EnableDisable
			MAX-ACCESS read-write
			STATUS current
			DESCRIPTION
				"Enable or disable 'downlink multicast routing' option 
				(Satellite to Ethernet)."
			::= { cdmipFeaturesConfig 4 }
		
		cdmipQosOpt OBJECT-TYPE
			SYNTAX EnableDisable
			MAX-ACCESS read-write
			STATUS current
			DESCRIPTION
				"Enable or disable 'Quality of Service' (QoS) in the modem's router."
			::= { cdmipFeaturesConfig 7 }
		
		cdmipTransmit3xDesEncryptionOpt OBJECT-TYPE
			SYNTAX INTEGER
				{
				disable(0),
				enable(1),
				perRoute(2)
				}
			MAX-ACCESS read-write
			STATUS current
			DESCRIPTION
				"Enable or disable 'transmit 3xDES encryption' option."
			::= { cdmipFeaturesConfig 10 }
		
		cdmipIgmpOpt OBJECT-TYPE
			SYNTAX EnableDisable
			MAX-ACCESS read-write
			STATUS current
			DESCRIPTION
				"Enable or disable IGMP option."
			::= { cdmipFeaturesConfig 12 }
		
		cdmipTxHeaderCompressionOpt OBJECT-TYPE
			SYNTAX INTEGER
				{
				disable(0),
				enable(1),
				perRoute(2)
				}
			MAX-ACCESS read-write
			STATUS current
			DESCRIPTION
				"Enable or disable the Transmit 'IP Header Compression' option."
			::= { cdmipFeaturesConfig 13 }
		
		cdmipRxHeaderCompressionOpt OBJECT-TYPE
			SYNTAX EnableDisable
			MAX-ACCESS read-write
			STATUS current
			DESCRIPTION
				"Enable or disable Receive 'IP Header Compression' option."
			::= { cdmipFeaturesConfig 14 }
		
		cdmipTxPayloadCompressionOpt OBJECT-TYPE
			SYNTAX INTEGER
				{
				disable(0),
				enable(1),
				perRoute(2)
				}
			MAX-ACCESS read-write
			STATUS current
			DESCRIPTION
				"Enable or disable 'Tx Payload Compression' option."
			::= { cdmipFeaturesConfig 15 }
		
		cdmip3xDesConfig OBJECT IDENTIFIER ::= { cdmipAdministration 7 }
		
-- cdmipTransmitKey1 starts at child number "3"
		cdmipTransmitKey1 OBJECT-TYPE
			SYNTAX DisplayString (SIZE (48))
			MAX-ACCESS read-write
			STATUS current
			DESCRIPTION
				"Triple DES (3xDES) Transmit Encrypt Key #1. 
				The key length is 192 bits (24 bytes or 48 HEX characters)."
			::= { cdmip3xDesConfig 3 }
		
		cdmipTransmitKey2 OBJECT-TYPE
			SYNTAX DisplayString (SIZE (48))
			MAX-ACCESS read-write
			STATUS current
			DESCRIPTION
				"Triple DES (3xDES) Transmit Encrypt Key #2. 
				The key length is 192 bits (24 bytes or 48 HEX characters)."
			::= { cdmip3xDesConfig 4 }
		
		cdmipTransmitKey3 OBJECT-TYPE
			SYNTAX DisplayString (SIZE (48))
			MAX-ACCESS read-write
			STATUS current
			DESCRIPTION
				"Triple DES (3xDES) Transmit Encrypt Key #3. 
				The key length is 192 bits (24 Bytes or 48 HEX characters)."
			::= { cdmip3xDesConfig 5 }
		
		cdmipTransmitKey4 OBJECT-TYPE
			SYNTAX DisplayString (SIZE (48))
			MAX-ACCESS read-write
			STATUS current
			DESCRIPTION
				"Triple DES (3xDES) Transmit Encrypt Key #4. 
				The key length is 192 bits (24 Bytes or 48 HEX characters)."
			::= { cdmip3xDesConfig 6 }
		
		cdmipTransmitKey5 OBJECT-TYPE
			SYNTAX DisplayString (SIZE (48))
			MAX-ACCESS read-write
			STATUS current
			DESCRIPTION
				"Triple DES (3xDES) Transmit Encrypt Key #5. 
				The key length is 192 bits (24 Bytes or 48 HEX characters)."
			::= { cdmip3xDesConfig 7 }
		
		cdmipTransmitKey6 OBJECT-TYPE
			SYNTAX DisplayString (SIZE (48))
			MAX-ACCESS read-write
			STATUS current
			DESCRIPTION
				"Triple DES (3xDES) Transmit Encrypt Key #6. 
				The key length is 192 bits (24 Bytes or 48 HEX characters)."
			::= { cdmip3xDesConfig 8 }
		
		cdmipTransmitKey7 OBJECT-TYPE
			SYNTAX DisplayString (SIZE (48))
			MAX-ACCESS read-write
			STATUS current
			DESCRIPTION
				"Triple DES (3xDES) Transmit Encrypt Key #7. 
				The key length is 192 bits (24 Bytes or 48 HEX characters)."
			::= { cdmip3xDesConfig 9 }
		
		cdmipTransmitKey8 OBJECT-TYPE
			SYNTAX DisplayString (SIZE (48))
			MAX-ACCESS read-write
			STATUS current
			DESCRIPTION
				"Triple DES (3xDES) Transmit Encrypt Key #8. 
				The key length is 192 bits (24 Bytes or 48 HEX characters)."
			::= { cdmip3xDesConfig 10 }
		
		cdmipReceiveKey1 OBJECT-TYPE
			SYNTAX DisplayString (SIZE (48))
			MAX-ACCESS read-write
			STATUS current
			DESCRIPTION
				"Triple DES (3xDES) Receive Decrypt Key #1. 
				The key length is 192 bits (24 bytes or 48 HEX characters)."
			::= { cdmip3xDesConfig 11 }
		
		cdmipReceiveKey2 OBJECT-TYPE
			SYNTAX DisplayString (SIZE (48))
			MAX-ACCESS read-write
			STATUS current
			DESCRIPTION
				"Triple DES (3xDES) Receive Decrypt Key #2. 
				The key length is 192 bits (24 bytes or 48 HEX characters)."
			::= { cdmip3xDesConfig 12 }
		
		cdmipReceiveKey3 OBJECT-TYPE
			SYNTAX DisplayString (SIZE (48))
			MAX-ACCESS read-write
			STATUS current
			DESCRIPTION
				"Triple DES (3xDES) Receive Decrypt Key #3. 
				The key length is 192 bits (24 Bytes or 48 HEX characters)."
			::= { cdmip3xDesConfig 13 }
		
		cdmipReceiveKey4 OBJECT-TYPE
			SYNTAX DisplayString (SIZE (48))
			MAX-ACCESS read-write
			STATUS current
			DESCRIPTION
				"Triple DES (3xDES) Receive Decrypt Key #4. 
				The key length is 192 bits (24 Bytes or 48 HEX characters)."
			::= { cdmip3xDesConfig 14 }
		
		cdmipReceiveKey5 OBJECT-TYPE
			SYNTAX DisplayString (SIZE (48))
			MAX-ACCESS read-write
			STATUS current
			DESCRIPTION
				"Triple DES (3xDES) Receive Decrypt Key #5. 
				The key length is 192 bits (24 Bytes or 48 HEX characters)."
			::= { cdmip3xDesConfig 15 }
		
		cdmipReceiveKey6 OBJECT-TYPE
			SYNTAX DisplayString (SIZE (48))
			MAX-ACCESS read-write
			STATUS current
			DESCRIPTION
				"Triple DES (3xDES) Receive Decrypt Key #6. 
				The key length is 192 bits (24 Bytes or 48 HEX characters)."
			::= { cdmip3xDesConfig 16 }
		
		cdmipReceiveKey7 OBJECT-TYPE
			SYNTAX DisplayString (SIZE (48))
			MAX-ACCESS read-write
			STATUS current
			DESCRIPTION
				"Triple DES (3xDES) Receive Decrypt Key #7. 
				The key length is 192 bits (24 Bytes or 48 HEX characters)."
			::= { cdmip3xDesConfig 17 }
		
		cdmipReceiveKey8 OBJECT-TYPE
			SYNTAX DisplayString (SIZE (48))
			MAX-ACCESS read-write
			STATUS current
			DESCRIPTION
				"Triple DES (3xDES) Receive Decrypt Key #8. 
				The key length is 192 bits (24 Bytes or 48 HEX characters)."
			::= { cdmip3xDesConfig 18 }
		
		cdmipSmtp OBJECT IDENTIFIER ::= { cdmipAdministration 8 }
		
		cdmipSmtpServerIpAddress OBJECT-TYPE
			SYNTAX IpAddress
			MAX-ACCESS read-write
			STATUS current
			DESCRIPTION
				"IP address of the SMTP server on your local LAN."
			::= { cdmipSmtp 1 }
		
		cdmipSmtpDomain OBJECT-TYPE
			SYNTAX DisplayString
			MAX-ACCESS read-write
			STATUS current
			DESCRIPTION
				"SMTP Domain (i.e. comtechefdata.com)"
			::= { cdmipSmtp 2 }
		
		cdmipSmtpDestinationName OBJECT-TYPE
			SYNTAX DisplayString
			MAX-ACCESS read-write
			STATUS current
			DESCRIPTION
				"SMTP Destination Email User Name (i.e. cdmipsupport)"
			::= { cdmipSmtp 3 }
		
		cdmipSnmp OBJECT IDENTIFIER ::= { cdmipAdministration 9 }
		
		cdmipSnmpTrapDestinationIpAddress OBJECT-TYPE
			SYNTAX IpAddress
			MAX-ACCESS read-write
			STATUS current
			DESCRIPTION
				"SNMP Trap Destination #1:
				The primary IP Address to which trap will be sent."
			::= { cdmipSnmp 1 }
		
		cdmipSnmpTrapCommunity OBJECT-TYPE
			SYNTAX DisplayString
			MAX-ACCESS read-write
			STATUS current
			DESCRIPTION
				"The trap community string to be used for SNMP trap messages."
			::= { cdmipSnmp 2 }
		
		cdmipSnmpTrapVersion OBJECT-TYPE
			SYNTAX INTEGER
				{
				snmpV1(1),
				snmpV2(2)
				}
			MAX-ACCESS read-write
			STATUS current
			DESCRIPTION
				"The SNMP Trap Version:
				Use V1 for SNMP Version 1 Traps.
				Use V2 for SNMP Version 2 Notifications."
			::= { cdmipSnmp 3 }
		
		cdmipSnmpAuthenticationFailureCommunity OBJECT-TYPE
			SYNTAX DisplayString
			MAX-ACCESS accessible-for-notify
			STATUS current
			DESCRIPTION
				"NOTE: Used ONLY in the Authentification Failure Trap (No access).
				The community string which was invalid for a SET or GET SNMP message."
			::= { cdmipSnmp 4 }
		
		cdmipSnmpAuthenticationFailureAddress OBJECT-TYPE
			SYNTAX IpAddress
			MAX-ACCESS accessible-for-notify
			STATUS current
			DESCRIPTION
				"NOTE: Used ONLY in the Authentification Failure Trap (No access).
				IP Address which sent an SNMP message with an invalid 
				SET or GET community string."
			::= { cdmipSnmp 5 }
		
		cdmipSnmpTrapDestinationIpAddress2 OBJECT-TYPE
			SYNTAX IpAddress
			MAX-ACCESS read-write
			STATUS current
			DESCRIPTION
				"SNMP Trap Destination #2:
				The secondary IP Address to which traps will be sent."
			::= { cdmipSnmp 6 }
		
		cdmipWorkingMode OBJECT-TYPE
			SYNTAX INTEGER
				{
				routerSmallNetworkMode(1),
				routerLargeNetworkMode(2),
				routerPointToPointMode(3),
				routerVipersatMode(4),
				easyConnectMode(5)
				}
			MAX-ACCESS read-write
			STATUS current
			DESCRIPTION
				"Configure the IP Card's working mode. 
				The CDM-IP can operate in any of these modes.
				1. Router - Small Network Mode:
				     The system functions as router and uses the route table to 
				     determine how to forward packets in a small network HDLC 
				     address mode. The HDLC packet uses a 1 byte HDLC address.  
				     The valid values are from 1 to 254 (0x1 - 0xFE).
				2. Router - Large Network Mode:
				     The system functions as router and uses the route table to 
				     determine how to forward packets in a large network HDLC 
				     address mode. The HDLC packet uses a 2- byte HDLC address.  
				     The valid values are from 1 to 32766 (0x1 - 0x7FFE).
				3. Router - Point to Point - 	
				     The system functions as router and uses the route table to 
				     determine how to forward packets in a point-to-point HDLC 
				     address mode. 
				     The HDLC packet does not use a HDLC address.
				4. Router - Vipersat Mode - The system functions in Vipersat mode.
				5. EasyConnect mode - The system forwards all packets it receives. 
				     The HDLC packet does not use a HDLC address.
				
				
				***  IMPORTANT NOTE ***
				Changing Working mode requires the system to reboot.
				System configuration is saved before rebooting.
				
				Please make sure you are setting the correct value.
				"
			::= { cdmipAdministration 10 }
		
		cdmipEasyconnectMulticastOption OBJECT-TYPE
			SYNTAX EnableDisable
			MAX-ACCESS read-write
			STATUS current
			DESCRIPTION
				"Enable/Disable the Easyconnect multicast option.
				Enabling this option allows the modem working in 
				EasyConnect operation to pass multicast traffic."
			::= { cdmipAdministration 11 }
		
		cdmipHdrcompRefreshRateUdpRtp1 OBJECT-TYPE
			SYNTAX INTEGER (1..600)
			MAX-ACCESS read-write
			STATUS current
			DESCRIPTION
				"Header compression Refresh Rate for UDP/RTP1.
				Valid range is 1 - 600 packets per full 
				IP/UDP/RTP Header."
			::= { cdmipAdministration 12 }
		
		cdmipHdrcompRefreshRateUdp OBJECT-TYPE
			SYNTAX INTEGER (1..600)
			MAX-ACCESS read-write
			STATUS current
			DESCRIPTION
				"Header Compression Refresh Rate for UDP.
				Valid range is 1 - 600 packets per full 
				IP/UDP Header."
			::= { cdmipAdministration 13 }
		
		cdmipHdrcompRefreshRateAllOther OBJECT-TYPE
			SYNTAX INTEGER (1..600)
			MAX-ACCESS read-write
			STATUS current
			DESCRIPTION
				"Header Compression Refresh Rate for all other protocols.
				Valid range is 1 - 600 packet per full IP Header."
			::= { cdmipAdministration 14 }
		
		cdmipPayloadCompRefreshRate OBJECT-TYPE
			SYNTAX INTEGER (1..600)
			MAX-ACCESS read-write
			STATUS current
			DESCRIPTION
				"Refresh rate for Payload Compression in packets.
				Valid range is 1 = 600 packets before a refresh
				ofthe payload compression algorithm is done."
			::= { cdmipAdministration 15 }
		
		cdmipInterfaces OBJECT IDENTIFIER ::= { cdmipController 3 }
		
		cdmipEthernetInterface OBJECT IDENTIFIER ::= { cdmipInterfaces 1 }
		
		cdmipEthernetMacAddress OBJECT-TYPE
			SYNTAX DisplayString (SIZE (12))
			MAX-ACCESS read-only
			STATUS current
			DESCRIPTION
				"The MAC address for the Ethernet interface."
			::= { cdmipEthernetInterface 1 }
		
		cdmipEthernetSpeed OBJECT-TYPE
			SYNTAX INTEGER
				{
				auto(1),
				halfDuplex10M(2),
				halfDuplex100M(3),
				fullDuplex10M(4),
				fullDuplex100M(5)
				}
			MAX-ACCESS read-write
			STATUS current
			DESCRIPTION
				"The speed and mode of the Ehternet interface:
				The valid settings are:
				1. Automatic.
				2. 10 Mbps - Half Duplex.
				3. 100 Mpbs - Half Duplex.
				4. 10 Mbps - Full Duplex.
				5. 100 Mbps - Full Duplex.  "
			::= { cdmipEthernetInterface 2 }
		
		cdmipEthernetIpAddress OBJECT-TYPE
			SYNTAX IpAddress
			MAX-ACCESS read-write
			STATUS current
			DESCRIPTION
				"The IP address for the Ethernet interface."
			::= { cdmipEthernetInterface 3 }
		
		cdmipEthernetSubnetPrefixLen OBJECT-TYPE
			SYNTAX INTEGER (8..30)
			MAX-ACCESS read-write
			STATUS current
			DESCRIPTION
				"The subnet mask prefix length for the Ethernet interface."
			::= { cdmipEthernetInterface 4 }
		
		cdmipSatelliteInterface OBJECT IDENTIFIER ::= { cdmipInterfaces 2 }
		
		cdmipSatelliteHdlcAddress1 OBJECT-TYPE
			SYNTAX INTEGER (1..65535)
			MAX-ACCESS read-write
			STATUS current
			DESCRIPTION
				"HDLC Channel Address #1 filtered by the HSR
				
				Valid values of HDLC address depends on the Network mode.
				
				  In Small Network Mode - Frame will have 1 Byte of HDLC addr.
				                         valid values are 1 - 254. (0x1 - 0xFE)
				  In Large Network Mode - Frame will have 2 Bytes of HDLC address.
				                      valid values are 1 - 32766 (0x1 - 0x7FFE)
				
				  In Point-to-Point Mode - HDLC addresses are NOT-USED.
				
				An HDLC Address of '0(Zero)' is interpretted as NOT-DEFINED or NOT-USED
				
				An HDLC address cannot have 0x00 or 0xFF in least Significant Byte.
				i.e., 0x400 or 0x6ff or 0x11ff are NOT valid HDLC addresses.
				
				User is NOT allowed to configure HDLC address while system is
				operating in EASY CONNECT MODE.
				
				To Invalidate/Delete HDLC Address, set the MIB member
				'cdmipSatelliteHdlcAddressDelete' to the HDLC address number.
				HDLC Address number range from 1...4
				"
			::= { cdmipSatelliteInterface 5 }
		
		cdmipSatelliteHdlcAddress2 OBJECT-TYPE
			SYNTAX INTEGER (1..65535)
			MAX-ACCESS read-write
			STATUS current
			DESCRIPTION
				"HDLC Channel Address #2 filtered by the HSR
				
				Valid values of HDLC address depends on the Network mode.
				
				  In Small Network Mode - Frame will have 1 Byte of HDLC addr.
				                         valid values are 1 - 254. (0x1 - 0xFE)
				  In Large Network Mode - Frame will have 2 Bytes of HDLC address.
				                      valid values are 1 - 32766 (0x1 - 0x7FFE)
				
				  In Point-to-Point Mode - HDLC addresses are NOT-USED.
				
				An HDLC Address of '0(Zero)' is interpretted as NOT-DEFINED or NOT-USED
				
				An HDLC address cannot have 0x00 or 0xFF in least Significant Byte.
				i.e., 0x400 or 0x6ff or 0x11ff are NOT valid HDLC addresses.
				
				User is NOT allowed to configure HDLC address while system is
				operating in EASY CONNECT MODE.
				
				To Invalidate/Delete HDLC Address, set the MIB member
				'cdmipSatelliteHdlcAddressDelete' to the HDLC address number.
				HDLC Address number range from 1...4
				"
			::= { cdmipSatelliteInterface 6 }
		
		cdmipSatelliteHdlcAddress3 OBJECT-TYPE
			SYNTAX INTEGER (1..65535)
			MAX-ACCESS read-write
			STATUS current
			DESCRIPTION
				"HDLC Channel Address #3 filtered by the HSR
				
				Valid values of HDLC address depends on the Network mode.
				
				  In Small Network Mode - Frame will have 1 Byte of HDLC addr.
				                         valid values are 1 - 254. (0x1 - 0xFE)
				  In Large Network Mode - Frame will have 2 Bytes of HDLC address.
				                      valid values are 1 - 32766 (0x1 - 0x7FFE)
				
				  In Point-to-Point Mode - HDLC addresses are NOT-USED.
				
				An HDLC Address of '0(Zero)' is interpretted as NOT-DEFINED or NOT-USED
				
				An HDLC address cannot have 0x00 or 0xFF in least Significant Byte.
				i.e., 0x400 or 0x6ff or 0x11ff are NOT valid HDLC addresses.
				
				User is NOT allowed to configure HDLC address while system is
				operating in EASY CONNECT MODE.
				
				To Invalidate/Delete HDLC Address, set the MIB member
				'cdmipSatelliteHdlcAddressDelete' to the HDLC address number.
				HDLC Address number range from 1...4
				"
			::= { cdmipSatelliteInterface 7 }
		
		cdmipSatelliteHdlcAddress4 OBJECT-TYPE
			SYNTAX INTEGER (1..65535)
			MAX-ACCESS read-write
			STATUS current
			DESCRIPTION
				"HDLC Channel Address #4 filtered by the HSR
				
				Valid values of HDLC address depends on the Network mode.
				
				  In Small Network Mode - Frame will have 1 Byte of HDLC addr.
				                         valid values are 1 - 254. (0x1 - 0xFE)
				  In Large Network Mode - Frame will have 2 Bytes of HDLC address.
				                      valid values are 1 - 32766 (0x1 - 0x7FFE)
				
				  In Point-to-Point Mode - HDLC addresses are NOT-USED.
				
				An HDLC Address of '0(Zero)' is interpretted as NOT-DEFINED or NOT-USED
				
				An HDLC address cannot have 0x00 or 0xFF in least Significant Byte.
				i.e., 0x400 or 0x6ff or 0x11ff are NOT valid HDLC addresses.
				
				User is NOT allowed to configure HDLC address while system is
				operating in EASY CONNECT MODE.
				
				To Invalidate/Delete HDLC Address, set the MIB member
				'cdmipSatelliteHdlcAddressDelete' to the HDLC address number.
				HDLC Address number range from 1...4"
			::= { cdmipSatelliteInterface 8 }
		
		cdmipSatelliteHdlcAddressDelete OBJECT-TYPE
			SYNTAX INTEGER (1..4)
			MAX-ACCESS read-write
			STATUS current
			DESCRIPTION
				"Used to delete a specified HDLC Address. 
				Setting this entry to value 1...4 deletes/invalidates
				the corresponding HDLC Address. 
				1. for HDLCAddress #1
				2. for HDLCAddress #2
				3. for HDLCAddress #3
				4. for HDLCAddress #4
				
				When a HDLC Address is deleted/invalidated, it is displayed as
				'0' (NOT-DEFINED or NOT-USED) on SNMP Gets."
			::= { cdmipSatelliteInterface 9 }
		
		cdmipSatelliteHdlcAddressModeConfig OBJECT-TYPE
			SYNTAX INTEGER
				{
				smallNetworkMode(1),
				largeNetworkMode(2),
				pointToPointMode(3),
				vipersatMode(4)
				}
			MAX-ACCESS read-only
			STATUS current
			DESCRIPTION
				"The size of HDLC address used for frames sent over the satellite
				interface can range from 0 - 2 bytes. 
				
				This range allows the system to operate in one of these modes:
				1. Small Network Mode  - The frame will have 1 byte of HDLC address.
				                         Valid values are 1 - 254. (0x1 - 0xFE).
				2. Large Network Mode  - The frame will have 2 bytes of HDLC address.
				                         Valid values are 1 - 32767 (0x1 - 0x7FFE).
				3. Point-to-Point Mode - The frame does not use any HDLC address.
				4. Vipersat Mode       - The frame does not use any HDLC address."
			::= { cdmipSatelliteInterface 10 }
		
		cdmipRouteTable OBJECT IDENTIFIER ::= { cdmipController 4 }
		
-- cdmipIpRouteTable starts at child number "3"
		cdmipIpRouteTable OBJECT-TYPE
			SYNTAX SEQUENCE OF CdmipIpRouteEntry
			MAX-ACCESS not-accessible
			STATUS current
			DESCRIPTION
				"CDMIP IP Route Table"
			::= { cdmipRouteTable 3 }
		
		cdmipIpRouteEntry OBJECT-TYPE
			SYNTAX CdmipIpRouteEntry
			MAX-ACCESS not-accessible
			STATUS current
			DESCRIPTION
				"CDMIP IP Route Entry"
			INDEX { cdmipIpRouteIndex }
			::= { cdmipIpRouteTable 1 }
		
		CdmipIpRouteEntry ::=
			SEQUENCE { 
				cdmipIpRouteIndex
					INTEGER,
				cdmipIpRouteName
					DisplayString,
				cdmipIpRouteDestAddress
					IpAddress,
				cdmipIpRouteDestMaskLen
					INTEGER,
				cdmipIpRouteNextHopAddress
					IpAddress,
				cdmipIpRouteMulticastOptions
					INTEGER,
				cdmipIpRouteState
					INTEGER,
				cdmipIpRouteHdlcAddress
					INTEGER,
				cdmipIpRouteHdrComp
					EnableDisable,
				cdmipIpRoutePayloadComp
					EnableDisable,
				cdmipIpRoute3xDes
					EnableDisable,
				cdmipIpRouteDesKey
					INTEGER,
				cdmipIpRouteRowStatus
					INTEGER
			 }

		cdmipIpRouteIndex OBJECT-TYPE
			SYNTAX INTEGER (1..1024)
			MAX-ACCESS read-write
			STATUS current
			DESCRIPTION
				"The index for the route table."
			::= { cdmipIpRouteEntry 1 }
		
		cdmipIpRouteName OBJECT-TYPE
			SYNTAX DisplayString
			MAX-ACCESS read-write
			STATUS current
			DESCRIPTION
				"The name for the route.  
				The route name must be unique."
			::= { cdmipIpRouteEntry 2 }
		
		cdmipIpRouteDestAddress OBJECT-TYPE
			SYNTAX IpAddress
			MAX-ACCESS read-write
			STATUS current
			DESCRIPTION
				"The destination IP address for the route.
				
				***Note***:
				Do not add multicast routes for Vipersat Multicast addresses."
			::= { cdmipIpRouteEntry 3 }
		
		cdmipIpRouteDestMaskLen OBJECT-TYPE
			SYNTAX INTEGER (0..32)
			MAX-ACCESS read-write
			STATUS current
			DESCRIPTION
				"The number of bits in the subnet mask for the destination IP address
				for the route."
			::= { cdmipIpRouteEntry 4 }
		
		cdmipIpRouteNextHopAddress OBJECT-TYPE
			SYNTAX IpAddress
			MAX-ACCESS read-write
			STATUS current
			DESCRIPTION
				"The Next Hop IP Address is valid only for routes destined to 
				the Ethernet interface.
				
				This IP address must be a locally attached router.
				
				Set 'cdmipIpRouteState' to 'toEthernet' state before
				setting 'cdmipIpRouteNextHopAddress'."
			::= { cdmipIpRouteEntry 5 }
		
		cdmipIpRouteMulticastOptions OBJECT-TYPE
			SYNTAX INTEGER
				{
				noRouting(1),
				ethToSatRouting(2),
				satToEthRouting(3),
				satToEthAndEthToSatRouting(4)
				}
			MAX-ACCESS read-write
			STATUS current
			DESCRIPTION
				"Configures how router should handle multicast traffic.
				
				Valid options are:
				1. Do not forward any multicast traffic (drop all).
				2. Forward multicast traffic from Ethernet to Satellite only.
				3. Forward multicast traffic from Satellite to Ethernet only.
				4. Forward multicast traffic in both directions."
			DEFVAL { 1 }
			::= { cdmipIpRouteEntry 6 }
		
		cdmipIpRouteState OBJECT-TYPE
			SYNTAX INTEGER
				{
				toSatellite(1),
				toEthernet(2)
				}
			MAX-ACCESS read-write
			STATUS current
			DESCRIPTION
				"The route state specifies the route's destination.
				
				The valid values are: 
				1. To Ethernet (route goes to Ethernet interface).
				2. To Satellite (route goes to Satellite interface)."
			::= { cdmipIpRouteEntry 7 }
		
		cdmipIpRouteHdlcAddress OBJECT-TYPE
			SYNTAX INTEGER (1..65535)
			MAX-ACCESS read-write
			STATUS current
			DESCRIPTION
				"The HDLC Address is valid only for routes destined to 
				the Satellite interface.
				
				This can also be viewed as the 'next-hop' identifier for 
				the route destined to satellite.
				
				The valid range of HDLC Address depends on Network mode.
				
				  1. Small Network mode -  1 - 254   (0x01 - 0xFE)
				  2. Large Network Mode -  1 - 32766 (0x01 - 0x7FFE)
				
				An HDLC Address cannot have 0x00 or 0xFF in Least 
				Significant Byte (LSB).
				
				Set 'cdmipIpRouteState' to 'toSatellite' state before
				setting 'cdmipIpRouteHdlcAddress'.
				"
			::= { cdmipIpRouteEntry 8 }
		
		cdmipIpRouteHdrComp OBJECT-TYPE
			SYNTAX EnableDisable
			MAX-ACCESS read-write
			STATUS current
			DESCRIPTION
				"Enable or disable IP header compression on this route.
				
				To Set this parameter, you need to have Header Compression Feature
				available on your modem.
				
				It may return 'commit_failed' if feature is not available on 
				modem.
				"
			::= { cdmipIpRouteEntry 9 }
		
		cdmipIpRoutePayloadComp OBJECT-TYPE
			SYNTAX EnableDisable
			MAX-ACCESS read-write
			STATUS current
			DESCRIPTION
				"Enable or disable payload compression on this route.
				
				To set this parameter, you need to have Datagram/Payload
				Compression feature available on your modem.
				
				It may return 'commit_failed' if feature is not available on 
				modem.
				
				"
			::= { cdmipIpRouteEntry 10 }
		
		cdmipIpRoute3xDes OBJECT-TYPE
			SYNTAX EnableDisable
			MAX-ACCESS read-write
			STATUS current
			DESCRIPTION
				"Enable or disable 3xDES [Triple DES Encryption] on this route.
				
				It may return 'commit_failed' if 3xDES feature is not available on 
				modem.
				"
			::= { cdmipIpRouteEntry 11 }
		
		cdmipIpRouteDesKey OBJECT-TYPE
			SYNTAX INTEGER
				{
				key1(1),
				key2(2),
				key3(3),
				key4(4),
				key5(5),
				key6(6),
				key7(7),
				key8(8),
				random(9),
				clear(10)
				}
			MAX-ACCESS read-write
			STATUS current
			DESCRIPTION
				"Pick which DES key to use for this route.
				
				The system supports 8 3xDES (Triple DES - 24 Byte Length) keys.
				This specifies the 3xDES key to be used for this flow.
				
				
				 1 - 8 for Key1 to Key8
				 9 - Randomly pick one of the 8 keys.
				10 - Clear"
			DEFVAL { 1 }
			::= { cdmipIpRouteEntry 12 }
		
		cdmipIpRouteRowStatus OBJECT-TYPE
			SYNTAX INTEGER
				{
				active(1),
				notInService(2),
				notReady(3),
				createAndGo(4),
				createAndWait(5),
				destroy(6)
				}
			MAX-ACCESS read-write
			STATUS current
			DESCRIPTION
				"In SMIv2 tables, the RowStatus textual convention is used to manage the creation and deletion of conceptual rows. This column has six defined values.
				
				active(1) - which indicates that the conceptual row with all column is available for use by the managed device
				notInService(2) - this row state is not yet supported
				notReady(3) - this row state is not yet supported
				createAndGo(4) - which is supplied by a manager wishing to create a new instance of a conceptual row and to have its status automatically set to active, making it available for use by the managed device.
				createAndWait(5) - this row create is not yet supported
				destroy(6) - which is supplied by a manager wishing to delete all of the instances associated with an existing conceptual row."
			::= { cdmipIpRouteEntry 13 }
		
		cdmipProtocols OBJECT IDENTIFIER ::= { cdmipController 5 }
		
		cdmipIgmpConfig OBJECT IDENTIFIER ::= { cdmipProtocols 1 }
		
		cdmipIgmpTable OBJECT-TYPE
			SYNTAX SEQUENCE OF CimIgmpEntry
			MAX-ACCESS not-accessible
			STATUS current
			DESCRIPTION
				"IGMP Table"
			::= { cdmipIgmpConfig 1 }
		
		cdmipIgmpEntry OBJECT-TYPE
			SYNTAX CimIgmpEntry
			MAX-ACCESS not-accessible
			STATUS current
			DESCRIPTION
				"IGMP Entry"
			INDEX { cdmipIgmpIndex }
			::= { cdmipIgmpTable 1 }
		
		CimIgmpEntry ::=
			SEQUENCE { 
				cdmipIgmpIndex
					INTEGER,
				cdmipIgmpTTL
					INTEGER,
				cdmipIgmpClientState
					INTEGER,
				cdmipIgmpSrc
					INTEGER,
				cdmipIgmpGroupIpAddress
					IpAddress
			 }

		cdmipIgmpIndex OBJECT-TYPE
			SYNTAX INTEGER (1..256)
			MAX-ACCESS read-only
			STATUS current
			DESCRIPTION
				"The index for the IGMP table."
			::= { cdmipIgmpEntry 1 }
		
		cdmipIgmpTTL OBJECT-TYPE
			SYNTAX INTEGER (0..255)
			MAX-ACCESS read-only
			STATUS current
			DESCRIPTION
				"The IGMP Time to live (TTL) for the multicast group."
			::= { cdmipIgmpEntry 2 }
		
		cdmipIgmpClientState OBJECT-TYPE
			SYNTAX INTEGER
				{
				idle(1),
				active(2),
				closing(3)
				}
			MAX-ACCESS read-only
			STATUS current
			DESCRIPTION
				"The current state of the multicast group.
				Possible states are:
				1. Idle.
				2. Active.
				3. Closing."
			::= { cdmipIgmpEntry 3 }
		
		cdmipIgmpSrc OBJECT-TYPE
			SYNTAX INTEGER
				{
				other(1),
				sat(2)
				}
			MAX-ACCESS read-only
			STATUS current
			DESCRIPTION
				"Show which interface the multicast group is coming from.
				
				Possible values are:
				1. Other - from the Ethernet interface.
				2. Sat - from the Satellite interface."
			::= { cdmipIgmpEntry 4 }
		
		cdmipIgmpGroupIpAddress OBJECT-TYPE
			SYNTAX IpAddress
			MAX-ACCESS read-only
			STATUS current
			DESCRIPTION
				"The multicast address for the IGMP group."
			::= { cdmipIgmpEntry 5 }
		
		cdmipIgmpReceiver OBJECT IDENTIFIER ::= { cdmipIgmpConfig 2 }
		
		cdmipIgmpEnable OBJECT-TYPE
			SYNTAX EnableDisable
			MAX-ACCESS read-only
			STATUS current
			DESCRIPTION
				"Enable or disable IGMP.
				
				1. IGMP is enabled.
				2. IGMP is disabled."
			::= { cdmipIgmpReceiver 1 }
		
		cdmipIgmpQueryPeriod OBJECT-TYPE
			SYNTAX INTEGER (1..600)
			MAX-ACCESS read-write
			STATUS current
			DESCRIPTION
				"Modem as IGMP Server: IGMP query period in seconds."
			::= { cdmipIgmpReceiver 2 }
		
		cdmipIgmpMaxRespTime OBJECT-TYPE
			SYNTAX INTEGER (1..600)
			MAX-ACCESS read-write
			STATUS current
			DESCRIPTION
				"Modem as Sever: IGMP max. response time in seconds."
			::= { cdmipIgmpReceiver 3 }
		
		cdmipIgmpMaxMissBeforeDrop OBJECT-TYPE
			SYNTAX INTEGER (1..30)
			MAX-ACCESS read-write
			STATUS current
			DESCRIPTION
				"Modem as Server: Number of missed responses before leaving an IGMP group."
			::= { cdmipIgmpReceiver 4 }
		
		cdmipIgmpTransmiter OBJECT IDENTIFIER ::= { cdmipIgmpConfig 3 }
		
		cdmipIgmpRecognizeQueries OBJECT-TYPE
			SYNTAX EnableDisable
			MAX-ACCESS read-write
			STATUS current
			DESCRIPTION
				"Modem as Client: Recognize IGMP Queries"
			::= { cdmipIgmpTransmiter 1 }
		
		cdmipIgmpVersionUnsolicitedReports OBJECT-TYPE
			SYNTAX INTEGER
				{
				v1(1),
				v2(2)
				}
			MAX-ACCESS read-write
			STATUS current
			DESCRIPTION
				"Modem as Client: IGMP Version used for Unsolicited Reports.
				
				Possible values are:
				1. Version 1.
				2. Version 2."
			::= { cdmipIgmpTransmiter 2 }
		
		cdmipIgmpForceAlertOption OBJECT-TYPE
			SYNTAX EnableDisable
			MAX-ACCESS read-write
			STATUS current
			DESCRIPTION
				"Modem as Client: Router Alert Option for V1 report."
			::= { cdmipIgmpTransmiter 3 }
		
		cdmipIgmpUnsolicitedReportInterval OBJECT-TYPE
			SYNTAX INTEGER (0..25)
			MAX-ACCESS read-write
			STATUS current
			DESCRIPTION
				"Modem as Client: Unsolicited Report Interval in seconds."
			::= { cdmipIgmpTransmiter 4 }
		
		cdmipDhcpRelayConfig OBJECT IDENTIFIER ::= { cdmipProtocols 2 }
		
		cdmipDhcpServerIpAddress OBJECT-TYPE
			SYNTAX IpAddress
			MAX-ACCESS read-write
			STATUS current
			DESCRIPTION
				"The IP address of the DHCP Server."
			::= { cdmipDhcpRelayConfig 1 }
		
		cdmipRedundancy OBJECT IDENTIFIER ::= { cdmipController 6 }
		
		cdmipCurrentRedundantState OBJECT-TYPE
			SYNTAX INTEGER
				{
				offLine(0),
				onLine(1)
				}
			MAX-ACCESS read-only
			STATUS current
			DESCRIPTION
				"The redundancy state of the modem. 
				
				1. OnLine - actively passing IP traffic.
				0. OffLine - in standby mode; no IP traffic."
			::= { cdmipRedundancy 1 }
		
		cdmipLocalUnitManagementIpAddress OBJECT-TYPE
			SYNTAX IpAddress
			MAX-ACCESS read-only
			STATUS current
			DESCRIPTION
				"The IP Address for management of the IP parameters (READ ONLY).
				
				***
				NOTE: This address is the same as the Ethernet IP address.
				***"
			::= { cdmipRedundancy 2 }
		
		cdmipRedundantUnitManagementIpAddress OBJECT-TYPE
			SYNTAX IpAddress
			MAX-ACCESS read-only
			STATUS current
			DESCRIPTION
				"The IP Address of the redundant unit (READ ONLY).
				
				***
				NOTE: This address is the same as other unit's Ethernet IP address.
				***
				
				"
			::= { cdmipRedundancy 3 }
		
		cdmipRedundantTrafficIpAddress OBJECT-TYPE
			SYNTAX IpAddress
			MAX-ACCESS read-write
			STATUS current
			DESCRIPTION
				"The IP address for traffic passing through the redundant pair of modem.
				This address is only active in the ONLINE modem.
				
				***
				NOTE: The traffic IP can only be set on the ONLINE unit.
				***"
			::= { cdmipRedundancy 4 }
		
		cdmipRedundantTrafficSubnetMaskLen OBJECT-TYPE
			SYNTAX INTEGER (8..32)
			MAX-ACCESS read-write
			STATUS current
			DESCRIPTION
				"The subnet mask prefix length for the traffic IP address.
				
				***
				NOTE: The traffic IP subnet mask can only be set on the ONLINE unit.
				***"
			::= { cdmipRedundancy 5 }
		
		cdmipForceUnitOffline OBJECT-TYPE
			SYNTAX INTEGER { force(1) }
			MAX-ACCESS read-write
			STATUS current
			DESCRIPTION
				"The allows the user to force a modem into standby mode.
				When a 'force' is executed the ONLINE unit goes to standby mode.
				Also, the OFFLINE unit now becomes active.
				
				***
				NOTE: A 'force' can only be executed on the ONLINE unit.
				***"
			::= { cdmipRedundancy 6 }
		
		cdmipOperMaint OBJECT IDENTIFIER ::= { cdmipController 7 }
		
		cdmipAppVersion OBJECT-TYPE
			SYNTAX DisplayString
			MAX-ACCESS read-only
			STATUS current
			DESCRIPTION
				"Displays the version information for the application image and FPGA images."
			::= { cdmipOperMaint 1 }
		
		cdmipSaveConfiguration OBJECT-TYPE
			SYNTAX INTEGER { save(1) }
			MAX-ACCESS read-write
			STATUS current
			DESCRIPTION
				"Setting this value to '1' will save the PARAM permanent storage.
				
				Only value:
				1. Save - save the PARAM to permanent storage.
				"
			::= { cdmipOperMaint 2 }
		
		cdmipReset OBJECT-TYPE
			SYNTAX INTEGER { reset(1) }
			MAX-ACCESS read-write
			STATUS current
			DESCRIPTION
				"Setting this value to '1' will reboot the IP card.
				
				Only value:
				1. Rest - reboot the IP card."
			::= { cdmipOperMaint 3 }
		
-- cdmipRestoreFactoryDefaults starts at child number "5"
		cdmipRestoreFactoryDefaults OBJECT-TYPE
			SYNTAX INTEGER { restore(1) }
			MAX-ACCESS read-write
			STATUS current
			DESCRIPTION
				"Setting this value to '1' will restore factory defaults to the system.
				
				Only value:
				1. Restore - restore factory defaults.
				
				***
				NOTE: Restoring factory defaults will erase PARAM in permanent storage.
				Make sure, before setting this to True.
				***"
			::= { cdmipOperMaint 5 }
		
		cdmipLoadParamsFromStorage OBJECT-TYPE
			SYNTAX INTEGER { load(1) }
			MAX-ACCESS read-write
			STATUS current
			DESCRIPTION
				"Setting the value to '1' will load the PARAM from the permanent storage.
				
				Only value:
				1. Load - load PARAM from permanent storage."
			::= { cdmipOperMaint 6 }
		
		cdmipIPModuleBootFrom OBJECT-TYPE
			SYNTAX INTEGER
				{
				latest(0),
				image1(1),
				image2(2)
				}
			MAX-ACCESS read-write
			STATUS current
			DESCRIPTION
				"Setting this parameter lets the IP Module to boot 
				from a specified image. 
				
				0. Latest  - boots with the image that has the latest 
				             timestamp (date and time).
				1. Image 1 - boots with the image stored in Image 1.
				2. Image 2 - boots with the image stored in Image 2."
			::= { cdmipOperMaint 7 }
		
		cdmipUpgradeTo OBJECT-TYPE
			SYNTAX INTEGER
				{
				oldest(0),
				image1(1),
				image2(2)
				}
			MAX-ACCESS read-write
			STATUS current
			DESCRIPTION
				"Setting this parameter specifies Image to overwrite with 
				the new upgraded image. 
				
				0. Oldest - Saves the new upgrade image over the image 
				            that has the oldest timestamp (date and time).
				1. Image1  - Saves the new upgrade image into Image #1.
				2. Image2  - Saves the new upgrade image into Image #2.
				
				
				***
				NOTE: This parameter must be set before performing an upgrade.
				***"
			::= { cdmipOperMaint 8 }
		
		cdmipParamConfig OBJECT-TYPE
			SYNTAX INTEGER
				{
				factoryDefaults(1),
				paramFile(2)
				}
			MAX-ACCESS read-write
			STATUS current
			DESCRIPTION
				"Setting this parameter tells how the IP card will get its
				configuration data when booting up:
				
				Configuration data can be loaded from the following locations:
				1. Factory Defaultls - load data from factory defaults.
				2. PARAM File        - load data from PARAM in permanent storage."
			::= { cdmipOperMaint 9 }
		
		cdmipUnitInformation OBJECT IDENTIFIER ::= { cdmipOperMaint 10 }
		
		cdmipBootImageInfo OBJECT-TYPE
			SYNTAX DisplayString
			MAX-ACCESS read-only
			STATUS current
			DESCRIPTION
				"Displays version information for bootrom image."
			::= { cdmipUnitInformation 1 }
		
		cdmipAppImage1Info OBJECT-TYPE
			SYNTAX DisplayString
			MAX-ACCESS read-only
			STATUS current
			DESCRIPTION
				"Displays version information for application image in slot #1."
			::= { cdmipUnitInformation 2 }
		
		cdmipAppImage2Info OBJECT-TYPE
			SYNTAX DisplayString
			MAX-ACCESS read-only
			STATUS current
			DESCRIPTION
				"Displays version information for application image in slot #2."
			::= { cdmipUnitInformation 3 }
		
		cdmipFramerVersion OBJECT-TYPE
			SYNTAX INTEGER
				{
				framer1(1),
				framer2(2)
				}
			MAX-ACCESS read-only
			STATUS current
			DESCRIPTION
				"Displays version information for framer installed in the IP card."
			::= { cdmipUnitInformation 4 }
		
		cdmipBaseModemBootFrom OBJECT-TYPE
			SYNTAX INTEGER
				{
				latest(0),
				image1(1),
				image2(2)
				}
			MAX-ACCESS read-write
			STATUS current
			DESCRIPTION
				"Setting this parameter lets the Base Modem boot 
				from a specified image. 
				
				0. Latest  - boots with the Base Modem image that has the latest 
				             timestamp (date and time).
				1. Image 1 - boots with the Base Modem image stored in Image 1.
				2. Image 2 - boots with the Base Modem image stored in Image 2."
			::= { cdmipOperMaint 11 }
		
		cdmipStatistics OBJECT IDENTIFIER ::= { cdmipController 8 }
		
		cdmipEthernetStatistics OBJECT IDENTIFIER ::= { cdmipStatistics 1 }
		
		cdmipEtherTransmitGoodFrames OBJECT-TYPE
			SYNTAX Counter32
			MAX-ACCESS read-only
			STATUS current
			DESCRIPTION
				"The number of transmitted good frames from the Ethernet interface."
			::= { cdmipEthernetStatistics 1 }
		
		cdmipEtherTransmitMaxCollisionCount OBJECT-TYPE
			SYNTAX Counter32
			MAX-ACCESS read-only
			STATUS current
			DESCRIPTION
				"The number of frames that were NOT transmitted because they
				encountered maximum configured collisions. This counter should
				only increment when network is heavily saturated with traffic."
			::= { cdmipEthernetStatistics 2 }
		
		cdmipEtherTransmitLateCollisionCount OBJECT-TYPE
			SYNTAX Counter32
			MAX-ACCESS read-only
			STATUS current
			DESCRIPTION
				"The number of frames that were NOT transmitted because they
				encountered a collision outside the normal collision window."
			::= { cdmipEthernetStatistics 3 }
		
		cdmipEtherTransmitDMAUnderrunCount OBJECT-TYPE
			SYNTAX Counter32
			MAX-ACCESS read-only
			STATUS current
			DESCRIPTION
				"The number of frames that were either NOT transmitted OR retransmitted 
				due to transmit DMA underrun. Underruns occur due to lack of PCI 
				bandwidth resulting in the internal transmit FIFO running 
				dry during the transmission of a frame.
				"
			::= { cdmipEthernetStatistics 4 }
		
		cdmipEtherTransmitLostCarrierSenseCount OBJECT-TYPE
			SYNTAX Counter32
			MAX-ACCESS read-only
			STATUS current
			DESCRIPTION
				"The number of frames transmitted by the device despite the fact 
				that it detected the de-assertion of Transmit Lost Carrier 
				Sense (CRS) during the transmission."
			::= { cdmipEthernetStatistics 5 }
		
		cdmipEtherTransmitDeferredCount OBJECT-TYPE
			SYNTAX Counter32
			MAX-ACCESS read-only
			STATUS current
			DESCRIPTION
				"The number of frames deferred before transmission due to 
				activity on the link.
				"
			::= { cdmipEthernetStatistics 6 }
		
		cdmipEtherTransmitSingleCollisionCount OBJECT-TYPE
			SYNTAX Counter32
			MAX-ACCESS read-only
			STATUS current
			DESCRIPTION
				"The number of transmitted frames that encountered only 
				one collision."
			::= { cdmipEthernetStatistics 7 }
		
		cdmipEtherTransmitMultipleCollisionCount OBJECT-TYPE
			SYNTAX Counter32
			MAX-ACCESS read-only
			STATUS current
			DESCRIPTION
				"The number of transmitted frames that encountered more than one
				collision."
			::= { cdmipEthernetStatistics 8 }
		
		cdmipEtherTransmitTotalCollisionCount OBJECT-TYPE
			SYNTAX Counter32
			MAX-ACCESS read-only
			STATUS current
			DESCRIPTION
				"This counter contains the total number of collisions that were
				encountered while attempting to transmit. This count includes
				late collisions and collisions from frames that encountered
				maximum collisions."
			::= { cdmipEthernetStatistics 9 }
		
		cdmipEtherReceiveGoodFrames OBJECT-TYPE
			SYNTAX Counter32
			MAX-ACCESS read-only
			STATUS current
			DESCRIPTION
				"The number of frames properly received from the link. It is updated
				only after actual reception from the link is completed and all
				data bytes are stored in memory.
				"
			::= { cdmipEthernetStatistics 10 }
		
		cdmipEtherReceiveCRCErrorFrameCount OBJECT-TYPE
			SYNTAX Counter32
			MAX-ACCESS read-only
			STATUS current
			DESCRIPTION
				"The number of aligned frames discarded due to a CRC error."
			::= { cdmipEthernetStatistics 11 }
		
		cdmipEtherReceiveAllignErrorCount OBJECT-TYPE
			SYNTAX Counter32
			MAX-ACCESS read-only
			STATUS current
			DESCRIPTION
				"The number of frames that are both misaligned [in other words, CRS 
				de-asserts on a non-octet boundary] and contain a CRC error."
			::= { cdmipEthernetStatistics 12 }
		
		cdmipEtherReceiveResourceErrorCount OBJECT-TYPE
			SYNTAX Counter32
			MAX-ACCESS read-only
			STATUS current
			DESCRIPTION
				"The number of good frames discarded to unavailable resources."
			::= { cdmipEthernetStatistics 13 }
		
		cdmipEtherReceiveFifoOverrunErrorCount OBJECT-TYPE
			SYNTAX Counter32
			MAX-ACCESS read-only
			STATUS current
			DESCRIPTION
				"The number of frames known to be lost because the internal receive
				FIFO overflowed [also known as receive overrun]. This can occur if
				the device is unable to get necessary PCI bandwidth. If the 
				overflow condition persists for more than one frame, the frames
				that follow the first can also be lost.
				
				A frame that was counted as an overrun will not be counted in
				other error counters, like short frames, misaligned, or CRC error."
			::= { cdmipEthernetStatistics 14 }
		
		cdmipEtherReceiveCollisionDetectErrorCount OBJECT-TYPE
			SYNTAX Counter32
			MAX-ACCESS read-only
			STATUS current
			DESCRIPTION
				"The number of frames that encountered a collision during reception.
				
				This counter is always zero on the 82559 Ethernet chip."
			::= { cdmipEthernetStatistics 15 }
		
		cdmipEtherReceiveShortFrameCount OBJECT-TYPE
			SYNTAX Counter32
			MAX-ACCESS read-only
			STATUS current
			DESCRIPTION
				"The number of received frames that are shorter than the minimum frame
				length."
			::= { cdmipEthernetStatistics 16 }
		
		cdmipEtherTransmitFlowControlPauseFrames OBJECT-TYPE
			SYNTAX Counter32
			MAX-ACCESS read-only
			STATUS current
			DESCRIPTION
				"The number of flow control frames transmitted by the device. This 
				count includes both the XOFF and XON frames transmitted by the 
				device.
				"
			::= { cdmipEthernetStatistics 17 }
		
		cdmipEtherReceiveFlowControlPauseFrames OBJECT-TYPE
			SYNTAX Counter32
			MAX-ACCESS read-only
			STATUS current
			DESCRIPTION
				"The number of flow control frames received by the device. This count
				includes both XOFF and XON frames received.
				"
			::= { cdmipEthernetStatistics 18 }
		
		cdmipEtherResetCounters OBJECT-TYPE
			SYNTAX INTEGER { reset(1) }
			MAX-ACCESS read-write
			STATUS current
			DESCRIPTION
				"Setting this parameter to '1' will reset all Ethernet transmit 
				and receive counters."
			::= { cdmipEthernetStatistics 19 }
		
		cdmipIpRoutingStatistics OBJECT IDENTIFIER ::= { cdmipStatistics 3 }
		
		cdmipTotalIpPacketsFromSatellite OBJECT-TYPE
			SYNTAX Counter32
			MAX-ACCESS read-only
			STATUS current
			DESCRIPTION
				"The total number of IP packets received from the Satellite interface."
			::= { cdmipIpRoutingStatistics 1 }
		
		cdmipTotalIpPacketsRoutedToSatellite OBJECT-TYPE
			SYNTAX Counter32
			MAX-ACCESS read-only
			STATUS current
			DESCRIPTION
				"The total number of IP packets sent to the Satellite interface."
			::= { cdmipIpRoutingStatistics 2 }
		
		cdmipTotalIpPacketsFromEthernet OBJECT-TYPE
			SYNTAX Counter32
			MAX-ACCESS read-only
			STATUS current
			DESCRIPTION
				"The total number of IP packets received from the Ethernet interface."
			::= { cdmipIpRoutingStatistics 3 }
		
		cdmipTotalIpPacketsRoutedToEthernet OBJECT-TYPE
			SYNTAX Counter32
			MAX-ACCESS read-only
			STATUS current
			DESCRIPTION
				"The total number of IP packets sent to the Ethernet interface."
			::= { cdmipIpRoutingStatistics 4 }
		
		cdmipIgmpPacketsReceived OBJECT-TYPE
			SYNTAX Counter32
			MAX-ACCESS read-only
			STATUS current
			DESCRIPTION
				"The total number of multicast IGMP packets received from any interface."
			::= { cdmipIpRoutingStatistics 10 }
		
		cdmipIpOptionPacketsReceived OBJECT-TYPE
			SYNTAX Counter32
			MAX-ACCESS read-only
			STATUS current
			DESCRIPTION
				"The total number of packets received with IP options in the header."
			::= { cdmipIpRoutingStatistics 11 }
		
		cdmipDroppedPacketsTotal OBJECT-TYPE
			SYNTAX Counter32
			MAX-ACCESS read-only
			STATUS current
			DESCRIPTION
				"The total number of packets dropped for any reason."
			::= { cdmipIpRoutingStatistics 12 }
		
		cdmipDroppedPacketsTTLExpired OBJECT-TYPE
			SYNTAX Counter32
			MAX-ACCESS read-only
			STATUS current
			DESCRIPTION
				"The total number of packets dropped because TTL (time to live) expired."
			::= { cdmipIpRoutingStatistics 13 }
		
		cdmipDroppedPacketsBadIpHeader OBJECT-TYPE
			SYNTAX Counter32
			MAX-ACCESS read-only
			STATUS current
			DESCRIPTION
				"The total number of packets dropped because of a bad IP header checksum."
			::= { cdmipIpRoutingStatistics 14 }
		
		cdmipDroppedPacketsNoRoute OBJECT-TYPE
			SYNTAX Counter32
			MAX-ACCESS read-only
			STATUS current
			DESCRIPTION
				"The total number of packets dropped because of no route."
			::= { cdmipIpRoutingStatistics 15 }
		
		cdmipDroppedPacketsMulticast OBJECT-TYPE
			SYNTAX Counter32
			MAX-ACCESS read-only
			STATUS current
			DESCRIPTION
				"The number of multicast packets dropped because of 'Satellite 
				to Ethernet Option' is disabled."
			::= { cdmipIpRoutingStatistics 16 }
		
		cdmipDroppedPacketsFiltered OBJECT-TYPE
			SYNTAX Counter32
			MAX-ACCESS read-only
			STATUS current
			DESCRIPTION
				"The number of packets dropped because of a software decision."
			::= { cdmipIpRoutingStatistics 17 }
		
		cdmipDroppedPacketsMulticastDisableGroup OBJECT-TYPE
			SYNTAX Counter32
			MAX-ACCESS read-only
			STATUS current
			DESCRIPTION
				"The number of multicast packets dropped because the IGMP multicast group 
				is disabled."
			::= { cdmipIpRoutingStatistics 18 }
		
		cdmipDroppedPacketsNoArpEntry OBJECT-TYPE
			SYNTAX Counter32
			MAX-ACCESS read-only
			STATUS current
			DESCRIPTION
				"The number of packets dropped because there is no ARP entry in the 
				ARP table."
			::= { cdmipIpRoutingStatistics 19 }
		
		cdmipDroppedPacketsBadBufferLength OBJECT-TYPE
			SYNTAX Counter32
			MAX-ACCESS read-only
			STATUS current
			DESCRIPTION
				"The number of packets dropped because of a bad buffer length."
			::= { cdmipIpRoutingStatistics 20 }
		
		cdmipDroppedPacketsBadIpVersion OBJECT-TYPE
			SYNTAX Counter32
			MAX-ACCESS read-only
			STATUS current
			DESCRIPTION
				"The number of packets dropped because of an unsupported IP 
				version (i.e. V6)."
			::= { cdmipIpRoutingStatistics 21 }
		
		cdmipDroppedPacketsQosFilterRule OBJECT-TYPE
			SYNTAX Counter32
			MAX-ACCESS read-only
			STATUS current
			DESCRIPTION
				"The number of packets filtered because of the 'Filter' flag on a
				QoS rule."
			::= { cdmipIpRoutingStatistics 22 }
		
		cdmipDroppedPacketsEasyConnectMulticastOption OBJECT-TYPE
			SYNTAX Counter32
			MAX-ACCESS read-only
			STATUS current
			DESCRIPTION
				"The number of multicast packets dropped in EasyConnect mode
				because the Multicast Option is disabled."
			::= { cdmipIpRoutingStatistics 23 }
		
		cdmipDroppedPacketsRouterQueueFull OBJECT-TYPE
			SYNTAX Counter32
			MAX-ACCESS read-only
			STATUS current
			DESCRIPTION
				"The total number of packets dropped because router queue is full."
			::= { cdmipIpRoutingStatistics 24 }
		
		cdmipResetCounters OBJECT-TYPE
			SYNTAX INTEGER { reset(1) }
			MAX-ACCESS read-write
			STATUS current
			DESCRIPTION
				"Setting this parameter to '1' will clear all IP routing, WAN, 
				and Ethernet statistics."
			::= { cdmipIpRoutingStatistics 26 }
		
		cdmipQosStatistics OBJECT IDENTIFIER ::= { cdmipStatistics 4 }
		
		cdmipQosStatisticsTable OBJECT-TYPE
			SYNTAX SEQUENCE OF CimQosStatisticsEntry
			MAX-ACCESS not-accessible
			STATUS current
			DESCRIPTION
				"Description."
			::= { cdmipQosStatistics 1 }
		
		cdmipQosStatisticsEntry OBJECT-TYPE
			SYNTAX CimQosStatisticsEntry
			MAX-ACCESS not-accessible
			STATUS current
			DESCRIPTION
				"Description."
			INDEX { cdmipQosStatsQueueIndex }
			::= { cdmipQosStatisticsTable 1 }
		
		CimQosStatisticsEntry ::=
			SEQUENCE { 
				cdmipQosStatsQueueIndex
					INTEGER,
				cdmipQosStatsSentPackets
					Counter32,
				cdmipQosStatsSentPacketsPerSecond
					Counter32,
				cdmipQosStatsSentBytes
					Counter32,
				cdmipQosStatsDroppedPackets
					Counter32,
				cdmipQosStatsDroppedBytes
					Counter32,
				cdmipQosStatsCurrentTxRate
					Counter32,
				cdmipQosStatsAverageTxRate
					Counter32,
				cdmipQosStatsMaxTxRate
					Counter32,
				cdmipQosStatsActiveFlows
					Counter32,
				cdmipQosStatsResetCounters
					INTEGER
			 }

		cdmipQosStatsQueueIndex OBJECT-TYPE
			SYNTAX INTEGER (1..32)
			MAX-ACCESS read-only
			STATUS current
			DESCRIPTION
				"The index of the QoS rule for which stats are being displayed."
			::= { cdmipQosStatisticsEntry 1 }
		
		cdmipQosStatsSentPackets OBJECT-TYPE
			SYNTAX Counter32
			MAX-ACCESS read-only
			STATUS current
			DESCRIPTION
				"The total number of packets sent through this QoS queue."
			::= { cdmipQosStatisticsEntry 2 }
		
		cdmipQosStatsSentPacketsPerSecond OBJECT-TYPE
			SYNTAX Counter32
			MAX-ACCESS read-only
			STATUS current
			DESCRIPTION
				"The number of packets per second sent through this QoS queue."
			::= { cdmipQosStatisticsEntry 3 }
		
		cdmipQosStatsSentBytes OBJECT-TYPE
			SYNTAX Counter32
			MAX-ACCESS read-only
			STATUS current
			DESCRIPTION
				"The total number of bytes sent through this QoS queue."
			::= { cdmipQosStatisticsEntry 4 }
		
		cdmipQosStatsDroppedPackets OBJECT-TYPE
			SYNTAX Counter32
			MAX-ACCESS read-only
			STATUS current
			DESCRIPTION
				"The total number of packets dropped from this QoS queue."
			::= { cdmipQosStatisticsEntry 5 }
		
		cdmipQosStatsDroppedBytes OBJECT-TYPE
			SYNTAX Counter32
			MAX-ACCESS read-only
			STATUS current
			DESCRIPTION
				"The total number of bytes dropped from this QoS queue."
			::= { cdmipQosStatisticsEntry 6 }
		
		cdmipQosStatsCurrentTxRate OBJECT-TYPE
			SYNTAX Counter32
			MAX-ACCESS read-only
			STATUS current
			DESCRIPTION
				"The current Tx data rate associated with this QoS queue."
			::= { cdmipQosStatisticsEntry 7 }
		
		cdmipQosStatsAverageTxRate OBJECT-TYPE
			SYNTAX Counter32
			MAX-ACCESS read-only
			STATUS current
			DESCRIPTION
				"The average Tx data rate associated with this QoS queue."
			::= { cdmipQosStatisticsEntry 8 }
		
		cdmipQosStatsMaxTxRate OBJECT-TYPE
			SYNTAX Counter32
			MAX-ACCESS read-only
			STATUS current
			DESCRIPTION
				"The maximum Tx data rate associated with this QoS queue."
			::= { cdmipQosStatisticsEntry 9 }
		
		cdmipQosStatsActiveFlows OBJECT-TYPE
			SYNTAX Counter32
			MAX-ACCESS read-only
			STATUS current
			DESCRIPTION
				"The number of active flows associated with this QoS queue."
			::= { cdmipQosStatisticsEntry 10 }
		
		cdmipQosStatsResetCounters OBJECT-TYPE
			SYNTAX INTEGER { reset(1) }
			MAX-ACCESS read-write
			STATUS current
			DESCRIPTION
				"Setting this to '1' will reset all the statistics counters associated 
				with this QoS queue."
			::= { cdmipQosStatisticsEntry 11 }
		
		cdmipWanFpgaStatistics OBJECT IDENTIFIER ::= { cdmipStatistics 5 }
		
		cdmipWanFpgaRxBadAddrCount OBJECT-TYPE
			SYNTAX Counter32
			MAX-ACCESS read-only
			STATUS current
			DESCRIPTION
				"The number of received frames from the Satellite interface 
				that do not match any of the HDLC addresses or the broadcast address. 
				If 'frame bypass' is enabled, then non-matching frames are not 
				counted as having a bad address. "
			::= { cdmipWanFpgaStatistics 1 }
		
		cdmipWanFpgaRxPktProcessorCrcErrorCount OBJECT-TYPE
			SYNTAX Counter32
			MAX-ACCESS read-only
			STATUS current
			DESCRIPTION
				"The number of received frames from the Satellite interface 
				that failed the packet processor CRC check."
			::= { cdmipWanFpgaStatistics 2 }
		
		cdmipWanFpgaRxAbortOctetErrorCount OBJECT-TYPE
			SYNTAX Counter32
			MAX-ACCESS read-only
			STATUS current
			DESCRIPTION
				"The number of the aborted frames from the Satellite interface 
				plus the number of octet error frames.  An octet error is when 
				the received frame does not start on a byte boudary."
			::= { cdmipWanFpgaStatistics 3 }
		
		cdmipWanFpgaRxOverrunErrorCount OBJECT-TYPE
			SYNTAX Counter32
			MAX-ACCESS read-only
			STATUS current
			DESCRIPTION
				"The number of received frames from the Satellite interface 
				that exceeded a max. frame length of 2K bytes in length or 
				overflowed the HDLC buffer."
			::= { cdmipWanFpgaStatistics 4 }
		
		cdmipWanFpgaRxHdlcCrcErrorCount OBJECT-TYPE
			SYNTAX Counter32
			MAX-ACCESS read-only
			STATUS current
			DESCRIPTION
				"The number of received frames from the Satellite interface 
				that failed the HDLC CRC check."
			::= { cdmipWanFpgaStatistics 5 }
		
		cdmipWanFpgaRxHdlcPayLoadCount OBJECT-TYPE
			SYNTAX Counter32
			MAX-ACCESS read-only
			STATUS current
			DESCRIPTION
				"The count of payload bytes that were received over the Satellite interface,
				excluding any frame overhead."
			::= { cdmipWanFpgaStatistics 6 }
		
		cdmipWanFpgaRxHdlcHeaderCount OBJECT-TYPE
			SYNTAX Counter32
			MAX-ACCESS read-only
			STATUS current
			DESCRIPTION
				"The count of HDLC header bytes received over the Satellite interface,
				including control, HDLC address, Flow ID, and CRC."
			::= { cdmipWanFpgaStatistics 7 }
		
		cdmipWanFpgaRxHdlcPacketCount OBJECT-TYPE
			SYNTAX Counter32
			MAX-ACCESS read-only
			STATUS current
			DESCRIPTION
				"The number of frames received over the Satellite interface."
			::= { cdmipWanFpgaStatistics 8 }
		
		cdmipWanFpgaTxHdlcHeaderCount OBJECT-TYPE
			SYNTAX Counter32
			MAX-ACCESS read-only
			STATUS current
			DESCRIPTION
				"The number of HDLC header bytes transmitted over the Satellite interface.
				"
			::= { cdmipWanFpgaStatistics 9 }
		
		cdmipWanFpgaTxHdlcPayLoadCount OBJECT-TYPE
			SYNTAX Counter32
			MAX-ACCESS read-only
			STATUS current
			DESCRIPTION
				"The number of payload bytes transmitted over the Satellite interface.
				"
			::= { cdmipWanFpgaStatistics 10 }
		
		cdmipWanFpgaTxHdlcPacketCount OBJECT-TYPE
			SYNTAX Counter32
			MAX-ACCESS read-only
			STATUS current
			DESCRIPTION
				"The number of packets transmitted over the Satellite interface.
				"
			::= { cdmipWanFpgaStatistics 11 }
		
		cdmipWanFpgaResetAllCounters OBJECT-TYPE
			SYNTAX INTEGER { reset(1) }
			MAX-ACCESS read-write
			STATUS current
			DESCRIPTION
				"Setting this variable to 'reset' will reset all the WAN FPGA Rx & Tx
				counters."
			::= { cdmipWanFpgaStatistics 12 }
		
		cdmipWanFpgaWanUtilization OBJECT-TYPE
			SYNTAX INTEGER (0..100)
			UNITS "% (percentage)"
			MAX-ACCESS read-only
			STATUS current
			DESCRIPTION
				"The percentage (%) of Tx bandwidth that is being utilized."
			::= { cdmipWanFpgaStatistics 13 }
		
		cdmipWanFpgaLanToWanTraffic OBJECT-TYPE
			SYNTAX INTEGER (0..100000)
			UNITS "kbps"
			MAX-ACCESS read-only
			STATUS current
			DESCRIPTION
				"The data rate (Kbps) before IP header and payload compression of 
				Ethernet traffic destined for the Satellite interface."
			::= { cdmipWanFpgaStatistics 14 }
		
		cdmipWanFpgaActualWanTraffic OBJECT-TYPE
			SYNTAX INTEGER (0..5000)
			UNITS "kbps"
			MAX-ACCESS read-only
			STATUS current
			DESCRIPTION
				"The 'compressed' data rate (Kbps) after IP header and payload 
				compression of traffic transmitted on the Satellite interface."
			::= { cdmipWanFpgaStatistics 15 }
		
		cdmipWanFpgaWanBandwidthSaved OBJECT-TYPE
			SYNTAX INTEGER (0..100)
			UNITS "% (percentage)"
			MAX-ACCESS read-only
			STATUS current
			DESCRIPTION
				"The percentage (%) of Satellite bandwidth saved because of IP header
				and payload compression."
			::= { cdmipWanFpgaStatistics 16 }
		
		cdmipCompressionStatistics OBJECT IDENTIFIER ::= { cdmipStatistics 6 }
		
		cdmipCompressionStatisticsTable OBJECT-TYPE
			SYNTAX SEQUENCE OF CdmipCompressionStatisticsEntry
			MAX-ACCESS not-accessible
			STATUS current
			DESCRIPTION
				"Description."
			::= { cdmipCompressionStatistics 1 }
		
		cdmipCompressionStatisticsEntry OBJECT-TYPE
			SYNTAX CdmipCompressionStatisticsEntry
			MAX-ACCESS not-accessible
			STATUS current
			DESCRIPTION
				"Description."
			INDEX { cdmipHdrcompStatsQueueIndex }
			::= { cdmipCompressionStatisticsTable 1 }
		
		CdmipCompressionStatisticsEntry ::=
			SEQUENCE { 
				cdmipHdrcompStatsQueueIndex
					INTEGER,
				cdmipHdrcompStatsPreHdrcompBytes
					Counter32,
				cdmipHdrcompStatsPostHdrcompBytes
					Counter32,
				cdmipHdrcompRatio
					INTEGER,
				cdmipPayloadCompPrePayloadCompBytes
					Counter32,
				cdmipPayloadCompPostPayloadCompBytes
					Counter32,
				cdmipPayloadCompRatio
					INTEGER,
				cdmipCompStatsResetCounters
					INTEGER
			 }

		cdmipHdrcompStatsQueueIndex OBJECT-TYPE
			SYNTAX INTEGER (1..32)
			MAX-ACCESS read-only
			STATUS current
			DESCRIPTION
				"The index of the QoS queue for which the IP header compression stats 
				are being displayed."
			::= { cdmipCompressionStatisticsEntry 1 }
		
		cdmipHdrcompStatsPreHdrcompBytes OBJECT-TYPE
			SYNTAX Counter32
			MAX-ACCESS read-only
			STATUS current
			DESCRIPTION
				"The total number of bytes in all packets before IP header compression
				has been performed."
			::= { cdmipCompressionStatisticsEntry 2 }
		
		cdmipHdrcompStatsPostHdrcompBytes OBJECT-TYPE
			SYNTAX Counter32
			MAX-ACCESS read-only
			STATUS current
			DESCRIPTION
				"The total number of bytes in all 'compressed' packets after IP header 
				compression has been performed."
			::= { cdmipCompressionStatisticsEntry 3 }
		
		cdmipHdrcompRatio OBJECT-TYPE
			SYNTAX INTEGER (0..10000)
			MAX-ACCESS read-only
			STATUS current
			DESCRIPTION
				"The percentage (%) of saving gained by performing IP header compression
				on all packets destined for the Satellite interface.
				
				The percentage is then multiplied by 100 to make it an integer."
			::= { cdmipCompressionStatisticsEntry 4 }
		
		cdmipPayloadCompPrePayloadCompBytes OBJECT-TYPE
			SYNTAX Counter32
			MAX-ACCESS read-only
			STATUS current
			DESCRIPTION
				"The total number of bytes in all packets before payload compression 
				has been performed.
				
				To get the standard payload compression ratio in the form 1:x.xx
				
				        (Pre Payload Compression Bytes)
				x.xx =  -------------------------------
				        (Post Payload Compression Bytes)
				"
			::= { cdmipCompressionStatisticsEntry 5 }
		
		cdmipPayloadCompPostPayloadCompBytes OBJECT-TYPE
			SYNTAX Counter32
			MAX-ACCESS read-only
			STATUS current
			DESCRIPTION
				"The total number of bytes in all packets after payload compression
				has been performed.
				
				To get the standard payload compression ratio in the form 1:x.xx
				
				        (Pre Payload Compression Bytes)
				x.xx =  -------------------------------
				        (Post Payload Compression Bytes)"
			::= { cdmipCompressionStatisticsEntry 6 }
		
		cdmipPayloadCompRatio OBJECT-TYPE
			SYNTAX INTEGER (1..10000)
			MAX-ACCESS read-only
			STATUS current
			DESCRIPTION
				"This parameter is the standard payload compression ratio.
				
				To get the standard payload compression ratio in the form 1:x.xx
				
				          (Pre Payload Compression Bytes)
				  x.xx =  -------------------------------
				          (Post Payload Compression Bytes)
				
				The ratio is then converted into an integer by multiplying by 100."
			::= { cdmipCompressionStatisticsEntry 7 }
		
		cdmipCompStatsResetCounters OBJECT-TYPE
			SYNTAX INTEGER { reset(1) }
			MAX-ACCESS read-write
			STATUS current
			DESCRIPTION
				"Setting this to '1' will reset all IP header compression 
				and payload compression stats counters."
			::= { cdmipCompressionStatisticsEntry 8 }
		
		cdmipQosRules OBJECT IDENTIFIER ::= { cdmipController 9 }
		
-- cdmipQosRulesTable starts at child number "2"
		cdmipQosRulesTable OBJECT-TYPE
			SYNTAX SEQUENCE OF CdmipQosRulesEntry
			MAX-ACCESS not-accessible
			STATUS current
			DESCRIPTION
				"Description."
			::= { cdmipQosRules 2 }
		
		cdmipQosRulesEntry OBJECT-TYPE
			SYNTAX CdmipQosRulesEntry
			MAX-ACCESS not-accessible
			STATUS current
			DESCRIPTION
				"Description."
			INDEX { cdmipQosRulesIndex }
			::= { cdmipQosRulesTable 1 }
		
		CdmipQosRulesEntry ::=
			SEQUENCE { 
				cdmipQosRulesIndex
					INTEGER,
				cdmipQosRulesSrcIpAddr
					IpAddress,
				cdmipQosRulesSrcIpMaskLen
					INTEGER,
				cdmipQosRulesDstIpAddr
					IpAddress,
				cdmipQosRulesDstIpMaskLen
					INTEGER,
				cdmipQosRulesProtocol
					INTEGER,
				cdmipQosRulesSrcPortMin
					INTEGER,
				cdmipQosRulesSrcPortMax
					INTEGER,
				cdmipQosRulesDstPortMin
					INTEGER,
				cdmipQosRulesDstPortMax
					INTEGER,
				cdmipQosRulesMinBw
					INTEGER,
				cdmipQosRulesMaxBw
					INTEGER,
				cdmipQosRulesPriority
					INTEGER,
				cdmipQosRulesWred
					EnableDisable,
				cdmipQosRulesFilter
					EnableDisable,
				cdmipQosRulesRowStatus
					INTEGER
			 }

		cdmipQosRulesIndex OBJECT-TYPE
			SYNTAX INTEGER (1..32)
			MAX-ACCESS read-write
			STATUS current
			DESCRIPTION
				"The index for the QoS rule. 
				
				The valid values are 1 - 32."
			::= { cdmipQosRulesEntry 1 }
		
		cdmipQosRulesSrcIpAddr OBJECT-TYPE
			SYNTAX IpAddress
			MAX-ACCESS read-write
			STATUS current
			DESCRIPTION
				"The source IP address for the QoS rule."
			::= { cdmipQosRulesEntry 2 }
		
		cdmipQosRulesSrcIpMaskLen OBJECT-TYPE
			SYNTAX INTEGER (0..32)
			MAX-ACCESS read-write
			STATUS current
			DESCRIPTION
				"The source IP subnet mask length for the QoS rule."
			::= { cdmipQosRulesEntry 3 }
		
		cdmipQosRulesDstIpAddr OBJECT-TYPE
			SYNTAX IpAddress
			MAX-ACCESS read-write
			STATUS current
			DESCRIPTION
				"The destination IP address for the QoS rule."
			::= { cdmipQosRulesEntry 4 }
		
		cdmipQosRulesDstIpMaskLen OBJECT-TYPE
			SYNTAX INTEGER (0..32)
			MAX-ACCESS read-write
			STATUS current
			DESCRIPTION
				"The destination IP subnet mask length for the QoS rule."
			::= { cdmipQosRulesEntry 5 }
		
		cdmipQosRulesProtocol OBJECT-TYPE
			SYNTAX INTEGER
				{
				udp(1),
				tcp(2),
				icmp(3),
				rtp(4),
				rtpVoice(5),
				rtpVideo(6),
				rtpSignal(7),
				ftp(8),
				http(9),
				telnet(10),
				smtp(11),
				snmp(12),
				sap(13),
				oracle(14),
				citrix(15),
				sql(16),
				allIp(17),
				nonIp(18),
				all(19)
				}
			MAX-ACCESS read-write
			STATUS current
			DESCRIPTION
				"The protocol type for the QoS rule.
				
				Only the default rule is configured with 'All'. Setting
				protocol field to 'All' for other rules is not permitted,
				may result in 'wrong value'
				
				Setting the protocol to Non-IP would configure the QoS rule
				parameters to pre-set default values. User is only allowed to set
				max bandwidth, priority & filter flag for a Non-IP qos rule.
				
				User is not allowed to create/modify a rule with RTP Signaling
				protocol. The software does this.
				
				IMPORTANT: Configure rtpSignal rule for rtpVoice/rtpVideo rules."
			::= { cdmipQosRulesEntry 6 }
		
		cdmipQosRulesSrcPortMin OBJECT-TYPE
			SYNTAX INTEGER (0..65536)
			MAX-ACCESS read-write
			STATUS current
			DESCRIPTION
				"The starting UDP/TCP source port (minimum) for the QoS rule.
				
				A QoS rule can be configured with a port range of aaaa - bbbb by
				setting 'cdmipQosRulesSrcPortMin' to aaaa and 'cdmipQosRulesSrcPortMax' 
				to bbbb.
				
				***
				NOTE: Enter 65536 to match all ports.
				***"
			::= { cdmipQosRulesEntry 7 }
		
		cdmipQosRulesSrcPortMax OBJECT-TYPE
			SYNTAX INTEGER (0..65536)
			MAX-ACCESS read-write
			STATUS current
			DESCRIPTION
				"The ending UDP/TCP source port (maximum) for the QoS rule.
				
				A QoS rule can be configured with a port range of aaaa - bbbb by
				setting 'cdmipQosRulesSrcPortMin' to aaaa and 'cdmipQosRulesSrcPortMax' 
				to bbbb.
				
				***
				NOTE: Enter 65536 to match all ports.
				***"
			::= { cdmipQosRulesEntry 8 }
		
		cdmipQosRulesDstPortMin OBJECT-TYPE
			SYNTAX INTEGER (0..65536)
			MAX-ACCESS read-write
			STATUS current
			DESCRIPTION
				"The starting destination port number (minimum) for the QoS rule.
				
				A QoS rule can be configured with a port range of xxxx - yyyy by
				setting 'cdmipQosRulesDstPortMin' to xxxx and 'cdmipQosRulesDstPortMax' 
				to yyyy.
				
				***
				NOTE: Enter 65536 for match all ports.
				***"
			::= { cdmipQosRulesEntry 9 }
		
		cdmipQosRulesDstPortMax OBJECT-TYPE
			SYNTAX INTEGER (0..65536)
			MAX-ACCESS read-write
			STATUS current
			DESCRIPTION
				"The ending destination port number (maximum) for the QoS rule.
				
				A QoS rule can be configured with a port range of xxxx - yyyy by
				setting 'cdmipQosRulesDstPortMin' to xxxx and 'cdmipQosRulesDstPortMax' 
				to yyyy.
				
				***
				NOTE: Enter 65536 for match all ports.
				***"
			::= { cdmipQosRulesEntry 10 }
		
		cdmipQosRulesMinBw OBJECT-TYPE
			SYNTAX INTEGER (0..99999)
			UNITS "kbps"
			MAX-ACCESS read-write
			STATUS current
			DESCRIPTION
				"The minimum bandwidth (Kbps) for the QoS rule.
				
				***
				NOTE: Only valid for 'Minimum Bandwidth & Maximum Bandwidth' mode.
				***"
			::= { cdmipQosRulesEntry 11 }
		
		cdmipQosRulesMaxBw OBJECT-TYPE
			SYNTAX INTEGER (0..99999)
			UNITS "kbps"
			MAX-ACCESS read-write
			STATUS current
			DESCRIPTION
				"The maximum bandwidth (Kbps) for the QoS rule.
				
				***
				NOTE: Valid for both 'Maximum Bandwidth & Priority' and 'Minimum 
				Bandwidth & Maximum Bandwidth' modes.
				***"
			::= { cdmipQosRulesEntry 12 }
		
		cdmipQosRulesPriority OBJECT-TYPE
			SYNTAX INTEGER
				{
				priority1(1),
				priority2(2),
				priority3(3),
				priority4(4),
				priority5(5),
				priority6(6),
				priority7(7),
				priority8(8)
				}
			MAX-ACCESS read-write
			STATUS current
			DESCRIPTION
				"The priority for the QoS rule.
				
				The valid values are:
				Priority 1 - Highest
				Priority 2, 3, 4, 5, 6, 7 - Middle
				Priority 8 - Lowest
				
				***
				NOTE: Only valid for 'Maximum Bandwidth & Priority' mode.
				***"
			::= { cdmipQosRulesEntry 13 }
		
		cdmipQosRulesWred OBJECT-TYPE
			SYNTAX EnableDisable
			MAX-ACCESS read-write
			STATUS current
			DESCRIPTION
				"The WRED (Weighted Random Early Drop) option for the QoS rule.
				
				This is the mechanism by which packets are treated upon queue full.
				If this is enabled, the packets are dropped randomly upon detection 
				of queue full or queue getting full.
				"
			::= { cdmipQosRulesEntry 14 }
		
		cdmipQosRulesFilter OBJECT-TYPE
			SYNTAX EnableDisable
			MAX-ACCESS read-write
			STATUS current
			DESCRIPTION
				"The filter option for the QoS rule.
				
				***
				NOTE: This option will filter ALL packets associated with this QoS rule.
				***
				"
			::= { cdmipQosRulesEntry 15 }
		
		cdmipQosRulesRowStatus OBJECT-TYPE
			SYNTAX INTEGER
				{
				active(1),
				notInService(2),
				notReady(3),
				createAndGo(4),
				createAndWait(5),
				destroy(6)
				}
			MAX-ACCESS read-write
			STATUS current
			DESCRIPTION
				"In SMIv2 tables, the RowStatus textual convention is used to 
				manage the creation and deletion of conceptual rows. 
				
				This column has six defined values.
				
				active(1)        - which indicates that the conceptual row with all 
				                   column is available for use by the managed device.
				notInService(2)  - this row state is not yet supported.
				notReady(3)      - this row state is not yet supported.
				createAndGo(4)   - which is supplied by a manager wishing to create 
				                   a new instance of a conceptual row and to have its 
				                   status automatically set to active, making it 
				                   available for use by the managed device.
				createAndWait(5) - this row create is not yet supported
				destroy(6)       - which is supplied by a manager wishing to delete 
				                   all of the instances associated with an existing 
				                   conceptual row."
			::= { cdmipQosRulesEntry 16 }
		
		cdmipDiffServRulesTable OBJECT-TYPE
			SYNTAX SEQUENCE OF CdmipDiffServRulesEntry
			MAX-ACCESS not-accessible
			STATUS current
			DESCRIPTION
				"Differential Services (DiffServ) Rules Table."
			::= { cdmipQosRules 3 }
		
		cdmipDiffServRulesEntry OBJECT-TYPE
			SYNTAX CdmipDiffServRulesEntry
			MAX-ACCESS not-accessible
			STATUS current
			DESCRIPTION
				"Description."
			INDEX { cdmipDiffServRulesIndex }
			::= { cdmipDiffServRulesTable 1 }
		
		CdmipDiffServRulesEntry ::=
			SEQUENCE { 
				cdmipDiffServRulesIndex
					INTEGER,
				cdmipDiffServRulesClass
					OCTET STRING,
				cdmipDiffServRulesDscp
					Integer32,
				cdmipDiffServRulesMinBw
					INTEGER,
				cdmipDiffServRulesMaxBw
					INTEGER,
				cdmipDiffServRulesPriority
					INTEGER,
				cdmipDiffServRulesRowStatus
					INTEGER
			 }

		cdmipDiffServRulesIndex OBJECT-TYPE
			SYNTAX INTEGER (1..12)
			MAX-ACCESS read-write
			STATUS current
			DESCRIPTION
				"The index for the DiffServ rule."
			::= { cdmipDiffServRulesEntry 1 }
		
		cdmipDiffServRulesClass OBJECT-TYPE
			SYNTAX OCTET STRING (SIZE (1..9))
			MAX-ACCESS read-only
			STATUS current
			DESCRIPTION
				"The DiffServ class name for the DiffServ rule.
				
				There are three types of DiffServ rules:
				    1. Expedite Forwarding
				    2. Class-1 to Class-8
				    3. Assured Forwarding-1 to Assured Forwarding-4
				
				***
				NOTE: This is NOT a user configurable parameter.
				***"
			::= { cdmipDiffServRulesEntry 2 }
		
		cdmipDiffServRulesDscp OBJECT-TYPE
			SYNTAX Integer32
			MAX-ACCESS read-only
			STATUS current
			DESCRIPTION
				"The DiffServ code point (DSCP) for the DiffServ rule. 
				
				***
				NOTE: This is NOT a user configurable parameter.
				***"
			::= { cdmipDiffServRulesEntry 3 }
		
		cdmipDiffServRulesMinBw OBJECT-TYPE
			SYNTAX INTEGER (0..99999)
			UNITS "kbps"
			MAX-ACCESS read-write
			STATUS current
			DESCRIPTION
				"The minimum bandwidth (Kbps) for the DiffServ rule.
				
				
				***
				NOTE: This value can only be set for DiffServ rules of 
				'Assured Forwarding Class'.
				
				NOTE: The total minimum bandwidth of all rules should NOT exceed the 
				Tx data rate of the modem.
				***"
			::= { cdmipDiffServRulesEntry 4 }
		
		cdmipDiffServRulesMaxBw OBJECT-TYPE
			SYNTAX INTEGER (0..99999)
			UNITS "kbps"
			MAX-ACCESS read-write
			STATUS current
			DESCRIPTION
				"The maximum bandwidth (Kbps) for the DiffServ rule.
				
				***
				NOTE: This value can only be set for DiffServ rules of 
				'Assured Forwarding Class'.
				***"
			::= { cdmipDiffServRulesEntry 5 }
		
		cdmipDiffServRulesPriority OBJECT-TYPE
			SYNTAX INTEGER (1..8)
			MAX-ACCESS read-only
			STATUS current
			DESCRIPTION
				"The priority of the DiffServ rule. 
				
				***
				NOTE: This is NOT a user configurable parameter.
				***"
			::= { cdmipDiffServRulesEntry 6 }
		
		cdmipDiffServRulesRowStatus OBJECT-TYPE
			SYNTAX INTEGER
				{
				active(1),
				notInService(2),
				notReady(3),
				createAndGo(4),
				createAndWait(5),
				destroy(6)
				}
			MAX-ACCESS read-write
			STATUS current
			DESCRIPTION
				"In SMIv2 tables, the RowStatus textual convention is used to manage 
				the creation and deletion of conceptual rows. 
				
				This column has six defined values.
				active(1)        - which indicates that the conceptual row with all 
				                   column is available for use by the managed device
				notInService(2)  - this row state is not yet supported
				notReady(3)      - this row state is not yet supported
				createAndGo(4)   - which is supplied by a manager wishing to create a 
				                   new instance of a conceptual row and to have its 
				                   status automatically set to active, making it 
				                   available for use by the managed device.
				createAndWait(5) - this row create is not yet supported
				destroy(6)       - which is supplied by a manager wishing to delete 
				                   all of the instances associated with an existing 
				                   conceptual row.
				
				Right now, the diffserv initialisation process creates all necessary
				Diffserv rules. User is allowed to modify minBw & maxBw for ASF
				(Assured Forwarding) class rules only. User is not allowed to create
				new rules."
			::= { cdmipDiffServRulesEntry 9 }
		
		cdmipQosMode OBJECT-TYPE
			SYNTAX INTEGER
				{
				qosModeMaxPriority(1),
				qosModeMinMax(2),
				qosModeDiffServ(3)
				}
			MAX-ACCESS read-write
			STATUS current
			DESCRIPTION
				"The QoS configuration modes for the QoS subsystem.
				
				The valid values are:
				  1. Maximum Bandwidth & Priority.
				  2. Minimum Bandwidth & Maximum Bandwidth.
				  3. Differential Services Mode.
				
				"
			::= { cdmipQosRules 4 }
		
		cdmipControllerConformance OBJECT IDENTIFIER ::= { cdmipController 10 }
		
		cdmipControllerGroups OBJECT IDENTIFIER ::= { cdmipControllerConformance 1 }
		
		cdmipAdministrationGroup OBJECT-GROUP
			OBJECTS { cdmipMibVersion, cdmipAccessIpAddress1, cdmipAccessSubnetMaskLen1, cdmipAccessIpAddress2, cdmipAccessSubnetMaskLen2, 
				cdmipAccessIpAddress3, cdmipAccessSubnetMaskLen3, cdmipAccessIpAddress4, cdmipAccessListEnforcement, cdmipQosOption, 
				cdmipEncryptionOption, cdmipIgmpOption, cdmipHeaderCompressionOption, cdmipPayloadCompressionOption, cdmipTelnetFeature, 
				cdmipPingReplyFeature, cdmipDownlinkRouteMulticastFeature, cdmipQosOpt, cdmipTransmit3xDesEncryptionOpt, cdmipIgmpOpt, 
				cdmipTxHeaderCompressionOpt, cdmipRxHeaderCompressionOpt, cdmipTxPayloadCompressionOpt, cdmipTransmitKey1, cdmipTransmitKey2, 
				cdmipTransmitKey3, cdmipTransmitKey4, cdmipTransmitKey5, cdmipTransmitKey6, cdmipTransmitKey7, 
				cdmipTransmitKey8, cdmipReceiveKey1, cdmipReceiveKey2, cdmipReceiveKey3, cdmipReceiveKey4, 
				cdmipReceiveKey5, cdmipReceiveKey6, cdmipReceiveKey7, cdmipReceiveKey8, cdmipSmtpServerIpAddress, 
				cdmipSmtpDomain, cdmipSmtpDestinationName, cdmipSnmpTrapDestinationIpAddress, cdmipSnmpTrapCommunity, cdmipSnmpTrapVersion, 
				cdmipSnmpAuthenticationFailureCommunity, cdmipSnmpAuthenticationFailureAddress, cdmipWorkingMode, cdmipEasyconnectMulticastOption, cdmipHdrcompRefreshRateUdpRtp1, 
				cdmipHdrcompRefreshRateUdp, cdmipHdrcompRefreshRateAllOther, cdmipPayloadCompRefreshRate, cdmipAccessSubnetMaskLen4, cdmipSnmpTrapDestinationIpAddress2
				 }
			STATUS current
			DESCRIPTION
				"CDM-IP Controller Administration Group."
			::= { cdmipControllerGroups 1 }
		
		cdmipInterfacesGroup OBJECT-GROUP
			OBJECTS { cdmipEthernetMacAddress, cdmipEthernetSpeed, cdmipEthernetIpAddress, cdmipEthernetSubnetPrefixLen, cdmipSatelliteHdlcAddress1, 
				cdmipSatelliteHdlcAddress2, cdmipSatelliteHdlcAddress3, cdmipSatelliteHdlcAddress4, cdmipSatelliteHdlcAddressDelete, cdmipSatelliteHdlcAddressModeConfig
				 }
			STATUS current
			DESCRIPTION
				"CDM-IP Controller Interface Group."
			::= { cdmipControllerGroups 2 }
		
		cdmipRouteTableGroup OBJECT-GROUP
			OBJECTS { cdmipIpRouteIndex, cdmipIpRouteName, cdmipIpRouteDestAddress, cdmipIpRouteDestMaskLen, cdmipIpRouteNextHopAddress, 
				cdmipIpRouteMulticastOptions, cdmipIpRouteState, cdmipIpRouteHdlcAddress, cdmipIpRouteHdrComp, cdmipIpRoutePayloadComp, 
				cdmipIpRoute3xDes, cdmipIpRouteDesKey, cdmipIpRouteRowStatus }
			STATUS current
			DESCRIPTION
				"CDM-IP Controller Route Table Group."
			::= { cdmipControllerGroups 3 }
		
		cdmipProtocolsGroup OBJECT-GROUP
			OBJECTS { cdmipIgmpIndex, cdmipIgmpTTL, cdmipIgmpClientState, cdmipIgmpSrc, cdmipIgmpGroupIpAddress, 
				cdmipIgmpEnable, cdmipIgmpQueryPeriod, cdmipIgmpMaxRespTime, cdmipIgmpMaxMissBeforeDrop, cdmipIgmpRecognizeQueries, 
				cdmipIgmpVersionUnsolicitedReports, cdmipIgmpForceAlertOption, cdmipIgmpUnsolicitedReportInterval, cdmipDhcpServerIpAddress }
			STATUS current
			DESCRIPTION
				"CDM-IP Controller Protocols Group."
			::= { cdmipControllerGroups 4 }
		
		cdmipRedundancyGroup OBJECT-GROUP
			OBJECTS { cdmipCurrentRedundantState, cdmipLocalUnitManagementIpAddress, cdmipRedundantUnitManagementIpAddress, cdmipRedundantTrafficIpAddress, cdmipRedundantTrafficSubnetMaskLen, 
				cdmipForceUnitOffline }
			STATUS current
			DESCRIPTION
				"CDM-IP Controller Redundancy Group."
			::= { cdmipControllerGroups 5 }
		
		cdmipOperMaintGroup OBJECT-GROUP
			OBJECTS { cdmipAppVersion, cdmipSaveConfiguration, cdmipReset, cdmipRestoreFactoryDefaults, cdmipLoadParamsFromStorage, 
				cdmipParamConfig, cdmipBootImageInfo, cdmipAppImage1Info, cdmipAppImage2Info, cdmipFramerVersion, 
				cdmipIPModuleBootFrom, cdmipUpgradeTo, cdmipBaseModemBootFrom }
			STATUS current
			DESCRIPTION
				"CDM-IP Controller Oper. Maint. Group."
			::= { cdmipControllerGroups 6 }
		
		cdmipStatisticsGroup OBJECT-GROUP
			OBJECTS { cdmipEtherTransmitGoodFrames, cdmipEtherTransmitMaxCollisionCount, cdmipEtherTransmitLateCollisionCount, cdmipEtherTransmitDMAUnderrunCount, cdmipEtherTransmitLostCarrierSenseCount, 
				cdmipEtherTransmitDeferredCount, cdmipEtherTransmitSingleCollisionCount, cdmipEtherTransmitMultipleCollisionCount, cdmipEtherTransmitTotalCollisionCount, cdmipEtherReceiveGoodFrames, 
				cdmipEtherReceiveCRCErrorFrameCount, cdmipEtherReceiveAllignErrorCount, cdmipEtherReceiveResourceErrorCount, cdmipEtherReceiveFifoOverrunErrorCount, cdmipEtherReceiveCollisionDetectErrorCount, 
				cdmipEtherReceiveShortFrameCount, cdmipEtherTransmitFlowControlPauseFrames, cdmipEtherReceiveFlowControlPauseFrames, cdmipEtherResetCounters, cdmipTotalIpPacketsFromSatellite, 
				cdmipTotalIpPacketsRoutedToSatellite, cdmipTotalIpPacketsFromEthernet, cdmipTotalIpPacketsRoutedToEthernet, cdmipIgmpPacketsReceived, cdmipIpOptionPacketsReceived, 
				cdmipDroppedPacketsTotal, cdmipDroppedPacketsTTLExpired, cdmipDroppedPacketsBadIpHeader, cdmipDroppedPacketsNoRoute, cdmipDroppedPacketsMulticast, 
				cdmipDroppedPacketsFiltered, cdmipDroppedPacketsMulticastDisableGroup, cdmipDroppedPacketsNoArpEntry, cdmipDroppedPacketsBadBufferLength, cdmipDroppedPacketsBadIpVersion, 
				cdmipDroppedPacketsQosFilterRule, cdmipDroppedPacketsEasyConnectMulticastOption, cdmipDroppedPacketsRouterQueueFull, cdmipResetCounters, cdmipQosStatsQueueIndex, 
				cdmipQosStatsSentPackets, cdmipQosStatsSentPacketsPerSecond, cdmipQosStatsSentBytes, cdmipQosStatsDroppedPackets, cdmipQosStatsDroppedBytes, 
				cdmipQosStatsCurrentTxRate, cdmipQosStatsAverageTxRate, cdmipQosStatsMaxTxRate, cdmipQosStatsActiveFlows, cdmipQosStatsResetCounters, 
				cdmipWanFpgaRxBadAddrCount, cdmipWanFpgaRxPktProcessorCrcErrorCount, cdmipWanFpgaRxAbortOctetErrorCount, cdmipWanFpgaRxOverrunErrorCount, cdmipWanFpgaRxHdlcCrcErrorCount, 
				cdmipWanFpgaRxHdlcPayLoadCount, cdmipWanFpgaRxHdlcHeaderCount, cdmipWanFpgaRxHdlcPacketCount, cdmipWanFpgaTxHdlcHeaderCount, cdmipWanFpgaTxHdlcPayLoadCount, 
				cdmipWanFpgaTxHdlcPacketCount, cdmipWanFpgaResetAllCounters, cdmipWanFpgaWanUtilization, cdmipWanFpgaLanToWanTraffic, cdmipWanFpgaActualWanTraffic, 
				cdmipWanFpgaWanBandwidthSaved, cdmipHdrcompStatsQueueIndex, cdmipHdrcompStatsPreHdrcompBytes, cdmipHdrcompStatsPostHdrcompBytes, cdmipHdrcompRatio, 
				cdmipPayloadCompPrePayloadCompBytes, cdmipPayloadCompPostPayloadCompBytes, cdmipPayloadCompRatio, cdmipCompStatsResetCounters }
			STATUS current
			DESCRIPTION
				"CDM-IP Controller Statistics Group."
			::= { cdmipControllerGroups 7 }
		
		cdmipQosRulesGroup OBJECT-GROUP
			OBJECTS { cdmipQosRulesIndex, cdmipQosRulesSrcIpAddr, cdmipQosRulesSrcIpMaskLen, cdmipQosRulesDstIpAddr, cdmipQosRulesDstIpMaskLen, 
				cdmipQosRulesProtocol, cdmipQosRulesSrcPortMin, cdmipQosRulesSrcPortMax, cdmipQosRulesDstPortMin, cdmipQosRulesDstPortMax, 
				cdmipQosRulesMinBw, cdmipQosRulesMaxBw, cdmipQosRulesPriority, cdmipQosRulesWred, cdmipQosRulesFilter, 
				cdmipQosRulesRowStatus, cdmipDiffServRulesIndex, cdmipDiffServRulesClass, cdmipDiffServRulesDscp, cdmipDiffServRulesMinBw, 
				cdmipDiffServRulesMaxBw, cdmipDiffServRulesPriority, cdmipDiffServRulesRowStatus, cdmipQosMode }
			STATUS current
			DESCRIPTION
				"CDM-IP Controller Qos Rules Group."
			::= { cdmipControllerGroups 8 }
		
		cdmipControllerCompliances OBJECT IDENTIFIER ::= { cdmipControllerConformance 2 }
		
		cdmipControllerCompliance MODULE-COMPLIANCE
			STATUS current
			DESCRIPTION
				"CDM-IP Controller Compliance."
			MODULE -- this module
				MANDATORY-GROUPS { cdmipAdministrationGroup, cdmipInterfacesGroup, cdmipRouteTableGroup, cdmipProtocolsGroup, cdmipRedundancyGroup, 
					cdmipOperMaintGroup, cdmipStatisticsGroup, cdmipQosRulesGroup }
			::= { cdmipControllerCompliances 1 }
		
	
	END

--
-- CDMIPController.my
--
