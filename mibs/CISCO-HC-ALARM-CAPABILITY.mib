-- *****************************************************************
-- CISCO-HC-ALARM-CAPABILITY.my:
-- Cisco HC-ALARM-MIB AGENT-CAPABILITIES
--
-- March 2004, Thomas Wu
--
-- Copyright (c) 2004 by Cisco Systems, Inc.
-- All rights reserved.
-- *****************************************************************

CISCO-HC-ALARM-CAPABILITY DEFINITIONS ::= BEGIN

IMPORTS
        MODULE-IDENTITY
                FROM SNMPv2-SMI
        AGENT-CAPABILITIES
                FROM SNMPv2-CONF
        OwnerString
                FROM RMON-MIB
        StorageType
                FROM SNMPv2-TC
        ciscoAgentCapability
                FROM CISCO-SMI;

ciscoHcAlarmCapability MODULE-IDENTITY
        LAST-UPDATED    "200403220000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of HC-ALARM-MIB."

        REVISION        "200403220000Z"
        DESCRIPTION
                "Initial version of this MIB module."
        ::= { ciscoAgentCapability 398 }

ciscoHcAlarmCapCatOSV08R0401 AGENT-CAPABILITIES
    PRODUCT-RELEASE     "Cisco CatOS 8.4(1)."
    STATUS              current
    DESCRIPTION         "HC-ALARM-MIB capabilities."

    SUPPORTS            HC-ALARM-MIB
        INCLUDES        {
                           hcAlarmControlGroup,
                           hcAlarmCapabilitiesGroup,
                           hcAlarmNotificationsGroup
                        }

        VARIATION        hcAlarmOwner
            SYNTAX       OwnerString (SIZE (1..20))
            DESCRIPTION  "Implementation only supports
                          1 to 20 octets."

        VARIATION        hcAlarmStorageType
            SYNTAX       StorageType { volatile(2),
                                   nonVolatile(3) }
            DESCRIPTION  "Implementation only supports
                          volatile(2) and nonVolatile(3)."

    ::= { ciscoHcAlarmCapability 1 }

END
