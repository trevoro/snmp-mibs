VERILINK-ENTERPRISE-NCMALARM-MIB

	-- set up MIB-wide defaults
	-- all functions can use %n for object name and
	-- %t for object type, %p for parent name,
	-- %d for name of default-bearing node and %% for %

	  DEFINITIONS ::= BEGIN

     IMPORTS
	     enterprises
		     FROM RFC1155-SMI
	     DisplayString
		     FROM RFC1213-MIB
	     OBJECT-TYPE
		     FROM RFC-1212
	     TRAP-TYPE
                     FROM RFC-1215;

	     


 
     --  This MIB module uses the extended OBJECT-TYPE macro as
     --  defined in RFC 1212.
     --  This MIB module uses the TRAP-TYPE macro as
     --  defined in RFC 1215.


	     	verilink         OBJECT IDENTIFIER ::= { enterprises 321 }
	     	as2000           OBJECT IDENTIFIER ::= { verilink 1 }
	     	ncmAlarm         OBJECT IDENTIFIER ::= { as2000 100 }
	     	ncm-generic      OBJECT IDENTIFIER ::= { as2000 3012 }
	     	ncm-dsu          OBJECT IDENTIFIER ::= { as2000 3022 }
         	ncm-dbu          OBJECT IDENTIFIER ::= { as2000 3023 }
         	ncm-dds          OBJECT IDENTIFIER ::= { as2000 3024 }
		ncm-ddsu         OBJECT IDENTIFIER ::= { as2000 3028 }
		ncm-sdiu	 OBJECT IDENTIFIER ::= { as2000 3029 }
	     	ncm-csu          OBJECT IDENTIFIER ::= { as2000 3025 }
	     	ncm-isdn         OBJECT IDENTIFIER ::= { as2000 3031 }
     	 	ncm-idcsu        OBJECT IDENTIFIER ::= { as2000 3027 }
	     	ncm-imux         OBJECT IDENTIFIER ::= { as2000 3030 }
	     	ncm-ds3          OBJECT IDENTIFIER ::= { as2000 3036 }
		ncm-m13          OBJECT IDENTIFIER ::= { as2000 3037 }
                ncm-japisdn      OBJECT IDENTIFIER ::= { as2000 3038 }








	  

   -- Specific Enterprise Trap for NCM



	ncmAlarmNodeAddr OBJECT-TYPE
	  SYNTAX INTEGER
	  ACCESS read-only
	  STATUS mandatory
	  DESCRIPTION
	       "The node id of the node that has the alarm."
		--DEFAULT get-function    get-dummy-number




		  ::= { ncmAlarm 1 }




	ncmAlarmShelf OBJECT-TYPE
	  SYNTAX INTEGER
	  ACCESS read-only
	  STATUS mandatory
	  DESCRIPTION
	       "The shelf number that has the alarm."
		--DEFAULT get-function    get-dummy-number





		  ::= { ncmAlarm 2 }



     ncmAlarmSlot OBJECT-TYPE
	  SYNTAX INTEGER
	  ACCESS read-only
	  STATUS mandatory
	  DESCRIPTION
	       "The slot number that has the alarm."
	--DEFAULT get-function    get-dummy-number



		  ::= { ncmAlarm 3 }



     ncmAlarmPort OBJECT-TYPE
	  SYNTAX INTEGER
	  ACCESS read-only
	  STATUS mandatory
	  DESCRIPTION
	       "The Port number that has the alarm."

	--DEFAULT get-function    get-dummy-number




		  ::= { ncmAlarm 4 }


	ncmAlarmCard OBJECT-TYPE
	  SYNTAX DisplayString (SIZE (0..255))
	  ACCESS read-only
	  STATUS mandatory
	  DESCRIPTION
	       "The card type that generated the alarm "
	 --DEFAULT get-function    get-dummy-string


		  ::= { ncmAlarm 5 }


	 ncmAlarmTimestamp    OBJECT-TYPE
		SYNTAX  INTEGER
		ACCESS  read-only
		STATUS  mandatory
		DESCRIPTION
		"The timestamp of  the alarm in GMT time sec format."

	--DEFAULT get-function    get-dummy-number



		::= { ncmAlarm 6 }

 
	ncmAlarmSeverity     OBJECT-TYPE
		SYNTAX  INTEGER
		ACCESS  read-only
		STATUS  mandatory
		DESCRIPTION
		"The Severity of  the alarm. The Severity levels are
		0 is cleared, 1 is Informational, 2 is warning, 3 is
			minor, 4 is Major and 5 is critical ."

	--DEFAULT get-function    get-dummy-number



		::= { ncmAlarm 7 }
 
 
	ncmAlarmInstance      OBJECT-TYPE
		SYNTAX  INTEGER
		ACCESS  read-only
		STATUS  mandatory
		DESCRIPTION
		"The alarm Instance of  the alarm."

	--DEFAULT get-function    get-dummy-number



 
		::= { ncmAlarm 8 }


	 ncmAlarmEquipId       OBJECT-TYPE
		SYNTAX  INTEGER
		ACCESS  read-only
		STATUS  mandatory
		DESCRIPTION
		"The Equipment id of the equipment that generate the
			 alarm."

	--DEFAULT get-function    get-dummy-number




 
		::= { ncmAlarm 9 }
 
 
	ncmAlarmObjectType    OBJECT-TYPE
		SYNTAX  INTEGER
		ACCESS  read-only
		STATUS  mandatory
		DESCRIPTION
		"The object type that generated  the alarm.The
			object type is as follows
 
 
		0 = E1 port Identifier
		1 = Data Port
		2 = Circuit
		3 = Power
		4 = Clock Reference
		5 = Timing Bus
		6 = Reference Bus
		7 = Not Used
		8 = Software
		9 = Equipment
		10 = T1 Port.."


	 --DEFAULT get-function    get-dummy-number


	 
		::= { ncmAlarm 10 }
 



	


	ncmAlarmString OBJECT-TYPE
	  SYNTAX DisplayString (SIZE (0..255))
	  ACCESS read-only
	  STATUS mandatory
	  DESCRIPTION
	       "Description of the Alarm Codes used in the
			as2000 Verilink Enterprise Trap "
	--DEFAULT get-function    get-dummy-string
 


		  ::= { ncmAlarm 11 }


     ncmTrap TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "The ncm Alarm Status"
	  ::= 4000 


-- ncm CSU Power UP Traps 

     ncmnearCSUPowerUP TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End CSU Power Up Alarm"
	  ::= 4001

     ncmncmfarCSUPowrUP TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End CSU Power Up Alarm"
	  ::= 4003

-- NEAR END Network and Equipment Alarms (Table B1,B2)

     ncmnearBERexceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End Network/Equipment BER exceeded Alarm"
	  ::= 5101

     ncmnearBERexceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End Network/Equipment BER exceeded Cleared Alarm"
	  ::= 5102

     ncmnearESLexceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Network/Equipment ESL exceeded Alarm"
	  ::= 5103

     ncmnearESLexceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Network/Equipment ESL exceeded Cleared Alarm"
	  ::= 5104

     ncmnearESexceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End Network/Equipment ES exceeded Alarm"
	  ::= 5105

     ncmnearESexceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End Network/Equipment ES exceeded Cleared Alarm"
	  ::= 5106

     ncmnearUASexceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
		}
	  DESCRIPTION
	       "Near-End Network/Equipment UAS exceeded Alarm"
	  ::= 5107

     ncmnearUASexceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End Network/Equipment UAS exceeded Cleared Alarm"
	  ::= 5108

     ncmnearLELBlooped TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End Network/Equipment LLB/ELB looped Alarm"
	  ::= 5109

     ncmnearLELBloopedCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End Network/Equipment LLB/ELB looped Cleared Alarm"
	  ::= 5110

     ncmnearPRLBlooped TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End Network/Equipment PLB/RLB looped Alarm"
	  ::= 5111

     ncmnearPRLBloopedCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End Network/Equipment PLB/RLB looped Cleared Alarm"
	  ::= 5112

     ncmnearLOS TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End Network/Equipment LOS Alarm"
	  ::= 5113

     ncmnearLOSCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End Network/Equipment LOS Cleared Alarm"
	  ::= 5114

     ncmnearRAI TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End Network/Equipment RAI Alarm"
	  ::= 5115

     ncmnearRAICleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End Network/Equipment RAI Cleared Alarm"
	  ::= 5116

     ncmnearLOF TRAP-TYPE
	  ENTERPRISE    as2000
	  VARIABLES {
			
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End Network/Equipment LOF Alarm"
	  ::= 5117

     ncmnearLOFCleared TRAP-TYPE
	  ENTERPRISE    as2000
	  VARIABLES {
		
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End Network/Equipment LOF Cleared Alarm"
	  ::= 5118

     ncmnearAIS TRAP-TYPE
	  ENTERPRISE    as2000
	  VARIABLES {
		
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Network/Equipment AIS Alarm"
	  ::= 5119

     ncmnearAISCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End Network/Equipment AIS Cleared Alarm"
	  ::= 5120

     ncmnearTestSIG TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End Network/Equipment Test SIG Alarm"
	  ::= 5121

     ncmnearTestSIGCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End Network/Equipment Test SIG Cleared Alarm"
	  ::= 5122

     ncmnearCSULossExtClk TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End CSU Loss of External Clock Alarm"
	  ::= 5123



	

     ncmnearCSULossExtClkCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Near-End CSU Loss of External Clock Cleared Alarm"
	  ::= 5124


	ncmnearEQPTBERExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment BER exceeded Alarm"
	  ::= 5201

	ncmnearEQPTBERExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment BER exceeded cleared Alarm"
	  ::= 5202

	ncmnearEQPTESLExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment ES-L exceeded Alarm"
	  ::= 5203


	ncmnearEQPTESLExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment ES-L exceeded cleared Alarm"
	  ::= 5204

	ncmnearEQPTESExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment ES exceeded Alarm"
	  ::= 5205
	

	ncmnearEQPTESExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment ES exceeded cleared Alarm"
	  ::= 5206

	ncmnearEQPTUASExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment ES exceeded Alarm"
	  ::= 5207
	

	ncmnearEQPTUASExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment UAS exceeded cleared Alarm"
	  ::= 5208


	ncmnearEQPTELBLooped TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment ELB Looped Alarm"
	  ::= 5209
	

	ncmnearEQPTELBLoopedCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment ELB Looped cleared Alarm"
	  ::= 5210

	ncmnearEQPTRLBLooped TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment RLB Looped Alarm"
	  ::= 5211
	

	ncmnearEQPTRLBLoopedCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment ELB Looped cleared Alarm"
	  ::= 5212


	ncmnearEQPTLOS TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment LOS Alarm"
	  ::= 5213
	

	ncmnearEQPTLOSCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment LOS cleared Alarm"
	  ::= 5214

	ncmnearEQPTRAI TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment RAI Alarm"
	  ::= 5215
	

	ncmnearEQPTRAICleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment RAI cleared Alarm"
	  ::= 5216


	ncmnearEQPTLOF TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment LOF Alarm"
	  ::= 5217
	

	ncmnearEQPTLOFCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment LOF cleared Alarm"
	  ::= 5218

	ncmnearEQPTAIS TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment AIS Alarm"
	  ::= 5219
	

	ncmnearEQPTAISCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment AIS cleared Alarm"
	  ::= 5220


	ncmnearEQPTTSA TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment TSA Alarm"
	  ::= 5221
	

	ncmnearEQPTTSACleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment TSA cleared Alarm"
	  ::= 5222



	

     ncmnearEQPTLowDensity TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment low density Alarm"
	  ::= 5223

     ncmnearEQPTLowDensityCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Near-End Equipment low density Cleared Alarm"
	  ::= 5224

-- FAR END Network and Equipment Alarms (Table B3,B4)


     ncmfarBERexceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString



		

		  }
	  DESCRIPTION
	       "ncm Far-End Network/Equipment BER exceeded Alarm"
	  ::= 5301

     ncmfarBERexceededCleared TRAP-TYPE
	  ENTERPRISE    as2000
	  VARIABLES {


		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmFar-End Network/Equipment BER exceeded Cleared Alarm"
	  ::= 5302

     ncmfarESLexceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "ncmFar-End Network/Equipment ESL exceeded Alarm"
	  ::= 5303

     ncmfarESLexceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "ncmFar-End Network/Equipment ESL exceeded Cleared Alarm"
	  ::= 5304

     ncmfarESexceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmFar-End Network/Equipment ES exceeded Alarm"
	  ::= 5305

     ncmfarESexceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "ncmFar-End Network/Equipment ES exceeded Cleared Alarm"
	  ::= 5306

     ncmfarUASexceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End Network/Equipment UAS exceeded Alarm"
	  ::= 5307

     ncmfarUASexceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End Network/Equipment UAS exceeded Cleared Alarm"
	  ::= 5308

     ncmfarLELBlooped TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End Network/Equipment LLB/ELB looped Alarm"
	  ::= 5309

     ncmfarLELBloopedCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End Network/Equipment LLB/ELB looped Cleared Alarm"
	  ::= 5310

     ncmfarPRLBlooped TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmFar-End Network/Equipment PLB/RLB looped Alarm"
	  ::= 5311

     ncmfarPRLBloopedCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End Network/Equipment PLB/RLB looped Cleared Alarm"
	  ::= 5312

     ncmfarLOS TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmFar-End Network/Equipment LOS Alarm"
	  ::= 5313

     ncmfarLOSCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End Network/Equipment LOS Cleared Alarm"
	  ::= 5314

     ncmfarRAI TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "ncmFar-End Network/Equipment RAI Alarm"
	  ::= 5315

     ncmfarRAICleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "ncmFar-End Network/Equipment RAI Cleared Alarm"
	  ::= 5316

     ncmfarLOF TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End Network/Equipment LOF Alarm"
	  ::= 5317

     ncmfarLOFCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End Network/Equipment LOF Cleared Alarm"
	  ::= 5318

     ncmfarAIS TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmFar-End Network/Equipment AIS Alarm"
	  ::= 5319

     ncmfarAISCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmFar-End Network/Equipment AIS Cleared Alarm"
	  ::= 5320


     ncmfarTestSIG TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "ncmFar-End Network/Equipment Test SIG applied Alarm"
	  ::= 5321

     ncmfarTestSIGCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End Network/Equipment Test SIG Cleared Alarm"
	  ::= 5322

     ncmfarCSULossExtClk TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End CSU Loss of External Clock Alarm"
	  ::= 5323

     ncmfarCSULossExtClkCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "ncmFar-End CSU Loss of External Clock Cleared Alarm"
	  ::= 5324


	 ncmFarEQPTBERExceeded TRAP-TYPE
          ENTERPRISE    as2000
          VARIABLES {

                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment BER exceeded Alarm"
          ::= 5401

	ncmFarEQPTBERExceededCleared TRAP-TYPE
          ENTERPRISE    as2000
          VARIABLES {

                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment BER exceeded cleared Alarm"
          ::= 5402

	 ncmFarEQPTESLExceededCleared TRAP-TYPE
          ENTERPRISE    as2000
          VARIABLES {

                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment ES-L exceeded cleared Alarm"
          ::= 5404

        ncmFarEQPTESExceeded TRAP-TYPE
          ENTERPRISE    as2000
          VARIABLES {

                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment ES exceeded Alarm"
          ::= 5405


	 ncmFarEQPTESExceededCleared TRAP-TYPE
          ENTERPRISE    as2000
          VARIABLES {

                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment ES exceeded cleared Alarm"
          ::= 5406


	
	ncmFarEQPTUASExceeded TRAP-TYPE
          ENTERPRISE    as2000
          VARIABLES {

                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment ES exceeded Alarm"
          ::= 5407
        
 
        ncmFarEQPTUASExceededCleared TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment UAS exceeded cleared Alarm"
          ::= 5408

	ncmFarEQPTELBLooped TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment ELB Looped Alarm"
          ::= 5409
        
 
        ncmFarEQPTELBLoopedCleared TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment ELB Looped cleared Alarm"
          ::= 5410

	 ncmFarEQPTRLBLooped TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment RLB Looped Alarm"
          ::= 5411
        
 
        ncmFarEQPTRLBLoopedCleared TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment ELB Looped cleared Alarm"
          ::= 5412


	 ncmFarEQPTLOS TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment LOS Alarm"
          ::= 5413
        
 
        ncmFarEQPTLOSCleared TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment LOS cleared Alarm"
          ::= 5414


	ncmFarEQPTRAI TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment RAI Alarm"
          ::= 5415
        
 
        ncmFarEQPTRAICleared TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment RAI cleared Alarm"
          ::= 5416

	 ncmFarEQPTLOF TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment LOF Alarm"
          ::= 5417
        
 
        ncmFarEQPTLOFCleared TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment LOF cleared Alarm"
          ::= 5418

	ncmFarEQPTAIS TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment AIS Alarm"
          ::= 5419
        
 
        ncmFarEQPTAISCleared TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment AIS cleared Alarm"
          ::= 5420
 


	ncmFarEQPTTSA TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment TSA Alarm"
          ::= 5421
        
 
        ncmFarEQPTTSACleared TRAP-TYPE
          ENTERPRISE    as2000
          VARIABLES {
 
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "ncmFar-End Equipment TSA cleared Alarm"
          ::= 5422
 
 


     ncmFarEQPTLowDensity TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "ncmFar-End Equipment low density Alarm"
	  ::= 5423

     ncmFarEQPTLowDensityCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "ncmFar-End Equipment low density Cleared Alarm"
	  ::= 5424

-- Additional NCC 2020 Status Codes (Table B-5)


	ncmPlugPresent TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Plug Present Alarm"
	  ::= 6996


	ncmPlugAbsent TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       " Plug Absent Alarm"
	  ::= 6997


	ncmFEPlugPresent TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "FE Plug Present Alarm"
	  ::= 6998


	ncmFEPlugAbsent TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "FE Plug Absent Alarm"
	  ::= 6999





     ncmtiuDualClksPresent TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "TIU Dual Clocks Present Alarm"
	  ::= 6601

     ncmtiuDualClksPresentCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "TIU Dual Clocks Present Alarm Cleared"
	  ::= 6602

     ncmtiuNoClksPresent TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "TIU No Clocks Present Alarm"
	  ::= 6603

     ncmtiuNoClksPresentCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "TIU No Clocks Present Alarm Cleared"
	  ::= 6604

     ncmdiuPort1LOS TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 Data Loss of Signal Alarm"
	  ::= 6801

     ncmdiuPort1LOSCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port1 Data Loss of Signal Alarm Cleared"
	  ::= 6802

     ncmdiuPort2LOS TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 Data Loss of Signal Alarm"
	  ::= 6803

     ncmdiuPort2LOSCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port2 Data Loss of Signal Alarm Cleared"
	  ::= 6804

	ncmddsPortAbnormalStationCodeExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 Abnormal Station Code Exceeded Alarm"
	  ::= 6805

	ncmddsPortAbnormalStationCodeExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port1 Abnormal Station Code Exceeded Alarm Cleared"
	  ::= 6806

	ncmddsPortControlModeIdleExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 Control Mode Idle Exceeded Alarm"
	  ::= 6807

	ncmddsPortControlModeIdleExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 Control Mode Idle Exceeded Alarm Cleared"
	  ::= 6808

	ncmddsPortMuxOutSyncExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port1 Mux Out of Sync Exceeded Alarm "
	  ::= 6809

	
	ncmddsPortMuxOutSyncExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 Mux Out of Sync Exceeded Alarm Cleared"
	  ::= 6810

	ncmddsPortUnassignedMuxChannelExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port1 Unassigned Mux Channel Exceeded Alarm "
	  ::= 6811

	ncmddsPortUnassignedMuxChannelExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 Unassigned Mux Channel Exceeded Alarm Cleared "
	  ::= 6812


	ncmddsPortMJUAlertExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		
	  }
	  DESCRIPTION
	       "Port1 MJU Alert Exceeded Alarm "
	  ::= 6813

	ncmddsPortMJUAlertExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 MJU Alert Exceeded Alarm Cleared "
	  ::= 6814

	ncmddsPortTestCodeExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port1 Test Code Exceeded Alarm "
	  ::= 6815

	
	ncmddsPortTestCodeExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port1 Test Code Exceeded Alarm Cleared "
	  ::= 6816


	ncmddsPortTestAlertExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port1 Test Alert Exceeded Alarm "
	  ::= 6817

	ncmddsPortTestAlertExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 Test Alert Exceeded Alarm Cleared "
	  ::= 6818


	ncmddsPortBlockExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port1 Block Exceeded Alarm "
	  ::= 6819

	ncmddsPortBlockExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port1 Block Exceeded Alarm Cleared "
	  ::= 6820

	

	ncmddsPortReleaseExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port1 Release Exceeded Alarm "
	  ::= 6821

	ncmddsPortReleaseExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
		       "Port1 Release Exceeded Alarm Cleared "
		  ::= 6822

		ncmddsPortLoop TRAP-TYPE
		  ENTERPRISE    as2000
		  VARIABLES {

			ncmAlarmNodeAddr,
			ncmAlarmShelf,
			ncmAlarmSlot,
			ncmAlarmPort,
			ncmAlarmCard,
			ncmAlarmTimestamp,
			ncmAlarmSeverity,
			ncmAlarmInstance,
			ncmAlarmEquipId,
			ncmAlarmObjectType,
			ncmAlarmString

				  }
		  DESCRIPTION
		       "Port1 loop Alarm "
	  ::= 6823

	

	  ncmddsPortLoopCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port1 loop Alarm Cleared "
	  ::= 6824


	
	ncmddsPortncmFarLooped TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 ncmFar Looped Alarm "
	  ::= 6825

	ncmddsPortncmFarLoopCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 ncmFar Loop Cleared "
	  ::= 6826

	ncmddsPortTestSignal TRAP-TYPE
	  ENTERPRISE    as2000
	  VARIABLES {
		
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 Test Signal Alarm "
	  ::= 6827

	ncmddsPortTestSignalCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1 Test Signal Cleared "
	  ::= 6828

	ncmddsPort2AbnormalStationCodeExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 Abnormal Station Code Exceeded Alarm"
	  ::= 6829

	ncmddsPort2AbnormalStationCodeExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port2 Abnormal Station Code Exceeded Alarm Cleared"
	  ::= 6830

	ncmddsPort2ControlModeIdleExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 Control Mode Idle Exceeded Alarm"
	  ::= 6831

	ncmddsPort2ControlModeIdleExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 Control Mode Idle Exceeded Alarm Cleared"
	  ::= 6832

	ncmddsPort2MuxOutSyncExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port2 Mux Out of Sync Exceeded Alarm "
	  ::= 6833

	
	ncmddsPort2MuxOutSyncExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 Mux Out of Sync Exceeded Alarm Cleared"
	  ::= 6834

	ncmddsPort2UnassignedMuxChannelExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port2 Unassigned Mux Channel Exceeded Alarm "
	  ::= 6835

	ncmddsPort2UnassignedMuxChannelExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 Unassigned Mux Channel Exceeded Alarm Cleared "
	  ::= 6836


	ncmddsPort2MJUAlertExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		
	  }
	  DESCRIPTION
	       "Port2 MJU Alert Exceeded Alarm "
	  ::= 6837

	ncmddsPort2MJUAlertExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 MJU Alert Exceeded Alarm Cleared "
	  ::= 6838

	ncmddsPort2TestCodeExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port2 Test Code Exceeded Alarm "
	  ::= 6839

	
	ncmddsPort2TestCodeExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port2 Test Code Exceeded Alarm Cleared "
	  ::= 6840


	ncmddsPort2TestAlertExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port2 Test Alert Exceeded Alarm "
	  ::= 6841

	ncmddsPort2TestAlertExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 Test Alert Exceeded Alarm Cleared "
	  ::= 6842


	ncmddsPort2BlockExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port2 Block Exceeded Alarm "
	  ::= 6843

	ncmddsPort2BlockExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port2 Block Exceeded Alarm Cleared "
	  ::= 6844

	

	ncmddsPort2ReleaseExceeded TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port2 Release Exceeded Alarm "
	  ::= 6845

	ncmddsPort2ReleaseExceededCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port2 Release Exceeded Alarm Cleared "
	  ::= 6846

	ncmddsPort2Loop TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

			  }
	  DESCRIPTION
	       "Port2 loop Alarm "
	  ::= 6847

	

	  ncmddsPort2LoopCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Port2 loop Alarm Cleared "
	  ::= 6848


	
	ncmddsPort2ncmFarLooped TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 ncmFar Looped Alarm "
	  ::= 6849

	ncmddsPort2ncmFarLoopCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 ncmFar Loop Cleared "
	  ::= 6850

	ncmddsPort2TestSignal TRAP-TYPE
	  ENTERPRISE    as2000
	  VARIABLES {
		
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 Test Signal Alarm "
	  ::= 6851

	ncmddsPort2TestSignalCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port2 Test Signal Cleared "
	  ::= 6852

	ncmdbuAlarm TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1/2 Dial Backup Alarm "
	  ::= 6853
 
	ncmdbuAlarmClear TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Port1/2 Dial Backup Alarm Cleared"
	  ::= 6854

	ncmdbuBackupConnection TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "Backup Connection Failed Alarm "
	  ::= 6855
 
	ncmdiuPortALLOnes TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

		  }
	  DESCRIPTION
	       "DIU Port1/2 All-Ones Alarm. All-Ones alarm is used to
		detect ncmfar end router failure. The ncmfar end must be 
		provisioned to send All-ones on Loss of Signal"
	  ::= 6857

     ncmdiuPortALLOnesCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "DIU Port1/2 All Ones Alarm Cleared"
	  ::= 6858

	ncmdbuPortASCOn TRAP-TYPE
	  ENTERPRISE    as2000
	  VARIABLES {	


		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	


		


	  }
	  DESCRIPTION
	       "Dbu Port1/2 ASC ON"
	  ::= 6861

	ncmdbuPortASCOff TRAP-TYPE
	  ENTERPRISE    as2000
	  VARIABLES {


			ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Dbu Port1/2 ASC OFF"
	  ::= 6862

	ncmdbuPortLOFOn TRAP-TYPE
	  ENTERPRISE    as2000
	  VARIABLES {


		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Dbu Port1/2 LOF ON"
	  ::= 6863

	ncmdbuPortLOFOff TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


		  }
	  DESCRIPTION
	       "Dbu Port1/2 LOF OFF"
	  ::= 6864

	ncmdbuPortCDOn TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


			  }
	  DESCRIPTION
	       "Dbu Port1/2 CD ON"
	  ::= 6865

	ncmdbuPortCDOff TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Dbu Port1/2 CD OFF"
	  ::= 6866

	ncmdbuPortUSEROn TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Dbu Port1/2 USER ON"
	  ::= 6867

	ncmdbuPortUSEROff TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Dbu Port1/2 USER OFF"
	  ::= 6868

	ncmdbuPortYELAlarmOn TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Dbu Port1/2 YEL Alarm ON"
	  ::= 6869


	ncmdbuPortYELAlarmOff TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Dbu Port1/2 YEL Alarm OFF"
	  ::= 6870


	ncmdbuPortNetworkBEROn TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Dbu Port1/2 Network BER ON"
	  ::= 6871


	ncmdbuPortNetworkBEROff TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Dbu Port1/2 Network BER OFF"
	  ::= 6872


	ncmdbuPortAllOnesAlarm TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Dbu Port1/2 All Ones Alarm"
	  ::= 6873


	 ncmdbuPortAllOnesAlarmCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


		  }
	  DESCRIPTION
	       "Dbu Port1/2 All Ones Alarm Cleared"
	  ::= 6874


	 ncmdbuPortLOSOn TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Dbu Port1/2 LOS ON"
	  ::= 6875


	
	ncmdbuPortLOSOff TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


		  }
	  DESCRIPTION
	       "Dbu Port1/2 LOS Off"
	  ::= 6876

      ncmalarmBufferFull TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Alarm Buffer Full"
	  ::= 7001

     ncmnearAPowerSupply TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


		  }
	  DESCRIPTION
	       "Near-End A Power Supply Alarm"
	  ::= 7002

     ncmnearAPowerSupplyCleared TRAP-TYPE
	  ENTERPRISE    as2000
	  VARIABLES {


		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


		  }
	  DESCRIPTION
	       "Near-End A Power Supply Alarm Cleared"
	  ::= 7003

     ncmfarAPowerSupply TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "ncmFar-End A Power Supply Alarm"
	  ::= 7004

     ncmfarAPowerSupplyCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


		  }
	  DESCRIPTION
	       "ncmFar-End A Power Supply Alarm Cleared"
	  ::= 7005

     ncmnearBPowerSupply TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Near-End B Power Supply Alarm"
	  ::= 7006

     ncmnearBPowerSupplyCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

	  }
	  DESCRIPTION
	       "Near-End B Power Supply Alarm Cleared"
	  ::= 7007

     ncmfarBPowerSupply TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


		  }
	  DESCRIPTION
	       "ncmFar-End B Power Supply Alarm"
	  ::= 7008

     ncmfarBPowerSupplyCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString



		  }
	  DESCRIPTION
	       "ncmFar-End B Power Supply Alarm Cleared"
	  ::= 7009

     powerUPLoopExists TRAP-TYPE
	  ENTERPRISE    as2000
	  VARIABLES {

	ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


	  }
	  DESCRIPTION
	       "Power-UP Loop Exists Alarm"
	  ::= 7010

     postNETFailure TRAP-TYPE
	  ENTERPRISE    as2000
	  VARIABLES {

	ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


	  }
	  DESCRIPTION
	       "Power-UP Self Test to NET Failure Alarm"
	  ::= 7011

	 postEQPTFailure TRAP-TYPE
	  ENTERPRISE    as2000
	  VARIABLES {

	ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString



			  }
	  DESCRIPTION
	       "Power-UP Self Test to Equipment Failure Alarm"
	  ::= 7012

	 lowBattery TRAP-TYPE
	  ENTERPRISE    as2000
	  VARIABLES {

	ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString



			  }
	  DESCRIPTION
	       "Low Battery Alarm"
	  ::= 7013
 
	 ncminvDownload TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString



			  }
	  DESCRIPTION
	       "Invalid Download"
	  ::= 7014

	ncmapsAlarmSet TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString



			  }
	  DESCRIPTION
	       "Set the aps Alarm"
	  ::= 9001

	ncmapsAlarmClear TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString



	  }
	  DESCRIPTION
	       "Set the aps Alarm Clear"
	  ::= 9002
	
	ncmapsSwitchedSet TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString



		  }
	  DESCRIPTION
	       "aps Switch Set"
	  ::= 9003

	ncmapsSwitchedClear TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString


	  }
	  DESCRIPTION
	       "aps Switch Clear"
	  ::= 9004



	 ncmipOverT1LinkDown TRAP-TYPE
          ENTERPRISE    as2000
          VARIABLES {

                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString


          }
          DESCRIPTION
               "IP Over T1 Link Down Alarm"
          ::= 9005




	ncmipOverT1LinkUp TRAP-TYPE 
          ENTERPRISE    as2000 
          VARIABLES { 
 
                ncmAlarmNodeAddr, 
                ncmAlarmShelf, 
                ncmAlarmSlot, 
                ncmAlarmPort, 
                ncmAlarmCard, 
                ncmAlarmTimestamp, 
                ncmAlarmSeverity, 
                ncmAlarmInstance, 
                ncmAlarmEquipId, 
                ncmAlarmObjectType, 
                ncmAlarmString 
 
 
          }
          DESCRIPTION 
               "IP Over T1 Link Up Alarm"
          ::= 9006






-- Quad CSU Power UP Traps

     ncmnearquadCSUPowerUP TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End CSU Power Up Alarm"
	  ::= 10000

     ncmfarCSUPowerUP TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmFar-End CSU Power Up Alarm"
	  ::= 10003

-- NEAR END ACE Quad Equipment Alarms

     ncmnearAceLOS TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End  Equipment LOS Alarm"
	  ::= 11100


	ncmnearAceLOSCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End  Equipment LOS Alarm Cleared"
	  ::= 16101


	

     
     ncmnearAceLOF TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End  Equipment LOF Alarm"
	  ::= 11101


	ncmnearAceLOFCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End  Equipment LOF Alarm Cleared"
	  ::= 16102


     
-- Plugged and unplugged trap objects

     ncmnearNewPlug TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End New Plug Alarm"
	  ::= 6501

     ncmnearPlugAbsent TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Plug Absent Alarm"
	  ::= 6503

     ncmnearPlugPresent TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Plug Present Alarm"
	  ::= 6505

-- NCM Traps


	 ncmActive TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "NCM Active Alarm"
	  ::= 8000


	 ncmStandBy TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "NCM StandBy Alarm"
	  ::= 8001


	ncmCircuitErr TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "NCM Circuit Err Alarm"
	  ::= 8002


	ncmFanShelfFail TRAP-TYPE
          ENTERPRISE    as2000
          VARIABLES {
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "Fan Shelf Failed Alarm"
          ::= 8003
 
        ncmFanShelfAlarmCleared TRAP-TYPE
          ENTERPRISE    as2000
          VARIABLES {
                ncmAlarmNodeAddr,
                ncmAlarmShelf,
                ncmAlarmSlot,
                ncmAlarmPort,
                ncmAlarmCard,
                ncmAlarmTimestamp,
                ncmAlarmSeverity,
                ncmAlarmInstance,
                ncmAlarmEquipId,
                ncmAlarmObjectType,
                ncmAlarmString
          }
          DESCRIPTION
               "Fan Shelf Alarm Cleared"
          ::= 8004


	

-- Quad Power supply status

     ncmnearQuadAPowerSupply TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End A Power Supply Alarm"
	  ::= 11002

     ncmnearQuadAPowerSupplyCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End A Power Supply Alarm Cleared"
	  ::= 11003

     ncmnearQuadBPowerSupply TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End B Power Supply Alarm"
	  ::= 11006

     ncmnearQuadBPowerSupplyCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End B Power Supply Alarm Cleared"
	  ::= 11007

-- ACE Quad Specific Enterprising Traps

     ncmnearRemoteAI TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Remote Alarm Indication trap"
	  ::= 11102

	ncmnearRemoteAICleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Remote Alarm Indication trap Cleared"
	  ::= 16103


     ncmnearLOMFalignm TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near End Loss of Multiframe Alignment alarm."
	  ::= 11103

	ncmnearLOMFalignmCleared TRAP-TYPE
	  ENTERPRISE    as2000
	  VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near End Loss of Multiframe Alignment alarm Cleared."
	  ::= 16104


     ncmnearRemoteMAS TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Remote MAS alarm."
	  ::= 11104

	 ncmnearRemoteMASCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Remote MAS alarm Cleared."
	  ::= 16105


     ncmnearIAS TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Indication alarm Signal alarm."
	  ::= 11105

	ncmnearIASCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Indication alarm Signal alarm Cleared."
	  ::= 16106


     ncmnearFAS TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,  
		ncmAlarmString
	  }
	  DESCRIPTION
	       "Near-End Frame Alignment Signal alarm."
	  ::= 11106


	ncmnearFASCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,  
		ncmAlarmString
	  }
	  DESCRIPTION
	       "Near-End Frame Alignment Signal alarm Cleared."
	  ::= 16107


     ncmnearFASeXceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Frame Alignment Signal Rate Exceeded alarm."
	  ::= 11107

	ncmnearFASeXceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Frame Alignment Signal Rate Exceeded alarm Cleared."
	  ::= 16108


     ncmnearCVCeXceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Code Violations Count Exceeded alarm."
	  ::= 11108


	ncmnearCVCeXceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Code Violations Count Exceeded alarm Cleared."
	  ::= 16109


     ncmnearCRCeXceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End CRC Exceeded alarm."
	  ::= 11109

	ncmnearCRCeXceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End CRC Exceeded alarm Cleared."
	  ::= 16110


     ncmnearFECeXceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Framing Error Count Exceeded alarm."
	  ::= 11110

	ncmnearFECeXceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Framing Error Count Exceeded alarm Cleared."
	  ::= 16111


     ncmnearCarrier TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Carrier Failure alarm."
	  ::= 11111


	ncmnearCarrierCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Carrier Failure alarm Cleared."
	  ::= 16112


     ncmnearDwnLdCode TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End DownLoad Code alarm."
	  ::= 11113

	 ncmnearDwnLdCodeCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End DownLoad Code alarm Cleared."
	  ::= 16114


     ncmnearLActCLK TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End CSU Loss of Active Clock alarm."
	  ::= 11114


	ncmnearLActCLKCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End CSU Loss of Active Clock alarm Cleared."
	  ::= 16115


     ncmnearLstdbyCLK TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End CSU Loss of Standby Clock alarm."
	  ::= 11115


	ncmnearLstdbyCLKCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End CSU Loss of Standby Clock alarm Cleared."
	  ::= 16116


     ncmnearRefTBUS TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Reference Timing Bus alarm."
	  ::= 11116

	 ncmnearRefTBUSCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Reference Timing Bus alarm Cleared."
	  ::= 16117


     ncmnearTBUS TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Timing Bus alarm."
	  ::= 11117


	ncmnearTBUSCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Timing Bus alarm Cleared."
	  ::= 16118


     ncmnearLLB TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End line loop back (LLB) alarm."
	  ::= 11119


	ncmnearLLBCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End line loop back (LLB) alarm Cleared."
	  ::= 16120


     ncmnearELB TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment Loop Back (ELB)  alarm."
	  ::= 11120

	ncmnearELBCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Equipment Loop Back (ELB)  alarm Cleared."
	  ::= 16121


     ncmnearPLB TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Payload Loop Back (PLB) alarm."
	  ::= 11121

	 ncmnearPLBCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Payload Loop Back (PLB) alarm Cleared."
	  ::= 16122


     ncmnearRLB TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Repeater Loop Back (RLB) alarm."
	  ::= 11122

	ncmnearRLBCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Near-End Repeater Loop Back (RLB) alarm Cleared."
	  ::= 16123



	ncmalmSESExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "T1 SES Threshold Exceeded alarm "
	  ::= 11123

	ncmalmSESExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "T1 SES Threshold Exceeded alarm Cleared"
	  ::= 16124


	ncmalmUASExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "T1 UAS Threshold Exceeded alarm "
	  ::= 11124

	ncmalmUASExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "T1 UAS Threshold Exceeded alarm Cleared"
	  ::= 16125



	ncmalmBERExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "BER Threshold Exceeded alarm "
	  ::= 11125


	ncmalmBERExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "BER Threshold Exceeded alarm Cleared "
	  ::= 16126


	ncmalmQ931LinkUP TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "FDL Q931 channel up alarm "
	  ::= 11126

	

	ncmalmQ931LinkDown TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "FDL Q931 Channel down alarm "
	  ::= 11127


	ncmalmPortDown TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Line removed by Line removal alarm "
	  ::= 11128


	ncmalmPortDownCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Line removed by Line removal alarm  Cleared"
	  ::= 16129





	ncmalmCGA TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Carrier Group Alarm (LOS and/or LOF) alarm "
	  ::= 11129


	ncmalmCGACleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Carrier Group Alarm (LOS and/or LOF) alarm Cleared "
	  ::= 16130


	ncmalmLOFThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "LOF Threshold exceeded alarm "
	  ::= 11130


	ncmalmLOFThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "LOF Threshold exceeded alarm Cleared "
	  ::= 16131


	

	ncmalmLOSThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "LOS Threshold exceeded alarm "
	  ::= 11131


	ncmalmLOSThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "LOS Threshold exceeded alarm Cleared "
	  ::= 16132




	ncmalmRAIThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "RAI Threshold exceeded alarm "
	  ::= 11132


	ncmalmRAIThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "RAI Threshold exceeded alarm Cleared "
	  ::= 16133




	ncmalmAISThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "AIS Threshold exceeded alarm "
	  ::= 11133


	ncmalmAISThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "AIS Threshold exceeded alarm Cleared."
	  ::= 16134


	ncmalmBPVThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "BPV Threshold exceeded alarm "
	  ::= 11134

	ncmalmBPVThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "BPV Threshold exceeded alarm Cleared "
	  ::= 16135


	ncmalmES15MINThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ES 15 MIN Threshold exceeded alarm "
	  ::= 11135


	ncmalmES15MINThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ES 15 MIN Threshold exceeded alarm Cleared"
	  ::= 16136


	ncmalmES24HRThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ES 24 HR Threshold exceeded alarm "
	  ::= 11136


	ncmalmES24HRThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ES 24 HR Threshold exceeded alarm Cleared "
	  ::= 16137



	ncmalmSES15MINThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "SES 15 MIN Threshold exceeded alarm "
	  ::= 11137


	ncmalmSES15MINThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "SES 15 MIN Threshold exceeded alarm Cleared"
	  ::= 16138


	ncmalmSES24HRThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "SES 24 HR Threshold exceeded alarm "
	  ::= 11138


	ncmalmSES24HRThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "SES 24 HR Threshold exceeded alarm Cleared "
	  ::= 16139



--	MCI Alarm Threshold Exceeded

	ncmalmCVP15MINThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "CVP 15 MIN Threshold exceeded alarm "
	  ::= 11139


	ncmalmCVP15MINThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "CVP 15 MIN Threshold exceeded alarm Cleared "
	  ::= 16140



	ncmalmCVP24HRThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "CVP 24 HR Threshold exceeded alarm "
	  ::= 11140


	ncmalmCVP24HRThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "CVP 24 HR Threshold exceeded alarm Cleared "
	  ::= 16141



	ncmalmCVL15MINThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "CVL 15 MIN Threshold exceeded alarm "
	  ::= 11141


	ncmalmCVL15MINThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "CVL 15 MIN Threshold exceeded alarm Cleared"
	  ::= 16142



	ncmalmCVL24HRThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "CVL 24 HR Threshold exceeded alarm "
	  ::= 11142

	ncmalmCVL24HRThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "CVL 24 HR Threshold exceeded alarm Cleared "
	  ::= 16143



	ncmalmESL15MINThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ESL 15 MIN Threshold exceeded alarm "
	  ::= 11143


	ncmalmESL15MINThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ESL 15 MIN Threshold exceeded alarm Cleared "
	  ::= 16144



	ncmalmESL24HRThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ESL 24 HR Threshold exceeded alarm "
	  ::= 11144


	ncmalmESL24HRThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ESL 24 HR Threshold exceeded alarm Cleared "
	  ::= 16145



	ncmalmSESL15MINThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "SESL 15 MIN Threshold exceeded alarm "
	  ::= 11145


	ncmalmSESL15MINThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "SESL 15 MIN Threshold exceeded alarm Cleared"
	  ::= 16146



	ncmalmSESL24HRThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "SESL 24 HR Threshold exceeded alarm "
	  ::= 11146


	ncmalmSESL24HRThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "SESL 24 HR Threshold exceeded alarm Cleared"
	  ::= 16147



	ncmalmUASP15MINThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "UASP 15 MIN Threshold exceeded alarm "
	  ::= 11147


	ncmalmUASP15MINThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "UASP 15 MIN Threshold exceeded alarm Cleared "
	  ::= 16148



	ncmalmUASP24HRThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "UASP 24 HR Threshold exceeded alarm "
	  ::= 11148


	ncmalmUASP24HRThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "UASP 24 HR Threshold exceeded alarm Cleared "
	  ::= 16149



	ncmalmBBERThresholdExceeded TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "BBER Threshold exceeded alarm "
	  ::= 11149


	ncmalmBBERThresholdExceededCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "BBER Threshold exceeded alarm Cleared "
	  ::= 16150



	ncmalmDataPortRTS TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Data Port RTS/CTS "
	  ::= 11160

	ncmalmDataPortRTSCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Data Port RTS/CTS Cleared"
	  ::= 16161



	ncmalmDataPortDTR TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Data Port DTR/DSR "
	  ::= 11161


	ncmalmDataPortDTRCleared TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Data Port DTR/DSR Cleared "
	  ::= 16162




	
		
-- IMUX Specific Enterprising Traps

     ncmalmImxDTEport TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux DTE port not ready alarm "
	  ::= 12105

     ncmalmImxLocOsc TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Local Oscillator Failure alarm "
	  ::= 12107

     ncmimuxLn1Bndwid TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #1 added Bandwidth alarm "
	  ::= 12112

     ncmimuxLn2Bndwid TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #2 added Bandwidth alarm "
	  ::= 12114

     ncmimuxLn3Bndwid TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #3 added Bandwidth alarm "
	  ::= 12116

     ncmimuxLn4Bndwid TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #4 added Bandwidth alarm "
	  ::= 12118

     ncmimuxLn5Bndwid TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #5 added Bandwidth alarm "
	  ::= 12122

     ncmimuxLn6Bndwid TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #6 added Bandwidth alarm "
	  ::= 12124

     ncmimuxLn7Bndwid TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #7 added Bandwidth alarm "
	  ::= 12126

     ncmimuxLn8Bndwid TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #8 added Bandwidth alarm "
	  ::= 12128

-- IMUX Specific Cleared Traps

     ncmalmImxDTEportReady TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "IMUX DTE port ready cleared alarm ."
	  ::= 12106

     ncmalmImxLocOscClear TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Local Oscillator Restored alarm "
	  ::= 12108

     ncmalmLn1BndwidClear TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #1 Removed Bandwidth alarm "
	  ::= 12111

     ncmimuxLn2BndwidClear TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #2 Removed Bandwidth alarm "
	  ::= 12113

     ncmimuxLn3BndwidClear TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #3 Removed Bandwidth alarm "
	  ::= 12115

     ncmimuxLn4BndwidClear TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #4 Removed Bandwidth alarm "
	  ::= 12117

     ncmimuxLn5BndwidClear TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #5 Removed Bandwidth alarm "
	  ::= 12121

     ncmimuxLn6BndwidClear TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #6 Removed Bandwidth alarm "
	  ::= 12123

     ncmimuxLn7BndwidClear TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #7 Removed Bandwidth alarm "
	  ::= 12125

     ncmimuxLn8BndwidClear TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux Carrier Line #8 Removed Bandwidth alarm "
	  ::= 12127


	 ncmimuxELBLoopbackActivated TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux ELB Loopback Activated  alarm "
	  ::= 12131


	ncmimuxELBLoopbackDeActivated TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux ELB Loopback DeActivated  alarm "
	  ::= 12132

	 ncmimuxPLBLoopbackActivated TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux PLB Loopback Activated  alarm "
	  ::= 12133


	ncmimuxPLBLoopbackDeActivated TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux PLB Loopback DeActivated  alarm "
	  ::= 12134


	 ncmimuxILBLoopbackActivated TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux ILB(Backplane) Loopback Activated  alarm "
	  ::= 12135


	ncmimuxILBLoopbackDeActivated TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "Imux ILB (Backplane) Loopback DeActivated  alarm "
	  ::= 12136


--	ACE ISDN PRI Alarms



	ncmPriIllegalConfiguration TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncm Pri Illegal Configuration Alarm "
	  ::= 13401



	ncmPriL2Up TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri L2 Up Alarm "
	  ::= 13402


	ncmPriL2Down TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri L2 down Alarm "
	  ::= 13403


	ncmPriDISCReceived TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Disc Received Alarm "
	  ::= 13404

	ncmPriDISCSent TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Disc Sent Alarm "
	  ::= 13405


	ncmPriL2IllegalMessageReceived TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri L2 Illegal Message Received"
	  ::= 13406


	ncmPriUnknownAcpCommand TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Unknown Acp command Alarm "
	  ::= 13407


	ncmPriIllegalAcpCommand TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Illegal Acp command Alarm "
	  ::= 13408


	ncmPriL3Up TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri L3 Up Alarm "
	  ::= 13410

	ncmPriL3Down TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri L3 Down Alarm "
	  ::= 13411

	ncmPriDChannelBackupSuccess TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri D Channel Backup Success Alarm"
	  ::= 13412


	ncmPriDChannelBackupFailure TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri D Channel Backup Failure Alarm "
	  ::= 13413


	ncmPriL3IllegalMessageReceived TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri L3 Illegal Message Received Alarm "
	  ::= 13414


	ncmPriL3SwitchError TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri L3 Switch Error Alarm "
	  ::= 13415


	ncmPriCallSetUp TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri call setup Alarm "
	  ::= 13416


	ncmPriCallSetUpFailure TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri call setup failure Alarm "
	  ::= 13417

	ncmPriCallTakeDownSuccess TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri call take down Success Alarm "
	  ::= 13418


	ncmPriCallTakeDownFailure TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri call take down failure Alarm "
	  ::= 13419


	ncmPriTestCallFailure TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Test Call Failure Alarm "
	  ::= 13420


	ncmPriSecurityIncomingCallReject TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Security Incomming Call Reject Alarm "
	  ::= 13421


	ncmPriSecurityOutgoingCallReject TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Security Outgoing Call Reject Alarm "
	  ::= 13422


	ncmPriStackUp TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Stack Up Alarm "
	  ::= 13423


	ncmPriStackDown TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Stack Down Alarm "
	  ::= 13424


	ncmPriApplicationIllegalMessage TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Application Illegal Message Alarm "
	  ::= 13425



	ncmPriCircuitBuilderCallReject TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Circuit Builder Call Reject Alarm "
	  ::= 13426


	ncmPriStackActivationFailure TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Stack Activation Failure Alarm "
	  ::= 13427

	ncmPriCircuitManagerCallRejectTakeDown TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmPri Circuit Manager Call Reject Take Down Alarm "
	  ::= 13428


	



	--	ncmDS3 Alarms 


	ncmDS3LosOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Loss of Signal On Alarm "
	  ::= 14001


	ncmDS3LosOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Loss of Signal Off Alarm "
	  ::= 14002


	ncmDS3OOFOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Out Of Frame On Alarm "
	  ::= 14003



	ncmDS3OOFOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Out Of Frame Off Alarm "
	  ::= 14004


	ncmDS3AISOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Alarm Indication Signal On Alarm "
	  ::= 14005



	ncmDS3AISOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Alarm Indication Signal Off Alarm "
	  ::= 14006


	ncmDS3IdleOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Idle Maintanance Signal On Alarm "
	  ::= 14007



	ncmDS3IdleOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Idle Maintanance Signal Off Alarm "
	  ::= 14008


	ncmDS3YellowOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Yellow Alarm On Alarm "
	  ::= 14009



	ncmDS3YellowOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Yellow Alarm Off Alarm "
	  ::= 14010


	ncmDS3LOSFailureOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Loss of signal failure On Alarm "
	  ::= 14040



	ncmDS3LOSFailureOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Loss of signal failure Off Alarm "
	  ::= 14041



	ncmDS3OutOfFrameFailureOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Out Of Frame failure On Alarm "
	  ::= 14042



	ncmDS3OutOfFrameFailureOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Out Of Frame failure Off Alarm "
	  ::= 14043


	ncmDS3AISFailureOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Alarm Indication signal failure On Alarm "
	  ::= 14046



	ncmDS3AISFailureOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Alarm Indication Signal failure Off Alarm "
	  ::= 14047


	

	ncmDS3ReceiveFIFOOverflowOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Receive FIFO Overflow On Alarm "
	  ::= 14048



	ncmDS3ReceiveFIFOOverflowOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Receive FIFO Overflow Off Alarm "
	  ::= 14049



	ncmDS3TransmitFIFOOverflowOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FIFO Overflow On Alarm "
	  ::= 14050



	ncmDS3TransmitFIFOOverflowOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FIFO Overflow Off Alarm "
	  ::= 14051



	ncmDS3LossTransmitClockOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Loss Transmit clock On Alarm "
	  ::= 14052



	ncmDS3LossTransmitClockOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Loss Transmit Clock Off Alarm "
	  ::= 14053


	ncmDS3ncmFarEndBlockErrorOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Block Error On Alarm "
	  ::= 14054



	ncmDS3ncmFarEndBlockErrorOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Block Error Off Alarm "
	  ::= 14055





	ncmDS3QRTLCVCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour LCV alert cross threshold Alarm "
	  ::= 14080

	ncmDS3QRTLESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour LES alert cross threshold Alarm "
	  ::= 14081


	ncmDS3QRTLSESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour LSES alert cross threshold Alarm "
	  ::= 14082

	ncmDS3QRTPCVCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour PCV alert cross threshold Alarm "
	  ::= 14083


	ncmDS3QRTPESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour PES alert cross threshold Alarm "
	  ::= 14084


	ncmDS3QRTPSESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour PSES alert cross threshold Alarm "
	  ::= 14085


	ncmDS3QRTSEFSCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour SEFS alert cross threshold Alarm "
	  ::= 14086


	ncmDS3QRTAISSCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour AISS alert cross threshold Alarm "
	  ::= 14087



	ncmDS3QRTUASCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour UAS alert cross threshold Alarm "
	  ::= 14088


	ncmDS3QRTCCVCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour CCV alert cross threshold Alarm "
	  ::= 14097


	ncmDS3QRTCESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour CES alert cross threshold Alarm "
	  ::= 14098


	ncmDS3QRTCSESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour CSES alert cross threshold Alarm "
	  ::= 14099


	ncmDS3QRTLOSSCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour LOSS alert cross threshold Alarm "
	  ::= 14100


	ncmDS3QRTLOFCCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 quarter hour LOFC alert cross threshold Alarm "
	  ::= 14101


	ncmDS3ncmFarEndQRTCCVCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End quarter hour CCV alert cross threshold Alarm "
	  ::= 14102


	ncmDS3ncmFarEndQRTCESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End quarter hour CES alert cross threshold Alarm "
	  ::= 14103


	ncmDS3ncmFarEndQRTCSESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End quarter hour CSES alert cross threshold Alarm "
	  ::= 14104

	ncmDS3ncmFarEndQRTUASCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End quarter hour UAS alert cross threshold Alarm "
	  ::= 14105



	ncmDS3DayLCVCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day LCV alert cross threshold Alarm "
	  ::= 14112



	ncmDS3DayLESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day LES alert cross threshold Alarm "
	  ::= 14113


	ncmDS3DayLSESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day LSES alert cross threshold Alarm "
	  ::= 14114


	ncmDS3DayPCVCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day PCV alert cross threshold Alarm "
	  ::= 14115


	ncmDS3DayPESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day PES alert cross threshold Alarm "
	  ::= 14116



	ncmDS3DayPSESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day PSES alert cross threshold Alarm "
	  ::= 14117


	ncmDS3DayPSEFSCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day PSEFS alert cross threshold Alarm "
	  ::= 14118


	ncmDS3DayAISSCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day AISS alert cross threshold Alarm "
	  ::= 14119


	ncmDS3DayUASCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day UAS alert cross threshold Alarm "
	  ::= 14120


	ncmDS3DayCCVCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day CCV alert cross threshold Alarm "
	  ::= 14129


	ncmDS3DayCESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day CES alert cross threshold Alarm "
	  ::= 14130


	ncmDS3DayCSESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day CSES alert cross threshold Alarm "
	  ::= 14131


	ncmDS3DayLOSSCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day LOSS alert cross threshold Alarm "
	  ::= 14132


	ncmDS3DayLOFCCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Day LOFC alert cross threshold Alarm "
	  ::= 14133


	ncmDS3ncmFarEndDayCCVCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Day CCV alert cross threshold Alarm "
	  ::= 14134


	ncmDS3ncmFarEndDayCESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Day CES alert cross threshold Alarm "
	  ::= 14135


	ncmDS3ncmFarEndDayCSESCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Day CSES alert cross threshold Alarm "
	  ::= 14136


	ncmDS3ncmFarEndDayUASCrossThreshold TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Day UAS alert cross threshold Alarm "
	  ::= 14137



	ncmDS3IPCChannelFailureOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 IPC Channel failure on Alarm "
	  ::= 14145



	ncmDS3IPCChannelFailureOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 IPC Channel failure off Alarm "
	  ::= 14146


	ncmDS3SARCardMajorAlarmOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 SAR card major Alarm on Alarm "
	  ::= 14147


	ncmDS3SARCardMajorAlarmOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 SAR card major Alarm off Alarm "
	  ::= 14148


	ncmDS3DxiHeartBeatFailureOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 DXI heart beat failure  on Alarm "
	  ::= 14149


	ncmDS3DxiHeartBeatFailureOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 DXI heart beat failure off Alarm "
	  ::= 14150


	ncmDS3HSSIPortUp TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 HSSI Port Up Alarm "
	  ::= 14151


	ncmDS3HSSIPortDown TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 HSSI Port Down Alarm "
	  ::= 14152


	 ncmDS3FEACEquipmentFailureSAOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Equipment Failure SA On Alarm "
	  ::= 14160


	ncmDS3FEACEquipmentFailureSAOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Equipment Failure SA Off Alarm "
	  ::= 14176



	ncmDS3FEACLosOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Los On Alarm "
	  ::= 14161


	ncmDS3FEACLosOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Los Off Alarm "
	  ::= 14177


	ncmDS3FEACOOFOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC OOF On Alarm "
	  ::= 14162


	ncmDS3FEACOOFOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC OOF On Alarm "
	  ::= 14178


	ncmDS3FEACAISOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Alarm indication signal On Alarm "
	  ::= 14163


	ncmDS3FEACAISOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Alarm indication signal Off Alarm "
	  ::= 14179



	ncmDS3FEACIDLEOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Idle On Alarm "
	  ::= 14164


	ncmDS3FEACIDLEOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Idle Off Alarm "
	  ::= 14180


	ncmDS3FEACEqptFailureNSAOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Equipment Failure NSA On Alarm "
	  ::= 14165


	ncmDS3FEACEqptFailureNSAOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Equipment Failure NSA Off Alarm "
	  ::= 14181


	ncmDS3FEACCommonEqptFailureOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Common Equipment Failure On Alarm "
	  ::= 14166


	ncmDS3FEACCommonEqptFailureOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Common Equipment Failure Off Alarm "
	  ::= 14182


	ncmDS3FEACMultiDs1LosHBEROn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Multi Ds1 Los HBER  On Alarm "
	  ::= 14167


	ncmDS3FEACMultiDs1LosHBEROff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Multi Ds1 Los HBER  Off Alarm "
	  ::= 14183


	ncmDS3FEACDs1EqptFailureOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Ds1 Equipment Failure On Alarm "
	  ::= 14168


	ncmDS3FEACDs1EqptFailureOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Ds1 Equipment Failure Off Alarm "
	  ::= 14184

	ncmDS3FEACSingleDs1LosHBEROn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Single Ds1 Los HBER On Alarm "
	  ::= 14169


	ncmDS3FEACSingleDs1LosHBEROff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Single Ds1 Los HBER Off Alarm "
	  ::= 14185


	ncmDS3FEACDs1EqptFailureNSAOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Ds1 Equipment Failure NSA On Alarm "
	  ::= 14170


	ncmDS3FEACDs1EqptFailureNSAOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Ds1 Equipment Failure NSA Off Alarm "
	  ::= 14186


	ncmDS3FEACLineLoopActivationOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Line Loop Activation On Alarm "
	  ::= 14171


	ncmDS3FEACLineLoopActivationOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Line Loop Activation Off Alarm "
	  ::= 14187




	ncmDS3FEACLineLoopDeActivationOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Line Loop DeActivation On Alarm "
	  ::= 14172


	ncmDS3FEACLineLoopDeActivationOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Line Loop DeActivation Off Alarm "
	  ::= 14188


	ncmDS3FEACLineOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Line On Alarm "
	  ::= 14173


	ncmDS3FEACLineOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 FEAC Line Off Alarm "
	  ::= 14189


	ncmDS3DataRateSetFailure TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 data rate set failure Alarm "
	  ::= 14224


	ncmDS3TransmitFEACLineLoopActivationOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Line Loop Activation On Alarm "
	  ::= 14225


	ncmDS3TransmitFEACLineLoopActivationOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Line Loop Activation Off Alarm "
	  ::= 14226


	ncmDS3TransmitFEACLineLoopDeActivationOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Line Loop DeActivation On Alarm "
	  ::= 14227


	ncmDS3TransmitFEACLineLoopDeActivationOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Line Loop DeActivation Off Alarm "
	  ::= 14228


	ncmDS3TransmitYellowAlarmOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit Yellow Alarm On Alarm "
	  ::= 14229


	ncmDS3TransmitYellowAlarmOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit Yellow Alarm Off Alarm "
	  ::= 14230



	ncmDS3TransmitAISAlarmOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit Alarm Indication Signal On Alarm "
	  ::= 14231


	ncmDS3TransmitAISAlarmOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit Alarm Indication Signal Off Alarm "
	  ::= 14232



	ncmDS3TransmitIdleAlarmOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit Idle On Alarm "
	  ::= 14233


	ncmDS3TransmitIdleAlarmOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit Idle Alarm Off Alarm "
	  ::= 14234


	ncmDS3TransmitFEBEAlarmOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEBE Alarm On Alarm "
	  ::= 14235


	ncmDS3TransmitFEBEAlarmOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEBE Alarm Off Alarm "
	  ::= 14236


	ncmDS3TransmitFEACLosOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Los On Alarm "
	  ::= 14239


	ncmDS3TransmitFEACLosOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Los Off Alarm "
	  ::= 14240



	ncmDS3TransmitFEACOOFOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC OOF On Alarm "
	  ::= 14241


	ncmDS3TransmitFEACOOFOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC OOF Off Alarm "
	  ::= 14242


	ncmDS3TransmitFEACAISOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Alarm Indication Siganl On Alarm "
	  ::= 14243


	ncmDS3TransmitFEACAISOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Alarm Indication Signal Off Alarm "
	  ::= 14244


	ncmDS3TransmitFEACIdleOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC idle On Alarm "
	  ::= 14245


	ncmDS3TransmitFEACIdleOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC idle Off Alarm "
	  ::= 14246


	ncmDS3TransmitFEACEqptFailureNSAOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Equipment Failure NSA On Alarm "
	  ::= 14247


	ncmDS3TransmitFEACEqptFailureNSAOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Equipment Failure NSA Off Alarm "
	  ::= 14248


	ncmDS3TransmitFEACCommonEqptFailureNSAOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC common Equipment Failure NSA On Alarm "
	  ::= 14249


	ncmDS3TransmitFEACCommonEqptFailureNSAOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Equipment Failure NSA Off Alarm "
	  ::= 14250


	ncmDS3TransmitFEACLineOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Line On Alarm "
	  ::= 14251


	ncmDS3TransmitFEACLineOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC Line Off Alarm "
	  ::= 14252


	ncmDS3TransmitFEACNoAlarm TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 Transmit FEAC No Alarm "
	  ::= 14253

	ncmDS3UserLocalLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 User Local Loopback On Alarm "
	  ::= 14256


	ncmDS3UserLocalLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 User Local Loopback Off Alarm "
	  ::= 14257


	
	ncmDS3UserPayloadLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 User Payload Loopback On Alarm "
	  ::= 14258


	ncmDS3UserPayloadLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 User Payload Loopback Off Alarm "
	  ::= 14259


	ncmDS3UserEquipmentLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 User Equipment Loopback On Alarm "
	  ::= 14260


	ncmDS3UserEquipmentLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 User Equipment Loopback Off Alarm "
	  ::= 14261



	ncmDS3UserNoLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 User No Loopback On Alarm "
	  ::= 14262


	ncmDS3UserNoLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 User No Loopback Off Alarm "
	  ::= 14263



	ncmDS3HSSILocalLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 HSSI Local Loopback On Alarm "
	  ::= 14264


	ncmDS3HSSILocalLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 HSSI Local Loopback Off Alarm "
	  ::= 14265


	ncmDS3HSSIPayloadLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 HSSI Payload Loopback On Alarm "
	  ::= 14266

	ncmDS3HSSIPayloadLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 HSSI Payload Loopback Off Alarm "
	  ::= 14267



	ncmDS3HSSIEquipmentLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 HSSI Equipment Loopback On Alarm "
	  ::= 14268


	ncmDS3HSSIEquipmentLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 HSSI Equipment Loopback Off Alarm "
	  ::= 14269

	

	ncmDS3HSSINoLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 HSSI No Loopback On Alarm "
	  ::= 14270


	ncmDS3HSSINoLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 HSSI No Loopback Off Alarm "
	  ::= 14271

	ncmDS3ncmFarEndLocalLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Local Loopback On Alarm "
	  ::= 14272


	ncmDS3ncmFarEndLocalLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Local Loopback Off Alarm "
	  ::= 14273

	ncmDS3ncmFarEndPayloadLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Payload Loopback On Alarm "
	  ::= 14274


	ncmDS3ncmFarEndPayloadLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Payload Loopback Off Alarm "
	  ::= 14275

	ncmDS3ncmFarEndEqptLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Equipment Loopback On Alarm "
	  ::= 14276


	ncmDS3ncmFarEndEqptLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Equipment Loopback Off Alarm "
	  ::= 14277

	ncmDS3ncmFarEndNoLoopbackOn TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End No Loopback On Alarm "
	  ::= 14278


	ncmDS3ncmFarEndNoLoopbackOff TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End No Loopback Off Alarm "
	  ::= 14279


	ncmDS3ncmFarEndPayloadLoopbackOnFailure TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Payload Loopback On Failure Alarm "
	  ::= 14280

	ncmDS3ncmFarEndPayloadLoopbackOffFailure TRAP-TYPE
	  ENTERPRISE    as2000
	  VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
	  }
	  DESCRIPTION
	       "ncmDS3 ncmFar End Payload Loopback Off Failure Alarm "
	  ::= 14281



	 ncmDS3UserEquipmentLoopbackOnPortTwo TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                        }   
          DESCRIPTION
               " ncm DS3 User Equipment Loopback On Port 2 Alarm "
          ::= 14288

        ncmDS3UserEquipmentLoopbackOFFPortTwo TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                          }
          DESCRIPTION
               "ncm DS3 User Equipment Loopback OFF Port 2 Alarm "
          ::= 14289
 
 
         ncmDS3HssiEquipmentLoopbackOnPortTwo TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                          }
          DESCRIPTION
               "ncm DS3 HSSI Equipment Loopback ON Port 2 Alarm "
          ::= 14290

	ncmDS3HssiEquipmentLoopbackOFFPortTwo TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                          }
          DESCRIPTION
               "ncm DS3 HSSI Equipment Loopback OFF Port 2 Alarm "
          ::= 14291


         ncmDS3FarEndEquipmentLoopbackONPortTwo TRAP-TYPE
          ENTERPRISE    as2000
          VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                        }
          DESCRIPTION
               "ncm DS3 Far End Equipment Loopback ON Port 2 Alarm "
          ::= 14292



        ncmDS3FarEndEquipmentLoopbackOFFPortTwo TRAP-TYPE
          ENTERPRISE    as2000
          VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm DS3 Far End Equipment Loopback OFF Port 2 Alarm "
          ::= 14293



	ncmDS3HssiPortUpPortTwo TRAP-TYPE
          ENTERPRISE    as2000
          VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm DS3 HSSI Port UP Port 2 Alarm "
          ::= 14294
 
 
 
         
        ncmDS3HssiPortDownPortTwo TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm DS3 HSSI Port Down Port 2 Alarm "
          ::= 14295
 
 
 
 
         ncmDS3HssiPortOneRateChange TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                          }
          DESCRIPTION
               "ncm DS3 HSSI Port One Rate Change Alarm "
          ::= 14296
 

	 ncmDS3HssiPortTwoRateChange TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                        }
          DESCRIPTION
               "ncm DS3 HSSI Port Two Rate Change Alarm "
          ::= 14297
 
         
 
        ncmDS3HssiPortOneRateChangeFarEnd TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm DS3 HSSI Port One Rate Change Far End Alarm "
          ::= 14298
 
 
        ncmDS3HssiPortTwoRateChangeFarEnd TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                          }
          DESCRIPTION
               "ncm DS3 HSSI Port Two Rate Change Far End Alarm "
          ::= 14299
 


	ncmDS3HssiLocalLoopbackOnDual TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm DS3 HSSI Local Loopback On Dual DS3 Alarm "
          ::= 14300
 
 
        ncmDS3HssiLocalLoopbackOffDual TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm DS3 HSSI Local Loopback Off Dual DS3 Alarm "
          ::= 14301
 
        ncmDS3UserLineLoopbackOn TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                       }
          DESCRIPTION
               "ncm DS3 User Line Loopback On Alarm "
          ::= 14304


	 ncmDS3UserLineLoopbackOff TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
          }
          DESCRIPTION
               "ncm DS3 User Line Loopback Off Alarm "
          ::= 14305
 
 
        ncmT1LOS TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                          }
          DESCRIPTION
               "ncm T1 LOS Alarm "
          ::= 14320
 
 
        ncmT1LOF TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm T1 LOF Alarm "
          ::= 14321


	 ncmT1AIS TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm T1 AIS Alarm "
          ::= 14322
 
 
 
        ncmT1YEL TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                        }
          DESCRIPTION
               "ncm T1 YEL Alarm "
          ::= 14323
 
 
        ncmT1OUT TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm T1 OUT Alarm "
          ::= 14324


	 ncmT1LineLoop TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
          }
          DESCRIPTION
               "ncm T1 Line Loop Alarm "
          ::= 14325
 
        ncmT1LocalLoop TRAP-TYPE
          ENTERPRISE    as2000
          VARIABLES {
		
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm T1 Local Loop Alarm "
          ::= 14326
 
 
        ncmT1FarEndLoopback TRAP-TYPE
          ENTERPRISE    as2000
          VARIABLES {
		
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString
          }
          DESCRIPTION
               "ncm T1 FarEnd Loopback Alarm "
          ::= 14327


	ncmActiveReferenceClockLOS TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm Active Reference Clock LOS Alarm "
          ::= 14328
 
 
        ncmStandbyReferenceClockLOS TRAP-TYPE
          ENTERPRISE    as2000
          VARIABLES {

		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm Standby Reference Clock LOS Alarm "
          ::= 14329
 
 
        ncmBothReferenceClockLOS TRAP-TYPE
          ENTERPRISE    as2000
          VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                          }
          DESCRIPTION
               "ncm Both Reference Clock LOS Alarm "
          ::= 14330


	ncmTimeBusLOS TRAP-TYPE
          ENTERPRISE    as2000
          VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm Time Bus LOS Alarm "
          ::= 14331
 

	ncmT1In TRAP-TYPE
          ENTERPRISE    as2000
          VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm T1 line in service Alarm "
          ::= 14336


	ncmT1LineLoopbackOff TRAP-TYPE
          ENTERPRISE    as2000
          VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm T1 line loopback off Alarm "
          ::= 14337


	ncmT1LocalLoopbackOff TRAP-TYPE
          ENTERPRISE    as2000
          VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm T1 local loopback off Alarm "
          ::= 14338


	ncmT1FarEndLoopbackOff TRAP-TYPE
          ENTERPRISE    as2000
          VARIABLES {
		ncmAlarmNodeAddr,
		ncmAlarmShelf,
		ncmAlarmSlot,
		ncmAlarmPort,
		ncmAlarmCard,
		ncmAlarmTimestamp,
		ncmAlarmSeverity,
		ncmAlarmInstance,
		ncmAlarmEquipId,
		ncmAlarmObjectType,
		ncmAlarmString

                         }
          DESCRIPTION
               "ncm T1 Far End loopback off Alarm "
          ::= 14339




	



	
    END
