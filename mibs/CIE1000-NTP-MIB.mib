-- *****************************************************************
-- NTP-MIB:  Cisco private MIB
-- ****************************************************************

CIE1000-NTP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    CIE1000InetAddress FROM CIE1000-TC
    Integer32 FROM SNMPv2-SMI
    TruthValue FROM SNMPv2-TC
    ;

cie1000NtpMib MODULE-IDENTITY
    LAST-UPDATED "201410100000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of NTP"
    REVISION    "201410100000Z"
    DESCRIPTION
        "Editorial changes"
    REVISION    "201407010000Z"
    DESCRIPTION
        "Initial version"
    ::= { cie1000SwitchMgmt 57 }


cie1000NtpMibObjects OBJECT IDENTIFIER
    ::= { cie1000NtpMib 1 }

cie1000NtpConfig OBJECT IDENTIFIER
    ::= { cie1000NtpMibObjects 2 }

cie1000NtpConfigGlobals OBJECT IDENTIFIER
    ::= { cie1000NtpConfig 1 }

cie1000NtpConfigGlobalsMode OBJECT-TYPE
    SYNTAX      TruthValue
    MAX-ACCESS  read-write
    STATUS      current
    DESCRIPTION
        "Global config mode of NTP. true is to enable NTP function in the system
         and false is to disable it."
    ::= { cie1000NtpConfigGlobals 1 }

cie1000NtpConfigServerTable OBJECT-TYPE
    SYNTAX      SEQUENCE OF CIE1000NtpConfigServerEntry
    MAX-ACCESS  not-accessible
    STATUS      current
    DESCRIPTION
        "This is a table of NTP server."
    ::= { cie1000NtpConfig 2 }

cie1000NtpConfigServerEntry OBJECT-TYPE
    SYNTAX      CIE1000NtpConfigServerEntry
    MAX-ACCESS  not-accessible
    STATUS      current
    DESCRIPTION
        "Each server has a set of parameters."
    INDEX       { cie1000NtpConfigServerIndex }
    ::= { cie1000NtpConfigServerTable 1 }

CIE1000NtpConfigServerEntry ::= SEQUENCE {
    cie1000NtpConfigServerIndex    Integer32,
    cie1000NtpConfigServerAddress  CIE1000InetAddress
}

cie1000NtpConfigServerIndex OBJECT-TYPE
    SYNTAX      Integer32 (1..5)
    MAX-ACCESS  accessible-for-notify
    STATUS      current
    DESCRIPTION
        "The index of NTP servers."
    ::= { cie1000NtpConfigServerEntry 1 }

cie1000NtpConfigServerAddress OBJECT-TYPE
    SYNTAX      CIE1000InetAddress
    MAX-ACCESS  read-write
    STATUS      current
    DESCRIPTION
        "Internet address of a NTP server."
    ::= { cie1000NtpConfigServerEntry 2 }

cie1000NtpMibConformance OBJECT IDENTIFIER
    ::= { cie1000NtpMib 2 }

cie1000NtpMibCompliances OBJECT IDENTIFIER
    ::= { cie1000NtpMibConformance 1 }

cie1000NtpMibGroups OBJECT IDENTIFIER
    ::= { cie1000NtpMibConformance 2 }

cie1000NtpConfigGlobalsInfoGroup OBJECT-GROUP
    OBJECTS     { cie1000NtpConfigGlobalsMode }
    STATUS      current
    DESCRIPTION
        "A collection of objects."
    ::= { cie1000NtpMibGroups 1 }

cie1000NtpConfigServerTableInfoGroup OBJECT-GROUP
    OBJECTS     { cie1000NtpConfigServerIndex,
                  cie1000NtpConfigServerAddress }
    STATUS      current
    DESCRIPTION
        "A collection of objects."
    ::= { cie1000NtpMibGroups 2 }

cie1000NtpMibCompliance MODULE-COMPLIANCE
    STATUS      current
    DESCRIPTION
        "The compliance statement for the implementation."

    MODULE      -- this module

    MANDATORY-GROUPS { cie1000NtpConfigGlobalsInfoGroup,
                       cie1000NtpConfigServerTableInfoGroup }

    ::= { cie1000NtpMibCompliances 1 }

END
