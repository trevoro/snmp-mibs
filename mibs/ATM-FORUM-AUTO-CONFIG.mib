ATM-FORUM-AUTO-CONFIG DEFINITIONS ::= BEGIN

    IMPORTS
          DisplayString, RowPointer    FROM SNMPv2-TC
          OBJECT-TYPE                  FROM SNMPv2-SMI
          atmForum, atmForumUni        FROM ATM-FORUM-TC-MIB
          TRAP-TYPE                    FROM RFC-1215;

    -- ----------------------------------------------------------------
    -- ATM Forum ILMI Extension for Auto Configuration
 
    -- This definition contains the following tables
    -- ATM Service Type Table
    -- ATM Service Connection Information Table
    -- AAL1 Profile Table
    -- AAL3/4 Profile Table
    -- AAL 5 Profile Table
    -- AAL 2 Profile Table
    -- --------------------------------------------------------------

    atmfAutoConfigGroup OBJECT IDENTIFIER ::= { atmForumUni 12 }

    ------------------------------------------------------------------
    -- ATM Forum ILMI Extension for Auto Configuration
    -- ATM Service Type
    ------------------------------------------------------------------

    atmfAtmServiceTypeTable OBJECT-TYPE
        SYNTAX SEQUENCE OF AtmfAtmServiceTypeEntry
        MAX-ACCESS not-accessible
        STATUS current
        DESCRIPTION
            "The ATM Forum ILMI Auto Configuration Extension ATM
            Service Type Information. "
        ::= { atmfAutoConfigGroup 1 }

    atmfAtmServiceTypeEntry OBJECT-TYPE
        SYNTAX AtmfAtmServiceTypeEntry
        MAX-ACCESS not-accessible
        STATUS current
        DESCRIPTION
            "An entry in the service type table describes the reference
            information about a service that may be associated with
            individual ATM connections for the purpose of auto-
            configuration. This information describe the name and sub-
            name of the service, the client layer protocol using the ATM
            service, the TM 4.0 service category, and the TM 4.0
            conformance definition."
        INDEX { atmfAtmServiceTypeIndex }
        ::= { atmfAtmServiceTypeTable 1 }

    AtmfAtmServiceTypeEntry ::= SEQUENCE {
         atmfAtmServiceTypeIndex        INTEGER,
         atmfAtmServiceProviderName     DisplayString,
         atmfAtmServiceName             DisplayString,
         atmfAtmServiceSubName          DisplayString,
         atmfAtmServiceClient           DisplayString,
         atmfAtmServiceTMCategory       INTEGER,
         atmfAtmServiceTMConformanceDef INTEGER
    }

    atmfAtmServiceTypeIndex OBJECT-TYPE
        SYNTAX INTEGER (1..2147483647)
        MAX-ACCESS read-only
        STATUS current
        DESCRIPTION
            "A number between which identifies the entry in the Service
            Type Table. "
        ::= { atmfAtmServiceTypeEntry 1 }

    atmfAtmServiceProviderName OBJECT-TYPE
        SYNTAX DisplayString
        MAX-ACCESS read-only
        STATUS current
        DESCRIPTION
            "This string identifies the name of the service provider for
            the service described in this profile. The value of this
            attribute should not set to NULL."
        ::= { atmfAtmServiceTypeEntry 2 }

    atmfAtmServiceName OBJECT-TYPE
        SYNTAX DisplayString
        MAX-ACCESS read-only
        STATUS current
        DESCRIPTION
            "This string identifies the name of the service described in
            this profile. The value of this attribute should not be set
            to NULL. "
        ::= { atmfAtmServiceTypeEntry 3 }
 
    atmfAtmServiceSubName OBJECT-TYPE
        SYNTAX DisplayString
        MAX-ACCESS read-only
        STATUS current
        DESCRIPTION
            "This string identifies the sub-name of the service described
            in this profile. A Service may have zero or more sub-names,
            each with its own service type profile. "
        ::= { atmfAtmServiceTypeEntry 4 }

    atmfAtmServiceClient OBJECT-TYPE
        SYNTAX DisplayString
        MAX-ACCESS read-only
        STATUS current
        DESCRIPTION
            "This string identifies the client protocol of the service
            described in this profile. A Service (sub-service) may have
            zero or more described client, each with its own service type
            profile. "
        ::= { atmfAtmServiceTypeEntry 5 }

    atmfAtmServiceTMCategory OBJECT-TYPE
        SYNTAX INTEGER {
                   other  (1),
                   cbr    (2),
                   rtVbr  (3),
                   nrtVbr (4),
                   abr    (5),
                   ubr    (6),
                   gfr    (7)
               }
        MAX-ACCESS read-only
        STATUS current
        DESCRIPTION
            "The TM 4.0 Service category used for this service type.
            Indicates CBR, rt-VBR, nrt-VBR, ABR, UBR, (or GFR)"
        ::= { atmfAtmServiceTypeEntry 6 }

    atmfAtmServiceTMConformanceDef OBJECT-TYPE
        SYNTAX INTEGER {
                     none (0),
                     other(1),
                     cbr1 (2),
                     vbr1 (3),
                     vbr2 (4),
                     vbr3 (5),
                     ubr1 (6),
                     ubr2 (7),
                     abr (8),
                     gfr1 (9),
                     gfr2 (10)
              }
        MAX-ACCESS read-only
        STATUS current
        DESCRIPTION
            "The TM 4.1 conformance definition used for this service type.
            Indicates CBR.1, VBR.1, VBR.2, VBR.3, UBR.1, UBR.2, ABR,
            GFR.1, or GFR.2. "
        ::= { atmfAtmServiceTypeEntry 7 }

    ------------------------------------------------------------------
    -- ATM Forum ILMI Extension for Auto Configuration
    -- ATM Service Connection Information
    ------------------------------------------------------------------

    atmfAtmServiceConnInfoTable OBJECT-TYPE
        SYNTAX SEQUENCE OF AtmfAtmServiceConnInfoEntry
        MAX-ACCESS not-accessible
        STATUS current
        DESCRIPTION
            "The ATM Forum ILMI Auto Configuration Extension ATM
            Service Connection Information. "
        ::= { atmfAutoConfigGroup 2 }

    atmfAtmServiceConnInfoEntry OBJECT-TYPE
        SYNTAX AtmfAtmServiceConnInfoEntry
        MAX-ACCESS not-accessible
        STATUS current
        DESCRIPTION
            "An entry in the service connection information table
            describes the ATM connection that provides a service across
            an ATM interface. The connection is identified by port and
            VPI/VCI value. Information about the connection includes the
            connection type (VP or VC, SVC or PVC), and the association of
            the connection with a service type. Specific connection
            information, such as traffic descriptors, should be accessed
            in the atmfVpc and atmfVcc tables defined in ILMI. "
        INDEX { atmfAtmServicePortIndex, atmfAtmServiceVpi,
                atmfAtmServiceVci }
        ::= { atmfAtmServiceConnInfoTable 1 }

    AtmfAtmServiceConnInfoEntry ::= SEQUENCE {
         atmfAtmServicePortIndex         INTEGER,
         atmfAtmServiceVpi               INTEGER,
         atmfAtmServiceVci               INTEGER,
         atmfAtmServiceSignalId          INTEGER,
         atmfAtmServiceConnServiceIndex  INTEGER,
         atmfAtmServiceConnName          DisplayString,
         atmfAtmServiceConnAALType       INTEGER,
         atmfAtmServiceConnAALIndex      INTEGER
         }

    atmfAtmServicePortIndex OBJECT-TYPE
        SYNTAX INTEGER (0..2147483647)
        MAX-ACCESS read-only
        STATUS current
        DESCRIPTION
            "The value of 0 (zero)has the special meaning of identifying
            the ATM Interface over which this ILMI message was received. "
        ::= { atmfAtmServiceConnInfoEntry 1 }
 
    atmfAtmServiceVpi OBJECT-TYPE
        SYNTAX INTEGER (0..255)
        MAX-ACCESS read-only
        STATUS current
        DESCRIPTION
            "The VPI value of the ATM service connection at the local ATM
            interface. "
        ::= { atmfAtmServiceConnInfoEntry 2 }
 
    atmfAtmServiceVci OBJECT-TYPE
        SYNTAX INTEGER (0..65535)
        MAX-ACCESS read-only
        STATUS current
        DESCRIPTION
            "The VCI value of the ATM service connection at the local ATM
            interface. If the atmfAtmServiceSignalId indicates that the
            connection is a VP connection, the value of this attribute
            shall be set to 0 (zero) and any meaning of this attribute
            ignored."
        ::= { atmfAtmServiceConnInfoEntry 3 }
 
    atmfAtmServiceSignalId OBJECT-TYPE
        SYNTAX INTEGER {
                    vcCI(0),
                    vpCI(1)
               }
        MAX-ACCESS read-only
        STATUS  current
        DESCRIPTION
            "This attribute represents the characteristic
            information of the layer network domain. It may be set to
            either VC characteristic information (vcCI) or VP
            characteristic information (vpCI)."
        ::= { atmfAtmServiceConnInfoEntry 4 }

    atmfAtmServiceConnServiceIndex OBJECT-TYPE
        SYNTAX INTEGER
        MAX-ACCESS read-only
        STATUS current
        DESCRIPTION
            "The value of this object identifies the row in the
            atmfAtmServiceTypeTable. This entry represents the
            association between an ATM service connection and an ATM
            service type profile that describes it. "
        ::= { atmfAtmServiceConnInfoEntry 5 }
 
    atmfAtmServiceConnName OBJECT-TYPE
        SYNTAX DisplayString
        MAX-ACCESS read-only
        STATUS current
        DESCRIPTION
            "This string identifies the name of the service connection.
            The value of this attribute may be set to NULL. "
        ::= { atmfAtmServiceConnInfoEntry 6 }
 
    atmfAtmServiceConnAALType OBJECT-TYPE
        SYNTAX INTEGER {
                    none (0),
                    aal1 (1),
                    aal34 (2),
                    aal5 (3),
                    other (4),
                    unknown (5),
                    aal2 (6)
                }
        MAX-ACCESS read-only
        STATUS current
        DESCRIPTION
            "Describes the AAL Type of the ATM service connection. A
            value of none indicates that no AAL is used. The AAL types
            include AAL1, AAL 3/4, and AAL 5. The value other may be a
            user-defined AAL type. The unknown type indicates that the
            AAL type cannot be determined. "
        ::= { atmfAtmServiceConnInfoEntry 7 }
 
    atmfAtmServiceConnAALIndex OBJECT-TYPE
        SYNTAX INTEGER
        MAX-ACCESS read-only
        STATUS current
        DESCRIPTION
            "The value of this object identifies the row in the
            atmfAAL1ProfileTable for AAL 1 connection, the
            atmfAAL34ProfileTable for AAL3/4 connection, and the
            atmfAAL5ProfileTable for AAL 5 connections. This entry
            represents the association between an ATM service connection
            and an ATM Adaptation Layer profile that describes it. "
        ::= { atmfAtmServiceConnInfoEntry 8 }

    ------------------------------------------------------------------
    -- ATM Forum ILMI Extension for Auto Configuration
    -- ATM AAL1 Profile
    ------------------------------------------------------------------
 
    atmfAAL1ProfileTable OBJECT-TYPE
        SYNTAX SEQUENCE OF AtmfAAL1ProfileEntry
        MAX-ACCESS not-accessible
        STATUS current
        DESCRIPTION
            "The ATM Forum ILMI Auto Configuration Extension AAL1
            Profile Information. "
        ::= { atmfAutoConfigGroup 3 }
 
    atmfAAL1ProfileEntry OBJECT-TYPE
        SYNTAX AtmfAAL1ProfileEntry
        MAX-ACCESS not-accessible
        STATUS current
        DESCRIPTION
            "An entry in the AAL1 Profile table provides data that
            describes the AAL1 processing function. "
        INDEX { atmfAAL1ProfileIndex }
        ::= { atmfAAL1ProfileTable 1 }
 
    AtmfAAL1ProfileEntry ::= SEQUENCE {
         atmfAAL1ProfileIndex         INTEGER,
         atmfAAL1Subtype              INTEGER,
         atmfAAL1CBRRate              INTEGER,
         atmfAAL1ClkRecoveryType      INTEGER,
         atmfAAL1FEC                  INTEGER,
         atmfAAL1SDT                  INTEGER,
         atmfAAL1PartiallyFilledCells INTEGER,
         atmfAAL1CellLossIntegrPeriod INTEGER
    }
 
    atmfAAL1ProfileIndex OBJECT-TYPE
        SYNTAX INTEGER (1..2147483647)
        MAX-ACCESS read-only
        STATUS current
        DESCRIPTION
            "A number between which identifies the entry in the AAL1
            Profile Table. "
        ::= { atmfAAL1ProfileEntry 1 }
 
    atmfAAL1Subtype OBJECT-TYPE
        SYNTAX INTEGER {
                   null (0),
                   voiceBand (1),
                   circuitEmulationSynchronous (2),
                   circuitEmulationAsynchronous (3),
                   highQualityAuto (4),
                   video (5)
               }
        MAX-ACCESS read-only
        STATUS current
        DESCRIPTION
            "This attribute describes AAL type 1 subtype used by the CBR
            service application (e.g. 64 KBPS voice band signal
            transport, circuit transport). "
        ::= { atmfAAL1ProfileEntry 2 }

    atmfAAL1CBRRate OBJECT-TYPE
        SYNTAX INTEGER
        MAX-ACCESS read-only
        STATUS current
        DESCRIPTION
            "This attribute describes the rate of the CBR service
            supported by the AAL."
        ::= { atmfAAL1ProfileEntry 3 }
 
    atmfAAL1ClkRecoveryType OBJECT-TYPE
        SYNTAX INTEGER {
                   synchronous (0),
                   srts(1),
                   adaptive (2)
               }
        MAX-ACCESS read-only
        STATUS current
        DESCRIPTION
            "This attribute indicates whether the clock recovery type is
            synchronous, asynchronous-SRTS(Synchronous Residual Time Stamp),
            or asynchronous-Adaptive Clock Recovery. "
        ::= { atmfAAL1ProfileEntry 4 }
 
    atmfAAL1FEC OBJECT-TYPE
        SYNTAX INTEGER {
                   noFEC (0),
                   lossSensitiveSignalFEC (1),
                   delaySensitiveSignalFEC (2)
               }
        MAX-ACCESS read-only
        STATUS current
        DESCRIPTION
            "This attribute indicates the FEC method: no FEC, FEC for
            Loss Sensitive Signal Transport, or FEC for Delay Sensitive
            Signal Transport. "
        ::= { atmfAAL1ProfileEntry 5 }

    atmfAAL1SDT OBJECT-TYPE
        SYNTAX INTEGER {
                   false (0),
                   true(1)
               }
        MAX-ACCESS read-only
        STATUS current
        DESCRIPTION
            "This attribute indicates whether Structured Data Transfer
            (SDT) has been configured at the AAL. A value of TRUE means
            SDT has been selected. This attribute value can be set to
            TRUE only when the Forward Error Correction Type attribute
            equals noFEC. "
        ::= { atmfAAL1ProfileEntry 6 }

    atmfAAL1PartiallyFilledCells OBJECT-TYPE
        SYNTAX INTEGER
        MAX-ACCESS read-only
        STATUS current
        DESCRIPTION
            "This attribute identifies the number of leading octets in
            use."
        ::= { atmfAAL1ProfileEntry 7 }
 
    atmfAAL1CellLossIntegrPeriod OBJECT-TYPE
        SYNTAX INTEGER
        MAX-ACCESS read-only
        STATUS current
        DESCRIPTION
            "This attribute represents the time in milliseconds for the
            cell loss integration period. If cells are lost for this
            period of time, the Interworking VCC Termination Point entity
            will generate a cell starvation alarm."
        ::= { atmfAAL1ProfileEntry 8 }

    ------------------------------------------------------------------
    -- ATM Forum ILMI Extension for Auto Configuration
    -- ATM AAL3/4 Profile
    ------------------------------------------------------------------
 
    atmfAAL34ProfileTable OBJECT-TYPE
        SYNTAX SEQUENCE OF AtmfAAL34ProfileEntry
        MAX-ACCESS not-accessible
        STATUS current
        DESCRIPTION
            "The ATM Forum ILMI Auto Configuration Extension AAL3/4
            Profile Information. "
        ::= { atmfAutoConfigGroup 4 }
 
    atmfAAL34ProfileEntry OBJECT-TYPE
        SYNTAX AtmfAAL34ProfileEntry
        MAX-ACCESS not-accessible
        STATUS current
        DESCRIPTION
            "An entry in the AAL34 Profile table provides data that
            describes the AAL3/4 processing function. "
        INDEX { atmfAAL34ProfileIndex }
        ::= { atmfAAL34ProfileTable 1 }
 
    AtmfAAL34ProfileEntry ::= SEQUENCE {
         atmfAAL34ProfileIndex            INTEGER,
         atmfAAL34MaxCpcsSduSizeForward   INTEGER,
         atmfAAL34MaxCpcsSduSizeBackward  INTEGER,
         atmfAAL34MIDRangeLow             INTEGER,
         atmfAAL34MIDRangeHigh            INTEGER,
         atmfAAL34AALMode                 INTEGER,
         atmfAAL34SscsType                INTEGER
    }

    atmfAAL34ProfileIndex OBJECT-TYPE
        SYNTAX INTEGER (1..2147483647)
        MAX-ACCESS read-only
        STATUS current
        DESCRIPTION
            "A number between which identifies the entry in the AAL3/4
            Profile Table. "
        ::= { atmfAAL34ProfileEntry 1 }

    atmfAAL34MaxCpcsSduSizeForward OBJECT-TYPE
        SYNTAX INTEGER (1..65535)
        MAX-ACCESS read-only
        STATUS current
        DESCRIPTION
            "This attribute represents the maximum CPCS_PDU size that will
            be transmitted over the connection in both the incoming
            (forward) direction of transmission. "
        ::= { atmfAAL34ProfileEntry 2 }
 
    atmfAAL34MaxCpcsSduSizeBackward OBJECT-TYPE
        SYNTAX INTEGER (1..65535)
        MAX-ACCESS read-only
        STATUS current
        DESCRIPTION
            "This attribute represents the maximum CPCS_PDU size that will
            be transmitted over the connection in both the outgoing
            (backward) direction of transmission. "
        ::= { atmfAAL34ProfileEntry 3 }
 
    atmfAAL34MIDRangeLow OBJECT-TYPE
        SYNTAX INTEGER (1..66536)
        MAX-ACCESS read-only
        STATUS current
        DESCRIPTION
            "This attribute represents the low value of MID supported at
            the AAL for the supporting VCC."
        ::= { atmfAAL34ProfileEntry 4 }
 
    atmfAAL34MIDRangeHigh OBJECT-TYPE
        SYNTAX INTEGER (1..66536)
        MAX-ACCESS read-only
        STATUS current
        DESCRIPTION
            "This attribute represents the high value of MID supported at
            the AAL for the supporting VCC."
        ::= { atmfAAL34ProfileEntry 5 }
 
    atmfAAL34AALMode OBJECT-TYPE
        SYNTAX INTEGER {
                   messageAssured (0),
                   messageUnassured (1),
                   streamingAssured (2),
                   streamingUnassured (3)
               }
        MAX-ACCESS read-only
        STATUS current
        DESCRIPTION
            "This attribute indicates whether the AAL for the supporting
            VCC is operating in message mode or streaming mode, assured or
            unassured. "
        ::= { atmfAAL34ProfileEntry 6 }
 
    atmfAAL34SscsType OBJECT-TYPE
        SYNTAX INTEGER {
                     null (0),
                     dataAssured (1),
                     dataNonAssured (2),
                     frameRelay (3)
               }
        MAX-ACCESS read-only
        STATUS current
        DESCRIPTION
            "This attribute identifies the SSCS type for the AAL. Valid
            values are NULL, Data SSCS based on SSCOP (assured operation),
            Data SSCS based on SSCOP (non-assured operation), or Frame
            Relay SSCS "
        ::= { atmfAAL34ProfileEntry 7 }
 
    ------------------------------------------------------------------
    -- ATM Forum ILMI Extension for Auto Configuration
    -- ATM AAL5 Profile
    ------------------------------------------------------------------
 
    atmfAAL5ProfileTable OBJECT-TYPE
        SYNTAX SEQUENCE OF AtmfAAL5ProfileEntry
        MAX-ACCESS not-accessible
        STATUS current
        DESCRIPTION
            "The ATM Forum ILMI Auto Configuration Extension AAL5
            Profile Information. "
        ::= { atmfAutoConfigGroup 5 }
 
    atmfAAL5ProfileEntry OBJECT-TYPE
        SYNTAX AtmfAAL5ProfileEntry
        MAX-ACCESS not-accessible
        STATUS current
        DESCRIPTION
            "An entry in the AAL5 Profile table provides data that
            describes the AAL5 processing function. "
        INDEX { atmfAAL5ProfileIndex }
        ::= { atmfAAL5ProfileTable 1 }
 
    AtmfAAL5ProfileEntry ::= SEQUENCE {
         atmfAAL5ProfileIndex           INTEGER,
         atmfAAL5MaxCpcsSduSizeForward  INTEGER,
         atmfAAL5MaxCpcsSduSizeBackward INTEGER,
         atmfAAL5AALMode                INTEGER,
         atmfAAL5SscsType               INTEGER
    }
 
    atmfAAL5ProfileIndex OBJECT-TYPE
        SYNTAX INTEGER (1..2147483647)
        MAX-ACCESS read-only
        STATUS current
        DESCRIPTION
            "A number between which identifies the entry in the AAL5
            Profile Table. "
        ::= { atmfAAL5ProfileEntry 1 }
 
    atmfAAL5MaxCpcsSduSizeForward OBJECT-TYPE
        SYNTAX INTEGER (1..65535)
        MAX-ACCESS read-only
        STATUS current
        DESCRIPTION
            "This attribute represents the maximum CPCS_PDU size that will
            be transmitted over the connection in both the incoming
            (forward) direction of transmission. "
        ::= { atmfAAL5ProfileEntry 2 }
 
    atmfAAL5MaxCpcsSduSizeBackward OBJECT-TYPE
        SYNTAX INTEGER (1..65535)
        MAX-ACCESS read-only
        STATUS current
        DESCRIPTION
            "This attribute represents the maximum CPCS_PDU size that will
            be transmitted over the connection in both the outgoing
            (backward) direction of transmission. "
        ::= { atmfAAL5ProfileEntry 3 }
 
    atmfAAL5AALMode OBJECT-TYPE
        SYNTAX INTEGER {
                     messageAssured (0),
                     messageUnassured (1),
                     streamingAssured (2),
                     streamingUnassured (3)
               }
        MAX-ACCESS read-only
        STATUS current
        DESCRIPTION
            "This attribute indicates whether the AAL for the supporting
            VCC is operating in message mode or streaming mode, assured or
            unassured. "
        ::= { atmfAAL5ProfileEntry 4 }
 
    atmfAAL5SscsType OBJECT-TYPE
        SYNTAX INTEGER {
                   null (0),
                   dataAssured (1),
                   dataNonAssured (2),
                   frameRelay (3)
               }
        MAX-ACCESS read-only
        STATUS current
        DESCRIPTION
            "This attribute identifies the SSCS type for the AAL. Valid
            values are NULL, Data SSCS based on SSCOP (assured operation),
            Data SSCS based on SSCOP (non-assured operation), or Frame
            Relay SSCS "
        ::= { atmfAAL5ProfileEntry 5 }
 
    ------------------------------------------------------------------
    -- ATM Forum ILMI Extension for Auto Configuration
    -- ATM Common AAL2 Profile
    -- In the case where an AAL2CommonProfileEntry contains parameter(s)
    -- which is/are set to a value that is/are not supported by the AAL2
    -- entity in the ATU-R, the user-side IME must raise an
    -- atmfAtmServiceConfFail trap towards the network-side IME. The
    -- atmfAtmServiceConfFailReason should be 'unsupportedAAL' and
    -- the atmfAtmServiceConfFailOID must point to the
    -- atmfAAL2CommonProfileEntry that contains the unsupported
    -- parameter(s).
    ------------------------------------------------------------------
 
    atmfAAL2CommonProfileTable OBJECT-TYPE
        SYNTAX SEQUENCE OF AtmfAAL2CommonProfileEntry
        MAX-ACCESS not-accessible
        STATUS current
        DESCRIPTION
            "The ATM Forum ILMI Auto Configuration Extension AAL2 Profile
            Information. This table contains AAL2 parameters that are common
            to all AAL2 applications. These parameters are taken from
            I.363.2, I.366.1 and I.366.2"
        ::= { atmfAutoConfigGroup 6 }

    atmfAAL2CommonProfileEntry OBJECT-TYPE
        SYNTAX AtmfAAL2CommonProfileEntry
        MAX-ACCESS not-accessible
        STATUS current
        DESCRIPTION
            "An atmfAAL2CommonProfileEntry provides AAL2 common parameters
            of operation that are to be used by the PVC associated with this entry."
        INDEX { atmfAAL2ProfileIndex }
        ::= { atmfAAL2CommonProfileTable 1 }
 
    AtmfAAL2CommonProfileEntry ::= SEQUENCE {
         atmfAAL2ProfileIndex                    INTEGER,
         atmfAAL2ApplicationIdentifier           INTEGER,
         atmfAAL2ConfigResponsibility            INTEGER,
         atmfAAL2CpsMaxMultiplexedChannels       INTEGER,
         atmfAAL2CpsMaxSduLength                 INTEGER,
         atmfAAL2SscsMaxSssarSduLength           INTEGER,
         atmfAAL2SscsSstedStatus                 INTEGER,
         atmfAAL2SscsSsadtStatus                 INTEGER,
         atmfAAL2SscsServiceCategory             INTEGER,
         atmfAAL2SscsAudioServiceTransport       INTEGER,
         atmfAAL2SscsProfileSource               INTEGER,
         atmfAAL2SscsIeeeOui                     INTEGER,
         atmfAAL2SscsPredefinedProfileIdentifier INTEGER,
         atmfAAL2SscsPcmEncoding                 INTEGER,
         atmfAAL2SscsFaxDemodulationTransport    INTEGER,
         atmfAAL2SscsCasSignalingTransport       INTEGER,
         atmfAAL2SscsDtmfDigitPacketTransport    INTEGER,
         atmfAAL2SscsMfR1DigitPacketTransport    INTEGER,
         atmfAAL2SscsMfR2DigitPacketTransport    INTEGER,
         atmfAAL2SscsCircuitModeDataTransport    INTEGER,
         atmfAAL2SscsCircuitModeDataNumChannels  INTEGER,
         atmfAAL2SscsFrameModeDataTransport      INTEGER,
         atmfAAL2SscsFrameModeDataMaxLength      INTEGER,
         atmfAAL2SscopSduLength                  INTEGER,
         atmfAAL2SscopUuFieldLength              INTEGER

    }

    atmfAAL2ProfileIndex OBJECT-TYPE
        SYNTAX INTEGER
        MAX-ACCESS read-only
        STATUS current
        DESCRIPTION
            "A number which uniquely identifies the entry in the AAL2
            Profile Table."
        ::= { atmfAAL2CommonProfileEntry 1 }

    atmfAAL2ApplicationIdentifier OBJECT-TYPE
        SYNTAX INTEGER
        MAX-ACCESS read-only
        STATUS current
        DESCRIPTION
        "The application identifier specifies which AAL2
        application is using the PVC. In addition it specifies
        protocol combinations to be used on AAL2 channels between
        IWFs, i.e. it implicitly configures the use of I.366.1 or
        I.366.2 for bearer and signalling AAL2 channels. The value
        of this object should be one of those values given in the
        administered list of AppIds for AAL2 Applications in
        section 5 of the ATM Forum document of well-known addresses
        and assigned codes which can be located at
        vhttp://www.atmforum.com/atmforum/specs/public_assigned_codes.pdf."
     ::= { atmfAAL2CommonProfileEntry 2 }
 
     atmfAAL2ConfigResponsibility OBJECT-TYPE
        SYNTAX INTEGER {
                ilmi (1),
                lesEoc (2),
                other (3)
                }
        MAX-ACCESS read-only
        STATUS current
        DESCRIPTION
           "This object identifies which management channel is
            responsible for AAL2 provisioning and auto-configuration.
            The user-side IME must check the value of this parameter
            first before configuring the AAL2 for the PVC to determine
            whether or not this responsibility lies with ILMI.
            ilmi - if this is selected then the user-side IME must use
            the AAL2 Profile defined in this entry and associated AAL2
            Profile extension table entry to auto-configure the AAL2
            for the PVC.
            lesEoc - if this is selected then the user-side IME must
            not auto-configure the AAL2 using ILMI. The AAL2 Profile
            parameters do not need to be provisioned by the network-
            side IME and with the exception of this object the AAL2
            profile parameters in the ILMI MIB are not applicable. The
            Loop Emulation Service Embedded Operations Channel (LES
            EOC) shall be used to provision the AAL2 for the PVC. The
            start-up AAL2 parameters for this PVC must assume the
            default values specified in the af-vmoa-0145.000 MIB such
            that the LES EOC is operational.
            other - if this is selected then the user-side IME must not
            auto-configure the AAL2 using ILMI. The AAL2 Profile
            parameters do not need to be provisioned by the network-
            side IME and with the exception of this object the AAL2
            profile parameters in the ILMI MIB are not applicable.
            Another mechanism will be used to provision the AAL2 at the
            ATU-R for the PVC."
        ::= { atmfAAL2CommonProfileEntry 3 }

    atmfAAL2CpsMaxMultiplexedChannels OBJECT-TYPE
      SYNTAX INTEGER (1..255)
        MAX-ACCESS read-only
        STATUS current
        DESCRIPTION         "Maximum number of multiplexed channels."
        DEFVAL { 255 }
        ::= { atmfAAL2CommonProfileEntry 4 }
 
    atmfAAL2CpsMaxSduLength OBJECT-TYPE
        SYNTAX INTEGER (45 | 64)
        MAX-ACCESS read-only
        STATUS current
        DESCRIPTION
            "Maximum CPS-SDU size given in octets. This parameter is
            bidirectional, i.e. its value applies to both directions of the
            AAL2 connection."
        DEFVAL { 45 }
        ::= { atmfAAL2CommonProfileEntry 5 }

    atmfAAL2SscsMaxSssarSduLength OBJECT-TYPE
        SYNTAX INTEGER (1..65568)
        MAX-ACCESS read-only
        STATUS current
        DESCRIPTION
            "This is the maximum size and SSSAR-SDU can take as defined
            in I.366.1. This parameter only applies to those AAL2 channels
            using I.366.1 SSSAR. This parameter is bidirectional, i.e its value
            applies to both directions of the AAL2 connection. Note that if the
            appID indicates Loop Emulation Service as the AAL2 application
            then the minimum allowable value of this parameter is 493."
        ::= { atmfAAL2CommonProfileEntry 6 }
 
    atmfAAL2SscsSstedStatus OBJECT-TYPE
        SYNTAX INTEGER {
                   selected(1),
                   notSelected(2)
               }
        MAX-ACCESS read-only
        STATUS current
        DESCRIPTION
            "This specifies whether the SSTED service is used or not.
            If the value of this object is 'selected' then I.366.1
            SSSAR must be supported by the AAL2. This parameter only
            applies to those AAL2 channels using I.366.1 SSSAR."
        ::= { atmfAAL2CommonProfileEntry 7 }
 
    atmfAAL2SscsSsadtStatus OBJECT-TYPE
        SYNTAX INTEGER {
                   selected(1),
                   notSelected(2)
               }
        MAX-ACCESS read-only
        STATUS current
        DESCRIPTION
            "This specifies whether SSADT service is used or not.
            Note that if the value of this object is 'selected' then
            I.366.1 SSSAR must be supported and by implication the SSTED
            service must also be 'selected'. This parameter only applies
            to those AAL2 channels using I.366.1 SSSAR."
        ::= { atmfAAL2CommonProfileEntry 8 }

    atmfAAL2SscsServiceCategory OBJECT-TYPE
        SYNTAX INTEGER {
                   audio (1),
                   multirate (2),
                   audioAndMultiRate (3)
               }
        MAX-ACCESS read-only
        STATUS current
        DESCRIPTION
            "This object describes the type of service category supported
            by this AAL2 PVC."
        DEFVAL { audio }
        ::= { atmfAAL2CommonProfileEntry 9 }
 
    atmfAAL2SscsAudioServiceTransport OBJECT-TYPE
        SYNTAX INTEGER {
                   disabled (1),
                   enabled (2)
               }
        MAX-ACCESS read-only
        STATUS current
        DESCRIPTION
            "This object describes whether the Audio Service that
            is used for transporting voice and voiceband data is enabled
            or disabled."
        DEFVAL { enabled }
        ::= { atmfAAL2CommonProfileEntry 10 }
 
    atmfAAL2SscsProfileSource OBJECT-TYPE
        SYNTAX INTEGER {
                   itut (1),
                   other (2)
               }
        MAX-ACCESS read-only
        STATUS current
        DESCRIPTION
            "This attribute describes the source of the profile. "
        DEFVAL { itut }
        ::= { atmfAAL2CommonProfileEntry 11 }
 
    atmfAAL2SscsIeeeOui OBJECT-TYPE
        SYNTAX INTEGER
        MAX-ACCESS read-only
        STATUS current
        DESCRIPTION
            "This attribute contains the IEEE Organizationally Unique
            Identifier (OUI) of the organisation that specified the
            profile being used, if other than ITU-T. For example, if
            the source is the ATM Forum, the value of this object is 00A03E.
            This attribute is only meaningful if atmfAAL2SccsProfileSource
            has the value 'other'."
        ::= { atmfAAL2CommonProfileEntry 12 }
 
    atmfAAL2SscsPredefinedProfileIdentifier OBJECT-TYPE
        SYNTAX INTEGER
        MAX-ACCESS read-only
        STATUS current
        DESCRIPTION
            "This object describes the predefined profile identifier."
        DEFVAL { 1 }
        ::= { atmfAAL2CommonProfileEntry 13 }
 
    atmfAAL2SscsPcmEncoding OBJECT-TYPE
        SYNTAX INTEGER {
                   aLaw (1),
                   ulaw (2)
               }
        MAX-ACCESS read-only
        STATUS current
        DESCRIPTION
            "This object describes the type of PCM encoding used."
        DEFVAL { aLaw }
        ::= { atmfAAL2CommonProfileEntry 14 }
 
    atmfAAL2SscsFaxDemodulationTransport OBJECT-TYPE
        SYNTAX INTEGER {
                   disabled (1),
                   enabled  (2)
               }
       MAX-ACCESS read-only
       STATUS current
       DESCRIPTION
           "This object describes whether transport of demodulated
           facsimile data is enabled or disabled."
       DEFVAL { disabled }
       ::= { atmfAAL2CommonProfileEntry 15 }
 
    atmfAAL2SscsCasSignalingTransport OBJECT-TYPE
        SYNTAX INTEGER {
                   disabled (1),
                   enabled (2)
               }
        MAX-ACCESS read-only
        STATUS current
        DESCRIPTION
            "This attribute describes whether transport of CAS
            signaling bits is enabled or disabled."
        DEFVAL { disabled }
        ::= { atmfAAL2CommonProfileEntry 16 }
 
    atmfAAL2SscsDtmfDigitPacketTransport OBJECT-TYPE
        SYNTAX INTEGER {
                     disabled (1),
                     enabled (2)
               }
        MAX-ACCESS read-only
        STATUS current
        DESCRIPTION
            "This attribute describes whether transport of DTMF dialled
            digits is enabled or disabled."
        DEFVAL { disabled }
        ::= { atmfAAL2CommonProfileEntry 17 }

    atmfAAL2SscsMfR1DigitPacketTransport OBJECT-TYPE
        SYNTAX INTEGER {
                     disabled (1),
                     enabled (2)
               }
        MAX-ACCESS read-only
        STATUS current
        DESCRIPTION
            "This object describes whether transport of MF-R1 dialled
            digits is enabled or disabled."
        DEFVAL { disabled }
        ::= { atmfAAL2CommonProfileEntry 18 }

    atmfAAL2SscsMfR2DigitPacketTransport OBJECT-TYPE
        SYNTAX INTEGER {
                     disabled (1),
                     enabled (2)
               }
        MAX-ACCESS read-only
        STATUS current
        DESCRIPTION
            "This object describes whether transport of MF-R2 dialled
            digits is enabled or disabled."
        DEFVAL { disabled }
        ::= { atmfAAL2CommonProfileEntry 19 }

    atmfAAL2SscsCircuitModeDataTransport OBJECT-TYPE
        SYNTAX INTEGER {
                     disabled (1),
                     enabled (2)
               }
        MAX-ACCESS read-only
        STATUS current
        DESCRIPTION
            "This object describes whether transport of circuit mode
            data is enabled or disabled."
        DEFVAL { disabled }
        ::= { atmfAAL2CommonProfileEntry 20 }

    atmfAAL2SscsCircuitModeDataNumChannels OBJECT-TYPE
        SYNTAX INTEGER (1..31)
        MAX-ACCESS read-only
        STATUS current
        DESCRIPTION
            "This object describes the multiplier N in N*64kbit/s
            circuit mode data. It is only applicable if the value of
            atmfAAL2SscsCircuitModeDataTransport is 'enabled'."
        DEFVAL { 1 }
        ::= { atmfAAL2CommonProfileEntry 21 }

    atmfAAL2SscsFrameModeDataTransport OBJECT-TYPE
        SYNTAX INTEGER {
                     disabled (1),
                     enabled (2)
               }
        MAX-ACCESS read-only
        STATUS current
        DESCRIPTION
            "This object describes whether the I.366.2 frame mode data
            service is enabled or disabled."
        DEFVAL { disabled }
        ::= { atmfAAL2CommonProfileEntry 22 }

    atmfAAL2SscsFrameModeDataMaxLength OBJECT-TYPE
        SYNTAX INTEGER (1..65535)
        MAX-ACCESS read-only
        STATUS current
        DESCRIPTION
            "This object specifies the maximum length of I.366.2
            frame mode data. It is only applicable if the value
            of atmfAAL2FrameModeDataTransport is 'enabled'."
        ::= { atmfAAL2CommonProfileEntry 23 }

   atmfAAL2SscopSduLength OBJECT-TYPE
       SYNTAX INTEGER (1..65524)
       MAX-ACCESS read-only
       STATUS current
       DESCRIPTION
           "The Maximum SSCOP-SDU length. This object is only required
           is the value of atmfAAL2SscsSsadtStatus is selected else it
           is not applicable."
       ::= { atmfAAL2CommonProfileEntry 24 }

   atmfAAL2SscopUuFieldLength OBJECT-TYPE
       SYNTAX INTEGER (1..65524)
       MAX-ACCESS read-only
       STATUS current
       DESCRIPTION
          "The Maximum SSCOP-UU field length. This object is only
          required is the value of atmfAAL2SscsSsadtStatus is
          selected else it is not applicable."
      ::= { atmfAAL2CommonProfileEntry 25 }

    ------------------------------------------------------------------
    -- ATM Forum ILMI Extension for Auto Configuration
    -- ATM Trunking AAL2 Profile
    ------------------------------------------------------------------

    atmfAAL2TrunkingProfileTable OBJECT-TYPE
        SYNTAX SEQUENCE OF AtmfAAL2TrunkingProfileEntry
        MAX-ACCESS not-accessible
        STATUS current
        DESCRIPTION
            "The ATM Forum ILMI Auto Configuration Extension AAL2
            Profile Information. This table contains AAL2 parameters
            that are specific to the ATM Trunking AAL 2 application.
            These parameters are taken from af-vtoa-0113.000"
        ::= { atmfAutoConfigGroup 7 }

    atmfAAL2TrunkingProfileEntry OBJECT-TYPE
        SYNTAX AtmfAAL2TrunkingProfileEntry
        MAX-ACCESS not-accessible
        STATUS current
        DESCRIPTION
            "An atmfAAL2TrunkingProfileEntry provides AAL2 parameters
            of operation for ATM Trunking applications to be used in
            addition to those provided in the Common AAL2 Profile Table.
            These together provide complete configuration of AAL2 for
            PVCs that support ATM Trunking using AAl2 as defined in
            af-vtoa-0113.000."
        INDEX { atmfAAL2ProfileIndex }
        ::= { atmfAAL2TrunkingProfileTable 1 }

    AtmfAAL2TrunkingProfileEntry ::= SEQUENCE {
         atmfAAL2Vcci           INTEGER,
         atmfAAL2SignalingVcci  INTEGER
    }

    atmfAAL2Vcci OBJECT-TYPE
        SYNTAX INTEGER
        MAX-ACCESS read-only
        STATUS current
        DESCRIPTION
            "This object uniquely identifies a PVC between IWFs."
        ::= { atmfAAL2TrunkingProfileEntry 1 }

    atmfAAL2SignalingVcci OBJECT-TYPE
        SYNTAX INTEGER
        MAX-ACCESS read-only
        STATUS current
        DESCRIPTION
            "This object specifies the VCCI of the PVC that is used
            to carry the CCS for this PVC."
        ::= { atmfAAL2TrunkingProfileEntry 2 }

    ------------------------------------------------------------------
    -- ATM Forum ILMI Extension for Auto Configuration
    -- ATM LES AAL2 Profile
    -- In the case where an AAL2LESProfileEntry contains parameter(s)
    -- which is/are set to a value that is/are not supported by the AAL2
    -- entity in the ATU-R, the user-side IME must raise an
    -- atmfAtmServiceConfFail trap towards the network-side IME. The
    -- atmfAtmServiceConfFailReason should be 'unsupportedAAL' and
    -- the atmfAtmServiceConfFailOID must point to the
    -- atmfAAL2LESProfileEntry that contains the unsupported
    -- parameter(s).
    ------------------------------------------------------------------

    atmfAAL2LESProfileTable OBJECT-TYPE
        SYNTAX SEQUENCE OF AtmfAAL2LESProfileEntry
        MAX-ACCESS not-accessible
        STATUS current
        DESCRIPTION
            "The ATM Forum ILMI Auto Configuration Extension AAL2 Profile
            Information. This table contains AAL2 parameters that are
            specific to the ATM LES AAL 2 application. These parameters
            are taken from af-vmna-0145.000"
        ::= { atmfAutoConfigGroup 8 }

    atmfAAL2LESProfileEntry OBJECT-TYPE
        SYNTAX AtmfAAL2LESProfileEntry
        MAX-ACCESS not-accessible
        STATUS current
        DESCRIPTION
            "An atmfAAL2LESProfileEntry provides AAL2 parameters of
            operation for LES applications to be used in addition to
            those provided in the Common AAL2 Profile Table. These together
            provide complete configuration of AAL2 for PVCs that support
            LES using AAl2 as defined in af-vmoa-0145.000."
        INDEX { atmfAAL2ProfileIndex }
        ::= { atmfAAL2LESProfileTable 1 }

    AtmfAAL2LESProfileEntry ::= SEQUENCE {
         atmfAAL2CpsCIDLowerLimit  INTEGER,
         atmfAAL2CpsCIDUpperLimit  INTEGER,
         atmfAAL2CpsOptimisation   INTEGER
    }

    atmfAAL2CpsCIDLowerLimit OBJECT-TYPE
        SYNTAX INTEGER (16..223)
        MAX-ACCESS read-only
        STATUS current
        DESCRIPTION
            "The minimum value the CID can take for AAL2 bearer channels
            and ISDN-D channels."
        DEFVAL { 16 }
        ::= { atmfAAL2LESProfileEntry 1 }

    atmfAAL2CpsCIDUpperLimit OBJECT-TYPE
        SYNTAX INTEGER (16..223)
        MAX-ACCESS read-only
        STATUS current
        DESCRIPTION
            " The maximum value the CID can take for AAL2 bearer channels
            and ISDN-D channels."
        DEFVAL { 223 }
        ::= { atmfAAL2LESProfileEntry 2 }

    atmfAAL2CpsOptimisation OBJECT-TYPE
        SYNTAX     INTEGER {
                        singleCpsPacketPerCpsPduNoOverlap(1),
                        multipleCpsPacketsPerCpsPduWithOverlap(2)
                   }
        MAX-ACCESS  read-only
        STATUS current
        DESCRIPTION
            "This object refers to the mode of operation of the CPS on the
            CP-IWF The value of this object imposes a restriction on the
            CPS-SDU length and hence must override the value of     atmfAAl2CpsMaxSDULength.
            singleCpsPacketPerCpsPduNoOverlap -A single CPS Packet is contained
            within a CPS-PDU and no overlap can occur into the next CPS-PDU.
            If this option is selected, then Timer_CU is not applicable.
            Also Max CPS-SDU size must be less than or equal to 44.
            multipleCpsPacketsPerCpsPduWithOverlap - Multiple CPS Packets are
            contained within a CPS-PDU and overlap can occur into the next CPS-PDU. If
            this option is selected, then Timer_CU is applicable.
            Also Max CPS-SDU size must be less than or equal to 64."
        DEFVAL { singleCpsPacketPerCpsPduNoOverlap }
         ::= { atmfAAL2LESProfileEntry 3 }

    ------------------------------------------------------------------
    -- ATM Forum ILMI Extension for Auto Configuration
    -- atmfAtmServicePhyMacIdentifier
    ------------------------------------------------------------------

    atmfAtmServiceConnInfoExtensionTable OBJECT-TYPE
        SYNTAX SEQUENCE OF AtmfAtmServiceConnInfoExtensionEntry
        MAX-ACCESS not-accessible
        STATUS current
        DESCRIPTION
            "The ATM Forum ILMI Auto Configuration Extension ATM
            Service Connection Information. "
        ::= { atmfAutoConfigGroup 9 }

    atmfAtmServiceConnInfoExtensionEntry OBJECT-TYPE
        SYNTAX AtmfAtmServiceConnInfoExtensionEntry
        MAX-ACCESS not-accessible
        STATUS current
        DESCRIPTION
          "An entry in the service connection information extension table
        provides additional elements that help describe the ATM connection
        that provides a service across an ATM interface. The connection
        is identified by port and VPI/VCI value."
        AUGMENTS { atmfAtmServiceConnInfoEntry }
        ::= { atmfAtmServiceConnInfoExtensionTable 1 }

    AtmfAtmServiceConnInfoExtensionEntry ::= SEQUENCE {
         atmfAtmServicePhyMacIdentifier INTEGER
    }

    atmfAtmServicePhyMacIdentifier OBJECT-TYPE
        SYNTAX INTEGER
        MAX-ACCESS read-only
        STATUS current
        DESCRIPTION
            " When the physical and/or MAC layer has more than one
            PHY-connection or MAC-connection, this object is used to
            select the PHY- or MAC-connection to be bound to the PVC.
            The semantics of the value of this object is PHY and/or
            MAC specific. This semantics generally shall be specified
            with the PHY or MAC. However, the semantics for the two
            PHY/MAC specifications which have been identified as having
            multiple connections is provided here for convenience:
 
          When the physical layer is dual latency ADSL, the PhyMacIdentifier
            selects the latency path to be bound to each direction of
            transmission for the PVC. The value of the PhyMacIdentifier
            shall be as follows:
                default = 0
                upstream and downstream both interleaved path = 1
                upstream and downstream both fast path = 2
                upstream interleaved path, downstream fast path = 3
                upstream fast path, downstream interleaved path = 4
          The 'default' value shall be used for single latency ADSL PHYs.

            When the physical and MAC layers are IEEE 802.14, the
            PhyMacIdentifier specifies the 802.14 Local Identifier for the PVC"
        ::= { atmfAtmServiceConnInfoExtensionEntry 1  }

    ------------------------------------------------------------------
    -- ATM Forum ILMI Extension for Auto Configuration
    -- Layer 2 and Layer 3 Protocol ID
    ------------------------------------------------------------------

    atmfAtmServiceTypeExtensionTable OBJECT-TYPE
        SYNTAX SEQUENCE OF AtmfAtmServiceTypeExtensionEntry
        MAX-ACCESS not-accessible
        STATUS current
        DESCRIPTION
            "The ATM Forum ILMI Auto Configuration Extension ATM
            Service Type Extension Information. "
        ::= { atmfAutoConfigGroup 10 }

    atmfAtmServiceTypeExtensionEntry OBJECT-TYPE
        SYNTAX AtmfAtmServiceTypeExtensionEntry
        MAX-ACCESS not-accessible
        STATUS current
        DESCRIPTION
            "An entry in the service type extension table describes additional
            information about a service that may be associated with individual
            ATM connections for the purpose of auto-configuration. This
            information describes the Client Protocol ID's associated with a
            particular service."
        AUGMENTS { atmfAtmServiceTypeEntry }
        ::= { atmfAtmServiceTypeExtensionTable 1 }

    AtmfAtmServiceTypeExtensionEntry ::= SEQUENCE {
         atmfAtmServiceLayer2ProtocolId OCTET STRING,
         atmfAtmServiceLayer3ProtocolId OCTET STRING
    }

    atmfAtmServiceLayer2ProtocolId OBJECT-TYPE
        SYNTAX OCTET STRING
        MAX-ACCESS read-only
        STATUS current
        DESCRIPTION
            "This object shall be used to select the user plane layer 2
            protocol (if any) to be used above the AAL. The first octet
            of this object shall be encoded as follows. Bits 5-7 (i.e.
            the three most significant bits) shall be set to 0; any other
            values shall be ignored. Bits 0-4 (i.e. the five least significant
            bits) shall be encoded as shown in the entry for 'User information
            layer 2 protocol (octet 6)' in Table 4-10/Q.2931. However, if no
            user plane layer 2 protocol is present above the AAL, then the
            first (and only) octet shall be encoded as '0b00000000'. If the
            encoding of the first octet requires subsequent octets, then bit 7
            (i.e., the most significant bit) of each of these octets shall be
            set to 0; however, if it is set to 1, it shall be ignored. Bits 0-6
            shall be encoded according to table 4-10/Q.2931. If more than one
            subsequent octet is needed, then octets shall appear in the order
            shown in figure 4-16/Q.2931."
        ::= { atmfAtmServiceTypeExtensionEntry 1 }

    atmfAtmServiceLayer3ProtocolId OBJECT-TYPE
        SYNTAX OCTET STRING
        MAX-ACCESS read-only
        STATUS current
        DESCRIPTION
            "This object shall be used to select a user plane layer 3 protocol
          (or user plane layer 2 bridging). The first octet of this object
          shall be encoded as follows. Bits 5-7 (i.e., the three most
          significant bits) shall be set to 0; any other values shall be
          ignored. Bits 0-4 (i.e., the five least significant bits) shall be
          encoded as shown in the entry for 'User information layer 3
          protocol (octet 7)' in Table 4-10/Q.2931. However, if no user plane
          layer 3 protocol is specified, then the first (and only) octet
          shall be encoded as '0b00000000'.
            a) If ISO TR9577 network layer protocol identification is to be
          used, then the first octet shall be encoded to indicate 'ISO/IEC
          TR9577'. In this case, either:
            i) the user plane layer 3 protocol is to be selected in the
            management plane. The second octet of this object shall
            contain the ISO/IEC TR9577 Initial Protocol Identifier (IPI).
            - For layer 3 protocols for which ISO/IEC has assigned a
            Network Layer Protocol Identifier (NLPID), then this NLPID
            shall be used as the IPI, and the length of the octet
            string shall be 2.
            - For layer 3 protocols for which ISO/IEC has not assigned
            an NLPID, the IPI shall be encoded to indicate 'IEEE
            802.1a SNAP identifier' (see Annex D of ISO/IEC 9577). The
            following five octets (octets 3 through 7) of this object
            shall then contain a SNAP identifier, which consists of a
            3-octet organization unique identifier (OUI) and a 2-octet
            protocol identifier (PID). This SNAP coding shall be used
            only if ISO/IEC has not assigned a Network Layer Protocol
            Identifier for the layer 3 or layer 2 protocol. The octet
            string shall thus be 7 octets long.
            - If an IME wishes to indicate that bridged LAN frames are
            to be carried in the user plane then the IPI shall be
            encoded to indicate 'IEEE 802.1a SNAP identifier'. The
            following five octets of this object shall contain a SNAP
            identifier, which indicates the bridged protocol.
            For consistency with SIG 4.0, use of the ISO/IEC subsequent
            protocol identifier (SPI) is not recommended but not explicitly
            prohibited as one can envision scenarios where it has utility.
            or
            ii) the user plane layer 3 protocol is to be selected using
            network layer protocol identification in the user plane. The
            octet-string shall be one octet long. The first octet(s) of
            each layer 3 protocol data unit shall contain layer 3
            protocol identification according to ISO/IEC TR9577.

            b)If bits 0-4 of the first octet of the octet string are set to any
            value other than 'ISO/IEC TR9577', then any subsequent octets shall
            be encoded as follows. Bit 7 (i.e., the most significant bit) of
            each of these octets shall be set to 0; however, if it is set to 1,
            it shall be ignored. Bits 0-6 shall be encoded according to the
            codings for octet 7a, octet 7b and octet 7c specified in table 4-
            10/Q.2931. If more than one subsequent octet is needed, then octets
            shall appear in the order shown in figure 4-16/Q.2931."
        ::= { atmfAtmServiceTypeExtensionEntry 2}

    ------------------------------------------------------------------
    -- ATM Forum ILMI Extension for Auto Configuration
    -- AAL5 Profile Extension Table
    -- This extension is required for supporting AAL2 trunking
    ------------------------------------------------------------------
 
    atmfAAL5ProfileExtensionTable OBJECT-TYPE
        SYNTAX SEQUENCE OF AtmfAAL5ProfileExtensionEntry
        MAX-ACCESS not-accessible
        STATUS current
        DESCRIPTION
            "Additional parameters for the AAL5 Profile are stored in
             this table."
        ::= { atmfAutoConfigGroup 11 }
 
    atmfAAL5ProfileExtensionEntry OBJECT-TYPE
        SYNTAX AtmfAAL5ProfileExtensionEntry
        MAX-ACCESS not-accessible
        STATUS current
        DESCRIPTION
            "An entry in this table augments an entry in the
          atmfAAL5ProfileTable"
        AUGMENTS { atmfAAL5ProfileEntry }
        ::= { atmfAAL5ProfileExtensionTable 1 }
 
    AtmfAAL5ProfileExtensionEntry ::= SEQUENCE {
          atmfAAL5Vcci    INTEGER
    }
 
    atmfAAL5Vcci OBJECT-TYPE
        SYNTAX INTEGER
        MAX-ACCESS read-only
        STATUS current
        DESCRIPTION
            "This object's value is only applicable if the AAL5 VCC is
            carrying CCS for AAL2 narrowband calls."
        ::= { atmfAAL5ProfileExtensionEntry 1 }

    ------------------------------------------------------------------
    -- ATM Forum ILMI Extension for Auto Configuration
    -- Configuration Failed Trap
    ------------------------------------------------------------------

    atmfAtmServiceConfFail TRAP-TYPE
        ENTERPRISE atmForum
        VARIABLES { atmfAtmServiceConfFailReason, atmfAtmServiceConfFailOID }
        DESCRIPTION
           "The user-side IME will send this trap whenever it
            is unable to configure itself based on the information
            provided in the ILMI auto-configuration MIB. The variables
            included in the trap identify the reason for the failure
            and the row in the MIB table that caused the failure. "
        ::= 3

     atmfAtmServiceConfFailReason OBJECT-TYPE
         SYNTAX    INTEGER {
                             unsupportedClientProtocol (1),
                             unsupportedServiceCategory (2),
                             unsupportedAAL (3),
                             invalidVPIVCIValue (4),
                             tooManyPVCs (5),
                             incompleteConfigurationInformation (6),
                             inconsistentConfigurationInformation (7)
                   }
         MAX-ACCESS   read-only
         STATUS    current
         DESCRIPTION
             "The reason for the failure to configure the PVC at the ATU-R"
         ::= { atmfAutoConfigGroup 12 }

     atmfAtmServiceConfFailOID OBJECT-TYPE
         SYNTAX RowPointer
         MAX-ACCESS read-only
         STATUS current
         DESCRIPTION
             "This object holds a pointer to a row in the appropriate
             table depending on the value of the atmfAtmServiceFailReason
             object. This will allow the network side to determine MIB
             information that caused the auto-configuration failure.
             The value of this object should be as follows:
             If atmfAtmServiceConfFailReason = 1 or 2, then this object's
             value points to the row in the atmfAtmServiceTypeTable that
             is the cause of the problem.
             If atmfAtmServiceConfFailReason = 3, then this object's value
             points to the row in the atmfAALxProfileTable, where x is
             1, 2, 34, or 5 depending on the AAL that can't be supported.
             If atmfAtmServiceConfFailReason = 4, then this object's value
             points to the row in the atmfAtmServiceConnInfoTable that is
             the cause of the problem.
             For any other value of atmfAtmServiceConfFailReason, this
             object's value should be ignored."
         ::= { atmfAutoConfigGroup 13 }

END
