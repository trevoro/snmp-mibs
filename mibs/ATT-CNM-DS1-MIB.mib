-- SCCS version: "@(#)att_ds1.mib	4.1.2.2"

--
--		Copyright 1992 AT&T
--		All Rights Reserved
--
--	NOTICE
--	------
--	The information in this document is subject to change
--	without notice. AT&T assumes no responsibility for
--	any errors that may appear in this document.
--
--	Notwithstanding any other lease or license agreement
--	that may pertain to, or accompany the delivery of,
--	this computer software, the rights of the Government
--	regarding its use, reproduction and disclosure are as
--	set forth in Government contract no. GS00K89AGS6495.
--

--
-- Title: AT&T DS1 MIB for Customer Network Management
--


        ATT-CNM-DS1-MIB DEFINITIONS ::= BEGIN

        IMPORTS
		enterprises, Gauge
                        FROM RFC1155-SMI
                DisplayString
                        FROM RFC1213-MIB
                OBJECT-TYPE
                        FROM RFC-1212;

	--
	-- Object Identifiers
	--

        att-2		OBJECT IDENTIFIER ::= { enterprises 74 }
        att-products	OBJECT IDENTIFIER ::= { att-2 1 }
        att-mgmt	OBJECT IDENTIFIER ::= { att-2 2 }
        att-cnmAgent	OBJECT IDENTIFIER ::= { att-products 9 }
        att-cnm		OBJECT IDENTIFIER ::= { att-mgmt 15 }
        att-cnm-ds1	OBJECT IDENTIFIER ::= { att-cnm 3 }


	--
	-- the DS1 group of objects (att-cnm-ds1) include:
	--
	--	the DS1 Configuration table
	--	the DS1 Status table
	--	the DS1 Error Counts table
	--


	-- the DS1 Configuration table

	--
	-- This table provides configuration information
	-- on the DS1 interfaces supported by this system.
	--

	attCNMds1ConfigTable OBJECT-TYPE
		SYNTAX	SEQUENCE OF AttCNMds1ConfigEntry
		ACCESS  not-accessible
		STATUS  mandatory
		DESCRIPTION
			"A list of entries containing configuration
			information for all DS1 interfaces managed by
			this system."
		::= { att-cnm-ds1 1 }

	attCNMds1ConfigEntry OBJECT-TYPE
		SYNTAX  AttCNMds1ConfigEntry
		ACCESS  not-accessible
		STATUS  mandatory
		DESCRIPTION
			"An entry containing configuration information
			for a particular DS1 interface."
		INDEX	{ attCNMds1ConfigIndex }
		::= { attCNMds1ConfigTable 1 }

	AttCNMds1ConfigEntry ::=
		SEQUENCE {
		    attCNMds1ConfigIndex
			INTEGER,
		    attCNMds1LineType
			INTEGER,
		    attCNMds1ZeroCoding
			INTEGER,
		    attCNMds1ErrorsMaxIntervals
			INTEGER,
		    attCNMds1ErrorsIntervalLen
			INTEGER
		}

	attCNMds1ConfigIndex OBJECT-TYPE
		SYNTAX  INTEGER
		ACCESS  read-only
		STATUS  mandatory
		DESCRIPTION
			"A unique value for each DS1 interface. The interface
			identified by a particular value of this index is
			the same interface as identified by the same value
			of an attCNMifConfigIndex object instance."
		::= { attCNMds1ConfigEntry 1 }

	attCNMds1LineType OBJECT-TYPE
		SYNTAX	INTEGER {
			    other(1),
			    ds1ESF(2),
			    ds1D4(3),
			    ds1ANSI-ESF(4),
			    ds1G704(5),
			    ds1G704-CRC(6)
			}
		ACCESS	read-only
		STATUS	mandatory
		DESCRIPTION
			"This variable indicates the variety of DS1 frame
			format supported by this interface.

			For SMDS, this variable will have the value
			ds1ANSI-ESF, denoting that this interface
			supports the DS1 Extended Super Frame format
			as specified by ANSI."
		::= { attCNMds1ConfigEntry 2 }

	attCNMds1ZeroCoding OBJECT-TYPE
		SYNTAX	INTEGER {
			    ds1JammedBit(1),
			    ds1B8ZS(2),
			    ds1InvertedHDLC(3),
			    ds1HDB3(4),
			    ds1ZBTSI(5)
			}
		ACCESS	read-only
		STATUS	mandatory
		DESCRIPTION
			"This variable describes the variety of zero
			code suppression/substitution used on the DS1
			interface."
		::= { attCNMds1ConfigEntry 3 }

	attCNMds1ErrorsMaxIntervals OBJECT-TYPE
		SYNTAX	INTEGER
		ACCESS	read-only
		STATUS	mandatory
		DESCRIPTION
			"This variable identifies the maximum number
			of measurement intervals supported for the
			error counts maintained by this DS1 interface
			in the attCNMds1ErrorsTable."
		::= { attCNMds1ConfigEntry 4 }

	attCNMds1ErrorsIntervalLen OBJECT-TYPE
		SYNTAX	INTEGER
		ACCESS	read-only
		STATUS	mandatory
		DESCRIPTION
			"This variable identifies the number of seconds
			that make up one complete measurement interval for
			the error counts maintained by this DS1 interface
			in the attCNMds1ErrorsTable."
		::= { attCNMds1ConfigEntry 5 }

	-- the DS1 Status table

	--
	-- This table provides status information
	-- on the DS1 interfaces supported by this system.
	--

	attCNMds1StatusTable OBJECT-TYPE
		SYNTAX	SEQUENCE OF AttCNMds1StatusEntry
		ACCESS  not-accessible
		STATUS  mandatory
		DESCRIPTION
			"A list of entries containing status information
			for all DS1 interfaces managed by this system."
		::= { att-cnm-ds1 2 }

	attCNMds1StatusEntry OBJECT-TYPE
		SYNTAX  AttCNMds1StatusEntry
		ACCESS  not-accessible
		STATUS  mandatory
		DESCRIPTION
			"An entry containing status information for a
			particular DS1 interface."
		INDEX	{ attCNMds1StatusIndex }
		::= { attCNMds1StatusTable 1 }

	AttCNMds1StatusEntry ::=
		SEQUENCE {
		    attCNMds1StatusIndex
			INTEGER,
		    attCNMds1LineStatus
			INTEGER
		}

	attCNMds1StatusIndex OBJECT-TYPE
		SYNTAX  INTEGER
		ACCESS  read-only
		STATUS  mandatory
		DESCRIPTION
			"A unique value for each DS1 interface. The interface
			identified by a particular value of this index is
			the same interface as identified by the same value
			of an attCNMifConfigIndex object instance."
		::= { attCNMds1StatusEntry 1 }
	
	attCNMds1LineStatus OBJECT-TYPE
		SYNTAX	INTEGER
		ACCESS	read-only
		STATUS	mandatory
		DESCRIPTION
			"This variable indicates the most Line Status
			of this interface. This object is a bit map
			represented as a sum, therefore, it can represent
			multiple failures (alarms) simultaneously. The
			various bit positions are:

				1	No Alarm Present
				2	Yellow Alarm
				4	Near End Alarm-Indication-Signal (AIS)
				8	Near End Loss-Of-Frame (LOF)
				16	Near End Loss-Of-Signal (LOS)

			For example, for an interface that has LOF and
			LOS outstanding, this object will have a value
			of 24."
		::= { attCNMds1StatusEntry 2 }


	-- the DS1 Error Counts table

	--
	-- This table provides counts on the various protocol
	-- errors encountered by a DS1 interface during the
	-- specified measurement interval.
	--

	attCNMds1ErrorsTable OBJECT-TYPE
		SYNTAX	SEQUENCE OF AttCNMds1ErrorsEntry
		ACCESS  not-accessible
		STATUS  mandatory
		DESCRIPTION
			"A list of entries containing protocol error counts,
			maintained during the specified measurement interval,
			for all DS1 interfaces managed by this system."
		::= { att-cnm-ds1 3 }

	attCNMds1ErrorsEntry OBJECT-TYPE
		SYNTAX  AttCNMds1ErrorsEntry
		ACCESS  not-accessible
		STATUS  mandatory
		DESCRIPTION
			"An entry containing protocol error counts,
			maintained during the specified measurement interval,
			for a particular DS1 interface."
		INDEX	{ attCNMds1ErrorsIndex,
				attCNMds1ErrorsInterval }
		::= { attCNMds1ErrorsTable 1 }

	AttCNMds1ErrorsEntry ::=
		SEQUENCE {
		    attCNMds1ErrorsIndex
			INTEGER,
		    attCNMds1ErrorsInterval
			INTEGER,
		    attCNMds1ErrorsTimeStamp
			INTEGER,
		    attCNMds1ErrorsLocalTime
			DisplayString,
		    attCNMds1LCVs
			Gauge,
		    attCNMds1LESs
			Gauge,
		    attCNMds1LSESs
			Gauge,
		    attCNMds1CVs
			Gauge,
		    attCNMds1ESs
			Gauge,
		    attCNMds1SESs
			Gauge,
		    attCNMds1SEFSs
			Gauge,
		    attCNMds1UASs
			Gauge
		}

	attCNMds1ErrorsIndex OBJECT-TYPE
		SYNTAX	INTEGER
		ACCESS	read-only
		STATUS	mandatory
		DESCRIPTION
			"A unique value for each DS1 interface. The interface
			identified by a particular value of this index is
			the same interface as identified by the same value
			of an attCNMifConfigIndex object instance."
		::= { attCNMds1ErrorsEntry 1 }

	attCNMds1ErrorsInterval OBJECT-TYPE
		SYNTAX  INTEGER
		ACCESS  read-only
		STATUS  mandatory
		DESCRIPTION
			"This variable identifies the measurement interval
			number for which the measurement is provided. It is
			a number between 1 and XX, where 1 identifies the
			most recently completed measurement interval and XX
			is the least recently completed measurement interval.

			The value of XX is specified by the
			attCNMds1ErrorsMaxIntervals object given in the
			attCNMds1ConfigTable.

			The maximum length of each measurement interval is
			specified by the attCNMds1ErrorsIntervalLen object
			given in the attCNMds1ConfigTable."
		::= { attCNMds1ErrorsEntry 2 }

	attCNMds1ErrorsTimeStamp OBJECT-TYPE
		SYNTAX  INTEGER
		ACCESS  read-only
		STATUS  mandatory
		DESCRIPTION
			"The time stamp corresponding to the end of the
			specified measurement interval, as measured in
			seconds from 00:00:00 UTC (Coordinated Universal
			Time) January 1, 1970. Any fraction is rounded up."
		::= { attCNMds1ErrorsEntry 3 }

	attCNMds1ErrorsLocalTime OBJECT-TYPE
		SYNTAX  DisplayString(SIZE(0..255))
		ACCESS  read-only
		STATUS  mandatory
		DESCRIPTION
			"The time stamp corresponding to the end of the
			specified measurement interval.  Any fraction is
			rounded up. It is given as a printable ASCII string
			showing the local time at the end of the interval."
		::= { attCNMds1ErrorsEntry 4 }

	attCNMds1LCVs OBJECT-TYPE
		SYNTAX	Gauge
		ACCESS	read-only
		STATUS	mandatory
		DESCRIPTION
			"The counter associated with the number of Line
			Code Violations encountered by a DS1 interface
			during the specified measurement interval.

			A Line Code Violation is the occurrence of a
			received Bipolar Violation that is not part of a
			zero-substitution code.

			The Bipolar Violation Rate is generally viewed as
			approximating the Bit Error Rate."
		::= { attCNMds1ErrorsEntry 5 }

	attCNMds1LESs OBJECT-TYPE
		SYNTAX	Gauge
		ACCESS	read-only
		STATUS	mandatory
		DESCRIPTION
			"The counter associated with the number of Line
			Errored Seconds encountered by a DS1 interface
			during the specified measurement interval.

			A Line Errored Second is any second with at least
			one Line Code Violation."
		::= { attCNMds1ErrorsEntry 6 }

	attCNMds1LSESs OBJECT-TYPE
		SYNTAX	Gauge
		ACCESS	read-only
		STATUS	mandatory
		DESCRIPTION
			"The counter associated with the number of Line
			Severely Errored Seconds encountered by a DS1
			interface during the specified measurement interval.

			A Line Severely Errored Second is any second with
			16 or more Lince Code Violations monitored at the
			DS1 rate."
		::= { attCNMds1ErrorsEntry 7 }

	attCNMds1CVs OBJECT-TYPE
		SYNTAX	Gauge
		ACCESS	read-only
		STATUS	mandatory
		DESCRIPTION
			"The counter associated with the number of Code
			Violations encountered by a DS1 interface during
			the specified measurement interval.

			A Code Violation is the occurrence of a received
			CRC-6 code that is not identical to the corresponding
			locally-calculated code."
		::= { attCNMds1ErrorsEntry 8 }

	attCNMds1ESs OBJECT-TYPE
		SYNTAX	Gauge
		ACCESS	read-only
		STATUS	mandatory
		DESCRIPTION
			"The counter associated with the number of Errored
			Seconds encountered by a DS1 interface during the
			specified measurement interval.

			An Errored Second is any second with at least one
			Code Violation."
		::= { attCNMds1ErrorsEntry 9 }

	attCNMds1SESs OBJECT-TYPE
		SYNTAX	Gauge
		ACCESS	read-only
		STATUS	mandatory
		DESCRIPTION
			"The counter associated with the number of Severely
			Errored Seconds encountered by a DS1 interface
			during the specified measurement interval.

			A Severely Errored Second is any second with 15 or
			more Code Violations monitored at the DS1 rate."
		::= { attCNMds1ErrorsEntry 10 }

	attCNMds1SEFSs OBJECT-TYPE
		SYNTAX	Gauge
		ACCESS	read-only
		STATUS	mandatory
		DESCRIPTION
			"The counter associated with the number of Severely
			Errored Framing Seconds encountered by a DS1
			interface during the specified measurement interval.

			A Severely Errored Framing Second is any second
			during which one or more Severely Errored Framing
			(SEF) events occurred."
		::= { attCNMds1ErrorsEntry 11 }

	attCNMds1UASs OBJECT-TYPE
		SYNTAX	Gauge
		ACCESS	read-only
		STATUS	mandatory
		DESCRIPTION
			"The counter associated with the number of
			Unavailable Seconds encountered by a DS1
			interface during the specified measurement interval.

			An Unavailable Second is any second during which
			the DS1 interface was unavailable to offer service."
		::= { attCNMds1ErrorsEntry 12 }


	END
