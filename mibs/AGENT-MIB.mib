-- *****************************************************************************************
-- firmware version 4.00.004 2007/3/1 by Yan
-- 1.Add group 'agentTrustHostMgmt'(DLink MIB Genmgmt.mib revision 2.6)
-- 2.Add group 'agentFDBMgmt', 'agentARPMgmt'.(DLink MIB Genmgmt.mib revision 2.7)
-- *****************************************************************************************
-- Revision 1.7
-- Copyright 2000 D-Link Inc.
-- All rights reserved.

AGENT-MIB  DEFINITIONS ::= BEGIN

    IMPORTS
        IpAddress			        FROM RFC1155-SMI
        MODULE-IDENTITY, OBJECT-TYPE,
        Integer32		 	FROM SNMPv2-SMI
        RowStatus            	FROM SNMPv2-TC
        DisplayString		FROM RFC1213-MIB                
        dlink-common-mgmt	FROM DLINK-ID-REC-MIB;        
    	
      agentGeneralMgmt MODULE-IDENTITY
	    LAST-UPDATED "0007150000Z"
	    ORGANIZATION "D-Link, Inc."
	    CONTACT-INFO
	        "   D-Link Customer Service

		    Postal: No. 20,Park Ave, II, Science-based
			        Industrial Park, Hsinchu, taiwan, R.O.C.

		       Tel: 886-3-577-9966

		    E-mail: "
	    DESCRIPTION
		    "The Structure of Common Management Information for the
		    D-Link enterprise."
        ::= {  dlink-common-mgmt 1 }

    -- ****************
    -- agentBasicInfo *
    -- ****************
    agentBasicInfo          OBJECT IDENTIFIER ::= { agentGeneralMgmt 1 }
        
    agentMgmtProtocolCapability OBJECT-TYPE
        SYNTAX  INTEGER {   
                    other(1),
                    snmp-ip(2),
                    snmp-ipx(3),
                    snmp-ip-ipx(4)
                }
        MAX-ACCESS  read-only
        STATUS  current
        DESCRIPTION
            "The network management protocol(s) supported by this agent."
        ::= { agentBasicInfo 1 }


    -- *************************
    -- agentMibcapabilityTable *
    -- *************************

    agentMibCapabilityTable OBJECT-TYPE
        SYNTAX  SEQUENCE OF AgentMibCapabilityEntry
        MAX-ACCESS  not-accessible
        STATUS  current
        DESCRIPTION
            "A list of MIB capability entries supported by this agent."    
        ::= { agentBasicInfo 2 }

    agentMibCapabilityEntry OBJECT-TYPE
        SYNTAX  AgentMibCapabilityEntry
        MAX-ACCESS  not-accessible
        STATUS  current
        DESCRIPTION
            "A MIB capability entry contains objects describing a particular MIB
             supported by this agent."
        INDEX   { agentMibCapabilityIndex }
        ::= { agentMibCapabilityTable 1 }

    AgentMibCapabilityEntry ::= 
        SEQUENCE {
            agentMibCapabilityIndex
                Integer32,
            agentMibCapabilityDescr
                DisplayString,
            agentMibCapabilityVersion
                Integer32,
            agentMibCapabilityType
                INTEGER
        }

    agentMibCapabilityIndex OBJECT-TYPE
        SYNTAX  Integer32
        MAX-ACCESS  read-only
        STATUS  current
        DESCRIPTION
            "A list of agentMibCapabilityDescr entries."
        ::= { agentMibCapabilityEntry 1 }

    agentMibCapabilityDescr OBJECT-TYPE
        SYNTAX  DisplayString (SIZE (0..35))
        MAX-ACCESS  read-only
        STATUS  current
        DESCRIPTION
            "The name of the MIB supported by the agent."
        ::= { agentMibCapabilityEntry 2 }

    agentMibCapabilityVersion OBJECT-TYPE
        SYNTAX  Integer32
        MAX-ACCESS  read-only
        STATUS  current
        DESCRIPTION
            "The version of the MIB specified in this entry."
        ::= { agentMibCapabilityEntry 3 }

    agentMibCapabilityType OBJECT-TYPE
        SYNTAX  INTEGER {
                    other(1),
                    standard(2),
                    proprietary(3),
                    experiment(4)
                }
        MAX-ACCESS  read-only
        STATUS  current
        DESCRIPTION
            "The type of the MIB specified in this entry."
        ::= { agentMibCapabilityEntry 4 }


    agentStatusConsoleInUse   OBJECT-TYPE
        SYNTAX INTEGER {
               other(1),
               in-use(2),
               not-in-use(3)
               }
        MAX-ACCESS read-only
        STATUS current
        DESCRIPTION
            "This indicates whether console is currently in-use."
        ::= { agentBasicInfo 3 }

    agentStatusSaveCfg OBJECT-TYPE
        SYNTAX INTEGER {
               other(1),
               proceeding(2),
               completed(3),
               changed-not-save(4),
               failed(5)
               }
        MAX-ACCESS read-only
        STATUS current
        DESCRIPTION
            "This indicates the status of the device configuration.
            
            other(1) - this entry is currently in use but the conditions 
                     under which it will remain so are different from each 
                     of the following values.
            proceeding(2) - the device configuration is being currently saved into the NV-RAM.
            completed(3) ¡V all of the device configuration parameters have been
                     saved into NV-RAM.
            changed-not-save(4)¡V some of the device configuration parameters have
                     been changed but not saved into NV-RAM.
            failed(5) - The process to save device configuration is failed."
        ::= { agentBasicInfo 4 }

     agentStatusFileTransfer OBJECT-TYPE
        SYNTAX  INTEGER {
                    other(1) ,
                    in-process(2),
                    invalid-file(3),
                    violation(4),
                    file-not-found(5),
                    disk-full(6),
                    complete(7),
                    time-out(8),
                    not-format(9),
                    memory-full(10)
                }
        MAX-ACCESS  read-only
        STATUS  current
        DESCRIPTION
            "status of firmware download control. If the value is 'other',
            means never firmware updated since device started up." 
        ::= { agentBasicInfo 5 } 


-- *************************
    -- agentPORTutilizationTable *
    -- *************************
    agentPORTutilizationTable OBJECT-TYPE
        SYNTAX  SEQUENCE OF AgentPORTutilizationEntry
        MAX-ACCESS  not-accessible
        STATUS  current
        DESCRIPTION
            "This table specifies the current utilization of a specified port."
        ::= { agentBasicInfo 8 }

    agentPORTutilizationEntry OBJECT-TYPE
        SYNTAX  AgentPORTutilizationEntry
        MAX-ACCESS  not-accessible
        STATUS  current
        DESCRIPTION
            "A list of information regarding the port utilization function."
        INDEX   { agentPORTutilizationProtIndex }
        ::= { agentPORTutilizationTable 1 }

    AgentPORTutilizationEntry ::=
        SEQUENCE {
            agentPORTutilizationProtIndex
                INTEGER,
            agentPORTutilizationTX
                INTEGER,
            agentPORTutilizationRX
                INTEGER,
            agentPORTutilizationUtil
                INTEGER
        }

    agentPORTutilizationProtIndex OBJECT-TYPE
        SYNTAX  INTEGER (1..65535)
        MAX-ACCESS  read-only
        STATUS  current
        DESCRIPTION
            "This object indicates the module's port number."
        ::= { agentPORTutilizationEntry 1 }

    agentPORTutilizationTX OBJECT-TYPE
        SYNTAX  INTEGER
        MAX-ACCESS  read-only
        STATUS  current
        DESCRIPTION
            "The current rate of transmitted frames on the specified port."
        ::= { agentPORTutilizationEntry 2 }

    agentPORTutilizationRX OBJECT-TYPE
        SYNTAX  INTEGER
        MAX-ACCESS  read-only
        STATUS  current
        DESCRIPTION
            "The current rate of received frames on the specified port."
        ::= { agentPORTutilizationEntry 3 }

    agentPORTutilizationUtil OBJECT-TYPE
        SYNTAX  INTEGER (0..100)
        UNITS       "%"
        MAX-ACCESS  read-only
        STATUS  current
        DESCRIPTION
            "The current percentages regarding port statistics."
        ::= { agentPORTutilizationEntry 4 }
        
        
    -- ******************
    -- agentBasicConfig *
    -- ******************
      agentBasicConfig        OBJECT IDENTIFIER ::= { agentGeneralMgmt 2 }

    agentBscSwFileTable OBJECT-TYPE
        SYNTAX  SEQUENCE OF AgentBscSwFileEntry
        MAX-ACCESS  not-accessible
        STATUS  current
        DESCRIPTION
            "A list of MIB Basic Config entries supported file Update by this agent."    
        ::= { agentBasicConfig 1 }    
        
    agentBscSwFileEntry OBJECT-TYPE
        SYNTAX  AgentBscSwFileEntry
        MAX-ACCESS  not-accessible
        STATUS  current
        DESCRIPTION
            "A basic config entry contains objects describing a particular MIB
             supported by this agent."
        INDEX   { agentBscSwFileIndex }
        ::= { agentBscSwFileTable 1 }        

    AgentBscSwFileEntry ::=
    	SEQUENCE {
    		agentBscSwFileIndex
    			Integer32,
    		agentBscSwFileDscr
    			DisplayString,
    		agentBscSwFileAddr
    			IpAddress,
    		agentBscSwFileTransferType
    			INTEGER,
        	agentBscSwFile
        		DisplayString,
        	agentBscSwFileLocateId
        		INTEGER,
        	agentBscSwFileLoadType
        		INTEGER,
        	agentBscSwFileCtrl
        		INTEGER
        }

    agentBscSwFileIndex OBJECT-TYPE
    	SYNTAX	Integer32
    	MAX-ACCESS	read-write
    	STATUS	current
    	DESCRIPTION
    		"The table index for the file entry"
    	::= { agentBscSwFileEntry 1 }

    agentBscSwFileDscr OBJECT-TYPE
        SYNTAX  DisplayString  (SIZE (0..64))
        MAX-ACCESS  read-write
        STATUS  current
        DESCRIPTION
            "The description for the purpose of the software file in this entry.
			 Note:
			 For system which does not support change of this object, setting value to 
			 this object will cause the system to return bad-value error message.
			 "
        ::= { agentBscSwFileEntry 2 }
        
    agentBscSwFileAddr OBJECT-TYPE
        SYNTAX  IpAddress
        MAX-ACCESS  read-write
        STATUS  current
        DESCRIPTION
            "The IP address where the File to be downloaded is located, or the IP address
            where the file will be uploaded to."
        ::= {  agentBscSwFileEntry 3 }
            	
    agentBscSwFileTransferType OBJECT-TYPE
        SYNTAX  INTEGER {
                    other(1),
                    network-load(2),
                    out-of-band-load(3)
                }
        MAX-ACCESS  read-write
        STATUS  current
        DESCRIPTION
            "The channel through which the file will be downloaded or uploaded. 

			 Note:
			 For system which does not support all channels, setting value to the unsupported 
			 channel will cause the system to return bad-value error message.
			 "
        ::= { agentBscSwFileEntry 4 }

    agentBscSwFile OBJECT-TYPE
        SYNTAX  DisplayString  (SIZE (0..128))
        MAX-ACCESS  read-write
        STATUS  current
        DESCRIPTION
            "The name of the file to be downloaded from the TFTP server, or to be uploaded
            to."
        ::= { agentBscSwFileEntry 5 }
        
     agentBscSwFileLocateId OBJECT-TYPE
        SYNTAX  INTEGER (1..16)
        MAX-ACCESS  read-write
        STATUS  current
        DESCRIPTION
            "This object describes the type of the file.
             runtime-code(1),
             log-file(2),
             cfg-file(3)
             
			 Note:
			 For system which does not support change of this object, setting value to 
			 this object will cause the system to return bad-value error message.
             " 
        ::= { agentBscSwFileEntry 6 }
        
     agentBscSwFileLoadType OBJECT-TYPE
        SYNTAX  INTEGER {
                    other(1),
                    upload(2),
                    download(3)
                }
        MAX-ACCESS  read-write
        STATUS  current
        DESCRIPTION
        	"This object provides the user to select download or upload function for the file.

			 Note:
			 For system which does not support change of this object, setting value to 
			 this object will cause the system to return bad-value error message.
			 "
        ::= { agentBscSwFileEntry 7 }
                                               
     agentBscSwFileCtrl OBJECT-TYPE
        SYNTAX  INTEGER {
                    other(1),
                    inactive(2),
                    start(3),
                    delete(4),
                    create-and-go(5)
                }
        MAX-ACCESS  read-write
        STATUS  current
        DESCRIPTION
            "This object provides the user to download runtime software. The setting 
 		  	 will take effect when the system is restart. See Note(1) below
 		  
			 Note:
			 For system which does not support change of this object to some value, 
			 setting object to these values cause the system to return 
			 bad-value error message.
			 "
        ::= { agentBscSwFileEntry 8 }

	agentFileTransfer OBJECT-TYPE
		SYNTAX INTEGER {
				other(1),
				start(2),
				start-and-reset(3),
				noaction(4)
			}
		MAX-ACCESS read-write
		STATUS obsolete
		DESCRIPTION
			"This object will execute the download or upload action. If start(2), it will
			begin to download/upload, but no reset as follow. If start-and-reset(3), then
			the reset will active after download or upload. No action if(4). 

			 Note:
			 Because these funiction will be limited by the system support. Some of the 
			 select item will invalid. When one of the item user select,it will response with 
			 bad-value status."
		::= { agentBasicConfig 2 }
				
    agentSystemReset OBJECT-TYPE
        SYNTAX  INTEGER {
                    other(1),
                    cold-start(2),
                    warm-start(3),
                    no-reset(4)
                }
        MAX-ACCESS  read-write
        STATUS  current
        DESCRIPTION
            "This object indicates the agent system reset state. Setting this
             object to no-reset(4) has no effect. Setting this object to
             cold-start(2) or warm-start(3) will reset the agent. The agent 
             always returns no-reset(4) when this object is read."
        ::= { agentBasicConfig 3 }

    agentRs232PortConfig OBJECT-TYPE
        SYNTAX  INTEGER  {
                    other(1),
                    console(2),
                    out-of-band(3),
					notAvail(4)
                }
        MAX-ACCESS  read-write
        STATUS  current
        DESCRIPTION
            "This object indicates the RS-232C mode while device restart."
        ::= { agentBasicConfig 4 }

    agentOutOfBandBaudRateConfig OBJECT-TYPE
        SYNTAX  INTEGER {
                    other(1),
                    baudRate-2400 (2),
                    baudRate-9600 (3),
                    baudRate-19200(4),
                    baudRate-38400(5),
                    baudRate-115200(6)
                }
        MAX-ACCESS  read-write
        STATUS  obsolete
        DESCRIPTION
            "This object allows user to specify out_of_band baud rate. It will take effect
			 when the system is restart. 
			 
			 Note:
			 Because these funiction will be limited by the system support. Some of the 
			 select item will invalid. When one of the item user select,it will response with 
			 bad-value status.			 
			 "
        ::= { agentBasicConfig 5 }

     agentSaveCfg OBJECT-TYPE
        SYNTAX INTEGER {
        			other(1),
        			--idle(2),
        			cfg(3),
        			log(4),
        			all(5)
        		}
        MAX-ACCESS read-write
        STATUS current
        DESCRIPTION
            "This indicates the current device saving type will be saved into to NV-RAM.
            other(1) - none of the following.
            cfg(3) - save configuration.
            log(4) - save log.	
            all(5) - save both ( active configuration & log)."
        ::= { agentBasicConfig 6 }                

--***************************************************************************
--agentTrustHostMgmt
--***************************************************************************

    agentTrustHostMgmt       OBJECT IDENTIFIER ::= { agentBasicConfig 10 }

    agentTrustHostTable OBJECT-TYPE
        SYNTAX  SEQUENCE OF AgentTrustHostEntry
        MAX-ACCESS  not-accessible
        STATUS  current
        DESCRIPTION
            "This table contains Trust Host information."
        ::= { agentTrustHostMgmt 1 }

    agentTrustHostEntry OBJECT-TYPE
        SYNTAX  AgentTrustHostEntry
        MAX-ACCESS  not-accessible
        STATUS  current
        DESCRIPTION
            "A list of information about Trust Host."
        INDEX  { agentTrustHostIndex }
        ::= { agentTrustHostTable 1 }

    AgentTrustHostEntry ::=
        SEQUENCE {
            agentTrustHostIndex
                INTEGER,
            agentTrustHostIPAddress
                IpAddress,
            agentTrustHostRowStatus
                RowStatus,
            agentTrustHostIPSubnetMask
                IpAddress                
        }

    agentTrustHostIndex OBJECT-TYPE
        SYNTAX  INTEGER (1..10)
        MAX-ACCESS  read-only
        STATUS  current
        DESCRIPTION
            "The index of Trust Host entry."
        ::= { agentTrustHostEntry 1 }

    agentTrustHostIPAddress OBJECT-TYPE
        SYNTAX  IpAddress
        MAX-ACCESS  read-create
        STATUS  current
        DESCRIPTION
            "Specifies the IP address of the Trust Host."
        ::= { agentTrustHostEntry 2 }

    agentTrustHostRowStatus OBJECT-TYPE
        SYNTAX  RowStatus
        MAX-ACCESS  read-create
        STATUS  current
        DESCRIPTION
            "Indicates the status of this entry. When creating a Trust Host
             entry, the IP address should be set, too."
        ::= { agentTrustHostEntry 3 }

    agentTrustHostIPSubnetMask OBJECT-TYPE
        SYNTAX  IpAddress
        MAX-ACCESS  read-create
        STATUS  current
        DESCRIPTION
            "Specifies the IP subnet mask of the Trust Host."
        ::= { agentTrustHostEntry 4 }
        
--***************************
--agentTrustHostDelAllState *
--***************************
    agentTrustHostDelAllState OBJECT-TYPE
        SYNTAX	INTEGER{
			    		none(1),
			    		start(2)
			    		}
        MAX-ACCESS  read-write
        STATUS      current
        DESCRIPTION
            "Used to delete all Trust Host entries."
        ::= { agentTrustHostMgmt 2 }

--***************************************************************************
--agentFDBMgmt
--***************************************************************************

    agentFDBMgmt       OBJECT IDENTIFIER ::= { agentBasicConfig 11 }

    agentFDBClearAllState OBJECT-TYPE
        SYNTAX  INTEGER{
    		other(1),
    		start(2)
    		}
        MAX-ACCESS  read-write
        STATUS  current
        DESCRIPTION
            "Used to clear all FDB entries."
        ::= { agentFDBMgmt 1 }

--***************************************************************************
--agentARPMgmt
--***************************************************************************

    agentARPMgmt       OBJECT IDENTIFIER ::= { agentBasicConfig 12 }

    agentARPClearAllState OBJECT-TYPE
        SYNTAX  INTEGER{
    		other(1),
    		start(2)
    		}
        MAX-ACCESS  read-write
        STATUS  current
        DESCRIPTION
            "Used to clear all ARP entries."
        ::= { agentARPMgmt 1 }
                   
    -- ***********************
    -- agentIpProtocolConfig *
    -- ***********************
    agentIpProtoConfig      OBJECT IDENTIFIER ::= { agentGeneralMgmt 3 }

    agentIpNumOfIf OBJECT-TYPE
        SYNTAX  Integer32
        MAX-ACCESS  read-only
        STATUS  current
        DESCRIPTION
            "The total number of IP interfaces supported by this agent."
        ::= {  agentIpProtoConfig 1 }

    agentIpTftpServerAddr OBJECT-TYPE
        SYNTAX  IpAddress
        MAX-ACCESS  read-write
        STATUS  obsolete
        DESCRIPTION
            "The IP Address of TFTP Server."
        ::= {  agentIpProtoConfig 2 }

    agentIpGetIpFrom OBJECT-TYPE
        SYNTAX  INTEGER {
                    other(1),
                    disabled(2),
                    bootp(3),
                    dhcp(4)
                }
        MAX-ACCESS  read-write
        STATUS  current
        DESCRIPTION
            "This object indicates whether the agent get its system IP address
             from Bootp/DHCP server at start up."
        ::= { agentIpProtoConfig 3 }	

	-- End of agentIpIfTable ---------        
    -- ************************
    -- agentIptrapMangerTable *
    -- ************************

--	agentIpTrapManager	OBJECT IDENTIFIER ::= { agentGeneralMgmt 4 }
	
--    agentIpTrapManagerTable OBJECT-TYPE
--        SYNTAX  SEQUENCE OF AgentIpTrapManagerEntry
--        MAX-ACCESS  not-accessible
--        STATUS  current
--        DESCRIPTION
--            "A list of trap managers to which SNMP traps will be sent."
--        ::= {  agentIpTrapManager 1 }

--    agentIpTrapManagerEntry OBJECT-TYPE
--        SYNTAX  AgentIpTrapManagerEntry
--        MAX-ACCESS  not-accessible
--        STATUS  current
--        DESCRIPTION
--            "Each entry contains the particular trap manager settings."
--        INDEX   { agentIpTrapManagerIpAddr }
--        ::= { agentIpTrapManagerTable 1 }
--
--    AgentIpTrapManagerEntry ::= 
--        SEQUENCE {
--                    agentIpTrapManagerIpAddr
--                        IpAddress,
--                    agentIpTrapManagerComm
--                        DisplayString,
--                    agentIpTrapManagerMsgVer
--                        INTEGER,
--                    agentIpTrapManagerStatus
--                        INTEGER
--        }
--
--    agentIpTrapManagerIpAddr OBJECT-TYPE
--        SYNTAX  IpAddress
--        MAX-ACCESS  read-only
--        STATUS  current
--        DESCRIPTION
--            "The IP address where SNMP traps will be destined for"
--        ::= { agentIpTrapManagerEntry 1 }
--
--    agentIpTrapManagerComm OBJECT-TYPE
--        SYNTAX  DisplayString (SIZE (0..20))
--        MAX-ACCESS  read-write
--        STATUS  current
--        DESCRIPTION
--            "The community string used to encode SNMP trap packet to be 
--             sent to the trap
--             manager."
--        ::= { agentIpTrapManagerEntry 2 }
        
--    agentIpTrapManagerMsgVer OBJECT-TYPE
--        SYNTAX  INTEGER {
--                    snmpAgentVersionDependent(1),
--                    v1Trap(2),
--                    v2Trap(3)
--                }
--        MAX-ACCESS  read-write
--        STATUS  current
--        DESCRIPTION
--            "This object indicates the version of trap packets to be 
--             sent to
--             this trap manager. the default setting is 
--             SNMPAgentVersionDependent .
--             
--			 Note:
--			 Because these funiction will be limited by the system support. Some 
--             of the 
--			 select item will invalid. When one of the item user select,it will 
--             response with 
--			 bad-value status.	             "
--        ::= { agentIpTrapManagerEntry 3 }        
--
--    agentIpTrapManagerStatus OBJECT-TYPE
--        SYNTAX  INTEGER {
--                    other(1),
--                    disabled(2),
--                    enabled(3)
--                }
--        MAX-ACCESS  read-write
--        STATUS  current
--        DESCRIPTION
--            "This object indicates whether or not the trap should be 
--            sent to
--             this trap manager."
--        ::= { agentIpTrapManagerEntry 4}    
--

    -- Add for Slip_Console mode swtich 11-9-2001 WindChen

	agentConsoleModeManager	OBJECT IDENTIFIER ::= { agentGeneralMgmt 5 }
	
    agentConsoleModeManagerDataBits OBJECT-TYPE
        SYNTAX  INTEGER {
        		other(1),
        		bits-7(2),
        		bits-8(3)
        	}        
        MAX-ACCESS  read-write     
        STATUS  current
        DESCRIPTION
            "The DataBits for console mode, If the agentRs232PortConfig change to console mode
            then the device will use this group to make a setup for console value and 
            agentSlipModeManager group will deactive automatically. "
        ::= { agentConsoleModeManager 1 }

    agentConsoleModeManagerStopBits OBJECT-TYPE
        SYNTAX  INTEGER {
        		other(1),
        		stopbits-1(2),
        		stopbits-2(3)
        	}        
        MAX-ACCESS  read-write     
        STATUS  current
        DESCRIPTION
            "The Stop Bits for console mode "
        ::= { agentConsoleModeManager 2 }

    agentConsoleModeManagerParity OBJECT-TYPE
        SYNTAX  INTEGER {
        		none(1),
        		odd(2),
        		even(3)
        	}        
        MAX-ACCESS  read-write     
        STATUS  current
        DESCRIPTION
            "The Parity for console mode, If the agentRs232PortConfig change to console mode
            then the device will use this group to make a setup for console value and  
            agentSlipModeManager group will deactive automatically. "
        ::= { agentConsoleModeManager 3 }
        
    agentConsoleModeManagerBaudRate OBJECT-TYPE
        SYNTAX  INTEGER {
                    other(1),
                    baudRate-2400(2),
                    baudRate-9600(3),
                    baudRate-19200(4),
                    baudRate-38400(5),
                    baudRate-57200(6),
                    baudRate-115200(7)
                    
                }
        MAX-ACCESS  read-write
        STATUS  current
        DESCRIPTION
            "The transmit rate for console mode.
            
			 Note:
			 Because these funiction will be limited by the system support. Some of the 
			 select item will invalid. When one of the item user select,it will response with 
			 bad-value status.	            
            "
        ::= { agentConsoleModeManager 4 }
	
	agentConsoleModeManagerLogoutTime OBJECT-TYPE
        SYNTAX  INTEGER {
        		never(1),
        		two-minutes(2),
        		five-minutes(3),
				ten-minutes(4),
				fifteen-minutes(5)
        	}        
        MAX-ACCESS  read-write     
        STATUS  current
        DESCRIPTION
            "The time period of auto logout."
        ::= { agentConsoleModeManager 5 }
      

    -- Slip Mode Manager
	
--	agentSlipModeManager	OBJECT IDENTIFIER ::= { agentGeneralMgmt 6 }

--    agentSlipModeManagerLocalIP OBJECT-TYPE
--        SYNTAX  IpAddress
--        MAX-ACCESS  read-write
--        STATUS  current
--        DESCRIPTION
--            "The Local IP address for slip mode, If the agentRs232PortConfig change to out-of-band mode
--            then the device will use this group to make a setup for slip value and  agentConsoleModeManager
--            group will deactive automatically. "
--        ::= { agentSlipModeManager 1 }
--	
--    agentSlipModeManagerRemoteIP OBJECT-TYPE
--        SYNTAX  IpAddress
--        MAX-ACCESS  read-write
--        STATUS  current
--        DESCRIPTION
--            "The Remote IP address for slip mode "
--        ::= { agentSlipModeManager 2 }
--        
--    agentSlipModeManagerMTU OBJECT-TYPE
--        SYNTAX  INTEGER {
--                    other(1),
--                    mtu-1006(2),
--                    mtu-1500(3)
--                }
--        MAX-ACCESS  read-write
--        STATUS  current
--        DESCRIPTION
--            "The MTU Value for Slip Mode "
--        ::= { agentSlipModeManager 3 }
        
--    agentSlipModeManagerBaudRate OBJECT-TYPE
--        SYNTAX  INTEGER {
--                    other(1),
--                    baudRate-2400(2),
--                    baudRate-9600(3),
--                    baudRate-19200(4),
--                    baudRate-38400(5),
--                    baudRate-57200(6),
--                    baudRate-115200(7)                    
--                }
--        MAX-ACCESS  read-write
--        STATUS  current
--        DESCRIPTION
--            "The transmit rate for Slip Mode.
--            
--			 Note:
--			 Because these funiction will be limited by the system support. Some of the 
--			 select item will invalid. When one of the item user select,it will response with 
--			 bad-value status.	            
--            "
--        ::= { agentSlipModeManager 4 }
     
          
END
