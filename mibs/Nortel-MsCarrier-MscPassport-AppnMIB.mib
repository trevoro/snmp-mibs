Nortel-MsCarrier-MscPassport-AppnMIB
DEFINITIONS ::= BEGIN



IMPORTS

      OBJECT-TYPE
   FROM RFC-1212

      TimeTicks
   FROM RFC1155-SMI

      mscPassportMIBs,
      mscComponents
   FROM Nortel-MsCarrier-MscPassport-UsefulDefinitionsMIB

      RowPointer,
      DisplayString,
      StorageType,
      RowStatus,
      Gauge32,
      Integer32,
      Unsigned32
   FROM Nortel-MsCarrier-MscPassport-StandardTextualConventionsMIB

      AsciiString,
      Hex,
      NonReplicated,
      HexString,
      EnterpriseDateAndTime,
      PassportCounter64,
      Link,
      AsciiStringIndex,
      DigitString,
      DashedHexString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Appn Enterprise MIB."

appnMIB OBJECT IDENTIFIER ::= { mscPassportMIBs 29 }










-- 
-- Appn/<string>
-- This component defines the overall characteristics of a SNA APPN 
-- Network Node. 

mscAppn OBJECT IDENTIFIER ::= { mscComponents 110 }



mscAppnRowStatusTable OBJECT-TYPE
   SYNTAX     SEQUENCE OF MscAppnRowStatusEntry
   ACCESS     not-accessible
   STATUS     mandatory
   DESCRIPTION
     "This entry controls the addition and deletion of 
      mscAppn components."
::= { mscAppn 1 }

mscAppnRowStatusEntry OBJECT-TYPE
   SYNTAX     MscAppnRowStatusEntry
   ACCESS     not-accessible
   STATUS     mandatory
   DESCRIPTION
     "A single entry in the table represents a single 
      mscAppn component."
   INDEX {
      mscAppnIndex }
::= { mscAppnRowStatusTable 1 }

MscAppnRowStatusEntry ::= SEQUENCE {
   mscAppnRowStatus
      RowStatus,
   mscAppnComponentName
      DisplayString,
   mscAppnStorageType
      StorageType,
   mscAppnIndex
      AsciiStringIndex }

mscAppnRowStatus OBJECT-TYPE
   SYNTAX     RowStatus 
   ACCESS     read-write
   STATUS     mandatory
   DESCRIPTION
     "This variable is used as the basis for SNMP naming of
      mscAppn components.
      These components can be added and deleted."
::= { mscAppnRowStatusEntry 1 }

mscAppnComponentName OBJECT-TYPE
   SYNTAX     DisplayString 
   ACCESS     read-only
   STATUS     mandatory
   DESCRIPTION
     "This variable provides the component's string name for
      use with the ASCII Console Interface"
::= { mscAppnRowStatusEntry 2 }

mscAppnStorageType OBJECT-TYPE
   SYNTAX     StorageType 
   ACCESS     read-only
   STATUS     mandatory
   DESCRIPTION
     "This variable represents the storage type value for the
      mscAppn tables."
::= { mscAppnRowStatusEntry 4 }

mscAppnIndex OBJECT-TYPE
   SYNTAX     AsciiStringIndex (SIZE (1..17))
   ACCESS     not-accessible
   STATUS     mandatory
   DESCRIPTION
     "This variable represents the index for the mscAppn tables."
::= { mscAppnRowStatusEntry 10 }

mscAppnProcessParmsTable OBJECT-TYPE
   SYNTAX     SEQUENCE OF MscAppnProcessParmsEntry
   ACCESS     not-accessible
   STATUS     mandatory
   DESCRIPTION
     "This group contains attributes of the SNA service which are 
      required for operation within the Passport environment."
::= { mscAppn 100 }

mscAppnProcessParmsEntry OBJECT-TYPE
   SYNTAX     MscAppnProcessParmsEntry
   ACCESS     not-accessible
   STATUS     mandatory
   DESCRIPTION
     "An entry in the mscAppnProcessParmsTable."
   INDEX {
      mscAppnIndex }
::= { mscAppnProcessParmsTable 1 }

MscAppnProcessParmsEntry ::= SEQUENCE {
   mscAppnLogicalProcessor
      Link,
   mscAppnMaximumSvcs
      Unsigned32,
   mscAppnMaximumLinkStations
      Unsigned32 }

mscAppnLogicalProcessor OBJECT-TYPE
   SYNTAX     Link 
   ACCESS     read-write
   STATUS     mandatory
   DESCRIPTION
     "This attribute specifies the logical processor on which the Appn 
      component will utilize memory and CPU resources."
::= { mscAppnProcessParmsEntry 1 }

mscAppnMaximumSvcs OBJECT-TYPE
   SYNTAX     Unsigned32 (1..4096)
   ACCESS     read-write
   STATUS     mandatory
   DESCRIPTION
     "This attribute specifies the total number of general switched virtual 
      circuits (GSVC) that can be active on this Appn node. Once this 
      number is reached no GSVC calls will be accepted by the service.  
      This attribute does not include  the Frame Relay switched virtual 
      circuits."
   DEFVAL     { 1000 }
::= { mscAppnProcessParmsEntry 22 }

mscAppnMaximumLinkStations OBJECT-TYPE
   SYNTAX     Unsigned32 (1..4096)
   ACCESS     read-write
   STATUS     mandatory
   DESCRIPTION
     "This attribute specifies the total number of link stations for GSVCs, 
      Frame Relay PVCs and SVCs that can be active on this Appn node. 
      Once the value of activeLinkStations reaches or exceeds the value 
      of maximumLinkStations, no new incoming SVC calls (GSVCs 
      and Frame Relay SVCs) will be accepted by the service until the 
      value of activeLinkStations is again below the value of 
      maximumLinkStations.  Outgoing GSVCs and Frame Relay PVCs 
      (incoming or outgoing) are provisioned and their call setups at this 
      end are not  affected when the  value of activeLinkStations reaches 
      or exceeds the value of maximumLinkStations.
      
      Link stations are dynamically created for the end user applications 
      as required.  Therefore  the value of activeLinkStations may exceed 
      the value of maximumLinkStations."
   DEFVAL     { 1000 }
::= { mscAppnProcessParmsEntry 23 }

mscAppnControlPointCreateParmsTable OBJECT-TYPE
   SYNTAX     SEQUENCE OF MscAppnControlPointCreateParmsEntry
   ACCESS     not-accessible
   STATUS     mandatory
   DESCRIPTION
     "Parameters required to define the behavior of the SNA node."
::= { mscAppn 101 }

mscAppnControlPointCreateParmsEntry OBJECT-TYPE
   SYNTAX     MscAppnControlPointCreateParmsEntry
   ACCESS     not-accessible
   STATUS     mandatory
   DESCRIPTION
     "An entry in the mscAppnControlPointCreateParmsTable."
   INDEX {
      mscAppnIndex }
::= { mscAppnControlPointCreateParmsTable 1 }

MscAppnControlPointCreateParmsEntry ::= SEQUENCE {
   mscAppnFqCpName
      AsciiString,
   mscAppnBlockNumber
      Hex,
   mscAppnIdNumber
      Hex,
   mscAppnRouteAdditionResistance
      Unsigned32,
   mscAppnFeatures
      OCTET STRING,
   mscAppnMaximumLocates
      Unsigned32,
   mscAppnMaximumDirectorySize
      Unsigned32,
   mscAppnMdsTxAlertQueueSize
      Unsigned32,
   mscAppnTreeCacheSize
      Unsigned32,
   mscAppnTreeCacheUseLimit
      Unsigned32,
   mscAppnMaximumTopologyNodes
      Unsigned32,
   mscAppnMaximumTopologyTgs
      Unsigned32,
   mscAppnMaximumIsrSessions
      Unsigned32,
   mscAppnIsrUpperCongestionThreshold
      Unsigned32,
   mscAppnIsrLowerCongestionThreshold
      Unsigned32,
   mscAppnIsrMaxRuSize
      Unsigned32,
   mscAppnIsrRxPacingWindow
      Unsigned32,
   mscAppnLocateTimeout
      Unsigned32,
   mscAppnHprSupport
      INTEGER,
   mscAppnDlurSupport
      INTEGER }

mscAppnFqCpName OBJECT-TYPE
   SYNTAX     AsciiString (SIZE (3..17))
   ACCESS     read-write
   STATUS     mandatory
   DESCRIPTION
     "The network qualified control point (CP) name. This is the name by 
      which the node is identified within the APPN network. It is 
      signalled on the XID 3 exchange and is the end-point of CP-CP 
      sessions established with this node.
      
      The first portion of this name, up to the period, is the network 
      identifier for the network to which this node belongs. An APPN 
      network is a portion of a virtual private network which has a 
      separately administered name space. This network identifier is the 
      implicit qualifier of all resources which do not have an explicit 
      network identifier."
::= { mscAppnControlPointCreateParmsEntry 1 }

mscAppnBlockNumber OBJECT-TYPE
   SYNTAX     Hex (0..4095)
   ACCESS     read-write
   STATUS     mandatory
   DESCRIPTION
     "The block number identifies the product of the node. It is the first 
      three hexadecimal digits of the SNA node id."
::= { mscAppnControlPointCreateParmsEntry 3 }

mscAppnIdNumber OBJECT-TYPE
   SYNTAX     Hex (0..1048575)
   ACCESS     read-write
   STATUS     mandatory
   DESCRIPTION
     "The idNumber is used to identify the local SNA node. It is the last 
      five hexadecimal digits of the SNA node id and is administratively 
      defined. The idNumber will be combined with the three 
      hexadecimal digit block number to form the SNA node id. The SNA 
      node id is included in APPN alerts and in XIDs. A unique value is 
      required for connections to SNA."
::= { mscAppnControlPointCreateParmsEntry 4 }

mscAppnRouteAdditionResistance OBJECT-TYPE
   SYNTAX     Unsigned32 (0..255)
   ACCESS     read-write
   STATUS     mandatory
   DESCRIPTION
     "Route addition resistance is a value that indicates the relative 
      desirability of using this node for intermediate session traffic.The 
      value, which can be any integer 0-255, is used in route computation. 
      The lower the value, the more desirable the node is for intermediate 
      routing."
   DEFVAL     { 128 }
::= { mscAppnControlPointCreateParmsEntry 5 }

mscAppnFeatures OBJECT-TYPE
   SYNTAX     OCTET STRING (SIZE (1))
   ACCESS     read-write
   STATUS     mandatory
   DESCRIPTION
     "This attribute supports several YES/NO flags which are defined in 
      the create parameters:
      
      multipleDomainSupport
      
      If present, specifies that Management Services (MS) supports 
      Multiple Domain Support (MDS) and MS capabilities exchange.
      
      registerWithCDS
      
      If present, for a network node this specifies whether local and 
      domain resources may be registered with a central directory server.
      
      
      storeEndptRscvs
      
      If present, specifies that route selection control vectors (RSCV) 
      should be stored for diagnostic purposes on sessions which 
      terminate in this node. Note that selecting this value means that an 
      RSCV will be stored for each ISR session. This extra storage can be 
      up to 256 bytes per session.
      
      storeIsrRscvs
      
      If present, specifies that route selection control vectors (RSCV) 
      should be stored for diagnostic purposes on intermediate session 
      routing (ISR) sessions. Note that selecting this value means that an 
      RSCV will be stored for each ISR session. This extra storage can be 
      up to 256 bytes per session.

      Description of bits:
      multipleDomainSupport(0)
      registerWithCDS(1)
      storeEndptRscvs(2)
      storeIsrRscvs(3)"
   DEFVAL     { '80'H }
::= { mscAppnControlPointCreateParmsEntry 6 }

mscAppnMaximumLocates OBJECT-TYPE
   SYNTAX     Unsigned32 (0..65535)
   ACCESS     read-write
   STATUS     mandatory
   DESCRIPTION
     "This attribute represents the maximum number of locate requests 
      the node can handle simultaneously. Attribute locateTimeout should 
      be set to ensure that locate requests can timeout, thereby freeing up 
      node resources."
   DEFVAL     { 256 }
::= { mscAppnControlPointCreateParmsEntry 7 }

mscAppnMaximumDirectorySize OBJECT-TYPE
   SYNTAX     Unsigned32 (0..65535)
   ACCESS     read-write
   STATUS     mandatory
   DESCRIPTION
     "This attribute contains the maximum number of SnaDirectoryEntry 
      components that can be defined or learned by this node. A value of 
      zero means unlimited."
   DEFVAL     { 0 }
::= { mscAppnControlPointCreateParmsEntry 8 }

mscAppnMdsTxAlertQueueSize OBJECT-TYPE
   SYNTAX     Unsigned32 (0..65535)
   ACCESS     read-write
   STATUS     mandatory
   DESCRIPTION
     "This is the size of Multiple Domain Support send alert queue. When 
      the limit is reached, the MDS component deletes the oldest entry in 
      the queue."
   DEFVAL     { 100 }
::= { mscAppnControlPointCreateParmsEntry 9 }

mscAppnTreeCacheSize OBJECT-TYPE
   SYNTAX     Unsigned32 (8..65535)
   ACCESS     read-write
   STATUS     mandatory
   DESCRIPTION
     "This is the topology database routing tree cache size."
   DEFVAL     { 40 }
::= { mscAppnControlPointCreateParmsEntry 10 }

mscAppnTreeCacheUseLimit OBJECT-TYPE
   SYNTAX     Unsigned32 (1..65535)
   ACCESS     read-write
   STATUS     mandatory
   DESCRIPTION
     "This is the number of times a cached tree can be reused. Once this 
      number is exceeded, the tree is discarded and recomputed. This 
      allows the node to balance sessions among equal weight routes. A 
      low value provides better load balancing at the expense of increased 
      activation latency. The minimum is 1."
   DEFVAL     { 4 }
::= { mscAppnControlPointCreateParmsEntry 11 }

mscAppnMaximumTopologyNodes OBJECT-TYPE
   SYNTAX     Unsigned32 (0..65535)
   ACCESS     read-write
   STATUS     mandatory
   DESCRIPTION
     "This is the maximum number of Appn network nodes that can be 
      stored in the Topology Database (zero means unlimited)."
   DEFVAL     { 0 }
::= { mscAppnControlPointCreateParmsEntry 12 }

mscAppnMaximumTopologyTgs OBJECT-TYPE
   SYNTAX     Unsigned32 (0..65535)
   ACCESS     read-write
   STATUS     mandatory
   DESCRIPTION
     "This is the maximum number of Transmission Groups that can be 
      stored in the Topology Database (zero means unlimited)."
   DEFVAL     { 0 }
::= { mscAppnControlPointCreateParmsEntry 13 }

mscAppnMaximumIsrSessions OBJECT-TYPE
   SYNTAX     Unsigned32 (100..65535)
   ACCESS     read-write
   STATUS     mandatory
   DESCRIPTION
     "This attribute represents the maximum number of ISR sessions this 
      node can participate in at once. The minimum value is 100."
   DEFVAL     { 1000 }
::= { mscAppnControlPointCreateParmsEntry 14 }

mscAppnIsrUpperCongestionThreshold OBJECT-TYPE
   SYNTAX     Unsigned32 (0..65535)
   ACCESS     read-write
   STATUS     mandatory
   DESCRIPTION
     "This is the upper threshold for ISR sessions. This attribute and the 
      following one control the node's ISR congestion status. The node 
      state changes from uncongested to congested if the number of ISR 
      sessions exceeds the upper threshold. The node state changes back 
      to uncongested once the number of ISR sessions dips below the 
      lower threshold. To prevent thrashing, the lower threshold should be 
      less than the upper threshold. The upper threshold should be lower 
      than maximumIsrSessions."
   DEFVAL     { 500 }
::= { mscAppnControlPointCreateParmsEntry 15 }

mscAppnIsrLowerCongestionThreshold OBJECT-TYPE
   SYNTAX     Unsigned32 (0..65535)
   ACCESS     read-write
   STATUS     mandatory
   DESCRIPTION
     "This is the lower threshold for the ISR session congestion 
      algorithm. This value should be less than 
      isrUpperCongestionThreshold."
   DEFVAL     { 400 }
::= { mscAppnControlPointCreateParmsEntry 16 }

mscAppnIsrMaxRuSize OBJECT-TYPE
   SYNTAX     Unsigned32 (0..65535)
   ACCESS     read-write
   STATUS     mandatory
   DESCRIPTION
     "Maximum request unit (RU) size supported for intermediate routing 
      (ISR) sessions."
   DEFVAL     { 4096 }
::= { mscAppnControlPointCreateParmsEntry 17 }

mscAppnIsrRxPacingWindow OBJECT-TYPE
   SYNTAX     Unsigned32 (0..32767)
   ACCESS     read-write
   STATUS     mandatory
   DESCRIPTION
     "This is the suggested receive pacing window size for intermediate 
      sessions. This value is only used on the secondary hop of 
      intermediate sessions if the adjacent node does not support adaptive 
      pacing. A value of zero means that no pacing will occur."
   DEFVAL     { 8 }
::= { mscAppnControlPointCreateParmsEntry 18 }

mscAppnLocateTimeout OBJECT-TYPE
   SYNTAX     Unsigned32 (0..65535)
   ACCESS     read-write
   STATUS     mandatory
   DESCRIPTION
     "This attribute specifies the time in seconds before a network search 
      will time-out. A value of zero indicates that the search has no time 
      limit."
   DEFVAL     { 60 }
::= { mscAppnControlPointCreateParmsEntry 19 }

mscAppnHprSupport OBJECT-TYPE
   SYNTAX     INTEGER  {
                 none(0),
                 anrOnly(1),
                 rtp(2) }
   ACCESS     read-write
   STATUS     mandatory
   DESCRIPTION
     "This attribute specifies the type of High Performance Routing 
      (HPR) that is to be used on this node. The options are: none - the 
      node does not support HPR, anrOnly - the node only supports 
      Automatic Network Routing (ANR),  or rtp - the node supports 
      Rapid Transport Protocol as an end point.
      The default value of rtp ensures that the node can Aping other nodes 
      via a HPR pipe, this option is also required to allow dependent LU 
      sessions teminating on this node to use HPR and for the node to act 
      as a boundary node between ISR only nodes and the HPR capable 
      portion of the network.  With this option, the node can work with 
      non-HPR capable nodes."
   DEFVAL     { rtp }
::= { mscAppnControlPointCreateParmsEntry 20 }

mscAppnDlurSupport OBJECT-TYPE
   SYNTAX     INTEGER  {
                 no(0),
                 yes(1) }
   ACCESS     read-write
   STATUS     mandatory
   DESCRIPTION
     "This attribute specifies whether or not this node supports dependent 
      logical unit requestor (DLUR).  By default, DLUR is not supported.  
      If this attribute is set to yes, ensure that the Dlur subcomponent is 
      provisioned with appropriate values, if this attribute is set to no, the 
      Dlur subcomponent is not used and is ignored if present."
   DEFVAL     { no }
::= { mscAppnControlPointCreateParmsEntry 21 }

mscAppnStateTable OBJECT-TYPE
   SYNTAX     SEQUENCE OF MscAppnStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAppn 102 }

mscAppnStateEntry OBJECT-TYPE
   SYNTAX     MscAppnStateEntry
   ACCESS     not-accessible
   STATUS     mandatory
   DESCRIPTION
     "An entry in the mscAppnStateTable."
   INDEX {
      mscAppnIndex }
::= { mscAppnStateTable 1 }

MscAppnStateEntry ::= SEQUENCE {
   mscAppnAdminState
      INTEGER,
   mscAppnOperationalState
      INTEGER,
   mscAppnUsageState
      INTEGER }

mscAppnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAppnStateEntry 1 }

mscAppnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAppnStateEntry 2 }

mscAppnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAppnStateEntry 3 }

mscAppnOperationalTable OBJECT-TYPE
   SYNTAX     SEQUENCE OF MscAppnOperationalEntry
   ACCESS     not-accessible
   STATUS     mandatory
   DESCRIPTION
     "This group contains the node operational characteristics."
::= { mscAppn 103 }

mscAppnOperationalEntry OBJECT-TYPE
   SYNTAX     MscAppnOperationalEntry
   ACCESS     not-accessible
   STATUS     mandatory
   DESCRIPTION
     "An entry in the mscAppnOperationalTable."
   INDEX {
      mscAppnIndex }
::= { mscAppnOperationalTable 1 }

MscAppnOperationalEntry ::= SEQUENCE {
   mscAppnUpTime
      Unsigned32,
   mscAppnHeapSpaceLimit
      Gauge32,
   mscAppnHeapSpaceCurrent
      Gauge32,
   mscAppnMemWarningThreshold
      Unsigned32,
   mscAppnMemCriticalThreshold
      Unsigned32,
   mscAppnNnFunctionsSupported
      OCTET STRING,
   mscAppnGeneralFunctionsSupported
      OCTET STRING,
   mscAppnStatus
      OCTET STRING,
   mscAppnFlowReductionSequenceNumber
      Unsigned32,
   mscAppnResourceSequenceNumber
      Unsigned32,
   mscAppnDefinedLsGoodXids
      PassportCounter64,
   mscAppnDefinedLsBadXids
      PassportCounter64,
   mscAppnDynamicLsGoodXids
      PassportCounter64,
   mscAppnDynamicLsBadXids
      PassportCounter64,
   mscAppnActiveSvcs
      Unsigned32,
   mscAppnActiveLinkStations
      Unsigned32 }

mscAppnUpTime OBJECT-TYPE
   SYNTAX     Unsigned32 (0..4294967295)
   ACCESS     read-only
   STATUS     mandatory
   DESCRIPTION
     "This attribute represents the time in hundredths of a second since 
      the node was started or restarted."
::= { mscAppnOperationalEntry 1 }

mscAppnHeapSpaceLimit OBJECT-TYPE
   SYNTAX     Gauge32 (0..4294967295)
   ACCESS     read-only
   STATUS     mandatory
   DESCRIPTION
     "This attribute represents the size of the heap in bytes, as obtained by 
      storage management from the underlying operating system."
::= { mscAppnOperationalEntry 2 }

mscAppnHeapSpaceCurrent OBJECT-TYPE
   SYNTAX     Gauge32 (0..4294967295)
   ACCESS     read-only
   STATUS     mandatory
   DESCRIPTION
     "This attribute contains the number of bytes in the memory segment 
      that are currently allocated to the processes associated with the 
      Appn component.
      
      SNMP APPN MIB = ibmappnMemoryUsed"
::= { mscAppnOperationalEntry 3 }

mscAppnMemWarningThreshold OBJECT-TYPE
   SYNTAX     Unsigned32 (0..4294967295)
   ACCESS     read-only
   STATUS     mandatory
   DESCRIPTION
     "This attribute contains the memory allocation threshold beyond 
      which storage management considers the storage resources to be 
      constrained. This is calculated as a fraction of heapSpaceLimit.
      
      The value returned now is always zero until the functionality is 
      supported in future release.
      
      SNMP APPN MIB = ibmappnMemoryWarnThresh"
::= { mscAppnOperationalEntry 4 }

mscAppnMemCriticalThreshold OBJECT-TYPE
   SYNTAX     Unsigned32 (0..4294967295)
   ACCESS     read-only
   STATUS     mandatory
   DESCRIPTION
     "This attribute represents the memory allocation threshold beyond 
      which storage management considers the storage resources to be 
      critically constrained. The value is calculated as a fraction of 
      heapSpaceLimit.
      
      The value returned now is always zero until the functionality is 
      supported in future release."
::= { mscAppnOperationalEntry 5 }

mscAppnNnFunctionsSupported OBJECT-TYPE
   SYNTAX     OCTET STRING (SIZE (1))
   ACCESS     read-only
   STATUS     mandatory
   DESCRIPTION
     "The network node functions supported may include any of the 
      following:
      
      receiveRegistration - If present, indicates that this node supports 
      receiving registered characteristics on a GDS frame. This function 
      is not supported in the current release.
      
      gateway - If present, indicates that this is a gateway node.
      
      centralDirectoryServer - If present, indicates that this node 
      supports central directory server cache.
      
      treeCaching -If present, indicates that this node supports route tree 
      cache.
      
      treeUpdates - If present, indicates that this node supports 
      incremental tree update, which is only supported when tree caching 
      is supported.
      
      intermediateSessionRouting - Indicates that the node supports 
      intermediate session routing.

      Description of bits:
      receiveRegistration(0)
      gateway(1)
      centralDirectoryServer(2)
      treeCaching(3)
      treeUpdates(4)
      intermediateSessionRouting(5)"
::= { mscAppnOperationalEntry 6 }

mscAppnGeneralFunctionsSupported OBJECT-TYPE
   SYNTAX     OCTET STRING (SIZE (1))
   ACCESS     read-only
   STATUS     mandatory
   DESCRIPTION
     "The general functions supported may include any of the following:
      
      negotiableLs -If present, indicates that this node supports 
      negotiable link stations.
      
      segmentReassembly -If present, indicates whether this node 
      supports segment reassembly. This is only supported when segment 
      generation is also supported.
      
      bindReassembly -If present, indicates whether this node supports 
      Bind segment reassembly. This will only be supported when Bind 
      segment generation is also supported.
      
      parallelTgs -If present, indicates whether this node supports parallel 
      TGs.
      
      callIn - If present, indicates whether this node allows call-in from 
      nodes not defined locally.
      
      adaptivePacing - If present, indicates whether this node supports 
      adaptive bind pacing.

      Description of bits:
      negotiableLs(0)
      segmentReassembly(1)
      bindReassembly(2)
      parallelTgs(3)
      callIn(4)
      adaptivePacing(5)"
::= { mscAppnOperationalEntry 7 }

mscAppnStatus OBJECT-TYPE
   SYNTAX     OCTET STRING (SIZE (1))
   ACCESS     read-only
   STATUS     mandatory
   DESCRIPTION
     "This attribute contains the status of the node. This may be 
      nodeUncongested or one or more of the following:
      
      isrCongested
      The number of ISR sessions is greater than specified by the 
      isrSessionsUpperThreshold attribute. This node is not be included 
      in route selection by other nodes when this congestion exists.
      
      
      endPtDepleted
      The number of end-point sessions has reached the maximum 
      specified.
      
      
      isrDepleted
      The number of ISR sessions has reached the maximum specified by 
      the maximumIsrSessions attribute. This node is not included in 
      intermediate route selection by other nodes when resources are 
      depleted.
      
      
      quiescing
      Indicates whether the node is quiescing. This node is not included 
      in route selection by other nodes when the node is quiescing.

      Description of bits:
      nodeUncongested(0)
      notused1(1)
      quiescing(2)
      notused3(3)
      notused4(4)
      endPtDepleted(5)
      isrDepleted(6)
      isrCongested(7)"
::= { mscAppnOperationalEntry 8 }

mscAppnFlowReductionSequenceNumber OBJECT-TYPE
   SYNTAX     Unsigned32 (0..4294967295)
   ACCESS     read-only
   STATUS     mandatory
   DESCRIPTION
     "Flow reduction sequence numbers (FRSNs) are associated with 
      Topology Database Updates (TDUs) and are unique only within 
      each APPN network node. A TDU can be associated with multiple 
      APPN resources. This object is the last FRSN sent in a topology 
      update the adjacent network nodes.
      
      SNMP APPN MIB = ibmappnNodeNnFrsn"
::= { mscAppnOperationalEntry 9 }

mscAppnResourceSequenceNumber OBJECT-TYPE
   SYNTAX     Unsigned32 (0..4294967295)
   ACCESS     read-only
   STATUS     mandatory
   DESCRIPTION
     "Resource sequence number of this Appn network node."
::= { mscAppnOperationalEntry 10 }

mscAppnDefinedLsGoodXids OBJECT-TYPE
   SYNTAX     PassportCounter64 
   ACCESS     read-only
   STATUS     mandatory
   DESCRIPTION
     "This attribute represents the total number of successful XIDs that 
      have been received on all defined link stations since the last time 
      this node was initialized. When the upper limit is reached, the 
      number wraps around to 0."
::= { mscAppnOperationalEntry 11 }

mscAppnDefinedLsBadXids OBJECT-TYPE
   SYNTAX     PassportCounter64 
   ACCESS     read-only
   STATUS     mandatory
   DESCRIPTION
     "This attribute represents the total number of unsuccessful XIDs that 
      have been received on all defined link stations since the last time 
      this node was initialized. When the upper limit is reached, the 
      number wraps around to 0."
::= { mscAppnOperationalEntry 12 }

mscAppnDynamicLsGoodXids OBJECT-TYPE
   SYNTAX     PassportCounter64 
   ACCESS     read-only
   STATUS     mandatory
   DESCRIPTION
     "This attribute represents the total number of successful XIDs that 
      have been received on all dynamic link stations since the last time 
      this node was initialized. When the upper limit is reached, the 
      number wraps around to 0."
::= { mscAppnOperationalEntry 13 }

mscAppnDynamicLsBadXids OBJECT-TYPE
   SYNTAX     PassportCounter64 
   ACCESS     read-only
   STATUS     mandatory
   DESCRIPTION
     "This attribute represents the total number of unsuccessful XIDs that 
      have been received on all dynamic link stations since the last time 
      this node was initialized. When the upper limit is reached, the 
      number wraps around to 0."
::= { mscAppnOperationalEntry 14 }

mscAppnActiveSvcs OBJECT-TYPE
   SYNTAX     Unsigned32 (0..4096)
   ACCESS     read-only
   STATUS     mandatory
   DESCRIPTION
     "This attribute indicates the number of general switched virtual 
      circuits (GSVC) on this Appn node at the time of the query. This 
      attribute does not include the Frame Relay switched virtual circuits."
::= { mscAppnOperationalEntry 15 }

mscAppnActiveLinkStations OBJECT-TYPE
   SYNTAX     Unsigned32 (0..4096)
   ACCESS     read-only
   STATUS     mandatory
   DESCRIPTION
     "This attribute indicates the number of link stations (for GSVCs, 
      Frame Relay PVCs and SVCs) on the Appn node at the time of the 
      query."
::= { mscAppnOperationalEntry 16 }


-- Appn/<string> DataNetworkAddress
-- This provisioned component defines the common characteristics of 
-- a data network address for establishment of a virtual circuit. This 
-- component is derived from the virtual circuit services Dna 
-- component and specifies the subset of the capabilities of that 
-- component which are supported by the SNA service. 

mscAppnDna OBJECT IDENTIFIER ::= { mscAppn 2 }



mscAppnDnaRowStatusTable OBJECT-TYPE
   SYNTAX     SEQUENCE OF MscAppnDnaRowStatusEntry
   ACCESS     not-accessible
   STATUS     mandatory
   DESCRIPTION
     "This entry controls the addition and deletion of 
      mscAppnDna components."
::= { mscAppnDna 1 }

mscAppnDnaRowStatusEntry OBJECT-TYPE
   SYNTAX     MscAppnDnaRowStatusEntry
   ACCESS     not-accessible
   STATUS     mandatory
   DESCRIPTION
     "A single entry in the table represents a single 
      mscAppnDna component."
   INDEX {
      mscAppnIndex,
      mscAppnDnaIndex }
::= { mscAppnDnaRowStatusTable 1 }

MscAppnDnaRowStatusEntry ::= SEQUENCE {
   mscAppnDnaRowStatus
      RowStatus,
   mscAppnDnaComponentName
      DisplayString,
   mscAppnDnaStorageType
      StorageType,
   mscAppnDnaIndex
      NonReplicated }

mscAppnDnaRowStatus OBJECT-TYPE
   SYNTAX     RowStatus 
   ACCESS     read-only
   STATUS     mandatory
   DESCRIPTION
     "This variable is used as the basis for SNMP naming of
      mscAppnDna components.
      These components cannot be added nor deleted."
::= { mscAppnDnaRowStatusEntry 1 }

mscAppnDnaComponentName OBJECT-TYPE
   SYNTAX     DisplayString 
   ACCESS     read-only
   STATUS     mandatory
   DESCRIPTION
     "This variable provides the component's string name for
      use with the ASCII Console Interface"
::= { mscAppnDnaRowStatusEntry 2 }

mscAppnDnaStorageType OBJECT-TYPE
   SYNTAX     StorageType 
   ACCESS     read-only
   STATUS     mandatory
   DESCRIPTION
     "This variable represents the storage type value for the
      mscAppnDna tables."
::= { mscAppnDnaRowStatusEntry 4 }

mscAppnDnaIndex OBJECT-TYPE
   SYNTAX     NonReplicated 
   ACCESS     not-accessible
   STATUS     mandatory
   DESCRIPTION
     "This variable represents the index for the mscAppnDna tables."
::= { mscAppnDnaRowStatusEntry 10 }

mscAppnDnaAddressTable OBJECT-TYPE
   SYNTAX     SEQUENCE OF MscAppnDnaAddressEntry
   ACCESS     not-accessible
   STATUS     mandatory
   DESCRIPTION
     "Address group contains attributes common to all Dna's. Every Dna 
      used in the network is defined with this group of 2 attributes. String 
      of address digits is complemented by type of address and Npi. 
      These attributes are used to interpret format of the address digits."
::= { mscAppnDna 10 }

mscAppnDnaAddressEntry OBJECT-TYPE
   SYNTAX     MscAppnDnaAddressEntry
   ACCESS     not-accessible
   STATUS     mandatory
   DESCRIPTION
     "An entry in the mscAppnDnaAddressTable."
   INDEX {
      mscAppnIndex,
      mscAppnDnaIndex }
::= { mscAppnDnaAddressTable 1 }

MscAppnDnaAddressEntry ::= SEQUENCE {
   mscAppnDnaNumberingPlanIndicator
      INTEGER,
   mscAppnDnaDataNetworkAddress
      DigitString }

mscAppnDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans. 
      X.121 is used in packet switched data networks."
   DEFVAL     { x121 }
::= { mscAppnDnaAddressEntry 1 }

mscAppnDnaDataNetworkAddress OBJECT-TYPE
   SYNTAX     DigitString (SIZE (1..15))
   ACCESS     read-write
   STATUS     mandatory
   DESCRIPTION
     "Dna attribute contains digits which form unique identifier of the 
      customer interface. It can be compared (approximation only) to 
      telephone number where phone number identifies unique telephone 
      set. Dna digits are selected and assigned by network operators."
::= { mscAppnDnaAddressEntry 2 }

mscAppnDnaOutgoingOptionsTable OBJECT-TYPE
   SYNTAX     SEQUENCE OF MscAppnDnaOutgoingOptionsEntry
   ACCESS     not-accessible
   STATUS     mandatory
   DESCRIPTION
     "OutgoingOptions group defines call options of a Dna for calls 
      which are made out of the interface represented by Dna. All these 
      options are not used for calls arriving to the interface represented by 
      Dna."
::= { mscAppnDna 12 }

mscAppnDnaOutgoingOptionsEntry OBJECT-TYPE
   SYNTAX     MscAppnDnaOutgoingOptionsEntry
   ACCESS     not-accessible
   STATUS     mandatory
   DESCRIPTION
     "An entry in the mscAppnDnaOutgoingOptionsTable."
   INDEX {
      mscAppnIndex,
      mscAppnDnaIndex }
::= { mscAppnDnaOutgoingOptionsTable 1 }

MscAppnDnaOutgoingOptionsEntry ::= SEQUENCE {
   mscAppnDnaOutDefaultPriority
      INTEGER,
   mscAppnDnaOutDefaultPathSensitivity
      INTEGER,
   mscAppnDnaOutPathSensitivityOverRide
      INTEGER,
   mscAppnDnaOutDefaultPathReliability
      INTEGER,
   mscAppnDnaOutAccess
      INTEGER,
   mscAppnDnaDefaultTransferPriority
      INTEGER,
   mscAppnDnaTransferPriorityOverRide
      INTEGER }

mscAppnDnaOutDefaultPriority OBJECT-TYPE
   SYNTAX     INTEGER  {
                 normal(0),
                 high(1) }
   ACCESS     read-write
   STATUS     mandatory
   DESCRIPTION
     "This attribute, if set to normal indicates that the default priority for 
      outgoing calls (from the DTE to the network) using this particular 
      Dna is normal priority - if the priority is not specified by the DTE. 
      If this attribute is set to high then the default priority for outgoing 
      calls using this particular Dna is high priority.
      
      This option can be also included in X.25 signalling, in such case it 
      will be overruled."
   DEFVAL     { normal }
::= { mscAppnDnaOutgoingOptionsEntry 7 }

mscAppnDnaOutDefaultPathSensitivity OBJECT-TYPE
   SYNTAX     INTEGER  {
                 throughput(0),
                 delay(1) }
   ACCESS     read-write
   STATUS     obsolete
   DESCRIPTION
     "This attribute specifies the default class of routing for delay/
      throughput sensitive routing for all outgoing calls (from the DTE to 
      the network) using this particular Dna. The chosen default class of 
      routing applies to all outgoing calls established using this Dna, and 
      applies to the packets travelling in both directions on all outgoing 
      calls (local to remote, and remote to local). For incoming calls, the 
      default class of routing is chosen by the calling party (as opposed to 
      DPN, where either end of the call can choose the default routing 
      class).
      This attribute, if set to a value of throughput, indicates that the 
      default class of routing is throughput sensitive routing. If set to a 
      value of delay, then the default class of routing is delay sensitive 
      routing.
      In the future, the class of routing sensitivity may be overridden at 
      the calling end of the call as follows:
      The default class of routing sensitivity can be overridden by the 
      DTE in the call request packet through the TDS&I (Transit Delay 
      Selection & Indication) facility if the DTE supports this facility. 
      Whether or not the DTE is permitted to signal the TDS&I facility 
      will depend on the DTE (i.e.: TDS&I is supported in X.25 only), 
      and will depend on whether the port is configured to permit the 
      TDS&I facility. In Passport, the treatment of DTE facilities (for 
      example, NUI, RPOA, and TDS&I) is not fully defined yet since it 
      is not required. At the point in time when it is required, the 
      parameter to control whether or not the DTE is permitted to signal 
      the TDS&I will be in a Facility Treatment component. Currently, 
      the default is to disallow the TDS&I facility from the DTE."
   DEFVAL     { throughput }
::= { mscAppnDnaOutgoingOptionsEntry 11 }

mscAppnDnaOutPathSensitivityOverRide OBJECT-TYPE
   SYNTAX     INTEGER  {
                 no(0),
                 yes(1) }
   ACCESS     read-write
   STATUS     obsolete
   DESCRIPTION
     "If this attribute is set to yes in the call request, the called end will 
      use the calling end provisioning data on sensitivity to override its 
      provisioning data,"
   DEFVAL     { yes }
::= { mscAppnDnaOutgoingOptionsEntry 12 }

mscAppnDnaOutDefaultPathReliability OBJECT-TYPE
   SYNTAX     INTEGER  {
                 high(0),
                 normal(1) }
   ACCESS     read-write
   STATUS     mandatory
   DESCRIPTION
     "This attribute specifies the default class of routing for reliability 
      routing for all outgoing calls (from the DTE to the network) using 
      this particular Dna. The chosen default class of routing applies to 
      all outgoing calls established using this Dna, and applies to the 
      packets travelling in both directions on all outgoing calls (local to 
      remote, and remote to local). For incoming calls, the default class of 
      routing is chosen by the calling party (as opposed to DPN, where 
      either end of the call can choose the default routing class).
      This attribute, if set to a value of normal, indicates that the default 
      class of routing is normal reliability routing. If set to a value of 
      high, then the default class of routing is high reliability routing.
      High reliability is the standard choice for most DPN and Passport 
      services. It usually indicates that packets are overflowed or 
      retransmitted at various routing levels. Typically high reliability 
      results in duplication and disordering of packets in the network 
      when errors are detected or during link congestion. However, the Vc 
      handles the duplication and disordering to ensure that packets are 
      delivered to the DTE properly.
      For the Frame Relay service, duplication of packets is not desired, 
      in which case, normal reliability may be chosen as the preferred 
      class of routing."
   DEFVAL     { normal }
::= { mscAppnDnaOutgoingOptionsEntry 14 }

mscAppnDnaOutAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that outgoing 
      calls (from the DTE to the network) to the open (non-CUG) part of 
      the network are permitted. It also permits outgoing calls to DTEs 
      that have Incoming Access capabilities. If set to a value of 
      disallowed, then such calls cannot be made using this Dna - such 
      calls will be cleared by the local DCE.
      This attribute corresponds to the CCITT 'Closed User Group with 
      Outgoing Access' feature for Dna's in that outgoing access is 
      granted if this attribute is set to a value of allowed."
   DEFVAL     { disallowed }
::= { mscAppnDnaOutgoingOptionsEntry 17 }

mscAppnDnaDefaultTransferPriority OBJECT-TYPE
   SYNTAX     INTEGER  {
                 normal(0),
                 high(9) }
   ACCESS     read-write
   STATUS     mandatory
   DESCRIPTION
     "This attribute specifies the default transfer priority to network for 
      all outgoing calls using this particular Dna. It is overRidden by 
      the transferPriority provisioned in the DLCI Direct Call sub-
      component.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, the trunk queue is set to 
      high, the routing metric is set to delay.
      
      When the transfer priority is set at normal, the trunk queue is set to 
      normal, the routing metric is set to throughput.
      
      The default of defaultTransferPriority is normal."
   DEFVAL     { normal }
::= { mscAppnDnaOutgoingOptionsEntry 18 }

mscAppnDnaTransferPriorityOverRide OBJECT-TYPE
   SYNTAX     INTEGER  {
                 no(0),
                 yes(1) }
   ACCESS     read-write
   STATUS     mandatory
   DESCRIPTION
     "When this attribute is set to yes in the call request, the called end 
      will use the calling end provisioning data on transfer priority to 
      override its own provisioning data. If it is set no, the called end will 
      use its own provisioning data on transfer priority.
      
      The default of outTransferPriorityOverRide is yes."
   DEFVAL     { yes }
::= { mscAppnDnaOutgoingOptionsEntry 19 }

mscAppnDnaIncomingOptionsTable OBJECT-TYPE
   SYNTAX     SEQUENCE OF MscAppnDnaIncomingOptionsEntry
   ACCESS     not-accessible
   STATUS     mandatory
   DESCRIPTION
     "IncomingOptions defines set of options for incoming calls. These 
      options are used for calls arriving to the interface represented by 
      Dna. For calls originated from the interface, IncomingOptions 
      attributes are not used."
::= { mscAppnDna 13 }

mscAppnDnaIncomingOptionsEntry OBJECT-TYPE
   SYNTAX     MscAppnDnaIncomingOptionsEntry
   ACCESS     not-accessible
   STATUS     mandatory
   DESCRIPTION
     "An entry in the mscAppnDnaIncomingOptionsTable."
   INDEX {
      mscAppnIndex,
      mscAppnDnaIndex }
::= { mscAppnDnaIncomingOptionsTable 1 }

MscAppnDnaIncomingOptionsEntry ::= SEQUENCE {
   mscAppnDnaIncAccess
      INTEGER }

mscAppnDnaIncAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that incoming 
      calls (from the network to the DTE) from the open (non-CUG) part 
      of the network are permitted. It also permits incoming calls from 
      DTEs that have Outgoing Access capabilities. If set to a value of 
      disallowed, then such calls cannot be made to this Dna - such calls 
      will be cleared by the local DCE.
      This attribute corresponds to the CCITT 'Closed User Group with 
      Incoming Access' feature for Dnas in that incoming access is 
      granted if this attribute is set to a value of allowed."
   DEFVAL     { disallowed }
::= { mscAppnDnaIncomingOptionsEntry 9 }

mscAppnDnaCallOptionsTable OBJECT-TYPE
   SYNTAX     SEQUENCE OF MscAppnDnaCallOptionsEntry
   ACCESS     not-accessible
   STATUS     mandatory
   DESCRIPTION
     "CallOptions group defines additional options for calls not related 
      directly to direction of a call."
::= { mscAppnDna 14 }

mscAppnDnaCallOptionsEntry OBJECT-TYPE
   SYNTAX     MscAppnDnaCallOptionsEntry
   ACCESS     not-accessible
   STATUS     mandatory
   DESCRIPTION
     "An entry in the mscAppnDnaCallOptionsTable."
   INDEX {
      mscAppnIndex,
      mscAppnDnaIndex }
::= { mscAppnDnaCallOptionsTable 1 }

MscAppnDnaCallOptionsEntry ::= SEQUENCE {
   mscAppnDnaDefaultRecvFrmNetworkThruputClass
      Unsigned32,
   mscAppnDnaDefaultSendToNetworkThruputClass
      Unsigned32,
   mscAppnDnaDefaultRecvFrmNetworkWindowSize
      Unsigned32,
   mscAppnDnaDefaultSendToNetworkWindowSize
      Unsigned32,
   mscAppnDnaAccountClass
      Unsigned32,
   mscAppnDnaAccountCollection
      OCTET STRING,
   mscAppnDnaServiceExchange
      Unsigned32 }

mscAppnDnaDefaultRecvFrmNetworkThruputClass OBJECT-TYPE
   SYNTAX     Unsigned32 (0..15)
   ACCESS     read-write
   STATUS     mandatory
   DESCRIPTION
     "This attribute indicates the default receive throughput class for all 
      calls using this particular Dna."
   DEFVAL     { 13 }
::= { mscAppnDnaCallOptionsEntry 5 }

mscAppnDnaDefaultSendToNetworkThruputClass OBJECT-TYPE
   SYNTAX     Unsigned32 (0..15)
   ACCESS     read-write
   STATUS     mandatory
   DESCRIPTION
     "This attribute indicates the default send throughput class for all calls 
      using this particular Dna."
   DEFVAL     { 13 }
::= { mscAppnDnaCallOptionsEntry 6 }

mscAppnDnaDefaultRecvFrmNetworkWindowSize OBJECT-TYPE
   SYNTAX     Unsigned32 (1..7)
   ACCESS     read-write
   STATUS     mandatory
   DESCRIPTION
     "This attribute indicates the default number of data packets that can 
      be received by the DTE from the DCE before more packets can be 
      received. This view is oriented with respect to the DTE."
   DEFVAL     { 2 }
::= { mscAppnDnaCallOptionsEntry 7 }

mscAppnDnaDefaultSendToNetworkWindowSize OBJECT-TYPE
   SYNTAX     Unsigned32 (1..7)
   ACCESS     read-write
   STATUS     mandatory
   DESCRIPTION
     "This attribute indicates the number of data packets that can be 
      transmitted from the DTE to the DCE and must be acknowledged 
      before more packets can be transmitted."
   DEFVAL     { 2 }
::= { mscAppnDnaCallOptionsEntry 8 }

mscAppnDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator and it is an arbitrary 
      number."
   DEFVAL     { 0 }
::= { mscAppnDnaCallOptionsEntry 10 }

mscAppnDnaAccountCollection OBJECT-TYPE
   SYNTAX     OCTET STRING (SIZE (1))
   ACCESS     read-write
   STATUS     mandatory
   DESCRIPTION
     "This attribute indicates that accounting records are to be collected 
      by the network for the various reasons: billing, test, study, auditing. 
      The last of the parameters, force, indicates that accounting records 
      are to be collected irrespective of other collection reasons. If none 
      of these reasons are set, then accounting will be suppressed.

      Description of bits:
      bill(0)
      test(1)
      study(2)
      audit(3)
      force(4)"
   DEFVAL     { '80'H }
::= { mscAppnDnaCallOptionsEntry 11 }

mscAppnDnaServiceExchange OBJECT-TYPE
   SYNTAX     Unsigned32 (0..255)
   ACCESS     read-write
   STATUS     mandatory
   DESCRIPTION
     "This attribute is an arbitrary number, entered by the network 
      operator. It is included in the accounting record created by Vc."
   DEFVAL     { 0 }
::= { mscAppnDnaCallOptionsEntry 12 }


-- Appn/n Dna/n HgMember
-- This component specifies the Hunt Groups to which this member 
-- belongs. A hunt group member subscribes to at least one hunt 
-- group.  

mscAppnDnaHgM OBJECT IDENTIFIER ::= { mscAppnDna 2 }



mscAppnDnaHgMRowStatusTable OBJECT-TYPE
   SYNTAX     SEQUENCE OF MscAppnDnaHgMRowStatusEntry
   ACCESS     not-accessible
   STATUS     mandatory
   DESCRIPTION
     "This entry controls the addition and deletion of 
      mscAppnDnaHgM components."
::= { mscAppnDnaHgM 1 }

mscAppnDnaHgMRowStatusEntry OBJECT-TYPE
   SYNTAX     MscAppnDnaHgMRowStatusEntry
   ACCESS     not-accessible
   STATUS     mandatory
   DESCRIPTION
     "A single entry in the table represents a single 
      mscAppnDnaHgM component."
   INDEX {
      mscAppnIndex,
      mscAppnDnaIndex,
      mscAppnDnaHgMIndex }
::= { mscAppnDnaHgMRowStatusTable 1 }

MscAppnDnaHgMRowStatusEntry ::= SEQUENCE {
   mscAppnDnaHgMRowStatus
      RowStatus,
   mscAppnDnaHgMComponentName
      DisplayString,
   mscAppnDnaHgMStorageType
      StorageType,
   mscAppnDnaHgMIndex
      NonReplicated }

mscAppnDnaHgMRowStatus OBJECT-TYPE
   SYNTAX     RowStatus 
   ACCESS     read-write
   STATUS     mandatory
   DESCRIPTION
     "This variable is used as the basis for SNMP naming of
      mscAppnDnaHgM components.
      These components can be added and deleted."
::= { mscAppnDnaHgMRowStatusEntry 1 }

mscAppnDnaHgMComponentName OBJECT-TYPE
   SYNTAX     DisplayString 
   ACCESS     read-only
   STATUS     mandatory
   DESCRIPTION
     "This variable provides the component's string name for
      use with the ASCII Console Interface"
::= { mscAppnDnaHgMRowStatusEntry 2 }

mscAppnDnaHgMStorageType OBJECT-TYPE
   SYNTAX     StorageType 
   ACCESS     read-only
   STATUS     mandatory
   DESCRIPTION
     "This variable represents the storage type value for the
      mscAppnDnaHgM tables."
::= { mscAppnDnaHgMRowStatusEntry 4 }

mscAppnDnaHgMIndex OBJECT-TYPE
   SYNTAX     NonReplicated 
   ACCESS     not-accessible
   STATUS     mandatory
   DESCRIPTION
     "This variable represents the index for the mscAppnDnaHgM tables."
::= { mscAppnDnaHgMRowStatusEntry 10 }

mscAppnDnaHgMIfTable OBJECT-TYPE
   SYNTAX     SEQUENCE OF MscAppnDnaHgMIfEntry
   ACCESS     not-accessible
   STATUS     mandatory
   DESCRIPTION
     "This group contains the interface parameters between the 
      HuntGroupMember and the Hunt Group server."
::= { mscAppnDnaHgM 10 }

mscAppnDnaHgMIfEntry OBJECT-TYPE
   SYNTAX     MscAppnDnaHgMIfEntry
   ACCESS     not-accessible
   STATUS     mandatory
   DESCRIPTION
     "An entry in the mscAppnDnaHgMIfTable."
   INDEX {
      mscAppnIndex,
      mscAppnDnaIndex,
      mscAppnDnaHgMIndex }
::= { mscAppnDnaHgMIfTable 1 }

MscAppnDnaHgMIfEntry ::= SEQUENCE {
   mscAppnDnaHgMAvailabilityUpdateThreshold
      Unsigned32 }

mscAppnDnaHgMAvailabilityUpdateThreshold OBJECT-TYPE
   SYNTAX     Unsigned32 (0..4096)
   ACCESS     read-write
   STATUS     mandatory
   DESCRIPTION
     "This attribute indicates the number of channels that have to be freed 
      or occupied before the Availability Message Packet (AMP) is sent 
      to the Hunt Group Server informing it of the status of this interface."
   DEFVAL     { 1 }
::= { mscAppnDnaHgMIfEntry 1 }

mscAppnDnaHgMOpTable OBJECT-TYPE
   SYNTAX     SEQUENCE OF MscAppnDnaHgMOpEntry
   ACCESS     not-accessible
   STATUS     mandatory
   DESCRIPTION
     "This group contains the operational attributes of the 
      HuntGroupMember component."
::= { mscAppnDnaHgM 11 }

mscAppnDnaHgMOpEntry OBJECT-TYPE
   SYNTAX     MscAppnDnaHgMOpEntry
   ACCESS     not-accessible
   STATUS     mandatory
   DESCRIPTION
     "An entry in the mscAppnDnaHgMOpTable."
   INDEX {
      mscAppnIndex,
      mscAppnDnaIndex,
      mscAppnDnaHgMIndex }
::= { mscAppnDnaHgMOpTable 1 }

MscAppnDnaHgMOpEntry ::= SEQUENCE {
   mscAppnDnaHgMMaxAvailableChannels
      Unsigned32,
   mscAppnDnaHgMAvailableChannels
      Unsigned32,
   mscAppnDnaHgMAvailabilityDelta
      INTEGER }

mscAppnDnaHgMMaxAvailableChannels OBJECT-TYPE
   SYNTAX     Unsigned32 (0..4096)
   ACCESS     read-only
   STATUS     mandatory
   DESCRIPTION
     "This attribute indicates the maximum number of available channels 
      for this HuntGroupMember."
::= { mscAppnDnaHgMOpEntry 1 }

mscAppnDnaHgMAvailableChannels OBJECT-TYPE
   SYNTAX     Unsigned32 (0..4096)
   ACCESS     read-only
   STATUS     mandatory
   DESCRIPTION
     "This attribute indicates the number of available channels reported to 
      the hunt group in the Availability Message Packet (AMP). It is 
      incremented by the application when a channel is freed and 
      decremented when a channel is occupied."
::= { mscAppnDnaHgMOpEntry 2 }

mscAppnDnaHgMAvailabilityDelta OBJECT-TYPE
   SYNTAX     INTEGER (-4096..4096)
   ACCESS     read-only
   STATUS     mandatory
   DESCRIPTION
     "This attribute indicates the net change in the available channels 
      since the last Availability Message Packet (AMP) was sent to the 
      Hunt Group. Once the absolute value of this attribute reaches the 
      availabilityUpdateThreshold an AMP is sent to the host and the 
      availabilityDelta is reset to 0.
      If this attribute is positive it means an increase of the number of 
      available channels. If it is negative it means a decrease in the 
      number of available channels."
::= { mscAppnDnaHgMOpEntry 3 }


-- SnaAppn/n Dna/n HgM HuntGroupAddress/n
-- This component specifies the Hunt Group address to which this 
-- member belongs. A hunt group member belongs to at least one hunt 
-- group.

mscAppnDnaHgMHgAddr OBJECT IDENTIFIER ::= { mscAppnDnaHgM 2 }



mscAppnDnaHgMHgAddrRowStatusTable OBJECT-TYPE
   SYNTAX     SEQUENCE OF MscAppnDnaHgMHgAddrRowStatusEntry
   ACCESS     not-accessible
   STATUS     mandatory
   DESCRIPTION
     "This entry controls the addition and deletion of 
      mscAppnDnaHgMHgAddr components."
::= { mscAppnDnaHgMHgAddr 1 }

mscAppnDnaHgMHgAddrRowStatusEntry OBJECT-TYPE
   SYNTAX     MscAppnDnaHgMHgAddrRowStatusEntry
   ACCESS     not-accessible
   STATUS     mandatory
   DESCRIPTION
     "A single entry in the table represents a single 
      mscAppnDnaHgMHgAddr component."
   INDEX {
      mscAppnIndex,
      mscAppnDnaIndex,
      mscAppnDnaHgMIndex,
      mscAppnDnaHgMHgAddrIndex }
::= { mscAppnDnaHgMHgAddrRowStatusTable 1 }

MscAppnDnaHgMHgAddrRowStatusEntry ::= SEQUENCE {
   mscAppnDnaHgMHgAddrRowStatus
      RowStatus,
   mscAppnDnaHgMHgAddrComponentName
      DisplayString,
   mscAppnDnaHgMHgAddrStorageType
      StorageType,
   mscAppnDnaHgMHgAddrIndex
      Integer32 }

mscAppnDnaHgMHgAddrRowStatus OBJECT-TYPE
   SYNTAX     RowStatus 
   ACCESS     read-write
   STATUS     mandatory
   DESCRIPTION
     "This variable is used as the basis for SNMP naming of
      mscAppnDnaHgMHgAddr components.
      These components can be added and deleted."
::= { mscAppnDnaHgMHgAddrRowStatusEntry 1 }

mscAppnDnaHgMHgAddrComponentName OBJECT-TYPE
   SYNTAX     DisplayString 
   ACCESS     read-only
   STATUS     mandatory
   DESCRIPTION
     "This variable provides the component's string name for
      use with the ASCII Console Interface"
::= { mscAppnDnaHgMHgAddrRowStatusEntry 2 }

mscAppnDnaHgMHgAddrStorageType OBJECT-TYPE
   SYNTAX     StorageType 
   ACCESS     read-only
   STATUS     mandatory
   DESCRIPTION
     "This variable represents the storage type value for the
      mscAppnDnaHgMHgAddr tables."
::= { mscAppnDnaHgMHgAddrRowStatusEntry 4 }

mscAppnDnaHgMHgAddrIndex OBJECT-TYPE
   SYNTAX     Integer32 (0..1)
   ACCESS     not-accessible
   STATUS     mandatory
   DESCRIPTION
     "This variable represents the index for the mscAppnDnaHgMHgAddr tables."
::= { mscAppnDnaHgMHgAddrRowStatusEntry 10 }

mscAppnDnaHgMHgAddrAddrTable OBJECT-TYPE
   SYNTAX     SEQUENCE OF MscAppnDnaHgMHgAddrAddrEntry
   ACCESS     not-accessible
   STATUS     mandatory
   DESCRIPTION
     "This group contains attributes common to all DNAs. Every DNA 
      used in the network is defined with this group of 2 attributes."
::= { mscAppnDnaHgMHgAddr 10 }

mscAppnDnaHgMHgAddrAddrEntry OBJECT-TYPE
   SYNTAX     MscAppnDnaHgMHgAddrAddrEntry
   ACCESS     not-accessible
   STATUS     mandatory
   DESCRIPTION
     "An entry in the mscAppnDnaHgMHgAddrAddrTable."
   INDEX {
      mscAppnIndex,
      mscAppnDnaIndex,
      mscAppnDnaHgMIndex,
      mscAppnDnaHgMHgAddrIndex }
::= { mscAppnDnaHgMHgAddrAddrTable 1 }

MscAppnDnaHgMHgAddrAddrEntry ::= SEQUENCE {
   mscAppnDnaHgMHgAddrNumberingPlanIndicator
      INTEGER,
   mscAppnDnaHgMHgAddrDataNetworkAddress
      DigitString }

mscAppnDnaHgMHgAddrNumberingPlanIndicator OBJECT-TYPE
   SYNTAX     INTEGER  {
                 x121(0),
                 e164(1) }
   ACCESS     read-write
   STATUS     mandatory
   DESCRIPTION
     "This attribute specifies the Numbering Plan Indicator (NPI) of the 
      Dna that is entered. The address may belong to the X.121 or E.164 
      numbering plans."
   DEFVAL     { x121 }
::= { mscAppnDnaHgMHgAddrAddrEntry 1 }

mscAppnDnaHgMHgAddrDataNetworkAddress OBJECT-TYPE
   SYNTAX     DigitString (SIZE (1..15))
   ACCESS     read-write
   STATUS     mandatory
   DESCRIPTION
     "This attribute specifies the digits that form the unique identifier of 
      the customer interface. It can be compared (approximation only) to 
      a telephone number where phone number identifies unique 
      telephone set. Dna digits are selected and assigned by network 
      operators."
::= { mscAppnDnaHgMHgAddrAddrEntry 2 }


-- Appn/<string> Dna ClosedUserGroup/n
-- This component defines options associated with national or 
-- international Cug Identifier. Other Dnas in the network can have 
-- Cug's defined which groups these Dnas by Cug interlockCode. If 
-- Dnas are defined with Cugs, calls from Dnas which do not have the 
-- same interlockCode defined are refused. Attributes incAccess and 
-- outAccess can override this rule.

mscAppnDnaCug OBJECT IDENTIFIER ::= { mscAppnDna 3 }



mscAppnDnaCugRowStatusTable OBJECT-TYPE
   SYNTAX     SEQUENCE OF MscAppnDnaCugRowStatusEntry
   ACCESS     not-accessible
   STATUS     mandatory
   DESCRIPTION
     "This entry controls the addition and deletion of 
      mscAppnDnaCug components."
::= { mscAppnDnaCug 1 }

mscAppnDnaCugRowStatusEntry OBJECT-TYPE
   SYNTAX     MscAppnDnaCugRowStatusEntry
   ACCESS     not-accessible
   STATUS     mandatory
   DESCRIPTION
     "A single entry in the table represents a single 
      mscAppnDnaCug component."
   INDEX {
      mscAppnIndex,
      mscAppnDnaIndex,
      mscAppnDnaCugIndex }
::= { mscAppnDnaCugRowStatusTable 1 }

MscAppnDnaCugRowStatusEntry ::= SEQUENCE {
   mscAppnDnaCugRowStatus
      RowStatus,
   mscAppnDnaCugComponentName
      DisplayString,
   mscAppnDnaCugStorageType
      StorageType,
   mscAppnDnaCugIndex
      Integer32 }

mscAppnDnaCugRowStatus OBJECT-TYPE
   SYNTAX     RowStatus 
   ACCESS     read-write
   STATUS     mandatory
   DESCRIPTION
     "This variable is used as the basis for SNMP naming of
      mscAppnDnaCug components.
      These components can be added and deleted."
::= { mscAppnDnaCugRowStatusEntry 1 }

mscAppnDnaCugComponentName OBJECT-TYPE
   SYNTAX     DisplayString 
   ACCESS     read-only
   STATUS     mandatory
   DESCRIPTION
     "This variable provides the component's string name for
      use with the ASCII Console Interface"
::= { mscAppnDnaCugRowStatusEntry 2 }

mscAppnDnaCugStorageType OBJECT-TYPE
   SYNTAX     StorageType 
   ACCESS     read-only
   STATUS     mandatory
   DESCRIPTION
     "This variable represents the storage type value for the
      mscAppnDnaCug tables."
::= { mscAppnDnaCugRowStatusEntry 4 }

mscAppnDnaCugIndex OBJECT-TYPE
   SYNTAX     Integer32 (1..255)
   ACCESS     not-accessible
   STATUS     mandatory
   DESCRIPTION
     "This variable represents the index for the mscAppnDnaCug tables."
::= { mscAppnDnaCugRowStatusEntry 10 }

mscAppnDnaCugCugOptionsTable OBJECT-TYPE
   SYNTAX     SEQUENCE OF MscAppnDnaCugCugOptionsEntry
   ACCESS     not-accessible
   STATUS     mandatory
   DESCRIPTION
     "Attributes in this group defines ClosedUserGroup options 
      associated with interlockCode. Dnas with the same Cug 
      (interlockCode) make calls within this group. Various combinations 
      which permit or prevent calls in the same Cug group are defined 
      here."
::= { mscAppnDnaCug 10 }

mscAppnDnaCugCugOptionsEntry OBJECT-TYPE
   SYNTAX     MscAppnDnaCugCugOptionsEntry
   ACCESS     not-accessible
   STATUS     mandatory
   DESCRIPTION
     "An entry in the mscAppnDnaCugCugOptionsTable."
   INDEX {
      mscAppnIndex,
      mscAppnDnaIndex,
      mscAppnDnaCugIndex }
::= { mscAppnDnaCugCugOptionsTable 1 }

MscAppnDnaCugCugOptionsEntry ::= SEQUENCE {
   mscAppnDnaCugType
      INTEGER,
   mscAppnDnaCugDnic
      DigitString,
   mscAppnDnaCugInterlockCode
      Unsigned32,
   mscAppnDnaCugPreferential
      INTEGER,
   mscAppnDnaCugOutCalls
      INTEGER,
   mscAppnDnaCugIncCalls
      INTEGER,
   mscAppnDnaCugPrivileged
      INTEGER }

mscAppnDnaCugType OBJECT-TYPE
   SYNTAX     INTEGER  {
                 national(0),
                 international(1) }
   ACCESS     read-write
   STATUS     mandatory
   DESCRIPTION
     "This attribute specifies the Cug type - the Cug is either a national 
      Cug, or an international Cug. International closed user groups are 
      usually established between DTEs for which there is an X.75 
      Gateway between; whereas national closed user groups are usually 
      established between DTEs for which there is no X.75 Gateway 
      between. (National Cugs cannot normally traverse an X.75 
      Gateway).
      If this attribute is set to national, then the Cug is a national Cug, in 
      which case, the dnic should be left at its default value since it is not 
      part of a national Cug. If this attribute is set to international, then 
      the Cug is an international Cug, in which case, the dnic should be 
      set appropriately as part of the Cug interlockCode."
   DEFVAL     { national }
::= { mscAppnDnaCugCugOptionsEntry 1 }

mscAppnDnaCugDnic OBJECT-TYPE
   SYNTAX     DigitString (SIZE (4))
   ACCESS     read-write
   STATUS     mandatory
   DESCRIPTION
     "This attribute specifies the dnic (Data Network ID Code) the Cug 
      by which packet networks are identified. This attribute is not 
      applicable if the Cug is a national Cug, as specified by the Cug type 
      attribute. There are usually 1 or 2 dnics assigned per country, for 
      public networks. The U.S. is an exception where each BOC has a 
      dnic. Also, a group of private networks can have its own dnic.
      
      dnic value is not an arbitrary number. It is assigned by international 
      agreement and controlled by CCITT."
   DEFVAL     { '30303030'H }  -- "0000"
::= { mscAppnDnaCugCugOptionsEntry 2 }

mscAppnDnaCugInterlockCode OBJECT-TYPE
   SYNTAX     Unsigned32 (0..65535)
   ACCESS     read-write
   STATUS     mandatory
   DESCRIPTION
     "This attribute specifies the Cug identifier of a national or 
      international Cug call. It is an arbitrary number and it also can be 
      called Cug in some descriptions. Interfaces (Dnas) with this number 
      can make calls to Dnas with the same interlockCode."
   DEFVAL     { 0 }
::= { mscAppnDnaCugCugOptionsEntry 3 }

mscAppnDnaCugPreferential OBJECT-TYPE
   SYNTAX     INTEGER  {
                 no(0),
                 yes(1) }
   ACCESS     read-write
   STATUS     mandatory
   DESCRIPTION
     "This attribute, if set to yes indicates that this Cug is the preferential 
      Cug, in which case it will be used during the call establishment 
      phase if the DTE has not explicitly specified a Cug index in the call 
      request packet. If set to no, then this Cug is not the preferential 
      Cug.
      Only one of the Cugs associated with a particular Dna can be the 
      preferential Cug - only one Cug can have this attribute set to yes."
   DEFVAL     { no }
::= { mscAppnDnaCugCugOptionsEntry 4 }

mscAppnDnaCugOutCalls OBJECT-TYPE
   SYNTAX     INTEGER  {
                 disallowed(0),
                 allowed(1) }
   ACCESS     read-write
   STATUS     mandatory
   DESCRIPTION
     "This attribute, if set to allowed indicates that outgoing calls (from 
      the DTE into the network) be made using this particular Cug. If set 
      to a value of disallowed, then outgoing calls cannot be made using 
      this Cug - such calls will be cleared by the local DCE.
      This attribute corresponds to the CCITT 'Outgoing Calls Barred' 
      feature for Cugs in that outgoing calls are barred if this attribute is 
      set to a value of disallowed."
   DEFVAL     { allowed }
::= { mscAppnDnaCugCugOptionsEntry 5 }

mscAppnDnaCugIncCalls OBJECT-TYPE
   SYNTAX     INTEGER  {
                 disallowed(0),
                 allowed(1) }
   ACCESS     read-write
   STATUS     mandatory
   DESCRIPTION
     "This attribute, if set to allowed indicates that incoming calls (from 
      the network to the DTE) be made using this particular Cug. If set to 
      disallowed, then incoming calls cannot be made using this Cug - 
      such calls will be cleared by the local DCE.
      This attribute corresponds to the CCITT 'Incoming Calls Barred' 
      feature for Cugs in that incoming calls are barred if this attribute is 
      set to a value of disallowed."
   DEFVAL     { allowed }
::= { mscAppnDnaCugCugOptionsEntry 6 }

mscAppnDnaCugPrivileged OBJECT-TYPE
   SYNTAX     INTEGER  {
                 no(0),
                 yes(1) }
   ACCESS     read-write
   STATUS     mandatory
   DESCRIPTION
     "This attribute, if set to yes indicates that this Cug is a privileged 
      Cug. In DPN, at least one side of a call setup within a Cug must 
      have the Cug as a privileged Cug. If set to no, then the Cug is not 
      privileged.
      If both the local DTE and the remote DTE subscribe to the Cug, but 
      it is not privileged, then the call will be cleared. This attribute is 
      typically used for a host DTE which must accept calls from many 
      other DTEs in which case the other DTEs cannot call one another, 
      but can call the host. In this example, the host would have the 
      privileged Cug, and the other DTEs would belong to the same Cug, 
      but it would not be privileged."
   DEFVAL     { yes }
::= { mscAppnDnaCugCugOptionsEntry 7 }


-- Appn/<string> DataLinkConnectionIdentifier/n
-- This component represents the data link connection identifier on the 
-- frame relay service.

mscAppnDlci OBJECT IDENTIFIER ::= { mscAppn 3 }



mscAppnDlciRowStatusTable OBJECT-TYPE
   SYNTAX     SEQUENCE OF MscAppnDlciRowStatusEntry
   ACCESS     not-accessible
   STATUS     mandatory
   DESCRIPTION
     "This entry controls the addition and deletion of 
      mscAppnDlci components."
::= { mscAppnDlci 1 }

mscAppnDlciRowStatusEntry OBJECT-TYPE
   SYNTAX     MscAppnDlciRowStatusEntry
   ACCESS     not-accessible
   STATUS     mandatory
   DESCRIPTION
     "A single entry in the table represents a single 
      mscAppnDlci component."
   INDEX {
      mscAppnIndex,
      mscAppnDlciIndex }
::= { mscAppnDlciRowStatusTable 1 }

MscAppnDlciRowStatusEntry ::= SEQUENCE {
   mscAppnDlciRowStatus
      RowStatus,
   mscAppnDlciComponentName
      DisplayString,
   mscAppnDlciStorageType
      StorageType,
   mscAppnDlciIndex
      Integer32 }

mscAppnDlciRowStatus OBJECT-TYPE
   SYNTAX     RowStatus 
   ACCESS     read-write
   STATUS     mandatory
   DESCRIPTION
     "This variable is used as the basis for SNMP naming of
      mscAppnDlci components.
      These components can be added and deleted."
::= { mscAppnDlciRowStatusEntry 1 }

mscAppnDlciComponentName OBJECT-TYPE
   SYNTAX     DisplayString 
   ACCESS     read-only
   STATUS     mandatory
   DESCRIPTION
     "This variable provides the component's string name for
      use with the ASCII Console Interface"
::= { mscAppnDlciRowStatusEntry 2 }

mscAppnDlciStorageType OBJECT-TYPE
   SYNTAX     StorageType 
   ACCESS     read-only
   STATUS     mandatory
   DESCRIPTION
     "This variable represents the storage type value for the
      mscAppnDlci tables."
::= { mscAppnDlciRowStatusEntry 4 }

mscAppnDlciIndex OBJECT-TYPE
   SYNTAX     Integer32 (16..4095)
   ACCESS     not-accessible
   STATUS     mandatory
   DESCRIPTION
     "This variable represents the index for the mscAppnDlci tables."
::= { mscAppnDlciRowStatusEntry 10 }

mscAppnDlciStateTable OBJECT-TYPE
   SYNTAX     SEQUENCE OF MscAppnDlciStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAppnDlci 10 }

mscAppnDlciStateEntry OBJECT-TYPE
   SYNTAX     MscAppnDlciStateEntry
   ACCESS     not-accessible
   STATUS     mandatory
   DESCRIPTION
     "An entry in the mscAppnDlciStateTable."
   INDEX {
      mscAppnIndex,
      mscAppnDlciIndex }
::= { mscAppnDlciStateTable 1 }

MscAppnDlciStateEntry ::= SEQUENCE {
   mscAppnDlciAdminState
      INTEGER,
   mscAppnDlciOperationalState
      INTEGER,
   mscAppnDlciUsageState
      INTEGER }

mscAppnDlciAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAppnDlciStateEntry 1 }

mscAppnDlciOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAppnDlciStateEntry 2 }

mscAppnDlciUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAppnDlciStateEntry 3 }

mscAppnDlciSpOpTable OBJECT-TYPE
   SYNTAX     SEQUENCE OF MscAppnDlciSpOpEntry
   ACCESS     not-accessible
   STATUS     mandatory
   DESCRIPTION
     "This group contains the actual service parameters in  use for this 
      instance of Dlci."
::= { mscAppnDlci 12 }

mscAppnDlciSpOpEntry OBJECT-TYPE
   SYNTAX     MscAppnDlciSpOpEntry
   ACCESS     not-accessible
   STATUS     mandatory
   DESCRIPTION
     "An entry in the mscAppnDlciSpOpTable."
   INDEX {
      mscAppnIndex,
      mscAppnDlciIndex }
::= { mscAppnDlciSpOpTable 1 }

MscAppnDlciSpOpEntry ::= SEQUENCE {
   mscAppnDlciRateEnforcement
      INTEGER,
   mscAppnDlciCommittedInformationRate
      Gauge32,
   mscAppnDlciCommittedBurstSize
      Gauge32,
   mscAppnDlciExcessInformationRate
      Gauge32,
   mscAppnDlciExcessBurstSize
      Gauge32,
   mscAppnDlciMeasurementInterval
      Gauge32 }

mscAppnDlciRateEnforcement OBJECT-TYPE
   SYNTAX     INTEGER  {
                 off(0),
                 on(1) }
   ACCESS     read-only
   STATUS     mandatory
   DESCRIPTION
     "This attribute indicates  whether rate enforcement is in use
      for this Dlci."
   DEFVAL     { off }
::= { mscAppnDlciSpOpEntry 1 }

mscAppnDlciCommittedInformationRate OBJECT-TYPE
   SYNTAX     Gauge32 (0..4294967295)
   ACCESS     read-only
   STATUS     mandatory
   DESCRIPTION
     "This attribute indicates  the current effective committed information 
      rate (cir) in bits per second (bit/s).  cir is the rate at which the 
      network agrees to transfer data with Discard Eligiblity indication 
      DE=0 under normal conditions. 
      
      This attribute should be ignored when rateEnforcement is off."
::= { mscAppnDlciSpOpEntry 2 }

mscAppnDlciCommittedBurstSize OBJECT-TYPE
   SYNTAX     Gauge32 (0..4294967295)
   ACCESS     read-only
   STATUS     mandatory
   DESCRIPTION
     "This attribute indicates  the committed burst size (bc) in bits. bc is 
      the amount of data that the  network agrees to transfer under normal 
      conditions over a measurement interval (t). bc is used for data with  
      Discard Eligibility indication DE=0.  DE=1 data does not use bc at 
      all,  excessBurstSize if is used instead.
      
      This attribute should be ignored when rateEnforcement is off."
   DEFVAL     { 0 }
::= { mscAppnDlciSpOpEntry 3 }

mscAppnDlciExcessInformationRate OBJECT-TYPE
   SYNTAX     Gauge32 (0..4294967295)
   ACCESS     read-only
   STATUS     mandatory
   DESCRIPTION
     "This attribute indicates the current effective excess information rate 
      (eir) in bits per second (bit/s). eir is the rate at which the network 
      agrees to transfer data with Discard Eligibility indication DE=1 
      under normal conditions. DE can be set by the user or the network.  
      DE indication of a data  frame is set  to 1 by the network after cir  
      has been exceeded  while eir  is still available for data transfer."
::= { mscAppnDlciSpOpEntry 4 }

mscAppnDlciExcessBurstSize OBJECT-TYPE
   SYNTAX     Gauge32 (0..2048000)
   ACCESS     read-only
   STATUS     mandatory
   DESCRIPTION
     "This attribute indicates  the excess burst size (be) in bits. be is the 
      amount of uncommitted data that the network will attempt to deliver 
      over measurement interval (t). Data marked DE=1 by the user or by 
      the network is accounted for here.
      
      This attribute should be ignored when rateEnforcement is off."
   DEFVAL     { 0 }
::= { mscAppnDlciSpOpEntry 5 }

mscAppnDlciMeasurementInterval OBJECT-TYPE
   SYNTAX     Gauge32 (0..25500)
   ACCESS     read-only
   STATUS     mandatory
   DESCRIPTION
     "This attribute indicates  the time interval (in milliseconds) over 
      which rates and burst sizes are measured.
      
      This attribute should be ignored when rateEnforcement is off."
   DEFVAL     { 0 }
::= { mscAppnDlciSpOpEntry 6 }


-- Appn/<string> Dlci/n Dc
-- This component defines the characteristics of a direct call or 
-- permanent virtual circuit.This component is derived from the virtual 
-- circuit services Dc component and specifies the subset of the 
-- capabilities of that component which are supported by the SNA 
-- service.

mscAppnDlciDc OBJECT IDENTIFIER ::= { mscAppnDlci 2 }



mscAppnDlciDcRowStatusTable OBJECT-TYPE
   SYNTAX     SEQUENCE OF MscAppnDlciDcRowStatusEntry
   ACCESS     not-accessible
   STATUS     mandatory
   DESCRIPTION
     "This entry controls the addition and deletion of 
      mscAppnDlciDc components."
::= { mscAppnDlciDc 1 }

mscAppnDlciDcRowStatusEntry OBJECT-TYPE
   SYNTAX     MscAppnDlciDcRowStatusEntry
   ACCESS     not-accessible
   STATUS     mandatory
   DESCRIPTION
     "A single entry in the table represents a single 
      mscAppnDlciDc component."
   INDEX {
      mscAppnIndex,
      mscAppnDlciIndex,
      mscAppnDlciDcIndex }
::= { mscAppnDlciDcRowStatusTable 1 }

MscAppnDlciDcRowStatusEntry ::= SEQUENCE {
   mscAppnDlciDcRowStatus
      RowStatus,
   mscAppnDlciDcComponentName
      DisplayString,
   mscAppnDlciDcStorageType
      StorageType,
   mscAppnDlciDcIndex
      NonReplicated }

mscAppnDlciDcRowStatus OBJECT-TYPE
   SYNTAX     RowStatus 
   ACCESS     read-only
   STATUS     mandatory
   DESCRIPTION
     "This variable is used as the basis for SNMP naming of
      mscAppnDlciDc components.
      These components cannot be added nor deleted."
::= { mscAppnDlciDcRowStatusEntry 1 }

mscAppnDlciDcComponentName OBJECT-TYPE
   SYNTAX     DisplayString 
   ACCESS     read-only
   STATUS     mandatory
   DESCRIPTION
     "This variable provides the component's string name for
      use with the ASCII Console Interface"
::= { mscAppnDlciDcRowStatusEntry 2 }

mscAppnDlciDcStorageType OBJECT-TYPE
   SYNTAX     StorageType 
   ACCESS     read-only
   STATUS     mandatory
   DESCRIPTION
     "This variable represents the storage type value for the
      mscAppnDlciDc tables."
::= { mscAppnDlciDcRowStatusEntry 4 }

mscAppnDlciDcIndex OBJECT-TYPE
   SYNTAX     NonReplicated 
   ACCESS     not-accessible
   STATUS     mandatory
   DESCRIPTION
     "This variable represents the index for the mscAppnDlciDc tables."
::= { mscAppnDlciDcRowStatusEntry 10 }

mscAppnDlciDcOptionsTable OBJECT-TYPE
   SYNTAX     SEQUENCE OF MscAppnDlciDcOptionsEntry
   ACCESS     not-accessible
   STATUS     mandatory
   DESCRIPTION
     "The Options group defines attributes associated with a direct call. It 
      defines a complete connection in terms of path and call options. 
      This connection can be permanent (PVC) or switched (SVC). It can 
      have facilities. The total number of bytes of facilities including the 
      facility codes, and all of the facility data from all of the four classes 
      of facilities:
      CCITT_Facilities
      DTE_Facilities
      National_Facilities
      International_Facilities
      must not exceed 512."
::= { mscAppnDlciDc 10 }

mscAppnDlciDcOptionsEntry OBJECT-TYPE
   SYNTAX     MscAppnDlciDcOptionsEntry
   ACCESS     not-accessible
   STATUS     mandatory
   DESCRIPTION
     "An entry in the mscAppnDlciDcOptionsTable."
   INDEX {
      mscAppnIndex,
      mscAppnDlciIndex,
      mscAppnDlciDcIndex }
::= { mscAppnDlciDcOptionsTable 1 }

MscAppnDlciDcOptionsEntry ::= SEQUENCE {
   mscAppnDlciDcRemoteNpi
      INTEGER,
   mscAppnDlciDcRemoteDna
      DigitString,
   mscAppnDlciDcRemoteDlci
      Unsigned32,
   mscAppnDlciDcType
      INTEGER,
   mscAppnDlciDcTransferPriority
      INTEGER,
   mscAppnDlciDcDiscardPriority
      INTEGER }

mscAppnDlciDcRemoteNpi OBJECT-TYPE
   SYNTAX     INTEGER  {
                 x121(0),
                 e164(1) }
   ACCESS     read-write
   STATUS     mandatory
   DESCRIPTION
     "This attribute specifies the numbering plan used for remoteDna."
   DEFVAL     { x121 }
::= { mscAppnDlciDcOptionsEntry 3 }

mscAppnDlciDcRemoteDna OBJECT-TYPE
   SYNTAX     DigitString (SIZE (1..15))
   ACCESS     read-write
   STATUS     mandatory
   DESCRIPTION
     "This attribute specifies the Data Network Address (Dna) of the 
      remote. This is the called (destination) DTE address (Dna) to which 
      this direct call will be sent. Initially, the called DTE address 
      attribute must be present, that is, there must be a valid destination 
      address. However, it may be possible in the future to configure the 
      direct call with a mnemonic address, in which case, this attribute 
      will contain a zero-length Dna, and the mnemonic address will be 
      carried as one of the facilities."
::= { mscAppnDlciDcOptionsEntry 4 }

mscAppnDlciDcRemoteDlci OBJECT-TYPE
   SYNTAX     Unsigned32 (0..4095)
   ACCESS     read-write
   STATUS     mandatory
   DESCRIPTION
     "This attribute provides the remote DLCI (Logical Channel Number) 
      - it is used only for PVCs, where attribute type is set to 
      permanentMaster or permanentSlave or permanentBackupSlave.
      In switched case, value of remoteDlci is not known when call 
      request is made."
   DEFVAL     { 0 }
::= { mscAppnDlciDcOptionsEntry 5 }

mscAppnDlciDcType OBJECT-TYPE
   SYNTAX     INTEGER  {
                 permanentMaster(1),
                 permanentSlave(2),
                 permanentBackupSlave(3),
                 permanentSlaveWithBackup(4) }
   ACCESS     read-write
   STATUS     mandatory
   DESCRIPTION
     "This attribute specifies the type of Vc call:
      permanentMaster, 
      permanentSlave, 
      permanentSlaveWithBackup,
      permanentBackupSlave. 
      
      If the value is set to permanentMaster, then a permanent 
      connection will be established between two ends. The remote end 
      must be defined as a permanentSlave, permanentBackupSlave or 
      permanentSlaveWithBackup. The connection cannot be established 
      if the remote end is defined as anything else. The end defined as 
      permanentMaster always initiates the calls. It will attempt to call 
      once per minute.
      
      If the value is set to permanentSlave then a permanent connection 
      will be established between 2 ends. The remote end must be defined 
      as a permanentMaster. The connection cannot be established if the 
      remote end is defined as anything else. The permanentSlave end 
      will attempt to call once per minute.
      
      If the value is set to permanentSlaveWithBackup then a permanent 
      connection will be established between the 2 ends . The remote end 
      must be defined as a permanentMaster. The Connection cannot be 
      established if the remote end is defined as anything else. The 
      permanentSlaveWithBackup end will attempt to call once per 
      minute.
      
      If the value is set to permanentBackupSlave then a permanent 
      connection will be established between the 2 ends only if the 
      permanentMaster end is disconnected from the 
      permanentSlaveWithBackup end and a backup call is established 
      by the redirection system. If the permanentSlaveWithBackup 
      interface becomes visible again, the permanentBackupSlave end is 
      disconnected and the permanentSlaveWithBackup end is 
      reconnected to the permanentMaster end. The 
      permanentBackupSlave end does not try to establish PVC call."
   DEFVAL     { permanentMaster }
::= { mscAppnDlciDcOptionsEntry 6 }

mscAppnDlciDcTransferPriority OBJECT-TYPE
   SYNTAX     INTEGER  {
                 normal(0),
                 high(9),
                 useDnaDefTP(255) }
   ACCESS     read-write
   STATUS     mandatory
   DESCRIPTION
     "This attribute specifies the transfer priority to network for the 
      outgoing calls using this particular DLCI. It overRides the 
      defaultTransferPriority provisioned in its associated Dna 
      component.
      
      The transfer priority is a preference specified by an application 
      according to its delay-sensitivity requirement. Frames with high 
      transfer priority are served by the network before the frames with 
      normal priority.
      
      Each transfer priority contains a predetermined setting for trunk 
      queue (interrupting, delay or throughput), and routing metric (delay 
      or throughput). 
      
      When the transfer priority is set at high, the trunk queue is set to 
      high, the routing metric is set to delay.
      
      When the transfer priority is set at normal, the trunk queue is set to 
      normal, the routing metric is set to throughput.
      
      The default of transferPriority is useDnaDefTP. It means using the 
      provisioning value under defaultTransferPriority of its associated 
      Dna for this DLCI."
   DEFVAL     { useDnaDefTP }
::= { mscAppnDlciDcOptionsEntry 9 }

mscAppnDlciDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Traffic with normal priority are discarded 
      first than the traffic with high priority. The Dna default value 
      (provisioned by outDefaultPriority) is taken if this attribute is set to 
      the value useDnaDefPriority.
      
      The default of discardPriority is useDnaDefPriority."
   DEFVAL     { useDnaDefPriority }
::= { mscAppnDlciDcOptionsEntry 10 }

mscAppnDlciDcNfaTable OBJECT-TYPE
   SYNTAX     SEQUENCE OF MscAppnDlciDcNfaEntry
   ACCESS     not-accessible
   STATUS     obsolete
   DESCRIPTION
     "Two explicit attributes discardPriority and transferPriority are 
      created to replace H.01 and H.30 in the group 
      VcsDirectCallOptionsProv of this file. The migrate escape here 
      (DcComponent::migrateFaxEscape) propagates the old 
      provisioning data under H.01 and H.30 into discardPriority and 
      transferPriority. 
      
      The rule of the above propagation are: 0 in H.01 is equivalent to 
      discardPriority 0; 1 in H.01 is equivalent to discardPriority 1. And 
      0 in H.30 is equivalent to transferPriority normal; 1 in H.30 is 
      equivalent to transferPriority high.
      
      Please refer to discardPriority and transferPriority for more 
      information on how to use them."
::= { mscAppnDlciDc 283 }

mscAppnDlciDcNfaEntry OBJECT-TYPE
   SYNTAX     MscAppnDlciDcNfaEntry
   ACCESS     not-accessible
   STATUS     obsolete
   DESCRIPTION
     "An entry in the mscAppnDlciDcNfaTable."
   INDEX {
      mscAppnIndex,
      mscAppnDlciIndex,
      mscAppnDlciDcIndex,
      mscAppnDlciDcNfaIndex }
::= { mscAppnDlciDcNfaTable 1 }

MscAppnDlciDcNfaEntry ::= SEQUENCE {
   mscAppnDlciDcNfaIndex
      Integer32,
   mscAppnDlciDcNfaValue
      HexString,
   mscAppnDlciDcNfaRowStatus
      RowStatus }

mscAppnDlciDcNfaIndex OBJECT-TYPE
   SYNTAX     Integer32 (1 | 48)
   ACCESS     not-accessible
   STATUS     obsolete
   DESCRIPTION
     "This variable represents the index for the mscAppnDlciDcNfaTable."
::= { mscAppnDlciDcNfaEntry 1 }

mscAppnDlciDcNfaValue OBJECT-TYPE
   SYNTAX     HexString (SIZE (0..128))
   ACCESS     read-write
   STATUS     obsolete
   DESCRIPTION
     "This variable represents an individual value for the
      mscAppnDlciDcNfaTable."
::= { mscAppnDlciDcNfaEntry 2 }

mscAppnDlciDcNfaRowStatus OBJECT-TYPE
   SYNTAX     RowStatus 
   ACCESS     write-only
   STATUS     obsolete
   DESCRIPTION
     "This variable is used to control the addition and deletion 
      of individual values of the mscAppnDlciDcNfaTable."
::= { mscAppnDlciDcNfaEntry 3 }


-- This component defines attributes collected by Frame Relay Vc.

mscAppnDlciVc OBJECT IDENTIFIER ::= { mscAppnDlci 3 }



mscAppnDlciVcRowStatusTable OBJECT-TYPE
   SYNTAX     SEQUENCE OF MscAppnDlciVcRowStatusEntry
   ACCESS     not-accessible
   STATUS     mandatory
   DESCRIPTION
     "This entry controls the addition and deletion of 
      mscAppnDlciVc components."
::= { mscAppnDlciVc 1 }

mscAppnDlciVcRowStatusEntry OBJECT-TYPE
   SYNTAX     MscAppnDlciVcRowStatusEntry
   ACCESS     not-accessible
   STATUS     mandatory
   DESCRIPTION
     "A single entry in the table represents a single 
      mscAppnDlciVc component."
   INDEX {
      mscAppnIndex,
      mscAppnDlciIndex,
      mscAppnDlciVcIndex }
::= { mscAppnDlciVcRowStatusTable 1 }

MscAppnDlciVcRowStatusEntry ::= SEQUENCE {
   mscAppnDlciVcRowStatus
      RowStatus,
   mscAppnDlciVcComponentName
      DisplayString,
   mscAppnDlciVcStorageType
      StorageType,
   mscAppnDlciVcIndex
      NonReplicated }

mscAppnDlciVcRowStatus OBJECT-TYPE
   SYNTAX     RowStatus 
   ACCESS     read-only
   STATUS     mandatory
   DESCRIPTION
     "This variable is used as the basis for SNMP naming of
      mscAppnDlciVc components.
      These components cannot be added nor deleted."
::= { mscAppnDlciVcRowStatusEntry 1 }

mscAppnDlciVcComponentName OBJECT-TYPE
   SYNTAX     DisplayString 
   ACCESS     read-only
   STATUS     mandatory
   DESCRIPTION
     "This variable provides the component's string name for
      use with the ASCII Console Interface"
::= { mscAppnDlciVcRowStatusEntry 2 }

mscAppnDlciVcStorageType OBJECT-TYPE
   SYNTAX     StorageType 
   ACCESS     read-only
   STATUS     mandatory
   DESCRIPTION
     "This variable represents the storage type value for the
      mscAppnDlciVc tables."
::= { mscAppnDlciVcRowStatusEntry 4 }

mscAppnDlciVcIndex OBJECT-TYPE
   SYNTAX     NonReplicated 
   ACCESS     not-accessible
   STATUS     mandatory
   DESCRIPTION
     "This variable represents the index for the mscAppnDlciVc tables."
::= { mscAppnDlciVcRowStatusEntry 10 }

mscAppnDlciVcCadTable OBJECT-TYPE
   SYNTAX     SEQUENCE OF MscAppnDlciVcCadEntry
   ACCESS     not-accessible
   STATUS     mandatory
   DESCRIPTION
     "This group represents operational call data related to Frame Relay 
      Vc. It can be displayed only for Frame Relay Vc which is created by 
      application."
::= { mscAppnDlciVc 10 }

mscAppnDlciVcCadEntry OBJECT-TYPE
   SYNTAX     MscAppnDlciVcCadEntry
   ACCESS     not-accessible
   STATUS     mandatory
   DESCRIPTION
     "An entry in the mscAppnDlciVcCadTable."
   INDEX {
      mscAppnIndex,
      mscAppnDlciIndex,
      mscAppnDlciVcIndex }
::= { mscAppnDlciVcCadTable 1 }

MscAppnDlciVcCadEntry ::= SEQUENCE {
   mscAppnDlciVcType
      INTEGER,
   mscAppnDlciVcState
      INTEGER,
   mscAppnDlciVcPreviousState
      INTEGER,
   mscAppnDlciVcDiagnosticCode
      Unsigned32,
   mscAppnDlciVcPreviousDiagnosticCode
      Unsigned32,
   mscAppnDlciVcCalledNpi
      INTEGER,
   mscAppnDlciVcCalledDna
      DigitString,
   mscAppnDlciVcCalledLcn
      Unsigned32,
   mscAppnDlciVcCallingNpi
      INTEGER,
   mscAppnDlciVcCallingDna
      DigitString,
   mscAppnDlciVcCallingLcn
      Unsigned32,
   mscAppnDlciVcAccountingEnabled
      INTEGER,
   mscAppnDlciVcFastSelectCall
      INTEGER,
   mscAppnDlciVcPathReliability
      INTEGER,
   mscAppnDlciVcAccountingEnd
      INTEGER,
   mscAppnDlciVcPriority
      INTEGER,
   mscAppnDlciVcSegmentSize
      Unsigned32,
   mscAppnDlciVcMaxSubnetPktSize
      Unsigned32,
   mscAppnDlciVcRcosToNetwork
      INTEGER,
   mscAppnDlciVcRcosFromNetwork
      INTEGER,
   mscAppnDlciVcEmissionPriorityToNetwork
      INTEGER,
   mscAppnDlciVcEmissionPriorityFromNetwork
      INTEGER,
   mscAppnDlciVcDataPath
      AsciiString }

mscAppnDlciVcType OBJECT-TYPE
   SYNTAX     INTEGER  {
                 svc(0),
                 pvc(1),
                 spvc(2) }
   ACCESS     read-only
   STATUS     mandatory
   DESCRIPTION
     "This attribute displays the type of call, pvc,svc or spvc."
::= { mscAppnDlciVcCadEntry 1 }

mscAppnDlciVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscAppnDlciVcCadEntry 2 }

mscAppnDlciVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscAppnDlciVcCadEntry 3 }

mscAppnDlciVcDiagnosticCode OBJECT-TYPE
   SYNTAX     Unsigned32 (0..255)
   ACCESS     read-only
   STATUS     mandatory
   DESCRIPTION
     "This attribute displays the internal substate of call control. It is used 
      to further refine state of call processing."
::= { mscAppnDlciVcCadEntry 4 }

mscAppnDlciVcPreviousDiagnosticCode OBJECT-TYPE
   SYNTAX     Unsigned32 (0..255)
   ACCESS     read-only
   STATUS     mandatory
   DESCRIPTION
     "This attribute displays the internal substate of call control. It is used 
      to further refine state of call processing."
::= { mscAppnDlciVcCadEntry 5 }

mscAppnDlciVcCalledNpi OBJECT-TYPE
   SYNTAX     INTEGER  {
                 x121(0),
                 e164(1) }
   ACCESS     read-only
   STATUS     mandatory
   DESCRIPTION
     "This attribute displays the Numbering Plan Indicator (NPI) of the 
      called end."
::= { mscAppnDlciVcCadEntry 6 }

mscAppnDlciVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscAppnDlciVcCadEntry 7 }

mscAppnDlciVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscAppnDlciVcCadEntry 8 }

mscAppnDlciVcCallingNpi OBJECT-TYPE
   SYNTAX     INTEGER  {
                 x121(0),
                 e164(1) }
   ACCESS     read-only
   STATUS     mandatory
   DESCRIPTION
     "This attribute displays the Numbering Plan Indicator (NPI) of the 
      calling end."
::= { mscAppnDlciVcCadEntry 9 }

mscAppnDlciVcCallingDna OBJECT-TYPE
   SYNTAX     DigitString (SIZE (1..15))
   ACCESS     read-only
   STATUS     mandatory
   DESCRIPTION
     "This attribute displays the Data Network Address (Dna) of the 
      calling end."
::= { mscAppnDlciVcCadEntry 10 }

mscAppnDlciVcCallingLcn OBJECT-TYPE
   SYNTAX     Unsigned32 (1..65535)
   ACCESS     read-only
   STATUS     mandatory
   DESCRIPTION
     "This attribute displays the Logical Channel Number of the calling 
      end."
::= { mscAppnDlciVcCadEntry 11 }

mscAppnDlciVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscAppnDlciVcCadEntry 12 }

mscAppnDlciVcFastSelectCall OBJECT-TYPE
   SYNTAX     INTEGER  {
                 no(0),
                 yes(1) }
   ACCESS     read-only
   STATUS     mandatory
   DESCRIPTION
     "This attribute displays that this is a fast select call."
::= { mscAppnDlciVcCadEntry 13 }

mscAppnDlciVcPathReliability OBJECT-TYPE
   SYNTAX     INTEGER  {
                 high(0),
                 normal(1) }
   ACCESS     read-only
   STATUS     mandatory
   DESCRIPTION
     "This attribute displays the path reliability."
::= { mscAppnDlciVcCadEntry 19 }

mscAppnDlciVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscAppnDlciVcCadEntry 20 }

mscAppnDlciVcPriority OBJECT-TYPE
   SYNTAX     INTEGER  {
                 normal(0),
                 high(1) }
   ACCESS     read-only
   STATUS     mandatory
   DESCRIPTION
     "This attribute displays whether the call is a normal or a high 
      priority call."
::= { mscAppnDlciVcCadEntry 21 }

mscAppnDlciVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscAppnDlciVcCadEntry 22 }

mscAppnDlciVcMaxSubnetPktSize OBJECT-TYPE
   SYNTAX     Unsigned32 (0..4096)
   ACCESS     read-only
   STATUS     mandatory
   DESCRIPTION
     "This attribute indicates the maximum packet size allowed on the Vc."
::= { mscAppnDlciVcCadEntry 27 }

mscAppnDlciVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { mscAppnDlciVcCadEntry 28 }

mscAppnDlciVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { mscAppnDlciVcCadEntry 29 }

mscAppnDlciVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { mscAppnDlciVcCadEntry 30 }

mscAppnDlciVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { mscAppnDlciVcCadEntry 31 }

mscAppnDlciVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { mscAppnDlciVcCadEntry 32 }

mscAppnDlciVcIntdTable OBJECT-TYPE
   SYNTAX     SEQUENCE OF MscAppnDlciVcIntdEntry
   ACCESS     not-accessible
   STATUS     mandatory
   DESCRIPTION
     "This group defines display of interval data collected by Vc. Data in 
      this group is variable and may depend on time when this display 
      command is issued."
::= { mscAppnDlciVc 11 }

mscAppnDlciVcIntdEntry OBJECT-TYPE
   SYNTAX     MscAppnDlciVcIntdEntry
   ACCESS     not-accessible
   STATUS     mandatory
   DESCRIPTION
     "An entry in the mscAppnDlciVcIntdTable."
   INDEX {
      mscAppnIndex,
      mscAppnDlciIndex,
      mscAppnDlciVcIndex }
::= { mscAppnDlciVcIntdTable 1 }

MscAppnDlciVcIntdEntry ::= SEQUENCE {
   mscAppnDlciVcCallReferenceNumber
      Hex,
   mscAppnDlciVcElapsedTimeTillNow
      Unsigned32,
   mscAppnDlciVcSegmentsRx
      Unsigned32,
   mscAppnDlciVcSegmentsSent
      Unsigned32,
   mscAppnDlciVcStartTime
      EnterpriseDateAndTime }

mscAppnDlciVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscAppnDlciVcIntdEntry 1 }

mscAppnDlciVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscAppnDlciVcIntdEntry 2 }

mscAppnDlciVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscAppnDlciVcIntdEntry 3 }

mscAppnDlciVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscAppnDlciVcIntdEntry 4 }

mscAppnDlciVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscAppnDlciVcIntdEntry 5 }

mscAppnDlciVcFrdTable OBJECT-TYPE
   SYNTAX     SEQUENCE OF MscAppnDlciVcFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { mscAppnDlciVc 12 }

mscAppnDlciVcFrdEntry OBJECT-TYPE
   SYNTAX     MscAppnDlciVcFrdEntry
   ACCESS     not-accessible
   STATUS     mandatory
   DESCRIPTION
     "An entry in the mscAppnDlciVcFrdTable."
   INDEX {
      mscAppnIndex,
      mscAppnDlciIndex,
      mscAppnDlciVcIndex }
::= { mscAppnDlciVcFrdTable 1 }

MscAppnDlciVcFrdEntry ::= SEQUENCE {
   mscAppnDlciVcFrmCongestedToSubnet
      Unsigned32,
   mscAppnDlciVcCannotForwardToSubnet
      Unsigned32,
   mscAppnDlciVcNotDataXferToSubnet
      Unsigned32,
   mscAppnDlciVcOutOfRangeFrmFromSubnet
      Unsigned32,
   mscAppnDlciVcCombErrorsFromSubnet
      Unsigned32,
   mscAppnDlciVcDuplicatesFromSubnet
      Unsigned32,
   mscAppnDlciVcNotDataXferFromSubnet
      Unsigned32,
   mscAppnDlciVcFrmLossTimeouts
      Unsigned32,
   mscAppnDlciVcOoSeqByteCntExceeded
      Unsigned32,
   mscAppnDlciVcPeakOoSeqPktCount
      Unsigned32,
   mscAppnDlciVcPeakOoSeqFrmForwarded
      Unsigned32,
   mscAppnDlciVcSendSequenceNumber
      Unsigned32,
   mscAppnDlciVcPktRetryTimeouts
      Unsigned32,
   mscAppnDlciVcPeakRetryQueueSize
      Unsigned32,
   mscAppnDlciVcSubnetRecoveries
      Unsigned32,
   mscAppnDlciVcOoSeqPktCntExceeded
      Unsigned32,
   mscAppnDlciVcPeakOoSeqByteCount
      Unsigned32 }

mscAppnDlciVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { mscAppnDlciVcFrdEntry 2 }

mscAppnDlciVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { mscAppnDlciVcFrdEntry 3 }

mscAppnDlciVcNotDataXferToSubnet OBJECT-TYPE
   SYNTAX     Unsigned32 (0..5000)
   ACCESS     read-only
   STATUS     mandatory
   DESCRIPTION
     "This attribute records the number of frames from link discarded 
      when the Vc tries to recover from internal path failure."
::= { mscAppnDlciVcFrdEntry 4 }

mscAppnDlciVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { mscAppnDlciVcFrdEntry 5 }

mscAppnDlciVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { mscAppnDlciVcFrdEntry 6 }

mscAppnDlciVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { mscAppnDlciVcFrdEntry 7 }

mscAppnDlciVcNotDataXferFromSubnet OBJECT-TYPE
   SYNTAX     Unsigned32 (0..5000)
   ACCESS     read-only
   STATUS     mandatory
   DESCRIPTION
     "This attribute displays the number of subnet packets discarded when 
      data transfer is suspended in Vc recovery."
::= { mscAppnDlciVcFrdEntry 8 }

mscAppnDlciVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { mscAppnDlciVcFrdEntry 9 }

mscAppnDlciVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscAppnDlciVcFrdEntry 10 }

mscAppnDlciVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { mscAppnDlciVcFrdEntry 11 }

mscAppnDlciVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { mscAppnDlciVcFrdEntry 12 }

mscAppnDlciVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { mscAppnDlciVcFrdEntry 13 }

mscAppnDlciVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { mscAppnDlciVcFrdEntry 15 }

mscAppnDlciVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { mscAppnDlciVcFrdEntry 16 }

mscAppnDlciVcSubnetRecoveries OBJECT-TYPE
   SYNTAX     Unsigned32 (0..5000)
   ACCESS     read-only
   STATUS     mandatory
   DESCRIPTION
     "This attribute displays the number of successful Vc recovery 
      attempts."
::= { mscAppnDlciVcFrdEntry 17 }

mscAppnDlciVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { mscAppnDlciVcFrdEntry 19 }

mscAppnDlciVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { mscAppnDlciVcFrdEntry 20 }

mscAppnDlciVcDmepTable OBJECT-TYPE
   SYNTAX     SEQUENCE OF MscAppnDlciVcDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { mscAppnDlciVc 417 }

mscAppnDlciVcDmepEntry OBJECT-TYPE
   SYNTAX     MscAppnDlciVcDmepEntry
   ACCESS     not-accessible
   STATUS     mandatory
   DESCRIPTION
     "An entry in the mscAppnDlciVcDmepTable."
   INDEX {
      mscAppnIndex,
      mscAppnDlciIndex,
      mscAppnDlciVcIndex,
      mscAppnDlciVcDmepValue }
::= { mscAppnDlciVcDmepTable 1 }

MscAppnDlciVcDmepEntry ::= SEQUENCE {
   mscAppnDlciVcDmepValue
      RowPointer }

mscAppnDlciVcDmepValue OBJECT-TYPE
   SYNTAX     RowPointer 
   ACCESS     read-only
   STATUS     mandatory
   DESCRIPTION
     "This variable represents both the value and the index for the
      mscAppnDlciVcDmepTable."
::= { mscAppnDlciVcDmepEntry 1 }


-- Appn/<string> Dlci/n BnnLinkStationDefinition/<sap>
-- This component allows the user to control how the frame relay 
-- DLCI is used, by controlling the Link Station definition.This 
-- component is required if a connect out needs to be generated for a 
-- particular device connected over this DLCI.  The index of 
-- component is the SAP number of the device.  For APPN network 
-- node to network node connections, BnnLsDef/4 needs to be added 
-- to the DLCI at one end of the connecting PVC with dspuService set 
-- to none.   

mscAppnDlciBnnLsDef OBJECT IDENTIFIER ::= { mscAppnDlci 4 }



mscAppnDlciBnnLsDefRowStatusTable OBJECT-TYPE
   SYNTAX     SEQUENCE OF MscAppnDlciBnnLsDefRowStatusEntry
   ACCESS     not-accessible
   STATUS     mandatory
   DESCRIPTION
     "This entry controls the addition and deletion of 
      mscAppnDlciBnnLsDef components."
::= { mscAppnDlciBnnLsDef 1 }

mscAppnDlciBnnLsDefRowStatusEntry OBJECT-TYPE
   SYNTAX     MscAppnDlciBnnLsDefRowStatusEntry
   ACCESS     not-accessible
   STATUS     mandatory
   DESCRIPTION
     "A single entry in the table represents a single 
      mscAppnDlciBnnLsDef component."
   INDEX {
      mscAppnIndex,
      mscAppnDlciIndex,
      mscAppnDlciBnnLsDefIndex }
::= { mscAppnDlciBnnLsDefRowStatusTable 1 }

MscAppnDlciBnnLsDefRowStatusEntry ::= SEQUENCE {
   mscAppnDlciBnnLsDefRowStatus
      RowStatus,
   mscAppnDlciBnnLsDefComponentName
      DisplayString,
   mscAppnDlciBnnLsDefStorageType
      StorageType,
   mscAppnDlciBnnLsDefIndex
      Integer32 }

mscAppnDlciBnnLsDefRowStatus OBJECT-TYPE
   SYNTAX     RowStatus 
   ACCESS     read-write
   STATUS     mandatory
   DESCRIPTION
     "This variable is used as the basis for SNMP naming of
      mscAppnDlciBnnLsDef components.
      These components can be added and deleted."
::= { mscAppnDlciBnnLsDefRowStatusEntry 1 }

mscAppnDlciBnnLsDefComponentName OBJECT-TYPE
   SYNTAX     DisplayString 
   ACCESS     read-only
   STATUS     mandatory
   DESCRIPTION
     "This variable provides the component's string name for
      use with the ASCII Console Interface"
::= { mscAppnDlciBnnLsDefRowStatusEntry 2 }

mscAppnDlciBnnLsDefStorageType OBJECT-TYPE
   SYNTAX     StorageType 
   ACCESS     read-only
   STATUS     mandatory
   DESCRIPTION
     "This variable represents the storage type value for the
      mscAppnDlciBnnLsDef tables."
::= { mscAppnDlciBnnLsDefRowStatusEntry 4 }

mscAppnDlciBnnLsDefIndex OBJECT-TYPE
   SYNTAX     Integer32 (4 | 8 | 12 | 16 | 20 | 24 | 28 | 32 | 36 | 40 | 44 | 48 | 52 | 56 | 60 | 64 | 68 | 72 | 76 | 80 | 84 | 88 | 92 | 96 | 100 | 104 | 108 | 112 | 116 | 120 | 124 | 128 | 132 | 136 | 140 | 144 | 148 | 152 | 156 | 160 | 164 | 168 | 172 | 176 | 180 | 184 | 188 | 192 | 196 | 200 | 204 | 208 | 212 | 216 | 220 | 224 | 228 | 232 | 236 | 240 | 244 | 248 | 252)
   ACCESS     not-accessible
   STATUS     mandatory
   DESCRIPTION
     "This variable represents the index for the mscAppnDlciBnnLsDef tables."
::= { mscAppnDlciBnnLsDefRowStatusEntry 10 }

mscAppnDlciBnnLsDefProvTable OBJECT-TYPE
   SYNTAX     SEQUENCE OF MscAppnDlciBnnLsDefProvEntry
   ACCESS     not-accessible
   STATUS     mandatory
   DESCRIPTION
     "This group contains the provisioning data for a Link Station on a 
      frame relay DLCI."
::= { mscAppnDlciBnnLsDef 2 }

mscAppnDlciBnnLsDefProvEntry OBJECT-TYPE
   SYNTAX     MscAppnDlciBnnLsDefProvEntry
   ACCESS     not-accessible
   STATUS     mandatory
   DESCRIPTION
     "An entry in the mscAppnDlciBnnLsDefProvTable."
   INDEX {
      mscAppnIndex,
      mscAppnDlciIndex,
      mscAppnDlciBnnLsDefIndex }
::= { mscAppnDlciBnnLsDefProvTable 1 }

MscAppnDlciBnnLsDefProvEntry ::= SEQUENCE {
   mscAppnDlciBnnLsDefDspuService
      INTEGER,
   mscAppnDlciBnnLsDefAdjacentCpName
      AsciiString,
   mscAppnDlciBnnLsDefAdjacentCpType
      INTEGER,
   mscAppnDlciBnnLsDefTgNum
      Unsigned32,
   mscAppnDlciBnnLsDefDlusName
      AsciiString,
   mscAppnDlciBnnLsDefBackupDlusName
      AsciiString,
   mscAppnDlciBnnLsDefHprSupported
      INTEGER,
   mscAppnDlciBnnLsDefAdjacentNodeID
      Hex,
   mscAppnDlciBnnLsDefCpCpSessionSupport
      INTEGER,
   mscAppnDlciBnnLsDefMaxTxBtuSize
      Unsigned32,
   mscAppnDlciBnnLsDefLsRole
      INTEGER }

mscAppnDlciBnnLsDefDspuService OBJECT-TYPE
   SYNTAX     INTEGER  {
                 none(0),
                 dlur(2) }
   ACCESS     read-write
   STATUS     mandatory
   DESCRIPTION
     "This attribute specifies which down stream physical unit service is 
      supported on this Link Station."
   DEFVAL     { none }
::= { mscAppnDlciBnnLsDefProvEntry 1 }

mscAppnDlciBnnLsDefAdjacentCpName OBJECT-TYPE
   SYNTAX     AsciiString (SIZE (0..17))
   ACCESS     read-write
   STATUS     mandatory
   DESCRIPTION
     "This attribute specifies the fully qualified control point (FQCP) 
      name of the adjacent node.  This attribute is ignored if the adjacent 
      node is not an APPN node.
      
      If this attribute is not empty it is checked against the name received 
      from the adjacent node during the XID exchange, unless 
      adjacentCpType is set to backLevelLenNode (in which case it is 
      used to identify the adjacent node).
      
      The first portion of this name, up to the period, is the network 
      identifier for the network to which the adjacent node belongs. An 
      APPN network is a portion of a virtual private network which has a 
      separately administered name space. This network identifier is the 
      implicit qualifier of all resources which do not have an explicit 
      network identifier."
   DEFVAL     { ''H }  -- ""
::= { mscAppnDlciBnnLsDefProvEntry 2 }

mscAppnDlciBnnLsDefAdjacentCpType OBJECT-TYPE
   SYNTAX     INTEGER  {
                 appnNode(0),
                 networkNode(2),
                 endNode(3),
                 backLevelLenNode(5),
                 hostXID3(6),
                 hostXID0(7),
                 dlurXID(8),
                 dlurNoXID(9) }
   ACCESS     read-write
   STATUS     mandatory
   DESCRIPTION
     "This attribute specifies the adjacent control point (CP) type:
      
      networkNode - Specifies that the adjacent device is an APPN 
      network node.
      
      endNode - Specifies that the adjacent device is an APPN end node.
      
      appnNode - Specifies that the adjacent device is an APPN node or 
      an up-level LEN node, and the node type will be dynamically 
      determined during XID exchange.
      
      backLevelLenNode - Specifies that the adjacent device is a back-
      level LEN node.
      
      hostXID3 - Specifies that the adjacent device is a host and that this 
      APPN node should respond to a polling XID from the node with a 
      format 3 XID.
      
      hostXID0 - Specifies that the adjacent device is a host and that this 
      APPN node should respond to a polling XID from the node with a 
      format 0 XID.
      
      dlurXID - Specifies that the adjacent device is a downstream PU 
      requiring DLUR services and XID exchange in link activation
      
      dlurNoXID - Specifies that the adjacent device is a downstream PU 
      requiring DLUR services and no XID exchange in link activation"
   DEFVAL     { appnNode }
::= { mscAppnDlciBnnLsDefProvEntry 3 }

mscAppnDlciBnnLsDefTgNum OBJECT-TYPE
   SYNTAX     Unsigned32 (0..20)
   ACCESS     read-write
   STATUS     mandatory
   DESCRIPTION
     "This attribute specifies the TG number to be used for this link.  It is 
      only relevant if the adjacent device is an APPN node and is ignored 
      otherwise.  
      
      If adjacentCpType is set to backLevelLenNode this attribute is 
      ignored and the TG number is assumed to be 1. 
      
      If this attribute is set to zero (0), the TG number is dynamically 
      assigned and can be determined from the tgNum attribute of the 
      related LinkStation component.
      
      If this attribute is non-zero, the adjacentCpType must be set to 
      appnNode, networkNode, endNode or backLevelLenNode, and the 
      TG number on the adjacent device must also be set to the same 
      value."
   DEFVAL     { 0 }
::= { mscAppnDlciBnnLsDefProvEntry 5 }

mscAppnDlciBnnLsDefDlusName OBJECT-TYPE
   SYNTAX     AsciiString (SIZE (0..17))
   ACCESS     read-write
   STATUS     mandatory
   DESCRIPTION
     "This attribute specifies the fully qualified control point (FQCP) 
      name of the primary DLUS for this link station. This attribute is 
      ignored if the adjacent device does not request DLUR services.
      
      This attribute overrides the primaryDefDlusName and 
      secondaryDefDlusName specified in the DLUR component.
      If this attribute is empty, the primaryDefDlusName (specified in the 
      DLUR component), or secondaryDefDlusName (specified in the 
      DLUR component) will be used.
      
      The first portion of this name, up to the period, is the network 
      identifier for the network to which the DLUS node belongs. An 
      APPN network is a portion of a virtual private network which has a 
      separately administered name space. This network identifier is the 
      implicit qualifier of all resources which do not have an explicit 
      network identifier."
   DEFVAL     { ''H }  -- ""
::= { mscAppnDlciBnnLsDefProvEntry 6 }

mscAppnDlciBnnLsDefBackupDlusName OBJECT-TYPE
   SYNTAX     AsciiString (SIZE (0..17))
   ACCESS     read-write
   STATUS     mandatory
   DESCRIPTION
     "This attribute specifies the fully qualified control point (FQCP) 
      name of the backup DLUS for this link station.  This attribute is 
      ignored if the adjacent device does not request DLUR services.
      
      This attribute overrides the primaryDefDlusName and 
      secondaryDefDlusName specified in the DLUR component.
      If this attribute is empty and the dlusName attribute is empty, the 
      primaryDefDlusName (specified in the DLUR component), or 
      secondaryDefDlusName (specified in the DLUR component) will be 
      used. If this attribute is specified, the dlusName attribute must also 
      contain a non-empty string.
      
      The first portion of this name, up to the period, is the network 
      identifier for the network to which the DLUS node belongs. An 
      APPN network is a portion of a virtual private network which has a 
      separately administered name space. This network identifier is the 
      implicit qualifier of all resources which do not have an explicit 
      network identifier."
   DEFVAL     { ''H }  -- ""
::= { mscAppnDlciBnnLsDefProvEntry 7 }

mscAppnDlciBnnLsDefHprSupported OBJECT-TYPE
   SYNTAX     INTEGER  {
                 no(0),
                 sameAsNode(1) }
   ACCESS     read-write
   STATUS     mandatory
   DESCRIPTION
     "This attribute specifies whether high performance routing (HPR) is 
      supported on this link station. 
      
      If this attribute is set to sameAsNode, and the hprSupport attribute 
      in the APPN component is set to either rtp or anr, HPR will be 
      negotiated with the remote node, if the hprSupport attrbute in the 
      APPN component is set to no HPR will not be negotiated with the 
      remote node. If this attribute is set to no, HPR will not be 
      negotiated on this link station. The results of this negotiation are 
      visible in the hprSupport attribute of the related LinkStation 
      component"
   DEFVAL     { sameAsNode }
::= { mscAppnDlciBnnLsDefProvEntry 8 }

mscAppnDlciBnnLsDefAdjacentNodeID OBJECT-TYPE
   SYNTAX     Hex (0..4294967295)
   ACCESS     read-write
   STATUS     mandatory
   DESCRIPTION
     "This attribute specifies the node id of the adjacent device. 
      
      This attribute, if non-zero, is used to check the identity of the 
      adjacent device. If this attribute is zero, the identity is not checked.
      If adjacentCpType is set to dlurNoXID, this attribute is used to 
      identify the downstream PU to the DLUS."
   DEFVAL     { 0 }
::= { mscAppnDlciBnnLsDefProvEntry 9 }

mscAppnDlciBnnLsDefCpCpSessionSupport OBJECT-TYPE
   SYNTAX     INTEGER  {
                 no(0),
                 yes(1) }
   ACCESS     read-write
   STATUS     mandatory
   DESCRIPTION
     "This attribute specifies whether this link station supports CP-CP 
      sessions.  This attribute is ignored if the adjacent device is not an 
      APPN node."
   DEFVAL     { yes }
::= { mscAppnDlciBnnLsDefProvEntry 10 }

mscAppnDlciBnnLsDefMaxTxBtuSize OBJECT-TYPE
   SYNTAX     Unsigned32 (99..32768)
   ACCESS     read-write
   STATUS     mandatory
   DESCRIPTION
     "This attribute specifies the maximum basic transmission unit (BTU) 
      size that can be sent on this link station.  This attribute is used to 
      negotiate the maximum BTU size that can be transmitted between a 
      link station pair.  
      
      If the link and node are HPR-capable, then this attribute must be set 
      to a value greater than or equal to 768."
   DEFVAL     { 2048 }
::= { mscAppnDlciBnnLsDefProvEntry 11 }

mscAppnDlciBnnLsDefLsRole OBJECT-TYPE
   SYNTAX     INTEGER  {
                 negotiable(0),
                 primary(1),
                 secondary(2) }
   ACCESS     read-write
   STATUS     mandatory
   DESCRIPTION
     "This attribute specifies the role for this link station.  This attribute 
      will be ignored if adjacentCpType is set to hostXID0 or hostXID3 
      (the link station will always be secondary), or if  adjacentCpType is 
      set to dlurXID or dlurNoXID (the link station will always be 
      primary)."
   DEFVAL     { negotiable }
::= { mscAppnDlciBnnLsDefProvEntry 12 }


-- Appn/<string> Dlci/n ServiceParameters
-- The provisioned component contains  the rate enforcement 
-- parameters  for  the APPN DLCI.

mscAppnDlciSp OBJECT IDENTIFIER ::= { mscAppnDlci 5 }



mscAppnDlciSpRowStatusTable OBJECT-TYPE
   SYNTAX     SEQUENCE OF MscAppnDlciSpRowStatusEntry
   ACCESS     not-accessible
   STATUS     mandatory
   DESCRIPTION
     "This entry controls the addition and deletion of 
      mscAppnDlciSp components."
::= { mscAppnDlciSp 1 }

mscAppnDlciSpRowStatusEntry OBJECT-TYPE
   SYNTAX     MscAppnDlciSpRowStatusEntry
   ACCESS     not-accessible
   STATUS     mandatory
   DESCRIPTION
     "A single entry in the table represents a single 
      mscAppnDlciSp component."
   INDEX {
      mscAppnIndex,
      mscAppnDlciIndex,
      mscAppnDlciSpIndex }
::= { mscAppnDlciSpRowStatusTable 1 }

MscAppnDlciSpRowStatusEntry ::= SEQUENCE {
   mscAppnDlciSpRowStatus
      RowStatus,
   mscAppnDlciSpComponentName
      DisplayString,
   mscAppnDlciSpStorageType
      StorageType,
   mscAppnDlciSpIndex
      NonReplicated }

mscAppnDlciSpRowStatus OBJECT-TYPE
   SYNTAX     RowStatus 
   ACCESS     read-only
   STATUS     mandatory
   DESCRIPTION
     "This variable is used as the basis for SNMP naming of
      mscAppnDlciSp components.
      These components cannot be added nor deleted."
::= { mscAppnDlciSpRowStatusEntry 1 }

mscAppnDlciSpComponentName OBJECT-TYPE
   SYNTAX     DisplayString 
   ACCESS     read-only
   STATUS     mandatory
   DESCRIPTION
     "This variable provides the component's string name for
      use with the ASCII Console Interface"
::= { mscAppnDlciSpRowStatusEntry 2 }

mscAppnDlciSpStorageType OBJECT-TYPE
   SYNTAX     StorageType 
   ACCESS     read-only
   STATUS     mandatory
   DESCRIPTION
     "This variable represents the storage type value for the
      mscAppnDlciSp tables."
::= { mscAppnDlciSpRowStatusEntry 4 }

mscAppnDlciSpIndex OBJECT-TYPE
   SYNTAX     NonReplicated 
   ACCESS     not-accessible
   STATUS     mandatory
   DESCRIPTION
     "This variable represents the index for the mscAppnDlciSp tables."
::= { mscAppnDlciSpRowStatusEntry 10 }

mscAppnDlciSpParmsTable OBJECT-TYPE
   SYNTAX     SEQUENCE OF MscAppnDlciSpParmsEntry
   ACCESS     not-accessible
   STATUS     mandatory
   DESCRIPTION
     "This group contains the provisionable attributes for the Data Link 
      Connection Identifier.  These attributes reflect the service 
      parameters specific to this instance of Dlci."
::= { mscAppnDlciSp 11 }

mscAppnDlciSpParmsEntry OBJECT-TYPE
   SYNTAX     MscAppnDlciSpParmsEntry
   ACCESS     not-accessible
   STATUS     mandatory
   DESCRIPTION
     "An entry in the mscAppnDlciSpParmsTable."
   INDEX {
      mscAppnIndex,
      mscAppnDlciIndex,
      mscAppnDlciSpIndex }
::= { mscAppnDlciSpParmsTable 1 }

MscAppnDlciSpParmsEntry ::= SEQUENCE {
   mscAppnDlciSpRateEnforcement
      INTEGER,
   mscAppnDlciSpCommittedInformationRate
      Unsigned32,
   mscAppnDlciSpCommittedBurstSize
      Unsigned32,
   mscAppnDlciSpExcessBurstSize
      Unsigned32,
   mscAppnDlciSpMeasurementInterval
      Unsigned32 }

mscAppnDlciSpRateEnforcement OBJECT-TYPE
   SYNTAX     INTEGER  {
                 off(0),
                 on(1) }
   ACCESS     read-write
   STATUS     mandatory
   DESCRIPTION
     "This attribute specifies whether rate enforcement is to be used on 
      this DLCI.  Turning on rate enforcement means that the data sent 
      from the service to the virtual circuit is subjected to rate control."
   DEFVAL     { on }
::= { mscAppnDlciSpParmsEntry 1 }

mscAppnDlciSpCommittedInformationRate OBJECT-TYPE
   SYNTAX     Unsigned32 (0..50000000)
   ACCESS     read-write
   STATUS     mandatory
   DESCRIPTION
     "This attribute specifies the committed information rate (cir) in bits 
      per second (bit/s). When rateEnforcement is set to on, cir  is the 
      rate at which the network agrees to transfer information under 
      normal conditions. This rate is measured over a measurement 
      interval (t) that is determined internally based on cir and the 
      committed burst size (bc). An exception to this occurs when cir is 
      provisioned to be zero, in which case the measurement interval (t) 
      must be provisioned explicitly.
      
      This attribute is ignored when rateEnforcement is off. If 
      rateEnforcement is on and this attribute is 0, bc must also be 0."
   DEFVAL     { 64000 }
::= { mscAppnDlciSpParmsEntry 2 }

mscAppnDlciSpCommittedBurstSize OBJECT-TYPE
   SYNTAX     Unsigned32 (0..50000000)
   ACCESS     read-write
   STATUS     mandatory
   DESCRIPTION
     "This attribute specifies the committed burst size (bc) in bits. bc is 
      the amount of data that a network agrees to transfer under normal 
      conditions over a measurement interval (t). Data marked DE=1 is 
      not accounted for in bc.
      
      This attribute is ignored when rateEnforcement is off. If 
      rateEnforcement is on and this attribute is 0, cir must also be 0."
   DEFVAL     { 64000 }
::= { mscAppnDlciSpParmsEntry 3 }

mscAppnDlciSpExcessBurstSize OBJECT-TYPE
   SYNTAX     Unsigned32 (0..50000000)
   ACCESS     read-write
   STATUS     mandatory
   DESCRIPTION
     "This attribute specifies the excess burst size (be) in bits. be is the 
      amount of uncommitted data that the network will attempt to deliver 
      over measurement interval (t). Data marked DE=1 by the user or by 
      the network is accounted for here.
      
      cir, bc, and be cannot all be 0 when rateEnforcement is on."
   DEFVAL     { 0 }
::= { mscAppnDlciSpParmsEntry 4 }

mscAppnDlciSpMeasurementInterval OBJECT-TYPE
   SYNTAX     Unsigned32 (0..25500)
   ACCESS     read-write
   STATUS     mandatory
   DESCRIPTION
     "This attribute specifies the time interval (in milliseconds) over 
      which rates and burst sizes are measured.  When cir and bc are 0 
      and rateEnforcement is on, this attribute must be provisioned.  
      
      When cir and bc are non-zero, the time interval is internally 
      calculated. In that situation, this attribute  is ignored, and is not 
      representative of the time interval. This attribute is also ignored 
      when rateEnforcement is off.  If rateEnforcement is on and both cir 
      and bc are 0, this field must be non-zero."
   DEFVAL     { 0 }
::= { mscAppnDlciSpParmsEntry 5 }


-- Appn/<string> Dlci/n BanLinkStationDefinition/<mac>, <sap>
-- This component allows the user to control how the frame relay 
-- DLCI is used, by controlling the Link Station definition. This 
-- component is required if a connect out needs to be generated for a 
-- particular device connected over this DLCI.  The index of 
-- component is the MAC, SAP pair of the remote device.  For APPN 
-- network node to network node connections, BanLsDef needs to be 
-- added to the DLCI at one end of the connecting PVC with 
-- dspuService set to none.   

mscAppnDlciBanLsDef OBJECT IDENTIFIER ::= { mscAppnDlci 6 }



mscAppnDlciBanLsDefRowStatusTable OBJECT-TYPE
   SYNTAX     SEQUENCE OF MscAppnDlciBanLsDefRowStatusEntry
   ACCESS     not-accessible
   STATUS     mandatory
   DESCRIPTION
     "This entry controls the addition and deletion of 
      mscAppnDlciBanLsDef components."
::= { mscAppnDlciBanLsDef 1 }

mscAppnDlciBanLsDefRowStatusEntry OBJECT-TYPE
   SYNTAX     MscAppnDlciBanLsDefRowStatusEntry
   ACCESS     not-accessible
   STATUS     mandatory
   DESCRIPTION
     "A single entry in the table represents a single 
      mscAppnDlciBanLsDef component."
   INDEX {
      mscAppnIndex,
      mscAppnDlciIndex,
      mscAppnDlciBanLsDefMacIndex,
      mscAppnDlciBanLsDefSapIndex }
::= { mscAppnDlciBanLsDefRowStatusTable 1 }

MscAppnDlciBanLsDefRowStatusEntry ::= SEQUENCE {
   mscAppnDlciBanLsDefRowStatus
      RowStatus,
   mscAppnDlciBanLsDefComponentName
      DisplayString,
   mscAppnDlciBanLsDefStorageType
      StorageType,
   mscAppnDlciBanLsDefMacIndex
      DashedHexString,
   mscAppnDlciBanLsDefSapIndex
      Integer32 }

mscAppnDlciBanLsDefRowStatus OBJECT-TYPE
   SYNTAX     RowStatus 
   ACCESS     read-write
   STATUS     mandatory
   DESCRIPTION
     "This variable is used as the basis for SNMP naming of
      mscAppnDlciBanLsDef components.
      These components can be added and deleted."
::= { mscAppnDlciBanLsDefRowStatusEntry 1 }

mscAppnDlciBanLsDefComponentName OBJECT-TYPE
   SYNTAX     DisplayString 
   ACCESS     read-only
   STATUS     mandatory
   DESCRIPTION
     "This variable provides the component's string name for
      use with the ASCII Console Interface"
::= { mscAppnDlciBanLsDefRowStatusEntry 2 }

mscAppnDlciBanLsDefStorageType OBJECT-TYPE
   SYNTAX     StorageType 
   ACCESS     read-only
   STATUS     mandatory
   DESCRIPTION
     "This variable represents the storage type value for the
      mscAppnDlciBanLsDef tables."
::= { mscAppnDlciBanLsDefRowStatusEntry 4 }

mscAppnDlciBanLsDefMacIndex OBJECT-TYPE
   SYNTAX     DashedHexString (SIZE (6))
   ACCESS     not-accessible
   STATUS     mandatory
   DESCRIPTION
     "This variable represents an index for the mscAppnDlciBanLsDef tables."
::= { mscAppnDlciBanLsDefRowStatusEntry 10 }

mscAppnDlciBanLsDefSapIndex OBJECT-TYPE
   SYNTAX     Integer32 (4 | 8 | 12 | 16 | 20 | 24 | 28 | 32 | 36 | 40 | 44 | 48 | 52 | 56 | 60 | 64 | 68 | 72 | 76 | 80 | 84 | 88 | 92 | 96 | 100 | 104 | 108 | 112 | 116 | 120 | 124 | 128 | 132 | 136 | 140 | 144 | 148 | 152 | 156 | 160 | 164 | 168 | 172 | 176 | 180 | 184 | 188 | 192 | 196 | 200 | 204 | 208 | 212 | 216 | 220 | 224 | 228 | 232 | 236 | 240 | 244 | 248 | 252)
   ACCESS     not-accessible
   STATUS     mandatory
   DESCRIPTION
     "This variable represents an index for the mscAppnDlciBanLsDef tables."
::= { mscAppnDlciBanLsDefRowStatusEntry 11 }

mscAppnDlciBanLsDefProvTable OBJECT-TYPE
   SYNTAX     SEQUENCE OF MscAppnDlciBanLsDefProvEntry
   ACCESS     not-accessible
   STATUS     mandatory
   DESCRIPTION
     "This group contains the provisioning data for a Link Station on a 
      frame relay DLCI."
::= { mscAppnDlciBanLsDef 2 }

mscAppnDlciBanLsDefProvEntry OBJECT-TYPE
   SYNTAX     MscAppnDlciBanLsDefProvEntry
   ACCESS     not-accessible
   STATUS     mandatory
   DESCRIPTION
     "An entry in the mscAppnDlciBanLsDefProvTable."
   INDEX {
      mscAppnIndex,
      mscAppnDlciIndex,
      mscAppnDlciBanLsDefMacIndex,
      mscAppnDlciBanLsDefSapIndex }
::= { mscAppnDlciBanLsDefProvTable 1 }

MscAppnDlciBanLsDefProvEntry ::= SEQUENCE {
   mscAppnDlciBanLsDefDspuService
      INTEGER,
   mscAppnDlciBanLsDefAdjacentCpName
      AsciiString,
   mscAppnDlciBanLsDefAdjacentCpType
      INTEGER,
   mscAppnDlciBanLsDefTgNum
      Unsigned32,
   mscAppnDlciBanLsDefDlusName
      AsciiString,
   mscAppnDlciBanLsDefBackupDlusName
      AsciiString,
   mscAppnDlciBanLsDefHprSupported
      INTEGER,
   mscAppnDlciBanLsDefAdjacentNodeID
      Hex,
   mscAppnDlciBanLsDefCpCpSessionSupport
      INTEGER,
   mscAppnDlciBanLsDefMaxTxBtuSize
      Unsigned32,
   mscAppnDlciBanLsDefLsRole
      INTEGER }

mscAppnDlciBanLsDefDspuService OBJECT-TYPE
   SYNTAX     INTEGER  {
                 none(0),
                 dlur(2) }
   ACCESS     read-write
   STATUS     mandatory
   DESCRIPTION
     "This attribute specifies which down stream physical unit service is 
      supported on this Link Station."
   DEFVAL     { none }
::= { mscAppnDlciBanLsDefProvEntry 1 }

mscAppnDlciBanLsDefAdjacentCpName OBJECT-TYPE
   SYNTAX     AsciiString (SIZE (0..17))
   ACCESS     read-write
   STATUS     mandatory
   DESCRIPTION
     "This attribute specifies the fully qualified control point (FQCP) 
      name of the adjacent node.  This attribute is ignored if the adjacent 
      node is not an APPN node.
      
      If this attribute is not empty it is checked against the name received 
      from the adjacent node during the XID exchange, unless 
      adjacentCpType is set to backLevelLenNode (in which case it is 
      used to identify the adjacent node).
      
      The first portion of this name, up to the period, is the network 
      identifier for the network to which the adjacent node belongs. An 
      APPN network is a portion of a virtual private network which has a 
      separately administered name space. This network identifier is the 
      implicit qualifier of all resources which do not have an explicit 
      network identifier."
   DEFVAL     { ''H }  -- ""
::= { mscAppnDlciBanLsDefProvEntry 2 }

mscAppnDlciBanLsDefAdjacentCpType OBJECT-TYPE
   SYNTAX     INTEGER  {
                 appnNode(0),
                 networkNode(2),
                 endNode(3),
                 backLevelLenNode(5),
                 hostXID3(6),
                 hostXID0(7),
                 dlurXID(8),
                 dlurNoXID(9) }
   ACCESS     read-write
   STATUS     mandatory
   DESCRIPTION
     "This attribute specifies the adjacent control point (CP) type:
      
      networkNode - Specifies that the adjacent device is an APPN 
      network node.
      
      endNode - Specifies that the adjacent device is an APPN end node.
      
      appnNode - Specifies that the adjacent device is an APPN node or 
      an up-level LEN node, and the node type will be dynamically 
      determined during XID exchange.
      
      backLevelLenNode - Specifies that the adjacent device is a back-
      level LEN node.
      
      hostXID3 - Specifies that the adjacent device is a host and that this 
      APPN node should respond to a polling XID from the node with a 
      format 3 XID.
      
      hostXID0 - Specifies that the adjacent device is a host and that this 
      APPN node should respond to a polling XID from the node with a 
      format 0 XID.
      
      dlurXID - Specifies that the adjacent device is a downstream PU 
      requiring DLUR services and XID exchange in link activation
      
      dlurNoXID - Specifies that the adjacent device is a downstream PU 
      requiring DLUR services and no XID exchange in link activation"
   DEFVAL     { appnNode }
::= { mscAppnDlciBanLsDefProvEntry 3 }

mscAppnDlciBanLsDefTgNum OBJECT-TYPE
   SYNTAX     Unsigned32 (0..20)
   ACCESS     read-write
   STATUS     mandatory
   DESCRIPTION
     "This attribute specifies the TG number to be used for this link.  It is 
      only relevant if the adjacent device is an APPN node and is ignored 
      otherwise.  
      
      If adjacentCpType is set to backLevelLenNode this attribute is 
      ignored and the TG number is assumed to be 1. 
      
      If this attribute is set to zero (0), the TG number is dynamically 
      assigned and can be determined from the tgNum attribute of the 
      related LinkStation component.
      
      If this attribute is non-zero, the adjacentCpType must be set to 
      appnNode, networkNode, endNode or backLevelLenNode, and the 
      TG number on the adjacent device must also be set to the same 
      value."
   DEFVAL     { 0 }
::= { mscAppnDlciBanLsDefProvEntry 5 }

mscAppnDlciBanLsDefDlusName OBJECT-TYPE
   SYNTAX     AsciiString (SIZE (0..17))
   ACCESS     read-write
   STATUS     mandatory
   DESCRIPTION
     "This attribute specifies the fully qualified control point (FQCP) 
      name of the primary DLUS for this link station. This attribute is 
      ignored if the adjacent device does not request DLUR services.
      
      This attribute overrides the primaryDefDlusName and 
      secondaryDefDlusName specified in the DLUR component.
      If this attribute is empty, the primaryDefDlusName (specified in the 
      DLUR component), or secondaryDefDlusName (specified in the 
      DLUR component) will be used.
      
      The first portion of this name, up to the period, is the network 
      identifier for the network to which the DLUS node belongs. An 
      APPN network is a portion of a virtual private network which has a 
      separately administered name space. This network identifier is the 
      implicit qualifier of all resources which do not have an explicit 
      network identifier."
   DEFVAL     { ''H }  -- ""
::= { mscAppnDlciBanLsDefProvEntry 6 }

mscAppnDlciBanLsDefBackupDlusName OBJECT-TYPE
   SYNTAX     AsciiString (SIZE (0..17))
   ACCESS     read-write
   STATUS     mandatory
   DESCRIPTION
     "This attribute specifies the fully qualified control point (FQCP) 
      name of the backup DLUS for this link station.  This attribute is 
      ignored if the adjacent device does not request DLUR services.
      
      This attribute overrides the primaryDefDlusName and 
      secondaryDefDlusName specified in the DLUR component.
      If this attribute is empty and the dlusName attribute is empty, the 
      primaryDefDlusName (specified in the DLUR component), or 
      secondaryDefDlusName (specified in the DLUR component) will be 
      used. If this attribute is specified, the dlusName attribute must also 
      contain a non-empty string.
      
      The first portion of this name, up to the period, is the network 
      identifier for the network to which the DLUS node belongs. An 
      APPN network is a portion of a virtual private network which has a 
      separately administered name space. This network identifier is the 
      implicit qualifier of all resources which do not have an explicit 
      network identifier."
   DEFVAL     { ''H }  -- ""
::= { mscAppnDlciBanLsDefProvEntry 7 }

mscAppnDlciBanLsDefHprSupported OBJECT-TYPE
   SYNTAX     INTEGER  {
                 no(0),
                 sameAsNode(1) }
   ACCESS     read-write
   STATUS     mandatory
   DESCRIPTION
     "This attribute specifies whether high performance routing (HPR) is 
      supported on this link station. 
      
      If this attribute is set to sameAsNode, and the hprSupport attribute 
      in the APPN component is set to either rtp or anr, HPR will be 
      negotiated with the remote node, if the hprSupport attrbute in the 
      APPN component is set to no HPR will not be negotiated with the 
      remote node. If this attribute is set to no, HPR will not be 
      negotiated on this link station. The results of this negotiation are 
      visible in the hprSupport attribute of the related LinkStation 
      component"
   DEFVAL     { sameAsNode }
::= { mscAppnDlciBanLsDefProvEntry 8 }

mscAppnDlciBanLsDefAdjacentNodeID OBJECT-TYPE
   SYNTAX     Hex (0..4294967295)
   ACCESS     read-write
   STATUS     mandatory
   DESCRIPTION
     "This attribute specifies the node id of the adjacent device. 
      
      This attribute, if non-zero, is used to check the identity of the 
      adjacent device. If this attribute is zero, the identity is not checked.
      If adjacentCpType is set to dlurNoXID, this attribute is used to 
      identify the downstream PU to the DLUS."
   DEFVAL     { 0 }
::= { mscAppnDlciBanLsDefProvEntry 9 }

mscAppnDlciBanLsDefCpCpSessionSupport OBJECT-TYPE
   SYNTAX     INTEGER  {
                 no(0),
                 yes(1) }
   ACCESS     read-write
   STATUS     mandatory
   DESCRIPTION
     "This attribute specifies whether this link station supports CP-CP 
      sessions.  This attribute is ignored if the adjacent device is not an 
      APPN node."
   DEFVAL     { yes }
::= { mscAppnDlciBanLsDefProvEntry 10 }

mscAppnDlciBanLsDefMaxTxBtuSize OBJECT-TYPE
   SYNTAX     Unsigned32 (99..32768)
   ACCESS     read-write
   STATUS     mandatory
   DESCRIPTION
     "This attribute specifies the maximum basic transmission unit (BTU) 
      size that can be sent on this link station.  This attribute is used to 
      negotiate the maximum BTU size that can be transmitted between a 
      link station pair.  
      
      If the link and node are HPR-capable, then this attribute must be set 
      to a value greater than or equal to 768."
   DEFVAL     { 2048 }
::= { mscAppnDlciBanLsDefProvEntry 11 }

mscAppnDlciBanLsDefLsRole OBJECT-TYPE
   SYNTAX     INTEGER  {
                 negotiable(0),
                 primary(1),
                 secondary(2) }
   ACCESS     read-write
   STATUS     mandatory
   DESCRIPTION
     "This attribute specifies the role for this link station.  This attribute 
      will be ignored if adjacentCpType is set to hostXID0 or hostXID3 
      (the link station will always be secondary), or if  adjacentCpType is 
      set to dlurXID or dlurNoXID (the link station will always be 
      primary)."
   DEFVAL     { negotiable }
::= { mscAppnDlciBanLsDefProvEntry 12 }


-- Appn/<string> Dlci/n BoundaryAccessNode
-- This component represents the local MAC address and local SAP 
-- number used on frames sent on this DLCI. This component is 
-- required if this link station is to be activated by another adjacent 
-- node for PVC connection using BAN encapsulation.

mscAppnDlciBan OBJECT IDENTIFIER ::= { mscAppnDlci 7 }



mscAppnDlciBanRowStatusTable OBJECT-TYPE
   SYNTAX     SEQUENCE OF MscAppnDlciBanRowStatusEntry
   ACCESS     not-accessible
   STATUS     mandatory
   DESCRIPTION
     "This entry controls the addition and deletion of 
      mscAppnDlciBan components."
::= { mscAppnDlciBan 1 }

mscAppnDlciBanRowStatusEntry OBJECT-TYPE
   SYNTAX     MscAppnDlciBanRowStatusEntry
   ACCESS     not-accessible
   STATUS     mandatory
   DESCRIPTION
     "A single entry in the table represents a single 
      mscAppnDlciBan component."
   INDEX {
      mscAppnIndex,
      mscAppnDlciIndex,
      mscAppnDlciBanIndex }
::= { mscAppnDlciBanRowStatusTable 1 }

MscAppnDlciBanRowStatusEntry ::= SEQUENCE {
   mscAppnDlciBanRowStatus
      RowStatus,
   mscAppnDlciBanComponentName
      DisplayString,
   mscAppnDlciBanStorageType
      StorageType,
   mscAppnDlciBanIndex
      NonReplicated }

mscAppnDlciBanRowStatus OBJECT-TYPE
   SYNTAX     RowStatus 
   ACCESS     read-write
   STATUS     mandatory
   DESCRIPTION
     "This variable is used as the basis for SNMP naming of
      mscAppnDlciBan components.
      These components can be added and deleted."
::= { mscAppnDlciBanRowStatusEntry 1 }

mscAppnDlciBanComponentName OBJECT-TYPE
   SYNTAX     DisplayString 
   ACCESS     read-only
   STATUS     mandatory
   DESCRIPTION
     "This variable provides the component's string name for
      use with the ASCII Console Interface"
::= { mscAppnDlciBanRowStatusEntry 2 }

mscAppnDlciBanStorageType OBJECT-TYPE
   SYNTAX     StorageType 
   ACCESS     read-only
   STATUS     mandatory
   DESCRIPTION
     "This variable represents the storage type value for the
      mscAppnDlciBan tables."
::= { mscAppnDlciBanRowStatusEntry 4 }

mscAppnDlciBanIndex OBJECT-TYPE
   SYNTAX     NonReplicated 
   ACCESS     not-accessible
   STATUS     mandatory
   DESCRIPTION
     "This variable represents the index for the mscAppnDlciBan tables."
::= { mscAppnDlciBanRowStatusEntry 10 }

mscAppnDlciBanProvTable OBJECT-TYPE
   SYNTAX     SEQUENCE OF MscAppnDlciBanProvEntry
   ACCESS     not-accessible
   STATUS     mandatory
   DESCRIPTION
     "This group contains the provisioning data for the local link address 
      (MAP,SAP pair) to be used for a Frame Relay connection with 
      BAN encapsulation."
::= { mscAppnDlciBan 2 }

mscAppnDlciBanProvEntry OBJECT-TYPE
   SYNTAX     MscAppnDlciBanProvEntry
   ACCESS     not-accessible
   STATUS     mandatory
   DESCRIPTION
     "An entry in the mscAppnDlciBanProvTable."
   INDEX {
      mscAppnIndex,
      mscAppnDlciIndex,
      mscAppnDlciBanIndex }
::= { mscAppnDlciBanProvTable 1 }

MscAppnDlciBanProvEntry ::= SEQUENCE {
   mscAppnDlciBanLocalMac
      DashedHexString,
   mscAppnDlciBanLocalSap
      Hex }

mscAppnDlciBanLocalMac OBJECT-TYPE
   SYNTAX     DashedHexString (SIZE (6))
   ACCESS     read-write
   STATUS     mandatory
   DESCRIPTION
     "This attribute specifies the MAC address to be used for a Frame 
      Relay connection with BAN encapsulation."
   DEFVAL     { '4fff00000000'H }
::= { mscAppnDlciBanProvEntry 1 }

mscAppnDlciBanLocalSap OBJECT-TYPE
   SYNTAX     Hex (4 | 8 | 12 | 16 | 20 | 24 | 28 | 32 | 36 | 40 | 44 | 48 | 52 | 56 | 60 | 64 | 68 | 72 | 76 | 80 | 84 | 88 | 92 | 96 | 100 | 104 | 108 | 112 | 116 | 120 | 124 | 128 | 132 | 136 | 140 | 144 | 148 | 152 | 156 | 160 | 164 | 168 | 172 | 176 | 180 | 184 | 188 | 192 | 196 | 200 | 204 | 208 | 212 | 216 | 220 | 224 | 228 | 232 | 236 | 240 | 244 | 248 | 252)
   ACCESS     read-write
   STATUS     mandatory
   DESCRIPTION
     "This attribute specifies the local SAP number to be used  for a  
      Frame Relay connection with BAN encapsulation."
   DEFVAL     { 4 }
::= { mscAppnDlciBanProvEntry 2 }


-- Appn/<string> LogicalChannelNumber/n 
-- This component represents the logical channel number that the Vc 
-- terminates on in the QLLC based service.  The 
-- LogicalChannelNumber (Lcn)  component is either  added to 
-- initiate outgoing switched virtual circuit calls or is created 
-- dynamically when switched virtual circuit (SVC) calls are received 
-- by the Appn service. The range for defined Lcn components is 1-99. 
-- For defined Lcn components, command Lock Appn/n Lcn/m  will 
-- change the state of the component and clear the Vc associated with 
-- this Lcn.  Unlock Appn/n Lcn/m will also change the state of the 
-- component and will attempt to establish the Vc.  For dynamic Lcn 
-- components, Lock Appn/n Lcn/m will clear the Vc and the 
-- component will disappear.

mscAppnLcn OBJECT IDENTIFIER ::= { mscAppn 4 }



mscAppnLcnRowStatusTable OBJECT-TYPE
   SYNTAX     SEQUENCE OF MscAppnLcnRowStatusEntry
   ACCESS     not-accessible
   STATUS     mandatory
   DESCRIPTION
     "This entry controls the addition and deletion of 
      mscAppnLcn components."
::= { mscAppnLcn 1 }

mscAppnLcnRowStatusEntry OBJECT-TYPE
   SYNTAX     MscAppnLcnRowStatusEntry
   ACCESS     not-accessible
   STATUS     mandatory
   DESCRIPTION
     "A single entry in the table represents a single 
      mscAppnLcn component."
   INDEX {
      mscAppnIndex,
      mscAppnLcnIndex }
::= { mscAppnLcnRowStatusTable 1 }

MscAppnLcnRowStatusEntry ::= SEQUENCE {
   mscAppnLcnRowStatus
      RowStatus,
   mscAppnLcnComponentName
      DisplayString,
   mscAppnLcnStorageType
      StorageType,
   mscAppnLcnIndex
      Integer32 }

mscAppnLcnRowStatus OBJECT-TYPE
   SYNTAX     RowStatus 
   ACCESS     read-write
   STATUS     mandatory
   DESCRIPTION
     "This variable is used as the basis for SNMP naming of
      mscAppnLcn components.
      These components can be added and deleted."
::= { mscAppnLcnRowStatusEntry 1 }

mscAppnLcnComponentName OBJECT-TYPE
   SYNTAX     DisplayString 
   ACCESS     read-only
   STATUS     mandatory
   DESCRIPTION
     "This variable provides the component's string name for
      use with the ASCII Console Interface"
::= { mscAppnLcnRowStatusEntry 2 }

mscAppnLcnStorageType OBJECT-TYPE
   SYNTAX     StorageType 
   ACCESS     read-only
   STATUS     mandatory
   DESCRIPTION
     "This variable represents the storage type value for the
      mscAppnLcn tables."
::= { mscAppnLcnRowStatusEntry 4 }

mscAppnLcnIndex OBJECT-TYPE
   SYNTAX     Integer32 (1..4095)
   ACCESS     not-accessible
   STATUS     mandatory
   DESCRIPTION
     "This variable represents the index for the mscAppnLcn tables."
::= { mscAppnLcnRowStatusEntry 10 }

mscAppnLcnStateTable OBJECT-TYPE
   SYNTAX     SEQUENCE OF MscAppnLcnStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscAppnLcn 10 }

mscAppnLcnStateEntry OBJECT-TYPE
   SYNTAX     MscAppnLcnStateEntry
   ACCESS     not-accessible
   STATUS     mandatory
   DESCRIPTION
     "An entry in the mscAppnLcnStateTable."
   INDEX {
      mscAppnIndex,
      mscAppnLcnIndex }
::= { mscAppnLcnStateTable 1 }

MscAppnLcnStateEntry ::= SEQUENCE {
   mscAppnLcnAdminState
      INTEGER,
   mscAppnLcnOperationalState
      INTEGER,
   mscAppnLcnUsageState
      INTEGER }

mscAppnLcnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscAppnLcnStateEntry 1 }

mscAppnLcnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscAppnLcnStateEntry 2 }

mscAppnLcnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscAppnLcnStateEntry 3 }


-- Appn/<string> Lcn/n Dc
-- This component defines the characteristics of a direct call or 
-- permanent virtual circuit.This component is derived from the virtual 
-- circuit services Dc component and specifies the subset of the 
-- capabilities of that component which are supported by the SNA 
-- service.

mscAppnLcnDc OBJECT IDENTIFIER ::= { mscAppnLcn 2 }



mscAppnLcnDcRowStatusTable OBJECT-TYPE
   SYNTAX     SEQUENCE OF MscAppnLcnDcRowStatusEntry
   ACCESS     not-accessible
   STATUS     mandatory
   DESCRIPTION
     "This entry controls the addition and deletion of 
      mscAppnLcnDc components."
::= { mscAppnLcnDc 1 }

mscAppnLcnDcRowStatusEntry OBJECT-TYPE
   SYNTAX     MscAppnLcnDcRowStatusEntry
   ACCESS     not-accessible
   STATUS     mandatory
   DESCRIPTION
     "A single entry in the table represents a single 
      mscAppnLcnDc component."
   INDEX {
      mscAppnIndex,
      mscAppnLcnIndex,
      mscAppnLcnDcIndex }
::= { mscAppnLcnDcRowStatusTable 1 }

MscAppnLcnDcRowStatusEntry ::= SEQUENCE {
   mscAppnLcnDcRowStatus
      RowStatus,
   mscAppnLcnDcComponentName
      DisplayString,
   mscAppnLcnDcStorageType
      StorageType,
   mscAppnLcnDcIndex
      NonReplicated }

mscAppnLcnDcRowStatus OBJECT-TYPE
   SYNTAX     RowStatus 
   ACCESS     read-only
   STATUS     mandatory
   DESCRIPTION
     "This variable is used as the basis for SNMP naming of
      mscAppnLcnDc components.
      These components cannot be added nor deleted."
::= { mscAppnLcnDcRowStatusEntry 1 }

mscAppnLcnDcComponentName OBJECT-TYPE
   SYNTAX     DisplayString 
   ACCESS     read-only
   STATUS     mandatory
   DESCRIPTION
     "This variable provides the component's string name for
      use with the ASCII Console Interface"
::= { mscAppnLcnDcRowStatusEntry 2 }

mscAppnLcnDcStorageType OBJECT-TYPE
   SYNTAX     StorageType 
   ACCESS     read-only
   STATUS     mandatory
   DESCRIPTION
     "This variable represents the storage type value for the
      mscAppnLcnDc tables."
::= { mscAppnLcnDcRowStatusEntry 4 }

mscAppnLcnDcIndex OBJECT-TYPE
   SYNTAX     NonReplicated 
   ACCESS     not-accessible
   STATUS     mandatory
   DESCRIPTION
     "This variable represents the index for the mscAppnLcnDc tables."
::= { mscAppnLcnDcRowStatusEntry 10 }

mscAppnLcnDcOptionsTable OBJECT-TYPE
   SYNTAX     SEQUENCE OF MscAppnLcnDcOptionsEntry
   ACCESS     not-accessible
   STATUS     mandatory
   DESCRIPTION
     "Options group defines attributes associated with direct call. It 
      defines complete connection in terms of path and call options. This 
      connection can be permanent (pvc) or switched (svc). It can have 
      facilities. The total number of bytes of facilities including the 
      facility codes, and all of the facility data from all of the four classes 
      of facilities:
      CCITT_Facilities
      DTE_Facilities
      National_Facilities
      International_Facilities
      must not exceed 512 bytes."
::= { mscAppnLcnDc 10 }

mscAppnLcnDcOptionsEntry OBJECT-TYPE
   SYNTAX     MscAppnLcnDcOptionsEntry
   ACCESS     not-accessible
   STATUS     mandatory
   DESCRIPTION
     "An entry in the mscAppnLcnDcOptionsTable."
   INDEX {
      mscAppnIndex,
      mscAppnLcnIndex,
      mscAppnLcnDcIndex }
::= { mscAppnLcnDcOptionsTable 1 }

MscAppnLcnDcOptionsEntry ::= SEQUENCE {
   mscAppnLcnDcRemoteNpi
      INTEGER,
   mscAppnLcnDcRemoteDna
      DigitString,
   mscAppnLcnDcTransferPriority
      INTEGER,
   mscAppnLcnDcDiscardPriority
      INTEGER }

mscAppnLcnDcRemoteNpi OBJECT-TYPE
   SYNTAX     INTEGER  {
                 x121(0),
                 e164(1) }
   ACCESS     read-write
   STATUS     mandatory
   DESCRIPTION
     "RemoteNumbering Plan Indicator (Npi) indicates the numbering 
      plan used in the remoteDna."
   DEFVAL     { x121 }
::= { mscAppnLcnDcOptionsEntry 3 }

mscAppnLcnDcRemoteDna OBJECT-TYPE
   SYNTAX     DigitString (SIZE (1..15))
   ACCESS     read-write
   STATUS     mandatory
   DESCRIPTION
     "This attribute specifies the Data Network Address (Dna) of the 
      remote. This is the called (destination) DTE address (Dna) to which 
      this direct call will be sent. Initially, the called DTE address 
      attribute must be present, that is, there must be a valid destination 
      address. However, it may be possible in the future to configure the 
      direct call with a mnemonic address, in which case, this attribute 
      will contain a zero-length Dna, and the mnemonic address will be 
      carried as one of the facilities."
::= { mscAppnLcnDcOptionsEntry 4 }

mscAppnLcnDcTransferPriority OBJECT-TYPE
   SYNTAX     INTEGER  {
                 normal(0),
                 high(9),
                 useDnaDefTP(255) }
   ACCESS     read-write
   STATUS     mandatory
   DESCRIPTION
     "This attribute specifies the transfer priority to network for the 
      outgoing calls using this particular LCN. It overRides the 
      defaultTransferPriority provisioned in its associated Dna 
      component.
      
      The transfer priority is a preference specified by an application 
      according to its delay-sensitivity requirement. Frames with high 
      transfer priority are served by the network before the frames with 
      normal priority.
      
      Each transfer priority contains a predetermined setting for trunk 
      queue (interrupting, delay or throughput), and routing metric (delay 
      or throughput). 
      
      When the transfer priority is set at high, the trunk queue is set to 
      high, the routing metric is set to delay.
      
      When the transfer priority is set at normal, the trunk queue is set to 
      normal, the routing metric is set to throughput.
      
      The default of transferPriority is useDnaDefTP. It means using the 
      provisioning value under defaultTransferPriority of its associated 
      Dna for this DLCI."
   DEFVAL     { useDnaDefTP }
::= { mscAppnLcnDcOptionsEntry 9 }

mscAppnLcnDcDiscardPriority OBJECT-TYPE
   SYNTAX     INTEGER  {
                 normal(0),
                 high(1),
                 useDnaDefPriority(3) }
   ACCESS     read-write
   STATUS     mandatory
   DESCRIPTION
     "This attribute specifies the discard priority for outgoing call using 
      this LCN. 
      
      The discard priority has three provisioning values: normal, high, 
      and useDnaDefPriority. Traffic with normal priority are discarded 
      first than the traffic with high priority. The Dna default value 
      (provisioned by outDefaultPriority) is taken if this attribute is set to 
      the value useDnaDefPriority.
      
      The default of discardPriority is useDnaDefPriority."
   DEFVAL     { useDnaDefPriority }
::= { mscAppnLcnDcOptionsEntry 10 }


-- ... Vc()
-- This component defines display of general Vc dynamic attributes

mscAppnLcnVc OBJECT IDENTIFIER ::= { mscAppnLcn 3 }



mscAppnLcnVcRowStatusTable OBJECT-TYPE
   SYNTAX     SEQUENCE OF MscAppnLcnVcRowStatusEntry
   ACCESS     not-accessible
   STATUS     mandatory
   DESCRIPTION
     "This entry controls the addition and deletion of 
      mscAppnLcnVc components."
::= { mscAppnLcnVc 1 }

mscAppnLcnVcRowStatusEntry OBJECT-TYPE
   SYNTAX     MscAppnLcnVcRowStatusEntry
   ACCESS     not-accessible
   STATUS     mandatory
   DESCRIPTION
     "A single entry in the table represents a single 
      mscAppnLcnVc component."
   INDEX {
      mscAppnIndex,
      mscAppnLcnIndex,
      mscAppnLcnVcIndex }
::= { mscAppnLcnVcRowStatusTable 1 }

MscAppnLcnVcRowStatusEntry ::= SEQUENCE {
   mscAppnLcnVcRowStatus
      RowStatus,
   mscAppnLcnVcComponentName
      DisplayString,
   mscAppnLcnVcStorageType
      StorageType,
   mscAppnLcnVcIndex
      NonReplicated }

mscAppnLcnVcRowStatus OBJECT-TYPE
   SYNTAX     RowStatus 
   ACCESS     read-only
   STATUS     mandatory
   DESCRIPTION
     "This variable is used as the basis for SNMP naming of
      mscAppnLcnVc components.
      These components cannot be added nor deleted."
::= { mscAppnLcnVcRowStatusEntry 1 }

mscAppnLcnVcComponentName OBJECT-TYPE
   SYNTAX     DisplayString 
   ACCESS     read-only
   STATUS     mandatory
   DESCRIPTION
     "This variable provides the component's string name for
      use with the ASCII Console Interface"
::= { mscAppnLcnVcRowStatusEntry 2 }

mscAppnLcnVcStorageType OBJECT-TYPE
   SYNTAX     StorageType 
   ACCESS     read-only
   STATUS     mandatory
   DESCRIPTION
     "This variable represents the storage type value for the
      mscAppnLcnVc tables."
::= { mscAppnLcnVcRowStatusEntry 4 }

mscAppnLcnVcIndex OBJECT-TYPE
   SYNTAX     NonReplicated 
   ACCESS     not-accessible
   STATUS     mandatory
   DESCRIPTION
     "This variable represents the index for the mscAppnLcnVc tables."
::= { mscAppnLcnVcRowStatusEntry 10 }

mscAppnLcnVcCadTable OBJECT-TYPE
   SYNTAX     SEQUENCE OF MscAppnLcnVcCadEntry
   ACCESS     not-accessible
   STATUS     mandatory
   DESCRIPTION
     "This group represents operational call data related to General Vc. It 
      can be displayed only for General Vc which is created by 
      application."
::= { mscAppnLcnVc 10 }

mscAppnLcnVcCadEntry OBJECT-TYPE
   SYNTAX     MscAppnLcnVcCadEntry
   ACCESS     not-accessible
   STATUS     mandatory
   DESCRIPTION
     "An entry in the mscAppnLcnVcCadTable."
   INDEX {
      mscAppnIndex,
      mscAppnLcnIndex,
      mscAppnLcnVcIndex }
::= { mscAppnLcnVcCadTable 1 }

MscAppnLcnVcCadEntry ::= SEQUENCE {
   mscAppnLcnVcType
      INTEGER,
   mscAppnLcnVcState
      INTEGER,
   mscAppnLcnVcPreviousState
      INTEGER,
   mscAppnLcnVcDiagnosticCode
      Unsigned32,
   mscAppnLcnVcPreviousDiagnosticCode
      Unsigned32,
   mscAppnLcnVcCalledNpi
      INTEGER,
   mscAppnLcnVcCalledDna
      DigitString,
   mscAppnLcnVcCalledLcn
      Unsigned32,
   mscAppnLcnVcCallingNpi
      INTEGER,
   mscAppnLcnVcCallingDna
      DigitString,
   mscAppnLcnVcCallingLcn
      Unsigned32,
   mscAppnLcnVcAccountingEnabled
      INTEGER,
   mscAppnLcnVcFastSelectCall
      INTEGER,
   mscAppnLcnVcLocalRxPktSize
      INTEGER,
   mscAppnLcnVcLocalTxPktSize
      INTEGER,
   mscAppnLcnVcLocalTxWindowSize
      Unsigned32,
   mscAppnLcnVcLocalRxWindowSize
      Unsigned32,
   mscAppnLcnVcPathReliability
      INTEGER,
   mscAppnLcnVcAccountingEnd
      INTEGER,
   mscAppnLcnVcPriority
      INTEGER,
   mscAppnLcnVcSegmentSize
      Unsigned32,
   mscAppnLcnVcSubnetTxPktSize
      INTEGER,
   mscAppnLcnVcSubnetTxWindowSize
      Unsigned32,
   mscAppnLcnVcSubnetRxPktSize
      INTEGER,
   mscAppnLcnVcSubnetRxWindowSize
      Unsigned32,
   mscAppnLcnVcMaxSubnetPktSize
      Unsigned32,
   mscAppnLcnVcTransferPriorityToNetwork
      INTEGER,
   mscAppnLcnVcTransferPriorityFromNetwork
      INTEGER }

mscAppnLcnVcType OBJECT-TYPE
   SYNTAX     INTEGER  {
                 svc(0),
                 pvc(1) }
   ACCESS     read-only
   STATUS     mandatory
   DESCRIPTION
     "This attribute displays the type of call, pvc or svc. type is provided 
      at provisioning time."
::= { mscAppnLcnVcCadEntry 1 }

mscAppnLcnVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscAppnLcnVcCadEntry 2 }

mscAppnLcnVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscAppnLcnVcCadEntry 3 }

mscAppnLcnVcDiagnosticCode OBJECT-TYPE
   SYNTAX     Unsigned32 (0..255)
   ACCESS     read-only
   STATUS     mandatory
   DESCRIPTION
     "This attribute displays the internal substate of call control. It is used 
      to further refine state of call processing."
::= { mscAppnLcnVcCadEntry 4 }

mscAppnLcnVcPreviousDiagnosticCode OBJECT-TYPE
   SYNTAX     Unsigned32 (0..255)
   ACCESS     read-only
   STATUS     mandatory
   DESCRIPTION
     "This attribute displays the internal substate of call control. It is used 
      to further refine state of call processing."
::= { mscAppnLcnVcCadEntry 5 }

mscAppnLcnVcCalledNpi OBJECT-TYPE
   SYNTAX     INTEGER  {
                 x121(0),
                 e164(1) }
   ACCESS     read-only
   STATUS     mandatory
   DESCRIPTION
     "This attribute displays the Numbering Plan Indicator (NPI) of the 
      called end."
::= { mscAppnLcnVcCadEntry 6 }

mscAppnLcnVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscAppnLcnVcCadEntry 7 }

mscAppnLcnVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscAppnLcnVcCadEntry 8 }

mscAppnLcnVcCallingNpi OBJECT-TYPE
   SYNTAX     INTEGER  {
                 x121(0),
                 e164(1) }
   ACCESS     read-only
   STATUS     mandatory
   DESCRIPTION
     "This attribute displays the Numbering Plan Indicator (NPI) of the 
      calling end."
::= { mscAppnLcnVcCadEntry 9 }

mscAppnLcnVcCallingDna OBJECT-TYPE
   SYNTAX     DigitString (SIZE (1..15))
   ACCESS     read-only
   STATUS     mandatory
   DESCRIPTION
     "This attribute displays the Data Network Address (Dna) of the 
      calling end."
::= { mscAppnLcnVcCadEntry 10 }

mscAppnLcnVcCallingLcn OBJECT-TYPE
   SYNTAX     Unsigned32 (1..65535)
   ACCESS     read-only
   STATUS     mandatory
   DESCRIPTION
     "This attribute displays the Logical Channel Number of the calling 
      end."
::= { mscAppnLcnVcCadEntry 11 }

mscAppnLcnVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscAppnLcnVcCadEntry 12 }

mscAppnLcnVcFastSelectCall OBJECT-TYPE
   SYNTAX     INTEGER  {
                 no(0),
                 yes(1) }
   ACCESS     read-only
   STATUS     mandatory
   DESCRIPTION
     "This attribute displays that this is a fast select call."
::= { mscAppnLcnVcCadEntry 13 }

mscAppnLcnVcLocalRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { mscAppnLcnVcCadEntry 14 }

mscAppnLcnVcLocalTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { mscAppnLcnVcCadEntry 15 }

mscAppnLcnVcLocalTxWindowSize OBJECT-TYPE
   SYNTAX     Unsigned32 (0..127)
   ACCESS     read-only
   STATUS     mandatory
   DESCRIPTION
     "This attribute displays the send window size provided on incoming 
      call packets or the default when a call request packet does not 
      explicitly provide the window size."
::= { mscAppnLcnVcCadEntry 16 }

mscAppnLcnVcLocalRxWindowSize OBJECT-TYPE
   SYNTAX     Unsigned32 (0..127)
   ACCESS     read-only
   STATUS     mandatory
   DESCRIPTION
     "This attribute displays the receive window size provided on 
      incoming call packets or the default when a call request does not 
      explicitly provide the window sizes."
::= { mscAppnLcnVcCadEntry 17 }

mscAppnLcnVcPathReliability OBJECT-TYPE
   SYNTAX     INTEGER  {
                 high(0),
                 normal(1) }
   ACCESS     read-only
   STATUS     mandatory
   DESCRIPTION
     "This attribute displays the path reliability."
::= { mscAppnLcnVcCadEntry 19 }

mscAppnLcnVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscAppnLcnVcCadEntry 20 }

mscAppnLcnVcPriority OBJECT-TYPE
   SYNTAX     INTEGER  {
                 normal(0),
                 high(1) }
   ACCESS     read-only
   STATUS     mandatory
   DESCRIPTION
     "This attribute displays whether the call is a normal or a high 
      priority call."
::= { mscAppnLcnVcCadEntry 21 }

mscAppnLcnVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscAppnLcnVcCadEntry 22 }

mscAppnLcnVcSubnetTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of the data packets 
      on this Vc."
::= { mscAppnLcnVcCadEntry 23 }

mscAppnLcnVcSubnetTxWindowSize OBJECT-TYPE
   SYNTAX     Unsigned32 (0..4096)
   ACCESS     read-only
   STATUS     mandatory
   DESCRIPTION
     "This attribute displays the current send window size of Vc."
::= { mscAppnLcnVcCadEntry 24 }

mscAppnLcnVcSubnetRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of receive packets."
::= { mscAppnLcnVcCadEntry 25 }

mscAppnLcnVcSubnetRxWindowSize OBJECT-TYPE
   SYNTAX     Unsigned32 (0..4096)
   ACCESS     read-only
   STATUS     mandatory
   DESCRIPTION
     "This attribute displays the receive window size provided on 
      incoming call packets and to the default when a call request does 
      not explicitly provide the window sizes."
::= { mscAppnLcnVcCadEntry 26 }

mscAppnLcnVcMaxSubnetPktSize OBJECT-TYPE
   SYNTAX     Unsigned32 (0..4096)
   ACCESS     read-only
   STATUS     mandatory
   DESCRIPTION
     "This attribute displays the maximum packet size allowed on Vc."
::= { mscAppnLcnVcCadEntry 27 }

mscAppnLcnVcTransferPriorityToNetwork OBJECT-TYPE
   SYNTAX     INTEGER  {
                 normal(0),
                 high(9) }
   ACCESS     read-only
   STATUS     mandatory
   DESCRIPTION
     "This attribute displays the priority in which data is transferred to the 
      network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput).
      
      When the transfer priority is set at high, the trunk queue is set to 
      high, the routing metric is set to delay.
      
      When the transfer priority is set at normal, the trunk queue is set to 
      normal, the routing metric is set to throughput."
::= { mscAppnLcnVcCadEntry 28 }

mscAppnLcnVcTransferPriorityFromNetwork OBJECT-TYPE
   SYNTAX     INTEGER  {
                 normal(0),
                 high(9) }
   ACCESS     read-only
   STATUS     mandatory
   DESCRIPTION
     "This attribute displays the priority in which data is transferred from 
      the network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, and the trunk queue is set 
      to high, the routing metric is set to delay.
      
      When the transfer priority is set at normal, the trunk queue is set to 
      normal, and the routing metric is set to throughput."
::= { mscAppnLcnVcCadEntry 29 }

mscAppnLcnVcIntdTable OBJECT-TYPE
   SYNTAX     SEQUENCE OF MscAppnLcnVcIntdEntry
   ACCESS     not-accessible
   STATUS     mandatory
   DESCRIPTION
     "This group defines display of interval data collected by Vc. Data in 
      this group is variable and may depend on time when this display 
      command is issued."
::= { mscAppnLcnVc 11 }

mscAppnLcnVcIntdEntry OBJECT-TYPE
   SYNTAX     MscAppnLcnVcIntdEntry
   ACCESS     not-accessible
   STATUS     mandatory
   DESCRIPTION
     "An entry in the mscAppnLcnVcIntdTable."
   INDEX {
      mscAppnIndex,
      mscAppnLcnIndex,
      mscAppnLcnVcIndex }
::= { mscAppnLcnVcIntdTable 1 }

MscAppnLcnVcIntdEntry ::= SEQUENCE {
   mscAppnLcnVcCallReferenceNumber
      Hex,
   mscAppnLcnVcElapsedTimeTillNow
      Unsigned32,
   mscAppnLcnVcSegmentsRx
      Unsigned32,
   mscAppnLcnVcSegmentsSent
      Unsigned32,
   mscAppnLcnVcStartTime
      EnterpriseDateAndTime }

mscAppnLcnVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscAppnLcnVcIntdEntry 1 }

mscAppnLcnVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscAppnLcnVcIntdEntry 2 }

mscAppnLcnVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscAppnLcnVcIntdEntry 3 }

mscAppnLcnVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscAppnLcnVcIntdEntry 4 }

mscAppnLcnVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscAppnLcnVcIntdEntry 5 }

mscAppnLcnVcStatsTable OBJECT-TYPE
   SYNTAX     SEQUENCE OF MscAppnLcnVcStatsEntry
   ACCESS     not-accessible
   STATUS     mandatory
   DESCRIPTION
     "... Statistics(Stats)
      This group defines general attributes collected by general Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods."
::= { mscAppnLcnVc 12 }

mscAppnLcnVcStatsEntry OBJECT-TYPE
   SYNTAX     MscAppnLcnVcStatsEntry
   ACCESS     not-accessible
   STATUS     mandatory
   DESCRIPTION
     "An entry in the mscAppnLcnVcStatsTable."
   INDEX {
      mscAppnIndex,
      mscAppnLcnIndex,
      mscAppnLcnVcIndex }
::= { mscAppnLcnVcStatsTable 1 }

MscAppnLcnVcStatsEntry ::= SEQUENCE {
   mscAppnLcnVcAckStackingTimeouts
      Unsigned32,
   mscAppnLcnVcOutOfRangeFrmFromSubnet
      Unsigned32,
   mscAppnLcnVcDuplicatesFromSubnet
      Unsigned32,
   mscAppnLcnVcFrmRetryTimeouts
      Unsigned32,
   mscAppnLcnVcPeakRetryQueueSize
      Unsigned32,
   mscAppnLcnVcPeakOoSeqQueueSize
      Unsigned32,
   mscAppnLcnVcPeakOoSeqFrmForwarded
      Unsigned32,
   mscAppnLcnVcPeakStackedAcksRx
      Unsigned32,
   mscAppnLcnVcSubnetRecoveries
      Unsigned32,
   mscAppnLcnVcWindowClosuresToSubnet
      Unsigned32,
   mscAppnLcnVcWindowClosuresFromSubnet
      Unsigned32,
   mscAppnLcnVcWrTriggers
      Unsigned32 }

mscAppnLcnVcAckStackingTimeouts OBJECT-TYPE
   SYNTAX     Unsigned32 (0..5000)
   ACCESS     read-only
   STATUS     mandatory
   DESCRIPTION
     "This attribute counts the number of ack stacking timer expiries.
      It is used as an indicator of the acknowledgment behavior across the 
      subnet when ack stacking is in effect. If it expires often, usually this 
      means end users will experience longer delay.
      The ack stacking timer specifies how long the Vc will wait before 
      finally sending the subnet acknowledgment. if this attribute is set to 
      a value of 0, then the Vc will automatically return acknowledgment 
      packets without delay. If this attribute is set to a value other than 
      zero, then the Vc will wait for this amount of time in an attempt to 
      piggyback the acknowledgment packet on another credit or data 
      packet. If the Vc cannot piggyback the acknowledgment packet 
      within this time, then the packet is returned without piggybacking."
::= { mscAppnLcnVcStatsEntry 1 }

mscAppnLcnVcOutOfRangeFrmFromSubnet OBJECT-TYPE
   SYNTAX     Unsigned32 (0..5000)
   ACCESS     read-only
   STATUS     mandatory
   DESCRIPTION
     "This attribute counts the number of subnet frames discarded due to 
      the sequence number being out of range.
      Two Categories apply for the General Vc
      1) lost Acks (previous Range)
      2) unexpected Packets (next Range)
      Vc internally maintains its own sequence number of packet order 
      and sequencing. Due to packet retransmission, Vc may receive 
      duplicate packets that have the same Vc internal sequence number. 
      Only 1 copy is accepted by the Vc and other copies of the same 
      packets are detected through this count. This attribute can be used to 
      record the frequency of packet retransmission due to Vc and other 
      part of the subnet."
::= { mscAppnLcnVcStatsEntry 2 }

mscAppnLcnVcDuplicatesFromSubnet OBJECT-TYPE
   SYNTAX     Unsigned32 (0..5000)
   ACCESS     read-only
   STATUS     mandatory
   DESCRIPTION
     "This attribute counts the number of subnet packets discarded due to 
      duplication. It is used to detect software error fault or duplication 
      caused by retransmitting."
::= { mscAppnLcnVcStatsEntry 3 }

mscAppnLcnVcFrmRetryTimeouts OBJECT-TYPE
   SYNTAX     Unsigned32 (0..5000)
   ACCESS     read-only
   STATUS     mandatory
   DESCRIPTION
     "This attribute counts the number of frames which have 
      retransmission time-out.
      If packets from Vc into the subnet are discarded by the subnet, the 
      source Vc will not receive any acknowledgment. The retransmission 
      timer then expires and packets will be retransmitted again. Note that 
      the Vc idle probe may be retransmitted and is included in this count. 
      This statistics does not show the distribution of how many times 
      packets are retransmitted (e.g. first retransmission results in 
      successful packet forwarding)."
::= { mscAppnLcnVcStatsEntry 4 }

mscAppnLcnVcPeakRetryQueueSize OBJECT-TYPE
   SYNTAX     Unsigned32 (0..5000)
   ACCESS     read-only
   STATUS     mandatory
   DESCRIPTION
     "This attribute indicates the peak size of the retransmission queue.
      This attribute is used as an indicator of the acknowledgment 
      behavior across the subnet. It records the largest body of 
      unacknowledged packets."
::= { mscAppnLcnVcStatsEntry 5 }

mscAppnLcnVcPeakOoSeqQueueSize OBJECT-TYPE
   SYNTAX     Unsigned32 (0..5000)
   ACCESS     read-only
   STATUS     mandatory
   DESCRIPTION
     "This attribute indicates the peak size of the out of sequence queue.
      This attribute is used as an indicator of the sequencing behavior 
      across the subnet. It records the largest body of out of sequence 
      packets."
::= { mscAppnLcnVcStatsEntry 6 }

mscAppnLcnVcPeakOoSeqFrmForwarded OBJECT-TYPE
   SYNTAX     Unsigned32 (0..5000)
   ACCESS     read-only
   STATUS     mandatory
   DESCRIPTION
     "This attribute indicates the peak size of the sequence packet queue.
      This attribute is used as an indicator of the sequencing behavior 
      across the subnet. It records the largest body of out of sequence 
      packets, which by the receipt of an expected packet have been 
      transformed to expected packets. The number of times this peak is 
      reached is not recorded as it is traffic dependent."
::= { mscAppnLcnVcStatsEntry 7 }

mscAppnLcnVcPeakStackedAcksRx OBJECT-TYPE
   SYNTAX     Unsigned32 (0..5000)
   ACCESS     read-only
   STATUS     mandatory
   DESCRIPTION
     "This attribute indicates the peak size of wait acks.
      This attribute is used as an indicator of the acknowledgment 
      behavior across the subnet. It records the largest collective 
      acknowledgment."
::= { mscAppnLcnVcStatsEntry 8 }

mscAppnLcnVcSubnetRecoveries OBJECT-TYPE
   SYNTAX     Unsigned32 (0..5000)
   ACCESS     read-only
   STATUS     mandatory
   DESCRIPTION
     "This attribute counts the number of successful Vc recovery attempts.
      This attribute is used as an indicator of how many times the Vc path 
      is broken but can be recovered. This attribute is useful to record the 
      number of network path failures."
::= { mscAppnLcnVcStatsEntry 9 }

mscAppnLcnVcWindowClosuresToSubnet OBJECT-TYPE
   SYNTAX     Unsigned32 (0..5000)
   ACCESS     read-only
   STATUS     mandatory
   DESCRIPTION
     "This attribute counts the number of window closures to subnet.
      A packet may have been sent into the subnet but its 
      acknowledgment from the remote Vc has not yet been received. 
      This is a 8 bit sequence number.This number is useful in detecting 
      whether the Vc is sending any packet into the subnet."
::= { mscAppnLcnVcStatsEntry 10 }

mscAppnLcnVcWindowClosuresFromSubnet OBJECT-TYPE
   SYNTAX     Unsigned32 (0..5000)
   ACCESS     read-only
   STATUS     mandatory
   DESCRIPTION
     "This attribute counts the number of window closures from subnet.
      This attribute is useful in detecting whether the Vc is receiving any 
      packet from the subnet."
::= { mscAppnLcnVcStatsEntry 11 }

mscAppnLcnVcWrTriggers OBJECT-TYPE
   SYNTAX     Unsigned32 (0..5000)
   ACCESS     read-only
   STATUS     mandatory
   DESCRIPTION
     "This attribute displays the number of times the Vc stays within the 
      W-R region. The W-R region is a value used to determined the 
      timing of credit transmission. Should the current window size be 
      beneath this value, the credits will be transmitted immediately. 
      Otherwise, they will be transmitted later with actual data. The 
      wrTriggers statistic is therefore used to analyze the flow control and 
      credit mechanism."
::= { mscAppnLcnVcStatsEntry 12 }

-- 
-- *** THIS SUBTREE CURRENTLY NOT IMPLEMENTED ***
-- 

-- Appn/<string> Port/<string>
-- The Port component contains the operational information about a 
-- logical port.

mscAppnPort OBJECT IDENTIFIER ::= { mscAppn 5 }



mscAppnPortRowStatusTable OBJECT-TYPE
   SYNTAX     SEQUENCE OF MscAppnPortRowStatusEntry
   ACCESS     not-accessible
   STATUS     mandatory
   DESCRIPTION
     "*** THIS TABLE CURRENTLY NOT IMPLEMENTED ***

      This entry controls the addition and deletion of 
      mscAppnPort components."
::= { mscAppnPort 1 }

mscAppnPortRowStatusEntry OBJECT-TYPE
   SYNTAX     MscAppnPortRowStatusEntry
   ACCESS     not-accessible
   STATUS     mandatory
   DESCRIPTION
     "A single entry in the table represents a single 
      mscAppnPort component."
   INDEX {
      mscAppnIndex,
      mscAppnPortIndex }
::= { mscAppnPortRowStatusTable 1 }

MscAppnPortRowStatusEntry ::= SEQUENCE {
   mscAppnPortRowStatus
      RowStatus,
   mscAppnPortComponentName
      DisplayString,
   mscAppnPortStorageType
      StorageType,
   mscAppnPortIndex
      AsciiStringIndex }

mscAppnPortRowStatus OBJECT-TYPE
   SYNTAX     RowStatus 
   ACCESS     read-only
   STATUS     mandatory
   DESCRIPTION
     "This variable is used as the basis for SNMP naming of
      mscAppnPort components.
      These components cannot be added nor deleted."
::= { mscAppnPortRowStatusEntry 1 }

mscAppnPortComponentName OBJECT-TYPE
   SYNTAX     DisplayString 
   ACCESS     read-only
   STATUS     mandatory
   DESCRIPTION
     "This variable provides the component's string name for
      use with the ASCII Console Interface"
::= { mscAppnPortRowStatusEntry 2 }

mscAppnPortStorageType OBJECT-TYPE
   SYNTAX     StorageType 
   ACCESS     read-only
   STATUS     mandatory
   DESCRIPTION
     "This variable represents the storage type value for the
      mscAppnPort tables."
::= { mscAppnPortRowStatusEntry 4 }

mscAppnPortIndex OBJECT-TYPE
   SYNTAX     AsciiStringIndex (SIZE (1..8))
   ACCESS     not-accessible
   STATUS     mandatory
   DESCRIPTION
     "This variable represents the index for the mscAppnPort tables."
::= { mscAppnPortRowStatusEntry 10 }

mscAppnPortConfigTable OBJECT-TYPE
   SYNTAX     SEQUENCE OF MscAppnPortConfigEntry
   ACCESS     not-accessible
   STATUS     mandatory
   DESCRIPTION
     "*** THIS TABLE CURRENTLY NOT IMPLEMENTED ***

      Learned attributes of a SNA Port."
::= { mscAppnPort 10 }

mscAppnPortConfigEntry OBJECT-TYPE
   SYNTAX     MscAppnPortConfigEntry
   ACCESS     not-accessible
   STATUS     mandatory
   DESCRIPTION
     "An entry in the mscAppnPortConfigTable."
   INDEX {
      mscAppnIndex,
      mscAppnPortIndex }
::= { mscAppnPortConfigTable 1 }

MscAppnPortConfigEntry ::= SEQUENCE {
   mscAppnPortType
      INTEGER,
   mscAppnPortMaxRxBtuSize
      Unsigned32,
   mscAppnPortMaxTxBtuSize
      Unsigned32,
   mscAppnPortTotLinkActLim
      Unsigned32,
   mscAppnPortInbLinkActLim
      Unsigned32,
   mscAppnPortOutLinkActLim
      Unsigned32,
   mscAppnPortLsRole
      INTEGER,
   mscAppnPortActXidExchLim
      Unsigned32,
   mscAppnPortNonactXidExchLim
      Unsigned32,
   mscAppnPortLsXmitRxCap
      INTEGER,
   mscAppnPortMaxIfrmRxWindow
      Unsigned32,
   mscAppnPortTargetPacingCount
      Unsigned32 }

mscAppnPortType OBJECT-TYPE
   SYNTAX     INTEGER  {
                 nonSwitched(1),
                 switched(2),
                 sharedAccessFacilities(3) }
   ACCESS     read-only
   STATUS     mandatory
   DESCRIPTION
     "This attribute specifies the type of line used by the port. The 
      possible values are: 
      
      nonSwitched - 
      switched -
      sharedAccessFacilities -"
   DEFVAL     { sharedAccessFacilities }
::= { mscAppnPortConfigEntry 1 }

mscAppnPortMaxRxBtuSize OBJECT-TYPE
   SYNTAX     Unsigned32 (0..65535)
   ACCESS     read-only
   STATUS     mandatory
   DESCRIPTION
     "This is the maximum basic transmission unit (BTU) size that can be 
      received. The BTU is the unit of data and control information 
      passed between path control components."
   DEFVAL     { 2048 }
::= { mscAppnPortConfigEntry 2 }

mscAppnPortMaxTxBtuSize OBJECT-TYPE
   SYNTAX     Unsigned32 (0..65535)
   ACCESS     read-only
   STATUS     mandatory
   DESCRIPTION
     "This is the maximum basic transmission unit (BTU) size that can be 
      sent. The BTU is the unit of data and control information passed 
      between path control components."
   DEFVAL     { 2048 }
::= { mscAppnPortConfigEntry 3 }

mscAppnPortTotLinkActLim OBJECT-TYPE
   SYNTAX     Unsigned32 (0..99)
   ACCESS     read-only
   STATUS     mandatory
   DESCRIPTION
     "This is the total link activation limit. This is the maximum number 
      of active adjacent link stations the port will support. This value 
      limits the number of adjacent link stations that can be concurrently 
      connected to the local node through this port. The limit includes 
      adjacent link stations connected by both inbound and outbound link 
      activations. The distinction of inbound or outbound for link 
      activations is used to indicate which node initiated the connection. 
      For inbound link activations, the adjacent link station initiates the 
      connection with the local link station. For outbound link activations, 
      the local node initiates the connection with the adjacent link station.
      
      totLinkActLim must be greater than either inbLinkActLim or 
      outLinkActLim, but it should not greater than the sum of 
      inbLinkActLim and outLinkActLim."
   DEFVAL     { 99 }
::= { mscAppnPortConfigEntry 4 }

mscAppnPortInbLinkActLim OBJECT-TYPE
   SYNTAX     Unsigned32 (0..99)
   ACCESS     read-only
   STATUS     mandatory
   DESCRIPTION
     "This is the inbound link activation limit. This is the maximum 
      number of link stations which can be simultaneously active as a 
      result of connection initiations from adjacent nodes."
   DEFVAL     { 97 }
::= { mscAppnPortConfigEntry 5 }

mscAppnPortOutLinkActLim OBJECT-TYPE
   SYNTAX     Unsigned32 (0..99)
   ACCESS     read-only
   STATUS     mandatory
   DESCRIPTION
     "This is the outbound link activation limit. This is the maximum 
      number of link stations which can be simultaneously active as a 
      result of connection initiations by the local node."
   DEFVAL     { 2 }
::= { mscAppnPortConfigEntry 6 }

mscAppnPortLsRole OBJECT-TYPE
   SYNTAX     INTEGER  {
                 primary(1),
                 secondary(2),
                 negotiable(3) }
   ACCESS     read-only
   STATUS     mandatory
   DESCRIPTION
     "This is the initial role of the port's local link station when 
      communicating with an adjacent link station. The possible options 
      are negotiable, primary and secondary."
   DEFVAL     { negotiable }
::= { mscAppnPortConfigEntry 7 }

mscAppnPortActXidExchLim OBJECT-TYPE
   SYNTAX     Unsigned32 (0..65535)
   ACCESS     read-only
   STATUS     mandatory
   DESCRIPTION
     "This is the exchange limit for activation XIDs."
   DEFVAL     { 9 }
::= { mscAppnPortConfigEntry 8 }

mscAppnPortNonactXidExchLim OBJECT-TYPE
   SYNTAX     Unsigned32 (0..65535)
   ACCESS     read-only
   STATUS     mandatory
   DESCRIPTION
     "This is the exchange limit for non-activation XIDs."
   DEFVAL     { 5 }
::= { mscAppnPortConfigEntry 9 }

mscAppnPortLsXmitRxCap OBJECT-TYPE
   SYNTAX     INTEGER  {
                 twa(0),
                 tws(1) }
   ACCESS     read-only
   STATUS     mandatory
   DESCRIPTION
     "This is Link Station transmit/receive capability. This is either tws 
      (two-way simultaneous (full-duplex)) or twa (two-way alternate 
      (half-duplex))."
   DEFVAL     { tws }
::= { mscAppnPortConfigEntry 10 }

mscAppnPortMaxIfrmRxWindow OBJECT-TYPE
   SYNTAX     Unsigned32 (1..127)
   ACCESS     read-only
   STATUS     mandatory
   DESCRIPTION
     "This is the maximum number of I-frames that can be received by 
      the local link stations before an acknowledgment is sent."
   DEFVAL     { 7 }
::= { mscAppnPortConfigEntry 11 }

mscAppnPortTargetPacingCount OBJECT-TYPE
   SYNTAX     Unsigned32 (0..65535)
   ACCESS     read-only
   STATUS     mandatory
   DESCRIPTION
     "This is the desired pacing window size for BINDs on this 
      transmission group. The number is significant only when fixed 
      BIND pacing is being performed."
   DEFVAL     { 7 }
::= { mscAppnPortConfigEntry 12 }

mscAppnPortOperTable OBJECT-TYPE
   SYNTAX     SEQUENCE OF MscAppnPortOperEntry
   ACCESS     not-accessible
   STATUS     mandatory
   DESCRIPTION
     "*** THIS TABLE CURRENTLY NOT IMPLEMENTED ***

      Operational attributes of a SNA Port."
::= { mscAppnPort 11 }

mscAppnPortOperEntry OBJECT-TYPE
   SYNTAX     MscAppnPortOperEntry
   ACCESS     not-accessible
   STATUS     mandatory
   DESCRIPTION
     "An entry in the mscAppnPortOperTable."
   INDEX {
      mscAppnIndex,
      mscAppnPortIndex }
::= { mscAppnPortOperTable 1 }

MscAppnPortOperEntry ::= SEQUENCE {
   mscAppnPortState
      INTEGER,
   mscAppnPortDlcType
      INTEGER,
   mscAppnPortSimRim
      INTEGER,
   mscAppnPortDefinedLsGoodXids
      PassportCounter64,
   mscAppnPortDefinedLsBadXids
      PassportCounter64,
   mscAppnPortDynLsGoodXids
      PassportCounter64,
   mscAppnPortDynLsBadXids
      PassportCounter64 }

mscAppnPortState OBJECT-TYPE
   SYNTAX     INTEGER  {
                 inactive(1),
                 pendingActive(2),
                 active(3),
                 pendingInactive(4) }
   ACCESS     read-only
   STATUS     mandatory
   DESCRIPTION
     "The attribute represents the current operational state of the port. The 
      value can be any of the following:
      inactive - 
      pendingActive - 
      active - 
      pendingInactive -"
::= { mscAppnPortOperEntry 1 }

mscAppnPortDlcType OBJECT-TYPE
   SYNTAX     INTEGER  {
                 other(1),
                 sdlc(2),
                 tokenRing(6),
                 frameRelay(30),
                 x25(31) }
   ACCESS     read-only
   STATUS     mandatory
   DESCRIPTION
     "Type of the DLC interface used by this port. Possible values are: 
      sdlc - synchronous data link control
      x25 - QLLC logical link control
      tokenRing - IEEE 802.2 logical link control 
      frameRelay - RFC1490 and IEEE 802.2 logical link control
      other - dlc type other than those listed above."
::= { mscAppnPortOperEntry 2 }

mscAppnPortSimRim OBJECT-TYPE
   SYNTAX     INTEGER  {
                 yes(1),
                 no(2) }
   ACCESS     read-only
   STATUS     mandatory
   DESCRIPTION
     "This attribute indicates whether Set Initialization Mode (SIM) and 
      Receive Initialization Mode (RIM) are supported."
::= { mscAppnPortOperEntry 3 }

mscAppnPortDefinedLsGoodXids OBJECT-TYPE
   SYNTAX     PassportCounter64 
   ACCESS     read-only
   STATUS     mandatory
   DESCRIPTION
     "This is the total number of successful XIDs that have been received 
      on all of the defined link stations on this port since the last time this 
      port was started."
::= { mscAppnPortOperEntry 4 }

mscAppnPortDefinedLsBadXids OBJECT-TYPE
   SYNTAX     PassportCounter64 
   ACCESS     read-only
   STATUS     mandatory
   DESCRIPTION
     "This attributes contains the total number of unsuccessful XIDs that 
      have been received on all of the defined link stations on this port 
      since the last time this port was started."
::= { mscAppnPortOperEntry 5 }

mscAppnPortDynLsGoodXids OBJECT-TYPE
   SYNTAX     PassportCounter64 
   ACCESS     read-only
   STATUS     mandatory
   DESCRIPTION
     "This is the total number of successful XIDs that have been received 
      on all of the dynamic link stations on this port since the last time 
      this port was started."
::= { mscAppnPortOperEntry 6 }

mscAppnPortDynLsBadXids OBJECT-TYPE
   SYNTAX     PassportCounter64 
   ACCESS     read-only
   STATUS     mandatory
   DESCRIPTION
     "This is the total number of unsuccessful XIDs that have been 
      received on all of the dynamic link stations on this port since the 
      last time this port was started."
::= { mscAppnPortOperEntry 7 }

mscAppnPortTgCharTable OBJECT-TYPE
   SYNTAX     SEQUENCE OF MscAppnPortTgCharEntry
   ACCESS     not-accessible
   STATUS     mandatory
   DESCRIPTION
     "*** THIS TABLE CURRENTLY NOT IMPLEMENTED ***

      These attributes of the link station are in a group using a common 
      structure. This set provides the TG characteristics of the link 
      through this link station for route selection."
::= { mscAppnPort 12 }

mscAppnPortTgCharEntry OBJECT-TYPE
   SYNTAX     MscAppnPortTgCharEntry
   ACCESS     not-accessible
   STATUS     mandatory
   DESCRIPTION
     "An entry in the mscAppnPortTgCharTable."
   INDEX {
      mscAppnIndex,
      mscAppnPortIndex }
::= { mscAppnPortTgCharTable 1 }

MscAppnPortTgCharEntry ::= SEQUENCE {
   mscAppnPortEffectiveCap
      INTEGER,
   mscAppnPortConnectCost
      INTEGER,
   mscAppnPortByteCost
      INTEGER,
   mscAppnPortSecurity
      INTEGER,
   mscAppnPortPropagationDelay
      INTEGER,
   mscAppnPortUserDefinedParm1
      Unsigned32,
   mscAppnPortUserDefinedParm2
      Unsigned32,
   mscAppnPortUserDefinedParm3
      Unsigned32 }

mscAppnPortEffectiveCap OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 n600Gbps(255) }
   ACCESS     read-only
   STATUS     mandatory
   DESCRIPTION
     "The effective capacity is an integer value that indicates the capacity 
      in kilo bits per second. It is derived from the link bandwidth and the 
      maximum load factor with the range of 0 thru 603,979,776."
::= { mscAppnPortTgCharEntry 1 }

mscAppnPortConnectCost OBJECT-TYPE
   SYNTAX     INTEGER (0..255)
   ACCESS     read-only
   STATUS     mandatory
   DESCRIPTION
     "The cost-per-connect time is a characteristic represented by a 
      single-byte value in the range 0 to 255 that expresses a relative cost 
      of using a transmission group. The units for cost-per-connect time 
      are installation-defined and are typically based on the applicable 
      tariffs of the transmission facility being used by the transmission 
      group. The cost-per-connect time values that a network 
      administrator assigns to the transmission groups in a network 
      should reflect the relative expense of each transmission group as 
      compared to all other transmission groups in the network. A value 
      of 0 means that the cost of connecting over the transmission group 
      is at no additional cost (as in the case of a non-switched facility."
   DEFVAL     { 0 }
::= { mscAppnPortTgCharEntry 2 }

mscAppnPortByteCost OBJECT-TYPE
   SYNTAX     INTEGER (0..255)
   ACCESS     read-only
   STATUS     mandatory
   DESCRIPTION
     "Cost-per-byte is a single byte value in the range 0 to 255 that 
      expresses a relative cost of transmitting a byte over the associated 
      transmission group. The units for cost-per-byte are user-defined. 
      Like cost-per-connect-time, cost-per-byte is network specific and 
      will not be uniform across networks unless assignments are 
      coordinated."
   DEFVAL     { 0 }
::= { mscAppnPortTgCharEntry 3 }

mscAppnPortSecurity OBJECT-TYPE
   SYNTAX     INTEGER  {
                 unKnown(0),
                 nonSecure(1),
                 publicSwitchedNetwork(32),
                 undergroundCable(64),
                 secureConduit(96),
                 guardedConduit(128),
                 encrypted(160),
                 guardedRadiation(192) }
   ACCESS     read-only
   STATUS     mandatory
   DESCRIPTION
     "This static characteristic indicates the level of security protection. 
      The security values are architecturally defined to provide continuity 
      across all networks. Currently, security is encoded as one of the 
      following seven values:
      
      guardedRadiation - guarded conduit containing the transmission 
      medium; protected against physical and radiation tapping.
      encrypted - link level encryption is provided
      unknown - has not been determined 
      guardedConduit - guarded conduit; protected against physical 
      tapping
      secureConduit - secure conduit, not guarded; e.g. pressurized pipe
      undergroundCable - underground cable located in a secure country
      publicSwitchedNetwork - public switched network; secure in the 
      sense that there is no predetermined route that traffic will take
      nonSecure - all else, e.g. satellite-connected, located in a nonsecure 
      country."
   DEFVAL     { nonSecure }
::= { mscAppnPortTgCharEntry 4 }

mscAppnPortPropagationDelay OBJECT-TYPE
   SYNTAX     INTEGER  {
                 minimum(0),
                 negligible(76),
                 terrestrial(113),
                 packetSwitched(145),
                 long(153) }
   ACCESS     read-only
   STATUS     mandatory
   DESCRIPTION
     "The propagation delay is the length of time that it takes for a signal 
      to propagate from one end of the transmission group to the other. 
      Typical values are:
      
      minimum - minimum
      negligible - 400 microsec
      terrestrial - 10 msec
      packetSwitched - 150 msec
      long - 300 msec"
   DEFVAL     { terrestrial }
::= { mscAppnPortTgCharEntry 5 }

mscAppnPortUserDefinedParm1 OBJECT-TYPE
   SYNTAX     Unsigned32 (0..255)
   ACCESS     read-only
   STATUS     mandatory
   DESCRIPTION
     "This is the user defined routing parameter in range 0-255."
   DEFVAL     { 128 }
::= { mscAppnPortTgCharEntry 7 }

mscAppnPortUserDefinedParm2 OBJECT-TYPE
   SYNTAX     Unsigned32 (0..255)
   ACCESS     read-only
   STATUS     mandatory
   DESCRIPTION
     "This is the user defined routing parameter in range 0-255."
   DEFVAL     { 128 }
::= { mscAppnPortTgCharEntry 8 }

mscAppnPortUserDefinedParm3 OBJECT-TYPE
   SYNTAX     Unsigned32 (0..255)
   ACCESS     read-only
   STATUS     mandatory
   DESCRIPTION
     "This is the user defined routing parameter in range 0-255."
   DEFVAL     { 128 }
::= { mscAppnPortTgCharEntry 9 }

-- 
-- *** THIS SUBTREE CURRENTLY NOT IMPLEMENTED ***
-- 

-- Appn/<string> LinkStation/<string>
-- This component contains the operational characteristics of a single 
-- link station with a given link station name. A link station represents 
-- a single data link control connection to an adjacent node and the 
-- instance of Path Control that handles traffic on that logical link. 

mscAppnLs OBJECT IDENTIFIER ::= { mscAppn 6 }



mscAppnLsRowStatusTable OBJECT-TYPE
   SYNTAX     SEQUENCE OF MscAppnLsRowStatusEntry
   ACCESS     not-accessible
   STATUS     mandatory
   DESCRIPTION
     "*** THIS TABLE CURRENTLY NOT IMPLEMENTED ***

      This entry controls the addition and deletion of 
      mscAppnLs components."
::= { mscAppnLs 1 }

mscAppnLsRowStatusEntry OBJECT-TYPE
   SYNTAX     MscAppnLsRowStatusEntry
   ACCESS     not-accessible
   STATUS     mandatory
   DESCRIPTION
     "A single entry in the table represents a single 
      mscAppnLs component."
   INDEX {
      mscAppnIndex,
      mscAppnLsIndex }
::= { mscAppnLsRowStatusTable 1 }

MscAppnLsRowStatusEntry ::= SEQUENCE {
   mscAppnLsRowStatus
      RowStatus,
   mscAppnLsComponentName
      DisplayString,
   mscAppnLsStorageType
      StorageType,
   mscAppnLsIndex
      AsciiStringIndex }

mscAppnLsRowStatus OBJECT-TYPE
   SYNTAX     RowStatus 
   ACCESS     read-only
   STATUS     mandatory
   DESCRIPTION
     "This variable is used as the basis for SNMP naming of
      mscAppnLs components.
      These components cannot be added nor deleted."
::= { mscAppnLsRowStatusEntry 1 }

mscAppnLsComponentName OBJECT-TYPE
   SYNTAX     DisplayString 
   ACCESS     read-only
   STATUS     mandatory
   DESCRIPTION
     "This variable provides the component's string name for
      use with the ASCII Console Interface"
::= { mscAppnLsRowStatusEntry 2 }

mscAppnLsStorageType OBJECT-TYPE
   SYNTAX     StorageType 
   ACCESS     read-only
   STATUS     mandatory
   DESCRIPTION
     "This variable represents the storage type value for the
      mscAppnLs tables."
::= { mscAppnLsRowStatusEntry 4 }

mscAppnLsIndex OBJECT-TYPE
   SYNTAX     AsciiStringIndex (SIZE (1..8))
   ACCESS     not-accessible
   STATUS     mandatory
   DESCRIPTION
     "This variable represents the index for the mscAppnLs tables."
::= { mscAppnLsRowStatusEntry 10 }

mscAppnLsLsVcReferenceTable OBJECT-TYPE
   SYNTAX     SEQUENCE OF MscAppnLsLsVcReferenceEntry
   ACCESS     not-accessible
   STATUS     mandatory
   DESCRIPTION
     "*** THIS TABLE CURRENTLY NOT IMPLEMENTED ***

      This identifies which physical interface is associated with this link 
      station."
::= { mscAppnLs 10 }

mscAppnLsLsVcReferenceEntry OBJECT-TYPE
   SYNTAX     MscAppnLsLsVcReferenceEntry
   ACCESS     not-accessible
   STATUS     mandatory
   DESCRIPTION
     "An entry in the mscAppnLsLsVcReferenceTable."
   INDEX {
      mscAppnIndex,
      mscAppnLsIndex }
::= { mscAppnLsLsVcReferenceTable 1 }

MscAppnLsLsVcReferenceEntry ::= SEQUENCE {
   mscAppnLsName
      RowPointer,
   mscAppnLsSap
      Hex }

mscAppnLsName OBJECT-TYPE
   SYNTAX     RowPointer 
   ACCESS     read-only
   STATUS     mandatory
   DESCRIPTION
     "This string identifies which physical interface the link station is 
      associated with."
::= { mscAppnLsLsVcReferenceEntry 1 }

mscAppnLsSap OBJECT-TYPE
   SYNTAX     Hex (0..252)
   ACCESS     read-only
   STATUS     mandatory
   DESCRIPTION
     "This attribute indicates the SAP number of the device assigned to 
      this link station.  This field is only valid for dlcType of llc2. If the 
      dlcType is not llc2, this field will be 0."
::= { mscAppnLsLsVcReferenceEntry 2 }

mscAppnLsConfigTable OBJECT-TYPE
   SYNTAX     SEQUENCE OF MscAppnLsConfigEntry
   ACCESS     not-accessible
   STATUS     mandatory
   DESCRIPTION
     "*** THIS TABLE CURRENTLY NOT IMPLEMENTED ***

      This group contains the attributes that define the behavior of a SNA 
      link station."
::= { mscAppnLs 11 }

mscAppnLsConfigEntry OBJECT-TYPE
   SYNTAX     MscAppnLsConfigEntry
   ACCESS     not-accessible
   STATUS     mandatory
   DESCRIPTION
     "An entry in the mscAppnLsConfigTable."
   INDEX {
      mscAppnIndex,
      mscAppnLsIndex }
::= { mscAppnLsConfigTable 1 }

MscAppnLsConfigEntry ::= SEQUENCE {
   mscAppnLsPortName
      AsciiString,
   mscAppnLsFeatures
      OCTET STRING,
   mscAppnLsMaxTxBtuSize
      Unsigned32 }

mscAppnLsPortName OBJECT-TYPE
   SYNTAX     AsciiString (SIZE (1..8))
   ACCESS     read-only
   STATUS     mandatory
   DESCRIPTION
     "This attribute contains the name of the port associated with this link 
      station."
::= { mscAppnLsConfigEntry 1 }

mscAppnLsFeatures OBJECT-TYPE
   SYNTAX     OCTET STRING (SIZE (1))
   ACCESS     read-only
   STATUS     mandatory
   DESCRIPTION
     "Various optional features of a link station.
      
      autoActSupp
      
      If present specifies that the link can be activated automatically when 
      required by a session. A link cannot be automatically activated from 
      an independent LU session unless it has been started previously. 
      The link cannot be defined to support CP-CP sessions and to be 
      auto-activatable because this might cause inconsistent network 
      behavior.
      
      
      limitedResource
      
      If present, specifies that this link station is to be deactivated when 
      there are no sessions using the link. Note that link stations on a non-
      switched port cannot be configured as limited resource.
      
      
      backLvlLenEn
      
      If present, specifies that this link is to a back level LEN End Node.
      
      
      cpCpSessSupport
      
      If present, specifies that CP-CP sessions are supported by this link 
      station.

      Description of bits:
      autoActSupp(0)
      limitedResource(1)
      backLvlLenEn(2)
      cpCpSessSupport(3)"
::= { mscAppnLsConfigEntry 4 }

mscAppnLsMaxTxBtuSize OBJECT-TYPE
   SYNTAX     Unsigned32 (0..32767)
   ACCESS     read-only
   STATUS     mandatory
   DESCRIPTION
     "This is the maximum basic transmission unit (BTU) size that can be 
      sent. The BTU is the unit of data and control information passed 
      between path control components."
::= { mscAppnLsConfigEntry 6 }

mscAppnLsOperTable OBJECT-TYPE
   SYNTAX     SEQUENCE OF MscAppnLsOperEntry
   ACCESS     not-accessible
   STATUS     mandatory
   DESCRIPTION
     "*** THIS TABLE CURRENTLY NOT IMPLEMENTED ***

      Operational data of the link station."
::= { mscAppnLs 12 }

mscAppnLsOperEntry OBJECT-TYPE
   SYNTAX     MscAppnLsOperEntry
   ACCESS     not-accessible
   STATUS     mandatory
   DESCRIPTION
     "An entry in the mscAppnLsOperTable."
   INDEX {
      mscAppnIndex,
      mscAppnLsIndex }
::= { mscAppnLsOperTable 1 }

MscAppnLsOperEntry ::= SEQUENCE {
   mscAppnLsDlcType
      INTEGER,
   mscAppnLsLinkStationState
      INTEGER,
   mscAppnLsLinkStationSubState
      INTEGER,
   mscAppnLsActSessCount
      Gauge32,
   mscAppnLsActualCpName
      AsciiString,
   mscAppnLsActualCpType
      INTEGER,
   mscAppnLsDlcName
      AsciiString,
   mscAppnLsDynamicOrDefined
      INTEGER,
   mscAppnLsMigration
      INTEGER,
   mscAppnLsTgNum
      Unsigned32,
   mscAppnLsHprSupport
      INTEGER,
   mscAppnLsAnrLabel
      Hex }

mscAppnLsDlcType OBJECT-TYPE
   SYNTAX     INTEGER  {
                 other(1),
                 sdlc(2),
                 tokenRing(6),
                 llc2(30),
                 x25(31) }
   ACCESS     read-only
   STATUS     mandatory
   DESCRIPTION
     "This attribute indicates the type of data link control that this LS is 
      associated. Possible types are:
      
      sdlc - synchronous data link control
      x25 - QLLC logical link control
      tokenRing - IEEE 802.2 logical link control 
      llc2 - RFC1490 and IEEE 802.2 logical link control.
      other - dlc type other than those listed above."
::= { mscAppnLsOperEntry 1 }

mscAppnLsLinkStationState OBJECT-TYPE
   SYNTAX     INTEGER  {
                 inactive(1),
                 pendingActive(2),
                 active(3),
                 pendingInactive(4) }
   ACCESS     read-only
   STATUS     mandatory
   DESCRIPTION
     "This the current state of the link station. The possible values are:
      inactive - 
      active - 
      pendingActive - 
      pendingInactive -"
::= { mscAppnLsOperEntry 2 }

mscAppnLsLinkStationSubState OBJECT-TYPE
   SYNTAX     INTEGER  {
                 inactive(1),
                 sentReqOpnstn(2),
                 pendXidExch(3),
                 sentActAs(4),
                 sentSentMode(5),
                 active(6),
                 sentDeactAsOrd(7),
                 sentDiscOrd(8),
                 sentDestroyTg(9),
                 sentCreateTg(10),
                 sentConnReq(11),
                 pendRcvConnInd(12),
                 pendSendConnRsp(13),
                 sentConnRsp(14),
                 pendDeact(15) }
   ACCESS     read-only
   STATUS     mandatory
   DESCRIPTION
     "This is the current sub-state of the link station. The possible values 
      are: inactive, sentReqOpnstn, pendXidExch, sentActAs, 
      sendSetMode, active, sentDeactAsOrd, sentDiscOrd, 
      sentDestroyTg, sentCreateTg, sentConnReq,pendRcvConnInd, 
      pendSendConnRsp, sentConnRsp, pendDeact. These are described 
      in the APPN Architecture reference"
::= { mscAppnLsOperEntry 3 }

mscAppnLsActSessCount OBJECT-TYPE
   SYNTAX     Gauge32 (0..65535)
   ACCESS     read-only
   STATUS     mandatory
   DESCRIPTION
     "This is the total number of active sessions (both endpoint and 
      intermediate) using this link."
::= { mscAppnLsOperEntry 4 }

mscAppnLsActualCpName OBJECT-TYPE
   SYNTAX     AsciiString (SIZE (3..17))
   ACCESS     read-only
   STATUS     mandatory
   DESCRIPTION
     "This is the actual network qualified adjacent control point (CP) 
      name as determined from the XID 3 exchange."
::= { mscAppnLsOperEntry 5 }

mscAppnLsActualCpType OBJECT-TYPE
   SYNTAX     INTEGER  {
                 toBeDetermined(0),
                 networkNode(1),
                 endNode(2),
                 lowEntryNode(4) }
   ACCESS     read-only
   STATUS     mandatory
   DESCRIPTION
     "This is the actual type of adjacent node type as determined during 
      contact negotiation. The possible types are:
      endNode 
      lowEntryNode 
      networkNode
      toBeDetermine"
::= { mscAppnLsOperEntry 6 }

mscAppnLsDlcName OBJECT-TYPE
   SYNTAX     AsciiString (SIZE (1..8))
   ACCESS     read-only
   STATUS     mandatory
   DESCRIPTION
     "This is the name of the port group associated with the port through 
      which this link station is attached."
::= { mscAppnLsOperEntry 7 }

mscAppnLsDynamicOrDefined OBJECT-TYPE
   SYNTAX     INTEGER  {
                 dynamic(1),
                 defined(2) }
   ACCESS     read-only
   STATUS     mandatory
   DESCRIPTION
     "This attribute reflects whether the link was created explicitly or 
      dynamically (either in response to a connection request from the 
      adjacent node, or to connect dynamically to another node across a 
      connection network). The possible values are dynamic or defined."
::= { mscAppnLsOperEntry 8 }

mscAppnLsMigration OBJECT-TYPE
   SYNTAX     INTEGER  {
                 yes(1),
                 no(2),
                 unknown(3) }
   ACCESS     read-only
   STATUS     mandatory
   DESCRIPTION
     "This attribute specifies whether the adjacent node is a 
      migration level node, such as a low entry networking or LEN 
      node."
::= { mscAppnLsOperEntry 9 }

mscAppnLsTgNum OBJECT-TYPE
   SYNTAX     Unsigned32 (0..255)
   ACCESS     read-only
   STATUS     mandatory
   DESCRIPTION
     "This is the number associated with the transmission group using this 
      link station. It can be used to distinguish it from other transmission 
      groups to the same adjacent node."
::= { mscAppnLsOperEntry 10 }

mscAppnLsHprSupport OBJECT-TYPE
   SYNTAX     INTEGER  {
                 none(0),
                 anr(1),
                 rtp(2) }
   ACCESS     read-only
   STATUS     mandatory
   DESCRIPTION
     "This is the type of High Performance Routing (HPR) being used on 
      this link station. It is one of anr, rtp or none. The value in this 
      attribute are bounded by the values provisioned on this node and the 
      attached node."
::= { mscAppnLsOperEntry 11 }

mscAppnLsAnrLabel OBJECT-TYPE
   SYNTAX     Hex (0..65535)
   ACCESS     read-only
   STATUS     mandatory
   DESCRIPTION
     "This is the HPR ANR label associated with this link station."
::= { mscAppnLsOperEntry 12 }

mscAppnLsTgCharTable OBJECT-TYPE
   SYNTAX     SEQUENCE OF MscAppnLsTgCharEntry
   ACCESS     not-accessible
   STATUS     mandatory
   DESCRIPTION
     "*** THIS TABLE CURRENTLY NOT IMPLEMENTED ***

      These attributes of the link station are in a group using a common 
      structure. This set provides the TG characteristics of the link 
      through this link station for route selection."
::= { mscAppnLs 13 }

mscAppnLsTgCharEntry OBJECT-TYPE
   SYNTAX     MscAppnLsTgCharEntry
   ACCESS     not-accessible
   STATUS     mandatory
   DESCRIPTION
     "An entry in the mscAppnLsTgCharTable."
   INDEX {
      mscAppnIndex,
      mscAppnLsIndex }
::= { mscAppnLsTgCharTable 1 }

MscAppnLsTgCharEntry ::= SEQUENCE {
   mscAppnLsEffectiveCap
      INTEGER,
   mscAppnLsConnectCost
      INTEGER,
   mscAppnLsByteCost
      INTEGER,
   mscAppnLsSecurity
      INTEGER,
   mscAppnLsPropagationDelay
      INTEGER,
   mscAppnLsUserDefinedParm1
      Unsigned32,
   mscAppnLsUserDefinedParm2
      Unsigned32,
   mscAppnLsUserDefinedParm3
      Unsigned32 }

mscAppnLsEffectiveCap OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 n600Gbps(255) }
   ACCESS     read-only
   STATUS     mandatory
   DESCRIPTION
     "The effective capacity is an integer value that indicates the capacity 
      in kilo bits per second. It is derived from the link bandwidth and the 
      maximum load factor with the range of 0 thru 603,979,776."
::= { mscAppnLsTgCharEntry 1 }

mscAppnLsConnectCost OBJECT-TYPE
   SYNTAX     INTEGER (0..255)
   ACCESS     read-only
   STATUS     mandatory
   DESCRIPTION
     "The cost-per-connect time is a characteristic represented by a 
      single-byte value in the range 0 to 255 that expresses a relative cost 
      of using a transmission group. The units for cost-per-connect time 
      are installation-defined and are typically based on the applicable 
      tariffs of the transmission facility being used by the transmission 
      group. The cost-per-connect time values that a network 
      administrator assigns to the transmission groups in a network 
      should reflect the relative expense of each transmission group as 
      compared to all other transmission groups in the network. A value 
      of 0 means that the cost of connecting over the transmission group 
      is at no additional cost (as in the case of a non-switched facility."
   DEFVAL     { 0 }
::= { mscAppnLsTgCharEntry 2 }

mscAppnLsByteCost OBJECT-TYPE
   SYNTAX     INTEGER (0..255)
   ACCESS     read-only
   STATUS     mandatory
   DESCRIPTION
     "Cost-per-byte is a single byte value in the range 0 to 255 that 
      expresses a relative cost of transmitting a byte over the associated 
      transmission group. The units for cost-per-byte are user-defined. 
      Like cost-per-connect-time, cost-per-byte is network specific and 
      will not be uniform across networks unless assignments are 
      coordinated."
   DEFVAL     { 0 }
::= { mscAppnLsTgCharEntry 3 }

mscAppnLsSecurity OBJECT-TYPE
   SYNTAX     INTEGER  {
                 unKnown(0),
                 nonSecure(1),
                 publicSwitchedNetwork(32),
                 undergroundCable(64),
                 secureConduit(96),
                 guardedConduit(128),
                 encrypted(160),
                 guardedRadiation(192) }
   ACCESS     read-only
   STATUS     mandatory
   DESCRIPTION
     "This static characteristic indicates the level of security protection. 
      The security values are architecturally defined to provide continuity 
      across all networks. Currently, security is encoded as one of the 
      following seven values:
      
      guardedRadiation - guarded conduit containing the transmission 
      medium; protected against physical and radiation tapping.
      encrypted - link level encryption is provided
      unknown - has not been determined 
      guardedConduit - guarded conduit; protected against physical 
      tapping
      secureConduit - secure conduit, not guarded; e.g. pressurized pipe
      undergroundCable - underground cable located in a secure country
      publicSwitchedNetwork - public switched network; secure in the 
      sense that there is no predetermined route that traffic will take
      nonSecure - all else, e.g. satellite-connected, located in a nonsecure 
      country."
   DEFVAL     { nonSecure }
::= { mscAppnLsTgCharEntry 4 }

mscAppnLsPropagationDelay OBJECT-TYPE
   SYNTAX     INTEGER  {
                 minimum(0),
                 negligible(76),
                 terrestrial(113),
                 packetSwitched(145),
                 long(153) }
   ACCESS     read-only
   STATUS     mandatory
   DESCRIPTION
     "The propagation delay is the length of time that it takes for a signal 
      to propagate from one end of the transmission group to the other. 
      Typical values are:
      
      minimum - minimum
      negligible - 400 microsec
      terrestrial - 10 msec
      packetSwitched - 150 msec
      long - 300 msec"
   DEFVAL     { terrestrial }
::= { mscAppnLsTgCharEntry 5 }

mscAppnLsUserDefinedParm1 OBJECT-TYPE
   SYNTAX     Unsigned32 (0..255)
   ACCESS     read-only
   STATUS     mandatory
   DESCRIPTION
     "This is the user defined routing parameter in range 0-255."
   DEFVAL     { 128 }
::= { mscAppnLsTgCharEntry 7 }

mscAppnLsUserDefinedParm2 OBJECT-TYPE
   SYNTAX     Unsigned32 (0..255)
   ACCESS     read-only
   STATUS     mandatory
   DESCRIPTION
     "This is the user defined routing parameter in range 0-255."
   DEFVAL     { 128 }
::= { mscAppnLsTgCharEntry 8 }

mscAppnLsUserDefinedParm3 OBJECT-TYPE
   SYNTAX     Unsigned32 (0..255)
   ACCESS     read-only
   STATUS     mandatory
   DESCRIPTION
     "This is the user defined routing parameter in range 0-255."
   DEFVAL     { 128 }
::= { mscAppnLsTgCharEntry 9 }

mscAppnLsStatsTable OBJECT-TYPE
   SYNTAX     SEQUENCE OF MscAppnLsStatsEntry
   ACCESS     not-accessible
   STATUS     mandatory
   DESCRIPTION
     "*** THIS TABLE CURRENTLY NOT IMPLEMENTED ***

      This group contains the operational statistics of the link station."
::= { mscAppnLs 14 }

mscAppnLsStatsEntry OBJECT-TYPE
   SYNTAX     MscAppnLsStatsEntry
   ACCESS     not-accessible
   STATUS     mandatory
   DESCRIPTION
     "An entry in the mscAppnLsStatsTable."
   INDEX {
      mscAppnIndex,
      mscAppnLsIndex }
::= { mscAppnLsStatsTable 1 }

MscAppnLsStatsEntry ::= SEQUENCE {
   mscAppnLsInXidBytes
      PassportCounter64,
   mscAppnLsInMsgBytes
      PassportCounter64,
   mscAppnLsInXidFrames
      PassportCounter64,
   mscAppnLsInMsgFrames
      PassportCounter64,
   mscAppnLsOutXidBytes
      PassportCounter64,
   mscAppnLsOutMsgBytes
      PassportCounter64,
   mscAppnLsOutXidFrames
      PassportCounter64,
   mscAppnLsOutMsgFrames
      PassportCounter64,
   mscAppnLsInInvalidSnaFrames
      PassportCounter64,
   mscAppnLsInSessionControlFrames
      PassportCounter64,
   mscAppnLsOutSessionControlFrames
      PassportCounter64,
   mscAppnLsEchoResponse
      PassportCounter64,
   mscAppnLsCurrentDelay
      PassportCounter64,
   mscAppnLsMaxDelay
      PassportCounter64,
   mscAppnLsMinDelay
      PassportCounter64,
   mscAppnLsGoodXids
      PassportCounter64,
   mscAppnLsBadXids
      PassportCounter64 }

mscAppnLsInXidBytes OBJECT-TYPE
   SYNTAX     PassportCounter64 
   ACCESS     read-only
   STATUS     mandatory
   DESCRIPTION
     "This attribute counts the total number of XID bytes received on this 
      link station."
::= { mscAppnLsStatsEntry 1 }

mscAppnLsInMsgBytes OBJECT-TYPE
   SYNTAX     PassportCounter64 
   ACCESS     read-only
   STATUS     mandatory
   DESCRIPTION
     "This attribute counts the total number of message (I-frame) bytes 
      received on this link station."
::= { mscAppnLsStatsEntry 2 }

mscAppnLsInXidFrames OBJECT-TYPE
   SYNTAX     PassportCounter64 
   ACCESS     read-only
   STATUS     mandatory
   DESCRIPTION
     "This attribute counts the total number of XID frames received on 
      this link station."
::= { mscAppnLsStatsEntry 3 }

mscAppnLsInMsgFrames OBJECT-TYPE
   SYNTAX     PassportCounter64 
   ACCESS     read-only
   STATUS     mandatory
   DESCRIPTION
     "This attribute counts the total number of message (I-frame) frames 
      received on this link station."
::= { mscAppnLsStatsEntry 4 }

mscAppnLsOutXidBytes OBJECT-TYPE
   SYNTAX     PassportCounter64 
   ACCESS     read-only
   STATUS     mandatory
   DESCRIPTION
     "This attribute counts the total number of XID bytes sent on this link 
      station."
::= { mscAppnLsStatsEntry 5 }

mscAppnLsOutMsgBytes OBJECT-TYPE
   SYNTAX     PassportCounter64 
   ACCESS     read-only
   STATUS     mandatory
   DESCRIPTION
     "This attribute counts the total number of message (I-frame) bytes 
      sent on this link station."
::= { mscAppnLsStatsEntry 6 }

mscAppnLsOutXidFrames OBJECT-TYPE
   SYNTAX     PassportCounter64 
   ACCESS     read-only
   STATUS     mandatory
   DESCRIPTION
     "This attribute counts the total number of XID frames sent on this 
      link station."
::= { mscAppnLsStatsEntry 7 }

mscAppnLsOutMsgFrames OBJECT-TYPE
   SYNTAX     PassportCounter64 
   ACCESS     read-only
   STATUS     mandatory
   DESCRIPTION
     "This attribute counts the total number of message (I-frame) frames 
      sent on this link station."
::= { mscAppnLsStatsEntry 8 }

mscAppnLsInInvalidSnaFrames OBJECT-TYPE
   SYNTAX     PassportCounter64 
   ACCESS     read-only
   STATUS     mandatory
   DESCRIPTION
     "This attribute counts the total number of invalid SNA frames 
      received on this link station."
::= { mscAppnLsStatsEntry 9 }

mscAppnLsInSessionControlFrames OBJECT-TYPE
   SYNTAX     PassportCounter64 
   ACCESS     read-only
   STATUS     mandatory
   DESCRIPTION
     "This attribute counts the total number of session control frames 
      received on this link station."
::= { mscAppnLsStatsEntry 10 }

mscAppnLsOutSessionControlFrames OBJECT-TYPE
   SYNTAX     PassportCounter64 
   ACCESS     read-only
   STATUS     mandatory
   DESCRIPTION
     "This attribute counts the total number of session control frames sent 
      on this link station."
::= { mscAppnLsStatsEntry 11 }

mscAppnLsEchoResponse OBJECT-TYPE
   SYNTAX     PassportCounter64 
   ACCESS     read-only
   STATUS     mandatory
   DESCRIPTION
     "This attribute counts the total number of echo responses returned 
      from the adjacent node. A response should be returned for each test 
      frame sent by this node. Echo requests are sent periodically to 
      gauge the propagation delay to the adjacent node."
::= { mscAppnLsStatsEntry 12 }

mscAppnLsCurrentDelay OBJECT-TYPE
   SYNTAX     PassportCounter64 
   ACCESS     read-only
   STATUS     mandatory
   DESCRIPTION
     "This attribute counts the time (in milliseconds) that it took for the 
      last test signal to be sent and returned from this link station to the 
      adjacent link station."
::= { mscAppnLsStatsEntry 13 }

mscAppnLsMaxDelay OBJECT-TYPE
   SYNTAX     PassportCounter64 
   ACCESS     read-only
   STATUS     mandatory
   DESCRIPTION
     "This is the longest time taken (in milliseconds) for a test signal to be 
      sent and returned from this link station to the adjacent link station."
::= { mscAppnLsStatsEntry 14 }

mscAppnLsMinDelay OBJECT-TYPE
   SYNTAX     PassportCounter64 
   ACCESS     read-only
   STATUS     mandatory
   DESCRIPTION
     "This is the shortest time taken (in milliseconds) for a test signal to 
      be sent and returned from this link station to the adjacent link 
      station."
::= { mscAppnLsStatsEntry 15 }

mscAppnLsGoodXids OBJECT-TYPE
   SYNTAX     PassportCounter64 
   ACCESS     read-only
   STATUS     mandatory
   DESCRIPTION
     "This attribute contains the total number of successful XIDs that 
      have been received on this link station since it was started."
::= { mscAppnLsStatsEntry 17 }

mscAppnLsBadXids OBJECT-TYPE
   SYNTAX     PassportCounter64 
   ACCESS     read-only
   STATUS     mandatory
   DESCRIPTION
     "This attribute contains the total number of unsuccessful XIDs that 
      have been received on this link station since it was started."
::= { mscAppnLsStatsEntry 18 }

-- 
-- *** THIS SUBTREE CURRENTLY NOT IMPLEMENTED ***
-- 

-- Appn/<string> DirectoryEntry/<string>
-- This component represents an entry in the directory cache table. 
-- Entries are added to this table as a result of learning about a logical 
-- unit from adjacent network nodes.
-- The instance value is the name of a logical unit or control point.

mscAppnDirEnt OBJECT IDENTIFIER ::= { mscAppn 7 }



mscAppnDirEntRowStatusTable OBJECT-TYPE
   SYNTAX     SEQUENCE OF MscAppnDirEntRowStatusEntry
   ACCESS     not-accessible
   STATUS     mandatory
   DESCRIPTION
     "*** THIS TABLE CURRENTLY NOT IMPLEMENTED ***

      This entry controls the addition and deletion of 
      mscAppnDirEnt components."
::= { mscAppnDirEnt 1 }

mscAppnDirEntRowStatusEntry OBJECT-TYPE
   SYNTAX     MscAppnDirEntRowStatusEntry
   ACCESS     not-accessible
   STATUS     mandatory
   DESCRIPTION
     "A single entry in the table represents a single 
      mscAppnDirEnt component."
   INDEX {
      mscAppnIndex,
      mscAppnDirEntIndex }
::= { mscAppnDirEntRowStatusTable 1 }

MscAppnDirEntRowStatusEntry ::= SEQUENCE {
   mscAppnDirEntRowStatus
      RowStatus,
   mscAppnDirEntComponentName
      DisplayString,
   mscAppnDirEntStorageType
      StorageType,
   mscAppnDirEntIndex
      AsciiStringIndex }

mscAppnDirEntRowStatus OBJECT-TYPE
   SYNTAX     RowStatus 
   ACCESS     read-only
   STATUS     mandatory
   DESCRIPTION
     "This variable is used as the basis for SNMP naming of
      mscAppnDirEnt components.
      These components cannot be added nor deleted."
::= { mscAppnDirEntRowStatusEntry 1 }

mscAppnDirEntComponentName OBJECT-TYPE
   SYNTAX     DisplayString 
   ACCESS     read-only
   STATUS     mandatory
   DESCRIPTION
     "This variable provides the component's string name for
      use with the ASCII Console Interface"
::= { mscAppnDirEntRowStatusEntry 2 }

mscAppnDirEntStorageType OBJECT-TYPE
   SYNTAX     StorageType 
   ACCESS     read-only
   STATUS     mandatory
   DESCRIPTION
     "This variable represents the storage type value for the
      mscAppnDirEnt tables."
::= { mscAppnDirEntRowStatusEntry 4 }

mscAppnDirEntIndex OBJECT-TYPE
   SYNTAX     AsciiStringIndex (SIZE (1..17))
   ACCESS     not-accessible
   STATUS     mandatory
   DESCRIPTION
     "This variable represents the index for the mscAppnDirEnt tables."
::= { mscAppnDirEntRowStatusEntry 10 }

mscAppnDirEntOperTable OBJECT-TYPE
   SYNTAX     SEQUENCE OF MscAppnDirEntOperEntry
   ACCESS     not-accessible
   STATUS     mandatory
   DESCRIPTION
     "*** THIS TABLE CURRENTLY NOT IMPLEMENTED ***

      This group defines the attributes of the Directory Entry server."
::= { mscAppnDirEnt 10 }

mscAppnDirEntOperEntry OBJECT-TYPE
   SYNTAX     MscAppnDirEntOperEntry
   ACCESS     not-accessible
   STATUS     mandatory
   DESCRIPTION
     "An entry in the mscAppnDirEntOperTable."
   INDEX {
      mscAppnIndex,
      mscAppnDirEntIndex }
::= { mscAppnDirEntOperTable 1 }

MscAppnDirEntOperEntry ::= SEQUENCE {
   mscAppnDirEntServerName
      AsciiString,
   mscAppnDirEntLuOwnerName
      AsciiString,
   mscAppnDirEntLocation
      INTEGER,
   mscAppnDirEntEntryType
      INTEGER,
   mscAppnDirEntWildCard
      INTEGER }

mscAppnDirEntServerName OBJECT-TYPE
   SYNTAX     AsciiString (SIZE (3..17))
   ACCESS     read-only
   STATUS     mandatory
   DESCRIPTION
     "The fully-qualified control point (CP) name of the network node 
      server. For unassociated end node entries, the end node fully-
      qualified name is returned."
::= { mscAppnDirEntOperEntry 1 }

mscAppnDirEntLuOwnerName OBJECT-TYPE
   SYNTAX     AsciiString (SIZE (3..17))
   ACCESS     read-only
   STATUS     mandatory
   DESCRIPTION
     "It is the fully-qualified CP name of the node at which the LU is 
      located. This name is the same as the serving NN name when the 
      LU is located at a network node or an unassociated end node. It is 
      also the same as the fully-qualified LU name when this is the 
      control point LU for this node."
::= { mscAppnDirEntOperEntry 2 }

mscAppnDirEntLocation OBJECT-TYPE
   SYNTAX     INTEGER  {
                 local(0),
                 domain(1),
                 xdomain(2) }
   ACCESS     read-only
   STATUS     mandatory
   DESCRIPTION
     "Specifies the location of the resource. This may be one of the 
      following:
      
      The resource is at the local node.
      The resource belongs to an attached end node.
      The resource is not within the domain of the local node."
::= { mscAppnDirEntOperEntry 3 }

mscAppnDirEntEntryType OBJECT-TYPE
   SYNTAX     INTEGER  {
                 cache(0),
                 register(2),
                 home(3) }
   ACCESS     read-only
   STATUS     mandatory
   DESCRIPTION
     "Specifies whether the type of the directory entry is:
      
      cache - The LU has previously been located by a broadcast search 
      and the location information has been saved.
      home - The LU is in the domain of the local network node and the 
      LU information has been configured at the local node. 
      register - The LU is at an end node that is in the domain of the local 
      network node. Registered entries are registered by the served end 
      node."
::= { mscAppnDirEntOperEntry 4 }

mscAppnDirEntWildCard OBJECT-TYPE
   SYNTAX     INTEGER  {
                 other(1),
                 explicit(2),
                 partialWildcard(3),
                 fullWildcard(4) }
   ACCESS     read-only
   STATUS     mandatory
   DESCRIPTION
     "It indicates the type of wildcard used for the resources used for 
      LEN node."
::= { mscAppnDirEntOperEntry 5 }

-- 
-- *** THIS SUBTREE CURRENTLY NOT IMPLEMENTED ***
-- 

-- Appn/<string> AdjacentNetworkNode/<string> 
-- This dynamic component contains information from the topology 
-- database about a network node (NN) with which the current 
-- network node has a CP-CP session.
-- The instance value is the name of a network node control point

mscAppnAdjNn OBJECT IDENTIFIER ::= { mscAppn 8 }



mscAppnAdjNnRowStatusTable OBJECT-TYPE
   SYNTAX     SEQUENCE OF MscAppnAdjNnRowStatusEntry
   ACCESS     not-accessible
   STATUS     mandatory
   DESCRIPTION
     "*** THIS TABLE CURRENTLY NOT IMPLEMENTED ***

      This entry controls the addition and deletion of 
      mscAppnAdjNn components."
::= { mscAppnAdjNn 1 }

mscAppnAdjNnRowStatusEntry OBJECT-TYPE
   SYNTAX     MscAppnAdjNnRowStatusEntry
   ACCESS     not-accessible
   STATUS     mandatory
   DESCRIPTION
     "A single entry in the table represents a single 
      mscAppnAdjNn component."
   INDEX {
      mscAppnIndex,
      mscAppnAdjNnIndex }
::= { mscAppnAdjNnRowStatusTable 1 }

MscAppnAdjNnRowStatusEntry ::= SEQUENCE {
   mscAppnAdjNnRowStatus
      RowStatus,
   mscAppnAdjNnComponentName
      DisplayString,
   mscAppnAdjNnStorageType
      StorageType,
   mscAppnAdjNnIndex
      AsciiStringIndex }

mscAppnAdjNnRowStatus OBJECT-TYPE
   SYNTAX     RowStatus 
   ACCESS     read-only
   STATUS     mandatory
   DESCRIPTION
     "This variable is used as the basis for SNMP naming of
      mscAppnAdjNn components.
      These components cannot be added nor deleted."
::= { mscAppnAdjNnRowStatusEntry 1 }

mscAppnAdjNnComponentName OBJECT-TYPE
   SYNTAX     DisplayString 
   ACCESS     read-only
   STATUS     mandatory
   DESCRIPTION
     "This variable provides the component's string name for
      use with the ASCII Console Interface"
::= { mscAppnAdjNnRowStatusEntry 2 }

mscAppnAdjNnStorageType OBJECT-TYPE
   SYNTAX     StorageType 
   ACCESS     read-only
   STATUS     mandatory
   DESCRIPTION
     "This variable represents the storage type value for the
      mscAppnAdjNn tables."
::= { mscAppnAdjNnRowStatusEntry 4 }

mscAppnAdjNnIndex OBJECT-TYPE
   SYNTAX     AsciiStringIndex (SIZE (1..17))
   ACCESS     not-accessible
   STATUS     mandatory
   DESCRIPTION
     "This variable represents the index for the mscAppnAdjNn tables."
::= { mscAppnAdjNnRowStatusEntry 10 }

mscAppnAdjNnOperTable OBJECT-TYPE
   SYNTAX     SEQUENCE OF MscAppnAdjNnOperEntry
   ACCESS     not-accessible
   STATUS     mandatory
   DESCRIPTION
     "*** THIS TABLE CURRENTLY NOT IMPLEMENTED ***

      These operational attributes are only available for network nodes 
      which are directly attached to the current node. They are in a 
      separate group."
::= { mscAppnAdjNn 10 }

mscAppnAdjNnOperEntry OBJECT-TYPE
   SYNTAX     MscAppnAdjNnOperEntry
   ACCESS     not-accessible
   STATUS     mandatory
   DESCRIPTION
     "An entry in the mscAppnAdjNnOperTable."
   INDEX {
      mscAppnIndex,
      mscAppnAdjNnIndex }
::= { mscAppnAdjNnOperTable 1 }

MscAppnAdjNnOperEntry ::= SEQUENCE {
   mscAppnAdjNnCpCpSessStatus
      INTEGER,
   mscAppnAdjNnOutOfSeqTdus
      PassportCounter64,
   mscAppnAdjNnLastFrsnSent
      Unsigned32,
   mscAppnAdjNnLastFrsnReceived
      Unsigned32 }

mscAppnAdjNnCpCpSessStatus OBJECT-TYPE
   SYNTAX     INTEGER  {
                 active(1),
                 conLoserActive(2),
                 conWinnerActive(3),
                 inactive(4) }
   ACCESS     read-only
   STATUS     mandatory
   DESCRIPTION
     "Indicates the state of CP-CP sessions between this node and 
      adjacent network and end nodes. Inactive indicates no CP-CP 
      sessions exists between this node and the adjacent node. Active 
      indicates CP-CP sessions are active using both the ConWinner and 
      ConLoser sessions. The session initiated by this node is referred to 
      as the ConWinner session and is used by this node to send to the 
      adjacent node. The ConLoser session is initiated by the adjacent 
      node and is used by this node to receive from the adjacent node."
::= { mscAppnAdjNnOperEntry 1 }

mscAppnAdjNnOutOfSeqTdus OBJECT-TYPE
   SYNTAX     PassportCounter64 
   ACCESS     read-only
   STATUS     mandatory
   DESCRIPTION
     "Number of out of sequence topology database updates (TDU) 
      received from this node."
::= { mscAppnAdjNnOperEntry 2 }

mscAppnAdjNnLastFrsnSent OBJECT-TYPE
   SYNTAX     Unsigned32 (0..4294967295)
   ACCESS     read-only
   STATUS     mandatory
   DESCRIPTION
     "Flow reduction sequence numbers (FRSNs) are associated with 
      Topology Database Updates (TDUs) and are unique only within 
      each APPN network node. A TDU can be associated with multiple 
      APPN resources. This FRSN indicates the last TDU sent to this 
      adjacent node."
::= { mscAppnAdjNnOperEntry 3 }

mscAppnAdjNnLastFrsnReceived OBJECT-TYPE
   SYNTAX     Unsigned32 (0..4294967295)
   ACCESS     read-only
   STATUS     mandatory
   DESCRIPTION
     "Flow reduction sequence numbers (FRSNs) are associated with 
      Topology Database Updates (TDUs) and are unique only within 
      each APPN network node. A TDU can be associated with multiple 
      APPN resources. This FRSN indicates the last TDU received from 
      this adjacent node."
::= { mscAppnAdjNnOperEntry 4 }

-- 
-- *** THIS SUBTREE CURRENTLY NOT IMPLEMENTED ***
-- 

-- Appn/<string> NetworkNode/<string>
-- This dynamic component contains information from the topology 
-- database about a network node (NN) or Virtual Routing Node 
-- (VRN) in the network.
-- The instance value is the name of the node.

mscAppnNn OBJECT IDENTIFIER ::= { mscAppn 9 }



mscAppnNnRowStatusTable OBJECT-TYPE
   SYNTAX     SEQUENCE OF MscAppnNnRowStatusEntry
   ACCESS     not-accessible
   STATUS     mandatory
   DESCRIPTION
     "*** THIS TABLE CURRENTLY NOT IMPLEMENTED ***

      This entry controls the addition and deletion of 
      mscAppnNn components."
::= { mscAppnNn 1 }

mscAppnNnRowStatusEntry OBJECT-TYPE
   SYNTAX     MscAppnNnRowStatusEntry
   ACCESS     not-accessible
   STATUS     mandatory
   DESCRIPTION
     "A single entry in the table represents a single 
      mscAppnNn component."
   INDEX {
      mscAppnIndex,
      mscAppnNnIndex }
::= { mscAppnNnRowStatusTable 1 }

MscAppnNnRowStatusEntry ::= SEQUENCE {
   mscAppnNnRowStatus
      RowStatus,
   mscAppnNnComponentName
      DisplayString,
   mscAppnNnStorageType
      StorageType,
   mscAppnNnIndex
      AsciiStringIndex }

mscAppnNnRowStatus OBJECT-TYPE
   SYNTAX     RowStatus 
   ACCESS     read-only
   STATUS     mandatory
   DESCRIPTION
     "This variable is used as the basis for SNMP naming of
      mscAppnNn components.
      These components cannot be added nor deleted."
::= { mscAppnNnRowStatusEntry 1 }

mscAppnNnComponentName OBJECT-TYPE
   SYNTAX     DisplayString 
   ACCESS     read-only
   STATUS     mandatory
   DESCRIPTION
     "This variable provides the component's string name for
      use with the ASCII Console Interface"
::= { mscAppnNnRowStatusEntry 2 }

mscAppnNnStorageType OBJECT-TYPE
   SYNTAX     StorageType 
   ACCESS     read-only
   STATUS     mandatory
   DESCRIPTION
     "This variable represents the storage type value for the
      mscAppnNn tables."
::= { mscAppnNnRowStatusEntry 4 }

mscAppnNnIndex OBJECT-TYPE
   SYNTAX     AsciiStringIndex (SIZE (1..17))
   ACCESS     not-accessible
   STATUS     mandatory
   DESCRIPTION
     "This variable represents the index for the mscAppnNn tables."
::= { mscAppnNnRowStatusEntry 10 }

mscAppnNnOperTable OBJECT-TYPE
   SYNTAX     SEQUENCE OF MscAppnNnOperEntry
   ACCESS     not-accessible
   STATUS     mandatory
   DESCRIPTION
     "*** THIS TABLE CURRENTLY NOT IMPLEMENTED ***

      Operational attributes of a network node in the topology database."
::= { mscAppnNn 10 }

mscAppnNnOperEntry OBJECT-TYPE
   SYNTAX     MscAppnNnOperEntry
   ACCESS     not-accessible
   STATUS     mandatory
   DESCRIPTION
     "An entry in the mscAppnNnOperTable."
   INDEX {
      mscAppnIndex,
      mscAppnNnIndex }
::= { mscAppnNnOperTable 1 }

MscAppnNnOperEntry ::= SEQUENCE {
   mscAppnNnDaysLeft
      Unsigned32,
   mscAppnNnNodeType
      INTEGER,
   mscAppnNnResourceSequenceNumber
      Unsigned32,
   mscAppnNnRouteAdditionResistance
      INTEGER,
   mscAppnNnStatus
      OCTET STRING,
   mscAppnNnFunctionSupported
      OCTET STRING }

mscAppnNnDaysLeft OBJECT-TYPE
   SYNTAX     Unsigned32 (1..15)
   ACCESS     read-only
   STATUS     mandatory
   DESCRIPTION
     "The number of days before deletion of this node entry from the 
      Topology Database. This is set to zero for the local node entry, 
      which always exists."
::= { mscAppnNnOperEntry 2 }

mscAppnNnNodeType OBJECT-TYPE
   SYNTAX     INTEGER  {
                 toBeDetermined(0),
                 networkNode(1),
                 virtualRoutingNode(3) }
   ACCESS     read-only
   STATUS     mandatory
   DESCRIPTION
     "Type of the APPN node. Possible values are networkNode (nn) and 
      virtualRoutingNode (vrn)."
::= { mscAppnNnOperEntry 3 }

mscAppnNnResourceSequenceNumber OBJECT-TYPE
   SYNTAX     Unsigned32 (0..4294967295)
   ACCESS     read-only
   STATUS     mandatory
   DESCRIPTION
     "Resource sequence number. This is assigned by the network node 
      that owns this resource."
::= { mscAppnNnOperEntry 4 }

mscAppnNnRouteAdditionResistance OBJECT-TYPE
   SYNTAX     INTEGER (0..255)
   ACCESS     read-only
   STATUS     mandatory
   DESCRIPTION
     "Route addition resistance indicates the relative desirability of using 
      this node for intermediate session traffic. This value is used for 
      route computation. The lower the value, the more desirable the node 
      is for intermediate routing."
::= { mscAppnNnOperEntry 5 }

mscAppnNnStatus OBJECT-TYPE
   SYNTAX     OCTET STRING (SIZE (1))
   ACCESS     read-only
   STATUS     mandatory
   DESCRIPTION
     "This attribute specifies the status of the node. This may be one or 
      more of the following:
      
      congested - If present, indicates that this node is congested. This 
      node is not be included in route selection by other nodes when this 
      congestion exists.
      
      irrDepleted - If present, indicates that intermediate session routing 
      resources are depleted. This node is not included in intermediate 
      route selection by other nodes when resources are depleted.
      SNMP APPN MIB = ibmappnNnNodeIsrDepleted
      
      errDepleted - If present, indicates that session endpoint resources 
      are depleted.
      
      quiescing - If present, indicates that the node is quiescing. This 
      node is not included in route selection by other nodes when the 
      node is quiescing.

      Description of bits:
      congested(0)
      irrDepleted(1)
      errDepleted(2)
      quiescing(3)"
::= { mscAppnNnOperEntry 6 }

mscAppnNnFunctionSupported OBJECT-TYPE
   SYNTAX     OCTET STRING (SIZE (1))
   ACCESS     read-only
   STATUS     mandatory
   DESCRIPTION
     "This attribute specifies which functions are supported. This may be 
      one or more of the following:
      
      borderNode - If present, indicates that border node functionality is 
      supported.
      
      centralDirectoryServer -If present, indicates that the node is a 
      central directory.
      
      gateway - If present, indicates that the node provides gateway 
      functions.
      
      isr - If present, indicates that the node supports intermediate session 
      routing.

      Description of bits:
      notused0(0)
      gateway(1)
      centralDirectoryServer(2)
      hpr(3)
      rtp(4)
      isr(5)
      borderNode(6)"
::= { mscAppnNnOperEntry 7 }

-- 
-- *** THIS SUBTREE CURRENTLY NOT IMPLEMENTED ***
-- 

-- Appn/<string> LocalTransmissionGroup/<destination 
-- name<string>>, <fqcpName<string>>, <transmission 
-- group<n>> 
-- This component contains dynamic information about a transmission 
-- group between a network node and an adjacent node. It is part of 
-- the local topology database.

mscAppnLocTg OBJECT IDENTIFIER ::= { mscAppn 10 }



mscAppnLocTgRowStatusTable OBJECT-TYPE
   SYNTAX     SEQUENCE OF MscAppnLocTgRowStatusEntry
   ACCESS     not-accessible
   STATUS     mandatory
   DESCRIPTION
     "*** THIS TABLE CURRENTLY NOT IMPLEMENTED ***

      This entry controls the addition and deletion of 
      mscAppnLocTg components."
::= { mscAppnLocTg 1 }

mscAppnLocTgRowStatusEntry OBJECT-TYPE
   SYNTAX     MscAppnLocTgRowStatusEntry
   ACCESS     not-accessible
   STATUS     mandatory
   DESCRIPTION
     "A single entry in the table represents a single 
      mscAppnLocTg component."
   INDEX {
      mscAppnIndex,
      mscAppnLocTgDestFqcpNameIndex,
      mscAppnLocTgTransmissionGroupIndex }
::= { mscAppnLocTgRowStatusTable 1 }

MscAppnLocTgRowStatusEntry ::= SEQUENCE {
   mscAppnLocTgRowStatus
      RowStatus,
   mscAppnLocTgComponentName
      DisplayString,
   mscAppnLocTgStorageType
      StorageType,
   mscAppnLocTgDestFqcpNameIndex
      AsciiStringIndex,
   mscAppnLocTgTransmissionGroupIndex
      Integer32 }

mscAppnLocTgRowStatus OBJECT-TYPE
   SYNTAX     RowStatus 
   ACCESS     read-only
   STATUS     mandatory
   DESCRIPTION
     "This variable is used as the basis for SNMP naming of
      mscAppnLocTg components.
      These components cannot be added nor deleted."
::= { mscAppnLocTgRowStatusEntry 1 }

mscAppnLocTgComponentName OBJECT-TYPE
   SYNTAX     DisplayString 
   ACCESS     read-only
   STATUS     mandatory
   DESCRIPTION
     "This variable provides the component's string name for
      use with the ASCII Console Interface"
::= { mscAppnLocTgRowStatusEntry 2 }

mscAppnLocTgStorageType OBJECT-TYPE
   SYNTAX     StorageType 
   ACCESS     read-only
   STATUS     mandatory
   DESCRIPTION
     "This variable represents the storage type value for the
      mscAppnLocTg tables."
::= { mscAppnLocTgRowStatusEntry 4 }

mscAppnLocTgDestFqcpNameIndex OBJECT-TYPE
   SYNTAX     AsciiStringIndex (SIZE (3..17))
   ACCESS     not-accessible
   STATUS     mandatory
   DESCRIPTION
     "This variable represents an index for the mscAppnLocTg tables."
::= { mscAppnLocTgRowStatusEntry 10 }

mscAppnLocTgTransmissionGroupIndex OBJECT-TYPE
   SYNTAX     Integer32 (0..255)
   ACCESS     not-accessible
   STATUS     mandatory
   DESCRIPTION
     "This variable represents an index for the mscAppnLocTg tables."
::= { mscAppnLocTgRowStatusEntry 11 }

mscAppnLocTgOperTable OBJECT-TYPE
   SYNTAX     SEQUENCE OF MscAppnLocTgOperEntry
   ACCESS     not-accessible
   STATUS     mandatory
   DESCRIPTION
     "*** THIS TABLE CURRENTLY NOT IMPLEMENTED ***

      Gives the operational status of the local node transmission group."
::= { mscAppnLocTg 10 }

mscAppnLocTgOperEntry OBJECT-TYPE
   SYNTAX     MscAppnLocTgOperEntry
   ACCESS     not-accessible
   STATUS     mandatory
   DESCRIPTION
     "An entry in the mscAppnLocTgOperTable."
   INDEX {
      mscAppnIndex,
      mscAppnLocTgDestFqcpNameIndex,
      mscAppnLocTgTransmissionGroupIndex }
::= { mscAppnLocTgOperTable 1 }

MscAppnLocTgOperEntry ::= SEQUENCE {
   mscAppnLocTgStatus
      OCTET STRING,
   mscAppnLocTgResourceSequenceNumber
      Unsigned32 }

mscAppnLocTgStatus OBJECT-TYPE
   SYNTAX     OCTET STRING (SIZE (1))
   ACCESS     read-only
   STATUS     mandatory
   DESCRIPTION
     "Status of the transmission group can be one of
      operational, CpCpSession or quiescing.

      Description of bits:
      notused0(0)
      notused1(1)
      notused2(2)
      notused3(3)
      cpCpSession(4)
      quiescing(5)
      notused6(6)
      operational(7)"
::= { mscAppnLocTgOperEntry 1 }

mscAppnLocTgResourceSequenceNumber OBJECT-TYPE
   SYNTAX     Unsigned32 (0..4294967295)
   ACCESS     read-only
   STATUS     mandatory
   DESCRIPTION
     "This attribute contains the resource sequence number."
::= { mscAppnLocTgOperEntry 2 }

mscAppnLocTgLinkAddressTable OBJECT-TYPE
   SYNTAX     SEQUENCE OF MscAppnLocTgLinkAddressEntry
   ACCESS     not-accessible
   STATUS     mandatory
   DESCRIPTION
     "*** THIS TABLE CURRENTLY NOT IMPLEMENTED ***

      Contains the attribute for destination address."
::= { mscAppnLocTg 11 }

mscAppnLocTgLinkAddressEntry OBJECT-TYPE
   SYNTAX     MscAppnLocTgLinkAddressEntry
   ACCESS     not-accessible
   STATUS     mandatory
   DESCRIPTION
     "An entry in the mscAppnLocTgLinkAddressTable."
   INDEX {
      mscAppnIndex,
      mscAppnLocTgDestFqcpNameIndex,
      mscAppnLocTgTransmissionGroupIndex }
::= { mscAppnLocTgLinkAddressTable 1 }

MscAppnLocTgLinkAddressEntry ::= SEQUENCE {
   mscAppnLocTgDlcData
      HexString }

mscAppnLocTgDlcData OBJECT-TYPE
   SYNTAX     HexString (SIZE (0..32))
   ACCESS     read-only
   STATUS     mandatory
   DESCRIPTION
     "This attribute contains specific data related to the link connection. 
      
      Token-Ring - contains MAC/SAP
      X.25 Switched - contains dial digits
      X.21 Switched - contains dial digits
      Circuit Switched - contains dial digits
      Frame-Relay - contains DLCI and SAP
      
      The value will be set to zero if the destination node type is not a 
      virtual routing node."
::= { mscAppnLocTgLinkAddressEntry 1 }

mscAppnLocTgTgCharTable OBJECT-TYPE
   SYNTAX     SEQUENCE OF MscAppnLocTgTgCharEntry
   ACCESS     not-accessible
   STATUS     mandatory
   DESCRIPTION
     "*** THIS TABLE CURRENTLY NOT IMPLEMENTED ***

      These attributes of the link station are in a group using a common 
      structure. This set provides the TG characteristics of the link 
      through this link station for route selection."
::= { mscAppnLocTg 12 }

mscAppnLocTgTgCharEntry OBJECT-TYPE
   SYNTAX     MscAppnLocTgTgCharEntry
   ACCESS     not-accessible
   STATUS     mandatory
   DESCRIPTION
     "An entry in the mscAppnLocTgTgCharTable."
   INDEX {
      mscAppnIndex,
      mscAppnLocTgDestFqcpNameIndex,
      mscAppnLocTgTransmissionGroupIndex }
::= { mscAppnLocTgTgCharTable 1 }

MscAppnLocTgTgCharEntry ::= SEQUENCE {
   mscAppnLocTgEffectiveCap
      INTEGER,
   mscAppnLocTgConnectCost
      INTEGER,
   mscAppnLocTgByteCost
      INTEGER,
   mscAppnLocTgSecurity
      INTEGER,
   mscAppnLocTgPropagationDelay
      INTEGER,
   mscAppnLocTgUserDefinedParm1
      Unsigned32,
   mscAppnLocTgUserDefinedParm2
      Unsigned32,
   mscAppnLocTgUserDefinedParm3
      Unsigned32 }

mscAppnLocTgEffectiveCap OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 n600Gbps(255) }
   ACCESS     read-only
   STATUS     mandatory
   DESCRIPTION
     "The effective capacity is an integer value that indicates the capacity 
      in kilo bits per second. It is derived from the link bandwidth and the 
      maximum load factor with the range of 0 thru 603,979,776."
::= { mscAppnLocTgTgCharEntry 1 }

mscAppnLocTgConnectCost OBJECT-TYPE
   SYNTAX     INTEGER (0..255)
   ACCESS     read-only
   STATUS     mandatory
   DESCRIPTION
     "The cost-per-connect time is a characteristic represented by a 
      single-byte value in the range 0 to 255 that expresses a relative cost 
      of using a transmission group. The units for cost-per-connect time 
      are installation-defined and are typically based on the applicable 
      tariffs of the transmission facility being used by the transmission 
      group. The cost-per-connect time values that a network 
      administrator assigns to the transmission groups in a network 
      should reflect the relative expense of each transmission group as 
      compared to all other transmission groups in the network. A value 
      of 0 means that the cost of connecting over the transmission group 
      is at no additional cost (as in the case of a non-switched facility."
   DEFVAL     { 0 }
::= { mscAppnLocTgTgCharEntry 2 }

mscAppnLocTgByteCost OBJECT-TYPE
   SYNTAX     INTEGER (0..255)
   ACCESS     read-only
   STATUS     mandatory
   DESCRIPTION
     "Cost-per-byte is a single byte value in the range 0 to 255 that 
      expresses a relative cost of transmitting a byte over the associated 
      transmission group. The units for cost-per-byte are user-defined. 
      Like cost-per-connect-time, cost-per-byte is network specific and 
      will not be uniform across networks unless assignments are 
      coordinated."
   DEFVAL     { 0 }
::= { mscAppnLocTgTgCharEntry 3 }

mscAppnLocTgSecurity OBJECT-TYPE
   SYNTAX     INTEGER  {
                 unKnown(0),
                 nonSecure(1),
                 publicSwitchedNetwork(32),
                 undergroundCable(64),
                 secureConduit(96),
                 guardedConduit(128),
                 encrypted(160),
                 guardedRadiation(192) }
   ACCESS     read-only
   STATUS     mandatory
   DESCRIPTION
     "This static characteristic indicates the level of security protection. 
      The security values are architecturally defined to provide continuity 
      across all networks. Currently, security is encoded as one of the 
      following seven values:
      
      guardedRadiation - guarded conduit containing the transmission 
      medium; protected against physical and radiation tapping.
      encrypted - link level encryption is provided
      unknown - has not been determined 
      guardedConduit - guarded conduit; protected against physical 
      tapping
      secureConduit - secure conduit, not guarded; e.g. pressurized pipe
      undergroundCable - underground cable located in a secure country
      publicSwitchedNetwork - public switched network; secure in the 
      sense that there is no predetermined route that traffic will take
      nonSecure - all else, e.g. satellite-connected, located in a nonsecure 
      country."
   DEFVAL     { nonSecure }
::= { mscAppnLocTgTgCharEntry 4 }

mscAppnLocTgPropagationDelay OBJECT-TYPE
   SYNTAX     INTEGER  {
                 minimum(0),
                 negligible(76),
                 terrestrial(113),
                 packetSwitched(145),
                 long(153) }
   ACCESS     read-only
   STATUS     mandatory
   DESCRIPTION
     "The propagation delay is the length of time that it takes for a signal 
      to propagate from one end of the transmission group to the other. 
      Typical values are:
      
      minimum - minimum
      negligible - 400 microsec
      terrestrial - 10 msec
      packetSwitched - 150 msec
      long - 300 msec"
   DEFVAL     { terrestrial }
::= { mscAppnLocTgTgCharEntry 5 }

mscAppnLocTgUserDefinedParm1 OBJECT-TYPE
   SYNTAX     Unsigned32 (0..255)
   ACCESS     read-only
   STATUS     mandatory
   DESCRIPTION
     "This is the user defined routing parameter in range 0-255."
   DEFVAL     { 128 }
::= { mscAppnLocTgTgCharEntry 7 }

mscAppnLocTgUserDefinedParm2 OBJECT-TYPE
   SYNTAX     Unsigned32 (0..255)
   ACCESS     read-only
   STATUS     mandatory
   DESCRIPTION
     "This is the user defined routing parameter in range 0-255."
   DEFVAL     { 128 }
::= { mscAppnLocTgTgCharEntry 8 }

mscAppnLocTgUserDefinedParm3 OBJECT-TYPE
   SYNTAX     Unsigned32 (0..255)
   ACCESS     read-only
   STATUS     mandatory
   DESCRIPTION
     "This is the user defined routing parameter in range 0-255."
   DEFVAL     { 128 }
::= { mscAppnLocTgTgCharEntry 9 }

-- 
-- *** THIS SUBTREE CURRENTLY NOT IMPLEMENTED ***
-- 

-- Appn/<string> IsrSession/<fqcpName<string>>,<pcid<n>>
-- This is a dynamic component which contains information about a 
-- specific Intermediate Session Routing session passing through this 
-- node. 
-- The instance value is the fully qualified procedure correlation 
-- identifier of the session. This consists of the name of the control 
-- point which initiated the session plus an 8 byte unique identifier 
-- assigned by that control point. The fully qualified PCID uniquely 
-- identifies this session on all nodes through which it passes.

mscAppnIsrSess OBJECT IDENTIFIER ::= { mscAppn 11 }



mscAppnIsrSessRowStatusTable OBJECT-TYPE
   SYNTAX     SEQUENCE OF MscAppnIsrSessRowStatusEntry
   ACCESS     not-accessible
   STATUS     mandatory
   DESCRIPTION
     "*** THIS TABLE CURRENTLY NOT IMPLEMENTED ***

      This entry controls the addition and deletion of 
      mscAppnIsrSess components."
::= { mscAppnIsrSess 1 }

mscAppnIsrSessRowStatusEntry OBJECT-TYPE
   SYNTAX     MscAppnIsrSessRowStatusEntry
   ACCESS     not-accessible
   STATUS     mandatory
   DESCRIPTION
     "A single entry in the table represents a single 
      mscAppnIsrSess component."
   INDEX {
      mscAppnIndex,
      mscAppnIsrSessFqcpNameIndex,
      mscAppnIsrSessProcedureCorrelationIdIndex }
::= { mscAppnIsrSessRowStatusTable 1 }

MscAppnIsrSessRowStatusEntry ::= SEQUENCE {
   mscAppnIsrSessRowStatus
      RowStatus,
   mscAppnIsrSessComponentName
      DisplayString,
   mscAppnIsrSessStorageType
      StorageType,
   mscAppnIsrSessFqcpNameIndex
      AsciiStringIndex,
   mscAppnIsrSessProcedureCorrelationIdIndex
      HexString }

mscAppnIsrSessRowStatus OBJECT-TYPE
   SYNTAX     RowStatus 
   ACCESS     read-only
   STATUS     mandatory
   DESCRIPTION
     "This variable is used as the basis for SNMP naming of
      mscAppnIsrSess components.
      These components cannot be added nor deleted."
::= { mscAppnIsrSessRowStatusEntry 1 }

mscAppnIsrSessComponentName OBJECT-TYPE
   SYNTAX     DisplayString 
   ACCESS     read-only
   STATUS     mandatory
   DESCRIPTION
     "This variable provides the component's string name for
      use with the ASCII Console Interface"
::= { mscAppnIsrSessRowStatusEntry 2 }

mscAppnIsrSessStorageType OBJECT-TYPE
   SYNTAX     StorageType 
   ACCESS     read-only
   STATUS     mandatory
   DESCRIPTION
     "This variable represents the storage type value for the
      mscAppnIsrSess tables."
::= { mscAppnIsrSessRowStatusEntry 4 }

mscAppnIsrSessFqcpNameIndex OBJECT-TYPE
   SYNTAX     AsciiStringIndex (SIZE (3..17))
   ACCESS     not-accessible
   STATUS     mandatory
   DESCRIPTION
     "This variable represents an index for the mscAppnIsrSess tables."
::= { mscAppnIsrSessRowStatusEntry 10 }

mscAppnIsrSessProcedureCorrelationIdIndex OBJECT-TYPE
   SYNTAX     HexString (SIZE (8))
   ACCESS     not-accessible
   STATUS     mandatory
   DESCRIPTION
     "This variable represents an index for the mscAppnIsrSess tables."
::= { mscAppnIsrSessRowStatusEntry 11 }

mscAppnIsrSessOperTable OBJECT-TYPE
   SYNTAX     SEQUENCE OF MscAppnIsrSessOperEntry
   ACCESS     not-accessible
   STATUS     mandatory
   DESCRIPTION
     "*** THIS TABLE CURRENTLY NOT IMPLEMENTED ***

      This component contains dynamic information about an 
      intermediate session for which the network node is providing transit 
      routing."
::= { mscAppnIsrSess 10 }

mscAppnIsrSessOperEntry OBJECT-TYPE
   SYNTAX     MscAppnIsrSessOperEntry
   ACCESS     not-accessible
   STATUS     mandatory
   DESCRIPTION
     "An entry in the mscAppnIsrSessOperTable."
   INDEX {
      mscAppnIndex,
      mscAppnIsrSessFqcpNameIndex,
      mscAppnIsrSessProcedureCorrelationIdIndex }
::= { mscAppnIsrSessOperTable 1 }

MscAppnIsrSessOperEntry ::= SEQUENCE {
   mscAppnIsrSessTransmissionPriority
      INTEGER,
   mscAppnIsrSessCosName
      AsciiString,
   mscAppnIsrSessLimitedResource
      INTEGER }

mscAppnIsrSessTransmissionPriority OBJECT-TYPE
   SYNTAX     INTEGER  {
                 low(1),
                 medium(2),
                 high(3),
                 network(4) }
   ACCESS     read-only
   STATUS     mandatory
   DESCRIPTION
     "This attribute contains the transmission priority. This is one of low, 
      medium, high or network."
::= { mscAppnIsrSessOperEntry 1 }

mscAppnIsrSessCosName OBJECT-TYPE
   SYNTAX     AsciiString (SIZE (1..8))
   ACCESS     read-only
   STATUS     mandatory
   DESCRIPTION
     "This is the class of service used to select the route. Class of service 
      (COS) is a designation of the transport network characteristics, such 
      as route security, transmission priority, and bandwidth, needed for a 
      particular session. The class of service is derived from the mode 
      name specified by the initiator of the session."
::= { mscAppnIsrSessOperEntry 2 }

mscAppnIsrSessLimitedResource OBJECT-TYPE
   SYNTAX     INTEGER  {
                 yes(1),
                 no(2) }
   ACCESS     read-only
   STATUS     mandatory
   DESCRIPTION
     "This attribute specifies whether the session uses a limited resource 
      link. A limited resource link remains active only when being used 
      and is deactivated when session traffic ceases."
::= { mscAppnIsrSessOperEntry 3 }

-- 
-- *** THIS SUBTREE CURRENTLY NOT IMPLEMENTED ***
-- 

-- Appn/<string> IsrSession/((fqcpName<string>),(pcid/n) PriStats
-- This is a dynamic component which contains statistics and counters 
-- for the primary portion of an ISR session.

mscAppnIsrSessPriStats OBJECT IDENTIFIER ::= { mscAppnIsrSess 100 }



mscAppnIsrSessPriStatsRowStatusTable OBJECT-TYPE
   SYNTAX     SEQUENCE OF MscAppnIsrSessPriStatsRowStatusEntry
   ACCESS     not-accessible
   STATUS     mandatory
   DESCRIPTION
     "*** THIS TABLE CURRENTLY NOT IMPLEMENTED ***

      This entry controls the addition and deletion of 
      mscAppnIsrSessPriStats components."
::= { mscAppnIsrSessPriStats 1 }

mscAppnIsrSessPriStatsRowStatusEntry OBJECT-TYPE
   SYNTAX     MscAppnIsrSessPriStatsRowStatusEntry
   ACCESS     not-accessible
   STATUS     mandatory
   DESCRIPTION
     "A single entry in the table represents a single 
      mscAppnIsrSessPriStats component."
   INDEX {
      mscAppnIndex,
      mscAppnIsrSessFqcpNameIndex,
      mscAppnIsrSessProcedureCorrelationIdIndex,
      mscAppnIsrSessPriStatsIndex }
::= { mscAppnIsrSessPriStatsRowStatusTable 1 }

MscAppnIsrSessPriStatsRowStatusEntry ::= SEQUENCE {
   mscAppnIsrSessPriStatsRowStatus
      RowStatus,
   mscAppnIsrSessPriStatsComponentName
      DisplayString,
   mscAppnIsrSessPriStatsStorageType
      StorageType,
   mscAppnIsrSessPriStatsIndex
      NonReplicated }

mscAppnIsrSessPriStatsRowStatus OBJECT-TYPE
   SYNTAX     RowStatus 
   ACCESS     read-only
   STATUS     mandatory
   DESCRIPTION
     "This variable is used as the basis for SNMP naming of
      mscAppnIsrSessPriStats components.
      These components cannot be added nor deleted."
::= { mscAppnIsrSessPriStatsRowStatusEntry 1 }

mscAppnIsrSessPriStatsComponentName OBJECT-TYPE
   SYNTAX     DisplayString 
   ACCESS     read-only
   STATUS     mandatory
   DESCRIPTION
     "This variable provides the component's string name for
      use with the ASCII Console Interface"
::= { mscAppnIsrSessPriStatsRowStatusEntry 2 }

mscAppnIsrSessPriStatsStorageType OBJECT-TYPE
   SYNTAX     StorageType 
   ACCESS     read-only
   STATUS     mandatory
   DESCRIPTION
     "This variable represents the storage type value for the
      mscAppnIsrSessPriStats tables."
::= { mscAppnIsrSessPriStatsRowStatusEntry 4 }

mscAppnIsrSessPriStatsIndex OBJECT-TYPE
   SYNTAX     NonReplicated 
   ACCESS     not-accessible
   STATUS     mandatory
   DESCRIPTION
     "This variable represents the index for the mscAppnIsrSessPriStats tables."
::= { mscAppnIsrSessPriStatsRowStatusEntry 10 }

mscAppnIsrSessPriStatsStatsTable OBJECT-TYPE
   SYNTAX     SEQUENCE OF MscAppnIsrSessPriStatsStatsEntry
   ACCESS     not-accessible
   STATUS     mandatory
   DESCRIPTION
     "*** THIS TABLE CURRENTLY NOT IMPLEMENTED ***

      This component contains counters and statistics for a session."
::= { mscAppnIsrSessPriStats 10 }

mscAppnIsrSessPriStatsStatsEntry OBJECT-TYPE
   SYNTAX     MscAppnIsrSessPriStatsStatsEntry
   ACCESS     not-accessible
   STATUS     mandatory
   DESCRIPTION
     "An entry in the mscAppnIsrSessPriStatsStatsTable."
   INDEX {
      mscAppnIndex,
      mscAppnIsrSessFqcpNameIndex,
      mscAppnIsrSessProcedureCorrelationIdIndex,
      mscAppnIsrSessPriStatsIndex }
::= { mscAppnIsrSessPriStatsStatsTable 1 }

MscAppnIsrSessPriStatsStatsEntry ::= SEQUENCE {
   mscAppnIsrSessPriStatsRxRuSize
      Unsigned32,
   mscAppnIsrSessPriStatsMaxTxBtuSize
      Unsigned32,
   mscAppnIsrSessPriStatsMaxRxBtuSize
      Unsigned32,
   mscAppnIsrSessPriStatsMaxTxPacWin
      INTEGER,
   mscAppnIsrSessPriStatsCurTxPacWin
      INTEGER,
   mscAppnIsrSessPriStatsMaxRxPacWin
      INTEGER,
   mscAppnIsrSessPriStatsCurRxPacWin
      INTEGER,
   mscAppnIsrSessPriStatsTxDataframes
      PassportCounter64,
   mscAppnIsrSessPriStatsTxFmdFrames
      PassportCounter64,
   mscAppnIsrSessPriStatsTxDataBytes
      PassportCounter64,
   mscAppnIsrSessPriStatsRxDataFrames
      PassportCounter64,
   mscAppnIsrSessPriStatsRxFmdFrames
      PassportCounter64,
   mscAppnIsrSessPriStatsRxDataBytes
      PassportCounter64,
   mscAppnIsrSessPriStatsSidh
      Hex,
   mscAppnIsrSessPriStatsSidl
      Hex,
   mscAppnIsrSessPriStatsOdai
      INTEGER,
   mscAppnIsrSessPriStatsLsName
      AsciiString }

mscAppnIsrSessPriStatsRxRuSize OBJECT-TYPE
   SYNTAX     Unsigned32 (0..65535)
   ACCESS     read-only
   STATUS     mandatory
   DESCRIPTION
     "This is the maximum request unit (RU) size that can be used on the 
      session."
::= { mscAppnIsrSessPriStatsStatsEntry 1 }

mscAppnIsrSessPriStatsMaxTxBtuSize OBJECT-TYPE
   SYNTAX     Unsigned32 (0..65535)
   ACCESS     read-only
   STATUS     mandatory
   DESCRIPTION
     "This is the maximum BTU size (length of the information field in a 
      frame) that can be sent on the session."
::= { mscAppnIsrSessPriStatsStatsEntry 2 }

mscAppnIsrSessPriStatsMaxRxBtuSize OBJECT-TYPE
   SYNTAX     Unsigned32 (0..65535)
   ACCESS     read-only
   STATUS     mandatory
   DESCRIPTION
     "This is the maximum BTU size (length of the information field in a 
      frame) that can be received on the session."
::= { mscAppnIsrSessPriStatsStatsEntry 3 }

mscAppnIsrSessPriStatsMaxTxPacWin OBJECT-TYPE
   SYNTAX     INTEGER (0..32767)
   ACCESS     read-only
   STATUS     mandatory
   DESCRIPTION
     "This is the maximum size of the send pacing window on the  
      session."
::= { mscAppnIsrSessPriStatsStatsEntry 4 }

mscAppnIsrSessPriStatsCurTxPacWin OBJECT-TYPE
   SYNTAX     INTEGER (0..32767)
   ACCESS     read-only
   STATUS     mandatory
   DESCRIPTION
     "This is the current size of the send pacing window on the session."
::= { mscAppnIsrSessPriStatsStatsEntry 5 }

mscAppnIsrSessPriStatsMaxRxPacWin OBJECT-TYPE
   SYNTAX     INTEGER (0..32767)
   ACCESS     read-only
   STATUS     mandatory
   DESCRIPTION
     "This is the maximum size of the receive pacing window on the 
      session."
::= { mscAppnIsrSessPriStatsStatsEntry 6 }

mscAppnIsrSessPriStatsCurRxPacWin OBJECT-TYPE
   SYNTAX     INTEGER (0..32767)
   ACCESS     read-only
   STATUS     mandatory
   DESCRIPTION
     "This is the current size of the receive pacing window on the  
      session."
::= { mscAppnIsrSessPriStatsStatsEntry 7 }

mscAppnIsrSessPriStatsTxDataframes OBJECT-TYPE
   SYNTAX     PassportCounter64 
   ACCESS     read-only
   STATUS     mandatory
   DESCRIPTION
     "This attribute counts the number of normal flow data frames sent 
      on the session, the counter wraps to zero."
::= { mscAppnIsrSessPriStatsStatsEntry 8 }

mscAppnIsrSessPriStatsTxFmdFrames OBJECT-TYPE
   SYNTAX     PassportCounter64 
   ACCESS     read-only
   STATUS     mandatory
   DESCRIPTION
     "This attribute counts the number of FMD data frames sent on the 
      session, the counter wraps to zero."
::= { mscAppnIsrSessPriStatsStatsEntry 9 }

mscAppnIsrSessPriStatsTxDataBytes OBJECT-TYPE
   SYNTAX     PassportCounter64 
   ACCESS     read-only
   STATUS     mandatory
   DESCRIPTION
     "This is the number of normal flow data bytes sent on the session, 
      the counter wraps to zero."
::= { mscAppnIsrSessPriStatsStatsEntry 10 }

mscAppnIsrSessPriStatsRxDataFrames OBJECT-TYPE
   SYNTAX     PassportCounter64 
   ACCESS     read-only
   STATUS     mandatory
   DESCRIPTION
     "This is the number of normal flow data frames received on the 
      session, the counter wraps to zero."
::= { mscAppnIsrSessPriStatsStatsEntry 11 }

mscAppnIsrSessPriStatsRxFmdFrames OBJECT-TYPE
   SYNTAX     PassportCounter64 
   ACCESS     read-only
   STATUS     mandatory
   DESCRIPTION
     "This attribute counts the number of FMD data frames received on 
      the session, the counter wraps to zero."
::= { mscAppnIsrSessPriStatsStatsEntry 12 }

mscAppnIsrSessPriStatsRxDataBytes OBJECT-TYPE
   SYNTAX     PassportCounter64 
   ACCESS     read-only
   STATUS     mandatory
   DESCRIPTION
     "This is the number of normal flow data bytes received on the 
      session, the counter wraps to zero."
::= { mscAppnIsrSessPriStatsStatsEntry 13 }

mscAppnIsrSessPriStatsSidh OBJECT-TYPE
   SYNTAX     Hex (0..255)
   ACCESS     read-only
   STATUS     mandatory
   DESCRIPTION
     "This attribute contains the session identifier high byte on the 
      session."
::= { mscAppnIsrSessPriStatsStatsEntry 14 }

mscAppnIsrSessPriStatsSidl OBJECT-TYPE
   SYNTAX     Hex (0..255)
   ACCESS     read-only
   STATUS     mandatory
   DESCRIPTION
     "This attribute contains the session ID low byte on the SSCP session."
::= { mscAppnIsrSessPriStatsStatsEntry 15 }

mscAppnIsrSessPriStatsOdai OBJECT-TYPE
   SYNTAX     INTEGER  {
                 primary(0),
                 secondary(1) }
   ACCESS     read-only
   STATUS     mandatory
   DESCRIPTION
     "This is the origin destination assignor indicator (ODAI) on the 
      session."
::= { mscAppnIsrSessPriStatsStatsEntry 16 }

mscAppnIsrSessPriStatsLsName OBJECT-TYPE
   SYNTAX     AsciiString (SIZE (1..8))
   ACCESS     read-only
   STATUS     mandatory
   DESCRIPTION
     "This is the link station name associated with these counters and 
      statistics. This is an 8 character name of the link station over which 
      the data flowed. This field can be used to correlate the session 
      statistics with the link over which session data flows."
::= { mscAppnIsrSessPriStatsStatsEntry 17 }

-- 
-- *** THIS SUBTREE CURRENTLY NOT IMPLEMENTED ***
-- 

-- Appn/<string> IsrSession/((fqcpName<string>),(pcid/n) SecStats
-- This is a dynamic component which contains statistics and counters 
-- for the secondary portion of an ISR session.

mscAppnIsrSessSecStats OBJECT IDENTIFIER ::= { mscAppnIsrSess 101 }



mscAppnIsrSessSecStatsRowStatusTable OBJECT-TYPE
   SYNTAX     SEQUENCE OF MscAppnIsrSessSecStatsRowStatusEntry
   ACCESS     not-accessible
   STATUS     mandatory
   DESCRIPTION
     "*** THIS TABLE CURRENTLY NOT IMPLEMENTED ***

      This entry controls the addition and deletion of 
      mscAppnIsrSessSecStats components."
::= { mscAppnIsrSessSecStats 1 }

mscAppnIsrSessSecStatsRowStatusEntry OBJECT-TYPE
   SYNTAX     MscAppnIsrSessSecStatsRowStatusEntry
   ACCESS     not-accessible
   STATUS     mandatory
   DESCRIPTION
     "A single entry in the table represents a single 
      mscAppnIsrSessSecStats component."
   INDEX {
      mscAppnIndex,
      mscAppnIsrSessFqcpNameIndex,
      mscAppnIsrSessProcedureCorrelationIdIndex,
      mscAppnIsrSessSecStatsIndex }
::= { mscAppnIsrSessSecStatsRowStatusTable 1 }

MscAppnIsrSessSecStatsRowStatusEntry ::= SEQUENCE {
   mscAppnIsrSessSecStatsRowStatus
      RowStatus,
   mscAppnIsrSessSecStatsComponentName
      DisplayString,
   mscAppnIsrSessSecStatsStorageType
      StorageType,
   mscAppnIsrSessSecStatsIndex
      NonReplicated }

mscAppnIsrSessSecStatsRowStatus OBJECT-TYPE
   SYNTAX     RowStatus 
   ACCESS     read-only
   STATUS     mandatory
   DESCRIPTION
     "This variable is used as the basis for SNMP naming of
      mscAppnIsrSessSecStats components.
      These components cannot be added nor deleted."
::= { mscAppnIsrSessSecStatsRowStatusEntry 1 }

mscAppnIsrSessSecStatsComponentName OBJECT-TYPE
   SYNTAX     DisplayString 
   ACCESS     read-only
   STATUS     mandatory
   DESCRIPTION
     "This variable provides the component's string name for
      use with the ASCII Console Interface"
::= { mscAppnIsrSessSecStatsRowStatusEntry 2 }

mscAppnIsrSessSecStatsStorageType OBJECT-TYPE
   SYNTAX     StorageType 
   ACCESS     read-only
   STATUS     mandatory
   DESCRIPTION
     "This variable represents the storage type value for the
      mscAppnIsrSessSecStats tables."
::= { mscAppnIsrSessSecStatsRowStatusEntry 4 }

mscAppnIsrSessSecStatsIndex OBJECT-TYPE
   SYNTAX     NonReplicated 
   ACCESS     not-accessible
   STATUS     mandatory
   DESCRIPTION
     "This variable represents the index for the mscAppnIsrSessSecStats tables."
::= { mscAppnIsrSessSecStatsRowStatusEntry 10 }

mscAppnIsrSessSecStatsStatsTable OBJECT-TYPE
   SYNTAX     SEQUENCE OF MscAppnIsrSessSecStatsStatsEntry
   ACCESS     not-accessible
   STATUS     mandatory
   DESCRIPTION
     "*** THIS TABLE CURRENTLY NOT IMPLEMENTED ***

      This component contains counters and statistics for a session."
::= { mscAppnIsrSessSecStats 10 }

mscAppnIsrSessSecStatsStatsEntry OBJECT-TYPE
   SYNTAX     MscAppnIsrSessSecStatsStatsEntry
   ACCESS     not-accessible
   STATUS     mandatory
   DESCRIPTION
     "An entry in the mscAppnIsrSessSecStatsStatsTable."
   INDEX {
      mscAppnIndex,
      mscAppnIsrSessFqcpNameIndex,
      mscAppnIsrSessProcedureCorrelationIdIndex,
      mscAppnIsrSessSecStatsIndex }
::= { mscAppnIsrSessSecStatsStatsTable 1 }

MscAppnIsrSessSecStatsStatsEntry ::= SEQUENCE {
   mscAppnIsrSessSecStatsRxRuSize
      Unsigned32,
   mscAppnIsrSessSecStatsMaxTxBtuSize
      Unsigned32,
   mscAppnIsrSessSecStatsMaxRxBtuSize
      Unsigned32,
   mscAppnIsrSessSecStatsMaxTxPacWin
      INTEGER,
   mscAppnIsrSessSecStatsCurTxPacWin
      INTEGER,
   mscAppnIsrSessSecStatsMaxRxPacWin
      INTEGER,
   mscAppnIsrSessSecStatsCurRxPacWin
      INTEGER,
   mscAppnIsrSessSecStatsTxDataframes
      PassportCounter64,
   mscAppnIsrSessSecStatsTxFmdFrames
      PassportCounter64,
   mscAppnIsrSessSecStatsTxDataBytes
      PassportCounter64,
   mscAppnIsrSessSecStatsRxDataFrames
      PassportCounter64,
   mscAppnIsrSessSecStatsRxFmdFrames
      PassportCounter64,
   mscAppnIsrSessSecStatsRxDataBytes
      PassportCounter64,
   mscAppnIsrSessSecStatsSidh
      Hex,
   mscAppnIsrSessSecStatsSidl
      Hex,
   mscAppnIsrSessSecStatsOdai
      INTEGER,
   mscAppnIsrSessSecStatsLsName
      AsciiString }

mscAppnIsrSessSecStatsRxRuSize OBJECT-TYPE
   SYNTAX     Unsigned32 (0..65535)
   ACCESS     read-only
   STATUS     mandatory
   DESCRIPTION
     "This is the maximum request unit (RU) size that can be used on the 
      session."
::= { mscAppnIsrSessSecStatsStatsEntry 1 }

mscAppnIsrSessSecStatsMaxTxBtuSize OBJECT-TYPE
   SYNTAX     Unsigned32 (0..65535)
   ACCESS     read-only
   STATUS     mandatory
   DESCRIPTION
     "This is the maximum BTU size (length of the information field in a 
      frame) that can be sent on the session."
::= { mscAppnIsrSessSecStatsStatsEntry 2 }

mscAppnIsrSessSecStatsMaxRxBtuSize OBJECT-TYPE
   SYNTAX     Unsigned32 (0..65535)
   ACCESS     read-only
   STATUS     mandatory
   DESCRIPTION
     "This is the maximum BTU size (length of the information field in a 
      frame) that can be received on the session."
::= { mscAppnIsrSessSecStatsStatsEntry 3 }

mscAppnIsrSessSecStatsMaxTxPacWin OBJECT-TYPE
   SYNTAX     INTEGER (0..32767)
   ACCESS     read-only
   STATUS     mandatory
   DESCRIPTION
     "This is the maximum size of the send pacing window on the  
      session."
::= { mscAppnIsrSessSecStatsStatsEntry 4 }

mscAppnIsrSessSecStatsCurTxPacWin OBJECT-TYPE
   SYNTAX     INTEGER (0..32767)
   ACCESS     read-only
   STATUS     mandatory
   DESCRIPTION
     "This is the current size of the send pacing window on the session."
::= { mscAppnIsrSessSecStatsStatsEntry 5 }

mscAppnIsrSessSecStatsMaxRxPacWin OBJECT-TYPE
   SYNTAX     INTEGER (0..32767)
   ACCESS     read-only
   STATUS     mandatory
   DESCRIPTION
     "This is the maximum size of the receive pacing window on the 
      session."
::= { mscAppnIsrSessSecStatsStatsEntry 6 }

mscAppnIsrSessSecStatsCurRxPacWin OBJECT-TYPE
   SYNTAX     INTEGER (0..32767)
   ACCESS     read-only
   STATUS     mandatory
   DESCRIPTION
     "This is the current size of the receive pacing window on the  
      session."
::= { mscAppnIsrSessSecStatsStatsEntry 7 }

mscAppnIsrSessSecStatsTxDataframes OBJECT-TYPE
   SYNTAX     PassportCounter64 
   ACCESS     read-only
   STATUS     mandatory
   DESCRIPTION
     "This attribute counts the number of normal flow data frames sent 
      on the session, the counter wraps to zero."
::= { mscAppnIsrSessSecStatsStatsEntry 8 }

mscAppnIsrSessSecStatsTxFmdFrames OBJECT-TYPE
   SYNTAX     PassportCounter64 
   ACCESS     read-only
   STATUS     mandatory
   DESCRIPTION
     "This attribute counts the number of FMD data frames sent on the 
      session, the counter wraps to zero."
::= { mscAppnIsrSessSecStatsStatsEntry 9 }

mscAppnIsrSessSecStatsTxDataBytes OBJECT-TYPE
   SYNTAX     PassportCounter64 
   ACCESS     read-only
   STATUS     mandatory
   DESCRIPTION
     "This is the number of normal flow data bytes sent on the session, 
      the counter wraps to zero."
::= { mscAppnIsrSessSecStatsStatsEntry 10 }

mscAppnIsrSessSecStatsRxDataFrames OBJECT-TYPE
   SYNTAX     PassportCounter64 
   ACCESS     read-only
   STATUS     mandatory
   DESCRIPTION
     "This is the number of normal flow data frames received on the 
      session, the counter wraps to zero."
::= { mscAppnIsrSessSecStatsStatsEntry 11 }

mscAppnIsrSessSecStatsRxFmdFrames OBJECT-TYPE
   SYNTAX     PassportCounter64 
   ACCESS     read-only
   STATUS     mandatory
   DESCRIPTION
     "This attribute counts the number of FMD data frames received on 
      the session, the counter wraps to zero."
::= { mscAppnIsrSessSecStatsStatsEntry 12 }

mscAppnIsrSessSecStatsRxDataBytes OBJECT-TYPE
   SYNTAX     PassportCounter64 
   ACCESS     read-only
   STATUS     mandatory
   DESCRIPTION
     "This is the number of normal flow data bytes received on the 
      session, the counter wraps to zero."
::= { mscAppnIsrSessSecStatsStatsEntry 13 }

mscAppnIsrSessSecStatsSidh OBJECT-TYPE
   SYNTAX     Hex (0..255)
   ACCESS     read-only
   STATUS     mandatory
   DESCRIPTION
     "This attribute contains the session identifier high byte on the 
      session."
::= { mscAppnIsrSessSecStatsStatsEntry 14 }

mscAppnIsrSessSecStatsSidl OBJECT-TYPE
   SYNTAX     Hex (0..255)
   ACCESS     read-only
   STATUS     mandatory
   DESCRIPTION
     "This attribute contains the session ID low byte on the SSCP session."
::= { mscAppnIsrSessSecStatsStatsEntry 15 }

mscAppnIsrSessSecStatsOdai OBJECT-TYPE
   SYNTAX     INTEGER  {
                 primary(0),
                 secondary(1) }
   ACCESS     read-only
   STATUS     mandatory
   DESCRIPTION
     "This is the origin destination assignor indicator (ODAI) on the 
      session."
::= { mscAppnIsrSessSecStatsStatsEntry 16 }

mscAppnIsrSessSecStatsLsName OBJECT-TYPE
   SYNTAX     AsciiString (SIZE (1..8))
   ACCESS     read-only
   STATUS     mandatory
   DESCRIPTION
     "This is the link station name associated with these counters and 
      statistics. This is an 8 character name of the link station over which 
      the data flowed. This field can be used to correlate the session 
      statistics with the link over which session data flows."
::= { mscAppnIsrSessSecStatsStatsEntry 17 }

-- 
-- *** THIS SUBTREE CURRENTLY NOT IMPLEMENTED ***
-- 

-- Appn/<string> NetworkNodeTransmissionGroup/<frsn<n>>, 
-- <owner name<string>>, <owner type<nn | vrn>>, <destination 
-- name,<string>>, <destination type<nn|vrn>>,<transmission 
-- group<n>>
-- This component contains dynamic information about a transmission 
-- group between two network nodes. It is part of the topology 
-- database.

mscAppnNnTg OBJECT IDENTIFIER ::= { mscAppn 12 }



mscAppnNnTgRowStatusTable OBJECT-TYPE
   SYNTAX     SEQUENCE OF MscAppnNnTgRowStatusEntry
   ACCESS     not-accessible
   STATUS     mandatory
   DESCRIPTION
     "*** THIS TABLE CURRENTLY NOT IMPLEMENTED ***

      This entry controls the addition and deletion of 
      mscAppnNnTg components."
::= { mscAppnNnTg 1 }

mscAppnNnTgRowStatusEntry OBJECT-TYPE
   SYNTAX     MscAppnNnTgRowStatusEntry
   ACCESS     not-accessible
   STATUS     mandatory
   DESCRIPTION
     "A single entry in the table represents a single 
      mscAppnNnTg component."
   INDEX {
      mscAppnIndex,
      mscAppnNnTgOwnerFqcpNameIndex,
      mscAppnNnTgDestFqcpNameIndex,
      mscAppnNnTgTransmissionGroupIndex }
::= { mscAppnNnTgRowStatusTable 1 }

MscAppnNnTgRowStatusEntry ::= SEQUENCE {
   mscAppnNnTgRowStatus
      RowStatus,
   mscAppnNnTgComponentName
      DisplayString,
   mscAppnNnTgStorageType
      StorageType,
   mscAppnNnTgOwnerFqcpNameIndex
      AsciiStringIndex,
   mscAppnNnTgDestFqcpNameIndex
      AsciiStringIndex,
   mscAppnNnTgTransmissionGroupIndex
      Integer32 }

mscAppnNnTgRowStatus OBJECT-TYPE
   SYNTAX     RowStatus 
   ACCESS     read-only
   STATUS     mandatory
   DESCRIPTION
     "This variable is used as the basis for SNMP naming of
      mscAppnNnTg components.
      These components cannot be added nor deleted."
::= { mscAppnNnTgRowStatusEntry 1 }

mscAppnNnTgComponentName OBJECT-TYPE
   SYNTAX     DisplayString 
   ACCESS     read-only
   STATUS     mandatory
   DESCRIPTION
     "This variable provides the component's string name for
      use with the ASCII Console Interface"
::= { mscAppnNnTgRowStatusEntry 2 }

mscAppnNnTgStorageType OBJECT-TYPE
   SYNTAX     StorageType 
   ACCESS     read-only
   STATUS     mandatory
   DESCRIPTION
     "This variable represents the storage type value for the
      mscAppnNnTg tables."
::= { mscAppnNnTgRowStatusEntry 4 }

mscAppnNnTgOwnerFqcpNameIndex OBJECT-TYPE
   SYNTAX     AsciiStringIndex (SIZE (3..17))
   ACCESS     not-accessible
   STATUS     mandatory
   DESCRIPTION
     "This variable represents an index for the mscAppnNnTg tables."
::= { mscAppnNnTgRowStatusEntry 10 }

mscAppnNnTgDestFqcpNameIndex OBJECT-TYPE
   SYNTAX     AsciiStringIndex (SIZE (3..17))
   ACCESS     not-accessible
   STATUS     mandatory
   DESCRIPTION
     "This variable represents an index for the mscAppnNnTg tables."
::= { mscAppnNnTgRowStatusEntry 11 }

mscAppnNnTgTransmissionGroupIndex OBJECT-TYPE
   SYNTAX     Integer32 (0..255)
   ACCESS     not-accessible
   STATUS     mandatory
   DESCRIPTION
     "This variable represents an index for the mscAppnNnTg tables."
::= { mscAppnNnTgRowStatusEntry 12 }

mscAppnNnTgOperTable OBJECT-TYPE
   SYNTAX     SEQUENCE OF MscAppnNnTgOperEntry
   ACCESS     not-accessible
   STATUS     mandatory
   DESCRIPTION
     "*** THIS TABLE CURRENTLY NOT IMPLEMENTED ***

      This group contains the operational status of the transmission group 
      entry in the topology database."
::= { mscAppnNnTg 10 }

mscAppnNnTgOperEntry OBJECT-TYPE
   SYNTAX     MscAppnNnTgOperEntry
   ACCESS     not-accessible
   STATUS     mandatory
   DESCRIPTION
     "An entry in the mscAppnNnTgOperTable."
   INDEX {
      mscAppnIndex,
      mscAppnNnTgOwnerFqcpNameIndex,
      mscAppnNnTgDestFqcpNameIndex,
      mscAppnNnTgTransmissionGroupIndex }
::= { mscAppnNnTgOperTable 1 }

MscAppnNnTgOperEntry ::= SEQUENCE {
   mscAppnNnTgFlowReductionSequenceNumber
      Unsigned32,
   mscAppnNnTgDaysLeft
      Unsigned32,
   mscAppnNnTgResourceSequenceNumber
      Unsigned32,
   mscAppnNnTgStatus
      OCTET STRING }

mscAppnNnTgFlowReductionSequenceNumber OBJECT-TYPE
   SYNTAX     Unsigned32 (0..4294967295)
   ACCESS     read-only
   STATUS     mandatory
   DESCRIPTION
     "Flow reduction sequence numbers (FRSNs) are associated with 
      Topology Database Updates (TDUs) and are unique only within 
      each APPN network node. A TDU can be associated with multiple 
      APPN resources. This FRSN indicates the last time this resource 
      was updated at this node.
      
      SNMP APPN MIB = ibmappnNnTgFrsn"
::= { mscAppnNnTgOperEntry 1 }

mscAppnNnTgDaysLeft OBJECT-TYPE
   SYNTAX     Unsigned32 (1..15)
   ACCESS     read-only
   STATUS     mandatory
   DESCRIPTION
     "Number of days left until entry purged."
::= { mscAppnNnTgOperEntry 2 }

mscAppnNnTgResourceSequenceNumber OBJECT-TYPE
   SYNTAX     Unsigned32 (0..4294967295)
   ACCESS     read-only
   STATUS     mandatory
   DESCRIPTION
     "Resource sequence number."
::= { mscAppnNnTgOperEntry 3 }

mscAppnNnTgStatus OBJECT-TYPE
   SYNTAX     OCTET STRING (SIZE (1))
   ACCESS     read-only
   STATUS     mandatory
   DESCRIPTION
     "This attribute contains status information about the transmission 
      group from the topology database. It can be any combination of the 
      following: 
      
      operational
      If present indicates that the transmission group is operational.
      
      CpCpSessions
      If present, indicates that CP-CP sessions are supported on this 
      transmission group.
      
      quiescing
      If present, indicates that the transmission group is quiescing.

      Description of bits:
      notused0(0)
      notused1(1)
      notused2(2)
      notused3(3)
      cpCpSessions(4)
      quiescing(5)
      notused6(6)
      operational(7)"
::= { mscAppnNnTgOperEntry 4 }

mscAppnNnTgLinkAddressTable OBJECT-TYPE
   SYNTAX     SEQUENCE OF MscAppnNnTgLinkAddressEntry
   ACCESS     not-accessible
   STATUS     mandatory
   DESCRIPTION
     "*** THIS TABLE CURRENTLY NOT IMPLEMENTED ***

      Contains the attribute for destination address."
::= { mscAppnNnTg 11 }

mscAppnNnTgLinkAddressEntry OBJECT-TYPE
   SYNTAX     MscAppnNnTgLinkAddressEntry
   ACCESS     not-accessible
   STATUS     mandatory
   DESCRIPTION
     "An entry in the mscAppnNnTgLinkAddressTable."
   INDEX {
      mscAppnIndex,
      mscAppnNnTgOwnerFqcpNameIndex,
      mscAppnNnTgDestFqcpNameIndex,
      mscAppnNnTgTransmissionGroupIndex }
::= { mscAppnNnTgLinkAddressTable 1 }

MscAppnNnTgLinkAddressEntry ::= SEQUENCE {
   mscAppnNnTgDlcData
      HexString }

mscAppnNnTgDlcData OBJECT-TYPE
   SYNTAX     HexString (SIZE (0..32))
   ACCESS     read-only
   STATUS     mandatory
   DESCRIPTION
     "This attribute contains specific data related to the link connection. 
      
      Token-Ring - contains MAC/SAP
      X.25 Switched - contains dial digits
      X.21 Switched - contains dial digits
      Circuit Switched - contains dial digits
      Frame-Relay - contains DLCI and SAP
      
      The value will be set to zero if the destination node type is not a 
      virtual routing node."
::= { mscAppnNnTgLinkAddressEntry 1 }

mscAppnNnTgTgCharTable OBJECT-TYPE
   SYNTAX     SEQUENCE OF MscAppnNnTgTgCharEntry
   ACCESS     not-accessible
   STATUS     mandatory
   DESCRIPTION
     "*** THIS TABLE CURRENTLY NOT IMPLEMENTED ***

      These attributes of the link station are in a group using a common 
      structure. This set provides the TG characteristics of the link 
      through this link station for route selection."
::= { mscAppnNnTg 12 }

mscAppnNnTgTgCharEntry OBJECT-TYPE
   SYNTAX     MscAppnNnTgTgCharEntry
   ACCESS     not-accessible
   STATUS     mandatory
   DESCRIPTION
     "An entry in the mscAppnNnTgTgCharTable."
   INDEX {
      mscAppnIndex,
      mscAppnNnTgOwnerFqcpNameIndex,
      mscAppnNnTgDestFqcpNameIndex,
      mscAppnNnTgTransmissionGroupIndex }
::= { mscAppnNnTgTgCharTable 1 }

MscAppnNnTgTgCharEntry ::= SEQUENCE {
   mscAppnNnTgEffectiveCap
      INTEGER,
   mscAppnNnTgConnectCost
      INTEGER,
   mscAppnNnTgByteCost
      INTEGER,
   mscAppnNnTgSecurity
      INTEGER,
   mscAppnNnTgPropagationDelay
      INTEGER,
   mscAppnNnTgUserDefinedParm1
      Unsigned32,
   mscAppnNnTgUserDefinedParm2
      Unsigned32,
   mscAppnNnTgUserDefinedParm3
      Unsigned32 }

mscAppnNnTgEffectiveCap OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 n600Gbps(255) }
   ACCESS     read-only
   STATUS     mandatory
   DESCRIPTION
     "The effective capacity is an integer value that indicates the capacity 
      in kilo bits per second. It is derived from the link bandwidth and the 
      maximum load factor with the range of 0 thru 603,979,776."
::= { mscAppnNnTgTgCharEntry 1 }

mscAppnNnTgConnectCost OBJECT-TYPE
   SYNTAX     INTEGER (0..255)
   ACCESS     read-only
   STATUS     mandatory
   DESCRIPTION
     "The cost-per-connect time is a characteristic represented by a 
      single-byte value in the range 0 to 255 that expresses a relative cost 
      of using a transmission group. The units for cost-per-connect time 
      are installation-defined and are typically based on the applicable 
      tariffs of the transmission facility being used by the transmission 
      group. The cost-per-connect time values that a network 
      administrator assigns to the transmission groups in a network 
      should reflect the relative expense of each transmission group as 
      compared to all other transmission groups in the network. A value 
      of 0 means that the cost of connecting over the transmission group 
      is at no additional cost (as in the case of a non-switched facility."
   DEFVAL     { 0 }
::= { mscAppnNnTgTgCharEntry 2 }

mscAppnNnTgByteCost OBJECT-TYPE
   SYNTAX     INTEGER (0..255)
   ACCESS     read-only
   STATUS     mandatory
   DESCRIPTION
     "Cost-per-byte is a single byte value in the range 0 to 255 that 
      expresses a relative cost of transmitting a byte over the associated 
      transmission group. The units for cost-per-byte are user-defined. 
      Like cost-per-connect-time, cost-per-byte is network specific and 
      will not be uniform across networks unless assignments are 
      coordinated."
   DEFVAL     { 0 }
::= { mscAppnNnTgTgCharEntry 3 }

mscAppnNnTgSecurity OBJECT-TYPE
   SYNTAX     INTEGER  {
                 unKnown(0),
                 nonSecure(1),
                 publicSwitchedNetwork(32),
                 undergroundCable(64),
                 secureConduit(96),
                 guardedConduit(128),
                 encrypted(160),
                 guardedRadiation(192) }
   ACCESS     read-only
   STATUS     mandatory
   DESCRIPTION
     "This static characteristic indicates the level of security protection. 
      The security values are architecturally defined to provide continuity 
      across all networks. Currently, security is encoded as one of the 
      following seven values:
      
      guardedRadiation - guarded conduit containing the transmission 
      medium; protected against physical and radiation tapping.
      encrypted - link level encryption is provided
      unknown - has not been determined 
      guardedConduit - guarded conduit; protected against physical 
      tapping
      secureConduit - secure conduit, not guarded; e.g. pressurized pipe
      undergroundCable - underground cable located in a secure country
      publicSwitchedNetwork - public switched network; secure in the 
      sense that there is no predetermined route that traffic will take
      nonSecure - all else, e.g. satellite-connected, located in a nonsecure 
      country."
   DEFVAL     { nonSecure }
::= { mscAppnNnTgTgCharEntry 4 }

mscAppnNnTgPropagationDelay OBJECT-TYPE
   SYNTAX     INTEGER  {
                 minimum(0),
                 negligible(76),
                 terrestrial(113),
                 packetSwitched(145),
                 long(153) }
   ACCESS     read-only
   STATUS     mandatory
   DESCRIPTION
     "The propagation delay is the length of time that it takes for a signal 
      to propagate from one end of the transmission group to the other. 
      Typical values are:
      
      minimum - minimum
      negligible - 400 microsec
      terrestrial - 10 msec
      packetSwitched - 150 msec
      long - 300 msec"
   DEFVAL     { terrestrial }
::= { mscAppnNnTgTgCharEntry 5 }

mscAppnNnTgUserDefinedParm1 OBJECT-TYPE
   SYNTAX     Unsigned32 (0..255)
   ACCESS     read-only
   STATUS     mandatory
   DESCRIPTION
     "This is the user defined routing parameter in range 0-255."
   DEFVAL     { 128 }
::= { mscAppnNnTgTgCharEntry 7 }

mscAppnNnTgUserDefinedParm2 OBJECT-TYPE
   SYNTAX     Unsigned32 (0..255)
   ACCESS     read-only
   STATUS     mandatory
   DESCRIPTION
     "This is the user defined routing parameter in range 0-255."
   DEFVAL     { 128 }
::= { mscAppnNnTgTgCharEntry 8 }

mscAppnNnTgUserDefinedParm3 OBJECT-TYPE
   SYNTAX     Unsigned32 (0..255)
   ACCESS     read-only
   STATUS     mandatory
   DESCRIPTION
     "This is the user defined routing parameter in range 0-255."
   DEFVAL     { 128 }
::= { mscAppnNnTgTgCharEntry 9 }

-- 
-- *** THIS SUBTREE CURRENTLY NOT IMPLEMENTED ***
-- 

-- Appn/<string> Rtp/<string>
-- This is a dynamic component which contains information about 
-- High Performance Routing (HPR) - Rapid Transport Protocol (RTP) 
-- pipes terminating on this node.
-- The instance value is an 8 character string assigned algorithmically 
-- by the node.

mscAppnRtp OBJECT IDENTIFIER ::= { mscAppn 13 }



mscAppnRtpRowStatusTable OBJECT-TYPE
   SYNTAX     SEQUENCE OF MscAppnRtpRowStatusEntry
   ACCESS     not-accessible
   STATUS     mandatory
   DESCRIPTION
     "*** THIS TABLE CURRENTLY NOT IMPLEMENTED ***

      This entry controls the addition and deletion of 
      mscAppnRtp components."
::= { mscAppnRtp 1 }

mscAppnRtpRowStatusEntry OBJECT-TYPE
   SYNTAX     MscAppnRtpRowStatusEntry
   ACCESS     not-accessible
   STATUS     mandatory
   DESCRIPTION
     "A single entry in the table represents a single 
      mscAppnRtp component."
   INDEX {
      mscAppnIndex,
      mscAppnRtpIndex }
::= { mscAppnRtpRowStatusTable 1 }

MscAppnRtpRowStatusEntry ::= SEQUENCE {
   mscAppnRtpRowStatus
      RowStatus,
   mscAppnRtpComponentName
      DisplayString,
   mscAppnRtpStorageType
      StorageType,
   mscAppnRtpIndex
      AsciiStringIndex }

mscAppnRtpRowStatus OBJECT-TYPE
   SYNTAX     RowStatus 
   ACCESS     read-only
   STATUS     mandatory
   DESCRIPTION
     "This variable is used as the basis for SNMP naming of
      mscAppnRtp components.
      These components cannot be added nor deleted."
::= { mscAppnRtpRowStatusEntry 1 }

mscAppnRtpComponentName OBJECT-TYPE
   SYNTAX     DisplayString 
   ACCESS     read-only
   STATUS     mandatory
   DESCRIPTION
     "This variable provides the component's string name for
      use with the ASCII Console Interface"
::= { mscAppnRtpRowStatusEntry 2 }

mscAppnRtpStorageType OBJECT-TYPE
   SYNTAX     StorageType 
   ACCESS     read-only
   STATUS     mandatory
   DESCRIPTION
     "This variable represents the storage type value for the
      mscAppnRtp tables."
::= { mscAppnRtpRowStatusEntry 4 }

mscAppnRtpIndex OBJECT-TYPE
   SYNTAX     AsciiStringIndex (SIZE (1..8))
   ACCESS     not-accessible
   STATUS     mandatory
   DESCRIPTION
     "This variable represents the index for the mscAppnRtp tables."
::= { mscAppnRtpRowStatusEntry 10 }

mscAppnRtpOperTable OBJECT-TYPE
   SYNTAX     SEQUENCE OF MscAppnRtpOperEntry
   ACCESS     not-accessible
   STATUS     mandatory
   DESCRIPTION
     "*** THIS TABLE CURRENTLY NOT IMPLEMENTED ***

      This group contains the operational data for the High Performance 
      Routing-Rapid Transport Protocol pipe"
::= { mscAppnRtp 10 }

mscAppnRtpOperEntry OBJECT-TYPE
   SYNTAX     MscAppnRtpOperEntry
   ACCESS     not-accessible
   STATUS     mandatory
   DESCRIPTION
     "An entry in the mscAppnRtpOperTable."
   INDEX {
      mscAppnIndex,
      mscAppnRtpIndex }
::= { mscAppnRtpOperTable 1 }

MscAppnRtpOperEntry ::= SEQUENCE {
   mscAppnRtpLocalLsName
      AsciiString,
   mscAppnRtpRemoteCpName
      AsciiString,
   mscAppnRtpCosName
      AsciiString,
   mscAppnRtpActiveSessions
      INTEGER,
   mscAppnRtpLocalTcid
      HexString,
   mscAppnRtpRemoteTcid
      HexString,
   mscAppnRtpIdleTimer
      Unsigned32,
   mscAppnRtpMaxBtuSize
      INTEGER }

mscAppnRtpLocalLsName OBJECT-TYPE
   SYNTAX     AsciiString (SIZE (1..8))
   ACCESS     read-only
   STATUS     mandatory
   DESCRIPTION
     "This is the name of the local link station associated with this High 
      Performance Routing-Rapid Transport Protocol pipe"
::= { mscAppnRtpOperEntry 1 }

mscAppnRtpRemoteCpName OBJECT-TYPE
   SYNTAX     AsciiString (SIZE (1..17))
   ACCESS     read-only
   STATUS     mandatory
   DESCRIPTION
     "This is the CP name of the node at the other end of the High 
      Performance Routing-Rapid Transport Protocol pipe"
::= { mscAppnRtpOperEntry 2 }

mscAppnRtpCosName OBJECT-TYPE
   SYNTAX     AsciiString (SIZE (1..8))
   ACCESS     read-only
   STATUS     mandatory
   DESCRIPTION
     "This is the name of the Class of Service associated with this High 
      Performance Routing-Rapid Transport Protocol pipe"
::= { mscAppnRtpOperEntry 3 }

mscAppnRtpActiveSessions OBJECT-TYPE
   SYNTAX     INTEGER (0..32767)
   ACCESS     read-only
   STATUS     mandatory
   DESCRIPTION
     "The number of active sessions using this High Performance 
      Routing-Rapid Transport Protocol pipe"
::= { mscAppnRtpOperEntry 4 }

mscAppnRtpLocalTcid OBJECT-TYPE
   SYNTAX     HexString (SIZE (8))
   ACCESS     read-only
   STATUS     mandatory
   DESCRIPTION
     "The Transport Connection Identifier (TCID) assigned to this HPR 
      RTP pipe by the local node"
::= { mscAppnRtpOperEntry 5 }

mscAppnRtpRemoteTcid OBJECT-TYPE
   SYNTAX     HexString (SIZE (8))
   ACCESS     read-only
   STATUS     mandatory
   DESCRIPTION
     "The Transport Connection Identifier (TCID) assigned to this HPR 
      RTP pipe by the remote node."
::= { mscAppnRtpOperEntry 6 }

mscAppnRtpIdleTimer OBJECT-TYPE
   SYNTAX     Unsigned32 (0..4294967295)
   ACCESS     read-only
   STATUS     mandatory
   DESCRIPTION
     "The idle timer of this High Performance Routing-Rapid Transport 
      Protocol pipe (in seconds)"
::= { mscAppnRtpOperEntry 7 }

mscAppnRtpMaxBtuSize OBJECT-TYPE
   SYNTAX     INTEGER (0..32767)
   ACCESS     read-only
   STATUS     mandatory
   DESCRIPTION
     "The maximum BTU size (the length of the information field in a 
      frame) of the High Performance Routing-Rapid Transport Protocol 
      pipe."
::= { mscAppnRtpOperEntry 8 }

mscAppnRtpStatsTable OBJECT-TYPE
   SYNTAX     SEQUENCE OF MscAppnRtpStatsEntry
   ACCESS     not-accessible
   STATUS     mandatory
   DESCRIPTION
     "*** THIS TABLE CURRENTLY NOT IMPLEMENTED ***

      This group contains the statistics and counters for the High 
      Performance Routing-Rapid Transport Protocol pipe."
::= { mscAppnRtp 11 }

mscAppnRtpStatsEntry OBJECT-TYPE
   SYNTAX     MscAppnRtpStatsEntry
   ACCESS     not-accessible
   STATUS     mandatory
   DESCRIPTION
     "An entry in the mscAppnRtpStatsTable."
   INDEX {
      mscAppnIndex,
      mscAppnRtpIndex }
::= { mscAppnRtpStatsTable 1 }

MscAppnRtpStatsEntry ::= SEQUENCE {
   mscAppnRtpTxBytes
      PassportCounter64,
   mscAppnRtpRxBytes
      PassportCounter64,
   mscAppnRtpBytesResent
      PassportCounter64,
   mscAppnRtpBytesDiscarded
      PassportCounter64,
   mscAppnRtpPktTx
      PassportCounter64,
   mscAppnRtpPktRx
      PassportCounter64,
   mscAppnRtpPktResent
      PassportCounter64,
   mscAppnRtpPktDiscard
      PassportCounter64,
   mscAppnRtpLostFrames
      PassportCounter64,
   mscAppnRtpCurTxRate
      Gauge32,
   mscAppnRtpMaxTxRate
      Gauge32,
   mscAppnRtpMinTxRate
      Gauge32,
   mscAppnRtpCurRxRate
      Gauge32,
   mscAppnRtpMaxRxRate
      Gauge32,
   mscAppnRtpMinRxRate
      Gauge32,
   mscAppnRtpBurstSize
      Gauge32,
   mscAppnRtpUptime
      TimeTicks,
   mscAppnRtpSmoothRoundTripTime
      Gauge32,
   mscAppnRtpLastRoundTripTime
      Gauge32,
   mscAppnRtpShortReqTimer
      Gauge32,
   mscAppnRtpShortReqTimeouts
      PassportCounter64,
   mscAppnRtpIdleTimeouts
      PassportCounter64,
   mscAppnRtpRxInvalidSnaFrames
      PassportCounter64,
   mscAppnRtpInSessionControlFrames
      PassportCounter64,
   mscAppnRtpOutSessionControlFrames
      PassportCounter64 }

mscAppnRtpTxBytes OBJECT-TYPE
   SYNTAX     PassportCounter64 
   ACCESS     read-only
   STATUS     mandatory
   DESCRIPTION
     "This attribute is the total number of bytes sent on this High 
      Performance Routing-Rapid Transport Protocol pipe. This counter 
      wraps to zero."
::= { mscAppnRtpStatsEntry 1 }

mscAppnRtpRxBytes OBJECT-TYPE
   SYNTAX     PassportCounter64 
   ACCESS     read-only
   STATUS     mandatory
   DESCRIPTION
     "This attribute is the total number of bytes received on this High 
      Performance Routing-Rapid Transport Protocol pipe. This counter 
      wraps to zero."
::= { mscAppnRtpStatsEntry 2 }

mscAppnRtpBytesResent OBJECT-TYPE
   SYNTAX     PassportCounter64 
   ACCESS     read-only
   STATUS     mandatory
   DESCRIPTION
     "This attribute counts the total number of bytes resent on this High 
      Performance Routing-Rapid Transport Protocol pipe. This counter 
      wraps to zero."
::= { mscAppnRtpStatsEntry 3 }

mscAppnRtpBytesDiscarded OBJECT-TYPE
   SYNTAX     PassportCounter64 
   ACCESS     read-only
   STATUS     mandatory
   DESCRIPTION
     "This attribute counts the total number of bytes discarded on this 
      High Performance Routing-Rapid Transport Protocol pipe. High 
      numbers of discarded bytes may indicate a problem in the APPN 
      network. This counter wraps to zero."
::= { mscAppnRtpStatsEntry 4 }

mscAppnRtpPktTx OBJECT-TYPE
   SYNTAX     PassportCounter64 
   ACCESS     read-only
   STATUS     mandatory
   DESCRIPTION
     "This attribute counts the total number of packets sent on this High 
      Performance Routing-Rapid Transport Protocol pipe. This counter 
      wraps to zero."
::= { mscAppnRtpStatsEntry 5 }

mscAppnRtpPktRx OBJECT-TYPE
   SYNTAX     PassportCounter64 
   ACCESS     read-only
   STATUS     mandatory
   DESCRIPTION
     "This attribute counts the total number of packets received on this 
      High Performance Routing-Rapid Transport Protocol pipe. This 
      counter wraps to zero."
::= { mscAppnRtpStatsEntry 6 }

mscAppnRtpPktResent OBJECT-TYPE
   SYNTAX     PassportCounter64 
   ACCESS     read-only
   STATUS     mandatory
   DESCRIPTION
     "This attribute counts the total number of packets resent on this High 
      Performance Routing-Rapid Transport Protocol pipe. This counter 
      wraps to zero."
::= { mscAppnRtpStatsEntry 7 }

mscAppnRtpPktDiscard OBJECT-TYPE
   SYNTAX     PassportCounter64 
   ACCESS     read-only
   STATUS     mandatory
   DESCRIPTION
     "This attribute counts the total number of packets discarded on this 
      High Performance Routing-Rapid Transport Protocol pipe. Large 
      numbers of discarded packets may indicate a problem in the APPN 
      network. This counter wraps to zero."
::= { mscAppnRtpStatsEntry 8 }

mscAppnRtpLostFrames OBJECT-TYPE
   SYNTAX     PassportCounter64 
   ACCESS     read-only
   STATUS     mandatory
   DESCRIPTION
     "This attribute counts the number of lost frames detected on this 
      pipe. Excessive numbers of lost frames may indicate a problem in 
      the APPN network. This counter wraps to zero."
::= { mscAppnRtpStatsEntry 9 }

mscAppnRtpCurTxRate OBJECT-TYPE
   SYNTAX     Gauge32 (0..4294967295)
   ACCESS     read-only
   STATUS     mandatory
   DESCRIPTION
     "This attribute gives the current send rate on this pipe."
::= { mscAppnRtpStatsEntry 10 }

mscAppnRtpMaxTxRate OBJECT-TYPE
   SYNTAX     Gauge32 (0..4294967295)
   ACCESS     read-only
   STATUS     mandatory
   DESCRIPTION
     "This attribute give the maximum send rate on this pipe."
::= { mscAppnRtpStatsEntry 11 }

mscAppnRtpMinTxRate OBJECT-TYPE
   SYNTAX     Gauge32 (0..4294967295)
   ACCESS     read-only
   STATUS     mandatory
   DESCRIPTION
     "This attribute gives the minimum send rate on this pipe."
::= { mscAppnRtpStatsEntry 12 }

mscAppnRtpCurRxRate OBJECT-TYPE
   SYNTAX     Gauge32 (0..4294967295)
   ACCESS     read-only
   STATUS     mandatory
   DESCRIPTION
     "This attribute gives the current receive rate on this pipe."
::= { mscAppnRtpStatsEntry 13 }

mscAppnRtpMaxRxRate OBJECT-TYPE
   SYNTAX     Gauge32 (0..4294967295)
   ACCESS     read-only
   STATUS     mandatory
   DESCRIPTION
     "This attribute gives the maximum receive rate on this pipe."
::= { mscAppnRtpStatsEntry 14 }

mscAppnRtpMinRxRate OBJECT-TYPE
   SYNTAX     Gauge32 (0..4294967295)
   ACCESS     read-only
   STATUS     mandatory
   DESCRIPTION
     "This attribute gives the minimum receive rate on this pipe."
::= { mscAppnRtpStatsEntry 15 }

mscAppnRtpBurstSize OBJECT-TYPE
   SYNTAX     Gauge32 (0..4294967295)
   ACCESS     read-only
   STATUS     mandatory
   DESCRIPTION
     "This attribute gives the current burst size on this pipe."
::= { mscAppnRtpStatsEntry 16 }

mscAppnRtpUptime OBJECT-TYPE
   SYNTAX     TimeTicks 
   ACCESS     read-only
   STATUS     mandatory
   DESCRIPTION
     "This attribute gives the total uptime of this High Performance 
      Routing-Rapid Transport Protocol pipe."
::= { mscAppnRtpStatsEntry 17 }

mscAppnRtpSmoothRoundTripTime OBJECT-TYPE
   SYNTAX     Gauge32 (0..4294967295)
   ACCESS     read-only
   STATUS     mandatory
   DESCRIPTION
     "This attribute gives the smoothed round-trip time on this pipe."
::= { mscAppnRtpStatsEntry 18 }

mscAppnRtpLastRoundTripTime OBJECT-TYPE
   SYNTAX     Gauge32 (0..4294967295)
   ACCESS     read-only
   STATUS     mandatory
   DESCRIPTION
     "This attribute gives the last round-trip time on this pipe."
::= { mscAppnRtpStatsEntry 19 }

mscAppnRtpShortReqTimer OBJECT-TYPE
   SYNTAX     Gauge32 (0..4294967295)
   ACCESS     read-only
   STATUS     mandatory
   DESCRIPTION
     "This attribute gives the short request timer duration on this pipe."
::= { mscAppnRtpStatsEntry 20 }

mscAppnRtpShortReqTimeouts OBJECT-TYPE
   SYNTAX     PassportCounter64 
   ACCESS     read-only
   STATUS     mandatory
   DESCRIPTION
     "This attribute counts the number of short request timer timeouts on 
      this pipe."
::= { mscAppnRtpStatsEntry 21 }

mscAppnRtpIdleTimeouts OBJECT-TYPE
   SYNTAX     PassportCounter64 
   ACCESS     read-only
   STATUS     mandatory
   DESCRIPTION
     "This attribute count the number of idle timer timeouts on this pipe."
::= { mscAppnRtpStatsEntry 22 }

mscAppnRtpRxInvalidSnaFrames OBJECT-TYPE
   SYNTAX     PassportCounter64 
   ACCESS     read-only
   STATUS     mandatory
   DESCRIPTION
     "This attribute counts the number of invalid SNA frames received on 
      this pipe."
::= { mscAppnRtpStatsEntry 23 }

mscAppnRtpInSessionControlFrames OBJECT-TYPE
   SYNTAX     PassportCounter64 
   ACCESS     read-only
   STATUS     mandatory
   DESCRIPTION
     "This attribute counts the number of Session Control frames received 
      on this pipe."
::= { mscAppnRtpStatsEntry 24 }

mscAppnRtpOutSessionControlFrames OBJECT-TYPE
   SYNTAX     PassportCounter64 
   ACCESS     read-only
   STATUS     mandatory
   DESCRIPTION
     "This attribute counts the number of Session Control frames sent on 
      this pipe."
::= { mscAppnRtpStatsEntry 25 }

-- 
-- *** THIS SUBTREE CURRENTLY NOT IMPLEMENTED ***
-- 

-- Appn/<string> Dlu/<string>
-- This is a dynamic component which contains information about a 
-- specific dependent LU session.
-- The instance name is the dependent LU name as know to VTAM

mscAppnDlu OBJECT IDENTIFIER ::= { mscAppn 14 }



mscAppnDluRowStatusTable OBJECT-TYPE
   SYNTAX     SEQUENCE OF MscAppnDluRowStatusEntry
   ACCESS     not-accessible
   STATUS     mandatory
   DESCRIPTION
     "*** THIS TABLE CURRENTLY NOT IMPLEMENTED ***

      This entry controls the addition and deletion of 
      mscAppnDlu components."
::= { mscAppnDlu 1 }

mscAppnDluRowStatusEntry OBJECT-TYPE
   SYNTAX     MscAppnDluRowStatusEntry
   ACCESS     not-accessible
   STATUS     mandatory
   DESCRIPTION
     "A single entry in the table represents a single 
      mscAppnDlu component."
   INDEX {
      mscAppnIndex,
      mscAppnDluIndex }
::= { mscAppnDluRowStatusTable 1 }

MscAppnDluRowStatusEntry ::= SEQUENCE {
   mscAppnDluRowStatus
      RowStatus,
   mscAppnDluComponentName
      DisplayString,
   mscAppnDluStorageType
      StorageType,
   mscAppnDluIndex
      AsciiStringIndex }

mscAppnDluRowStatus OBJECT-TYPE
   SYNTAX     RowStatus 
   ACCESS     read-only
   STATUS     mandatory
   DESCRIPTION
     "This variable is used as the basis for SNMP naming of
      mscAppnDlu components.
      These components cannot be added nor deleted."
::= { mscAppnDluRowStatusEntry 1 }

mscAppnDluComponentName OBJECT-TYPE
   SYNTAX     DisplayString 
   ACCESS     read-only
   STATUS     mandatory
   DESCRIPTION
     "This variable provides the component's string name for
      use with the ASCII Console Interface"
::= { mscAppnDluRowStatusEntry 2 }

mscAppnDluStorageType OBJECT-TYPE
   SYNTAX     StorageType 
   ACCESS     read-only
   STATUS     mandatory
   DESCRIPTION
     "This variable represents the storage type value for the
      mscAppnDlu tables."
::= { mscAppnDluRowStatusEntry 4 }

mscAppnDluIndex OBJECT-TYPE
   SYNTAX     AsciiStringIndex (SIZE (1..8))
   ACCESS     not-accessible
   STATUS     mandatory
   DESCRIPTION
     "This variable represents the index for the mscAppnDlu tables."
::= { mscAppnDluRowStatusEntry 10 }

mscAppnDluOperTable OBJECT-TYPE
   SYNTAX     SEQUENCE OF MscAppnDluOperEntry
   ACCESS     not-accessible
   STATUS     mandatory
   DESCRIPTION
     "*** THIS TABLE CURRENTLY NOT IMPLEMENTED ***

      The group contains the operational data for a dependent LU session."
::= { mscAppnDlu 10 }

mscAppnDluOperEntry OBJECT-TYPE
   SYNTAX     MscAppnDluOperEntry
   ACCESS     not-accessible
   STATUS     mandatory
   DESCRIPTION
     "An entry in the mscAppnDluOperTable."
   INDEX {
      mscAppnIndex,
      mscAppnDluIndex }
::= { mscAppnDluOperTable 1 }

MscAppnDluOperEntry ::= SEQUENCE {
   mscAppnDluSscpSessActive
      INTEGER,
   mscAppnDluPluSessActive
      INTEGER,
   mscAppnDluDlusName
      AsciiString,
   mscAppnDluPluName
      AsciiString,
   mscAppnDluNauAddress
      INTEGER }

mscAppnDluSscpSessActive OBJECT-TYPE
   SYNTAX     INTEGER  {
                 inactive(0),
                 active(1) }
   ACCESS     read-only
   STATUS     mandatory
   DESCRIPTION
     "This attribute tells whether the SSCP-LU session is active"
::= { mscAppnDluOperEntry 1 }

mscAppnDluPluSessActive OBJECT-TYPE
   SYNTAX     INTEGER  {
                 inactive(0),
                 active(1) }
   ACCESS     read-only
   STATUS     mandatory
   DESCRIPTION
     "This attribute tells whether the dependent LU session is active."
::= { mscAppnDluOperEntry 2 }

mscAppnDluDlusName OBJECT-TYPE
   SYNTAX     AsciiString (SIZE (0..17))
   ACCESS     read-only
   STATUS     mandatory
   DESCRIPTION
     "This attribute tells the name of the dependent LU server name that 
      this dependent LU is connected to."
::= { mscAppnDluOperEntry 3 }

mscAppnDluPluName OBJECT-TYPE
   SYNTAX     AsciiString (SIZE (0..17))
   ACCESS     read-only
   STATUS     mandatory
   DESCRIPTION
     "This attribute tells the partner LU name of this dependent LU if the 
      LU is connected, it is a NULL string if the dependent LU does not 
      have an active session with a partner LU."
::= { mscAppnDluOperEntry 4 }

mscAppnDluNauAddress OBJECT-TYPE
   SYNTAX     INTEGER (0..255)
   ACCESS     read-only
   STATUS     mandatory
   DESCRIPTION
     "This attribute gives the NAU address of the dependent LU."
::= { mscAppnDluOperEntry 5 }

-- 
-- *** THIS SUBTREE CURRENTLY NOT IMPLEMENTED ***
-- 

-- Appn/<string> Dlu/<string> Sscp
-- This is a dynamic component which contains counters and other 
-- statistical data for the SSCP-LU session.

mscAppnDluSscp OBJECT IDENTIFIER ::= { mscAppnDlu 100 }



mscAppnDluSscpRowStatusTable OBJECT-TYPE
   SYNTAX     SEQUENCE OF MscAppnDluSscpRowStatusEntry
   ACCESS     not-accessible
   STATUS     mandatory
   DESCRIPTION
     "*** THIS TABLE CURRENTLY NOT IMPLEMENTED ***

      This entry controls the addition and deletion of 
      mscAppnDluSscp components."
::= { mscAppnDluSscp 1 }

mscAppnDluSscpRowStatusEntry OBJECT-TYPE
   SYNTAX     MscAppnDluSscpRowStatusEntry
   ACCESS     not-accessible
   STATUS     mandatory
   DESCRIPTION
     "A single entry in the table represents a single 
      mscAppnDluSscp component."
   INDEX {
      mscAppnIndex,
      mscAppnDluIndex,
      mscAppnDluSscpIndex }
::= { mscAppnDluSscpRowStatusTable 1 }

MscAppnDluSscpRowStatusEntry ::= SEQUENCE {
   mscAppnDluSscpRowStatus
      RowStatus,
   mscAppnDluSscpComponentName
      DisplayString,
   mscAppnDluSscpStorageType
      StorageType,
   mscAppnDluSscpIndex
      NonReplicated }

mscAppnDluSscpRowStatus OBJECT-TYPE
   SYNTAX     RowStatus 
   ACCESS     read-only
   STATUS     mandatory
   DESCRIPTION
     "This variable is used as the basis for SNMP naming of
      mscAppnDluSscp components.
      These components cannot be added nor deleted."
::= { mscAppnDluSscpRowStatusEntry 1 }

mscAppnDluSscpComponentName OBJECT-TYPE
   SYNTAX     DisplayString 
   ACCESS     read-only
   STATUS     mandatory
   DESCRIPTION
     "This variable provides the component's string name for
      use with the ASCII Console Interface"
::= { mscAppnDluSscpRowStatusEntry 2 }

mscAppnDluSscpStorageType OBJECT-TYPE
   SYNTAX     StorageType 
   ACCESS     read-only
   STATUS     mandatory
   DESCRIPTION
     "This variable represents the storage type value for the
      mscAppnDluSscp tables."
::= { mscAppnDluSscpRowStatusEntry 4 }

mscAppnDluSscpIndex OBJECT-TYPE
   SYNTAX     NonReplicated 
   ACCESS     not-accessible
   STATUS     mandatory
   DESCRIPTION
     "This variable represents the index for the mscAppnDluSscp tables."
::= { mscAppnDluSscpRowStatusEntry 10 }

mscAppnDluSscpStatsTable OBJECT-TYPE
   SYNTAX     SEQUENCE OF MscAppnDluSscpStatsEntry
   ACCESS     not-accessible
   STATUS     mandatory
   DESCRIPTION
     "*** THIS TABLE CURRENTLY NOT IMPLEMENTED ***

      This component contains counters and statistics for a session."
::= { mscAppnDluSscp 10 }

mscAppnDluSscpStatsEntry OBJECT-TYPE
   SYNTAX     MscAppnDluSscpStatsEntry
   ACCESS     not-accessible
   STATUS     mandatory
   DESCRIPTION
     "An entry in the mscAppnDluSscpStatsTable."
   INDEX {
      mscAppnIndex,
      mscAppnDluIndex,
      mscAppnDluSscpIndex }
::= { mscAppnDluSscpStatsTable 1 }

MscAppnDluSscpStatsEntry ::= SEQUENCE {
   mscAppnDluSscpRxRuSize
      Unsigned32,
   mscAppnDluSscpMaxTxBtuSize
      Unsigned32,
   mscAppnDluSscpMaxRxBtuSize
      Unsigned32,
   mscAppnDluSscpMaxTxPacWin
      INTEGER,
   mscAppnDluSscpCurTxPacWin
      INTEGER,
   mscAppnDluSscpMaxRxPacWin
      INTEGER,
   mscAppnDluSscpCurRxPacWin
      INTEGER,
   mscAppnDluSscpTxDataframes
      PassportCounter64,
   mscAppnDluSscpTxFmdFrames
      PassportCounter64,
   mscAppnDluSscpTxDataBytes
      PassportCounter64,
   mscAppnDluSscpRxDataFrames
      PassportCounter64,
   mscAppnDluSscpRxFmdFrames
      PassportCounter64,
   mscAppnDluSscpRxDataBytes
      PassportCounter64,
   mscAppnDluSscpSidh
      Hex,
   mscAppnDluSscpSidl
      Hex,
   mscAppnDluSscpOdai
      INTEGER,
   mscAppnDluSscpLsName
      AsciiString }

mscAppnDluSscpRxRuSize OBJECT-TYPE
   SYNTAX     Unsigned32 (0..65535)
   ACCESS     read-only
   STATUS     mandatory
   DESCRIPTION
     "This is the maximum request unit (RU) size that can be used on the 
      session."
::= { mscAppnDluSscpStatsEntry 1 }

mscAppnDluSscpMaxTxBtuSize OBJECT-TYPE
   SYNTAX     Unsigned32 (0..65535)
   ACCESS     read-only
   STATUS     mandatory
   DESCRIPTION
     "This is the maximum BTU size (length of the information field in a 
      frame) that can be sent on the session."
::= { mscAppnDluSscpStatsEntry 2 }

mscAppnDluSscpMaxRxBtuSize OBJECT-TYPE
   SYNTAX     Unsigned32 (0..65535)
   ACCESS     read-only
   STATUS     mandatory
   DESCRIPTION
     "This is the maximum BTU size (length of the information field in a 
      frame) that can be received on the session."
::= { mscAppnDluSscpStatsEntry 3 }

mscAppnDluSscpMaxTxPacWin OBJECT-TYPE
   SYNTAX     INTEGER (0..32767)
   ACCESS     read-only
   STATUS     mandatory
   DESCRIPTION
     "This is the maximum size of the send pacing window on the  
      session."
::= { mscAppnDluSscpStatsEntry 4 }

mscAppnDluSscpCurTxPacWin OBJECT-TYPE
   SYNTAX     INTEGER (0..32767)
   ACCESS     read-only
   STATUS     mandatory
   DESCRIPTION
     "This is the current size of the send pacing window on the session."
::= { mscAppnDluSscpStatsEntry 5 }

mscAppnDluSscpMaxRxPacWin OBJECT-TYPE
   SYNTAX     INTEGER (0..32767)
   ACCESS     read-only
   STATUS     mandatory
   DESCRIPTION
     "This is the maximum size of the receive pacing window on the 
      session."
::= { mscAppnDluSscpStatsEntry 6 }

mscAppnDluSscpCurRxPacWin OBJECT-TYPE
   SYNTAX     INTEGER (0..32767)
   ACCESS     read-only
   STATUS     mandatory
   DESCRIPTION
     "This is the current size of the receive pacing window on the  
      session."
::= { mscAppnDluSscpStatsEntry 7 }

mscAppnDluSscpTxDataframes OBJECT-TYPE
   SYNTAX     PassportCounter64 
   ACCESS     read-only
   STATUS     mandatory
   DESCRIPTION
     "This attribute counts the number of normal flow data frames sent 
      on the session, the counter wraps to zero."
::= { mscAppnDluSscpStatsEntry 8 }

mscAppnDluSscpTxFmdFrames OBJECT-TYPE
   SYNTAX     PassportCounter64 
   ACCESS     read-only
   STATUS     mandatory
   DESCRIPTION
     "This attribute counts the number of FMD data frames sent on the 
      session, the counter wraps to zero."
::= { mscAppnDluSscpStatsEntry 9 }

mscAppnDluSscpTxDataBytes OBJECT-TYPE
   SYNTAX     PassportCounter64 
   ACCESS     read-only
   STATUS     mandatory
   DESCRIPTION
     "This is the number of normal flow data bytes sent on the session, 
      the counter wraps to zero."
::= { mscAppnDluSscpStatsEntry 10 }

mscAppnDluSscpRxDataFrames OBJECT-TYPE
   SYNTAX     PassportCounter64 
   ACCESS     read-only
   STATUS     mandatory
   DESCRIPTION
     "This is the number of normal flow data frames received on the 
      session, the counter wraps to zero."
::= { mscAppnDluSscpStatsEntry 11 }

mscAppnDluSscpRxFmdFrames OBJECT-TYPE
   SYNTAX     PassportCounter64 
   ACCESS     read-only
   STATUS     mandatory
   DESCRIPTION
     "This attribute counts the number of FMD data frames received on 
      the session, the counter wraps to zero."
::= { mscAppnDluSscpStatsEntry 12 }

mscAppnDluSscpRxDataBytes OBJECT-TYPE
   SYNTAX     PassportCounter64 
   ACCESS     read-only
   STATUS     mandatory
   DESCRIPTION
     "This is the number of normal flow data bytes received on the 
      session, the counter wraps to zero."
::= { mscAppnDluSscpStatsEntry 13 }

mscAppnDluSscpSidh OBJECT-TYPE
   SYNTAX     Hex (0..255)
   ACCESS     read-only
   STATUS     mandatory
   DESCRIPTION
     "This attribute contains the session identifier high byte on the 
      session."
::= { mscAppnDluSscpStatsEntry 14 }

mscAppnDluSscpSidl OBJECT-TYPE
   SYNTAX     Hex (0..255)
   ACCESS     read-only
   STATUS     mandatory
   DESCRIPTION
     "This attribute contains the session ID low byte on the SSCP session."
::= { mscAppnDluSscpStatsEntry 15 }

mscAppnDluSscpOdai OBJECT-TYPE
   SYNTAX     INTEGER  {
                 primary(0),
                 secondary(1) }
   ACCESS     read-only
   STATUS     mandatory
   DESCRIPTION
     "This is the origin destination assignor indicator (ODAI) on the 
      session."
::= { mscAppnDluSscpStatsEntry 16 }

mscAppnDluSscpLsName OBJECT-TYPE
   SYNTAX     AsciiString (SIZE (1..8))
   ACCESS     read-only
   STATUS     mandatory
   DESCRIPTION
     "This is the link station name associated with these counters and 
      statistics. This is an 8 character name of the link station over which 
      the data flowed. This field can be used to correlate the session 
      statistics with the link over which session data flows."
::= { mscAppnDluSscpStatsEntry 17 }

-- 
-- *** THIS SUBTREE CURRENTLY NOT IMPLEMENTED ***
-- 

-- Appn/<string> Dlu/<string> UsStat
-- This is a dynamic component which contains counters and other 
-- statistical data for the upstream portion of the host application to 
-- dependent LU session.

mscAppnDluUsStat OBJECT IDENTIFIER ::= { mscAppnDlu 101 }



mscAppnDluUsStatRowStatusTable OBJECT-TYPE
   SYNTAX     SEQUENCE OF MscAppnDluUsStatRowStatusEntry
   ACCESS     not-accessible
   STATUS     mandatory
   DESCRIPTION
     "*** THIS TABLE CURRENTLY NOT IMPLEMENTED ***

      This entry controls the addition and deletion of 
      mscAppnDluUsStat components."
::= { mscAppnDluUsStat 1 }

mscAppnDluUsStatRowStatusEntry OBJECT-TYPE
   SYNTAX     MscAppnDluUsStatRowStatusEntry
   ACCESS     not-accessible
   STATUS     mandatory
   DESCRIPTION
     "A single entry in the table represents a single 
      mscAppnDluUsStat component."
   INDEX {
      mscAppnIndex,
      mscAppnDluIndex,
      mscAppnDluUsStatIndex }
::= { mscAppnDluUsStatRowStatusTable 1 }

MscAppnDluUsStatRowStatusEntry ::= SEQUENCE {
   mscAppnDluUsStatRowStatus
      RowStatus,
   mscAppnDluUsStatComponentName
      DisplayString,
   mscAppnDluUsStatStorageType
      StorageType,
   mscAppnDluUsStatIndex
      NonReplicated }

mscAppnDluUsStatRowStatus OBJECT-TYPE
   SYNTAX     RowStatus 
   ACCESS     read-only
   STATUS     mandatory
   DESCRIPTION
     "This variable is used as the basis for SNMP naming of
      mscAppnDluUsStat components.
      These components cannot be added nor deleted."
::= { mscAppnDluUsStatRowStatusEntry 1 }

mscAppnDluUsStatComponentName OBJECT-TYPE
   SYNTAX     DisplayString 
   ACCESS     read-only
   STATUS     mandatory
   DESCRIPTION
     "This variable provides the component's string name for
      use with the ASCII Console Interface"
::= { mscAppnDluUsStatRowStatusEntry 2 }

mscAppnDluUsStatStorageType OBJECT-TYPE
   SYNTAX     StorageType 
   ACCESS     read-only
   STATUS     mandatory
   DESCRIPTION
     "This variable represents the storage type value for the
      mscAppnDluUsStat tables."
::= { mscAppnDluUsStatRowStatusEntry 4 }

mscAppnDluUsStatIndex OBJECT-TYPE
   SYNTAX     NonReplicated 
   ACCESS     not-accessible
   STATUS     mandatory
   DESCRIPTION
     "This variable represents the index for the mscAppnDluUsStat tables."
::= { mscAppnDluUsStatRowStatusEntry 10 }

mscAppnDluUsStatStatsTable OBJECT-TYPE
   SYNTAX     SEQUENCE OF MscAppnDluUsStatStatsEntry
   ACCESS     not-accessible
   STATUS     mandatory
   DESCRIPTION
     "*** THIS TABLE CURRENTLY NOT IMPLEMENTED ***

      This component contains counters and statistics for a session."
::= { mscAppnDluUsStat 10 }

mscAppnDluUsStatStatsEntry OBJECT-TYPE
   SYNTAX     MscAppnDluUsStatStatsEntry
   ACCESS     not-accessible
   STATUS     mandatory
   DESCRIPTION
     "An entry in the mscAppnDluUsStatStatsTable."
   INDEX {
      mscAppnIndex,
      mscAppnDluIndex,
      mscAppnDluUsStatIndex }
::= { mscAppnDluUsStatStatsTable 1 }

MscAppnDluUsStatStatsEntry ::= SEQUENCE {
   mscAppnDluUsStatRxRuSize
      Unsigned32,
   mscAppnDluUsStatMaxTxBtuSize
      Unsigned32,
   mscAppnDluUsStatMaxRxBtuSize
      Unsigned32,
   mscAppnDluUsStatMaxTxPacWin
      INTEGER,
   mscAppnDluUsStatCurTxPacWin
      INTEGER,
   mscAppnDluUsStatMaxRxPacWin
      INTEGER,
   mscAppnDluUsStatCurRxPacWin
      INTEGER,
   mscAppnDluUsStatTxDataframes
      PassportCounter64,
   mscAppnDluUsStatTxFmdFrames
      PassportCounter64,
   mscAppnDluUsStatTxDataBytes
      PassportCounter64,
   mscAppnDluUsStatRxDataFrames
      PassportCounter64,
   mscAppnDluUsStatRxFmdFrames
      PassportCounter64,
   mscAppnDluUsStatRxDataBytes
      PassportCounter64,
   mscAppnDluUsStatSidh
      Hex,
   mscAppnDluUsStatSidl
      Hex,
   mscAppnDluUsStatOdai
      INTEGER,
   mscAppnDluUsStatLsName
      AsciiString }

mscAppnDluUsStatRxRuSize OBJECT-TYPE
   SYNTAX     Unsigned32 (0..65535)
   ACCESS     read-only
   STATUS     mandatory
   DESCRIPTION
     "This is the maximum request unit (RU) size that can be used on the 
      session."
::= { mscAppnDluUsStatStatsEntry 1 }

mscAppnDluUsStatMaxTxBtuSize OBJECT-TYPE
   SYNTAX     Unsigned32 (0..65535)
   ACCESS     read-only
   STATUS     mandatory
   DESCRIPTION
     "This is the maximum BTU size (length of the information field in a 
      frame) that can be sent on the session."
::= { mscAppnDluUsStatStatsEntry 2 }

mscAppnDluUsStatMaxRxBtuSize OBJECT-TYPE
   SYNTAX     Unsigned32 (0..65535)
   ACCESS     read-only
   STATUS     mandatory
   DESCRIPTION
     "This is the maximum BTU size (length of the information field in a 
      frame) that can be received on the session."
::= { mscAppnDluUsStatStatsEntry 3 }

mscAppnDluUsStatMaxTxPacWin OBJECT-TYPE
   SYNTAX     INTEGER (0..32767)
   ACCESS     read-only
   STATUS     mandatory
   DESCRIPTION
     "This is the maximum size of the send pacing window on the  
      session."
::= { mscAppnDluUsStatStatsEntry 4 }

mscAppnDluUsStatCurTxPacWin OBJECT-TYPE
   SYNTAX     INTEGER (0..32767)
   ACCESS     read-only
   STATUS     mandatory
   DESCRIPTION
     "This is the current size of the send pacing window on the session."
::= { mscAppnDluUsStatStatsEntry 5 }

mscAppnDluUsStatMaxRxPacWin OBJECT-TYPE
   SYNTAX     INTEGER (0..32767)
   ACCESS     read-only
   STATUS     mandatory
   DESCRIPTION
     "This is the maximum size of the receive pacing window on the 
      session."
::= { mscAppnDluUsStatStatsEntry 6 }

mscAppnDluUsStatCurRxPacWin OBJECT-TYPE
   SYNTAX     INTEGER (0..32767)
   ACCESS     read-only
   STATUS     mandatory
   DESCRIPTION
     "This is the current size of the receive pacing window on the  
      session."
::= { mscAppnDluUsStatStatsEntry 7 }

mscAppnDluUsStatTxDataframes OBJECT-TYPE
   SYNTAX     PassportCounter64 
   ACCESS     read-only
   STATUS     mandatory
   DESCRIPTION
     "This attribute counts the number of normal flow data frames sent 
      on the session, the counter wraps to zero."
::= { mscAppnDluUsStatStatsEntry 8 }

mscAppnDluUsStatTxFmdFrames OBJECT-TYPE
   SYNTAX     PassportCounter64 
   ACCESS     read-only
   STATUS     mandatory
   DESCRIPTION
     "This attribute counts the number of FMD data frames sent on the 
      session, the counter wraps to zero."
::= { mscAppnDluUsStatStatsEntry 9 }

mscAppnDluUsStatTxDataBytes OBJECT-TYPE
   SYNTAX     PassportCounter64 
   ACCESS     read-only
   STATUS     mandatory
   DESCRIPTION
     "This is the number of normal flow data bytes sent on the session, 
      the counter wraps to zero."
::= { mscAppnDluUsStatStatsEntry 10 }

mscAppnDluUsStatRxDataFrames OBJECT-TYPE
   SYNTAX     PassportCounter64 
   ACCESS     read-only
   STATUS     mandatory
   DESCRIPTION
     "This is the number of normal flow data frames received on the 
      session, the counter wraps to zero."
::= { mscAppnDluUsStatStatsEntry 11 }

mscAppnDluUsStatRxFmdFrames OBJECT-TYPE
   SYNTAX     PassportCounter64 
   ACCESS     read-only
   STATUS     mandatory
   DESCRIPTION
     "This attribute counts the number of FMD data frames received on 
      the session, the counter wraps to zero."
::= { mscAppnDluUsStatStatsEntry 12 }

mscAppnDluUsStatRxDataBytes OBJECT-TYPE
   SYNTAX     PassportCounter64 
   ACCESS     read-only
   STATUS     mandatory
   DESCRIPTION
     "This is the number of normal flow data bytes received on the 
      session, the counter wraps to zero."
::= { mscAppnDluUsStatStatsEntry 13 }

mscAppnDluUsStatSidh OBJECT-TYPE
   SYNTAX     Hex (0..255)
   ACCESS     read-only
   STATUS     mandatory
   DESCRIPTION
     "This attribute contains the session identifier high byte on the 
      session."
::= { mscAppnDluUsStatStatsEntry 14 }

mscAppnDluUsStatSidl OBJECT-TYPE
   SYNTAX     Hex (0..255)
   ACCESS     read-only
   STATUS     mandatory
   DESCRIPTION
     "This attribute contains the session ID low byte on the SSCP session."
::= { mscAppnDluUsStatStatsEntry 15 }

mscAppnDluUsStatOdai OBJECT-TYPE
   SYNTAX     INTEGER  {
                 primary(0),
                 secondary(1) }
   ACCESS     read-only
   STATUS     mandatory
   DESCRIPTION
     "This is the origin destination assignor indicator (ODAI) on the 
      session."
::= { mscAppnDluUsStatStatsEntry 16 }

mscAppnDluUsStatLsName OBJECT-TYPE
   SYNTAX     AsciiString (SIZE (1..8))
   ACCESS     read-only
   STATUS     mandatory
   DESCRIPTION
     "This is the link station name associated with these counters and 
      statistics. This is an 8 character name of the link station over which 
      the data flowed. This field can be used to correlate the session 
      statistics with the link over which session data flows."
::= { mscAppnDluUsStatStatsEntry 17 }

-- 
-- *** THIS SUBTREE CURRENTLY NOT IMPLEMENTED ***
-- 

-- Appn/<string> Dlu/<string> DsStat
-- This is a dynamic component which contains counters and other 
-- statistical data for the downstream portion of the host application to 
-- dependent LU session.

mscAppnDluDsStat OBJECT IDENTIFIER ::= { mscAppnDlu 102 }



mscAppnDluDsStatRowStatusTable OBJECT-TYPE
   SYNTAX     SEQUENCE OF MscAppnDluDsStatRowStatusEntry
   ACCESS     not-accessible
   STATUS     mandatory
   DESCRIPTION
     "*** THIS TABLE CURRENTLY NOT IMPLEMENTED ***

      This entry controls the addition and deletion of 
      mscAppnDluDsStat components."
::= { mscAppnDluDsStat 1 }

mscAppnDluDsStatRowStatusEntry OBJECT-TYPE
   SYNTAX     MscAppnDluDsStatRowStatusEntry
   ACCESS     not-accessible
   STATUS     mandatory
   DESCRIPTION
     "A single entry in the table represents a single 
      mscAppnDluDsStat component."
   INDEX {
      mscAppnIndex,
      mscAppnDluIndex,
      mscAppnDluDsStatIndex }
::= { mscAppnDluDsStatRowStatusTable 1 }

MscAppnDluDsStatRowStatusEntry ::= SEQUENCE {
   mscAppnDluDsStatRowStatus
      RowStatus,
   mscAppnDluDsStatComponentName
      DisplayString,
   mscAppnDluDsStatStorageType
      StorageType,
   mscAppnDluDsStatIndex
      NonReplicated }

mscAppnDluDsStatRowStatus OBJECT-TYPE
   SYNTAX     RowStatus 
   ACCESS     read-only
   STATUS     mandatory
   DESCRIPTION
     "This variable is used as the basis for SNMP naming of
      mscAppnDluDsStat components.
      These components cannot be added nor deleted."
::= { mscAppnDluDsStatRowStatusEntry 1 }

mscAppnDluDsStatComponentName OBJECT-TYPE
   SYNTAX     DisplayString 
   ACCESS     read-only
   STATUS     mandatory
   DESCRIPTION
     "This variable provides the component's string name for
      use with the ASCII Console Interface"
::= { mscAppnDluDsStatRowStatusEntry 2 }

mscAppnDluDsStatStorageType OBJECT-TYPE
   SYNTAX     StorageType 
   ACCESS     read-only
   STATUS     mandatory
   DESCRIPTION
     "This variable represents the storage type value for the
      mscAppnDluDsStat tables."
::= { mscAppnDluDsStatRowStatusEntry 4 }

mscAppnDluDsStatIndex OBJECT-TYPE
   SYNTAX     NonReplicated 
   ACCESS     not-accessible
   STATUS     mandatory
   DESCRIPTION
     "This variable represents the index for the mscAppnDluDsStat tables."
::= { mscAppnDluDsStatRowStatusEntry 10 }

mscAppnDluDsStatStatsTable OBJECT-TYPE
   SYNTAX     SEQUENCE OF MscAppnDluDsStatStatsEntry
   ACCESS     not-accessible
   STATUS     mandatory
   DESCRIPTION
     "*** THIS TABLE CURRENTLY NOT IMPLEMENTED ***

      This component contains counters and statistics for a session."
::= { mscAppnDluDsStat 10 }

mscAppnDluDsStatStatsEntry OBJECT-TYPE
   SYNTAX     MscAppnDluDsStatStatsEntry
   ACCESS     not-accessible
   STATUS     mandatory
   DESCRIPTION
     "An entry in the mscAppnDluDsStatStatsTable."
   INDEX {
      mscAppnIndex,
      mscAppnDluIndex,
      mscAppnDluDsStatIndex }
::= { mscAppnDluDsStatStatsTable 1 }

MscAppnDluDsStatStatsEntry ::= SEQUENCE {
   mscAppnDluDsStatRxRuSize
      Unsigned32,
   mscAppnDluDsStatMaxTxBtuSize
      Unsigned32,
   mscAppnDluDsStatMaxRxBtuSize
      Unsigned32,
   mscAppnDluDsStatMaxTxPacWin
      INTEGER,
   mscAppnDluDsStatCurTxPacWin
      INTEGER,
   mscAppnDluDsStatMaxRxPacWin
      INTEGER,
   mscAppnDluDsStatCurRxPacWin
      INTEGER,
   mscAppnDluDsStatTxDataframes
      PassportCounter64,
   mscAppnDluDsStatTxFmdFrames
      PassportCounter64,
   mscAppnDluDsStatTxDataBytes
      PassportCounter64,
   mscAppnDluDsStatRxDataFrames
      PassportCounter64,
   mscAppnDluDsStatRxFmdFrames
      PassportCounter64,
   mscAppnDluDsStatRxDataBytes
      PassportCounter64,
   mscAppnDluDsStatSidh
      Hex,
   mscAppnDluDsStatSidl
      Hex,
   mscAppnDluDsStatOdai
      INTEGER,
   mscAppnDluDsStatLsName
      AsciiString }

mscAppnDluDsStatRxRuSize OBJECT-TYPE
   SYNTAX     Unsigned32 (0..65535)
   ACCESS     read-only
   STATUS     mandatory
   DESCRIPTION
     "This is the maximum request unit (RU) size that can be used on the 
      session."
::= { mscAppnDluDsStatStatsEntry 1 }

mscAppnDluDsStatMaxTxBtuSize OBJECT-TYPE
   SYNTAX     Unsigned32 (0..65535)
   ACCESS     read-only
   STATUS     mandatory
   DESCRIPTION
     "This is the maximum BTU size (length of the information field in a 
      frame) that can be sent on the session."
::= { mscAppnDluDsStatStatsEntry 2 }

mscAppnDluDsStatMaxRxBtuSize OBJECT-TYPE
   SYNTAX     Unsigned32 (0..65535)
   ACCESS     read-only
   STATUS     mandatory
   DESCRIPTION
     "This is the maximum BTU size (length of the information field in a 
      frame) that can be received on the session."
::= { mscAppnDluDsStatStatsEntry 3 }

mscAppnDluDsStatMaxTxPacWin OBJECT-TYPE
   SYNTAX     INTEGER (0..32767)
   ACCESS     read-only
   STATUS     mandatory
   DESCRIPTION
     "This is the maximum size of the send pacing window on the  
      session."
::= { mscAppnDluDsStatStatsEntry 4 }

mscAppnDluDsStatCurTxPacWin OBJECT-TYPE
   SYNTAX     INTEGER (0..32767)
   ACCESS     read-only
   STATUS     mandatory
   DESCRIPTION
     "This is the current size of the send pacing window on the session."
::= { mscAppnDluDsStatStatsEntry 5 }

mscAppnDluDsStatMaxRxPacWin OBJECT-TYPE
   SYNTAX     INTEGER (0..32767)
   ACCESS     read-only
   STATUS     mandatory
   DESCRIPTION
     "This is the maximum size of the receive pacing window on the 
      session."
::= { mscAppnDluDsStatStatsEntry 6 }

mscAppnDluDsStatCurRxPacWin OBJECT-TYPE
   SYNTAX     INTEGER (0..32767)
   ACCESS     read-only
   STATUS     mandatory
   DESCRIPTION
     "This is the current size of the receive pacing window on the  
      session."
::= { mscAppnDluDsStatStatsEntry 7 }

mscAppnDluDsStatTxDataframes OBJECT-TYPE
   SYNTAX     PassportCounter64 
   ACCESS     read-only
   STATUS     mandatory
   DESCRIPTION
     "This attribute counts the number of normal flow data frames sent 
      on the session, the counter wraps to zero."
::= { mscAppnDluDsStatStatsEntry 8 }

mscAppnDluDsStatTxFmdFrames OBJECT-TYPE
   SYNTAX     PassportCounter64 
   ACCESS     read-only
   STATUS     mandatory
   DESCRIPTION
     "This attribute counts the number of FMD data frames sent on the 
      session, the counter wraps to zero."
::= { mscAppnDluDsStatStatsEntry 9 }

mscAppnDluDsStatTxDataBytes OBJECT-TYPE
   SYNTAX     PassportCounter64 
   ACCESS     read-only
   STATUS     mandatory
   DESCRIPTION
     "This is the number of normal flow data bytes sent on the session, 
      the counter wraps to zero."
::= { mscAppnDluDsStatStatsEntry 10 }

mscAppnDluDsStatRxDataFrames OBJECT-TYPE
   SYNTAX     PassportCounter64 
   ACCESS     read-only
   STATUS     mandatory
   DESCRIPTION
     "This is the number of normal flow data frames received on the 
      session, the counter wraps to zero."
::= { mscAppnDluDsStatStatsEntry 11 }

mscAppnDluDsStatRxFmdFrames OBJECT-TYPE
   SYNTAX     PassportCounter64 
   ACCESS     read-only
   STATUS     mandatory
   DESCRIPTION
     "This attribute counts the number of FMD data frames received on 
      the session, the counter wraps to zero."
::= { mscAppnDluDsStatStatsEntry 12 }

mscAppnDluDsStatRxDataBytes OBJECT-TYPE
   SYNTAX     PassportCounter64 
   ACCESS     read-only
   STATUS     mandatory
   DESCRIPTION
     "This is the number of normal flow data bytes received on the 
      session, the counter wraps to zero."
::= { mscAppnDluDsStatStatsEntry 13 }

mscAppnDluDsStatSidh OBJECT-TYPE
   SYNTAX     Hex (0..255)
   ACCESS     read-only
   STATUS     mandatory
   DESCRIPTION
     "This attribute contains the session identifier high byte on the 
      session."
::= { mscAppnDluDsStatStatsEntry 14 }

mscAppnDluDsStatSidl OBJECT-TYPE
   SYNTAX     Hex (0..255)
   ACCESS     read-only
   STATUS     mandatory
   DESCRIPTION
     "This attribute contains the session ID low byte on the SSCP session."
::= { mscAppnDluDsStatStatsEntry 15 }

mscAppnDluDsStatOdai OBJECT-TYPE
   SYNTAX     INTEGER  {
                 primary(0),
                 secondary(1) }
   ACCESS     read-only
   STATUS     mandatory
   DESCRIPTION
     "This is the origin destination assignor indicator (ODAI) on the 
      session."
::= { mscAppnDluDsStatStatsEntry 16 }

mscAppnDluDsStatLsName OBJECT-TYPE
   SYNTAX     AsciiString (SIZE (1..8))
   ACCESS     read-only
   STATUS     mandatory
   DESCRIPTION
     "This is the link station name associated with these counters and 
      statistics. This is an 8 character name of the link station over which 
      the data flowed. This field can be used to correlate the session 
      statistics with the link over which session data flows."
::= { mscAppnDluDsStatStatsEntry 17 }

-- 
-- *** THIS SUBTREE CURRENTLY NOT IMPLEMENTED ***
-- 

-- Appn/<string> Dlus/<string>
-- This is a dynamic component which contains information about the 
-- dependent logical unit (LU) requestor - dependent LU server 
-- (DLUR-DLUS) pipes.
-- The instance value is the name of the DLUS logical unit.

mscAppnDlus OBJECT IDENTIFIER ::= { mscAppn 15 }



mscAppnDlusRowStatusTable OBJECT-TYPE
   SYNTAX     SEQUENCE OF MscAppnDlusRowStatusEntry
   ACCESS     not-accessible
   STATUS     mandatory
   DESCRIPTION
     "*** THIS TABLE CURRENTLY NOT IMPLEMENTED ***

      This entry controls the addition and deletion of 
      mscAppnDlus components."
::= { mscAppnDlus 1 }

mscAppnDlusRowStatusEntry OBJECT-TYPE
   SYNTAX     MscAppnDlusRowStatusEntry
   ACCESS     not-accessible
   STATUS     mandatory
   DESCRIPTION
     "A single entry in the table represents a single 
      mscAppnDlus component."
   INDEX {
      mscAppnIndex,
      mscAppnDlusIndex }
::= { mscAppnDlusRowStatusTable 1 }

MscAppnDlusRowStatusEntry ::= SEQUENCE {
   mscAppnDlusRowStatus
      RowStatus,
   mscAppnDlusComponentName
      DisplayString,
   mscAppnDlusStorageType
      StorageType,
   mscAppnDlusIndex
      AsciiStringIndex }

mscAppnDlusRowStatus OBJECT-TYPE
   SYNTAX     RowStatus 
   ACCESS     read-only
   STATUS     mandatory
   DESCRIPTION
     "This variable is used as the basis for SNMP naming of
      mscAppnDlus components.
      These components cannot be added nor deleted."
::= { mscAppnDlusRowStatusEntry 1 }

mscAppnDlusComponentName OBJECT-TYPE
   SYNTAX     DisplayString 
   ACCESS     read-only
   STATUS     mandatory
   DESCRIPTION
     "This variable provides the component's string name for
      use with the ASCII Console Interface"
::= { mscAppnDlusRowStatusEntry 2 }

mscAppnDlusStorageType OBJECT-TYPE
   SYNTAX     StorageType 
   ACCESS     read-only
   STATUS     mandatory
   DESCRIPTION
     "This variable represents the storage type value for the
      mscAppnDlus tables."
::= { mscAppnDlusRowStatusEntry 4 }

mscAppnDlusIndex OBJECT-TYPE
   SYNTAX     AsciiStringIndex (SIZE (1..17))
   ACCESS     not-accessible
   STATUS     mandatory
   DESCRIPTION
     "This variable represents the index for the mscAppnDlus tables."
::= { mscAppnDlusRowStatusEntry 10 }

mscAppnDlusOperTable OBJECT-TYPE
   SYNTAX     SEQUENCE OF MscAppnDlusOperEntry
   ACCESS     not-accessible
   STATUS     mandatory
   DESCRIPTION
     "*** THIS TABLE CURRENTLY NOT IMPLEMENTED ***

      Information on the DLUR-DLUS pipe."
::= { mscAppnDlus 10 }

mscAppnDlusOperEntry OBJECT-TYPE
   SYNTAX     MscAppnDlusOperEntry
   ACCESS     not-accessible
   STATUS     mandatory
   DESCRIPTION
     "An entry in the mscAppnDlusOperTable."
   INDEX {
      mscAppnIndex,
      mscAppnDlusIndex }
::= { mscAppnDlusOperTable 1 }

MscAppnDlusOperEntry ::= SEQUENCE {
   mscAppnDlusPrimaryDlus
      INTEGER,
   mscAppnDlusPipeState
      INTEGER,
   mscAppnDlusActivePUs
      Gauge32 }

mscAppnDlusPrimaryDlus OBJECT-TYPE
   SYNTAX     INTEGER  {
                 no(0),
                 yes(1) }
   ACCESS     read-only
   STATUS     mandatory
   DESCRIPTION
     "This attribute indicates if this is the pipe to the primary default 
      dependent LU server."
::= { mscAppnDlusOperEntry 1 }

mscAppnDlusPipeState OBJECT-TYPE
   SYNTAX     INTEGER  {
                 inactive(0),
                 pendingActive(1),
                 active(2),
                 pendingInactive(3) }
   ACCESS     read-only
   STATUS     mandatory
   DESCRIPTION
     "This attribute indicates the current state of the DLUR-DLUS pipe. 
      inactive indicates the pipe is not connected (the session has likely 
      failed), pendingActive indicates the pipe is connecting, active 
      indicates the pipe is currently connected and data is flowing, and 
      pendingInactive indicates the pipe is being disconnected."
::= { mscAppnDlusOperEntry 2 }

mscAppnDlusActivePUs OBJECT-TYPE
   SYNTAX     Gauge32 (0..32767)
   ACCESS     read-only
   STATUS     mandatory
   DESCRIPTION
     "This attribute indicates the number of active physical units using the 
      pipe."
::= { mscAppnDlusOperEntry 3 }

mscAppnDlusDlusStatTable OBJECT-TYPE
   SYNTAX     SEQUENCE OF MscAppnDlusDlusStatEntry
   ACCESS     not-accessible
   STATUS     mandatory
   DESCRIPTION
     "*** THIS TABLE CURRENTLY NOT IMPLEMENTED ***

      This group contains the counters and statistics for the DLUR-DLUS 
      pipe"
::= { mscAppnDlus 11 }

mscAppnDlusDlusStatEntry OBJECT-TYPE
   SYNTAX     MscAppnDlusDlusStatEntry
   ACCESS     not-accessible
   STATUS     mandatory
   DESCRIPTION
     "An entry in the mscAppnDlusDlusStatTable."
   INDEX {
      mscAppnIndex,
      mscAppnDlusIndex }
::= { mscAppnDlusDlusStatTable 1 }

MscAppnDlusDlusStatEntry ::= SEQUENCE {
   mscAppnDlusReqActPuTx
      PassportCounter64,
   mscAppnDlusReqActPuRspRx
      PassportCounter64,
   mscAppnDlusActPuRx
      PassportCounter64,
   mscAppnDlusActPuRspTx
      PassportCounter64,
   mscAppnDlusReqDactPuTx
      PassportCounter64,
   mscAppnDlusReqDactPuRspRx
      PassportCounter64,
   mscAppnDlusDactPuRx
      PassportCounter64,
   mscAppnDlusDactPuRspTx
      PassportCounter64,
   mscAppnDlusActLuRx
      PassportCounter64,
   mscAppnDlusActLuRspTx
      PassportCounter64,
   mscAppnDlusDactLuRx
      PassportCounter64,
   mscAppnDlusDactLuRspTx
      PassportCounter64,
   mscAppnDlusSscpPuMuRx
      PassportCounter64,
   mscAppnDlusSscpPuMuTx
      PassportCounter64,
   mscAppnDlusSscpLuMuRx
      PassportCounter64,
   mscAppnDlusSscpLuMuTx
      PassportCounter64 }

mscAppnDlusReqActPuTx OBJECT-TYPE
   SYNTAX     PassportCounter64 
   ACCESS     read-only
   STATUS     mandatory
   DESCRIPTION
     "This attribute counts the number of REQACTPUs sent to the 
      DLUS. The counter wraps to zero."
::= { mscAppnDlusDlusStatEntry 1 }

mscAppnDlusReqActPuRspRx OBJECT-TYPE
   SYNTAX     PassportCounter64 
   ACCESS     read-only
   STATUS     mandatory
   DESCRIPTION
     "This attribute counts the number of REQACTPU responses received 
      from the DLUS. The counter wraps to zero."
::= { mscAppnDlusDlusStatEntry 2 }

mscAppnDlusActPuRx OBJECT-TYPE
   SYNTAX     PassportCounter64 
   ACCESS     read-only
   STATUS     mandatory
   DESCRIPTION
     "This attributes counts the number of ACTPUs received from the 
      DLUS. The counter wraps to zero."
::= { mscAppnDlusDlusStatEntry 3 }

mscAppnDlusActPuRspTx OBJECT-TYPE
   SYNTAX     PassportCounter64 
   ACCESS     read-only
   STATUS     mandatory
   DESCRIPTION
     "This attribute counts the number of ACTPU responses sent to the 
      DLUS. The counter wraps to zero."
::= { mscAppnDlusDlusStatEntry 4 }

mscAppnDlusReqDactPuTx OBJECT-TYPE
   SYNTAX     PassportCounter64 
   ACCESS     read-only
   STATUS     mandatory
   DESCRIPTION
     "This attribute counts the number of REQDACTPUs sent to the 
      DLUS. The counter wraps to zero."
::= { mscAppnDlusDlusStatEntry 5 }

mscAppnDlusReqDactPuRspRx OBJECT-TYPE
   SYNTAX     PassportCounter64 
   ACCESS     read-only
   STATUS     mandatory
   DESCRIPTION
     "This attribute counts the number of REQDACTPU responses 
      received from the DLUS. The counter wraps to zero."
::= { mscAppnDlusDlusStatEntry 6 }

mscAppnDlusDactPuRx OBJECT-TYPE
   SYNTAX     PassportCounter64 
   ACCESS     read-only
   STATUS     mandatory
   DESCRIPTION
     "This attribute counts the number of DACTPUs received from the 
      DLUS. The counter wraps to zero."
::= { mscAppnDlusDlusStatEntry 7 }

mscAppnDlusDactPuRspTx OBJECT-TYPE
   SYNTAX     PassportCounter64 
   ACCESS     read-only
   STATUS     mandatory
   DESCRIPTION
     "This attribute counts the number of DACTPU responses received 
      from the DLUS. The counter wraps to zero."
::= { mscAppnDlusDlusStatEntry 8 }

mscAppnDlusActLuRx OBJECT-TYPE
   SYNTAX     PassportCounter64 
   ACCESS     read-only
   STATUS     mandatory
   DESCRIPTION
     "This attribute counts the number of ACTLUs received from the 
      DLUS. The counter wraps to zero."
::= { mscAppnDlusDlusStatEntry 9 }

mscAppnDlusActLuRspTx OBJECT-TYPE
   SYNTAX     PassportCounter64 
   ACCESS     read-only
   STATUS     mandatory
   DESCRIPTION
     "This attribute counts the number of ACTLU responses sent to the 
      DLUS. The counter wraps to zero."
::= { mscAppnDlusDlusStatEntry 10 }

mscAppnDlusDactLuRx OBJECT-TYPE
   SYNTAX     PassportCounter64 
   ACCESS     read-only
   STATUS     mandatory
   DESCRIPTION
     "This attribute counts the number of DACTLUs received from the 
      DLUS. The counter wraps to zero."
::= { mscAppnDlusDlusStatEntry 11 }

mscAppnDlusDactLuRspTx OBJECT-TYPE
   SYNTAX     PassportCounter64 
   ACCESS     read-only
   STATUS     mandatory
   DESCRIPTION
     "This attribute counts the number of DACTLU responses sent to the 
      DLUS. The counter wraps to zero."
::= { mscAppnDlusDlusStatEntry 12 }

mscAppnDlusSscpPuMuRx OBJECT-TYPE
   SYNTAX     PassportCounter64 
   ACCESS     read-only
   STATUS     mandatory
   DESCRIPTION
     "This attribute counts the number of SSCP-PU MUs received. The 
      counter wraps to zero."
::= { mscAppnDlusDlusStatEntry 13 }

mscAppnDlusSscpPuMuTx OBJECT-TYPE
   SYNTAX     PassportCounter64 
   ACCESS     read-only
   STATUS     mandatory
   DESCRIPTION
     "This attribute counts the number of SSCP-PU MUs sent. The 
      counter wraps to zero."
::= { mscAppnDlusDlusStatEntry 14 }

mscAppnDlusSscpLuMuRx OBJECT-TYPE
   SYNTAX     PassportCounter64 
   ACCESS     read-only
   STATUS     mandatory
   DESCRIPTION
     "This attributes counts the number of SSCP-LU MUs received. The 
      counter wraps to zero."
::= { mscAppnDlusDlusStatEntry 15 }

mscAppnDlusSscpLuMuTx OBJECT-TYPE
   SYNTAX     PassportCounter64 
   ACCESS     read-only
   STATUS     mandatory
   DESCRIPTION
     "This attributes counts the number of SSCP-LU MUs sent. The 
      counter wraps to zero."
::= { mscAppnDlusDlusStatEntry 16 }


-- Appn/<string> DLUR
-- This component defines the default parameters for the dependent 
-- logical unit requestor (DLUR).  If DLUR does not work after the 
-- parameters in this component are set, ensure that the DLUR support 
-- is turned on in the Appn component.

mscAppnDLUR OBJECT IDENTIFIER ::= { mscAppn 16 }



mscAppnDLURRowStatusTable OBJECT-TYPE
   SYNTAX     SEQUENCE OF MscAppnDLURRowStatusEntry
   ACCESS     not-accessible
   STATUS     mandatory
   DESCRIPTION
     "This entry controls the addition and deletion of 
      mscAppnDLUR components."
::= { mscAppnDLUR 1 }

mscAppnDLURRowStatusEntry OBJECT-TYPE
   SYNTAX     MscAppnDLURRowStatusEntry
   ACCESS     not-accessible
   STATUS     mandatory
   DESCRIPTION
     "A single entry in the table represents a single 
      mscAppnDLUR component."
   INDEX {
      mscAppnIndex,
      mscAppnDLURIndex }
::= { mscAppnDLURRowStatusTable 1 }

MscAppnDLURRowStatusEntry ::= SEQUENCE {
   mscAppnDLURRowStatus
      RowStatus,
   mscAppnDLURComponentName
      DisplayString,
   mscAppnDLURStorageType
      StorageType,
   mscAppnDLURIndex
      NonReplicated }

mscAppnDLURRowStatus OBJECT-TYPE
   SYNTAX     RowStatus 
   ACCESS     read-write
   STATUS     mandatory
   DESCRIPTION
     "This variable is used as the basis for SNMP naming of
      mscAppnDLUR components.
      These components can be added and deleted."
::= { mscAppnDLURRowStatusEntry 1 }

mscAppnDLURComponentName OBJECT-TYPE
   SYNTAX     DisplayString 
   ACCESS     read-only
   STATUS     mandatory
   DESCRIPTION
     "This variable provides the component's string name for
      use with the ASCII Console Interface"
::= { mscAppnDLURRowStatusEntry 2 }

mscAppnDLURStorageType OBJECT-TYPE
   SYNTAX     StorageType 
   ACCESS     read-only
   STATUS     mandatory
   DESCRIPTION
     "This variable represents the storage type value for the
      mscAppnDLUR tables."
::= { mscAppnDLURRowStatusEntry 4 }

mscAppnDLURIndex OBJECT-TYPE
   SYNTAX     NonReplicated 
   ACCESS     not-accessible
   STATUS     mandatory
   DESCRIPTION
     "This variable represents the index for the mscAppnDLUR tables."
::= { mscAppnDLURRowStatusEntry 10 }

mscAppnDLURDlurParmsTable OBJECT-TYPE
   SYNTAX     SEQUENCE OF MscAppnDLURDlurParmsEntry
   ACCESS     not-accessible
   STATUS     mandatory
   DESCRIPTION
     "These parameters define the dependent LU requester options."
::= { mscAppnDLUR 2 }

mscAppnDLURDlurParmsEntry OBJECT-TYPE
   SYNTAX     MscAppnDLURDlurParmsEntry
   ACCESS     not-accessible
   STATUS     mandatory
   DESCRIPTION
     "An entry in the mscAppnDLURDlurParmsTable."
   INDEX {
      mscAppnIndex,
      mscAppnDLURIndex }
::= { mscAppnDLURDlurParmsTable 1 }

MscAppnDLURDlurParmsEntry ::= SEQUENCE {
   mscAppnDLURPrimaryDefDlusName
      AsciiString,
   mscAppnDLURSecondaryDefDlusName
      AsciiString,
   mscAppnDLURDlusRetryTimeout
      Unsigned32,
   mscAppnDLURDlusRetryLimit
      Unsigned32 }

mscAppnDLURPrimaryDefDlusName OBJECT-TYPE
   SYNTAX     AsciiString (SIZE (3..17))
   ACCESS     read-write
   STATUS     mandatory
   DESCRIPTION
     "The fully qualified CP name of the node that will serve as the 
      primary dependent LU server (DLUS)."
::= { mscAppnDLURDlurParmsEntry 2 }

mscAppnDLURSecondaryDefDlusName OBJECT-TYPE
   SYNTAX     AsciiString (SIZE (0..17))
   ACCESS     read-write
   STATUS     mandatory
   DESCRIPTION
     "The fully qualified CP name of the node that will serve as the 
      backup or secondary dependent LU server (DLUS)."
::= { mscAppnDLURDlurParmsEntry 3 }

mscAppnDLURDlusRetryTimeout OBJECT-TYPE
   SYNTAX     Unsigned32 (1..65535)
   ACCESS     read-write
   STATUS     mandatory
   DESCRIPTION
     "This attribute specifies the time in seconds before a network search  
      to locate a DLUS times out."
   DEFVAL     { 5 }
::= { mscAppnDLURDlurParmsEntry 4 }

mscAppnDLURDlusRetryLimit OBJECT-TYPE
   SYNTAX     Unsigned32 (0..65535)
   ACCESS     read-write
   STATUS     mandatory
   DESCRIPTION
     "This attribute specifies the maximum number of retry attempts that 
      will be made after an initial failure to contact a DLUS. If zero is 
      specifed, APPN will retry indefinitely. When this limit has been 
      reached, downstream PUs that are connected to APPN will be sent a 
      QDISC frame."
   DEFVAL     { 0 }
::= { mscAppnDLURDlurParmsEntry 5 }


-- Appn/<string> Cos/<string>
-- This component defines the characteristics of a named class of 
-- service. A class of service contains information used in selecting a 
-- route and priority for a specific session. The class of service 
-- component requires at least one tgRow and one nodeRow 
-- subcomponent  to a  maximum of eight.
-- A default set of class of service entries is added with the following 
-- names: SNASVCMG, CPSVCMG, #CONNECT, #INTER, #I 
-- NTERSC, #BATCH, #BATCHSC. These class of service entries  
-- are not to be deleted.

mscAppnCos OBJECT IDENTIFIER ::= { mscAppn 17 }



mscAppnCosRowStatusTable OBJECT-TYPE
   SYNTAX     SEQUENCE OF MscAppnCosRowStatusEntry
   ACCESS     not-accessible
   STATUS     mandatory
   DESCRIPTION
     "This entry controls the addition and deletion of 
      mscAppnCos components."
::= { mscAppnCos 1 }

mscAppnCosRowStatusEntry OBJECT-TYPE
   SYNTAX     MscAppnCosRowStatusEntry
   ACCESS     not-accessible
   STATUS     mandatory
   DESCRIPTION
     "A single entry in the table represents a single 
      mscAppnCos component."
   INDEX {
      mscAppnIndex,
      mscAppnCosIndex }
::= { mscAppnCosRowStatusTable 1 }

MscAppnCosRowStatusEntry ::= SEQUENCE {
   mscAppnCosRowStatus
      RowStatus,
   mscAppnCosComponentName
      DisplayString,
   mscAppnCosStorageType
      StorageType,
   mscAppnCosIndex
      AsciiStringIndex }

mscAppnCosRowStatus OBJECT-TYPE
   SYNTAX     RowStatus 
   ACCESS     read-write
   STATUS     mandatory
   DESCRIPTION
     "This variable is used as the basis for SNMP naming of
      mscAppnCos components.
      These components can be added and deleted."
::= { mscAppnCosRowStatusEntry 1 }

mscAppnCosComponentName OBJECT-TYPE
   SYNTAX     DisplayString 
   ACCESS     read-only
   STATUS     mandatory
   DESCRIPTION
     "This variable provides the component's string name for
      use with the ASCII Console Interface"
::= { mscAppnCosRowStatusEntry 2 }

mscAppnCosStorageType OBJECT-TYPE
   SYNTAX     StorageType 
   ACCESS     read-only
   STATUS     mandatory
   DESCRIPTION
     "This variable represents the storage type value for the
      mscAppnCos tables."
::= { mscAppnCosRowStatusEntry 4 }

mscAppnCosIndex OBJECT-TYPE
   SYNTAX     AsciiStringIndex (SIZE (1..8))
   ACCESS     not-accessible
   STATUS     mandatory
   DESCRIPTION
     "This variable represents the index for the mscAppnCos tables."
::= { mscAppnCosRowStatusEntry 10 }

mscAppnCosProvTable OBJECT-TYPE
   SYNTAX     SEQUENCE OF MscAppnCosProvEntry
   ACCESS     not-accessible
   STATUS     mandatory
   DESCRIPTION
     "This provisioning group specifies the transmission priority 
      associated with a Class of Service."
::= { mscAppnCos 104 }

mscAppnCosProvEntry OBJECT-TYPE
   SYNTAX     MscAppnCosProvEntry
   ACCESS     not-accessible
   STATUS     mandatory
   DESCRIPTION
     "An entry in the mscAppnCosProvTable."
   INDEX {
      mscAppnIndex,
      mscAppnCosIndex }
::= { mscAppnCosProvTable 1 }

MscAppnCosProvEntry ::= SEQUENCE {
   mscAppnCosTransmissionPriority
      INTEGER }

mscAppnCosTransmissionPriority OBJECT-TYPE
   SYNTAX     INTEGER  {
                 low(1),
                 medium(2),
                 high(3),
                 network(4) }
   ACCESS     read-write
   STATUS     mandatory
   DESCRIPTION
     "This attribute specifies the transmission priority of session traffic 
      using this class of service."
   DEFVAL     { low }
::= { mscAppnCosProvEntry 1 }


-- Appn/<string> Cos/<string> TgRow/<weight>
-- This component specifies the allowable ranges for transmission 
-- group characteristics for a class of service. During route calculation, 
-- a transmission group is considered acceptable if all of the  actual 
-- TG characteristics of a link fall within the range of required TG 
-- characteristics for a COS. A TG is considered unacceptable if at 
-- least one of the actual TG characteristics falls outside the range of 
-- the required TG values. 

mscAppnCosTg OBJECT IDENTIFIER ::= { mscAppnCos 10 }



mscAppnCosTgRowStatusTable OBJECT-TYPE
   SYNTAX     SEQUENCE OF MscAppnCosTgRowStatusEntry
   ACCESS     not-accessible
   STATUS     mandatory
   DESCRIPTION
     "This entry controls the addition and deletion of 
      mscAppnCosTg components."
::= { mscAppnCosTg 1 }

mscAppnCosTgRowStatusEntry OBJECT-TYPE
   SYNTAX     MscAppnCosTgRowStatusEntry
   ACCESS     not-accessible
   STATUS     mandatory
   DESCRIPTION
     "A single entry in the table represents a single 
      mscAppnCosTg component."
   INDEX {
      mscAppnIndex,
      mscAppnCosIndex,
      mscAppnCosTgIndex }
::= { mscAppnCosTgRowStatusTable 1 }

MscAppnCosTgRowStatusEntry ::= SEQUENCE {
   mscAppnCosTgRowStatus
      RowStatus,
   mscAppnCosTgComponentName
      DisplayString,
   mscAppnCosTgStorageType
      StorageType,
   mscAppnCosTgIndex
      Integer32 }

mscAppnCosTgRowStatus OBJECT-TYPE
   SYNTAX     RowStatus 
   ACCESS     read-write
   STATUS     mandatory
   DESCRIPTION
     "This variable is used as the basis for SNMP naming of
      mscAppnCosTg components.
      These components can be added and deleted."
::= { mscAppnCosTgRowStatusEntry 1 }

mscAppnCosTgComponentName OBJECT-TYPE
   SYNTAX     DisplayString 
   ACCESS     read-only
   STATUS     mandatory
   DESCRIPTION
     "This variable provides the component's string name for
      use with the ASCII Console Interface"
::= { mscAppnCosTgRowStatusEntry 2 }

mscAppnCosTgStorageType OBJECT-TYPE
   SYNTAX     StorageType 
   ACCESS     read-only
   STATUS     mandatory
   DESCRIPTION
     "This variable represents the storage type value for the
      mscAppnCosTg tables."
::= { mscAppnCosTgRowStatusEntry 4 }

mscAppnCosTgIndex OBJECT-TYPE
   SYNTAX     Integer32 (1..255)
   ACCESS     not-accessible
   STATUS     mandatory
   DESCRIPTION
     "This variable represents the index for the mscAppnCosTg tables."
::= { mscAppnCosTgRowStatusEntry 10 }

mscAppnCosTgProvTable OBJECT-TYPE
   SYNTAX     SEQUENCE OF MscAppnCosTgProvEntry
   ACCESS     not-accessible
   STATUS     mandatory
   DESCRIPTION
     "This group specifies a range of TG characteristics for a class of 
      service and is used in route selection for session traffic. 
      
      During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session."
::= { mscAppnCosTg 10 }

mscAppnCosTgProvEntry OBJECT-TYPE
   SYNTAX     MscAppnCosTgProvEntry
   ACCESS     not-accessible
   STATUS     mandatory
   DESCRIPTION
     "An entry in the mscAppnCosTgProvTable."
   INDEX {
      mscAppnIndex,
      mscAppnCosIndex,
      mscAppnCosTgIndex }
::= { mscAppnCosTgProvTable 1 }

MscAppnCosTgProvEntry ::= SEQUENCE {
   mscAppnCosTgMinEffectiveCapacity
      INTEGER,
   mscAppnCosTgMaxEffectiveCapacity
      INTEGER,
   mscAppnCosTgMinConnectCost
      INTEGER,
   mscAppnCosTgMaxConnectCost
      INTEGER,
   mscAppnCosTgMinByteCost
      INTEGER,
   mscAppnCosTgMaxByteCost
      INTEGER,
   mscAppnCosTgMinSecurity
      INTEGER,
   mscAppnCosTgMaxSecurity
      INTEGER,
   mscAppnCosTgMinPropDelay
      INTEGER,
   mscAppnCosTgMaxPropDelay
      INTEGER,
   mscAppnCosTgMinModemClass
      INTEGER,
   mscAppnCosTgMaxModemClass
      INTEGER,
   mscAppnCosTgMinUserDefParm1
      INTEGER,
   mscAppnCosTgMaxUserDefParm1
      INTEGER,
   mscAppnCosTgMinUserDefParm2
      INTEGER,
   mscAppnCosTgMaxUserDefParm2
      INTEGER,
   mscAppnCosTgMinUserDefParm3
      INTEGER,
   mscAppnCosTgMaxUserDefParm3
      INTEGER }

mscAppnCosTgMinEffectiveCapacity OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 max(255) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      acceptable speed for a TG using this Class of Service."
   DEFVAL     { min }
::= { mscAppnCosTgProvEntry 1 }

mscAppnCosTgMaxEffectiveCapacity OBJECT-TYPE
   SYNTAX     INTEGER  {
                 min(0),
                 n170bps(1),
                 n190bps(2),
                 n210bps(3),
                 n230bps(4),
                 n240bps(5),
                 n260bps(6),
                 n280bps(7),
                 n300bps(8),
                 n340bps(9),
                 n380bps(10),
                 n410bps(11),
                 n450bps(12),
                 n490bps(13),
                 n530bps(14),
                 n560bps(15),
                 n600bps(16),
                 n680bps(17),
                 n750bps(18),
                 n830bps(19),
                 n900bps(20),
                 n980bps(21),
                 n1050bps(22),
                 n1130bps(23),
                 n1200bps(24),
                 n1350bps(25),
                 n1500bps(26),
                 n1700bps(27),
                 n1800bps(28),
                 n2000bps(29),
                 n2100bps(30),
                 n2300bps(31),
                 n2400bps(32),
                 n2700bps(33),
                 n3000bps(34),
                 n3300bps(35),
                 n3600bps(36),
                 n3900bps(37),
                 n4200bps(38),
                 n4500bps(39),
                 n4800bps(40),
                 n5400bps(41),
                 n6000bps(42),
                 n6600bps(43),
                 n7200bps(44),
                 n7800bps(45),
                 n8400bps(46),
                 n9000bps(47),
                 n9600bps(48),
                 n10800bps(49),
                 n12000bps(50),
                 n13200bps(51),
                 n14400bps(52),
                 n15600bps(53),
                 n17kbps(54),
                 n18kbps(55),
                 n19kbps(56),
                 n22kbps(57),
                 n24kbps(58),
                 n26kbps(59),
                 n29kbps(60),
                 n31kbps(61),
                 n34kbps(62),
                 n36kbps(63),
                 n38kbps(64),
                 n43kbps(65),
                 n48kbps(66),
                 n53kbps(67),
                 n58kbps(68),
                 n62kbps(69),
                 n67kbps(70),
                 n72kbps(71),
                 n77kbps(72),
                 n86kbps(73),
                 n96kbps(74),
                 n106kbps(75),
                 n115kbps(76),
                 n125kbps(77),
                 n134kbps(78),
                 n144kbps(79),
                 n154kbps(80),
                 n170kbps(81),
                 n190kbps(82),
                 n210kbps(83),
                 n230kbps(84),
                 n250kbps(85),
                 n270kbps(86),
                 n290kbps(87),
                 n310kbps(88),
                 n350kbps(89),
                 n380kbps(90),
                 n420kbps(91),
                 n460kbps(92),
                 n500kbps(93),
                 n540kbps(94),
                 n580kbps(95),
                 n610kbps(96),
                 n690kbps(97),
                 n770kbps(98),
                 n840kbps(99),
                 n920kbps(100),
                 n1000kbps(101),
                 n1080kbps(102),
                 n1150kbps(103),
                 n1230kbps(104),
                 n1380kbps(105),
                 n1540kbps(106),
                 n1700kbps(107),
                 n1800kbps(108),
                 n2000kbps(109),
                 n2200kbps(110),
                 n2300kbps(111),
                 n2500kbps(112),
                 n2800kbps(113),
                 n3100kbps(114),
                 n3400kbps(115),
                 n3700kbps(116),
                 n4000kbps(117),
                 n4300kbps(118),
                 n4600kbps(119),
                 n4900kbps(120),
                 n5500kbps(121),
                 n6100kbps(122),
                 n6800kbps(123),
                 n7400kbps(124),
                 n8000kbps(125),
                 n8600kbps(126),
                 n9200kbps(127),
                 n9800kbps(128),
                 n11100kbps(129),
                 n12300kbps(130),
                 n13500kbps(131),
                 n14700kbps(132),
                 n16Mbps(133),
                 n17Mbps(134),
                 n18Mbps(135),
                 n20Mbps(136),
                 n22Mbps(137),
                 n25Mbps(138),
                 n27Mbps(139),
                 n29Mbps(140),
                 n32Mbps(141),
                 n34Mbps(142),
                 n37Mbps(143),
                 n39Mbps(144),
                 n44Mbps(145),
                 n49Mbps(146),
                 n54Mbps(147),
                 n59Mbps(148),
                 n64Mbps(149),
                 n69Mbps(150),
                 n74Mbps(151),
                 n79Mbps(152),
                 n88Mbps(153),
                 n98Mbps(154),
                 n108Mbps(155),
                 n118Mbps(156),
                 n128Mbps(157),
                 n138Mbps(158),
                 n147Mbps(159),
                 n157Mbps(160),
                 n180Mbps(161),
                 n200Mbps(162),
                 n220Mbps(163),
                 n240Mbps(164),
                 n260Mbps(165),
                 n280Mbps(166),
                 n290Mbps(167),
                 n310Mbps(168),
                 n350Mbps(169),
                 n390Mbps(170),
                 n430Mbps(171),
                 n470Mbps(172),
                 n510Mbps(173),
                 n550Mbps(174),
                 n590Mbps(175),
                 n630Mbps(176),
                 n710Mbps(177),
                 n790Mbps(178),
                 n870Mbps(179),
                 n940Mbps(180),
                 n1020Mbps(181),
                 n1100Mbps(182),
                 n1180Mbps(183),
                 n1260Mbps(184),
                 n1420Mbps(185),
                 n1570Mbps(186),
                 n1700Mbps(187),
                 n1900Mbps(188),
                 n2000Mbps(189),
                 n2200Mbps(190),
                 n2400Mbps(191),
                 n2500Mbps(192),
                 n2800Mbps(193),
                 n3100Mbps(194),
                 n3500Mbps(195),
                 n3800Mbps(196),
                 n4100Mbps(197),
                 n4400Mbps(198),
                 n4700Mbps(199),
                 n5000Mbps(200),
                 n5700Mbps(201),
                 n6300Mbps(202),
                 n6900Mbps(203),
                 n7500Mbps(204),
                 n8200Mbps(205),
                 n8800Mbps(206),
                 n9400Mbps(207),
                 n10100Mbps(208),
                 n11300Mbps(209),
                 n12600Mbps(210),
                 n13800Mbps(211),
                 n15100Mbps(212),
                 n16Gbps(213),
                 n18Gbps(214),
                 n19Gbps(215),
                 n20Gbps(216),
                 n23Gbps(217),
                 n25Gbps(218),
                 n28Gbps(219),
                 n30Gbps(220),
                 n33Gbps(221),
                 n35Gbps(222),
                 n38Gbps(223),
                 n40Gbps(224),
                 n45Gbps(225),
                 n50Gbps(226),
                 n55Gbps(227),
                 n60Gbps(228),
                 n65Gbps(229),
                 n70Gbps(230),
                 n75Gbps(231),
                 n81Gbps(232),
                 n91Gbps(233),
                 n101Gbps(234),
                 n111Gbps(235),
                 n121Gbps(236),
                 n131Gbps(237),
                 n141Gbps(238),
                 n151Gbps(239),
                 n160Gbps(240),
                 n180Gbps(241),
                 n200Gbps(242),
                 n220Gbps(243),
                 n240Gbps(244),
                 n260Gbps(245),
                 n280Gbps(246),
                 n300Gbps(247),
                 n320Gbps(248),
                 n360Gbps(249),
                 n400Gbps(250),
                 n440Gbps(251),
                 n480Gbps(252),
                 n520Gbps(253),
                 n560Gbps(254),
                 max(255) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      acceptable speed for a TG using this Class of Service."
   DEFVAL     { max }
::= { mscAppnCosTgProvEntry 2 }

mscAppnCosTgMinConnectCost OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      cost per connect time for a TG. It is represented by a number 
      between 0 and 255 and is the  relative cost of using a TG. The units 
      for cost-per-connect time are installation-defined and are typically 
      based on the applicable tariffs of the transmission facility being 
      used by the TG. The cost-per-connect time values that a network 
      administrator assigns to the TGs in a network should reflect the 
      relative expense of each TG as compared to all other TGs in the 
      network. A value of 0 means that there is no additional cost in 
      connecting over the TG(as in the case of a non-switched facility)."
   DEFVAL     { 0 }
::= { mscAppnCosTgProvEntry 3 }

mscAppnCosTgMaxConnectCost OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      cost per connect time for a TG. It is represented by a number 
      between 0 and 255 and is the relative cost of using a TG. The units 
      for cost-per-connect time are installation-defined and are typically 
      based on the applicable tariffs of the transmission facility being 
      used by the TG. The cost per connect time values that a network 
      administrator assigns to the TGs in a network should reflect the 
      relative expense of each TG as compared to all other TGs in the 
      network. A value of 0 means that there is no additional cost in 
      connecting over the TG (as in the case of a non-switched facility)."
   DEFVAL     { 255 }
::= { mscAppnCosTgProvEntry 4 }

mscAppnCosTgMinByteCost OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      cost per byte allowed for a TG to be used for a session. It is a single 
      byte value in the range 0 to 255 that expresses a relative cost of 
      transmitting a byte over the associated TG. The units for cost per 
      byte are user defined. Like cost per connect time, cost per byte is 
      network specific and will not be uniform across networks unless 
      assignments are coordinated."
   DEFVAL     { 0 }
::= { mscAppnCosTgProvEntry 5 }

mscAppnCosTgMaxByteCost OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      cost per byte allowed for a TG to be used for a session. It is a single 
      byte value in the range 0 to 255 that expresses a relative cost of 
      transmitting a byte over the associated TG. The units for cost per 
      byte are user defined. Like cost per connect time, cost per byte is 
      network specific and will not be uniform across networks unless 
      assignments are coordinated."
   DEFVAL     { 255 }
::= { mscAppnCosTgProvEntry 6 }

mscAppnCosTgMinSecurity OBJECT-TYPE
   SYNTAX     INTEGER  {
                 nonSecure(1),
                 publicSwitchedNetwork(32),
                 undergroundCable(64),
                 secureConduit(96),
                 guardedConduit(128),
                 encrypted(160),
                 guardedRadiation(192) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      level of security protection required for a TG to be allowed to route 
      session traffic. The security values are architecturally defined to 
      provide continuity across all networks. Currently, security is 
      encoded as one of the following seven values:
      
      guardedRadiation - guarded conduit containing the transmission 
      medium; protected against physical and radiation tapping.
      
      encrypted - link level encryption is provided
      guardedConduit - guarded conduit; protected against physical 
      tapping
      secureConduit- secure conduit, not guarded; e.g. pressurized pipe
      undergroundCable - underground cable located in a secure country
      publicSwitchedNetwork - public switched network; secure in the 
      sense that there is no predetermined route that traffic will take
      nonSecure - all else, for example satellite-connected, located in a 
      nonsecure country."
   DEFVAL     { nonSecure }
::= { mscAppnCosTgProvEntry 7 }

mscAppnCosTgMaxSecurity OBJECT-TYPE
   SYNTAX     INTEGER  {
                 nonSecure(1),
                 publicSwitchedNetwork(32),
                 undergroundCable(64),
                 secureConduit(96),
                 guardedConduit(128),
                 encrypted(160),
                 guardedRadiation(192) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      level of security protection required for a TG to be allowed to route 
      session traffic. The security values are architecturally defined to 
      provide continuity across all networks. Currently, security is 
      encoded as one of the following seven values:
      
      guardedRadiation - guarded conduit containing the transmission 
      medium; protected against physical and radiation tapping.
      
      encrypted - link level encryption is provided
      guardedConduit - guarded conduit; protected against physical 
      tapping
      secureConduit- secure conduit, not guarded; e.g. pressurized pipe
      undergroundCable - underground cable located in a secure country
      publicSwitchedNetwork - public switched network; secure in the 
      sense that there is no predetermined route that traffic will take
      nonSecure - all else, for example. satellite-connected, located in a 
      nonsecure country."
   DEFVAL     { guardedRadiation }
::= { mscAppnCosTgProvEntry 8 }

mscAppnCosTgMinPropDelay OBJECT-TYPE
   SYNTAX     INTEGER  {
                 minimum(0),
                 negligible(76),
                 terrestrial(113),
                 packetSwitched(145),
                 long(153),
                 maximum(255) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum  
      propagation delay for this Class of Service. Propogation delay is the 
      length of time that it takes for a signal to propagate from one end of 
      the TG to the other. Possible values are:
      
      minimum - minimum
      negligible - 400 microsec
      terrestrial - 10 msec
      packetSwitched - 150 msec
      long - 300 msec"
   DEFVAL     { minimum }
::= { mscAppnCosTgProvEntry 9 }

mscAppnCosTgMaxPropDelay OBJECT-TYPE
   SYNTAX     INTEGER  {
                 minimum(0),
                 negligible(76),
                 terrestrial(113),
                 packetSwitched(145),
                 long(153),
                 maximum(255) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum  
      propagation delay for this Class of Service. Propagation delay is the 
      length of time that it takes for a signal to propagate from one end of 
      the TG to the other. Possible values are:
      
      minimum - minimum
      negligible - 400 microsec
      terrestrial - 10 msec
      packetSwitched - 150 msec
      long - 300 msec"
   DEFVAL     { maximum }
::= { mscAppnCosTgProvEntry 10 }

mscAppnCosTgMinModemClass OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute  is part of the COS tables and specifies the minimum 
      modem class allowed for a TG to carry session traffic."
   DEFVAL     { 0 }
::= { mscAppnCosTgProvEntry 11 }

mscAppnCosTgMaxModemClass OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      modem class allowed for a TG to carry session traffic."
   DEFVAL     { 0 }
::= { mscAppnCosTgProvEntry 12 }

mscAppnCosTgMinUserDefParm1 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute  is part of the COS tables and specifies the minimum 
      acceptable value for user defined routing parameter number 1."
   DEFVAL     { 0 }
::= { mscAppnCosTgProvEntry 13 }

mscAppnCosTgMaxUserDefParm1 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute  is part of the COS tables and  specifies the maximum 
      acceptable value for user defined routing parameter number 1."
   DEFVAL     { 255 }
::= { mscAppnCosTgProvEntry 14 }

mscAppnCosTgMinUserDefParm2 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute  is part of the COS tables and  specifies the minimum 
      acceptable value for  user defined routing parameter number 2."
   DEFVAL     { 0 }
::= { mscAppnCosTgProvEntry 15 }

mscAppnCosTgMaxUserDefParm2 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and  specifies the maximum 
      acceptable value for  user defined routing parameter number 2."
   DEFVAL     { 255 }
::= { mscAppnCosTgProvEntry 16 }

mscAppnCosTgMinUserDefParm3 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum  
      acceptable value for  user defined routing parameter number 3."
   DEFVAL     { 0 }
::= { mscAppnCosTgProvEntry 17 }

mscAppnCosTgMaxUserDefParm3 OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and contains the maximum 
      acceptable value for  user defined routing parameter number 3."
   DEFVAL     { 255 }
::= { mscAppnCosTgProvEntry 18 }


-- Appn/<string> Cos/<string> NodeRow/<weight>
-- This component specifies the allowable ranges for a node's service  
-- characteristics for a class of service. During route calculation, a 
-- node is considered acceptable if all of the actual node 
-- characteristics fall within the range of required node characteristics 
-- for a COS. A node is considered unacceptable if at least one of the 
-- actual node characteristics falls outside the range of the required 
-- node  values. 

mscAppnCosNode OBJECT IDENTIFIER ::= { mscAppnCos 11 }



mscAppnCosNodeRowStatusTable OBJECT-TYPE
   SYNTAX     SEQUENCE OF MscAppnCosNodeRowStatusEntry
   ACCESS     not-accessible
   STATUS     mandatory
   DESCRIPTION
     "This entry controls the addition and deletion of 
      mscAppnCosNode components."
::= { mscAppnCosNode 1 }

mscAppnCosNodeRowStatusEntry OBJECT-TYPE
   SYNTAX     MscAppnCosNodeRowStatusEntry
   ACCESS     not-accessible
   STATUS     mandatory
   DESCRIPTION
     "A single entry in the table represents a single 
      mscAppnCosNode component."
   INDEX {
      mscAppnIndex,
      mscAppnCosIndex,
      mscAppnCosNodeIndex }
::= { mscAppnCosNodeRowStatusTable 1 }

MscAppnCosNodeRowStatusEntry ::= SEQUENCE {
   mscAppnCosNodeRowStatus
      RowStatus,
   mscAppnCosNodeComponentName
      DisplayString,
   mscAppnCosNodeStorageType
      StorageType,
   mscAppnCosNodeIndex
      Integer32 }

mscAppnCosNodeRowStatus OBJECT-TYPE
   SYNTAX     RowStatus 
   ACCESS     read-write
   STATUS     mandatory
   DESCRIPTION
     "This variable is used as the basis for SNMP naming of
      mscAppnCosNode components.
      These components can be added and deleted."
::= { mscAppnCosNodeRowStatusEntry 1 }

mscAppnCosNodeComponentName OBJECT-TYPE
   SYNTAX     DisplayString 
   ACCESS     read-only
   STATUS     mandatory
   DESCRIPTION
     "This variable provides the component's string name for
      use with the ASCII Console Interface"
::= { mscAppnCosNodeRowStatusEntry 2 }

mscAppnCosNodeStorageType OBJECT-TYPE
   SYNTAX     StorageType 
   ACCESS     read-only
   STATUS     mandatory
   DESCRIPTION
     "This variable represents the storage type value for the
      mscAppnCosNode tables."
::= { mscAppnCosNodeRowStatusEntry 4 }

mscAppnCosNodeIndex OBJECT-TYPE
   SYNTAX     Integer32 (1..255)
   ACCESS     not-accessible
   STATUS     mandatory
   DESCRIPTION
     "This variable represents the index for the mscAppnCosNode tables."
::= { mscAppnCosNodeRowStatusEntry 10 }

mscAppnCosNodeProvTable OBJECT-TYPE
   SYNTAX     SEQUENCE OF MscAppnCosNodeProvEntry
   ACCESS     not-accessible
   STATUS     mandatory
   DESCRIPTION
     "This group specifies a range of node characteristics for a class of 
      service and is used in route selection for session traffic. 
      
      During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned to 
      the node and TGs in the route.  The route with the lowest weight is 
      the one used for the session."
::= { mscAppnCosNode 10 }

mscAppnCosNodeProvEntry OBJECT-TYPE
   SYNTAX     MscAppnCosNodeProvEntry
   ACCESS     not-accessible
   STATUS     mandatory
   DESCRIPTION
     "An entry in the mscAppnCosNodeProvTable."
   INDEX {
      mscAppnIndex,
      mscAppnCosIndex,
      mscAppnCosNodeIndex }
::= { mscAppnCosNodeProvTable 1 }

MscAppnCosNodeProvEntry ::= SEQUENCE {
   mscAppnCosNodeMinRouteAddResistance
      INTEGER,
   mscAppnCosNodeMaxRouteAddResistance
      INTEGER,
   mscAppnCosNodeMinStatus
      INTEGER,
   mscAppnCosNodeMaxStatus
      INTEGER }

mscAppnCosNodeMinRouteAddResistance OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      route addition resistance value allowed for a node to route session 
      traffic.  Route addition resistance defines the desirability for a 
      network node to perform additional intermediate session routing. 
      The higher the value, the less desirable the node is for session 
      routing purposes."
   DEFVAL     { 0 }
::= { mscAppnCosNodeProvEntry 1 }

mscAppnCosNodeMaxRouteAddResistance OBJECT-TYPE
   SYNTAX     INTEGER (0..255)
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      route addition resistance value allowed for a node to route session 
      traffic.  Route addition resistance defines the desirability for a 
      network node to perform additional intermediate session routing. 
      The higher the value, the less desirable the node is for session 
      routing purposes."
   DEFVAL     { 255 }
::= { mscAppnCosNodeProvEntry 2 }

mscAppnCosNodeMinStatus OBJECT-TYPE
   SYNTAX     INTEGER  {
                 uncongested(0),
                 congested(1) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the minimum 
      congestion value that will be allowed for a node to carry session 
      traffic."
   DEFVAL     { uncongested }
::= { mscAppnCosNodeProvEntry 3 }

mscAppnCosNodeMaxStatus OBJECT-TYPE
   SYNTAX     INTEGER  {
                 uncongested(0),
                 congested(1) }
   ACCESS     read-write
   STATUS     mandatory
   DESCRIPTION
     "During route computation, APPN determines the optimum route 
      through a network in the following steps:
      - obtains the required route characteristics from the COS database  
      using the mode name specified in the session request
      - determines all possible combinations of transmission groups and 
      nodes that form a route to the destination database
      - the actual characteristics of the Nodes and TGs in these routes are 
      compared against the COS tables that contain the required 
      characteristics of the session.  A weight is assigned based on how 
      well the actual characteristics meet the required characteristics. 
      Where there is no match between actual and required 
      characteristics, the route containing the node or TG is excluded 
      from further computation.
      - Each possible route is quantified by adding the weights assigned 
      to the node and TGs in the route.  The route with the lowest weight 
      is the one used for the session.
      
      This attribute is part of the COS tables and specifies the maximum 
      congestion value that will be allowed for a node to carry session 
      traffic."
   DEFVAL     { uncongested }
::= { mscAppnCosNodeProvEntry 4 }


-- Appn/<string> FrameRelaySvc
-- This provisioned component defines the characteristics of the APPN 
-- service Frame Relay Switched Virtual Circuit (SVC) calls.

mscAppnFrSvc OBJECT IDENTIFIER ::= { mscAppn 18 }



mscAppnFrSvcRowStatusTable OBJECT-TYPE
   SYNTAX     SEQUENCE OF MscAppnFrSvcRowStatusEntry
   ACCESS     not-accessible
   STATUS     mandatory
   DESCRIPTION
     "This entry controls the addition and deletion of 
      mscAppnFrSvc components."
::= { mscAppnFrSvc 1 }

mscAppnFrSvcRowStatusEntry OBJECT-TYPE
   SYNTAX     MscAppnFrSvcRowStatusEntry
   ACCESS     not-accessible
   STATUS     mandatory
   DESCRIPTION
     "A single entry in the table represents a single 
      mscAppnFrSvc component."
   INDEX {
      mscAppnIndex,
      mscAppnFrSvcIndex }
::= { mscAppnFrSvcRowStatusTable 1 }

MscAppnFrSvcRowStatusEntry ::= SEQUENCE {
   mscAppnFrSvcRowStatus
      RowStatus,
   mscAppnFrSvcComponentName
      DisplayString,
   mscAppnFrSvcStorageType
      StorageType,
   mscAppnFrSvcIndex
      NonReplicated }

mscAppnFrSvcRowStatus OBJECT-TYPE
   SYNTAX     RowStatus 
   ACCESS     read-write
   STATUS     mandatory
   DESCRIPTION
     "This variable is used as the basis for SNMP naming of
      mscAppnFrSvc components.
      These components can be added and deleted."
::= { mscAppnFrSvcRowStatusEntry 1 }

mscAppnFrSvcComponentName OBJECT-TYPE
   SYNTAX     DisplayString 
   ACCESS     read-only
   STATUS     mandatory
   DESCRIPTION
     "This variable provides the component's string name for
      use with the ASCII Console Interface"
::= { mscAppnFrSvcRowStatusEntry 2 }

mscAppnFrSvcStorageType OBJECT-TYPE
   SYNTAX     StorageType 
   ACCESS     read-only
   STATUS     mandatory
   DESCRIPTION
     "This variable represents the storage type value for the
      mscAppnFrSvc tables."
::= { mscAppnFrSvcRowStatusEntry 4 }

mscAppnFrSvcIndex OBJECT-TYPE
   SYNTAX     NonReplicated 
   ACCESS     not-accessible
   STATUS     mandatory
   DESCRIPTION
     "This variable represents the index for the mscAppnFrSvc tables."
::= { mscAppnFrSvcRowStatusEntry 10 }

mscAppnFrSvcBanTable OBJECT-TYPE
   SYNTAX     SEQUENCE OF MscAppnFrSvcBanEntry
   ACCESS     not-accessible
   STATUS     mandatory
   DESCRIPTION
     "This group contains the BAN device MAC and SAP parameters for 
      the APPN service Frame Relay SVC calls."
::= { mscAppnFrSvc 10 }

mscAppnFrSvcBanEntry OBJECT-TYPE
   SYNTAX     MscAppnFrSvcBanEntry
   ACCESS     not-accessible
   STATUS     mandatory
   DESCRIPTION
     "An entry in the mscAppnFrSvcBanTable."
   INDEX {
      mscAppnIndex,
      mscAppnFrSvcIndex }
::= { mscAppnFrSvcBanTable 1 }

MscAppnFrSvcBanEntry ::= SEQUENCE {
   mscAppnFrSvcBanLocalMac
      DashedHexString,
   mscAppnFrSvcBanLocalSap
      Hex }

mscAppnFrSvcBanLocalMac OBJECT-TYPE
   SYNTAX     DashedHexString (SIZE (6))
   ACCESS     read-write
   STATUS     mandatory
   DESCRIPTION
     "This attribute specifies the MAC address to be used for Frame Relay 
      SVCs with BAN encapsulation."
   DEFVAL     { '4fff00000000'H }
::= { mscAppnFrSvcBanEntry 1 }

mscAppnFrSvcBanLocalSap OBJECT-TYPE
   SYNTAX     Hex (4 | 8 | 12 | 16 | 20 | 24 | 28 | 32 | 36 | 40 | 44 | 48 | 52 | 56 | 60 | 64 | 68 | 72 | 76 | 80 | 84 | 88 | 92 | 96 | 100 | 104 | 108 | 112 | 116 | 120 | 124 | 128 | 132 | 136 | 140 | 144 | 148 | 152 | 156 | 160 | 164 | 168 | 172 | 176 | 180 | 184 | 188 | 192 | 196 | 200 | 204 | 208 | 212 | 216 | 220 | 224 | 228 | 232 | 236 | 240 | 244 | 248 | 252)
   ACCESS     read-write
   STATUS     mandatory
   DESCRIPTION
     "This attribute specifies the local SAP number to be used  for  Frame 
      Relay SVCs with BAN encapsulation."
   DEFVAL     { 4 }
::= { mscAppnFrSvcBanEntry 2 }

mscAppnFrSvcProvisionedTable OBJECT-TYPE
   SYNTAX     SEQUENCE OF MscAppnFrSvcProvisionedEntry
   ACCESS     not-accessible
   STATUS     mandatory
   DESCRIPTION
     "This group contains the provisonable parameters for the APPN 
      service Frame Relay SVC calls."
::= { mscAppnFrSvc 11 }

mscAppnFrSvcProvisionedEntry OBJECT-TYPE
   SYNTAX     MscAppnFrSvcProvisionedEntry
   ACCESS     not-accessible
   STATUS     mandatory
   DESCRIPTION
     "An entry in the mscAppnFrSvcProvisionedTable."
   INDEX {
      mscAppnIndex,
      mscAppnFrSvcIndex }
::= { mscAppnFrSvcProvisionedTable 1 }

MscAppnFrSvcProvisionedEntry ::= SEQUENCE {
   mscAppnFrSvcMaximumFrameRelaySvcs
      Unsigned32,
   mscAppnFrSvcRateEnforcement
      INTEGER,
   mscAppnFrSvcMaximumCir
      Unsigned32 }

mscAppnFrSvcMaximumFrameRelaySvcs OBJECT-TYPE
   SYNTAX     Unsigned32 (1..3072)
   ACCESS     read-write
   STATUS     mandatory
   DESCRIPTION
     "This attribute specifies the maximum number of concurrently active 
      Frame  Relay SVC calls that are allowed for this service.  This 
      attribute does not include the general switched virtual circuits 
      (GSVC)."
   DEFVAL     { 1000 }
::= { mscAppnFrSvcProvisionedEntry 1 }

mscAppnFrSvcRateEnforcement OBJECT-TYPE
   SYNTAX     INTEGER  {
                 off(0),
                 on(1) }
   ACCESS     read-write
   STATUS     mandatory
   DESCRIPTION
     "This attribute specifies whether rate enforcement is to be used for 
      new Frame Relay SVCs on this service.  When rate enforcement is 
      on the rate of data sent by the service to  individual Frame Relay 
      SVCs is  controlled."
   DEFVAL     { on }
::= { mscAppnFrSvcProvisionedEntry 2 }

mscAppnFrSvcMaximumCir OBJECT-TYPE
   SYNTAX     Unsigned32 (0..52000000)
   ACCESS     read-write
   STATUS     mandatory
   DESCRIPTION
     "This attribute specifies the maximum rate enforcement  CIR 
      (Committed Information Rate) that is allowed for  use with the 
      Frame Relay SVCs on this service. During  call setup negotiation, if 
      the caller to  this service  requests a higher CIR value be used, the 
      CIR used is  reduced to the value of maximumCir."
   DEFVAL     { 2048000 }
::= { mscAppnFrSvcProvisionedEntry 4 }

mscAppnFrSvcOperationalTable OBJECT-TYPE
   SYNTAX     SEQUENCE OF MscAppnFrSvcOperationalEntry
   ACCESS     not-accessible
   STATUS     mandatory
   DESCRIPTION
     "This group contains the operational attributes for the APPN Frame 
      Relay SVC calls."
::= { mscAppnFrSvc 12 }

mscAppnFrSvcOperationalEntry OBJECT-TYPE
   SYNTAX     MscAppnFrSvcOperationalEntry
   ACCESS     not-accessible
   STATUS     mandatory
   DESCRIPTION
     "An entry in the mscAppnFrSvcOperationalTable."
   INDEX {
      mscAppnIndex,
      mscAppnFrSvcIndex }
::= { mscAppnFrSvcOperationalTable 1 }

MscAppnFrSvcOperationalEntry ::= SEQUENCE {
   mscAppnFrSvcCurrentNumberOfSvcCalls
      Gauge32 }

mscAppnFrSvcCurrentNumberOfSvcCalls OBJECT-TYPE
   SYNTAX     Gauge32 (0..3072)
   ACCESS     read-only
   STATUS     mandatory
   DESCRIPTION
     "This attribute indicates the number of Frame Relay SVCs  currently 
      existing on this service.  This attribute does not include the general 
      switched virtual circuits (GSVC)."
   DEFVAL     { 0 }
::= { mscAppnFrSvcOperationalEntry 1 }




-- 
-- Version and Compliance statements
-- 



-- Object-Group Statement:
-- A list of all current accessible leaf objects.

-- OBJECTS { mscAppnLcnUsageState,
--           mscAppnDLURPrimaryDefDlusName,
--           mscAppnCosTgMinModemClass,
--           mscAppnCosNodeStorageType,
--           mscAppnDlciSpStorageType,
--           mscAppnActiveSvcs,
--           mscAppnDluSscpCurTxPacWin,
--           mscAppnPortEffectiveCap,
--           mscAppnRtpPktRx,
--           mscAppnLsActSessCount,
--           mscAppnCosTgMinUserDefParm2,
--           mscAppnRtpRowStatus,
--           mscAppnLcnVcLocalTxPktSize,
--           mscAppnLocTgDlcData,
--           mscAppnDlciSpCommittedBurstSize,
--           mscAppnLcnVcCalledLcn,
--           mscAppnDlciStorageType,
--           mscAppnFlowReductionSequenceNumber,
--           mscAppnPortUserDefinedParm3,
--           mscAppnDluUsStatOdai,
--           mscAppnLcnVcFastSelectCall,
--           mscAppnCosTgMinByteCost,
--           mscAppnLcnVcComponentName,
--           mscAppnDlciBanLsDefComponentName,
--           mscAppnIsrSessCosName,
--           mscAppnLocTgEffectiveCap,
--           mscAppnIsrSessPriStatsMaxRxPacWin,
--           mscAppnDlciCommittedBurstSize,
--           mscAppnDlciVcStartTime,
--           mscAppnLcnVcMaxSubnetPktSize,
--           mscAppnDlciBanLocalSap,
--           mscAppnDlciSpRateEnforcement,
--           mscAppnDlciAdminState,
--           mscAppnDlciVcDiagnosticCode,
--           mscAppnLocTgResourceSequenceNumber,
--           mscAppnCosTgMinEffectiveCapacity,
--           mscAppnDlciCommittedInformationRate,
--           mscAppnDirEntLuOwnerName,
--           mscAppnNnDaysLeft,
--           mscAppnRtpUptime,
--           mscAppnMaximumTopologyTgs,
--           mscAppnDnaComponentName,
--           mscAppnDluDsStatComponentName,
--           mscAppnIdNumber,
--           mscAppnRtpLastRoundTripTime,
--           mscAppnLsOutMsgBytes,
--           mscAppnLocTgUserDefinedParm3,
--           mscAppnDluNauAddress,
--           mscAppnDlciBanLsDefDlusName,
--           mscAppnDlciRateEnforcement,
--           mscAppnDnaHgMHgAddrComponentName,
--           mscAppnAdjNnLastFrsnSent,
--           mscAppnLcnVcState,
--           mscAppnDlciVcPreviousDiagnosticCode,
--           mscAppnDlciVcAccountingEnabled,
--           mscAppnNnComponentName,
--           mscAppnDlciSpExcessBurstSize,
--           mscAppnLsOutXidFrames,
--           mscAppnDlciDcDiscardPriority,
--           mscAppnLsEffectiveCap,
--           mscAppnLocTgUserDefinedParm2,
--           mscAppnDlciVcPreviousState,
--           mscAppnDnaHgMMaxAvailableChannels,
--           mscAppnLcnDcComponentName,
--           mscAppnDlciVcPeakRetryQueueSize,
--           mscAppnUsageState,
--           mscAppnFrSvcStorageType,
--           mscAppnDluDsStatRxFmdFrames,
--           mscAppnDluUsStatCurRxPacWin,
--           mscAppnResourceSequenceNumber,
--           mscAppnLsOutXidBytes,
--           mscAppnLocTgUserDefinedParm1,
--           mscAppnDlciExcessBurstSize,
--           mscAppnDlciSpMeasurementInterval,
--           mscAppnLsUserDefinedParm3,
--           mscAppnDlciBnnLsDefStorageType,
--           mscAppnPortLsXmitRxCap,
--           mscAppnCosTgMaxByteCost,
--           mscAppnLcnVcSubnetTxPktSize,
--           mscAppnLcnVcCalledNpi,
--           mscAppnRtpLostFrames,
--           mscAppnDlusActPuRspTx,
--           mscAppnCosTgMaxPropDelay,
--           mscAppnLsUserDefinedParm2,
--           mscAppnDnaCugType,
--           mscAppnDlusActPuRx,
--           mscAppnDynamicLsBadXids,
--           mscAppnDnaOutDefaultPriority,
--           mscAppnDlciVcCalledLcn,
--           mscAppnDlciVcPathReliability,
--           mscAppnDlciVcCannotForwardToSubnet,
--           mscAppnFrSvcRateEnforcement,
--           mscAppnPortInbLinkActLim,
--           mscAppnDnaIncAccess,
--           mscAppnDlciBanStorageType,
--           mscAppnDlciVcCallReferenceNumber,
--           mscAppnLsUserDefinedParm1,
--           mscAppnRtpOutSessionControlFrames,
--           mscAppnDirEntRowStatus,
--           mscAppnPortType,
--           mscAppnMaximumLinkStations,
--           mscAppnDlusDactLuRspTx,
--           mscAppnNnFunctionsSupported,
--           mscAppnDluSscpRxRuSize,
--           mscAppnDlciVcNotDataXferToSubnet,
--           mscAppnGeneralFunctionsSupported,
--           mscAppnDnaHgMAvailableChannels,
--           mscAppnLsMinDelay,
--           mscAppnDlciSpCommittedInformationRate,
--           mscAppnLsTgNum,
--           mscAppnDluSscpMaxRxBtuSize,
--           mscAppnCosTgMaxUserDefParm2,
--           mscAppnDluSscpRowStatus,
--           mscAppnStatus,
--           mscAppnFrSvcMaximumFrameRelaySvcs,
--           mscAppnNnTgDaysLeft,
--           mscAppnDnaCugInterlockCode,
--           mscAppnMaximumSvcs,
--           mscAppnHprSupport,
--           mscAppnDlciVcStorageType,
--           mscAppnRouteAdditionResistance,
--           mscAppnLcnVcSubnetRxWindowSize,
--           mscAppnIsrSessSecStatsComponentName,
--           mscAppnDlciBnnLsDefHprSupported,
--           mscAppnLcnStorageType,
--           mscAppnIsrSessPriStatsCurTxPacWin,
--           mscAppnRtpRemoteTcid,
--           mscAppnDlciDcComponentName,
--           mscAppnDluSscpMaxTxPacWin,
--           mscAppnNnResourceSequenceNumber,
--           mscAppnNnTgComponentName,
--           mscAppnCosNodeMaxStatus,
--           mscAppnRtpCurTxRate,
--           mscAppnRtpMaxRxRate,
--           mscAppnLcnVcStartTime,
--           mscAppnIsrSessPriStatsStorageType,
--           mscAppnDnaDefaultSendToNetworkWindowSize,
--           mscAppnLcnAdminState,
--           mscAppnDluDsStatSidh,
--           mscAppnLcnVcDiagnosticCode,
--           mscAppnDlusActLuRx,
--           mscAppnDluStorageType,
--           mscAppnNnTgPropagationDelay,
--           mscAppnDluUsStatTxDataframes,
--           mscAppnLcnVcWindowClosuresToSubnet,
--           mscAppnDlciVcDataPath,
--           mscAppnCosComponentName,
--           mscAppnLsHprSupport,
--           mscAppnRtpInSessionControlFrames,
--           mscAppnDluSscpStorageType,
--           mscAppnPortDlcType,
--           mscAppnAdjNnComponentName,
--           mscAppnNnTgDlcData,
--           mscAppnDnaCugStorageType,
--           mscAppnDlciVcDmepValue,
--           mscAppnLcnVcType,
--           mscAppnDnaCugPrivileged,
--           mscAppnDlciVcElapsedTimeTillNow,
--           mscAppnLcnVcAccountingEnabled,
--           mscAppnLsCurrentDelay,
--           mscAppnDluUsStatTxDataBytes,
--           mscAppnDnaCugIncCalls,
--           mscAppnLcnDcDiscardPriority,
--           mscAppnLcnVcPreviousState,
--           mscAppnDlciExcessInformationRate,
--           mscAppnNnTgFlowReductionSequenceNumber,
--           mscAppnDnaDataNetworkAddress,
--           mscAppnIsrSessRowStatus,
--           mscAppnLcnVcPeakRetryQueueSize,
--           mscAppnDlciVcCalledNpi,
--           mscAppnDlciDcTransferPriority,
--           mscAppnPortStorageType,
--           mscAppnDnaDefaultSendToNetworkThruputClass,
--           mscAppnFqCpName,
--           mscAppnRtpPktDiscard,
--           mscAppnDluPluSessActive,
--           mscAppnIsrSessPriStatsMaxTxPacWin,
--           mscAppnCosNodeComponentName,
--           mscAppnNnStorageType,
--           mscAppnCosTgMaxConnectCost,
--           mscAppnPortSimRim,
--           mscAppnRtpSmoothRoundTripTime,
--           mscAppnIsrSessSecStatsRxRuSize,
--           mscAppnDlciBanLsDefAdjacentCpType,
--           mscAppnPortActXidExchLim,
--           mscAppnDlciSpRowStatus,
--           mscAppnNnStatus,
--           mscAppnDlciVcRcosFromNetwork,
--           mscAppnMaximumTopologyNodes,
--           mscAppnLcnVcPreviousDiagnosticCode,
--           mscAppnNnTgUserDefinedParm3,
--           mscAppnLcnVcCallingNpi,
--           mscAppnStorageType,
--           mscAppnDlusReqActPuRspRx,
--           mscAppnDnaHgMStorageType,
--           mscAppnLocTgStorageType,
--           mscAppnDlciBnnLsDefDspuService,
--           mscAppnDirEntEntryType,
--           mscAppnDluSscpMaxRxPacWin,
--           mscAppnDlusSscpPuMuTx,
--           mscAppnLsActualCpType,
--           mscAppnUpTime,
--           mscAppnLcnVcPriority,
--           mscAppnLsInInvalidSnaFrames,
--           mscAppnNnTgUserDefinedParm2,
--           mscAppnDlciVcOoSeqByteCntExceeded,
--           mscAppnPortUserDefinedParm1,
--           mscAppnDlciBnnLsDefAdjacentCpName,
--           mscAppnDlciBnnLsDefMaxTxBtuSize,
--           mscAppnDynamicLsGoodXids,
--           mscAppnAdminState,
--           mscAppnDluSscpLsName,
--           mscAppnDlciVcPktRetryTimeouts,
--           mscAppnDlciVcOutOfRangeFrmFromSubnet,
--           mscAppnLsEchoResponse,
--           mscAppnNnTgResourceSequenceNumber,
--           mscAppnNnTgUserDefinedParm1,
--           mscAppnLsLinkStationState,
--           mscAppnDlciBnnLsDefAdjacentNodeID,
--           mscAppnPortDynLsBadXids,
--           mscAppnLsSap,
--           mscAppnAdjNnRowStatus,
--           mscAppnDlusSscpPuMuRx,
--           mscAppnPortTargetPacingCount,
--           mscAppnDlciDcRemoteNpi,
--           mscAppnLsStorageType,
--           mscAppnPortMaxIfrmRxWindow,
--           mscAppnLcnVcLocalRxWindowSize,
--           mscAppnIsrSessSecStatsTxDataframes,
--           mscAppnDlciBnnLsDefLsRole,
--           mscAppnDlciVcSegmentSize,
--           mscAppnLcnVcStorageType,
--           mscAppnDlciBanLsDefStorageType,
--           mscAppnDnaHgMComponentName,
--           mscAppnDluDsStatCurTxPacWin,
--           mscAppnDluUsStatSidl,
--           mscAppnTreeCacheSize,
--           mscAppnLcnVcAccountingEnd,
--           mscAppnDluUsStatSidh,
--           mscAppnLcnVcPeakOoSeqFrmForwarded,
--           mscAppnDlciVcCallingNpi,
--           mscAppnDlusSscpLuMuTx,
--           mscAppnIsrSessPriStatsTxDataframes,
--           mscAppnDluDsStatStorageType,
--           mscAppnDlciVcCalledDna,
--           mscAppnIsrSessPriStatsRxDataBytes,
--           mscAppnCosTgComponentName,
--           mscAppnDnaHgMHgAddrStorageType,
--           mscAppnDnaDefaultTransferPriority,
--           mscAppnDlciBnnLsDefRowStatus,
--           mscAppnMaximumLocates,
--           mscAppnLcnDcTransferPriority,
--           mscAppnIsrSessPriStatsTxDataBytes,
--           mscAppnPortSecurity,
--           mscAppnMemWarningThreshold,
--           mscAppnFrSvcBanLocalMac,
--           mscAppnCosTgMinUserDefParm3,
--           mscAppnNnTgStatus,
--           mscAppnRtpBytesDiscarded,
--           mscAppnDlciDcType,
--           mscAppnRtpComponentName,
--           mscAppnDlusPrimaryDlus,
--           mscAppnRtpCurRxRate,
--           mscAppnIsrSessPriStatsMaxTxBtuSize,
--           mscAppnRtpLocalLsName,
--           mscAppnIsrSessPriStatsRxDataFrames,
--           mscAppnMemCriticalThreshold,
--           mscAppnDluUsStatMaxRxPacWin,
--           mscAppnDLURRowStatus,
--           mscAppnPortDefinedLsBadXids,
--           mscAppnDlciVcPeakOoSeqByteCount,
--           mscAppnRtpRxBytes,
--           mscAppnDlciBanRowStatus,
--           mscAppnDluSscpOdai,
--           mscAppnDluDsStatMaxTxPacWin,
--           mscAppnLocTgSecurity,
--           mscAppnDluSscpMaxTxBtuSize,
--           mscAppnDluSscpRxDataFrames,
--           mscAppnRtpLocalTcid,
--           mscAppnLcnVcAckStackingTimeouts,
--           mscAppnLcnVcPathReliability,
--           mscAppnLsDynamicOrDefined,
--           mscAppnDLURDlusRetryTimeout,
--           mscAppnDlusActLuRspTx,
--           mscAppnIsrSessPriStatsMaxRxBtuSize,
--           mscAppnDLURComponentName,
--           mscAppnFrSvcBanLocalSap,
--           mscAppnDluSscpRxDataBytes,
--           mscAppnDnaCugPreferential,
--           mscAppnDlciBnnLsDefBackupDlusName,
--           mscAppnPortMaxTxBtuSize,
--           mscAppnDlciVcRowStatus,
--           mscAppnDlusComponentName,
--           mscAppnDluUsStatTxFmdFrames,
--           mscAppnLcnDcRemoteDna,
--           mscAppnLcnRowStatus,
--           mscAppnDluComponentName,
--           mscAppnLsSecurity,
--           mscAppnLcnVcCallReferenceNumber,
--           mscAppnLcnVcOutOfRangeFrmFromSubnet,
--           mscAppnDluUsStatCurTxPacWin,
--           mscAppnDluUsStatStorageType,
--           mscAppnLcnVcCalledDna,
--           mscAppnDluDsStatRxRuSize,
--           mscAppnDlciVcCombErrorsFromSubnet,
--           mscAppnIsrSessPriStatsRowStatus,
--           mscAppnPortLsRole,
--           mscAppnPortMaxRxBtuSize,
--           mscAppnLsAnrLabel,
--           mscAppnDlciVcSegmentsRx,
--           mscAppnDlusStorageType,
--           mscAppnRtpMinTxRate,
--           mscAppnLcnVcSubnetRecoveries,
--           mscAppnRtpTxBytes,
--           mscAppnDluUsStatRxFmdFrames,
--           mscAppnIsrSessSecStatsStorageType,
--           mscAppnIsrSessPriStatsSidl,
--           mscAppnMaximumDirectorySize,
--           mscAppnLcnOperationalState,
--           mscAppnPortDynLsGoodXids,
--           mscAppnDlciDcStorageType,
--           mscAppnLcnVcSegmentSize,
--           mscAppnDnaCugRowStatus,
--           mscAppnRtpMaxBtuSize,
--           mscAppnIsrSessTransmissionPriority,
--           mscAppnDnaHgMHgAddrDataNetworkAddress,
--           mscAppnIsrSessSecStatsCurRxPacWin,
--           mscAppnDluUsStatRxDataFrames,
--           mscAppnIsrMaxRuSize,
--           mscAppnDnaStorageType,
--           mscAppnDirEntComponentName,
--           mscAppnDluSscpSidl,
--           mscAppnIsrSessSecStatsCurTxPacWin,
--           mscAppnLcnVcPeakOoSeqQueueSize,
--           mscAppnLcnVcWindowClosuresFromSubnet,
--           mscAppnDlciBanLsDefDspuService,
--           mscAppnDefinedLsBadXids,
--           mscAppnNnTgByteCost,
--           mscAppnLsMaxTxBtuSize,
--           mscAppnDluDsStatTxDataframes,
--           mscAppnPortRowStatus,
--           mscAppnNnTgConnectCost,
--           mscAppnDnaHgMAvailabilityUpdateThreshold,
--           mscAppnDlciBanLsDefAdjacentCpName,
--           mscAppnDlciBanLsDefMaxTxBtuSize,
--           mscAppnDluPluName,
--           mscAppnAdjNnStorageType,
--           mscAppnDlciVcCallingLcn,
--           mscAppnDnaAccountClass,
--           mscAppnIsrUpperCongestionThreshold,
--           mscAppnDluDsStatTxDataBytes,
--           mscAppnIsrSessSecStatsMaxTxPacWin,
--           mscAppnRtpMaxTxRate,
--           mscAppnDlciVcEmissionPriorityToNetwork,
--           mscAppnDluDsStatRxDataFrames,
--           mscAppnDlciBanLsDefAdjacentNodeID,
--           mscAppnDluDsStatOdai,
--           mscAppnRowStatus,
--           mscAppnDlusDactPuRspTx,
--           mscAppnDnaHgMRowStatus,
--           mscAppnDluDsStatMaxTxBtuSize,
--           mscAppnLocTgRowStatus,
--           mscAppnDlciBanLocalMac,
--           mscAppnDirEntLocation,
--           mscAppnNnTgStorageType,
--           mscAppnIsrSessPriStatsSidh,
--           mscAppnDnaOutAccess,
--           mscAppnAdjNnLastFrsnReceived,
--           mscAppnDlciVcOoSeqPktCntExceeded,
--           mscAppnDlciBanLsDefLsRole,
--           mscAppnCosTransmissionPriority,
--           mscAppnDlusSscpLuMuRx,
--           mscAppnRtpRxInvalidSnaFrames,
--           mscAppnDluDsStatRxDataBytes,
--           mscAppnIsrSessSecStatsMaxRxPacWin,
--           mscAppnDlciOperationalState,
--           mscAppnPortByteCost,
--           mscAppnCosTgMinUserDefParm1,
--           mscAppnDluSscpSidh,
--           mscAppnDlciVcNotDataXferFromSubnet,
--           mscAppnOperationalState,
--           mscAppnDluUsStatLsName,
--           mscAppnDluDsStatMaxRxBtuSize,
--           mscAppnIsrLowerCongestionThreshold,
--           mscAppnIsrSessPriStatsTxFmdFrames,
--           mscAppnDnaAccountCollection,
--           mscAppnDluRowStatus,
--           mscAppnLsRowStatus,
--           mscAppnDluDsStatCurRxPacWin,
--           mscAppnCosTgMaxEffectiveCapacity,
--           mscAppnLcnVcTransferPriorityToNetwork,
--           mscAppnDirEntServerName,
--           mscAppnPortConnectCost,
--           mscAppnLsOutMsgFrames,
--           mscAppnLcnVcRowStatus,
--           mscAppnDlciBanLsDefRowStatus,
--           mscAppnIsrSessSecStatsLsName,
--           mscAppnLocTgByteCost,
--           mscAppnRtpMinRxRate,
--           mscAppnTreeCacheUseLimit,
--           mscAppnActiveLinkStations,
--           mscAppnDluUsStatRxRuSize,
--           mscAppnRtpActiveSessions,
--           mscAppnDlciBnnLsDefTgNum,
--           mscAppnDluSscpTxFmdFrames,
--           mscAppnNnTgSecurity,
--           mscAppnIsrSessComponentName,
--           mscAppnIsrSessPriStatsRxFmdFrames,
--           mscAppnDnaRowStatus,
--           mscAppnDluDsStatRowStatus,
--           mscAppnDluUsStatRowStatus,
--           mscAppnDlusReqDactPuTx,
--           mscAppnLocTgConnectCost,
--           mscAppnCosTgMinSecurity,
--           mscAppnLcnVcSegmentsRx,
--           mscAppnLcnVcFrmRetryTimeouts,
--           mscAppnDnaHgMHgAddrRowStatus,
--           mscAppnDnaTransferPriorityOverRide,
--           mscAppnDluDsStatSidl,
--           mscAppnDluSscpTxDataBytes,
--           mscAppnDlciSpComponentName,
--           mscAppnNnRowStatus,
--           mscAppnDluSscpRxFmdFrames,
--           mscAppnDnaNumberingPlanIndicator,
--           mscAppnDnaServiceExchange,
--           mscAppnLsByteCost,
--           mscAppnLogicalProcessor,
--           mscAppnLcnVcLocalTxWindowSize,
--           mscAppnPortDefinedLsGoodXids,
--           mscAppnDnaCugOutCalls,
--           mscAppnIsrSessSecStatsTxDataBytes,
--           mscAppnNnFunctionSupported,
--           mscAppnDlciBnnLsDefAdjacentCpType,
--           mscAppnDlciDcRemoteDlci,
--           mscAppnDlciBanLsDefHprSupported,
--           mscAppnDlciComponentName,
--           mscAppnDlciVcPeakOoSeqPktCount,
--           mscAppnIsrSessSecStatsMaxTxBtuSize,
--           mscAppnDlciBnnLsDefDlusName,
--           mscAppnIsrSessSecStatsRxDataFrames,
--           mscAppnLsConnectCost,
--           mscAppnLsOutSessionControlFrames,
--           mscAppnPortOutLinkActLim,
--           mscAppnDlciBnnLsDefCpCpSessionSupport,
--           mscAppnDefinedLsGoodXids,
--           mscAppnRtpShortReqTimer,
--           mscAppnLsBadXids,
--           mscAppnLcnVcCallingLcn,
--           mscAppnLcnDcRemoteNpi,
--           mscAppnDlciVcEmissionPriorityFromNetwork,
--           mscAppnIsrSessSecStatsRxDataBytes,
--           mscAppnLsMigration,
--           mscAppnRtpIdleTimeouts,
--           mscAppnMaximumIsrSessions,
--           mscAppnDlciRowStatus,
--           mscAppnPortTotLinkActLim,
--           mscAppnRtpBytesResent,
--           mscAppnDluUsStatComponentName,
--           mscAppnDlciVcCallingDna,
--           mscAppnIsrSessSecStatsMaxRxBtuSize,
--           mscAppnDlciVcPeakOoSeqFrmForwarded,
--           mscAppnDlciVcFrmCongestedToSubnet,
--           mscAppnCosNodeMaxRouteAddResistance,
--           mscAppnDlurSupport,
--           mscAppnDluDlusName,
--           mscAppnRtpBurstSize,
--           mscAppnIsrSessLimitedResource,
--           mscAppnCosTgMaxSecurity,
--           mscAppnIsrSessPriStatsLsName,
--           mscAppnCosTgMaxUserDefParm3,
--           mscAppnLocateTimeout,
--           mscAppnCosTgMaxUserDefParm1,
--           mscAppnRtpShortReqTimeouts,
--           mscAppnFrSvcComponentName,
--           mscAppnIsrRxPacingWindow,
--           mscAppnDLURSecondaryDefDlusName,
--           mscAppnFrSvcRowStatus,
--           mscAppnLcnVcSegmentsSent,
--           mscAppnFrSvcMaximumCir,
--           mscAppnDlusRowStatus,
--           mscAppnDluDsStatTxFmdFrames,
--           mscAppnLcnVcSubnetRxPktSize,
--           mscAppnIsrSessPriStatsOdai,
--           mscAppnDlciVcDuplicatesFromSubnet,
--           mscAppnIsrSessSecStatsRowStatus,
--           mscAppnDlciBnnLsDefComponentName,
--           mscAppnAdjNnOutOfSeqTdus,
--           mscAppnLcnVcSubnetTxWindowSize,
--           mscAppnDnaCugDnic,
--           mscAppnLsMaxDelay,
--           mscAppnDlciDcRowStatus,
--           mscAppnDlusReqActPuTx,
--           mscAppnNnTgRowStatus,
--           mscAppnPortPropagationDelay,
--           mscAppnIsrSessSecStatsSidl,
--           mscAppnDluUsStatMaxRxBtuSize,
--           mscAppnDluSscpTxDataframes,
--           mscAppnLsPortName,
--           mscAppnDlciVcType,
--           mscAppnCosStorageType,
--           mscAppnLcnDcStorageType,
--           mscAppnCosTgMinConnectCost,
--           mscAppnCosTgRowStatus,
--           mscAppnLsDlcType,
--           mscAppnDlciUsageState,
--           mscAppnPortNonactXidExchLim,
--           mscAppnDLURStorageType,
--           mscAppnDlciBanComponentName,
--           mscAppnDluUsStatMaxTxPacWin,
--           mscAppnDlciVcSegmentsSent,
--           mscAppnNnNodeType,
--           mscAppnDluUsStatRxDataBytes,
--           mscAppnLcnVcPeakStackedAcksRx,
--           mscAppnIsrSessPriStatsCurRxPacWin,
--           mscAppnLocTgPropagationDelay,
--           mscAppnLsInMsgFrames,
--           mscAppnLsName,
--           mscAppnIsrSessSecStatsOdai,
--           mscAppnLocTgStatus,
--           mscAppnLsInSessionControlFrames,
--           mscAppnRtpStorageType,
--           mscAppnCosNodeMinRouteAddResistance,
--           mscAppnNnTgEffectiveCap,
--           mscAppnRtpPktResent,
--           mscAppnDirEntWildCard,
--           mscAppnFrSvcCurrentNumberOfSvcCalls,
--           mscAppnDlciVcFastSelectCall,
--           mscAppnLsInMsgBytes,
--           mscAppnDlciVcComponentName,
--           mscAppnLcnVcLocalRxPktSize,
--           mscAppnDlusPipeState,
--           mscAppnDirEntStorageType,
--           mscAppnCosNodeMinStatus,
--           mscAppnCosNodeRowStatus,
--           mscAppnLcnVcElapsedTimeTillNow,
--           mscAppnLcnComponentName,
--           mscAppnDlciVcMaxSubnetPktSize,
--           mscAppnDnaDefaultRecvFrmNetworkWindowSize,
--           mscAppnLsInXidFrames,
--           mscAppnIsrSessSecStatsSidh,
--           mscAppnDlusDactPuRx,
--           mscAppnDlciVcPriority,
--           mscAppnLsPropagationDelay,
--           mscAppnDlciVcSendSequenceNumber,
--           mscAppnDlciBanLsDefTgNum,
--           mscAppnDlusActivePUs,
--           mscAppnIsrSessPriStatsComponentName,
--           mscAppnFeatures,
--           mscAppnLsComponentName,
--           mscAppnDlciVcFrmLossTimeouts,
--           mscAppnLsInXidBytes,
--           mscAppnDnaOutDefaultPathReliability,
--           mscAppnDlciVcState,
--           mscAppnLsGoodXids,
--           mscAppnDlciVcSubnetRecoveries,
--           mscAppnDnaHgMAvailabilityDelta,
--           mscAppnLcnVcCallingDna,
--           mscAppnLsActualCpName,
--           mscAppnDluSscpComponentName,
--           mscAppnIsrSessSecStatsTxFmdFrames,
--           mscAppnCosTgStorageType,
--           mscAppnMdsTxAlertQueueSize,
--           mscAppnDnaCugComponentName,
--           mscAppnCosRowStatus,
--           mscAppnDnaDefaultRecvFrmNetworkThruputClass,
--           mscAppnLsDlcName,
--           mscAppnDluDsStatLsName,
--           mscAppnDlciDcRemoteDna,
--           mscAppnLcnVcTransferPriorityFromNetwork,
--           mscAppnDnaHgMHgAddrNumberingPlanIndicator,
--           mscAppnDlciBanLsDefBackupDlusName,
--           mscAppnDluUsStatMaxTxBtuSize,
--           mscAppnBlockNumber,
--           mscAppnPortComponentName,
--           mscAppnLsFeatures,
--           mscAppnHeapSpaceCurrent,
--           mscAppnDluSscpCurRxPacWin,
--           mscAppnCosTgMinPropDelay,
--           mscAppnRtpIdleTimer,
--           mscAppnLcnVcWrTriggers,
--           mscAppnDlciVcAccountingEnd,
--           mscAppnPortUserDefinedParm2,
--           mscAppnIsrSessSecStatsRxFmdFrames,
--           mscAppnDlusDactLuRx,
--           mscAppnDLURDlusRetryLimit,
--           mscAppnLcnVcDuplicatesFromSubnet,
--           mscAppnCosTgMaxModemClass,
--           mscAppnDluDsStatMaxRxPacWin,
--           mscAppnDluSscpSessActive,
--           mscAppnDlciBanLsDefCpCpSessionSupport,
--           mscAppnDlciMeasurementInterval,
--           mscAppnAdjNnCpCpSessStatus,
--           mscAppnRtpPktTx,
--           mscAppnRtpRemoteCpName,
--           mscAppnLcnDcRowStatus,
--           mscAppnComponentName,
--           mscAppnDlciVcRcosToNetwork,
--           mscAppnDlusReqDactPuRspRx,
--           mscAppnIsrSessStorageType,
--           mscAppnNnRouteAdditionResistance,
--           mscAppnLocTgComponentName,
--           mscAppnIsrSessPriStatsRxRuSize,
--           mscAppnRtpCosName,
--           mscAppnPortState,
--           mscAppnLsLinkStationSubState,
--           mscAppnHeapSpaceLimit }
-- STATUS  mandatory
-- DESCRIPTION
--   "A list of all current accessible leaf objects."

appnGroup OBJECT IDENTIFIER ::= { appnMIB 1 }
appnGroupCA OBJECT IDENTIFIER ::= { appnGroup 1 }
appnGroupCA02 OBJECT IDENTIFIER ::= { appnGroupCA 3 }
appnGroupCA02DevelopmentLoad OBJECT IDENTIFIER ::= { appnGroupCA02 1 }
appnGroupCA0214 OBJECT IDENTIFIER ::= { appnGroupCA02DevelopmentLoad 14 }
appnGroupCA0214A OBJECT IDENTIFIER ::= { appnGroupCA0214 1 }



-- Agent-Capabilities Statement:

-- PRODUCT-RELEASE "MscPassport Release 1.2 Appn."
-- STATUS          mandatory
-- DESCRIPTION     "Carrier Passport Appn MIB: MIB Version CA0214A,
--                  Software Version CA0214A."
-- SUPPORTS        Nortel-MsCarrier-MscPassport-AppnMIB
--    INCLUDES     { appnGroupCA0214A }

appnCapabilities OBJECT IDENTIFIER ::= { appnMIB 3 }
appnCapabilitiesCA OBJECT IDENTIFIER ::= { appnCapabilities 1 }
appnCapabilitiesCA02 OBJECT IDENTIFIER ::= { appnCapabilitiesCA 3 }
appnCapabilitiesCA02DevelopmentLoad OBJECT IDENTIFIER ::= { appnCapabilitiesCA02 1 }
appnCapabilitiesCA0214 OBJECT IDENTIFIER ::= { appnCapabilitiesCA02DevelopmentLoad 14 }
appnCapabilitiesCA0214A OBJECT IDENTIFIER ::= { appnCapabilitiesCA0214 1 }





END
