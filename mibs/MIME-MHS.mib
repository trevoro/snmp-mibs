-- WinAgents MIB Extraction Wizard
-- Extracted from rfc1495.txt 16.03.2005 20:20:18

MIME-MHS DEFINITIONS ::= BEGIN
	IMPORTS internet FROM RFC1155-SMI;


mail OBJECT IDENTIFIER ::= { internet 7 }

mime-mhs OBJECT IDENTIFIER ::= { mail 1 }

mime-mhs-headings OBJECT IDENTIFIER ::= { mime-mhs 1 }

id-hex-partial-message OBJECT IDENTIFIER ::=
        { mime-mhs-headings 1 }

id-hex-multipart-message OBJECT IDENTIFIER ::=
        { mime-mhs-headings 2 }


mime-mhs-bodies OBJECT IDENTIFIER ::= { mime-mhs 2 }


END
