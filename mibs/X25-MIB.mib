X25-MIB DEFINITIONS ::= BEGIN

	IMPORTS
		OBJECT-TYPE							FROM RFC-1212
		DisplayString						FROM RFC1213-MIB
		Counter, TimeTicks, enterprises		FROM RFC1155-SMI
		RowStatus							FROM SNMPv2-TC
		rs232PortIndex						FROM RS232-MIB
		TRAP-TYPE							FROM RFC-1215;


--	x25MIB MODULE-IDENTITY
--		LAST-UPDATED "9812230000Z"
--		ORGANIZATION "Northrop Grumman-Canada, Ltd."
--		CONTACT-INFO
--			"		Fulko K. Hew
--
--			Postal:	Northrop Grumman-Canada, Ltd.
--					777 Walkers Line
--					Burlington, Ontario
--					Canada
--					L7N 2G1
--
--			Tel:	+1 905 333 6000
--			Fax:	+1 905 333 6050
--
--			E-mail:	fulko@ngcan.com"
--		DESCRIPTION
--			"The MIB module to describe X.25 Level 3, Packet layer."

	ngcan			OBJECT IDENTIFIER ::= { enterprises 1978 }	-- Northrop Grumman-Canada, Ltd.
	tiger			OBJECT IDENTIFIER ::= { ngcan 2 }			-- Tiger (Network Access Device)

	x25MIB			OBJECT IDENTIFIER ::= { tiger 14 }

	x25L3			OBJECT IDENTIFIER ::= { x25MIB 1 }
	x25Traps		OBJECT IDENTIFIER ::= { x25MIB 2 }

	x25L3Traps		OBJECT IDENTIFIER ::= { x25Traps 1 }

	X25CallParamIndex ::= INTEGER
		-- A unique value, greater than zero, for each interface
		-- or interface sub-layer in the managed system.  It is
		-- recommended that values are assigned contiguously
		-- starting from 1.  The value for each interface sub-
		-- layer must remain constant at least from one re-
		-- initialization of the entity's network management
		-- system to the next re-initialization.

		-- InterfaceIndex contains the semantics of ifIndex and
		-- should be used for any objects defined on other mib
		-- modules that need these semantics.

	InterfaceIndex ::= INTEGER
		-- A unique value, greater than zero, for each interface
		-- or interface sub-layer in the managed system.  It is
		-- recommended that values are assigned contiguously
		-- starting from 1.  The value for each interface sub-
		-- layer must remain constant at least from one re-
		-- initialization of the entity's network management
		-- system to the next re-initialization."

	X121Address ::= OCTET STRING (SIZE(0..20))
		-- 0 to 20 bytes in length containing the ASCII
		-- characters [0-9], each octet contains one digit
		-- of the address.

		-- ###########################################################
		--				X.25 Administration Table
		-- ###########################################################

	x25AdmnTable OBJECT-TYPE
		SYNTAX		SEQUENCE OF X25AdmnEntry
		ACCESS		not-accessible
		STATUS		mandatory
		DESCRIPTION
			"This table contains configuration, channel assignments
			and statistics for an X.25 Packet Level Entity (PLE).
			The values are as last set by the administrator and/or
			the values actually in use by the PLE."
		::= { x25L3 1 }

	x25AdmnEntry OBJECT-TYPE
		SYNTAX		X25AdmnEntry
		ACCESS		not-accessible
		STATUS		mandatory
		DESCRIPTION
			"Entries of x25AdmnTable."
		INDEX		{ x25AdmnIndex }
		::= { x25AdmnTable 1 }

	X25AdmnEntry ::= SEQUENCE {
		x25AdmnIndex						InterfaceIndex,
		x25AdmnInterfaceMode				INTEGER,
		x25AdmnPacketSequencing				INTEGER,
		x25AdmnRestartTimer					INTEGER,
		x25AdmnCallTimer					INTEGER,
		x25AdmnResetTimer					INTEGER,
		x25AdmnClearTimer					INTEGER,
		x25AdmnWindowTimer					INTEGER,
		x25AdmnDataRxmtTimer				INTEGER,
		x25AdmnInterruptTimer				INTEGER,
		x25AdmnRejectTimer					INTEGER,
		x25AdmnRegistrationRequestTimer		INTEGER,
		x25AdmnRestartCount					INTEGER,
		x25AdmnResetCount					INTEGER,
		x25AdmnClearCount					INTEGER,
		x25AdmnDataRxmtCount				INTEGER,
		x25AdmnRejectCount					INTEGER,
		x25AdmnRegistrationRequestCount		INTEGER,
		x25AdmnNumberPVCs					INTEGER,
		x25AdmnDefCallParamId				X25CallParamIndex,
		x25AdmnProtocolVersionSupported		INTEGER,
		x25AdmnRegistrationMode				INTEGER,
		x25AdmnDiagnosticMode				INTEGER,
		x25AdmnInterruptSize				INTEGER,
		x25AdmnMaxTxWindow					INTEGER,
		x25AdmnMaxRxWindow					INTEGER,
		x25AdmnFacilityLength				INTEGER,
		x25AdmnCallDataSize					INTEGER,
		x25AdmnFastSelectCallDataSize		INTEGER,
		x25AdmnExtendedClear				INTEGER,
		x25AdmnCause						INTEGER,
		x25AdmnABit							INTEGER,
		x25AdmnRRTrigger					INTEGER,
		x25AdmnRRTimer						INTEGER,
		x25AdmnRRPiggy						INTEGER,
		x25AdmnTxRejectMode					INTEGER,
		x25AdmnRxRejectMode					INTEGER,
		x25AdmnDBit							INTEGER,
		x25AdmnR28Action					INTEGER,

		--
		-- Channel Assignments
		--

		x25ChannelLIC						INTEGER,
		x25ChannelHIC						INTEGER,
		x25ChannelLTC						INTEGER,
		x25ChannelHTC						INTEGER,
		x25ChannelLOC						INTEGER,
		x25ChannelHOC						INTEGER,

		--
		-- Statistics
		--

		x25StatInCalls						Counter,
		x25StatInCallRefusals				Counter,
		x25StatInProviderInitiatedClears	Counter,
		x25StatInRemotelyInitiatedResets	Counter,
		x25StatInProviderInitiatedResets 	Counter,
		x25StatInRestarts					Counter,
		x25StatInDataPackets				Counter,
		x25StatInAccusedOfProtocolErrors	Counter,
		x25StatInInterrupts					Counter,
		x25StatOutCallAttempts				Counter,
		x25StatOutCallFailures				Counter,
		x25StatOutInterrupts				Counter,
		x25StatOutDataPackets				Counter,
		x25StatPVCCircuits					Counter,
		x25StatSVCCircuits					Counter,
		x25StatRestartTimeouts				Counter,
		x25StatCallTimeouts					Counter,
		x25StatResetTimeouts				Counter,
		x25StatClearTimeouts				Counter,
		x25StatDataRxmtTimeouts				Counter,
		x25StatInterruptTimeouts			Counter,
		x25StatRetryCountExceededs			Counter,
		x25StatClearCountExceededs			Counter,

		x25AdminTrapControl					INTEGER
		}

	x25AdmnIndex OBJECT-TYPE
		SYNTAX		InterfaceIndex
		ACCESS		read-write
		STATUS		mandatory
		DESCRIPTION
			"The ifIndex value for the X.25 Interface."
		::= { x25AdmnEntry 1 }

	x25AdmnInterfaceMode OBJECT-TYPE
		SYNTAX		INTEGER {
			dte	(1),
			dce	(2),
			dxe	(3)
			}
		ACCESS		read-write
		STATUS		mandatory
		DESCRIPTION
			"Identifies DCE/DTE mode in which the interface operates.
			A value of dxe indicates the mode will be determined by XID
			negotiation."
		REFERENCE
			"10733 5.9 interfaceMode"
		::= { x25AdmnEntry 2 }

	x25AdmnPacketSequencing OBJECT-TYPE
		SYNTAX		INTEGER {
			modulo8		(1),
			modulo128	(2)
			}
		ACCESS		read-write
		STATUS		mandatory
		DESCRIPTION
			"The modulus of the packet sequence number space."
		REFERENCE
			"10733 extendedPacketSequencing; See ISO 8208 Section 7.1.1"
		::= { x25AdmnEntry 3 }

	x25AdmnRestartTimer OBJECT-TYPE
		SYNTAX		INTEGER (0..320000)
		ACCESS		read-write
		STATUS		mandatory
		DESCRIPTION
			"The T20 restart timer in milliseconds.
			UNITS: milliseconds"
		REFERENCE
			"10733 5.9 restartTime See ISO 8208 Section 4.1, table 26"
		::= { x25AdmnEntry 4 }

	x25AdmnCallTimer OBJECT-TYPE
		SYNTAX		INTEGER (0..320000)
		ACCESS		read-write
		STATUS		mandatory
		DESCRIPTION
			"The T21 Call timer in milliseconds.
			UNITS: milliseconds"
		REFERENCE
			"10733 callTime; See ISO 8208 Section 5.2.1, table 26"
		::= { x25AdmnEntry 5 }

	x25AdmnResetTimer OBJECT-TYPE
		SYNTAX		INTEGER (0..320000)
		ACCESS		read-write
		STATUS		mandatory
		DESCRIPTION
			"The T22 Reset timer in milliseconds.
			UNITS: milliseconds"
		REFERENCE
			"10733 resetTime; See ISO 8208 Section 8.1, table 26"
		::= { x25AdmnEntry 6 }

	x25AdmnClearTimer OBJECT-TYPE
		SYNTAX		INTEGER (0..320000)
		ACCESS		read-write
		STATUS		mandatory
		DESCRIPTION
			"The T23 Clear timer in milliseconds.
			UNITS: milliseconds"
		REFERENCE
			"10733 clearTime; See ISO 8208 Section 5.5.1, table 26"
		::= { x25AdmnEntry 7 }

	x25AdmnWindowTimer OBJECT-TYPE
		SYNTAX		INTEGER (0..320000)
		ACCESS		read-write
		STATUS		mandatory
		DESCRIPTION
			"The T24 window status transmission timer in milliseconds.
			A value of 0 indicates no window timer in use.
			UNITS: milliseconds"
		REFERENCE
			"10733 5.10.1 windowTime (opt);
			See ISO 8208 Section 11.2.2, table 26"
		DEFVAL		{ 60000 }
		::= { x25AdmnEntry 8 }

	x25AdmnDataRxmtTimer OBJECT-TYPE
		SYNTAX		INTEGER (0..320000)
		ACCESS		read-write
		STATUS		mandatory
		DESCRIPTION
			"The T25 data retransmission timer in milliseconds.
			A value of 0 indicates no data retransmission timer in use.
			UNITS: milliseconds"
		REFERENCE
			"10733 5.10.1 dataRetransmissionTime (opt);
			See ISO 8208 Section 11.2.1, table 26"
		::= { x25AdmnEntry 9 }

	x25AdmnInterruptTimer OBJECT-TYPE
		SYNTAX		INTEGER (0..320000)
		ACCESS		read-write
		STATUS		mandatory
		DESCRIPTION
			"The T26 interrupt timer in milliseconds.
			A value of 0 indicates no interrupt timer in use.
			UNITS: milliseconds"
		REFERENCE
			"10733 interruptTime;
			See ISO 8208 Section 6.8.1, table 26"
		::= { x25AdmnEntry 10 }

	x25AdmnRejectTimer OBJECT-TYPE
		SYNTAX		INTEGER (0..320000)
		ACCESS		read-write
		STATUS		mandatory
		DESCRIPTION
			"The T27 Reject retransmission timer in milliseconds.
			A value of 0 indicates no reject timer in use.
			UNITS: milliseconds"
		REFERENCE
			"10733 5.10.1 dataRejectTime (opt);
			See ISO 8208 Section 13.4.1, table 26"
		::= { x25AdmnEntry 11 }

	x25AdmnRegistrationRequestTimer OBJECT-TYPE
		SYNTAX		INTEGER (0..320000)
		ACCESS		read-write
		STATUS		mandatory
		DESCRIPTION
			"The T28 registration timer in milliseconds.
			A value of 0 indicates no registration timer in use.
			UNITS: milliseconds"
		REFERENCE
			"10733 5.8.1 registrationRequestTime (opt)
			See ISO 8208	Section 13.1.1.1, table 26"
		::= { x25AdmnEntry 12 }

	x25AdmnRestartCount OBJECT-TYPE
		SYNTAX		INTEGER (0..32000)
		ACCESS		read-write
		STATUS		mandatory
		DESCRIPTION
			"The R20 restart retransmission count."
		REFERENCE
			"10733 5.9 restartCount;
			See ISO 8208	Section 4.1, table 27"
		::= { x25AdmnEntry 13 }

	x25AdmnResetCount OBJECT-TYPE
		SYNTAX		INTEGER (0..32000)
		ACCESS		read-write
		STATUS		mandatory
		DESCRIPTION
			"The r22 Reset retransmission count."
		REFERENCE
			"10733 resetCount;
			See section ISO 8208 8.1, table 27"
		::= { x25AdmnEntry 14 }

	x25AdmnClearCount OBJECT-TYPE
		SYNTAX		INTEGER (0..32000)
		ACCESS		read-write
		STATUS		mandatory
		DESCRIPTION
			"The r23 Clear retransmission count."
		REFERENCE
			"10733 clearCount;
			See ISO 8208 Section 5.5.1, table 27"
		::= { x25AdmnEntry 15 }

	x25AdmnDataRxmtCount OBJECT-TYPE
		SYNTAX		INTEGER (0..32000)
		ACCESS		read-write
		STATUS		mandatory
		DESCRIPTION
			"The R25 Data retransmission count.  This value is irrelevant
			if the x25AdmnDataRxmtTimer indicates no timer in use."
		REFERENCE
			"10733 5.10.1 dataRetransmissionCount (opt)
			See ISO 8208 Section 11.2.1, table 27"
		::= { x25AdmnEntry 16 }

	x25AdmnRejectCount OBJECT-TYPE
		SYNTAX		INTEGER (0..32000)
		ACCESS		read-write
		STATUS		mandatory
		DESCRIPTION
			"The R27 reject retransmission count.  This value is
			irrelevant if the x25AdmnRejectTimer indicates no timer in use."
		REFERENCE
			"10733 5.10.1 dataRejectCount (opt)"
		::= { x25AdmnEntry 17 }

	x25AdmnRegistrationRequestCount OBJECT-TYPE
		SYNTAX		INTEGER (0..32000)
		ACCESS		read-write
		STATUS		mandatory
		DESCRIPTION
			"The R28 Registration retransmission Count.  This value is irrelevant
			if the x25AdmnRegistrationRequestTimer indicates no timer in use."
		REFERENCE
			"10733 5.8.1 registrationRequestCount (opt);
			See ISO 8208	Section 13.1.1.1, table 27"
		::= { x25AdmnEntry 18 }

	x25AdmnNumberPVCs OBJECT-TYPE
		SYNTAX		INTEGER (0..4096)
		ACCESS		read-write
		STATUS		mandatory
		DESCRIPTION
			"The number of PVC configured for this PLE.  The PVCs use channel
			numbers from 1 to this number. Set to 0 for no PVCs."
		::= { x25AdmnEntry 19 }

	x25AdmnDefCallParamId OBJECT-TYPE
		SYNTAX		X25CallParamIndex
		ACCESS		read-write
		STATUS		mandatory
		DESCRIPTION
			"This identifies the instance of the x25CallParmIndex for the entry in
			the x25CallParmTable which contains the default call parameters for this PLE."
		::= { x25AdmnEntry 20 }

	x25AdmnProtocolVersionSupported OBJECT-TYPE
		SYNTAX		INTEGER {
			ccitt-1976	(1),
			ccitt-1980	(2),
			ccitt-1984	(3),
			ccitt-1988	(4),
			ccitt-1992	(5),
			qllc		(6)
			}
		ACCESS		read-write
		STATUS		mandatory
		DESCRIPTION
			"Identifies the version of the X.25 protocol this interface should support."
		DEFVAL		{ ccitt-1992 }
		::= { x25AdmnEntry 21 }

	x25AdmnRegistrationMode OBJECT-TYPE
		SYNTAX		INTEGER {
			none	(1),
			auto	(2),
			user	(3)
			}
		ACCESS		read-write
		STATUS		mandatory
		DESCRIPTION
			"Defines how registration exchanges are handled.
			A value of auto indicates that the DTE always sends
			empty request at connection time and that a DCE automatically
			answers incoming requests. A value of user indicates that registration
			packets are handled at the user level and the packet level still updates
			its internal configuration according to the the confirmation content."
		DEFVAL		{ none }
		::= { x25AdmnEntry 22 }

	x25AdmnDiagnosticMode OBJECT-TYPE
		SYNTAX		INTEGER {
			standard	(1),
			on			(2),
			off			(3)
			}
		ACCESS		read-write
		STATUS		mandatory
		DESCRIPTION
			"Controls the generation of diagnostic packets.
			A value of standard means send diagnostics if configured as a DCE
			only, as per CCITT specification.  A value of on always sends diagnostic
			packets, and a value of off will never send diagnostic packets."
		DEFVAL		{ off }
		::= { x25AdmnEntry 23 }

	x25AdmnInterruptSize OBJECT-TYPE
		SYNTAX		INTEGER (1..32)
		ACCESS		read-write
		STATUS		mandatory
		DESCRIPTION
			"Defines the maximum user data size in interrupt packets.

			Use 1 for networks compliant with 1980 CCITT recommendation
			and before, use 32 for 1984 and later compliant networks,
			any other value is used only when dealing with non CCITT
			compliant implementations."
		DEFVAL		{ 32 }
		::= { x25AdmnEntry 24 }

	x25AdmnMaxTxWindow OBJECT-TYPE
		SYNTAX		INTEGER (1..128)
		ACCESS		read-write
		STATUS		mandatory
		DESCRIPTION
			"Specifies the maximum transmit window size that can be negotiated.
			1 through 7 for modulo 8.
			1 through 128 for modulo 128."
		DEFVAL		{ 2 }
		::= { x25AdmnEntry 25 }

	x25AdmnMaxRxWindow OBJECT-TYPE
		SYNTAX		INTEGER (1..128)
		ACCESS		read-write
		STATUS		mandatory
		DESCRIPTION
			"Specifies the maximum receive window size that can be negotiated.
			1 through 7 for modulo 8.
			1 through 128 for modulo 128."
		DEFVAL		{ 2 }
		::= { x25AdmnEntry 26 }

	x25AdmnFacilityLength OBJECT-TYPE
		SYNTAX		INTEGER (0..255)
		ACCESS		read-write
		STATUS		mandatory
		DESCRIPTION
			"Defines the maximum length of the Facility field.

			Use 63 for 1980 or earlier complience.
			Use 109 for 1984 and later compliant networks.
			Other value are used only when dealing with non CCITT
			compliant implementations."
		DEFVAL		{ 109 }
		::= { x25AdmnEntry 27 }

	x25AdmnCallDataSize OBJECT-TYPE
		SYNTAX		INTEGER (0..255)
		ACCESS		read-write
		STATUS		mandatory
		DESCRIPTION
			"Defines the maximum length of the user data in call
			request/indication packets when fast select not used.

			Use 16 for CCITT complience.
			Other value are used only when dealing with non CCITT
			compliant implementations."
		DEFVAL		{ 16 }
		::= { x25AdmnEntry 28 }

	x25AdmnFastSelectCallDataSize OBJECT-TYPE
		SYNTAX		INTEGER (0..255)
		ACCESS		read-write
		STATUS		mandatory
		DESCRIPTION
			"Defines the maximum length of the user data in call
			request/indication packets when fast select is used.

			Use 128 for CCITT complience.
			Other value are used only when dealing with non CCITT compliant implementations."
		DEFVAL		{ 128 }
		::= { x25AdmnEntry 29 }

	x25AdmnExtendedClear OBJECT-TYPE
		SYNTAX		INTEGER {
			off		(1),
			on		(2),
			convert	(3)
			}
		ACCESS		read-write
		STATUS		mandatory
		DESCRIPTION
			"Controls support for extended clear format (allow addresses and
			facilities in clear/clear cf packets).
			A value of on means that the extended clear format is supported.
			A value of off means that the extended clear is not supported,
			receipt from the user is an error.
			A value of convert means accept extended clears from the user but
			convert them to short format before transmission to the network,
			accept whatever the network sends us.

			Note:	The extended format is used in a clear if fast select is
					present in the facility field, no matter what the setting
					of this parameter is."
		DEFVAL		{ off }
		::= { x25AdmnEntry 30 }

	x25AdmnCause OBJECT-TYPE
		SYNTAX		INTEGER {
			asis		(1),
			ccitt-80	(2),
			ccitt-84	(3),
			clear		(4)
			}
		ACCESS		read-write
		STATUS		mandatory
		DESCRIPTION
			"Controls how a cause field from the user is converted.
			A value of asis means send the user cause as is.  A value of
			ccitt-80 means convert to 1980 format (clear if DTE, cause & 0x07F
			if DCE). A value of ccitt-84 means use 1984 format (0 or
			cause | 0x80 if DTE, cause & 0x07F if DCE).  A value of clear means
			always clear the cause fields from the user."
		DEFVAL		{ ccitt-84 }
		::= { x25AdmnEntry 31 }

	x25AdmnABit OBJECT-TYPE
		SYNTAX		INTEGER {
			on	(1),
			off	(2),
			ok	(3)
			}
		ACCESS		read-write
		STATUS		mandatory
		DESCRIPTION
			"x25AdmnABit defines how long addresses, (up to 17 digits,) are handled.

			A value of on, means always use the long address format.
			A value of off, means always use the short address format.
			A value of ok, means use the long format, but accept short
			addresses from the network."
		DEFVAL		{ off }
		::= { x25AdmnEntry 32 }

	x25AdmnRRTrigger OBJECT-TYPE
		SYNTAX		INTEGER (0..256)
		ACCESS		read-write
		STATUS		mandatory
		DESCRIPTION
			"This defines when the frame level sends RR.

			0:	Only send RR when the window is full. Very inefficient
				as it always causes the remote to enter flow control
				situations. Not recommended.

			1:	Send RR when receiving one mode data packet would make
				the window full.  Suggested value on modulo 7 point-to- point
				links with small transit delays.

			>=k:	If the value of the parameter is greater than the window
					size, this causes RR packets to always be transmitted
					immediately as soon as a data packet is received. To
					obtain this mode of operation whatever the negitiated
					window size may be, it is suggested to set the value of
					this parameter to 128.

			< k:	Use the specified value,

			256:	This special value causes RR packets transmission to occur
					whenever the receive window is half full.

			Where k is the value of lapbAdmnKWindowSize.
			(default = >=k)"
		::= { x25AdmnEntry 33 }

	x25AdmnRRTimer OBJECT-TYPE
		SYNTAX		INTEGER (0..320000)
		ACCESS		read-write
		STATUS		mandatory
		DESCRIPTION
			"This x25AdmnRRTimer only causes the transmission of an
			RR Packet when there are outstanding packets to acknowledge
			to the remote.  When the transmission of RR packets to the
			remote is delayed because the x25AdmnRRTrigger value is
			set to a value within the receive window, this timer is used
			to force the transmission of RR packets after some time. Without
			this timer, delaying RR Packets would cause the last packets
			of a transaction never to be acknowledged.

			Please note that this timer is not similar to the T24 timer.
			The T24 timer causes an RR packet to be sent whenever no packet
			carrying an ack has been sent for a while.  In addition, the
			duration of T24 is typically fairly large (60 seconds recommended),
			while this RR timer should be much smaller to ensure that packets
			are always acknowledged in a reasonable amount of time.

			Note:	The time is in milliseconds.

			Note:	Setting x25AdmnRRTrigger to a value outside of the
					receive window or setting this timer value to 0 force
					RR packets to always be transmitted as soon as a data
					packet is received from the remote without any delay.
			UNITS: milliseconds"
		DEFVAL		{ 2000 }
		::= { x25AdmnEntry 34 }

	x25AdmnRRPiggy OBJECT-TYPE
		SYNTAX		INTEGER {
			off	(1),
			on	(2)
			}
		ACCESS		read-write
		STATUS		mandatory
		DESCRIPTION
			"This specifies whether the frame level can
			'piggyback' acknowledgements in I frames."
		DEFVAL		{ on }
		::= { x25AdmnEntry 35 }

	x25AdmnTxRejectMode OBJECT-TYPE
		SYNTAX		INTEGER {
			reset		(1),
			rejectReset	(2),
			sendAlways	(3)
			}
		ACCESS		read-write
		STATUS		mandatory
		DESCRIPTION
			"Defines how packet level handles the reception of out of
			sequence data packets.
			A value of reset will reset the virtual circuit.
			A value of rejectReset will send reject packet if configured as a DTE.
			otherwise it will reset the virtual circuit.
			A value of sendAlways will cause a reject packet to always be sent,
			even when configured as a DCE.

			Note:	CCITT compliance requires the selection of either reset or rejectReset.
					The CCITT does not allow a DCE to send a reject."
		DEFVAL		{ reset }
		::= { x25AdmnEntry 36 }

	x25AdmnRxRejectMode OBJECT-TYPE
		SYNTAX		INTEGER {
			reset		(1),
			retxReset	(2),
			retxAlways	(3)
			}
		ACCESS		read-write
		STATUS		mandatory
		DESCRIPTION
			"Defines how packet level handles the reception of reject packets.

			A value of reset will reset the virtual circuit.
			A value of retxReset will retransmit packets if configured as a DCE.
			otherwise it will reset the virtual circuit.
			A value of retxAlways will cause retransmition of data packets
			even when configured as a DTE.

			Note:	CCITT compliance requires the selection of either reset or retxReset.
					The CCITT does not allow a DTE to retransmit."
		DEFVAL		{ reset }
		::= { x25AdmnEntry 37 }

	x25AdmnDBit OBJECT-TYPE
		SYNTAX		INTEGER {
			no		(1),
			ok		(2),
			bill	(3)
			}
		ACCESS		read-write
		STATUS		mandatory
		DESCRIPTION
			"Defines how packet level handles the D bit.

			A value of no indicates that the use of the D bit not allowed.
			A value of ok indicates that the use of the D bit is allowed.
			A value of bill indicates that the use of the D bit is allowed
			only if we are not billed for the call."
		DEFVAL		{ no }
		::= { x25AdmnEntry 38 }

	x25AdmnR28Action OBJECT-TYPE
		SYNTAX		INTEGER {
			fail	(1),
			ignore	(2)
			}
		ACCESS		read-write
		STATUS		mandatory
		DESCRIPTION
			"Selects the packet level action after R28 expirations of the
			registration timer T28.

			A value of fail means the link is considered as non operational
			and is disconnected. The x25AdmnRegistrationMode parameter
			determine if the complete reconnection procedure is tried again.

			A value of ignore means: Go to the ready state using the default link
			configuration, as if the registration never occurred."
		DEFVAL		{ ignore }
		::= { x25AdmnEntry 39 }

		--	MIB-II also provides:
		--
		-- ifDescr:
		--		On an X.25 interface this must include sufficient information to enable
		--		the system's administrator to determine the appropriate configuration
		--		information on a system having multiple X.25 subnetworks.
		--
		-- ifType: ddn-x25 or rfc877-x25
		--		an interface of type ddn-x25 will use an algorithm to translate between
		--		X.121 address and IP addresses.
		--		An interface of type rfc877-x25 will use a configuration table to translate
		--		between X.121 addresses and IP addresses.
		--
		-- ifMtu:
		--		the maximum PDU a higher layer can pass to X.25 or receive from X.25
		--
		-- ifSpeed:
		--		This will be the value of the local clock for this line.
		--		A value of zero indicates external clocking.
		--
		-- ifAdminStatus:
		--
		-- ifOperStatus
		--
		-- ifLastChange

		-- ###########################################################
		--			X.25 Channel Information
		-- ###########################################################

	x25ChannelLIC OBJECT-TYPE
		SYNTAX		INTEGER (0..4095)
		ACCESS		read-write
		STATUS		mandatory
		DESCRIPTION
			"Lowest Incoming channel.
			A value of 0 indicates that no LCN is available."
		DEFVAL		{ 0 }
		::= { x25AdmnEntry 40 }

	x25ChannelHIC OBJECT-TYPE
		SYNTAX		INTEGER (0..4095)
		ACCESS		read-write
		STATUS		mandatory
		DESCRIPTION
			"Highest Incoming channel.
			A value of 4095 indicates that no LCN is available."
		DEFVAL		{ 4095 }
		::= { x25AdmnEntry 41 }

	x25ChannelLTC OBJECT-TYPE
		SYNTAX		INTEGER (0..4095)
		ACCESS		read-write
		STATUS		mandatory
		DESCRIPTION
			"Lowest Two-way channel.
			A value of 0 indicates that no LCN is available."
		DEFVAL		{ 0 }
		::= { x25AdmnEntry 42 }

	x25ChannelHTC OBJECT-TYPE
		SYNTAX		INTEGER (0..4095)
		ACCESS		read-write
		STATUS		mandatory
		DESCRIPTION
			"Highest Two-way channel.
			A value of 0 indicates that no LCN is available."
		DEFVAL		{ 4095 }
		::= { x25AdmnEntry 43 }

	x25ChannelLOC OBJECT-TYPE
		SYNTAX		INTEGER (0..4095)
		ACCESS		read-write
		STATUS		mandatory
		DESCRIPTION
			"Lowest outgoing channel.
			A value of 0 indicates that no LCN is available."
		DEFVAL		{ 0 }
		::= { x25AdmnEntry 44 }

	x25ChannelHOC OBJECT-TYPE
		SYNTAX		INTEGER (0..4095)
		ACCESS		read-write
		STATUS		mandatory
		DESCRIPTION
			"Highest outgoing channel.
			A value of 0 indicates that no LCN is available."
		DEFVAL		{ 4095 }
		::= { x25AdmnEntry 45 }

		-- ###########################################################
		--			X.25 Statistics Information
		-- ###########################################################

	x25StatInCalls OBJECT-TYPE
		SYNTAX		Counter
		ACCESS		read-only
		STATUS		mandatory
		DESCRIPTION
			"The number of Call Request/Indication packets received."
		::= { x25AdmnEntry 46 }

	x25StatInCallRefusals OBJECT-TYPE
		SYNTAX		Counter
		ACCESS		read-only
		STATUS		mandatory
		DESCRIPTION
			"The number of incoming calls refused.  This includes calls refused by
			the PLE and by higher layers.  This also includes calls cleared because
			of restricted fast select."
		::= { x25AdmnEntry 47 }

	x25StatInProviderInitiatedClears OBJECT-TYPE
		SYNTAX		Counter
		ACCESS		read-only
		STATUS		mandatory
		DESCRIPTION
			"The number of Clear Request/Indication packets sent."
		::= { x25AdmnEntry 48 }

	x25StatInRemotelyInitiatedResets OBJECT-TYPE
		SYNTAX		Counter
		ACCESS		read-only
		STATUS		mandatory
		DESCRIPTION
			"The number of Reset Request/Indication packets received."
		::= { x25AdmnEntry 49 }

	x25StatInProviderInitiatedResets OBJECT-TYPE
		SYNTAX		Counter
		ACCESS		read-only
		STATUS		mandatory
		DESCRIPTION
			"The number of Reset Request/Indication packets sent."
		::= { x25AdmnEntry 50 }

	x25StatInRestarts OBJECT-TYPE
		SYNTAX		Counter
		ACCESS		read-only
		STATUS		mandatory
		DESCRIPTION
			"The number of Restart Request/Indication packets received."
		::= { x25AdmnEntry 51 }

	x25StatInDataPackets OBJECT-TYPE
		SYNTAX		Counter
		ACCESS		read-only
		STATUS		mandatory
		DESCRIPTION
			"The number of data packets received."
		REFERENCE
			"10733 5.9 dataPacketsReceived."
		::= { x25AdmnEntry 52 }

	x25StatInAccusedOfProtocolErrors OBJECT-TYPE
		SYNTAX		Counter
		ACCESS		read-only
		STATUS		mandatory
		DESCRIPTION
			"The number of packets received containing a procedure error cause
			code.  These include clear, reset, restart, or diagnostic packets."
		REFERENCE
			"CD 10733 5.9 accusedOfProtocolError"
		::= { x25AdmnEntry 53 }

	x25StatInInterrupts OBJECT-TYPE
		SYNTAX		Counter
		ACCESS		read-only
		STATUS		mandatory
		DESCRIPTION
			"The number of interrupt packets received by the PLE or over the PVC/VC."
		REFERENCE
			"10733 interruptPacketsReceived"
		::= { x25AdmnEntry 54 }

	x25StatOutCallAttempts OBJECT-TYPE
		SYNTAX		Counter
		ACCESS		read-only
		STATUS		mandatory
		DESCRIPTION
			"The number of calls attempted."
		REFERENCE
			"10733 5.9 callAttempts"
		::= { x25AdmnEntry 55 }

	x25StatOutCallFailures OBJECT-TYPE
		SYNTAX		Counter
		ACCESS		read-only
		STATUS		mandatory
		DESCRIPTION
			"The number of call attempts which failed.  This includes calls
			that were cleared because of restrictive fast select."
		::= { x25AdmnEntry 56 }

	x25StatOutInterrupts OBJECT-TYPE
		SYNTAX		Counter
		ACCESS		read-only
		STATUS		mandatory
		DESCRIPTION
			"The number of interrupt packets send by the PLE or over the PVC/VC."
		REFERENCE
			"10733 InterruptPacketsSent"
		::= { x25AdmnEntry 57 }

	x25StatOutDataPackets OBJECT-TYPE
		SYNTAX		Counter
		ACCESS		read-only
		STATUS		mandatory
		DESCRIPTION
			"The number of data packets sent by this PLE."
		REFERENCE
			"10733 dataPacketSent"
		::= { x25AdmnEntry 58 }

	x25StatPVCCircuits OBJECT-TYPE
		SYNTAX		Counter
		ACCESS		read-only
		STATUS		mandatory
		DESCRIPTION
			"The number of active PVC circuits."
		::= { x25AdmnEntry 59 }

	x25StatSVCCircuits OBJECT-TYPE
		SYNTAX		Counter
		ACCESS		read-only
		STATUS		mandatory
		DESCRIPTION
			"The number of active SVC Circuits.  This includes call indications
			received but not yet acknowledged."
		::= { x25AdmnEntry 60 }

	x25StatRestartTimeouts OBJECT-TYPE
		SYNTAX		Counter
		ACCESS		read-only
		STATUS		mandatory
		DESCRIPTION
			"The number of times the T20 restart timer expired."
		REFERENCE
			"10733 5.9 restartTimeouts"
		::= { x25AdmnEntry 61 }

	x25StatCallTimeouts OBJECT-TYPE
		SYNTAX		Counter
		ACCESS		read-only
		STATUS		mandatory
		DESCRIPTION
			"The number of times the T21 call timer expired."
		REFERENCE
			"10733 5.9 callTimeouts"
		::= { x25AdmnEntry 62 }

	x25StatResetTimeouts OBJECT-TYPE
		SYNTAX		Counter
		ACCESS		read-only
		STATUS		mandatory
		DESCRIPTION
			"The number of times the T22 reset timer expired."
		REFERENCE
			"10733 5.9 resetTimeouts"
		::= { x25AdmnEntry 63 }

	x25StatClearTimeouts OBJECT-TYPE
		SYNTAX		Counter
		ACCESS		read-only
		STATUS		mandatory
		DESCRIPTION
			"The number of times the T23 clear timer expired."
		REFERENCE
			"10733 5.9 clearTimeouts"
		::= { x25AdmnEntry 64 }

	x25StatDataRxmtTimeouts OBJECT-TYPE
		SYNTAX		Counter
		ACCESS		read-only
		STATUS		mandatory
		DESCRIPTION
			"The number of times the T25 data timer expired."
		REFERENCE
			"10733 5.9 dataRetransmissionsTimerExpiries"
		::= { x25AdmnEntry 65 }

	x25StatInterruptTimeouts OBJECT-TYPE
		SYNTAX		Counter
		ACCESS		read-only
		STATUS		mandatory
		DESCRIPTION
			"The number of times the T26 interrupt timer expired."
		REFERENCE
			"10733 5.9 interruptTimerExpires"
		::= { x25AdmnEntry 66 }

	x25StatRetryCountExceededs OBJECT-TYPE
		SYNTAX		Counter
		ACCESS		read-only
		STATUS		mandatory
		DESCRIPTION
			"The number of times a retry counter was exhausted."
		REFERENCE
			"10733 5.9 retryCountsExceeded"
		::= { x25AdmnEntry 67 }

	x25StatClearCountExceededs OBJECT-TYPE
		SYNTAX		Counter
		ACCESS		read-only
		STATUS		mandatory
		DESCRIPTION
			"The number of times the R23 clear count was exceeded."
		REFERENCE
			"10733 5.9 clearCountsExceeded"
		::= { x25AdmnEntry 68 }

	x25AdminTrapControl OBJECT-TYPE
		SYNTAX		INTEGER {
			disabled	(1),
			enabled		(2)
		}
		ACCESS		read-write
		STATUS		mandatory
		DESCRIPTION
			"If enabled, it allows the system to generate x25Restart and x25VC traps"
		DEFVAL		{ disabled }
		::= { x25AdmnEntry 69 }



		--	MIB-II also contains:
		--
		-- ifIn	Octets: Number of data octets delivered to upper layer entities.
		--
		-- ifInUcastPkts: Number of packets with a clear M-bit
		--		delivered to higher layer entities.
		--
		-- ifDiscards: Number of packets dropped for lack of buffering
		--
		-- ifInErrors: Number of packets received containing errors
		--		REFERENCE ProtocolErrorsDetectedLocally
		--
		-- ifInUnknownProtos: Number of packets with unknown circuit
		--		identifier.
		--
		-- ifOutOctets: Number of data octets delivered by
		--	X.25 to upper layers.
		--
		-- ifOutUcastPkts: Number of packets with a clear M-bit
		--		received from higher layer entities.

		-- ###########################################################
		--				X25 Per Circuits Information Table
		-- ###########################################################

	x25CircuitTable OBJECT-TYPE
		SYNTAX		SEQUENCE OF X25CircuitEntry
		ACCESS		not-accessible
		STATUS		mandatory
		DESCRIPTION
			"These objects contain general information about a specific circuit of an X.25 PLE."
		::= { x25L3 2 }

	x25CircuitEntry OBJECT-TYPE
		SYNTAX		X25CircuitEntry
		ACCESS		not-accessible
		STATUS		mandatory
		DESCRIPTION
			"Entries of x25CircuitTable."
		INDEX		{ x25CircuitIndex, x25CircuitChannel }
		::= { x25CircuitTable 1 }

	X25CircuitEntry ::= SEQUENCE {
		x25CircuitIndex							InterfaceIndex,
		x25CircuitChannel						INTEGER,
		x25CircuitStatus						INTEGER,
		x25CircuitEstablishTime					TimeTicks,
		x25CircuitDirection						INTEGER,
		x25CircuitInOctets						Counter,
		x25CircuitInPdus						Counter,
		x25CircuitInRemotelyInitiatedResets		Counter,
		x25CircuitInProviderInitiatedResets		Counter,
		x25CircuitInInterrupts					Counter,
		x25CircuitOutOctets						Counter,
		x25CircuitOutPdus						Counter,
		x25CircuitOutInterrupts					Counter,
		x25CircuitDataRetransmissionTimeouts	Counter,
		x25CircuitResetTimeouts					Counter,
		x25CircuitInterruptTimeouts				Counter,
		x25CircuitCallParamId					INTEGER,
		x25CircuitCalledAddress					X121Address,
		x25CircuitCallingAddress				X121Address,
		x25CircuitOriginallyCalledAddress		X121Address,
		x25CircuitDescr							DisplayString,

		x25CircuitRNRReceive					INTEGER,
		x25CircuitRNRSent						INTEGER,

		x25CircuitTrapType						INTEGER,
		x25CircuitTrapCause						INTEGER,
		x25CircuitTrapDiagnostic				INTEGER
		}


	x25CircuitIndex OBJECT-TYPE
		SYNTAX		InterfaceIndex
		ACCESS		read-only
		STATUS		mandatory
		DESCRIPTION
			"The ifIndex value for the X.25 Interface."
		::= { x25CircuitEntry 1 }

	x25CircuitChannel OBJECT-TYPE
		SYNTAX		INTEGER (0..4095)
		ACCESS		read-only
		STATUS		mandatory
		DESCRIPTION
			"The channel number for this circuit."
		::= { x25CircuitEntry 2 }

	x25CircuitStatus OBJECT-TYPE
		SYNTAX		INTEGER {			-- state table states
			inactive			(1),	-- Link disconnected
			wait-for-setup		(2),	-- Ready for VC setup
			received-call		(3),	-- Wait user call response
			sent-call			(4),	-- Wait network call confirm
			data-unused			(5),	-- Data transfer
			call-collision		(6),	-- Call collision
			sent-user-clear		(7),	-- Wait user clear response
			sent-net-clear		(8),	-- Wait network clear confirm
			data				(9),	-- Data transfer
			sent-user-reset		(10),	-- Wait user reset response
			sent-net-reset		(11)	-- Wait network reset confirm
			}
		ACCESS		read-only
		STATUS		mandatory
		DESCRIPTION
			"This object reports the current status of the circuit.
			'Network' refers to the X.25 network below this module.
			'User Application' refers to the software module above this module.

					<User Application>			- The software driving X.25 Level 3.
				<X.25 Packet Level Module>		- This module.
						<Network>				- LAPB --> X.25 Link.

			The state descriptions are as follows:

				inactive		- VC is not active.
				wait-for-setup	- VC is not active but ready for Call Setup.
				received-call	- Received Call Request/Indication from the Network,
								  awaiting User Application response.
				sent-call		- Sent the network a Call Request/Indication,
								  awaiting Network response.
				data-unused		- Data Transfer (unused)
				call-collision	- Call Collision - Sent the network a Call Request/Indication,
								  received Call Request/Indication from the Network.
				sent-user-clear	- Sent User Application a Clear request,
								  awaiting a Clear confirm from the User Application.
				sent-net-clear	- Sent the network a Clear Request/Indication,
								  awaiting a Clear Confirm/Response from the Network.
				data				- Data Transfer state.
				sent-user-reset	- Sent the User Application a Reset request,
								  awaiting a response from the User Application.
				sent-net-reset	- Sent the Network a Reset Request/Indication,
								  awaiting a response from the Network."
		::= { x25CircuitEntry 3 }

	x25CircuitEstablishTime OBJECT-TYPE
		SYNTAX		TimeTicks
		ACCESS		read-only
		STATUS		mandatory
		DESCRIPTION
			"The value of sysUpTime when the channel was associated
			with this circuit.  For outgoing SVCs, this is the time
			the first call packet was sent.  For incoming SVCs, this
			is the time the call indication was received.  For PVCs
			this is the time the PVC was able to pass data to a higher
			layer entity without loss of data."
		::= { x25CircuitEntry 4 }

	x25CircuitDirection OBJECT-TYPE
		SYNTAX		INTEGER {
			incoming	(1),
			outgoing	(2),
			pvc			(3)
			}
		ACCESS		read-only
		STATUS		mandatory
		DESCRIPTION
			"The direction of the call that established this circuit."
		REFERENCE
			"10733 direction"
		DEFVAL		{ pvc }
		::= { x25CircuitEntry 5 }

				-- X25 Circuit data flow statistics

	x25CircuitInOctets OBJECT-TYPE
		SYNTAX		Counter
		ACCESS		read-only
		STATUS		mandatory
		DESCRIPTION
			"The number of octets of user data delivered to upper layer."
		REFERENCE
			"5.11 octetsReceivedCounter"
		::= { x25CircuitEntry 6 }

	x25CircuitInPdus OBJECT-TYPE
		SYNTAX		Counter
		ACCESS		read-only
		STATUS		mandatory
		DESCRIPTION
			"The number of PDUs received for this circuit."
		REFERENCE
			"10733 5.11 dataPacketsReceived"
		::= { x25CircuitEntry 7 }

	x25CircuitInRemotelyInitiatedResets OBJECT-TYPE
		SYNTAX		Counter
		ACCESS		read-only
		STATUS		mandatory
		DESCRIPTION
			"The number of Resets received for this circuit with cause code of DTE initiated."
		REFERENCE
			"10733 remotelyInitiatedResets"
		::= { x25CircuitEntry 8 }

	x25CircuitInProviderInitiatedResets OBJECT-TYPE
		SYNTAX		Counter
		ACCESS		read-only
		STATUS		mandatory
		DESCRIPTION
			"The number of Resets received for this circuit with cause code other than DTE initiated."
		REFERENCE
			"10733 ProviderInitiatedResets"
		::= { x25CircuitEntry 9 }

	x25CircuitInInterrupts OBJECT-TYPE
		SYNTAX		Counter
		ACCESS		read-only
		STATUS		mandatory
		DESCRIPTION
			"The number of interrupt packets received for this circuit."
		REFERENCE
			"10733 interruptPacketsReceived"
		::= { x25CircuitEntry 10 }

	x25CircuitOutOctets OBJECT-TYPE
		SYNTAX		Counter
		ACCESS		read-only
		STATUS		mandatory
		DESCRIPTION
			"The number of octets of user data sent for this circuit."
		REFERENCE
			"10733 5.11 octetsSentCounter"
		::= { x25CircuitEntry 11 }

	x25CircuitOutPdus OBJECT-TYPE
		SYNTAX		Counter
		ACCESS		read-only
		STATUS		mandatory
		DESCRIPTION
			"The number of PDUs sent for this circuit."
		REFERENCE
			"10733 5.11 dataPacketsSent"
		::= { x25CircuitEntry 12 }

	x25CircuitOutInterrupts OBJECT-TYPE
		SYNTAX		Counter
		ACCESS		read-only
		STATUS		mandatory
		DESCRIPTION
			"The number of interrupt packets sent on this circuit."
		REFERENCE
			"10733 interruptPacketsSent"
		::= { x25CircuitEntry 13 }

			--
			-- X25 circuit timer statistics
			--

	x25CircuitDataRetransmissionTimeouts OBJECT-TYPE
		SYNTAX		Counter
		ACCESS		read-only
		STATUS		mandatory
		DESCRIPTION
			"The number of times the T25 data retransmission timer expired for this circuit."
		REFERENCE
			"10733 5.11 dataRetransmissionTimerExpiries"
		::= { x25CircuitEntry 14 }

	x25CircuitResetTimeouts OBJECT-TYPE
		SYNTAX		Counter
		ACCESS		read-only
		STATUS		mandatory
		DESCRIPTION
			"The number of times the T22 reset timer expired for this circuit."
		REFERENCE
			"10733 5.11 resetTimeouts"
		::= { x25CircuitEntry 15 }

	x25CircuitInterruptTimeouts OBJECT-TYPE
		SYNTAX		Counter
		ACCESS		read-only
		STATUS		mandatory
		DESCRIPTION
			"The number of times the T26 Interrupt timer expired for this circuit."
		REFERENCE
			"10733 interruptTimerExpiries"
		::= { x25CircuitEntry 16 }

	x25CircuitCallParamId OBJECT-TYPE
		SYNTAX		INTEGER
		ACCESS		read-only
		STATUS		mandatory
		DESCRIPTION
			"This identifies the instance of the x25CallParmIndex for the
			entry in the x25CallParmTable which contains the call parameters
			in use with this circuit.  The entry referenced must contain the
			values that are currently in use by the circuit rather than
			proposed values.  A value of NULL indicates the circuit is a PVC
			or is using all the default parameters."
		::= { x25CircuitEntry 17 }

	x25CircuitCalledAddress OBJECT-TYPE
		SYNTAX		X121Address
		ACCESS		read-only
		STATUS		mandatory
		DESCRIPTION
			"The Called X.121 Address in the Incoming or Outgoing Call packets."
		DEFVAL		{ ''h }
		::= { x25CircuitEntry 18 }

	x25CircuitCallingAddress OBJECT-TYPE
		SYNTAX		X121Address
		ACCESS		read-only
		STATUS		mandatory
		DESCRIPTION
			"The Calling X.121 Address in the Incoming or Outgoing Call packets."
		DEFVAL		{ ''h }
		::= { x25CircuitEntry 19 }

	x25CircuitOriginallyCalledAddress OBJECT-TYPE
		SYNTAX		X121Address
		ACCESS		read-only
		STATUS		mandatory
		DESCRIPTION
			"For incoming calls, this is the address in the call Redirection
			or Call Deflection Notification facility if the call was deflected
			or redirected, otherwise it will be called address from the call
			indication packet.  For outgoing calls, this is the address from
			the call request packet.  This will be zero length for PVCs."
		REFERENCE
			"10733 originallyCalledAddress"
		DEFVAL		{ ''h }
		::= { x25CircuitEntry 20 }

	x25CircuitDescr OBJECT-TYPE
		SYNTAX		DisplayString (SIZE (0..255))
		ACCESS		read-write
		STATUS		mandatory
		DESCRIPTION
			"A descriptive string associated with this circuit.  This provides a
			place for the agent to supply any descriptive information it knows
			about the use or owner of the circuit.  The agent may return the
			process identifier and user name for the process using the circuit.
			Alternative the agent may return the name of the configuration entry
			that caused a bridge to establish the circuit.  A zero length value
			indicates the agent doesn't have any additional information."
		DEFVAL		{ ''h }
		::= { x25CircuitEntry 21 }

	x25CircuitRNRReceive OBJECT-TYPE
		SYNTAX		INTEGER {
			no-rnr	(1),
			rnr		(2)
			}
		ACCESS		read-only
		STATUS		mandatory
		DESCRIPTION
			"This element shows whether a receive RNR (from the network) condition exits."
		::= { x25CircuitEntry 22 }

	x25CircuitRNRSent OBJECT-TYPE
		SYNTAX		INTEGER {
			no-rnr	(1),
			rnr		(2)
			}
		ACCESS		read-only
		STATUS		mandatory
		DESCRIPTION
			"This element shows whether a sent RNR (to the network) condition exits."
		::= { x25CircuitEntry 23 }

	x25CircuitTrapType OBJECT-TYPE
		SYNTAX		INTEGER {
			reset			(1),
			clear			(2),
			sent-rr2rnr     (3),
			sent-rnr2rr     (4),
			recv-rr2rnr     (5),
			recv-rnr2rr     (6)
			}
		ACCESS		read-only
		STATUS		mandatory
		DESCRIPTION
		"The type of event that caused the trap to occur.
			reset -			generated whenever that packet type is sent or received.
			clear -			generated whenever that packet type is sent or received.
			sent-rr2rnr -	generated whenever an RNR packet is transmitted, causing
							a flow control condition.
			sent-rnr2rr -	generated whenever an RR packet is transmitted ending
							a flow control condition.
			recv-rr2rnr -	generated whenever an RNR packet is received, causing
							a flow control condition.
			recv-rnr2rr -	generated whenever an RR packet is received ending
							a flow control condition."
		::= { x25CircuitEntry 24 }

	x25CircuitTrapCause OBJECT-TYPE
		SYNTAX		INTEGER (0..256)
		ACCESS		read-only
		STATUS		mandatory
		DESCRIPTION
			"The cause field of the message that caused the trap to occur."
		::= { x25CircuitEntry 25 }

	x25CircuitTrapDiagnostic OBJECT-TYPE
		SYNTAX		INTEGER (0..256)
		ACCESS		read-only
		STATUS		mandatory
		DESCRIPTION
			"The diagnostic field of the message that caused the trap to occur."
		::= { x25CircuitEntry 26 }


	-- ###########################################################
	--		The Call Parameter Table
	-- ###########################################################

	x25CallParmTable OBJECT-TYPE
		SYNTAX		SEQUENCE OF X25CallParmEntry
		ACCESS		not-accessible
		STATUS		mandatory
		DESCRIPTION
			"These objects contain the parameters that can be varied between
			X.25 calls.  The entries in this table are independent of the PLE.
			There exists only one of these tables for the entire system.
			The indexes for the entries are independent of any PLE or any circuit.
			Other tables reference entries in this table.  Entries in this
			table can be used for default PLE parameters, for parameters to use
			to place/answer a call, for the parameters currently in use for a
			circuit, or parameters that were used by a circuit.

			The number of references to a given set of parameters can be found
			in the x25CallParmRefCount object sharing the same instance identifier
			with the parameters.  The value of this reference count also affects
			the access of the objects in this table.  An object in this table with
			the same instance identifier as the instance identifier of an
			x25CallParmRefCount must be consider associated with that reference
			count.  An object with an associated reference count of zero can be
			written (if its MAX-ACCESS clause allows it).  An object with an associated
			reference count greater than zero can not be written (regardless of
			the MAX-ACCESS clause).  This ensures that a set of call parameters being
			referenced from another table can not be modified or changed in a ways
			inappropriate for continued use by that table."
		::= { x25L3 3 }

	x25CallParmEntry OBJECT-TYPE
		SYNTAX		X25CallParmEntry
		ACCESS		not-accessible
		STATUS		mandatory
		DESCRIPTION
			"Entries of x25CallParmTable."
		INDEX		{ x25CallParmIndex }
		::= { x25CallParmTable 1 }

	X25CallParmEntry ::= SEQUENCE {
		x25CallParmIndex						INTEGER,
		x25CallParmStatus						RowStatus,
		x25CallParmRefCount						INTEGER,
		x25CallParmInPacketSize 				INTEGER,
		x25CallParmOutPacketSize				INTEGER,
		x25CallParmInMaxPktSize 				INTEGER,
		x25CallParmOutMaxPktSize				INTEGER,
		x25CallParmInWindowSize					INTEGER,
		x25CallParmOutWindowSize				INTEGER,
		x25CallParmAcceptReverseCharging		INTEGER,
		x25CallParmProposeReverseCharging		INTEGER,
		x25CallParmFastSelect					INTEGER,
		x25CallParmInThruPutClasSize			INTEGER,
		x25CallParmOutThruPutClasSize			INTEGER,
		x25CallParmCug							DisplayString,
		x25CallParmCugoa						DisplayString,
		x25CallParmBcug							DisplayString,
		x25CallParmNui							OCTET STRING,
		x25CallParmChargingInfo					INTEGER,
		x25CallParmRpoa							DisplayString,
		x25CallParmTrnstDly						INTEGER,
		x25CallParmCallingExt					DisplayString,
		x25CallParmCalledExt					DisplayString,
		x25CallParmInMinThuPutCls				INTEGER,
		x25CallParmOutMinThuPutCls				INTEGER,
		x25CallParmEndTrnsDly					OCTET STRING,
		x25CallParmPriority						OCTET STRING,
		x25CallParmProtection					DisplayString,
		x25CallParmExptData						INTEGER,
		x25CallParmUserData						OCTET STRING,
		x25CallParmCallingNetworkFacilities		OCTET STRING,
		x25CallParmCalledNetworkFacilities		OCTET STRING
		}

	x25CallParmIndex OBJECT-TYPE
		SYNTAX		INTEGER
		ACCESS		read-write
		STATUS		mandatory
		DESCRIPTION
			"A value that distinguishes this entry from another entry.
			Entries in this table are referenced from other objects which
			identify call parameters.

			It is impossible to know which other objects in the MIB reference
			entries in the table by looking at this table.  Because of this,
			changes to parameters must be accomplished by creating a new entry
			in this table and then changing the referencing table to identify
			the new entry.

			Note that an agent will only use the values in this table when another
			table is changed to reference those values.  The number of other tables
			that reference an index object in this table can be found in
			x25CallParmRefCount.  The value of the reference count will affect the
			writability of the objects as explained above.

			Entries in this table which have a reference count of zero maybe deleted
			at the convence of the agent.  Care should be taken by the agent to give
			the NMS sufficient time to create a reference to newly created entries.

			Should a Management Station not find a free index with which to create
			a new entry, it may feel free to delete entries with a reference count
			of zero.  However in doing so the Management Station much realize it may
			impact other Management Stations."
		::= { x25CallParmEntry 1 }

	x25CallParmStatus OBJECT-TYPE
		SYNTAX		RowStatus
		ACCESS		read-write
		STATUS		mandatory
		DESCRIPTION
			"The status of this call parameter entry.  See RFC 1271 for details of usage."
		::= { x25CallParmEntry 2 }

	x25CallParmRefCount OBJECT-TYPE
		SYNTAX		INTEGER
		ACCESS		read-write
		STATUS		mandatory
		DESCRIPTION
			"The number of references know by a management station to exist
			to this set of call parameters.  This is the number of other
			objects that have returned a value of, and will return a value
			of, the index for this set of call parameters.  Examples of such
			objects is the x25AdmnDefCallParamId object defined above."
		::= { x25CallParmEntry 3 }

	x25CallParmInPacketSize OBJECT-TYPE
		SYNTAX		INTEGER (0..4096)
		ACCESS		read-write
		STATUS		mandatory
		DESCRIPTION
			"The default receive packet size in octets for a circuit.  A size of zero
			for a circuit means use the PLE default size.  A size of zero for the PLE
			means use a default size of 128."
		REFERENCE
			"10733 proposedPacketSize;
			See ISO 8208 Section 15.2.2.1.1"
		DEFVAL		{ 128 }
		::= { x25CallParmEntry 4 }

	x25CallParmOutPacketSize OBJECT-TYPE
		SYNTAX		INTEGER (0..4096)
		ACCESS		read-write
		STATUS		mandatory
		DESCRIPTION
			"The default transmit packet size in octets for a circuit.	A size of zero
			for a circuit means use the PLE default size.  A size of zero for the PLE
			default means use a default size of 128."
		REFERENCE
			"10733 proposedPacketSize;
			See ISO 8208 Section 15.2.2.1.1"
		DEFVAL		{ 128 }
		::= { x25CallParmEntry 5 }

	x25CallParmInWindowSize OBJECT-TYPE
		SYNTAX		INTEGER (0..127)
		ACCESS		read-write
		STATUS		mandatory
		DESCRIPTION
			"The receive window size for a circuit.
			A size of zero for a circuit means use the PLE default size.
			A size of zero for the PLE default means use 2."
		REFERENCE
			"10733 proposedWindowSize;
			See ISO 8208 Section 15.2.2.1.2"
		DEFVAL		{ 2 }
		::= { x25CallParmEntry 6 }

	x25CallParmOutWindowSize OBJECT-TYPE
		SYNTAX		INTEGER (0..127)
		ACCESS		read-write
		STATUS		mandatory
		DESCRIPTION
			"The transmit window size for a circuit.
			A size of zero for a circuit means use the PLE default size.
			A size of zero for the PLE default means use 2."
		REFERENCE
			"10733 proposedWindowSize;
			See ISO 8208 Section 15.2.2.1.2"
		DEFVAL		{ 2 }
		::= { x25CallParmEntry 7 }

	x25CallParmAcceptReverseCharging OBJECT-TYPE
		SYNTAX		INTEGER {
			default			(1),
			alwaysAccept	(2),
			alwaysRefuse	(3),
			onlyIfNotBilled	(4)
			}
		ACCESS		read-write
		STATUS		mandatory
		DESCRIPTION
			"An enumeration defining if the PLE will accept or refuse charges.
			A value of default for a circuit means use the PLE default value.
			A value of alwaysRefuse is only used for the PLE default and
			indicates the PLE will never accept reverse charging.
			A value of default for a PLE default means refuse."
		REFERENCE
			"10733 acceptReverseCharging"
		DEFVAL		{ alwaysRefuse }
		::= { x25CallParmEntry 8 }

	x25CallParmProposeReverseCharging OBJECT-TYPE
		SYNTAX		INTEGER {
			default	(1),
			reverse	(2),
			local	(3)
			}
		ACCESS		read-write
		STATUS		mandatory
		DESCRIPTION
				"An enumeration defining if the PLE should propose reverse or local charging.
				The value of default for a circuit means use the PLE default.
				The value of default for the PLE default means use local."
		REFERENCE
			"10733 proposedPacketSize; See ISO 8208 Section 15.2.2.6"
		DEFVAL		{ local }
		::= { x25CallParmEntry 9 }

	x25CallParmFastSelect OBJECT-TYPE
		SYNTAX		INTEGER {
			default			(1),
			alwaysReject	(2),
			onlyIncomming	(3),
			onlyOutgoing	(4),
			alwaysAccept	(5),
			onlyIfNotBilled	(6)
			}
		ACCESS		read-write
		STATUS		mandatory
		DESCRIPTION
			"Expresses preference for use of fast select facility.
			The value of default for a circuit is the PLE default.
			A value of default for the PLE means alwaysReject.
			A value of alwaysReject indicates a circuit may not use fast select."
		REFERENCE
			"10733 fastSelect; Sec ISO 8208 Section 15.2.2.6"
		DEFVAL		{ alwaysReject }
		::= { x25CallParmEntry 10 }

	x25CallParmInThruPutClasSize OBJECT-TYPE
		SYNTAX		INTEGER {
			tcReserved1		(1),
			tcReserved2		(2),
			tc75			(3),
			tc150			(4),
			tc300			(5),
			tc600			(6),
			tc1200			(7),
			tc2400			(8),
			tc4800			(9),
			tc9600			(10),
			tc19200			(11),
			tc48000			(12),
			tc64000			(13),
			tcReserved14	(14),
			tcReserved15	(15),
			tcReserved0		(16),
			tcNone			(17),
			tcDefault		(18)
			}
		ACCESS		read-write
		STATUS		mandatory
		DESCRIPTION
			"The incoming throughput class to negotiate.
			A value of tcDefault for a circuit means use the PLE default.
			A value of tcDefault for the PLE default means tcNone.
			A value of tcNone means do not negotiate throughtput class."
		REFERENCE
			"See ISO 8208 Section 15.2.2.2, table 18"
		DEFVAL		{ tcNone }
		::= { x25CallParmEntry 11 }

	x25CallParmOutThruPutClasSize OBJECT-TYPE
		SYNTAX		INTEGER {
			tcReserved1		(1),
			tcReserved2		(2),
			tc75			(3),
			tc150			(4),
			tc300			(5),
			tc600			(6),
			tc1200			(7),
			tc2400			(8),
			tc4800			(9),
			tc9600			(10),
			tc19200			(11),
			tc48000			(12),
			tc64000			(13),
			tcReserved14	(14),
			tcReserved15	(15),
			tcReserved0		(16),
			tcNone			(17),
			tcDefault		(18)
			}
		ACCESS		read-write
		STATUS		mandatory
		DESCRIPTION
			"The outgoing throughput class to negotiate.
			A value of tcDefault for a circuit means use the PLE default.
			A value of tcDefault for the PLE default means use tcNone.
			A value of tcNone means do not negotiate throughtput class."
		REFERENCE
			"See ISO 8208 Section 15.2.2.2, table 18"
		DEFVAL		{ tcNone }
		::= { x25CallParmEntry 12 }

	x25CallParmCug OBJECT-TYPE
		SYNTAX		DisplayString (SIZE(0..4))
		ACCESS		read-write
		STATUS		mandatory
		DESCRIPTION
			"The Closed User Group to specify.
			This consists of two or four octets containing the characters 0 through 9.
			A zero length string indicates no facility requested.
			A string length of three containing the characters DEF for a circuit means use
			the PLE default, (the PLE default parameter may not reference an entry of DEF.)"
		REFERENCE
			"See ISO 8208 Section 15.2.2.3"
		DEFVAL		{ ''h }
		::= { x25CallParmEntry 13 }

	x25CallParmCugoa OBJECT-TYPE
		SYNTAX		DisplayString (SIZE(0..4))
		ACCESS		read-write
		STATUS		mandatory
		DESCRIPTION
			"The Closed User Group with Outgoing Access to specify.  This
			consists of two or four octets containing the characters 0 through
			9.  A string length of three containing the characters DEF for a
			circuit means use the PLE default (the PLE default parameters may
			not reference an entry of DEF).  A zero length string indicates no
			facility requested."
		REFERENCE
			"See ISO 8208 Section 15.2.2.4"
		DEFVAL		{ ''h }
		::= { x25CallParmEntry 14 }

	x25CallParmBcug OBJECT-TYPE
		SYNTAX		DisplayString (SIZE(0..3))
		ACCESS		read-write
		STATUS		mandatory
		DESCRIPTION
			"The Bilateral Closed User Group to specify.  This consists of two
			octets containing the characters 0 through 9.  A string length of
			three containing the characters DEF for a circuit means use the PLE
			default (the PLE default parameter may not reference an entry of DEF).
			A zero length string indicates no facility requested."
		REFERENCE
			"See ISO 8208 Section 15.2.2.5"
		DEFVAL		{ ''h }
		::= { x25CallParmEntry 15 }

	x25CallParmNui OBJECT-TYPE
		SYNTAX		OCTET STRING (SIZE(0..108))
		ACCESS		read-write
		STATUS		mandatory
		DESCRIPTION
			"The Network User Identifier facility.  This is binary value to be
			included immediately after the length field.  The PLE will supply the
			length octet.  A zero length string indicates no facility requested.
			This value is ignored for the PLE default parameters entry."
		REFERENCE
			"See ISO 8208 Section 15.2.2.7"
		DEFVAL		{ ''h }
		::= { x25CallParmEntry 16 }

	x25CallParmChargingInfo OBJECT-TYPE
		SYNTAX		INTEGER {
			default			(1),
			noFacility		(2),
			noChargingInfo	(3),
			chargingInfo	(4)
			}
		ACCESS		read-write
		STATUS		mandatory
		DESCRIPTION
			"The charging Information facility.
			A value of default for a circuit means use the PLE default.
			The value of default for the default PLE parameters means use noFacility.
			The value of noFacility means do not include a facility."
		REFERENCE
			"See ISO 8208 Section 15.2.2.8"
		DEFVAL		{ noFacility }
		::= { x25CallParmEntry 17 }

	x25CallParmRpoa OBJECT-TYPE
		SYNTAX		DisplayString (SIZE(0..108))
		ACCESS		read-write
		STATUS		mandatory
		DESCRIPTION
			"The RPOA facility.  The octet string contains n * 4 sequences of
			the characters 0-9 to specify a facility with n entries.  The octet
			string containing the 3 characters DEF for a circuit specifies use
			of the PLE default (the entry for the PLE default may not contain
			DEF).  A zero length string indicates no facility requested."
		REFERENCE
			"See ISO 8208, section 15.2.2.9"
		DEFVAL		{ ''h }
		::= { x25CallParmEntry 18 }

	x25CallParmTrnstDly OBJECT-TYPE
		SYNTAX		INTEGER (0..65537)
		ACCESS		read-write
		STATUS		mandatory
		DESCRIPTION
			"The Transit Delay Selection and Indication value.
			A value of 65536 indicates no facility requested.
			A value of 65537 for a circuit means use the PLE default
			(the PLE default parameters entry may not use the value 65537).
			The value 65535 may only be used to indicate the value in use by a circuit."
		REFERENCE
			"See ISO 8208, Section 15.2.2.13"
		DEFVAL		{ 65536 }
		::= { x25CallParmEntry 19 }

		-- The following parameters are for CCITT facilities.

	x25CallParmCallingExt OBJECT-TYPE
		SYNTAX		DisplayString (SIZE(0..40))
		ACCESS		read-write
		STATUS		mandatory
		DESCRIPTION
			"The Calling Extension facility.  This contains one of the following:

			A sequence of hex digits with the value to be put in the facility.
			These digits will be converted to binary by the agent and put in the
			facility.  These octets do not include the length octet.

			A value containing the three character DEF for a circuit means use the
			PLE default, (the entry for the PLE default parameters may not use the
			value DEF).

			A zero length string indicates no facility requested."
		REFERENCE
			"See ISO 8208 Section 15.3.2.1"
		DEFVAL		{ ''h }
		::= { x25CallParmEntry 20 }

	x25CallParmCalledExt OBJECT-TYPE
		SYNTAX		DisplayString (SIZE(0..40))
		ACCESS		read-write
		STATUS		mandatory
		DESCRIPTION
			"The Called Extension facility.  This contains one of the following:

			A sequence of hex digits with the value to be put in the facility.
			These digits will be converted to binary by the agent and put in the
			facility.  These octets do not include the length octet.

			A value containing the three character DEF for a circuit means use the
			PLE default, (the entry for the PLE default parameters may not use the
			value DEF).

			A zero length string indicates no facility requested."
		REFERENCE
			"See ISO 8208 Section 15.3.2.2"
		DEFVAL		{ ''h }
		::= { x25CallParmEntry 21 }

	x25CallParmInMinThuPutCls OBJECT-TYPE
		SYNTAX		INTEGER (0..17)
		ACCESS		read-write
		STATUS		mandatory
		DESCRIPTION
			"The minimum input throughput Class.  A value of 17 for a circuit means
			use the PLE default (the PLE parameters entry may not use this value).
			A value of 16 indicates no facility requested."
		REFERENCE
			"See ISO 8208 Section 15.3.2.3"
		DEFVAL		{ 17 }
		::= { x25CallParmEntry 22 }

	x25CallParmOutMinThuPutCls OBJECT-TYPE
		SYNTAX		INTEGER (0..17)
		ACCESS		read-write
		STATUS		mandatory
		DESCRIPTION
			"The minimum output throughput Class.  A value of 17 for a circuit means
			use the PLE default (the PLE parameters entry may not use this value).
			A value of 16 indicates no facility requested."
		REFERENCE
			"See ISO 8208 Section 15.3.2.3"
		DEFVAL		{ 17 }
		::= { x25CallParmEntry 23 }

	x25CallParmEndTrnsDly OBJECT-TYPE
		SYNTAX		OCTET STRING (SIZE(0..6))
		ACCESS		read-write
		STATUS		mandatory
		DESCRIPTION
			"The End-to-End Transit Delay to negotiate.  An octet string of length
			2, 4, or 6 contains the facility encoded as specified in ISO/IEC 8208
			section 15.3.2.4.  An octet string of length 3 containing the three
			character DEF for a circuit means use the PLE default (the entry for
			the PLE default can not contain the characters DEF).  A zero length
			string indicates no facility requested."
		REFERENCE
			"See ISO 8208 Section 15.3.2.4"
		DEFVAL		{ ''h }
		::= { x25CallParmEntry 24 }

	x25CallParmPriority OBJECT-TYPE
		SYNTAX		OCTET STRING (SIZE(0..6))
		ACCESS		read-write
		STATUS		mandatory
		DESCRIPTION
			"The priority facility to negotiate.  The octet string encoded
			as specified in ISO/IEC 8208 section 15.3.2.5.  A zero length
			string indicates no facility requested.  The entry for the PLE
			default parameters must be zero length."
		REFERENCE
			"See ISO 8208 Section 15.3.2.5"
		DEFVAL		{ ''h }
		::= { x25CallParmEntry 25 }

	x25CallParmProtection OBJECT-TYPE
		SYNTAX		DisplayString (SIZE(0..108))
		ACCESS		read-write
		STATUS		mandatory
		DESCRIPTION
			"A string contains the following:

			A hex string containing the value for the protection facility.
			This will be converted from hex to the octets actually in the
			packet by the agent.  The agent will supply the length field
			and the length octet is not contained in this string.

			An string containing the 3 characters DEF for a circuit means
			use the PLE default (the entry for the PLE default parameters
			may not use the value DEF).

			A zero length string mean no facility requested."
		REFERENCE
			"See ISO 8208 Section 15.3.2.5"
		DEFVAL		{ ''h }
		::= { x25CallParmEntry 26 }

	x25CallParmExptData OBJECT-TYPE
		SYNTAX		INTEGER {
			default			(1),
			noExpeditedData	(2),
			expeditedData	(3)
			}
		ACCESS		read-write
		STATUS		mandatory
		DESCRIPTION
			"The Expedited Data facility to negotiate.  A value of default
			for a circuit means use the PLE default value.  The entry for
			the PLE default parameters may not have the value default."
		REFERENCE
			"See ISO 8208 Section 15.3.2.7"
		DEFVAL		{ noExpeditedData }
		::= { x25CallParmEntry 27 }

	x25CallParmUserData OBJECT-TYPE
		SYNTAX		OCTET STRING (SIZE (0..128))
		ACCESS		read-write
		STATUS		mandatory
		DESCRIPTION
			"The call user data as placed in the packet.  A zero length
			string indicates no call user data.  If both the circuit call
			parameters and the PLE default have call user data defined,
			the data from the circuit call parameters will be used.  If
			only the PLE has data defined, the PLE entry will be used.
			If neither the circuit call parameters or the PLE default
			entry has a value, no call user data will be sent."
		REFERENCE
			"See ISO 8208 Section 12.2.1.1.6, 12.2.1.2"
		DEFVAL		{ ''h }
		::= { x25CallParmEntry 28 }

	x25CallParmCallingNetworkFacilities OBJECT-TYPE
		SYNTAX		OCTET STRING (SIZE (0..108))
		ACCESS		read-write
		STATUS		mandatory
		DESCRIPTION
			"The calling network facilities.  The facilities are encoded here
			exactly as encoded in the call packet.  These facilities do not
			include the marker facility code.

			A zero length string in the entry for the parameter to use when
			establishing a circuit means use the PLE default.  A zero length string
			in the entry for PLE default parameters indicates no default facilities."
		REFERENCE
			"See ISO 8206 Section 15.1, category b"
		DEFVAL		{ ''h }
		::= { x25CallParmEntry 29 }

	x25CallParmCalledNetworkFacilities OBJECT-TYPE
		SYNTAX		OCTET STRING (SIZE (0..108))
		ACCESS		read-write
		STATUS		mandatory
		DESCRIPTION
			"The called network facilities.  The facilities are encoded here
			exactly as encoded in the call packet.  These facilities do not
			include the marker facility code.

			A zero length string in the entry for the parameter to use when
			establishing a circuit means use the PLE default.  A zero length string
			in the entry for PLE default parameters indicates no default facilities."
		REFERENCE
			"See ISO 8206 Section 15.1, category c"
		DEFVAL		{ ''h }
		::= { x25CallParmEntry 30 }

	x25CallParmInMaxPktSize OBJECT-TYPE
		SYNTAX		INTEGER (0..4096)
		ACCESS		read-write
		STATUS		mandatory
		DESCRIPTION
			"The maximum receive packet size in octets for a circuit.  A size of zero
			for a circuit means use the PLE default size.  A size of zero for the PLE
			means use a default size of 128."
		REFERENCE
			"10733 proposedPacketSize;
			See ISO 8208 Section 15.2.2.1.1"
		DEFVAL		{ 128 }
		::= { x25CallParmEntry 31 }

	x25CallParmOutMaxPktSize OBJECT-TYPE
		SYNTAX		INTEGER (0..4096)
		ACCESS		read-write
		STATUS		mandatory
		DESCRIPTION
			"The maximum transmit packet size in octets for a circuit.	A size of zero
			for a circuit means use the PLE default size.  A size of zero for the PLE
			default means use a default size of 128."
		REFERENCE
			"10733 proposedPacketSize;
			See ISO 8208 Section 15.2.2.1.1"
		DEFVAL		{ 128 }
		::= { x25CallParmEntry 32 }

		-- ###########################################################
		--					X.25 Traps
		-- ###########################################################

	x25Restart TRAP-TYPE
		ENTERPRISE		x25L3Traps
		VARIABLES		{ x25AdmnIndex, rs232PortIndex }
		DESCRIPTION
		"This trap means the X.25 PLE completed a link restart packet has been sent and:

			a) a restart packet was received (Restart Collision)
			b) a restart confirm packet was received.
			c) the Restart retransmission counter (R20) expires.

		The packet module now considers the link to be established and ready
		for Virtual Circuit establishment."
		::= 1

	x25VC TRAP-TYPE
		ENTERPRISE		x25L3Traps
		VARIABLES		{ x25CircuitIndex, x25CircuitChannel, x25CircuitTrapType, x25CircuitTrapCause, x25CircuitTrapDiagnostic, rs232PortIndex }
		DESCRIPTION
			"Sent if a virtual circuit needs to send a trap for one of its reasons listed in x25CircuitTrapType."
		::= 2

END
