ACC-ISDN DEFINITIONS ::= BEGIN

    IMPORTS
	 OBJECT-TYPE, IpAddress, TimeTicks, Gauge, Counter FROM RFC1155-SMI
	 TRAP-TYPE FROM RFC-1215
        accTrapLogSeqNum FROM ACC-SYSTEM
	accBRG, DisplayString, RowStatus, IfIndex, SmdsAddress
             FROM ACC-MIB
	accTrapLogSeverityType FROM ACC-SYSTEM;-- Basic Rate ISDN Group
    accIsdn OBJECT IDENTIFIER ::= { accBRG 36 }
	-- The IsdnDsl Group
        accIsdnDsl OBJECT IDENTIFIER ::= { accIsdn 1 }
	    -- Configuration and operational parameters maintained and 
	    -- reported on a per-terminal (bridge/router) basis.
            accIsdnDslIndex OBJECT-TYPE
		SYNTAX INTEGER (1..255)
		ACCESS read-only
		STATUS deprecated
		DESCRIPTION
		  " An index instantiating a particular digital subscriber
		    loop interface on this bridge/router terminal."
		::= { accIsdnDsl 1 }
	-- The IsdnSub Group
	-- Configuration and operational parameters maintained and
	-- reported on a per-subscriber interface basis.
            accIsdnSubTable OBJECT-TYPE
		SYNTAX SEQUENCE OF AccIsdnSubEntry
		ACCESS not-accessible
		STATUS deprecated
		DESCRIPTION
		  " ISDN subscriber table containing configuration and
		    operational parameters for all ISDN subscriber
		    interfaces on this bridge/router terminal."
		::= { accIsdn 2 }
            accIsdnSubEntry OBJECT-TYPE
		SYNTAX AccIsdnSubEntry
		ACCESS not-accessible
		STATUS deprecated
		DESCRIPTION
		  " Configuration and operational parameters for a
		    particular ISDN subscriber interface."
		INDEX { accIsdnDslIndex }
		::= { accIsdnSubTable 1 }
            AccIsdnSubEntry ::= SEQUENCE {
                accIsdnSubSwitchType	INTEGER,
                accIsdnSubChannelMode	INTEGER,
                accIsdnSubAdminStatus	INTEGER,
                accIsdnSubDiagLevel	INTEGER,
                accIsdnSubManualTei	INTEGER
		}
            accIsdnSubSwitchType OBJECT-TYPE
		SYNTAX INTEGER {
		    bri-net3(1),
		    bri-5ess(2),
		    bri-dms100(3),
		    bri-vn2(4),
		    bri-vn3(5),
		    bri-kdd(6),
		    bri-ntt(7),
		    bri-1tr6(8),
		    bri-ni1(9),
		    bri-ccitt(10)
		    }
		ACCESS read-write
		STATUS deprecated
		DESCRIPTION
		  " The particular type of central-office switch
		    providing access to the ISDN network and to
		    which this subscriber interface is connected."
		::= { accIsdnSubEntry 1 }
            accIsdnSubChannelMode OBJECT-TYPE
		SYNTAX INTEGER {
		    cm-1b-plus-d(1),
		    cm-2b-plus-d(2),
		    cm-1h-plus-d(3)
		    }
		ACCESS read-write
		STATUS deprecated
		DESCRIPTION
		  " The ISDN channel configuration mode."
		::= { accIsdnSubEntry 2 }
            accIsdnSubAdminStatus OBJECT-TYPE
		SYNTAX INTEGER {
		    enabled (1),
		    disabled (2)
		    }
		ACCESS read-write
		STATUS deprecated
		DESCRIPTION
		  " The administrative status of this subscriber
		    interface."
		::= { accIsdnSubEntry 3 }
            accIsdnSubDiagLevel OBJECT-TYPE
		SYNTAX INTEGER (0..5)
		ACCESS read-write
		STATUS deprecated
		DESCRIPTION
		  " The current diagnostic message level for this
		    subscriber interface."
		::= { accIsdnSubEntry 4 }
            accIsdnSubManualTei OBJECT-TYPE
		SYNTAX INTEGER (0..63) -- 127
		ACCESS read-write
		STATUS deprecated
		DESCRIPTION
		  " The TEI (terminal endpoint identifier) when manual
		    TEI assignment is required.  Setting this value
		    between 0 and 63 (inclusive) specifies manual TEI
		    assignment using the indicated value.  Setting 
		    this value to 127 (the broadcast TEI) specifies
		    automatic TEI assignment."
		::= { accIsdnSubEntry 5 }
	-- The IsdnStat Group
	-- Statistics and operational status maintained and
	-- reported on a per-subscriber interface basis.
            accIsdnStatTable OBJECT-TYPE
		SYNTAX SEQUENCE OF AccIsdnStatEntry
		ACCESS not-accessible
		STATUS deprecated
		DESCRIPTION
		  " Statistics and operational status maintained for all
		    ISDN subscriber interfaces on this bridge/router
		    terminal."
		::= { accIsdn 3 }
            accIsdnStatEntry OBJECT-TYPE
		SYNTAX AccIsdnStatEntry
		ACCESS not-accessible
		STATUS deprecated
		DESCRIPTION
		  " Statistics and operational status for a particular
		    ISDN subscriber interface."
		INDEX { accIsdnDslIndex }
		::= { accIsdnStatTable 1 }
            AccIsdnStatEntry ::= SEQUENCE {
                accIsdnStatHdlcInPackets    Counter,
                accIsdnStatHdlcInOctets	    Counter,
                accIsdnStatHdlcInErrors	    Counter,
                accIsdnStatHdlcInDiscs	    Counter,
                accIsdnStatHdlcOutPackets   Counter,
                accIsdnStatHdlcOutOctets    Counter,
                accIsdnStatHdlcOutErrors    Counter,
                accIsdnStatHdlcOutDiscs	    Counter,
                accIsdnStatLapdUnsolicResps Counter,
                accIsdnStatLapdPeerSabmes   Counter,
                accIsdnStatLapdN200Errors   Counter,
                accIsdnStatLapdNrSeqErrors  Counter,
                accIsdnStatLapdRecvdFrmrs   Counter,
                accIsdnStatLapdCntlErrors   Counter,
                accIsdnStatLapdInfoErrors   Counter,
                accIsdnStatLapdWrongSizes   Counter,
                accIsdnStatLapdN201Errors   Counter,
                accIsdnStatCallsOriginateds Counter,
                accIsdnStatCallsOfferreds   Counter,
                accIsdnStatCallsAnswereds   Counter,
                accIsdnStatCallsAccepteds   Counter,
                accIsdnStatCallsCompleteds  Counter,
                accIsdnStatCallsCleareds    Counter,
                accIsdnStatDslOperStatus    INTEGER,
                accIsdnStatLastCauses	    INTEGER
		}
            accIsdnStatHdlcInPackets OBJECT-TYPE
		SYNTAX Counter
		ACCESS read-only
		STATUS deprecated
		DESCRIPTION
		  " The number of packets received on the D-channel
		    of this subscriber interface."
		::= { accIsdnStatEntry 1 }
            accIsdnStatHdlcInOctets OBJECT-TYPE
		SYNTAX Counter
		ACCESS read-only
		STATUS deprecated
		DESCRIPTION
		  " The number of octets received on the D-channel
		    of this subscriber interface."
		::= { accIsdnStatEntry 2 }
            accIsdnStatHdlcInErrors OBJECT-TYPE
		SYNTAX Counter
		ACCESS read-only
		STATUS deprecated
		DESCRIPTION
		  " The number of input hardware errors counted by
		    the D-channel input/output driver."
		::= { accIsdnStatEntry 3 }
            accIsdnStatHdlcInDiscs OBJECT-TYPE
		SYNTAX Counter
		ACCESS read-only
		STATUS deprecated
		DESCRIPTION
		  " The number of input packets discarded by the
		    D-channel input/output driver."
		::= { accIsdnStatEntry 4 }
            accIsdnStatHdlcOutPackets OBJECT-TYPE
		SYNTAX Counter
		ACCESS read-only
		STATUS deprecated
		DESCRIPTION
		  " The number of packets transmitted on the D-channel
		    of this subscriber interface."
		::= { accIsdnStatEntry 5 }
            accIsdnStatHdlcOutOctets OBJECT-TYPE
		SYNTAX Counter
		ACCESS read-only
		STATUS deprecated
		DESCRIPTION
		  " The number of octets transmitted on the D-channel
		    of this subscriber interface."
		::= { accIsdnStatEntry 6 }
            accIsdnStatHdlcOutErrors OBJECT-TYPE
		SYNTAX Counter
		ACCESS read-only
		STATUS deprecated
		DESCRIPTION
		  " The number of output hardware errors counted by
		    the D-channel input/output driver."
		::= { accIsdnStatEntry 7 }
            accIsdnStatHdlcOutDiscs OBJECT-TYPE
		SYNTAX Counter
		ACCESS read-only
		STATUS deprecated
		DESCRIPTION
		  " The number of output packets discarded by the
		    D-channel input/output driver."
		::= { accIsdnStatEntry 8 }
            accIsdnStatLapdUnsolicResps OBJECT-TYPE
		SYNTAX Counter
		ACCESS read-only
		STATUS deprecated
		DESCRIPTION
		  " The number of unsolicited LAPD response frames
		    received on all data links associated with the
		    D-channel of this subscriber interface."
		::= { accIsdnStatEntry 9 }
            accIsdnStatLapdPeerSabmes OBJECT-TYPE
		SYNTAX Counter
		ACCESS read-only
		STATUS deprecated
		DESCRIPTION
		  " The number of peer SABME frames received on all
		    data links associated with the D-channel of this
		    subscriber interface."
		::= { accIsdnStatEntry 10 }
            accIsdnStatLapdN200Errors OBJECT-TYPE
		SYNTAX Counter
		ACCESS read-only
		STATUS deprecated
		DESCRIPTION
		  " The number of unsuccessful T200 timer recoveries
		    after a frame has been retransmitted N200 times."
		::= { accIsdnStatEntry 11 }
            accIsdnStatLapdNrSeqErrors OBJECT-TYPE
		SYNTAX Counter
		ACCESS read-only
		STATUS deprecated
		DESCRIPTION
		  " The number of N(R) sequence errors."
		::= { accIsdnStatEntry 12 }
            accIsdnStatLapdRecvdFrmrs OBJECT-TYPE
		SYNTAX Counter
		ACCESS read-only
		STATUS deprecated
		DESCRIPTION
		  " The number of LAPD FRMR response frames received."
		::= { accIsdnStatEntry 13 }
            accIsdnStatLapdCntlErrors OBJECT-TYPE
		SYNTAX Counter
		ACCESS read-only
		STATUS deprecated
		DESCRIPTION
		  " The number of LAPD frames received with an invalid
		    or non-implemented control field."
		::= { accIsdnStatEntry 14 }
            accIsdnStatLapdInfoErrors OBJECT-TYPE
		SYNTAX Counter
		ACCESS read-only
		STATUS deprecated
		DESCRIPTION
		  " The number of LAPD frames received with a
		    non-permitted information (I) field."
		::= { accIsdnStatEntry 15 }
            accIsdnStatLapdWrongSizes OBJECT-TYPE
		SYNTAX Counter
		ACCESS read-only
		STATUS deprecated
		DESCRIPTION
		  " The number of LAPD frames received which were the
		    wrong size."
		::= { accIsdnStatEntry 16 }
            accIsdnStatLapdN201Errors OBJECT-TYPE
		SYNTAX Counter
		ACCESS read-only
		STATUS deprecated
		DESCRIPTION
		  " The number of LAPD frames received which contained
		    and information field which exceeded N201."
		::= { accIsdnStatEntry 17 }
            accIsdnStatCallsOriginateds OBJECT-TYPE
		SYNTAX Counter
		ACCESS read-only
		STATUS deprecated
		DESCRIPTION
		  " The number of outgoing calls originated on this
		    subscriber interface."
		::= { accIsdnStatEntry 18 }
            accIsdnStatCallsOfferreds OBJECT-TYPE
		SYNTAX Counter
		ACCESS read-only
		STATUS deprecated
		DESCRIPTION
		  " The number of incoming calls offerred on this
		    subscriber interface."
		::= { accIsdnStatEntry 19 }
            accIsdnStatCallsAnswereds OBJECT-TYPE
		SYNTAX Counter
		ACCESS read-only
		STATUS deprecated
		DESCRIPTION
		  " The number of outgoing calls originated on this
		    subscriber interface which were answered by the
		    destination."
		::= { accIsdnStatEntry 20 }
            accIsdnStatCallsAccepteds OBJECT-TYPE
		SYNTAX Counter
		ACCESS read-only
		STATUS deprecated
		DESCRIPTION
		  " The number of incoming calls offerred on this
		    subscriber interface which were accepted for
		    connection."
		::= { accIsdnStatEntry 21 }
            accIsdnStatCallsCompleteds OBJECT-TYPE
		SYNTAX Counter
		ACCESS read-only
		STATUS deprecated
		DESCRIPTION
		  " The number of outgoing and incoming calls
		    completed (that is, the number of calls which
		    were successfully connected)."
		::= { accIsdnStatEntry 22 }
            accIsdnStatCallsCleareds OBJECT-TYPE
		SYNTAX Counter
		ACCESS read-only
		STATUS deprecated
		DESCRIPTION
		  " The number of outgoing and incoming calls
		    cleared."
		::= { accIsdnStatEntry 23 }
            accIsdnStatDslOperStatus OBJECT-TYPE
		SYNTAX INTEGER {
		    inactive(1),	-- layer-1 deactivated
		    waiting(2),		-- awaiting activation
		    activated(3),	-- layer-1 activated
		    established(4)	-- multi-frame established
		    }
		ACCESS read-only
		STATUS deprecated
		DESCRIPTION
		  " The operation status of this interface."
		::= { accIsdnStatEntry 24 }
            accIsdnStatLastCauses OBJECT-TYPE
		SYNTAX INTEGER (0..255)
		ACCESS read-only
		STATUS deprecated
		DESCRIPTION
		  " The last cause value sent or received on this
		    subscriber interface."
		::= { accIsdnStatEntry 25 }
	-- The IsdnCall Group
	-- Parameters and operational status maintained and
	-- reported on a per-call basis.
            accIsdnCallTable OBJECT-TYPE
		SYNTAX SEQUENCE OF AccIsdnCallEntry
		ACCESS not-accessible
		STATUS deprecated
		DESCRIPTION
		  " Parameters and operational status for ISDN calls
		    active on this bridge/router terminal."
		::= { accIsdn 4 }
            accIsdnCallEntry OBJECT-TYPE
		SYNTAX AccIsdnCallEntry
		ACCESS not-accessible
		STATUS deprecated
		DESCRIPTION
		  " Parameters and operational status for a particular
		    ISDN call which is presently active or is in the
		    process of being established or cleared."
		INDEX { accIsdnCallDslIndex, accIsdnCallIdentifier }
		::= { accIsdnCallTable 1 }
            AccIsdnCallEntry ::= SEQUENCE {
                accIsdnCallIdentifier	INTEGER,
                accIsdnCallReference	INTEGER,
                accIsdnCallChannelId	INTEGER,
                accIsdnCallIfIndex	INTEGER,
                accIsdnCallInfoRate	INTEGER,
                accIsdnCallState	INTEGER,
                accIsdnCallCause	INTEGER,
                accIsdnCallOrigin	INTEGER,
                accIsdnCallAddress	OCTET STRING,
                accIsdnCallDslIndex	INTEGER
		}
            accIsdnCallIdentifier OBJECT-TYPE
		SYNTAX INTEGER (0..65536)
		ACCESS read-only
		STATUS deprecated
		DESCRIPTION
		  " The internal call control identifier for this call."
		::= { accIsdnCallEntry 1 }
            accIsdnCallReference OBJECT-TYPE
		SYNTAX INTEGER (1..32767)
		ACCESS read-only
		STATUS deprecated
		DESCRIPTION
		  " The Q.931 call reference value for this call."
		::= { accIsdnCallEntry 2 }
            accIsdnCallChannelId OBJECT-TYPE
		SYNTAX INTEGER {
		    none(1),		-- no channel allocated
		    b1(2),		-- B1
		    b2(3),		-- B2
		    h0(4)		-- hyperchannel (B1 + B2)
		    }
		ACCESS read-only
		STATUS deprecated
		DESCRIPTION
		  " The bearer channel interface ID allocated for this
		    call."
		::= { accIsdnCallEntry 3 }
            accIsdnCallIfIndex OBJECT-TYPE
		SYNTAX INTEGER {
		    j1(1),		-- J1
		    j2(2)		-- J2
		    }
		ACCESS read-only
		STATUS deprecated
		DESCRIPTION
		  " The interface index of the physical port connected
		    by the bearer channel."
		::= { accIsdnCallEntry 4 }
            accIsdnCallInfoRate OBJECT-TYPE
		SYNTAX INTEGER {
		    packet(1),
		    r-64k(17),
		    r-2x64k(18),
		    r-384k(20),
		    r-1536k(22),
		    r-1920k(24)
		    }
		ACCESS read-only
		STATUS deprecated
		DESCRIPTION
		  " The information transfer rate."
		::= { accIsdnCallEntry 5 }
            accIsdnCallState OBJECT-TYPE
		SYNTAX INTEGER {
		    disconnected(1),
		    incoming(2),
		    outgoing(3),
		    routing(4),
		    releaseing(5),
		    connected(6)
		    }
		ACCESS read-only
		STATUS deprecated
		DESCRIPTION
		  " The current call control state (not Q.931)."
		::= { accIsdnCallEntry 6 }
            accIsdnCallCause OBJECT-TYPE
		SYNTAX INTEGER (0..255)
		ACCESS read-only
		STATUS deprecated
		DESCRIPTION
		  " The last cause value associated with this call."
		::= { accIsdnCallEntry 7 }
            accIsdnCallOrigin OBJECT-TYPE
		SYNTAX INTEGER {
		    none(1),		-- not yet originated
		    terminal(2),	-- outgoing (TE-to-NT)
		    network(3)		-- incoming (NT-to_TE)
		    }
		ACCESS read-only
		STATUS deprecated
		DESCRIPTION
		  " The originator of the call."
		::= { accIsdnCallEntry 8 }
            accIsdnCallAddress OBJECT-TYPE
		SYNTAX OCTET STRING
		ACCESS read-only
		STATUS deprecated
		DESCRIPTION
		  " The remote call address associated with this call.
		    For incoming calls, this is the calling ISDN address.
		    For outgoing calls, this is the called ISDN address."
		::= { accIsdnCallEntry 9 }
            accIsdnCallDslIndex OBJECT-TYPE
		SYNTAX INTEGER (1..255)
		ACCESS read-only
		STATUS deprecated
		DESCRIPTION
		  " The interface index for the digital subscriber loop."
		::= { accIsdnCallEntry 10 }
	-- ISDN Interface Group
	--
	-- Implementation of the ISDN interface group is mandatory for all
	-- systems that implement a basic rate or primary rate ISDN
	-- interface.  The ISDN interface group consists of three tables:
	--	ISDN Subscriber Table
	--	ISDN Statistics Table
	--	ISDN Call Table
	-- These tables are indexed by a digital subscriber loop (DSL)
	-- index which has the same value as the ifIndex for the ISDN
	-- interface.  Prior to Release 8.0, the DSL index was a
	-- sequential integer index assigned independently of ifIndex.
	-- Due to the change in how ISDN tables are indexed, as well as
	-- other flaws in the ACC ISDN MIB definition, the following
	-- branches are being deprecated, and have been replaced by new
	-- branches:
	--	accIsdnDsl OBJECT IDENTIFIER ::= { accIsdn 1 }
	--	accIsdnSub OBJECT IDENTIFIER ::= { accIsdn 2 }
	--	accIsdnStat OBJECT IDENTIFIER ::= { accIsdn 3 }
	--	accIsdnCall OBJECT IDENTIFIER ::= { accIsdn 4 }
	-- ISDN Subscriber Table
	-- The ISDN Subscriber Table contains one entry for each BRI or
	-- PRI subscriber connection.  Only ISDN interfaces with a D
	-- channel have an entry in this table.  NFAS interfaces are not
	-- represented in this table.
            accIsdnxSubTable OBJECT-TYPE
		SYNTAX SEQUENCE OF AccIsdnxSubEntry
		ACCESS not-accessible
		STATUS mandatory
		DESCRIPTION
		  " ISDN subscriber table containing configuration and
		    operational parameters for all ISDN subscriber
		    interfaces on this bridge/router terminal."
		::= { accIsdn 6 }
            accIsdnxSubEntry OBJECT-TYPE
		SYNTAX AccIsdnxSubEntry
		ACCESS not-accessible
		STATUS mandatory
		DESCRIPTION
		  "An entry in the ISDN Subscriber Table"
		INDEX { accIsdnxSubDslIndex }
		::= { accIsdnxSubTable 1 }
            AccIsdnxSubEntry ::= SEQUENCE {
		accIsdnxSubDslIndex INTEGER,
		accIsdnxSubSwitchType INTEGER,
		accIsdnxSubChanConfig INTEGER,
		accIsdnxSubAdminStatus INTEGER,
		accIsdnxSubDiagLevel INTEGER,
		accIsdnxSubManualTei INTEGER,
		accIsdnxSubOperStatus INTEGER,
		accIsdnxSubNumNfas INTEGER,
		accIsdnxSubLastCause INTEGER,
		accIsdnxSubSubaddrType INTEGER,
		accIsdnxSubVoiceOption INTEGER,
		accIsdnxSubCliOption INTEGER,
		accIsdnxSubEncodingMethod INTEGER,
		accIsdnxSubDialingMethod INTEGER,
		accIsdnxSubAutoSpid INTEGER,
		accIsdnxSubAutoSwitch INTEGER
		}
            accIsdnxSubDslIndex OBJECT-TYPE
		SYNTAX INTEGER -- (1..'7fffffff'h)
		ACCESS read-only
		STATUS mandatory
		DESCRIPTION
		  " The ifIndex of an ISDN BRI, DBRI, PRI/T1 or PRI/E1
		    interface on this managed device."
		::= { accIsdnxSubEntry 1 }
            accIsdnxSubSwitchType OBJECT-TYPE
		SYNTAX INTEGER {
		bri-net3(1),
		bri-5ess(2),
		bri-dms100(3),
		bri-vn2(4),
		bri-vn3(5),
		bri-kdd(6),
		bri-ntt(7),
		bri-1tr6(8),
		bri-ni1(9),
		bri-ccitt(10),
		bri-tad2(11),
		bri-ts013(12),
		bri-ni2(13),
		pri-4ess(14),
		pri-5ess(15),
		pri-dms100(16),
		pri-net5(17),
		pri-vn3(18),
		pri-kdd(19),
		pri-ntt(20),
		pri-1tr6(21),
		pri-ccitt(22),
		pri-tad30(23),
		pri-ts014(24),
		pri-ni2(25),
		bri-auto-na(26)
		}
		ACCESS read-write
		STATUS mandatory
		DESCRIPTION
		  " The particular type of central-office switch
		    providing access to the ISDN network and to which
		    this subscriber interface is connected."
		::= { accIsdnxSubEntry 2 }
            accIsdnxSubChanConfig OBJECT-TYPE
		SYNTAX INTEGER (1..255)
		ACCESS read-write
		STATUS mandatory
		DESCRIPTION
		  " The ISDN channel configuration mode.  Beginning with
		    release 8.0, this is the number of bearer channels
		    managed by the D channel.  This object is normally
		    read-only.  It can be written only when changing the
		    channel configuration from 2B+D to 1B+D on a Nile
		    configured with a BRI in J1."
		::= { accIsdnxSubEntry 3 }
            accIsdnxSubAdminStatus OBJECT-TYPE
		SYNTAX INTEGER {
		enabled (1),
		disabled (2),
		drain (3)
		}
		ACCESS read-write
		STATUS mandatory
		DESCRIPTION
		  "  The administrative status of this subscriber interface."
		::= { accIsdnxSubEntry 4 }
            accIsdnxSubDiagLevel OBJECT-TYPE
		SYNTAX INTEGER (0..6)
		ACCESS read-write
		STATUS mandatory
		DESCRIPTION
		  " The current diagnostic message level for this
		    subscriber interface."
		::= { accIsdnxSubEntry 5 }
            accIsdnxSubManualTei OBJECT-TYPE
		SYNTAX INTEGER (0..63) -- 127
		ACCESS read-write
		STATUS mandatory
		DESCRIPTION
		" The TEI (terminal endpoint identifier) when manual
		  TEI assignment is required.  Setting this value
		  between 0 and 63 (inclusive) specifies manual TEI
		  assignment using the indicated value.  Setting this
		  value to 127 (the broadcast TEI) specifies automatic
		  TEI assignment.  This object is writable only for BRI
		  subscribers.  For PRI subscribers, the value read is
		  always 0"
		::= { accIsdnxSubEntry 6 }
            accIsdnxSubOperStatus OBJECT-TYPE
		SYNTAX INTEGER {
		deactivated (1),	-- L1 deactivated
		activated (2),		-- L1 activated, no L2 datalink
		established (3),	-- L1 activated, L2 datalink, L3 quiet
		engaged (4)		-- L1 activated, L2 datalink, L3 active
		}
		ACCESS read-write
		STATUS mandatory
		DESCRIPTION
		" The operational status of this subscriber interface."
		::= { accIsdnxSubEntry 7 }
            accIsdnxSubNumNfas OBJECT-TYPE
		SYNTAX INTEGER (0..255)
		ACCESS read-only
		STATUS mandatory
		DESCRIPTION
		" Indicates the number of NFAS trunks managed by this D
		  channel."
		::= { accIsdnxSubEntry 8 }
            accIsdnxSubLastCause OBJECT-TYPE
		SYNTAX INTEGER (0..255)
		ACCESS read-only
		STATUS mandatory
		DESCRIPTION
		" The last clearing cause for a call associated with
		  this interface."
		::= { accIsdnxSubEntry 9 }
	    accIsdnxSubSubaddrType OBJECT-TYPE
		SYNTAX INTEGER {
		    nsap(1),
		    user(2)
		    }
		ACCESS read-write
		STATUS mandatory
		DESCRIPTION
		" Indicates the subaddress type for the ISDN interface."
		::= { accIsdnxSubEntry 10 }
	    accIsdnxSubVoiceOption OBJECT-TYPE
		SYNTAX INTEGER {
		    on(1),
		    off(2)
		    }
		ACCESS read-write
		STATUS mandatory
		DESCRIPTION
		" Indicates whether the user is able to receive circuit mode voice calls"
		::= { accIsdnxSubEntry 11 }
	    accIsdnxSubCliOption OBJECT-TYPE
		SYNTAX INTEGER {
		    on(1),
		    off(2)
		    }
		ACCESS read-write
		STATUS mandatory
		DESCRIPTION
		" Indicates whether a callers identifaction will be checked with 
		  known entries before accepting the call."
		::= { accIsdnxSubEntry 12 }
        accIsdnxSubEncodingMethod OBJECT-TYPE
                SYNTAX INTEGER {
                        a-law (1),
                        mu-law(2)
                }
                ACCESS  read-only
                STATUS  mandatory
                DESCRIPTION
                        " Companding algorithm to be used when initiating
                        or answering voice calls over this interface. This
                        is configured during initialization based on the
                        user configured switch type."
                ::= { accIsdnxSubEntry 13 } 
        accIsdnxSubDialingMethod OBJECT-TYPE
                SYNTAX INTEGER {
                        overlap (1),
                        enbloc  (2)
                }
                ACCESS  read-only
                STATUS  mandatory
                DESCRIPTION
                        " Dialing method to be used when initiating
                        voice calls over the ISDN line. This
                        is configured during initialization based on the
                        user configured switch type."
                ::= { accIsdnxSubEntry 14 }
        accIsdnxSubAutoSpid OBJECT-TYPE
                SYNTAX INTEGER {
                        enabled (1),
                        disabled (2)
                }
		ACCESS read-write
                STATUS  mandatory
                DESCRIPTION
                        " SR-3888 Automatic SPID detection enabled or 
                          disabled for a BRI subscriber interface."
                ::= { accIsdnxSubEntry 19 }
            accIsdnxSubAutoSwitch OBJECT-TYPE
		SYNTAX INTEGER {
			unknown(1),
			manual(2),
			bri-ni1(3),
			bri-5ess(4),
			bri-dms100(5)
		}
		ACCESS read-only
		STATUS mandatory
		DESCRIPTION
		  " The central-office switch type detected by the Automatic
		    Switch detection function."
		::= { accIsdnxSubEntry 20 }
	-- ISDN Statistics Table
	--
	-- The ISDN statistics table contains one entry for each BRI or
	-- PRI subscriber loop connection.
	-- In the case of PRI subscribers, an entry exists only for PRI
	-- interfaces enabled for common  channel signaling (i.e.,
	-- interfaces containing a D channel).
	-- No statistics are maintained for NFAS-enabled subscriber loops.
            accIsdnxStatTable OBJECT-TYPE
		SYNTAX SEQUENCE OF AccIsdnxStatEntry
		ACCESS not-accessible
		STATUS mandatory
		DESCRIPTION
		" Statistics and operational status maintained for all
		  ISDN subscriber interfaces on this bridge/router
		  terminal."
		::= { accIsdn 7 }
            accIsdnxStatEntry OBJECT-TYPE
		SYNTAX AccIsdnxStatEntry
		ACCESS not-accessible
		STATUS mandatory
		DESCRIPTION
		" An entry in the ISDN Statistics Table."
		INDEX { accIsdnxStatDslIndex }
		::= { accIsdnxStatTable 1 }
            AccIsdnxStatEntry ::= SEQUENCE {
		accIsdnxStatDslIndex INTEGER,
		accIsdnxStatHdlcInPackets Counter,
		accIsdnxStatHdlcInOctets Counter,
		accIsdnxStatHdlcInErrors Counter,
		accIsdnxStatHdlcInDiscards Counter,
		accIsdnxStatHdlcOutPackets Counter,
		accIsdnxStatHdlcOutOctets Counter,
		accIsdnxStatHdlcOutErrors Counter,
		accIsdnxStatHdlcOutDiscards Counter,
		accIsdnxStatLapdUnsolicResps Counter,
		accIsdnxStatLapdPeerSabmes Counter,
		accIsdnxStatLapdN200Errors Counter,
		accIsdnxStatLapdNrSeqErrors Counter,
		accIsdnxStatLapdRecvdFrmrs Counter,
		accIsdnxStatLapdCntlErrors Counter,
		accIsdnxStatLapdInfoErrors Counter,
		accIsdnxStatLapdWrongSizes Counter,
		accIsdnxStatLapdN201Errors Counter,
		accIsdnxStatCallOriginateds Counter,
		accIsdnxStatCallOfferreds Counter,
		accIsdnxStatCallRouteds Counter,
		accIsdnxStatCallAccepteds Counter,
		accIsdnxStatCallCompleteds Counter,
		accIsdnxStatCallCleareds Counter }
            accIsdnxStatDslIndex OBJECT-TYPE
		SYNTAX INTEGER -- (1..'7fffffff'h)
		ACCESS read-only
		STATUS mandatory
		DESCRIPTION
		" The ifIndex of an ISDN BRI, DBRI, PRI/T1 or PRI/E1
		  interface on this managed device."
		::= { accIsdnxStatEntry 1 }
            accIsdnxStatHdlcInPackets OBJECT-TYPE
		SYNTAX Counter
		ACCESS read-only
		STATUS mandatory
		DESCRIPTION
		" The number of packets received on the D-channel of
		  this ISDN interface."
		::= { accIsdnxStatEntry 2 }
            accIsdnxStatHdlcInOctets OBJECT-TYPE
		SYNTAX Counter
		ACCESS read-only
		STATUS mandatory
		DESCRIPTION
		" The number of octets received on the D-channel of
		  this ISDN interface."
		::= { accIsdnxStatEntry 3 }
            accIsdnxStatHdlcInErrors OBJECT-TYPE
		SYNTAX Counter
		ACCESS read-only
		STATUS mandatory
		DESCRIPTION
		" The number of input hardware errors counted by the
		  D-channel HDLC driver."
		::= { accIsdnxStatEntry 4 }
            accIsdnxStatHdlcInDiscards OBJECT-TYPE
		SYNTAX Counter
		ACCESS read-only
		STATUS mandatory
		DESCRIPTION
		" The number of input packets discarded by the
		  D-channel HDLC driver."
		::= { accIsdnxStatEntry 5 }
            accIsdnxStatHdlcOutPackets OBJECT-TYPE
		SYNTAX Counter
		ACCESS read-only
		STATUS mandatory
		DESCRIPTION
		" The number of packets transmitted on the D-channel of
		  this ISDN interface."
		::= { accIsdnxStatEntry 6 }
            accIsdnxStatHdlcOutOctets OBJECT-TYPE
		SYNTAX Counter
		ACCESS read-only
		STATUS mandatory
		DESCRIPTION
		" The number of octets transmitted on the D-channel of
		  this ISDN interface."
		::= { accIsdnxStatEntry 7 }
            accIsdnxStatHdlcOutErrors OBJECT-TYPE
		SYNTAX Counter
		ACCESS read-only
		STATUS mandatory
		DESCRIPTION
		" The number of output hardware errors counted by the
		  D-channel HDLC driver."
		::= { accIsdnxStatEntry 8 }
            accIsdnxStatHdlcOutDiscards OBJECT-TYPE
		SYNTAX Counter
		ACCESS read-only
		STATUS mandatory
		DESCRIPTION
		" The number of output packets discarded by the
		  D-channel HDLC driver."
		::= { accIsdnxStatEntry 9 }
            accIsdnxStatLapdUnsolicResps OBJECT-TYPE
		SYNTAX Counter
		ACCESS read-only
		STATUS mandatory
		DESCRIPTION
		" The number of unsolicited LAPD response frames
		  received on all data links associated with the
		  D-channel of this ISDN interface."
		::= { accIsdnxStatEntry 10 }
            accIsdnxStatLapdPeerSabmes OBJECT-TYPE
		SYNTAX Counter
		ACCESS read-only
		STATUS mandatory
		DESCRIPTION
		" The number of peer SABME frames received on all data
		  links associated with the D-channel of this ISDN
		  interface."
		::= { accIsdnxStatEntry 11 }
            accIsdnxStatLapdN200Errors OBJECT-TYPE
		SYNTAX Counter
		ACCESS read-only
		STATUS mandatory
		DESCRIPTION
		" The number of unsuccessful T200 timer recoveries
		  after a frame has been retransmitted N200 times."
		::= { accIsdnxStatEntry 12 }
            accIsdnxStatLapdNrSeqErrors OBJECT-TYPE
		SYNTAX Counter
		ACCESS read-only
		STATUS mandatory
		DESCRIPTION
		" The number of N(R) sequence errors."
		::= { accIsdnxStatEntry 13 }
            accIsdnxStatLapdRecvdFrmrs OBJECT-TYPE
		SYNTAX Counter
		ACCESS read-only
		STATUS mandatory
		DESCRIPTION
		" The number of LAPD FRMR response frames received."
		::= { accIsdnxStatEntry 14 }
            accIsdnxStatLapdCntlErrors OBJECT-TYPE
		SYNTAX Counter
		ACCESS read-only
		STATUS mandatory
		DESCRIPTION
		" The number of LAPD frames received with an invalid or
		  non-implemented control field."
		::= { accIsdnxStatEntry 15 }
            accIsdnxStatLapdInfoErrors OBJECT-TYPE
		SYNTAX Counter
		ACCESS read-only
		STATUS mandatory
		DESCRIPTION
		" The number of LAPD frames received with a
		  non-permitted information (I) field."
		::= { accIsdnxStatEntry 16 }
            accIsdnxStatLapdWrongSizes OBJECT-TYPE
		SYNTAX Counter
		ACCESS read-only
		STATUS mandatory
		DESCRIPTION
		" The number of LAPD frames received which were the
		  wrong size."
		::= { accIsdnxStatEntry 17 }
            accIsdnxStatLapdN201Errors OBJECT-TYPE
		SYNTAX Counter
		ACCESS read-only
		STATUS mandatory
		DESCRIPTION
		" The number of LAPD frames received which contained
		  and information field which exceeded N201."
		::= { accIsdnxStatEntry 18 }
            accIsdnxStatCallOriginateds OBJECT-TYPE
		SYNTAX Counter
		ACCESS read-only
		STATUS mandatory
		DESCRIPTION
		" The number of outgoing calls originated on this ISDN
		  interface."
		::= { accIsdnxStatEntry 19 }
            accIsdnxStatCallOfferreds OBJECT-TYPE
		SYNTAX Counter
		ACCESS read-only
		STATUS mandatory
		DESCRIPTION
		" The number of incoming calls offered on this ISDN
		  interface."
		::= { accIsdnxStatEntry 20 }
            accIsdnxStatCallRouteds OBJECT-TYPE
		SYNTAX Counter
		ACCESS read-only
		STATUS mandatory
		DESCRIPTION
		" The number of outgoing calls originated on this ISDN
		  interface which were routed by the network."
		::= { accIsdnxStatEntry 21 }
            accIsdnxStatCallAccepteds OBJECT-TYPE
		SYNTAX Counter
		ACCESS read-only
		STATUS mandatory
		DESCRIPTION
		" The number of incoming calls offered on this ISDN
		  interface which were accepted for connection."
		::= { accIsdnxStatEntry 22 }
            accIsdnxStatCallCompleteds OBJECT-TYPE
		SYNTAX Counter
		ACCESS read-only
		STATUS mandatory
		DESCRIPTION
		" The number of outgoing and incoming calls completed
		  (that is, the number of calls which were successfully
		  connected)."
		::= { accIsdnxStatEntry 23 }
            accIsdnxStatCallCleareds OBJECT-TYPE
		SYNTAX Counter
		ACCESS read-only
		STATUS mandatory
		DESCRIPTION
		" The number of outgoing and incoming calls cleared."
		::= { accIsdnxStatEntry 24 }
	-- ISDN Call Table
	-- The ISDN call table contains an entry for each call in
	-- progress. A call is in progress if its call state is
	-- non-zero (i.e., not IDLE). All calls on all ISDN interfaces
	-- are co-mingled in the same table.
            accIsdnxCallTable OBJECT-TYPE
		SYNTAX SEQUENCE OF AccIsdnxCallEntry
		ACCESS not-accessible
		STATUS mandatory
		DESCRIPTION
		" Parameters and operational status for ISDN calls in
		  progress on this bridge/router terminal."
		::= { accIsdn 8 }
            accIsdnxCallEntry OBJECT-TYPE
		SYNTAX AccIsdnxCallEntry
		ACCESS not-accessible
		STATUS mandatory
		DESCRIPTION
		" An entry in the ISDN Call Table."
		INDEX { accIsdnxCallDslIndex, accIsdnxCallReference, accIsdnxCallOrigin }
		::= { accIsdnxCallTable 1 }
            AccIsdnxCallEntry ::= SEQUENCE {
		accIsdnxCallDslIndex INTEGER,
		accIsdnxCallReference INTEGER,
		accIsdnxCallOrigin INTEGER,
		 accIsdnxCallCircuitIndex INTEGER,
		accIsdnxCallInfoRate INTEGER,
		accIsdnxCallState INTEGER,
		accIsdnxCallCause INTEGER,
		accIsdnxCallAddress OCTET STRING,
		accIsdnxCallInfoType INTEGER,
		accIsdnxCallSlotMap INTEGER
		}
            accIsdnxCallDslIndex OBJECT-TYPE
		SYNTAX INTEGER -- (1..'7fffffff'h)
		ACCESS read-only
		STATUS mandatory
		DESCRIPTION
		" The ifIndex of an ISDN BRI, DBRI, PRI/T1 or PRI/E1
		  interface on this managed device."
		::= { accIsdnxCallEntry 1 }
            accIsdnxCallReference OBJECT-TYPE
		SYNTAX INTEGER (1..32767)
		ACCESS read-only
		STATUS mandatory
		DESCRIPTION
		" The Q.931 call reference value for this call."
		::= { accIsdnxCallEntry 2 }
            accIsdnxCallOrigin OBJECT-TYPE
		SYNTAX INTEGER {
			none(1),	-- unknown                     
			terminal(2),	-- outgoing (TE-to-NT)         
			network(3)	-- incoming (NT-to-TE)
		}
		ACCESS read-only
		STATUS mandatory
		DESCRIPTION
		" The originator of the call."
		::= { accIsdnxCallEntry 3 }
            accIsdnxCallCircuitIndex OBJECT-TYPE
		SYNTAX INTEGER -- (1..'7fffffff'h)
		ACCESS read-only
		STATUS mandatory
		DESCRIPTION
		" The ifIndex for the circuit associated with this call."
		::= { accIsdnxCallEntry 4 }
            accIsdnxCallInfoRate OBJECT-TYPE
		SYNTAX INTEGER {
		info-rate-1x64k(1),
		info-rate-2x64k(2),
		info-rate-3x64k(3),
		info-rate-4x64k(4),
		info-rate-5x64k(5),
		info-rate-6x64k(6),
		info-rate-7x64k(7),
		info-rate-8x64k(8),
		info-rate-9x64k(9),
		info-rate-10x64k(10),
		info-rate-11x64k(11),
		info-rate-12x64k(12),
		info-rate-13x64k(13),
		info-rate-14x64k(14),
		info-rate-15x64k(15),
		info-rate-16x64k(16),
		info-rate-17x64k(17),
		info-rate-18x64k(18),
		info-rate-19x64k(19),
		info-rate-20x64k(20),
		info-rate-21x64k(21),
		info-rate-22x64k(22),
		info-rate-23x64k(23),
		info-rate-24x64k(24),
		info-rate-25x64k(25),
		info-rate-26x64k(26),
		info-rate-27x64k(27),
		info-rate-28x64k(28),
		info-rate-29x64k(29),
		info-rate-30x64k(30),
		info-rate-31x64k(31),
		packet(32)
		}
		ACCESS read-only
		STATUS mandatory
		DESCRIPTION
		" The information transfer rate."
		::= { accIsdnxCallEntry 5 }
            accIsdnxCallState OBJECT-TYPE
		SYNTAX INTEGER {
		idle (1),
		initiated (2),
		overlap-send (3),
		outgoing (4),
		delivered (5),
		present (6),
		received (7),
		connecting (8),
		incoming (9),
		active (10),
		discon-req (11),
		discon-ind (12),
		suspend (13),
		resume (14),
		release (15),
		overlap-recv (16)
		}
		ACCESS read-only
		STATUS mandatory
		DESCRIPTION
		" The Q.931 call control state."
		::= { accIsdnxCallEntry 6 }
            accIsdnxCallCause OBJECT-TYPE
		SYNTAX INTEGER (0..255)
		ACCESS read-only
		STATUS mandatory
		DESCRIPTION
		" The last cause value associated with this call."
		::= { accIsdnxCallEntry 7 }
            accIsdnxCallAddress OBJECT-TYPE
		SYNTAX OCTET STRING
		ACCESS read-only
		STATUS mandatory
		DESCRIPTION
		" The remote call address associated with this call.
		  For incoming calls, this is the calling ISDN
		  address.  For outgoing calls, this is the called ISDN
		  address."
		::= { accIsdnxCallEntry 8 }
            accIsdnxCallInfoType OBJECT-TYPE
		SYNTAX INTEGER {
		info-type-cmd (1),	-- circuit mode data (64kb/sec)
		info-type-cm56 (2),	-- circuit mode data (56kb/sec)
		info-type-cmv (3)	-- circuit mode data over voice
		}
		ACCESS read-only
		STATUS mandatory
		DESCRIPTION
		" The information transfer type:
		  info-type-cmd		circuit mode data, clear channel
		  			64 kbits/s
		  info-type-cm56	circuit mode data, rate-adapted
		  			to 56 kbits/s
		  info-type-cmv		circuit mode data over voice circuit"
		::= { accIsdnxCallEntry 9 }
            accIsdnxCallSlotMap OBJECT-TYPE
		SYNTAX INTEGER
		ACCESS read-only
		STATUS mandatory
		DESCRIPTION
		" A 31-bit mask which identifies the time-slots forming
		  a hyperchannel."
		::= { accIsdnxCallEntry 10 }
	-- The IsdnTest Group
        accIsdnTest OBJECT IDENTIFIER ::= { accIsdn 5 }
	    -- Parameters and commands maintained and reported on a
	    -- per-terminal basis used for controlling homologation
	    -- testing.
            accIsdnTestIfIndex OBJECT-TYPE
		SYNTAX INTEGER {
		    j1(1),		-- J1
		    j2(2)		-- J2
		    }
		ACCESS read-write
		STATUS mandatory
		DESCRIPTION
		  " The interface index for the physical port from
		    which a call will be made."
		::= { accIsdnTest 1 }
            accIsdnTestAddress OBJECT-TYPE
		SYNTAX OCTET STRING
		ACCESS read-write
		STATUS mandatory
		DESCRIPTION
		  " The ISDN destination call address."
		::= { accIsdnTest 2 }
            accIsdnTestCommand OBJECT-TYPE
		SYNTAX INTEGER {
		    normal(1),
		    accept(2),
		    reject(3),
		    ignore(4),
		    call(5),
		    clear(6),
		    disconnect(7),
		    loop(8),
		    unloop(9),
		    activate(10),
		    deactivate(11),
		    display(12)
		    }
		ACCESS read-write
		STATUS mandatory
		DESCRIPTION
		  " The action to be performed."
		::= { accIsdnTest 3 }
            accIsdnTestRouting OBJECT-TYPE
		SYNTAX INTEGER {
                    normal(1),
                    accept(2),
                    reject(3),
                    ignore(4),
                    call(5),
                    clear(6),
                    disconnect(7),
                    activate(8),
                    deactivate(9),
                    loop4(10),
                    reset(11),
                    display(12),
                    ones(13),
                    zeros(14),
                    bon(15),
                    boff(16)
		    }
		ACCESS read-only
		STATUS mandatory
		DESCRIPTION
		  " The action to be performed for incoming calls."
		::= { accIsdnTest 4 }
            accIsdnTestRegName OBJECT-TYPE
		SYNTAX INTEGER {
		    nr0(0),
		    nr1(1),
		    nr2(2),
		    nr3(3),
		    nr4(4),
		    nr5(5),
		    nr6(6),
		    br0(16),
		    br1(17),
		    br2(18),
		    br3(19),
		    br4(20),
		    br5(21),
		    br6(22),
		    br7(23),
		    br8(24),
		    br9(25),
		    br10(26),
		    br11(27),
		    br12(28),
		    br13(29),
		    br14(30),
		    br15(31)
		    }
		ACCESS read-write
		STATUS mandatory
		DESCRIPTION
		  " The name of the MC145474 register to write.
		"
		::= { accIsdnTest 5 }
            accIsdnTestRegValue OBJECT-TYPE
		SYNTAX INTEGER (0..255)
		ACCESS read-write
		STATUS mandatory
		DESCRIPTION
		  " The value to write to the MC145474 register."
		::= { accIsdnTest 6 }
            accwIsdnTestBChanMode OBJECT-TYPE
                SYNTAX INTEGER {
                    normal(1),
                    accept(2),
                    reject(3),
                    ignore(4),
                    call(5),
                    clear(6),
                    disconnect(7),
                    activate(8),
                    deactivate(9),
                    loop4(10),
                    reset(11),
                    display(12),
                    ones(13),
                    zeros(14),
                    bon(15),
                    boff(16)
                    }
                ACCESS read-write
                STATUS mandatory
                DESCRIPTION
                  " The action to be performed on the B-channel."
                ::= { accIsdnTest 7 }
            accwIsdnTestOptions OBJECT-TYPE
                SYNTAX INTEGER
                ACCESS read-write
                STATUS mandatory
                DESCRIPTION
                  " Test options in hex."
                ::= { accIsdnTest 8 }
-- ISDN SPID group
        accIsdnSpidTable OBJECT-TYPE
                SYNTAX SEQUENCE OF AccIsdnSpidEntry
                ACCESS not-accessible
                STATUS mandatory
                DESCRIPTION
                        " Valid SPIDs currently Registered with the
                          CO, required for placing/accepting calls."
                ::= { accIsdn 9 }
        accIsdnSpidEntry OBJECT-TYPE
                SYNTAX AccIsdnSpidEntry
                ACCESS not-accessible
                STATUS mandatory
                DESCRIPTION
                        " SPID information entry in the SPID Table."
                INDEX { accIsdnSpidIndex }
                ::= { accIsdnSpidTable 1 }
        AccIsdnSpidEntry ::= SEQUENCE {
		accIsdnSpidIndex INTEGER,
                accIsdnSpidValue DisplayString
		}
        accIsdnSpidIndex OBJECT-TYPE
                SYNTAX INTEGER
                ACCESS read-only
                STATUS mandatory
                DESCRIPTION
                        " An Index to Ports of B-channels."
                ::= { accIsdnSpidEntry 1 }
        accIsdnSpidValue OBJECT-TYPE
                SYNTAX DisplayString
                ACCESS read-write
                STATUS mandatory
                DESCRIPTION
                        " Value of SPID,Required for the terminal to be
                          active on the S/T bus."
                ::= { accIsdnSpidEntry 2 }
-- The IsdnTermination Status 
        accIsdnTerm OBJECT IDENTIFIER ::= { accIsdn 10 }
        -- Used for setting the Termination status on a Congo S/T interface 
	accIsdnxTermination OBJECT-TYPE
                SYNTAX  INTEGER {
                       on(1),
                       off(2)
                }
                ACCESS  read-write
                STATUS  mandatory
		DESCRIPTION
                  " ISDN Bus Termination status"
                ::= { accIsdnTerm 1 }
	accIsdnxCurrCalls OBJECT-TYPE
                SYNTAX  INTEGER 
                ACCESS  read-only
                STATUS  mandatory
		DESCRIPTION
                  " Number of active ISDN calls"
                ::= { accIsdn 11 }
-- START CFG_TRAP_ENHANCEMENTS 
-- Isdn traps
        accIsdnTraps OBJECT IDENTIFIER ::= { accIsdn 12 }
        accIsdnTrapMsg  OBJECT-TYPE
                SYNTAX  DisplayString
                ACCESS  read-only
                STATUS  mandatory
                DESCRIPTION
                        " ISDN Trap Message "
                ::= { accIsdnTraps 1 }
-- END MANILA_NEW

        accIsdnOutGoingCallTrap TRAP-TYPE
                ENTERPRISE   accIsdnTraps 
                VARIABLES  { accIsdnTrapMsg ,
                              accTrapLogSeqNum}
                DESCRIPTION
                  "While initializing the call control block.  
		   When the call was first originated to establish 
		   the correct connection endpoint specifier to use, 
		   there is a check on failing which this trap is 
	           generated 
SEVERITY-DEFAULT: Minor 
EVENTTYPE-DEFAULT: 10 
ADDITIONAL-TEXT-VARIABLES: { accTrapLogSeqNum,accIsdnTrapMsg }
PCAUSE-DEFAULT: 46 " 
 
                ::= 1
        accIsdnCallResetTrap TRAP-TYPE
                ENTERPRISE   accIsdnTraps 
                VARIABLES  { accIsdnTrapMsg ,
                              accTrapLogSeqNum}
                DESCRIPTION
                  "When a catestrophic event occurs, if there is 
		   no recovery because of less cblks, then the call 
		   is simply forced to clear, which is cause for this 
		   call reset trap 
SEVERITY-DEFAULT: Major 
EVENTTYPE-DEFAULT: 2 
ADDITIONAL-TEXT-VARIABLES: { accTrapLogSeqNum,accIsdnTrapMsg }
PCAUSE-DEFAULT: 6 " 
 
                ::= 2 
        accIsdnConnectTrap TRAP-TYPE
                ENTERPRISE   accIsdnTraps 
                VARIABLES  { accIsdnTrapMsg ,
                              accTrapLogSeqNum}
                DESCRIPTION
                  "Indication thruough this trap is a failure of 
		   Connect if the ICCB channel is present. Else deicdes 
		   there is no bearer channel and sends this trap. 
SEVERITY-DEFAULT: Minor 
EVENTTYPE-DEFAULT: 2 
ADDITIONAL-TEXT-VARIABLES: { accTrapLogSeqNum,accIsdnTrapMsg }
PCAUSE-DEFAULT: 46 " 
 
                ::= 3
        accIsdnStaleDialCntxtTrap TRAP-TYPE
                ENTERPRISE   accIsdnTraps 
                VARIABLES  { accIsdnTrapMsg ,
                              accTrapLogSeqNum}
                DESCRIPTION
                  "This trap is triggered when there is a mismatch in 
		   the Magicnumber. Treating it as a stale dial.
SEVERITY-DEFAULT: Minor 
EVENTTYPE-DEFAULT: 10 
ADDITIONAL-TEXT-VARIABLES: { accTrapLogSeqNum,accIsdnTrapMsg }
PCAUSE-DEFAULT: 46 " 
 
                ::= 4
        accIsdnIncomingCallTrap TRAP-TYPE
                ENTERPRISE   accIsdnTraps 
                VARIABLES  { accIsdnTrapMsg ,
                              accTrapLogSeqNum}
                DESCRIPTION
                  "This is generated during identifying the calling 
		   party, if the call has to be refused based on the 
		   validity of the calling number. The reason is also 
		   stated in the trap.
SEVERITY-DEFAULT: Warning 
EVENTTYPE-DEFAULT: 10 
ADDITIONAL-TEXT-VARIABLES: { accTrapLogSeqNum,accIsdnTrapMsg }
PCAUSE-DEFAULT: 102 " 
 
                ::= 5
        accIsdnCallTrap TRAP-TYPE
                ENTERPRISE   accIsdnTraps 
                VARIABLES  { accIsdnTrapMsg ,
                              accTrapLogSeqNum}
                DESCRIPTION
                  "This is generated during identifying the called party, 
		   if the call has to be refused based on the validity 
		   of the called number. The reason is also stated in 
		   the trap.
SEVERITY-DEFAULT: Warning 
EVENTTYPE-DEFAULT: 10 
ADDITIONAL-TEXT-VARIABLES: { accTrapLogSeqNum,accIsdnTrapMsg }
PCAUSE-DEFAULT: 102 " 
 
                ::= 6
        accIsdnApplTmrExpTrap TRAP-TYPE
                ENTERPRISE   accIsdnTraps 
                VARIABLES  { accIsdnTrapMsg ,
                              accTrapLogSeqNum}
                DESCRIPTION
                  "If the application timer expires during the call 
		   setup, then the call is aborted. This trap is sent 
		   to convey the same.
SEVERITY-DEFAULT: Warning 
EVENTTYPE-DEFAULT: 10 
ADDITIONAL-TEXT-VARIABLES: { accTrapLogSeqNum,accIsdnTrapMsg }
PCAUSE-DEFAULT: 102 " 
 
                ::= 7
        accIsdnApplTmrExpInClearTrap TRAP-TYPE
                ENTERPRISE   accIsdnTraps 
                VARIABLES  { accIsdnTrapMsg ,
                              accTrapLogSeqNum}
                DESCRIPTION
                  "If the application timer expires during the call 
		   clearing, then the call is aborted. This trap is 
		   sent to convey the same.
SEVERITY-DEFAULT: Warning 
EVENTTYPE-DEFAULT: 10 
ADDITIONAL-TEXT-VARIABLES: { accTrapLogSeqNum,accIsdnTrapMsg }
PCAUSE-DEFAULT: 102 " 
 
                ::= 8
        accIsdnChannelRestrtTrap TRAP-TYPE
                ENTERPRISE   accIsdnTraps 
                VARIABLES  { accIsdnTrapMsg ,
                              accTrapLogSeqNum}
                DESCRIPTION
                  "While determining valid the channel stat, if the 
		   action is to restart the channel, then the 
		   appropriate B-Channel is restarted. This trap indicates 
		   such a situation.
SEVERITY-DEFAULT: Warning 
EVENTTYPE-DEFAULT: 2 
ADDITIONAL-TEXT-VARIABLES: { accTrapLogSeqNum,accIsdnTrapMsg }
PCAUSE-DEFAULT: 6 " 
 
                ::= 9
        accIsdnDataLnkRelTrap TRAP-TYPE
                ENTERPRISE   accIsdnTraps 
                VARIABLES  { accIsdnTrapMsg,
			     accTrapLogSeverityType ,
         accTrapLogSeqNum}
                DESCRIPTION
                  "If the D-channel Data Link is is to be released 
		   making Datalink down, then this trap is triggered.
SEVERITY-DEFAULT: Warning 
EVENTTYPE-DEFAULT: 2 
ADDITIONAL-TEXT-VARIABLES: { accTrapLogSeqNum,accIsdnTrapMsg }
PCAUSE-DEFAULT: 108 " 
 
                ::= 10
        accIsdnDataLnkEstTrap TRAP-TYPE
                ENTERPRISE   accIsdnTraps 
                VARIABLES  { accIsdnTrapMsg,
			     accTrapLogSeverityType ,
         accTrapLogSeqNum}
                DESCRIPTION
                  "If the D-Channel Data Link is established making 
		   Datalink UP, then this trap is triggered.
SEVERITY-DEFAULT: Clear 
EVENTTYPE-DEFAULT: 2 
ADDITIONAL-TEXT-VARIABLES: { accTrapLogSeqNum,accIsdnTrapMsg }
PCAUSE-DEFAULT: 108 " 
 
                ::= 11
        accIsdnConfigStackTrap TRAP-TYPE
                ENTERPRISE   accIsdnTraps 
                VARIABLES  { accIsdnTrapMsg ,
                              accTrapLogSeqNum}
                DESCRIPTION
                  "If the ISDN stack cannot be configured because of 
		   reasons like unspecified switch type, or not 
		   supporting DCBU etc., then this trap is generated 
		   which is conveying that a configuration error has 
		   occured.
SEVERITY-DEFAULT: Warning 
EVENTTYPE-DEFAULT: 10 
ADDITIONAL-TEXT-VARIABLES: { accTrapLogSeqNum,accIsdnTrapMsg }
PCAUSE-DEFAULT: 7 " 
 
                ::= 12
        accIsdnSubscriberLoopTrap TRAP-TYPE
                ENTERPRISE   accIsdnTraps 
                VARIABLES  { accIsdnTrapMsg ,
                              accTrapLogSeqNum}
                DESCRIPTION
                  "When a catestorphic error like low cblk conditions 
		   occur, then it tries to recover by restting the 
		   subscriber's loop. That is when this trap is generated.
SEVERITY-DEFAULT: Minor 
EVENTTYPE-DEFAULT: 10 
ADDITIONAL-TEXT-VARIABLES: { accTrapLogSeqNum,accIsdnTrapMsg }
PCAUSE-DEFAULT: 46 " 
 
                ::= 13
        accIsdnRegisterTrap TRAP-TYPE
                ENTERPRISE   accIsdnTraps 
                VARIABLES  { accIsdnTrapMsg ,
                              accTrapLogSeqNum}
                DESCRIPTION
                  "If the registration name is not identified and found 
		   in the list, then it sends this trap.
SEVERITY-DEFAULT: Warning 
EVENTTYPE-DEFAULT: 10 
ADDITIONAL-TEXT-VARIABLES: { accTrapLogSeqNum,accIsdnTrapMsg }
PCAUSE-DEFAULT: 7 " 
 
                ::= 14
        accIsdnTrmnlRegErrTrap TRAP-TYPE
                ENTERPRISE   accIsdnTraps 
                VARIABLES  { accIsdnTrapMsg ,
                              accTrapLogSeqNum}
                DESCRIPTION
                  "If there is a error in getting the SPID indicates 
		   that the it is a unknown CES or may be a inoppurtune 
		   event has occured and hence the terminal registration 
		   error is sent.
SEVERITY-DEFAULT: Major 
EVENTTYPE-DEFAULT: 2 
ADDITIONAL-TEXT-VARIABLES: { accTrapLogSeqNum,accIsdnTrapMsg }
PCAUSE-DEFAULT: 6 " 
 
                ::= 15
        accIsdnTrmnlRegTrap TRAP-TYPE
                ENTERPRISE   accIsdnTraps 
                VARIABLES  { accIsdnTrapMsg ,
                              accTrapLogSeqNum}
                DESCRIPTION
                  "In the event SPID state being pending indicates that 
		   the the terminal registration failed. This trap 
		   indicates the same.
SEVERITY-DEFAULT: Major 
EVENTTYPE-DEFAULT: 2 
ADDITIONAL-TEXT-VARIABLES: { accTrapLogSeqNum,accIsdnTrapMsg }
PCAUSE-DEFAULT: 6 " 
 
                ::= 16
        accIsdnAwaitDatalnkEstTrap TRAP-TYPE
                ENTERPRISE   accIsdnTraps 
                VARIABLES  { accIsdnTrapMsg ,
                              accTrapLogSeqNum}
                DESCRIPTION
                  "If the SME_TERM_REGISTER request is apparently stuck,
		   most likely because a datalink cannot be established, 
		   then this trap is generated.
SEVERITY-DEFAULT: Major 
EVENTTYPE-DEFAULT: 2 
ADDITIONAL-TEXT-VARIABLES: { accTrapLogSeqNum,accIsdnTrapMsg }
PCAUSE-DEFAULT: 6 " 
 
                ::= 17 
        accIsdnDisconnectTrap TRAP-TYPE
                ENTERPRISE   accIsdnTraps 
                VARIABLES  { accIsdnTrapMsg ,
                              accTrapLogSeqNum}
                DESCRIPTION
                  "If the CCB state is proceeding and the ISDN CHANNEL 
		   ID is none then this trap can be triggered after 
		   which the call is abort.
SEVERITY-DEFAULT: Major 
EVENTTYPE-DEFAULT: 10 
ADDITIONAL-TEXT-VARIABLES: { accTrapLogSeqNum,accIsdnTrapMsg }
PCAUSE-DEFAULT: 6 " 
 
                ::= 18
        accIsdnOutGoingCallFailTrap TRAP-TYPE
                ENTERPRISE   accIsdnTraps 
                VARIABLES  { accIsdnTrapMsg ,
                              accTrapLogSeqNum}
                DESCRIPTION
                  "In the process of disconnect request from the RM 
		   Manager if there isn't any active call, then this 
		   trap is generated.
SEVERITY-DEFAULT: Minor 
EVENTTYPE-DEFAULT: 10 
ADDITIONAL-TEXT-VARIABLES: { accTrapLogSeqNum,accIsdnTrapMsg }
PCAUSE-DEFAULT: 46 " 
 
                ::= 19
        accIsdnTrap20 TRAP-TYPE
                ENTERPRISE   accIsdnTraps 
                VARIABLES  { accIsdnTrapMsg ,
                              accTrapLogSeqNum}
                DESCRIPTION
                  "If the RM Dial manger sends the request to set up 
		   and if it fails for various reason, then this trap 
		   is generated.
SEVERITY-DEFAULT: Minor 
EVENTTYPE-DEFAULT: 10 
ADDITIONAL-TEXT-VARIABLES: { accTrapLogSeqNum,accIsdnTrapMsg }
PCAUSE-DEFAULT: 46 " 
 
                ::= 20
        accIsdnModuleErrTrap TRAP-TYPE
                ENTERPRISE   accIsdnTraps 
                VARIABLES  { accIsdnTrapMsg ,
                              accTrapLogSeqNum}
                DESCRIPTION
                  "If the application timer expires during the call 
		   setup, then the call is aborted. This trap is sent 
		   to convey the same.
SEVERITY-DEFAULT: Minor 
EVENTTYPE-DEFAULT: 10 
ADDITIONAL-TEXT-VARIABLES: { accTrapLogSeqNum,accIsdnTrapMsg }
PCAUSE-DEFAULT: 46 " 
 
                ::= 21
        accIsdnTrap22 TRAP-TYPE
                ENTERPRISE   accIsdnTraps 
                VARIABLES  { accIsdnTrapMsg ,
                              accTrapLogSeqNum}
                DESCRIPTION
                  "If the application timer expires during the call 
		   clrearing, then the call is aborted. This trap is 
		   sent to convey the same.
SEVERITY-DEFAULT: Minor 
EVENTTYPE-DEFAULT: 10 
ADDITIONAL-TEXT-VARIABLES: { accTrapLogSeqNum,accIsdnTrapMsg }
PCAUSE-DEFAULT: 46 " 
 
                ::= 22
        accIsdnNfasIntfTrap TRAP-TYPE
                ENTERPRISE   accIsdnTraps 
                VARIABLES  { accIsdnTrapMsg ,
                              accTrapLogSeqNum}
                DESCRIPTION
                  "If there is a application-dependent error then this 
		   trap displays the module function and the error 
		   message.
SEVERITY-DEFAULT: Minor 
EVENTTYPE-DEFAULT: 10 
ADDITIONAL-TEXT-VARIABLES: { accTrapLogSeqNum,accIsdnTrapMsg }
PCAUSE-DEFAULT: 46 " 
 
                ::= 23
        accIsdnNoSpidTrap TRAP-TYPE
                ENTERPRISE   accIsdnTraps 
                VARIABLES  { accIsdnTrapMsg ,
                              accTrapLogSeqNum}
                DESCRIPTION
                  "While initialsing the layer1 task, if the interface 
		   is configured for NT mode, then this trap is generated.
SEVERITY-DEFAULT: Warning 
EVENTTYPE-DEFAULT: 10 
ADDITIONAL-TEXT-VARIABLES: { accTrapLogSeqNum,accIsdnTrapMsg }
PCAUSE-DEFAULT: 7 " 
 
                ::= 24
        accIsdnSpidConflictTrap TRAP-TYPE
                ENTERPRISE   accIsdnTraps 
                VARIABLES  { accIsdnTrapMsg ,
                              accTrapLogSeqNum}
                DESCRIPTION
                  "If the trial to get the internal interface id 
		   fails it means the NFAS  interface is not properly 
		   defined.
SEVERITY-DEFAULT: Warning 
EVENTTYPE-DEFAULT: 10 
ADDITIONAL-TEXT-VARIABLES: { accTrapLogSeqNum,accIsdnTrapMsg }
PCAUSE-DEFAULT: 7 " 
 
                ::= 25
        accIsdnInvSpidTrap TRAP-TYPE
                ENTERPRISE   accIsdnTraps 
                VARIABLES  { accIsdnTrapMsg ,
                              accTrapLogSeqNum}
                DESCRIPTION
                  "While getting the SPID tries to find the port. In 
		   the process if the port is not found and a corresponding  
		   PP index is not found then this trap is generated.
SEVERITY-DEFAULT: Warning 
EVENTTYPE-DEFAULT: 10 
ADDITIONAL-TEXT-VARIABLES: { accTrapLogSeqNum,accIsdnTrapMsg }
PCAUSE-DEFAULT: 7 " 
 
                ::= 26
        accIsdnSwBldTrap TRAP-TYPE
                ENTERPRISE   accIsdnTraps 
                VARIABLES  { accIsdnTrapMsg ,
                              accTrapLogSeqNum}
                DESCRIPTION
                  "While getting the SPID, it comapres the interface flag 
		   and if there is  a match, it triggers a config error, 
		   and hence the trap saying conflicting SPIDs.
SEVERITY-DEFAULT: Warning 
EVENTTYPE-DEFAULT: 10 
ADDITIONAL-TEXT-VARIABLES: { accTrapLogSeqNum,accIsdnTrapMsg }
PCAUSE-DEFAULT: 7 " 
 
                ::= 27
        accIsdnParametersTrap TRAP-TYPE
                ENTERPRISE   accIsdnTraps 
                VARIABLES  { accIsdnTrapMsg ,
                              accTrapLogSeqNum}
                DESCRIPTION
                  "If the SPID is too lengthy which is not supported 
		   then this trap is generated.
SEVERITY-DEFAULT: Warning 
EVENTTYPE-DEFAULT: 10 
ADDITIONAL-TEXT-VARIABLES: { accTrapLogSeqNum,accIsdnTrapMsg }
PCAUSE-DEFAULT: 7 " 
 
                ::= 28 
        accIsdnSwitchTypeTrap TRAP-TYPE
                ENTERPRISE   accIsdnTraps 
                VARIABLES  { accIsdnTrapMsg ,
                              accTrapLogSeqNum}
                DESCRIPTION
                  "Determines whether or not operating as the network 
		   side (NT) or user side (TE) and records this in the 
		   DSL entry. And generates a trap if the hardware 
		   configuration is not consistent with the software 
		   system build (Telenetworks requires USER vs. NETWORK 
		   to be bound at compile-time).
SEVERITY-DEFAULT: Warning 
EVENTTYPE-DEFAULT: 10 
ADDITIONAL-TEXT-VARIABLES: { accTrapLogSeqNum,accIsdnTrapMsg }
PCAUSE-DEFAULT: 7 " 
 
                ::= 29
        accIsdnManyIntfTrap TRAP-TYPE
                ENTERPRISE   accIsdnTraps 
                VARIABLES  { accIsdnTrapMsg ,
                              accTrapLogSeqNum}
                DESCRIPTION
                  "While initialzing the ISDN parameters, it validates 
		   from the NVM. While doing so if a error is encountered 
		   this config error trap is sent.
SEVERITY-DEFAULT: Warning 
EVENTTYPE-DEFAULT: 10 
ADDITIONAL-TEXT-VARIABLES: { accTrapLogSeqNum,accIsdnTrapMsg }
PCAUSE-DEFAULT: 7 " 
 
                ::= 30
        accIsdnPriGroupRangeTrap TRAP-TYPE
                ENTERPRISE   accIsdnTraps 
                VARIABLES  { accIsdnTrapMsg ,
                              accTrapLogSeqNum}
                DESCRIPTION
                  "Tries to make sure the switch type configured for 
		   the subscriber entry has been included in the system 
		   build. If not, generates this trap and proceeds as 
		   if the entry had been disabled. Also, makes sure the 
		   switch type is consistent with the installed interface.
SEVERITY-DEFAULT: Warning 
EVENTTYPE-DEFAULT: 10 
ADDITIONAL-TEXT-VARIABLES: { accTrapLogSeqNum,accIsdnTrapMsg }
PCAUSE-DEFAULT: 7 " 
 
                ::= 31
        accIsdnNfasIntfPriTrap TRAP-TYPE
                ENTERPRISE   accIsdnTraps 
                VARIABLES  { accIsdnTrapMsg ,
                              accTrapLogSeqNum}
                DESCRIPTION
                  "The maximum number of DSL entries is limited at 
		   compile time by the Telenetworks code. When it 
		   exceeds this this trap is  generated.
SEVERITY-DEFAULT: Warning 
EVENTTYPE-DEFAULT: 10 
ADDITIONAL-TEXT-VARIABLES: { accTrapLogSeqNum,accIsdnTrapMsg }
PCAUSE-DEFAULT: 7 " 
 
                ::= 32
        accIsdnManyNFASIntfTrap TRAP-TYPE
                ENTERPRISE   accIsdnTraps 
                VARIABLES  { accIsdnTrapMsg ,
                              accTrapLogSeqNum}
                DESCRIPTION
                  "If during initialization a invalid group is encountered 
		   as it is out of the range, then this trap is generated.
SEVERITY-DEFAULT: Warning 
EVENTTYPE-DEFAULT: 10 
ADDITIONAL-TEXT-VARIABLES: { accTrapLogSeqNum,accIsdnTrapMsg }
PCAUSE-DEFAULT: 7 " 
 
                ::= 33
        accIsdnPriGroupTrap TRAP-TYPE
                ENTERPRISE   accIsdnTraps 
                VARIABLES  { accIsdnTrapMsg ,
                              accTrapLogSeqNum}
                DESCRIPTION
                  "Looks for interfaces in PRI group 0. If the interface 
		   has a signaling channel, it is assumed to be a 
		   stand-alone interface. Otherwise, it is a 
		   orphan (i.e., misconfigured) NFAS interface, hence 
		   generates the trap.
SEVERITY-DEFAULT: Warning 
EVENTTYPE-DEFAULT: 10 
ADDITIONAL-TEXT-VARIABLES: { accTrapLogSeqNum,accIsdnTrapMsg }
PCAUSE-DEFAULT: 7 " 
 
                ::= 34
        accIsdnTrap35 TRAP-TYPE
                ENTERPRISE   accIsdnTraps 
                VARIABLES  { accIsdnTrapMsg ,
                              accTrapLogSeqNum}
                DESCRIPTION
                  "In the event of making sure the PRI group has a 
		   primary signaling interface and that the group can 
		   accommodate an additional NFAS interface, if the 
		   new pri id or secondary new id exceed the maximum 
		   interface id, this trap is generated.
SEVERITY-DEFAULT: Warning 
EVENTTYPE-DEFAULT: 10 
ADDITIONAL-TEXT-VARIABLES: { accTrapLogSeqNum,accIsdnTrapMsg }
PCAUSE-DEFAULT: 7 " 
 
                ::= 35
        accIsdnNoSrvcProIFTrap TRAP-TYPE
                ENTERPRISE   accIsdnTraps 
                VARIABLES  { accIsdnTrapMsg ,
                              accTrapLogSeqNum}
                DESCRIPTION
                  " No service profile identifier
SEVERITY-DEFAULT: Warning 
EVENTTYPE-DEFAULT: 10 
ADDITIONAL-TEXT-VARIABLES: { accTrapLogSeqNum,accIsdnTrapMsg }
PCAUSE-DEFAULT: 7 " 
 
                ::= 36
        accIsdnNTBldIncmptblHWTrap TRAP-TYPE
                ENTERPRISE   accIsdnTraps 
                VARIABLES  { accIsdnTrapMsg ,
                              accTrapLogSeqNum}
                DESCRIPTION
                  " Software NT build is incompatible with harware TE mode
SEVERITY-DEFAULT: Warning 
EVENTTYPE-DEFAULT: 10 
ADDITIONAL-TEXT-VARIABLES: { accTrapLogSeqNum,accIsdnTrapMsg }
PCAUSE-DEFAULT: 7 " 
 
                ::= 37
        accIsdnRcvdSpidTrap TRAP-TYPE
                ENTERPRISE   accIsdnTraps 
                VARIABLES  { accIsdnTrapMsg, accIsdnSpidValue ,
                              accTrapLogSeqNum}
                DESCRIPTION
                  " Received one spid 
SEVERITY-DEFAULT: Warning 
EVENTTYPE-DEFAULT: 10 
ADDITIONAL-TEXT-VARIABLES: { accTrapLogSeqNum,accIsdnTrapMsg }
PCAUSE-DEFAULT: 7 " 
 
                ::= 38
        accIsdnRcvdSpidsNWTrap TRAP-TYPE
                ENTERPRISE   accIsdnTraps 
                VARIABLES  { accIsdnTrapMsg, accIsdnSpidValue ,
                              accTrapLogSeqNum}
                DESCRIPTION
                  "Received spids from network 
SEVERITY-DEFAULT: Warning 
EVENTTYPE-DEFAULT: 10 
ADDITIONAL-TEXT-VARIABLES: { accTrapLogSeqNum,accIsdnTrapMsg }
PCAUSE-DEFAULT: 7 " 
 
                ::= 39
        accIsdnAutoSpidFldTrap TRAP-TYPE
                ENTERPRISE   accIsdnTraps 
                VARIABLES  { accIsdnTrapMsg ,
                              accTrapLogSeqNum}
                DESCRIPTION
                  "Auto spid failed (found %d suitable SPID(s))
SEVERITY-DEFAULT: Warning 
EVENTTYPE-DEFAULT: 10 
ADDITIONAL-TEXT-VARIABLES: { accTrapLogSeqNum,accIsdnTrapMsg }
PCAUSE-DEFAULT: 7 " 
 
                ::= 40
        accIsdnAutoSpidSccdTrap TRAP-TYPE
                ENTERPRISE   accIsdnTraps 
                VARIABLES  { accIsdnTrapMsg ,
                              accTrapLogSeqNum}
                DESCRIPTION
                  "Auto spid succeeded 
SEVERITY-DEFAULT: Warning 
EVENTTYPE-DEFAULT: 10 
ADDITIONAL-TEXT-VARIABLES: { accTrapLogSeqNum,accIsdnTrapMsg }
PCAUSE-DEFAULT: 7 " 
 
                ::= 41
        accIsdnAutoSpidFld1Trap TRAP-TYPE
                ENTERPRISE   accIsdnTraps 
                VARIABLES  { accIsdnTrapMsg ,
                              accTrapLogSeqNum}
                DESCRIPTION
                  "Auto spid failed (cause = %d) 
SEVERITY-DEFAULT: Warning 
EVENTTYPE-DEFAULT: 10 
ADDITIONAL-TEXT-VARIABLES: { accTrapLogSeqNum,accIsdnTrapMsg }
PCAUSE-DEFAULT: 7 " 
 
                ::= 42
        accIsdnAutoSwtchSccdTrap TRAP-TYPE
                ENTERPRISE   accIsdnTraps 
                VARIABLES  { accIsdnTrapMsg ,
                              accTrapLogSeqNum}
                DESCRIPTION
                  "Auto switch detection succeeded 
SEVERITY-DEFAULT: Warning 
EVENTTYPE-DEFAULT: 10 
ADDITIONAL-TEXT-VARIABLES: { accTrapLogSeqNum,accIsdnTrapMsg }
PCAUSE-DEFAULT: 7 " 
 
                ::= 43
        accIsdnAutoSwtchFldTrap TRAP-TYPE
                ENTERPRISE   accIsdnTraps 
                VARIABLES  { accIsdnTrapMsg ,
                              accTrapLogSeqNum}
                DESCRIPTION
                  "Auto switch detection failed (unspecified switch type) 
SEVERITY-DEFAULT: Warning 
EVENTTYPE-DEFAULT: 10 
ADDITIONAL-TEXT-VARIABLES: { accTrapLogSeqNum,accIsdnTrapMsg }
PCAUSE-DEFAULT: 7 " 
 
                ::= 44
        accIsdnAutoSwtchFld1Trap TRAP-TYPE
                ENTERPRISE   accIsdnTraps 
                VARIABLES  { accIsdnTrapMsg ,
                              accTrapLogSeqNum}
                DESCRIPTION
                  "Auto switch detection failed 
SEVERITY-DEFAULT: Warning 
EVENTTYPE-DEFAULT: 10 
ADDITIONAL-TEXT-VARIABLES: { accTrapLogSeqNum,accIsdnTrapMsg }
PCAUSE-DEFAULT: 7 " 
 
                ::= 45
END
