PDN-MPE-ARP-MIB DEFINITIONS ::= BEGIN

-- Version :  0.1 DRAFT
-- Enterprise pdn ARP mib (mpe support)
-- Copyright (C) 2000 Paradyne Corporation.

-- Created by : Wayne Jadoo / Prakash Easwar

-- This MIB contains objects that is used configure
-- ARP Entries and display ARP information on a Device

IMPORTS
SwitchState,
VnidRange
FROM PDN-TC
MacAddress, TruthValue,
RowStatus
FROM SNMPv2-TC
OBJECT-TYPE
FROM RFC-1212
IpAddress
FROM RFC1155-SMI
entPhysicalIndex
FROM ENTITY-MIB
mpe-arp
FROM PDN-HEADER-MIB
;


-- Bit32 is temporarily defined here to get mpe_Arp.mib to compile.
-- A textual convention is being defined for bit32, but needs 
-- to be approved by the mibwg. Until this has been completed
-- a temporary defintion is used here in order to get this mib
-- to compile to be proposed.

Bit32 ::= INTEGER 

mpePdnNetToMediaGenericMIBObjects  OBJECT IDENTIFIER ::= { mpe-arp 1 }
mpePdnNetToMediaMIBTraps OBJECT IDENTIFIER ::= { mpe-arp 2 }
mpePdnNetTo8023MediaParams OBJECT IDENTIFIER ::= { mpePdnNetToMediaGenericMIBObjects 1 }
mpePdnNetTo8023MediaConfig OBJECT IDENTIFIER ::= { mpePdnNetToMediaGenericMIBObjects 2 }


-- The ARP Parameters Configuration Table 802.3 media cards.

          mpePdnNetTo8023MediaParamsTable OBJECT-TYPE
              SYNTAX  SEQUENCE OF MpePdnNetTo8023MediaParamsEntry
              ACCESS  not-accessible
              STATUS  mandatory
              DESCRIPTION
                "A table that contains ARP Parameters  configuration information ."
              ::= { mpePdnNetTo8023MediaParams 1 }

          mpePdnNetTo8023MediaParamsEntry OBJECT-TYPE
              SYNTAX  MpePdnNetTo8023MediaParamsEntry
              ACCESS  not-accessible
              STATUS  mandatory
              DESCRIPTION
                      "A list of information about ARP Parameters."
              INDEX  { entPhysicalIndex }
              ::= { mpePdnNetTo8023MediaParamsTable 1 }


          MpePdnNetTo8023MediaParamsEntry ::=
              SEQUENCE {
                mpePdnNetTo8023MediaParamsCompEntryTimeout        INTEGER,
                mpePdnNetTo8023MediaParamsIncompEntryTimeout      INTEGER,
                mpePdnNetTo8023MediaParamsDefRouteEntryTimeout    INTEGER
              }

          mpePdnNetTo8023MediaParamsCompEntryTimeout OBJECT-TYPE
              SYNTAX  INTEGER
              ACCESS  read-write
              STATUS  mandatory
              DESCRIPTION
                      " Complete Entry Timeout is the length of time that 
                        a complete entry remains in the ARP table before 
                        removal.  A complete entry is one for which there is 
                        a MAC address -- i.e. a node has responded to the
                        ARP request. If an entry gets this old without being 
                        referenced, it will be removed from the table.  The 
                        range for this parameter is 1  to 200000 minutes."
              DEFVAL { 20 }
              ::= { mpePdnNetTo8023MediaParamsEntry 1 }

          mpePdnNetTo8023MediaParamsIncompEntryTimeout OBJECT-TYPE
              SYNTAX   INTEGER 
              ACCESS   read-write
              STATUS   mandatory
              DESCRIPTION
                      " Incomplete Entry Timeout is the length of time that 
                        an incomplete entry remains in the ARP table before 
                        removal. An incomplete entry is one for which there 
                        is no MAC address -- i.e. an ARP request has been made,
                        but no response has been received. This is also the 
                        amount of time that a packet will remain in the system 
                        while waiting for address resolution. The range 
                        for this parameter is  1 to  255  minutes."
              DEFVAL { 3 }
              ::= { mpePdnNetTo8023MediaParamsEntry 2 }
        
          mpePdnNetTo8023MediaParamsDefRouteEntryTimeout OBJECT-TYPE
              SYNTAX   INTEGER 
              ACCESS   read-write
              STATUS   mandatory
              DESCRIPTION
                      "Default Route Entry Timeout is the length of time 
                       a default route entry will remain in the ARP table. 
                       If default route gets this old without being referenced,
                       an ARP request will be sent to the next hop router.
                       If no response is received, it will be removed from 
                       the ARP table and the card will switch to the next 
                       reachable default route with the highest preference. 
                       The range for this parameter is 1  to  20  minutes."
              DEFVAL { 1 }
              ::= { mpePdnNetTo8023MediaParamsEntry 3 }

          END
