Wellfleet-TI-RUI-MIB DEFINITIONS ::= BEGIN

-- Created by mdl2asn version 3.1
-- Creation date: Wed Aug 30 16:49:32 EDT 1995


    IMPORTS

      Counter
        FROM RFC1155-SMI
      OBJECT-TYPE
        FROM RFC-1212
      DisplayString
        FROM RFC1213-MIB
      wfServices
        FROM Wellfleet-COMMON-MIB;


    wfTiRui		OBJECT IDENTIFIER ::= { wfServices 2 }

    wfTiRuiState OBJECT-TYPE
        SYNTAX	INTEGER {
    		    idle(1),
    		    busy(2)
    		}
        ACCESS	read-only
        STATUS	mandatory
        DESCRIPTION
                "The state of the ti rui command processor. Idle is normal state. Busy
                indicates a command is being processed. "
        DEFVAL	{ idle }
        ::= { wfTiRui 1 }

    wfTiRuiAction OBJECT-TYPE
        SYNTAX	DisplayString
        ACCESS	read-write
        STATUS	mandatory
        DESCRIPTION
                "Ti command request string"
        ::= { wfTiRui 2 }

    wfTiRuiResult OBJECT-TYPE
        SYNTAX	DisplayString
        ACCESS	read-only
        STATUS	mandatory
        DESCRIPTION
                "The result of the Ti command requst"
        ::= { wfTiRui 3 }

    wfTiRuiInReqs OBJECT-TYPE
        SYNTAX	Counter
        ACCESS	read-only
        STATUS	mandatory
        DESCRIPTION
                "Total number of command requests"
        ::= { wfTiRui 4 }

    wfTiRuiOutResults OBJECT-TYPE
        SYNTAX	Counter
        ACCESS	read-only
        STATUS	mandatory
        DESCRIPTION
                "Total number of command requests that processed without error"
        ::= { wfTiRui 5 }

    wfTiRuiOutResultsErr OBJECT-TYPE
        SYNTAX	Counter
        ACCESS	read-only
        STATUS	mandatory
        DESCRIPTION
                "Total number of command requests that could not be processed because of
                errors "
        ::= { wfTiRui 6 }

    END  -- Wellfleet-TI-RUI-MIB
