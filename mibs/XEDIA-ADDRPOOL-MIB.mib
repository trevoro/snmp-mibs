XEDIA-ADDRPOOL-MIB DEFINITIONS ::= BEGIN

IMPORTS 
    MODULE-IDENTITY, OBJECT-TYPE, IpAddress
        FROM SNMPv2-SMI
    TEXTUAL-CONVENTION, DisplayString, RowStatus        
        FROM SNMPv2-TC
    MODULE-COMPLIANCE, OBJECT-GROUP
        FROM SNMPv2-CONF
    xediaMibs
        FROM XEDIA-REG
    ;

xediaAddrPoolMIB MODULE-IDENTITY
    LAST-UPDATED "0001272155Z" -- January 27, 2000
    ORGANIZATION "Xedia Corp."
    CONTACT-INFO
        "support@xedia.com"
    DESCRIPTION
        "This module defines objects for management of Xedia's IP
        Address Pool."
    ::= { xediaMibs 43 }


-- ****************************************************************
-- Top-level organization of the MIB
-- ****************************************************************

addrPoolObjects          OBJECT IDENTIFIER ::= { xediaAddrPoolMIB 1 }
addrPoolConformance      OBJECT IDENTIFIER ::= { xediaAddrPoolMIB 2 }

-- ****************************************************************
-- Object Definitions
-- ****************************************************************

-- The Address Pool Configuration Table
--    show ip.x address-pool-configs
--    show ip.x address-pool-config.xxxx
--    config ip.x address-pool.xxxx

addrPoolConfigTable   OBJECT-TYPE
    SYNTAX          SEQUENCE OF AddrPoolConfigEntry
    MAX-ACCESS      not-accessible
    STATUS          current
    DESCRIPTION
       "The Addr Pool configuration table."
    ::= { addrPoolObjects 1 }

addrPoolConfigEntry   OBJECT-TYPE
    SYNTAX          AddrPoolConfigEntry
    MAX-ACCESS      not-accessible
    STATUS          current
    DESCRIPTION
       "An Addr Pool configuration entry. An entry in this
        table corresponds to a pool of ip addresses."
    INDEX { addrPoolConfigIdentifier }
    ::= { addrPoolConfigTable 1 }

AddrPoolConfigEntry ::=
    SEQUENCE {
        addrPoolConfigIdentifier
            DisplayString,
        addrPoolConfigNetwork
            IpAddress,
        addrPoolConfigMask
            IpAddress,
        addrPoolConfigRowStatus
            RowStatus
    }

addrPoolConfigIdentifier  OBJECT-TYPE
    SYNTAX          DisplayString (SIZE (1..64))
    MAX-ACCESS      not-accessible
    STATUS          current
    DESCRIPTION
       "The identifier is a domain name which can be matched against
        the user domain as received in the PPP user authentication
        information. For example if a local PPP layer was connected to
        a downlink of this Layer 2 Dial layer, and it's remote PPP peer
        requested that an address be assigned to it, the local PPP could
        request this address from the Layer 2 Dial layer, which would
        allocate it from a subnet defined in this table."
    ::= { addrPoolConfigEntry 1 }

addrPoolConfigNetwork OBJECT-TYPE
    SYNTAX      IpAddress
    MAX-ACCESS  read-create
    STATUS      current
    DESCRIPTION
        "Network from which ip addresses can be allocated and assigned
        to remote PPP peers."
    DEFVAL      { 0 }
    ::= { addrPoolConfigEntry 2 }

addrPoolConfigMask OBJECT-TYPE
    SYNTAX      IpAddress
    MAX-ACCESS  read-create
    STATUS      current
    DESCRIPTION
        "The subnet mask for addrPoolConfigNetwork"
    DEFVAL      { 0 }
    ::= { addrPoolConfigEntry 3 }

addrPoolConfigRowStatus  OBJECT-TYPE
    SYNTAX          RowStatus
    MAX-ACCESS      read-create
    STATUS          current
    DESCRIPTION
       "The status of this Pool entry."
    ::= { addrPoolConfigEntry 4 }


-- The Addr Address Pool Allocation Table
--    show ip.x address-pool-allocations
--    show ip.x address-pool-allocation.xxxx

addrPoolAllocationTable   OBJECT-TYPE
    SYNTAX          SEQUENCE OF AddrPoolAllocationEntry
    MAX-ACCESS      not-accessible
    STATUS          current
    DESCRIPTION
       "The Addr Pool allocation table."
    ::= { addrPoolObjects 2 }

addrPoolAllocationEntry   OBJECT-TYPE
    SYNTAX          AddrPoolAllocationEntry
    MAX-ACCESS      not-accessible
    STATUS          current
    DESCRIPTION
       "An Addr Pool allocation entry. An entry in this
        table corresponds to a pool of ip addresses."
    INDEX { addrPoolAllocationNameIdentifier, addrPoolAllocationIpAddress }
    ::= { addrPoolAllocationTable 1 }

AddrPoolAllocationEntry ::=
    SEQUENCE {
        addrPoolAllocationNameIdentifier
            DisplayString,
        addrPoolAllocationIpAddress
            IpAddress,
        addrPoolAllocationUserLayer
            DisplayString,
        addrPoolAllocationRemoteUser
            DisplayString
    }

addrPoolAllocationNameIdentifier  OBJECT-TYPE
    SYNTAX          DisplayString (SIZE (1..64))
    MAX-ACCESS      not-accessible
    STATUS          current
    DESCRIPTION
       "The identifier is a domain name."
    ::= { addrPoolAllocationEntry 1 }

addrPoolAllocationIpAddress  OBJECT-TYPE
    SYNTAX          IpAddress
    MAX-ACCESS      not-accessible
    STATUS          current
    DESCRIPTION
       "An ip address allocated from this address pool."
    ::= { addrPoolAllocationEntry 2 }

addrPoolAllocationUserLayer  OBJECT-TYPE
    SYNTAX          DisplayString
    MAX-ACCESS      read-only
    STATUS          current
    DESCRIPTION
       "The name of the local connected layer to which the address was
        allocated."
    ::= { addrPoolAllocationEntry 3 }

addrPoolAllocationRemoteUser  OBJECT-TYPE
    SYNTAX          DisplayString
    MAX-ACCESS      read-only
    STATUS          current
    DESCRIPTION
       "The name of the remote user to which the address was
        allocated."
    ::= { addrPoolAllocationEntry 4 }

-- ****************************************************************
-- Conformance Statements
-- ****************************************************************

addrPoolCompliances OBJECT IDENTIFIER ::= { addrPoolConformance 1 }
addrPoolGroups      OBJECT IDENTIFIER ::= { addrPoolConformance 2 }

--
-- Compliance Statements
--

addrPoolCompliance MODULE-COMPLIANCE
    STATUS      current
    DESCRIPTION
        "The compliance statement for all agents that support this
        MIB. A compliant agent implements all objects defined in this
        MIB."
    MODULE  -- this module
    MANDATORY-GROUPS {
        addrPoolConfigGroup,
        addrPoolAllocationGroup
    }
    ::= { addrPoolCompliances 1 }

--
-- Object Groups
--

addrPoolConfigGroup OBJECT-GROUP
    OBJECTS {
--        addrPoolConfigIdentifier,
        addrPoolConfigNetwork,
        addrPoolConfigMask
    }
    STATUS      current
    DESCRIPTION
        "A collection of objects providing configuration of address pools."
    ::= { addrPoolGroups 1 }

addrPoolAllocationGroup OBJECT-GROUP
    OBJECTS {
--        addrPoolAllocationNameIdentifier,
--        addrPoolAllocationIpAddress,
        addrPoolAllocationUserLayer,
        addrPoolAllocationRemoteUser
    }
    STATUS      current
    DESCRIPTION
        "A collection of objects providing status of address pools."
    ::= { addrPoolGroups 2 }

END
