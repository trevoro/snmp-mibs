Nortel-MsCarrier-MscPassport-ExternalTimingE1MIB
DEFINITIONS ::= BEGIN



IMPORTS

      OBJECT-TYPE
   FROM RFC-1212

      mscPassportMIBs
   FROM Nortel-MsCarrier-MscPassport-UsefulDefinitionsMIB

      DisplayString,
      StorageType,
      RowStatus,
      Integer32
   FROM Nortel-MsCarrier-MscPassport-StandardTextualConventionsMIB

      mscLpIndex,
      mscLp
   FROM Nortel-MsCarrier-MscPassport-LogicalProcessorMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     ExternalTimingE1 Enterprise MIB."

externalTimingE1MIB OBJECT IDENTIFIER ::= { mscPassportMIBs 152 }










-- Lp/0 EE1/n
-- The EE1 component controls an E1 external timing port on a CPeE 
-- Control Processor. The EE1 component can be added only under 
-- LP/0 and only if CP type is CPeE. The CPeE Control Processor 
-- supports up to two external timing ports.

mscLpEE1 OBJECT IDENTIFIER ::= { mscLp 29 }



mscLpEE1RowStatusTable OBJECT-TYPE
   SYNTAX     SEQUENCE OF MscLpEE1RowStatusEntry
   ACCESS     not-accessible
   STATUS     mandatory
   DESCRIPTION
     "This entry controls the addition and deletion of 
      mscLpEE1 components."
::= { mscLpEE1 1 }

mscLpEE1RowStatusEntry OBJECT-TYPE
   SYNTAX     MscLpEE1RowStatusEntry
   ACCESS     not-accessible
   STATUS     mandatory
   DESCRIPTION
     "A single entry in the table represents a single 
      mscLpEE1 component."
   INDEX {
      mscLpIndex,
      mscLpEE1Index }
::= { mscLpEE1RowStatusTable 1 }

MscLpEE1RowStatusEntry ::= SEQUENCE {
   mscLpEE1RowStatus
      RowStatus,
   mscLpEE1ComponentName
      DisplayString,
   mscLpEE1StorageType
      StorageType,
   mscLpEE1Index
      Integer32 }

mscLpEE1RowStatus OBJECT-TYPE
   SYNTAX     RowStatus 
   ACCESS     read-write
   STATUS     mandatory
   DESCRIPTION
     "This variable is used as the basis for SNMP naming of
      mscLpEE1 components.
      These components can be added and deleted."
::= { mscLpEE1RowStatusEntry 1 }

mscLpEE1ComponentName OBJECT-TYPE
   SYNTAX     DisplayString 
   ACCESS     read-only
   STATUS     mandatory
   DESCRIPTION
     "This variable provides the component's string name for
      use with the ASCII Console Interface"
::= { mscLpEE1RowStatusEntry 2 }

mscLpEE1StorageType OBJECT-TYPE
   SYNTAX     StorageType 
   ACCESS     read-only
   STATUS     mandatory
   DESCRIPTION
     "This variable represents the storage type value for the
      mscLpEE1 tables."
::= { mscLpEE1RowStatusEntry 4 }

mscLpEE1Index OBJECT-TYPE
   SYNTAX     Integer32 (0..1)
   ACCESS     not-accessible
   STATUS     mandatory
   DESCRIPTION
     "This variable represents the index for the mscLpEE1 tables."
::= { mscLpEE1RowStatusEntry 10 }

mscLpEE1OperStatusTable OBJECT-TYPE
   SYNTAX     SEQUENCE OF MscLpEE1OperStatusEntry
   ACCESS     not-accessible
   STATUS     mandatory
   DESCRIPTION
     "This group includes the Operational Status attribute. This attribute 
      defines the current operational state of this component."
::= { mscLpEE1 14 }

mscLpEE1OperStatusEntry OBJECT-TYPE
   SYNTAX     MscLpEE1OperStatusEntry
   ACCESS     not-accessible
   STATUS     mandatory
   DESCRIPTION
     "An entry in the mscLpEE1OperStatusTable."
   INDEX {
      mscLpIndex,
      mscLpEE1Index }
::= { mscLpEE1OperStatusTable 1 }

MscLpEE1OperStatusEntry ::= SEQUENCE {
   mscLpEE1SnmpOperStatus
      INTEGER }

mscLpEE1SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpEE1OperStatusEntry 1 }

mscLpEE1StateTable OBJECT-TYPE
   SYNTAX     SEQUENCE OF MscLpEE1StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscLpEE1 15 }

mscLpEE1StateEntry OBJECT-TYPE
   SYNTAX     MscLpEE1StateEntry
   ACCESS     not-accessible
   STATUS     mandatory
   DESCRIPTION
     "An entry in the mscLpEE1StateTable."
   INDEX {
      mscLpIndex,
      mscLpEE1Index }
::= { mscLpEE1StateTable 1 }

MscLpEE1StateEntry ::= SEQUENCE {
   mscLpEE1AdminState
      INTEGER,
   mscLpEE1OperationalState
      INTEGER,
   mscLpEE1UsageState
      INTEGER,
   mscLpEE1AvailabilityStatus
      OCTET STRING,
   mscLpEE1ProceduralStatus
      OCTET STRING,
   mscLpEE1ControlStatus
      OCTET STRING,
   mscLpEE1AlarmStatus
      OCTET STRING,
   mscLpEE1StandbyStatus
      INTEGER,
   mscLpEE1UnknownStatus
      INTEGER }

mscLpEE1AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscLpEE1StateEntry 1 }

mscLpEE1OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscLpEE1StateEntry 2 }

mscLpEE1UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscLpEE1StateEntry 3 }

mscLpEE1AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscLpEE1StateEntry 4 }

mscLpEE1ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscLpEE1StateEntry 5 }

mscLpEE1ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscLpEE1StateEntry 6 }

mscLpEE1AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscLpEE1StateEntry 7 }

mscLpEE1StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscLpEE1StateEntry 8 }

mscLpEE1UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscLpEE1StateEntry 9 }

mscLpEE1OperTable OBJECT-TYPE
   SYNTAX     SEQUENCE OF MscLpEE1OperEntry
   ACCESS     not-accessible
   STATUS     mandatory
   DESCRIPTION
     "This group contains the common operational data for EE1 and 
      EDS1 components."
::= { mscLpEE1 16 }

mscLpEE1OperEntry OBJECT-TYPE
   SYNTAX     MscLpEE1OperEntry
   ACCESS     not-accessible
   STATUS     mandatory
   DESCRIPTION
     "An entry in the mscLpEE1OperTable."
   INDEX {
      mscLpIndex,
      mscLpEE1Index }
::= { mscLpEE1OperTable 1 }

MscLpEE1OperEntry ::= SEQUENCE {
   mscLpEE1LosAlarm
      INTEGER,
   mscLpEE1LofAlarm
      INTEGER,
   mscLpEE1RxAisAlarm
      INTEGER }

mscLpEE1LosAlarm OBJECT-TYPE
   SYNTAX     INTEGER  {
                 on(0),
                 off(1) }
   ACCESS     read-only
   STATUS     mandatory
   DESCRIPTION
     "This attribute indicates whether a LOS (Loss of Signal) alarm state 
      has been entered. A LOS alarm is declared after LOS defects have 
      been observed and accumulated for a period of 2 seconds +/- 0.5 
      second . A LOS defect is detected upon observing all zeros for 150 
      ms . If the LOS defects are intermittently occurring, the LOS defect 
      accumulator is decremented at a rate of 1/10 of the incrementing 
      rate (alarm integration ratio of 1/10), with all measurements based 
      on a 200 ms polling cycle.
      The port goes into an operational state of disabled until the LOS 
      alarm state is cleared. The LOS alarm state is cleared when LOS 
      defects are absent for 10 seconds +/- 0.5 second."
   DEFVAL     { off }
::= { mscLpEE1OperEntry 1 }

mscLpEE1LofAlarm OBJECT-TYPE
   SYNTAX     INTEGER  {
                 on(0),
                 off(1) }
   ACCESS     read-only
   STATUS     mandatory
   DESCRIPTION
     "This attribute indicates whether a LOF (Loss of Frame) alarm state 
      has been entered. The LOF alarm state is entered when LOF defects 
      (for DS1: 2 out of 5 framing bits in error; for E1: 3 consecutive 
      frame alignment patterns in error) have been detected for 3 seconds 
      +/- 0.5 second . If the LOF defects are intermittently occurring, the 
      LOF defect accumulator is decremented at a rate of 1/10 of the 
      incrementing rate (alarm integration ratio of 1/10), with all 
      measurements based on a 200 ms polling cycle.
      The port goes into an operational state of disabled until the LOF 
      alarm state is cleared. The condition is cleared when framing has 
      been achieved for 10 seconds +/- 0.5 second."
   DEFVAL     { off }
::= { mscLpEE1OperEntry 2 }

mscLpEE1RxAisAlarm OBJECT-TYPE
   SYNTAX     INTEGER  {
                 on(0),
                 off(1) }
   ACCESS     read-only
   STATUS     mandatory
   DESCRIPTION
     "This attribute indicates whether an AIS (Alarm Indication Signal) 
      alarm has been entered. The AIS Alarm state is entered when AIS 
      defects have been observed and accumulated for 2.5 seconds +/- 0.5 
      second. An AIS defect is detected after having received less than 3 
      zeros in a 2048 bit period. If the AIS defects are intermittently 
      occurring, the AIS defect accumulator is decremented at a rate of 1/
      10 of the incrementing rate (alarm integration ratio of 1/10), with all 
      measurement based on a 200 ms polling cycle. The port goes into 
      an operational state of disabled for the duration of an AIS alarm 
      state. The AIS alarm state is cleared when AIS defects are absent 
      for 10 seconds +/- 0.5 second."
   DEFVAL     { off }
::= { mscLpEE1OperEntry 3 }




-- 
-- Version and Compliance statements
-- 



-- Object-Group Statement:
-- A list of all current accessible leaf objects.

-- OBJECTS { mscLpEE1ProceduralStatus,
--           mscLpEE1UnknownStatus,
--           mscLpEE1AvailabilityStatus,
--           mscLpEE1OperationalState,
--           mscLpEE1LofAlarm,
--           mscLpEE1SnmpOperStatus,
--           mscLpEE1AlarmStatus,
--           mscLpEE1UsageState,
--           mscLpEE1LosAlarm,
--           mscLpEE1ControlStatus,
--           mscLpEE1AdminState,
--           mscLpEE1ComponentName,
--           mscLpEE1StandbyStatus,
--           mscLpEE1RxAisAlarm,
--           mscLpEE1StorageType,
--           mscLpEE1RowStatus }
-- STATUS  mandatory
-- DESCRIPTION
--   "A list of all current accessible leaf objects."

externalTimingE1Group OBJECT IDENTIFIER ::= { externalTimingE1MIB 1 }
externalTimingE1GroupCA OBJECT IDENTIFIER ::= { externalTimingE1Group 1 }
externalTimingE1GroupCA02 OBJECT IDENTIFIER ::= { externalTimingE1GroupCA 3 }
externalTimingE1GroupCA02A OBJECT IDENTIFIER ::= { externalTimingE1GroupCA02 2 }



-- Agent-Capabilities Statement:

-- PRODUCT-RELEASE "MscPassport Release 1.2 ExternalTimingE1."
-- STATUS          mandatory
-- DESCRIPTION     "Carrier Passport ExternalTimingE1 MIB: MIB Version CA02A,
--                  Software Version CA02S9C."
-- SUPPORTS        Nortel-MsCarrier-MscPassport-ExternalTimingE1MIB
--    INCLUDES     { externalTimingE1GroupCA02A }

externalTimingE1Capabilities OBJECT IDENTIFIER ::= { externalTimingE1MIB 3 }
externalTimingE1CapabilitiesCA OBJECT IDENTIFIER ::= { externalTimingE1Capabilities 1 }
externalTimingE1CapabilitiesCA02 OBJECT IDENTIFIER ::= { externalTimingE1CapabilitiesCA 3 }
externalTimingE1CapabilitiesCA02A OBJECT IDENTIFIER ::= { externalTimingE1CapabilitiesCA02 2 }





END
