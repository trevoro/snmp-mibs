--
-- Juniper Enterprise Specific Chassis Traps for SNMP V1
--
-- Copyright (c) 1998-2000, Juniper Networks, Inc.
-- All rights reserved.
--
-- The contents of this document are subject to change without notice.
--

JUNIPER-V1-TRAPS-CHAS

DEFINITIONS ::= BEGIN

IMPORTS
    enterprises         FROM RFC1155-SMI
    TRAP-TYPE           FROM RFC-1215;


--  The following chassis objects are from Juniper Chassis MIB

    juniperMIB          OBJECT IDENTIFIER ::= { enterprises 2636 }

    jnxMibs             OBJECT IDENTIFIER ::= { juniperMIB 3 }
    jnxBoxAnatomy       OBJECT IDENTIFIER ::= { jnxMibs 1 }

    jnxContentsTable    OBJECT IDENTIFIER ::= { jnxBoxAnatomy 8 }
    jnxContentsEntry    OBJECT IDENTIFIER ::= { jnxContentsTable 1 }
    jnxContentsContainerIndex
                        OBJECT IDENTIFIER ::= { jnxContentsEntry 1 }
    jnxContentsL1Index  OBJECT IDENTIFIER ::= { jnxContentsEntry 2 }
    jnxContentsL2Index  OBJECT IDENTIFIER ::= { jnxContentsEntry 3 }
    jnxContentsL3Index  OBJECT IDENTIFIER ::= { jnxContentsEntry 4 }
    jnxContentsDescr    OBJECT IDENTIFIER ::= { jnxContentsEntry 6 }
		

--
--  Chassis traps
--

    jnxPowerSupplyFailureV1 TRAP-TYPE
        ENTERPRISE      juniperMIB
        VARIABLES { 
                    jnxContentsContainerIndex,
                    jnxContentsL1Index,
                    jnxContentsL2Index,
                    jnxContentsL3Index,
                    jnxContentsDescr
                  }
        DESCRIPTION
                "A jnxPowerSupplyFailure trap signifies that
                the specified power supply in the chassis has 
                been in the failure (bad DC output) condition."
        ::= 1


    jnxFanFailureV1 TRAP-TYPE
        ENTERPRISE      juniperMIB
        VARIABLES {
                    jnxContentsContainerIndex,
                    jnxContentsL1Index,
                    jnxContentsL2Index,
                    jnxContentsL3Index,
                    jnxContentsDescr
                  }
        DESCRIPTION
                "A jnxFanFailure trap signifies that the specified
                cooling fan or impeller in the chassis has been in
                the failure (not spinning) condition."
        ::= 2


    jnxOverTemperatureV1 TRAP-TYPE
        ENTERPRISE      juniperMIB
        VARIABLES { 
                    jnxContentsContainerIndex,
                    jnxContentsL1Index,
                    jnxContentsL2Index,
                    jnxContentsL3Index,
                    jnxContentsDescr
                  }
        DESCRIPTION
                "A jnxOverTemperature trap signifies that the 
                specified hardware component in the chassis has 
                experienced over temperature condition."
        ::= 3


END
