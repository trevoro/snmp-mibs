Nortel-MsCarrier-MscPassport-LaneClientMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      InterfaceIndex,
      Integer32,
      MacAddress,
      Unsigned32
   FROM Nortel-MsCarrier-MscPassport-StandardTextualConventionsMIB

      AsciiString,
      DashedHexString,
      NonReplicated,
      HexString,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     LaneClient Enterprise MIB."

laneClientMIB OBJECT IDENTIFIER ::= { mscPassportMIBs 71 }










-- LanEmulationClient/n
-- This component represents a LAN Emulation Client (LEC) as 
-- specified in the ATM Forum LAN Emulation over ATM 
-- Specification (LANE). The LEC provides a MAC level emulated 
-- Ethernet service to higher layer protocols using ATM VCCs.
-- 
-- The 'laneClient' feature must be provisioned on all ILS and ATM 
-- cards.

mscLec OBJECT IDENTIFIER ::= { mscComponents 124 }



mscLecRowStatusTable OBJECT-TYPE
   SYNTAX     SEQUENCE OF MscLecRowStatusEntry
   ACCESS     not-accessible
   STATUS     mandatory
   DESCRIPTION
     "This entry controls the addition and deletion of 
      mscLec components."
::= { mscLec 1 }

mscLecRowStatusEntry OBJECT-TYPE
   SYNTAX     MscLecRowStatusEntry
   ACCESS     not-accessible
   STATUS     mandatory
   DESCRIPTION
     "A single entry in the table represents a single 
      mscLec component."
   INDEX {
      mscLecIndex }
::= { mscLecRowStatusTable 1 }

MscLecRowStatusEntry ::= SEQUENCE {
   mscLecRowStatus
      RowStatus,
   mscLecComponentName
      DisplayString,
   mscLecStorageType
      StorageType,
   mscLecIndex
      Integer32 }

mscLecRowStatus OBJECT-TYPE
   SYNTAX     RowStatus 
   ACCESS     read-write
   STATUS     mandatory
   DESCRIPTION
     "This variable is used as the basis for SNMP naming of
      mscLec components.
      These components can be added and deleted."
::= { mscLecRowStatusEntry 1 }

mscLecComponentName OBJECT-TYPE
   SYNTAX     DisplayString 
   ACCESS     read-only
   STATUS     mandatory
   DESCRIPTION
     "This variable provides the component's string name for
      use with the ASCII Console Interface"
::= { mscLecRowStatusEntry 2 }

mscLecStorageType OBJECT-TYPE
   SYNTAX     StorageType 
   ACCESS     read-only
   STATUS     mandatory
   DESCRIPTION
     "This variable represents the storage type value for the
      mscLec tables."
::= { mscLecRowStatusEntry 4 }

mscLecIndex OBJECT-TYPE
   SYNTAX     Integer32 (0..31)
   ACCESS     not-accessible
   STATUS     mandatory
   DESCRIPTION
     "This variable represents the index for the mscLec tables."
::= { mscLecRowStatusEntry 10 }

mscLecCidDataTable OBJECT-TYPE
   SYNTAX     SEQUENCE OF MscLecCidDataEntry
   ACCESS     not-accessible
   STATUS     mandatory
   DESCRIPTION
     "This group contains the attribute for a component's Customer 
      Identifier (CID). Refer to the attribute description for a detailed 
      explanation of CIDs."
::= { mscLec 10 }

mscLecCidDataEntry OBJECT-TYPE
   SYNTAX     MscLecCidDataEntry
   ACCESS     not-accessible
   STATUS     mandatory
   DESCRIPTION
     "An entry in the mscLecCidDataTable."
   INDEX {
      mscLecIndex }
::= { mscLecCidDataTable 1 }

MscLecCidDataEntry ::= SEQUENCE {
   mscLecCustomerIdentifier
      Unsigned32 }

mscLecCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLecCidDataEntry 1 }

mscLecIfEntryTable OBJECT-TYPE
   SYNTAX     SEQUENCE OF MscLecIfEntryEntry
   ACCESS     not-accessible
   STATUS     mandatory
   DESCRIPTION
     "This group contains the provisionable attributes for the ifEntry."
::= { mscLec 11 }

mscLecIfEntryEntry OBJECT-TYPE
   SYNTAX     MscLecIfEntryEntry
   ACCESS     not-accessible
   STATUS     mandatory
   DESCRIPTION
     "An entry in the mscLecIfEntryTable."
   INDEX {
      mscLecIndex }
::= { mscLecIfEntryTable 1 }

MscLecIfEntryEntry ::= SEQUENCE {
   mscLecIfAdminStatus
      INTEGER,
   mscLecIfIndex
      InterfaceIndex }

mscLecIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLecIfEntryEntry 1 }

mscLecIfIndex OBJECT-TYPE
   SYNTAX     InterfaceIndex (1..65535)
   ACCESS     read-only
   STATUS     mandatory
   DESCRIPTION
     "This is the index for the IfEntry. Its value is automatically initialized 
      during the provisioning process."
::= { mscLecIfEntryEntry 2 }

mscLecMpTable OBJECT-TYPE
   SYNTAX     SEQUENCE OF MscLecMpEntry
   ACCESS     not-accessible
   STATUS     mandatory
   DESCRIPTION
     "This group contains the base provisioning data for the Media 
      Application component."
::= { mscLec 12 }

mscLecMpEntry OBJECT-TYPE
   SYNTAX     MscLecMpEntry
   ACCESS     not-accessible
   STATUS     mandatory
   DESCRIPTION
     "An entry in the mscLecMpTable."
   INDEX {
      mscLecIndex }
::= { mscLecMpTable 1 }

MscLecMpEntry ::= SEQUENCE {
   mscLecLinkToProtocolPort
      Link }

mscLecLinkToProtocolPort OBJECT-TYPE
   SYNTAX     Link 
   ACCESS     read-write
   STATUS     mandatory
   DESCRIPTION
     "This attribute contains a protocol port component name. The attribute 
      associates the application with a protocol port."
::= { mscLecMpEntry 1 }

mscLecProvTable OBJECT-TYPE
   SYNTAX     SEQUENCE OF MscLecProvEntry
   ACCESS     not-accessible
   STATUS     mandatory
   DESCRIPTION
     "This group contains the provisionable attributes for the 
      LanEmulationClient component."
::= { mscLec 13 }

mscLecProvEntry OBJECT-TYPE
   SYNTAX     MscLecProvEntry
   ACCESS     not-accessible
   STATUS     mandatory
   DESCRIPTION
     "An entry in the mscLecProvTable."
   INDEX {
      mscLecIndex }
::= { mscLecProvTable 1 }

MscLecProvEntry ::= SEQUENCE {
   mscLecLanType
      INTEGER,
   mscLecMaxFrameSize
      INTEGER,
   mscLecLanName
      AsciiString,
   mscLecV2Capable
      INTEGER,
   mscLecLecsAddress
      HexString,
   mscLecLesAddress
      HexString,
   mscLecMaxDataSvcs
      Unsigned32,
   mscLecMaxArpEntries
      Unsigned32,
   mscLecIlsForwarder
      Link }

mscLecLanType OBJECT-TYPE
   SYNTAX     INTEGER  {
                 unspecified(1),
                 ethernet(2) }
   ACCESS     read-write
   STATUS     mandatory
   DESCRIPTION
     "This attribute specifies the data frame format for this LEC. Auto-
      configuring LECs use this attribute in their Configure requests. 
      Manually-configured LECs use it in their Join requests. A value of 
      unspecified implies that the data frame format is obtained from the 
      LECS or LES.
      The value of this attribute may be overridden by the LECS or LES; 
      actualLanType contains the actual value."
   DEFVAL     { unspecified }
::= { mscLecProvEntry 1 }

mscLecMaxFrameSize OBJECT-TYPE
   SYNTAX     INTEGER  {
                 unspecified(0),
                 n1516(1516),
                 n1580(1580),
                 n4544(4544),
                 n9234(9234),
                 n18190(18190) }
   ACCESS     read-write
   STATUS     mandatory
   DESCRIPTION
     "This attribute specifies the maximum data frame size for this LEC. 
      Auto-configuring LECs use this attribute in their Configure 
      requests. Manually-configured LECs use it in their Join requests. A 
      value of unspecified may only be used for auto-configuring LECs.  
      A value of 1580 may only be specified for a LEC that has the 
      v2Capable attribute set to yes."
   DEFVAL     { unspecified }
::= { mscLecProvEntry 2 }

mscLecLanName OBJECT-TYPE
   SYNTAX     AsciiString (SIZE (0..32))
   ACCESS     read-write
   STATUS     mandatory
   DESCRIPTION
     "This attribute specifies the ELAN name for this LEC. Auto-
      configuring LECs use this attribute in their Configure requests. 
      Manually-configured LECs use it in their Join requests. An empty 
      string means unspecified.
      The value of this attribute may be overridden by the LECS or LES; 
      actualLanName contains the actual value."
::= { mscLecProvEntry 3 }

mscLecV2Capable OBJECT-TYPE
   SYNTAX     INTEGER  {
                 yes(1),
                 no(2) }
   ACCESS     read-write
   STATUS     mandatory
   DESCRIPTION
     "This attribute specifies whether this LEC exhibits LANE v2 
      behavior where it differs in its requirements from LANE v1 
      behavior."
   DEFVAL     { yes }
::= { mscLecProvEntry 4 }

mscLecLecsAddress OBJECT-TYPE
   SYNTAX     HexString (SIZE (0..20))
   ACCESS     read-write
   STATUS     mandatory
   DESCRIPTION
     "This attribute specifies the ATM address of the LECS. If this 
      attribute is non-null, the LEC attempts to set up a Configuration 
      Direct SVC to this address as the first step in the LECS Connect 
      phase. Otherwise, the well known LECS ATM address is used.
      Only one of the attributes lecsAddress and lesAddress can be 
      specified at one time."
::= { mscLecProvEntry 5 }

mscLecLesAddress OBJECT-TYPE
   SYNTAX     HexString (SIZE (0..20))
   ACCESS     read-write
   STATUS     mandatory
   DESCRIPTION
     "This attribute specifies the ATM address of the LES. The LEC uses 
      this address to connect directly to the LES, thus bypassing the 
      LECS. A LEC which did not use the LECS is deemed to be 
      manually-configured.
      Only one of the attributes lecsAddress and lesAddress can be 
      specified at one time."
::= { mscLecProvEntry 6 }

mscLecMaxDataSvcs OBJECT-TYPE
   SYNTAX     Unsigned32 (16..1018)
   ACCESS     read-write
   STATUS     mandatory
   DESCRIPTION
     "This attribute specifies the maximum number of Data Direct SVCs 
      which this LEC can have active at any one time. When operating at 
      the maximum, an SVC setup request releases the oldest 10% of the 
      Data Direct SVCs of this LEC.
      A SET alarm is issued when currDataSvcs rises above 95% of this 
      value and is CLEAR-ed when it falls below 85%.
      Set maxDataSvcs as low as acceptable since a fixed amount of 
      memory is consumed proportional to this value on every LP with 
      this feature present."
   DEFVAL     { 16 }
::= { mscLecProvEntry 7 }

mscLecMaxArpEntries OBJECT-TYPE
   SYNTAX     Unsigned32 (32..10240)
   ACCESS     read-write
   STATUS     mandatory
   DESCRIPTION
     "This attribute specifies the maximum number of entries which this 
      LEC can have in its LE_ARP table at any one time. When operating 
      at the maximum, if an additional entry must be installed, up to 10% 
      of the oldest entries are removed.
      A SET alarm is issued when currArpEntries rises above 95% of this 
      value and is CLEAR-ed when it falls below 85%."
   DEFVAL     { 5120 }
::= { mscLecProvEntry 8 }

mscLecIlsForwarder OBJECT-TYPE
   SYNTAX     Link 
   ACCESS     read-write
   STATUS     mandatory
   DESCRIPTION
     "This attribute specifies the IlsForwarder that this LEC is using."
::= { mscLecProvEntry 9 }

mscLecStateTable OBJECT-TYPE
   SYNTAX     SEQUENCE OF MscLecStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLec 15 }

mscLecStateEntry OBJECT-TYPE
   SYNTAX     MscLecStateEntry
   ACCESS     not-accessible
   STATUS     mandatory
   DESCRIPTION
     "An entry in the mscLecStateTable."
   INDEX {
      mscLecIndex }
::= { mscLecStateTable 1 }

MscLecStateEntry ::= SEQUENCE {
   mscLecAdminState
      INTEGER,
   mscLecOperationalState
      INTEGER,
   mscLecUsageState
      INTEGER }

mscLecAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLecStateEntry 1 }

mscLecOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLecStateEntry 2 }

mscLecUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLecStateEntry 3 }

mscLecOperStatusTable OBJECT-TYPE
   SYNTAX     SEQUENCE OF MscLecOperStatusEntry
   ACCESS     not-accessible
   STATUS     mandatory
   DESCRIPTION
     "This group includes the Operational Status attribute. This attribute 
      defines the current operational state of this component."
::= { mscLec 16 }

mscLecOperStatusEntry OBJECT-TYPE
   SYNTAX     MscLecOperStatusEntry
   ACCESS     not-accessible
   STATUS     mandatory
   DESCRIPTION
     "An entry in the mscLecOperStatusTable."
   INDEX {
      mscLecIndex }
::= { mscLecOperStatusTable 1 }

MscLecOperStatusEntry ::= SEQUENCE {
   mscLecSnmpOperStatus
      INTEGER }

mscLecSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLecOperStatusEntry 1 }

mscLecOperTable OBJECT-TYPE
   SYNTAX     SEQUENCE OF MscLecOperEntry
   ACCESS     not-accessible
   STATUS     mandatory
   DESCRIPTION
     "This group contains the operational status attributes of the 
      LanEmulationClient component."
::= { mscLec 17 }

mscLecOperEntry OBJECT-TYPE
   SYNTAX     MscLecOperEntry
   ACCESS     not-accessible
   STATUS     mandatory
   DESCRIPTION
     "An entry in the mscLecOperTable."
   INDEX {
      mscLecIndex }
::= { mscLecOperTable 1 }

MscLecOperEntry ::= SEQUENCE {
   mscLecActualLanType
      INTEGER,
   mscLecActualMaxFrameSize
      INTEGER,
   mscLecActualLanName
      AsciiString,
   mscLecElanId
      Unsigned32,
   mscLecActualV2Capable
      INTEGER,
   mscLecConfigurationSource
      INTEGER,
   mscLecActualLecsAddress
      HexString,
   mscLecActualLesAddress
      HexString,
   mscLecAtmAddress
      HexString,
   mscLecMacAddress
      MacAddress,
   mscLecLecId
      Unsigned32,
   mscLecInterfaceState
      INTEGER,
   mscLecLastFailureResponseCode
      INTEGER,
   mscLecLastFailureState
      INTEGER }

mscLecActualLanType OBJECT-TYPE
   SYNTAX     INTEGER  {
                 unspecified(1),
                 ethernet(2) }
   ACCESS     read-only
   STATUS     mandatory
   DESCRIPTION
     "This attribute indicates the data frame format of this LEC. This may 
      come from the lanType attribute, LECS or LES. The data frame 
      format is not unspecified for an operational LEC.
      This attribute represents the 'C2' LEC state parameter in the ATM 
      Forum LANE specification.
      
      Token Ring data frame format is not supported. The LEC does not 
      become operational if the LECS or LES specify a LAN type of 
      Token Ring."
::= { mscLecOperEntry 1 }

mscLecActualMaxFrameSize OBJECT-TYPE
   SYNTAX     INTEGER  {
                 unspecified(0),
                 n1516(1516),
                 n1580(1580),
                 n4544(4544),
                 n9234(9234),
                 n18190(18190) }
   ACCESS     read-only
   STATUS     mandatory
   DESCRIPTION
     "This attribute indicates the maximum data frame size of this LEC. 
      This may come from the maxFrameSize attribute, LECS or LES. 
      The value is not unspecified for an operational LEC. 
      If the LEC's actualV2Capable attribute is no, the value will be 
      limited to one of 1516, 4544, 9234, 18190.
      This attribute represents the 'C3' LEC state parameter in the ATM 
      Forum LANE specification."
::= { mscLecOperEntry 2 }

mscLecActualLanName OBJECT-TYPE
   SYNTAX     AsciiString (SIZE (0..32))
   ACCESS     read-only
   STATUS     mandatory
   DESCRIPTION
     "This attribute indicates the name of the ELAN to which this LEC is 
      connected. This may come from the lanName attribute, LECS or 
      LES. It may be null for an operational LEC.
      This attribute represents the 'C5' LEC state parameter in the ATM 
      Forum LANE specification."
::= { mscLecOperEntry 3 }

mscLecElanId OBJECT-TYPE
   SYNTAX     Unsigned32 (0..4294967295)
   ACCESS     read-only
   STATUS     mandatory
   DESCRIPTION
     "This attribute identifies the ELAN to which this LEC is connected. 
      For v2, the  value will be set in the configuration phase, 
      otherwise it will be 0."
::= { mscLecOperEntry 4 }

mscLecActualV2Capable OBJECT-TYPE
   SYNTAX     INTEGER  {
                 yes(1),
                 no(2) }
   ACCESS     read-only
   STATUS     mandatory
   DESCRIPTION
     "This attribute indicates whether this LEC exhibits LANE v2 
      behavior. The value is set in the Join phase."
::= { mscLecOperEntry 5 }

mscLecConfigurationSource OBJECT-TYPE
   SYNTAX     INTEGER  {
                 usedProvisionedLecsAddress(1),
                 gotLecsAddressViaIlmi(2),
                 usedWellKnownLecsAddress(3),
                 usedLecsPvc(4),
                 didNotUseLecs(5) }
   ACCESS     read-only
   STATUS     mandatory
   DESCRIPTION
     "This attribute indicates whether this LEC used the LECS, and if so, 
      the method  used to establish the Configuration Direct VCC. 
      The attribute retains this value when the LEC is reset.
      - usedProvisionedLecsAddress: The ATM address specified in 
      lecsAddress was used to locate the LECS.
      - gotLecsAddressViaIlmi: The ATM address of the LECS was 
      located via the ILMI protocol.
      - usedWellKnownLecsAddress: The well-known ATM address 
      0x47007900000000000000000000-00A03E000001-00 was used to 
      locate the LECS.
      - usedLecsPvc: The well known PVC of VPI=0, VCI=17 was used 
      to locate the LECS.
      - didNotUseLecs: The LECS was bypassed and the ATM address 
      specified in lesAddress was used to locate the LES."
::= { mscLecOperEntry 6 }

mscLecActualLecsAddress OBJECT-TYPE
   SYNTAX     HexString (SIZE (0..20))
   ACCESS     read-only
   STATUS     mandatory
   DESCRIPTION
     "This attribute indicates the ATM address of the LECS used to 
      configure this LEC. The address is null if the LECS was not used."
::= { mscLecOperEntry 7 }

mscLecActualLesAddress OBJECT-TYPE
   SYNTAX     HexString (SIZE (0..20))
   ACCESS     read-only
   STATUS     mandatory
   DESCRIPTION
     "This attribute indicates the ATM address of the LES which is 
      currently serving this LEC. The address is not null for an 
      operational LEC.
      This attribute represents the 'C9' LEC state parameter in the ATM 
      Forum LANE specification."
::= { mscLecOperEntry 8 }

mscLecAtmAddress OBJECT-TYPE
   SYNTAX     HexString (SIZE (0..20))
   ACCESS     read-only
   STATUS     mandatory
   DESCRIPTION
     "This attribute indicates the ATM address of this LEC.
      This attribute represents the 'C1' LEC state parameter in the ATM 
      Forum LANE specification."
::= { mscLecOperEntry 9 }

mscLecMacAddress OBJECT-TYPE
   SYNTAX     MacAddress (SIZE (6))
   ACCESS     read-only
   STATUS     mandatory
   DESCRIPTION
     "This attribute indicates the MAC address of this LEC.
      This attribute represents the 'C6' LEC state parameter in the ATM 
      Forum LANE specification."
::= { mscLecOperEntry 10 }

mscLecLecId OBJECT-TYPE
   SYNTAX     Unsigned32 (0..65279)
   ACCESS     read-only
   STATUS     mandatory
   DESCRIPTION
     "This attribute indicates the LANE Client Identifier (LECID) 
      assigned to this LEC by the LES during the Join phase. The LECID 
      uniquely identifies a LEC on a particular ELAN.
      This attribute represents the 'C14' LEC state parameter in the ATM 
      Forum LANE specification."
::= { mscLecOperEntry 11 }

mscLecInterfaceState OBJECT-TYPE
   SYNTAX     INTEGER  {
                 initialState(1),
                 lecsConnect(2),
                 configure(3),
                 join(4),
                 initialRegistration(5),
                 busConnect(6),
                 operational(7) }
   ACCESS     read-only
   STATUS     mandatory
   DESCRIPTION
     "This attribute indicates the current state of the LEC. Note that 
      ifOperStatus is up only when interfaceState is operational.
      - initialState: Some parameters (such as addresses and ELAN 
      name) are known to the LEC.
      - lecsConnect: LEC establishes Configuration Direct VCC to 
      LECS. Manually-configured LECs skip this state.
      - configure: LEC discovers LES.
      - join: LEC establishes control connections to LES. LEC is 
      assigned unique LECID and knows all ELAN parameters.
      - initialRegistration: LEC may register additional MAC addresses 
      with LES. This is in addition to the single MAC address registered 
      during Join phase.
      - busConnect: LEC issues LE_ARP to locate the BUS and sets up 
      the connection. The BUS then establishes the Multicast Forward 
      VCC to the LEC.
      - operational: LEC is operational and can forward data traffic."
::= { mscLecOperEntry 12 }

mscLecLastFailureResponseCode OBJECT-TYPE
   SYNTAX     INTEGER  {
                 none(1),
                 timeout(2),
                 undefinedError(3),
                 versionNotSupported(4),
                 invalidRequestParameters(5),
                 duplicateLanDestination(6),
                 duplicateAtmAddress(7),
                 insufficientResources(8),
                 accessDenied(9),
                 invalidRequesterId(10),
                 invalidLanDestination(11),
                 invalidAtmAddress(12),
                 noConfiguration(13),
                 leConfigureError(14),
                 insufficientInformation(15) }
   ACCESS     read-only
   STATUS     mandatory
   DESCRIPTION
     "The attribute indicates the status code from the last failed Configure 
      or Join response. Failed responses are those for which the 
      LE_CONFIGURE_RESPONSE / LE_JOIN_RESPONSE frame 
      contains a non-zero code, or fails to arrive within a time-out period. 
      If none of the LEC's requests have failed, this attribute has the value 
      none."
::= { mscLecOperEntry 13 }

mscLecLastFailureState OBJECT-TYPE
   SYNTAX     INTEGER  {
                 initialState(1),
                 lecsConnect(2),
                 configure(3),
                 join(4),
                 initialRegistration(5),
                 busConnect(6),
                 operational(7) }
   ACCESS     read-only
   STATUS     mandatory
   DESCRIPTION
     "This attribute indicates the state that the LEC was in when it 
      updated the lastFailureResponseCode. If lastFailureResponseCode 
      is none, this attribute has the value initialState.
      See the interfaceState attribute for a description of each state."
::= { mscLecOperEntry 14 }

mscLecStatsTable OBJECT-TYPE
   SYNTAX     SEQUENCE OF MscLecStatsEntry
   ACCESS     not-accessible
   STATUS     mandatory
   DESCRIPTION
     "This group contains the statistical attributes of the 
      LanEmulationClient component."
::= { mscLec 18 }

mscLecStatsEntry OBJECT-TYPE
   SYNTAX     MscLecStatsEntry
   ACCESS     not-accessible
   STATUS     mandatory
   DESCRIPTION
     "An entry in the mscLecStatsTable."
   INDEX {
      mscLecIndex }
::= { mscLecStatsTable 1 }

MscLecStatsEntry ::= SEQUENCE {
   mscLecArpRequestsOut
      Counter32,
   mscLecArpRepliesIn
      Counter32,
   mscLecArpRequestsIn
      Counter32,
   mscLecArpRepliesOut
      Counter32,
   mscLecControlFramesOut
      Counter32,
   mscLecControlFramesIn
      Counter32,
   mscLecSvcFailures
      Counter32,
   mscLecCurrDataSvcs
      Unsigned32,
   mscLecPeakDataSvcs
      Unsigned32,
   mscLecCurrArpEntries
      Unsigned32,
   mscLecPeakArpEntries
      Unsigned32,
   mscLecBadControlFrames
      Counter32,
   mscLecProtocolViolations
      Counter32,
   mscLecUnsupportedTlvs
      Counter32 }

mscLecArpRequestsOut OBJECT-TYPE
   SYNTAX     Counter32 
   ACCESS     read-only
   STATUS     mandatory
   DESCRIPTION
     "This attribute counts the LE_ARP_REQUESTS sent by this LEC. 
      This counter wraps to zero when the maximum value is reached."
::= { mscLecStatsEntry 1 }

mscLecArpRepliesIn OBJECT-TYPE
   SYNTAX     Counter32 
   ACCESS     read-only
   STATUS     mandatory
   DESCRIPTION
     "This attribute counts the LE_ARP_RESPONSES received by this 
      LEC. This counter wraps to zero when the maximum value is 
      reached."
::= { mscLecStatsEntry 2 }

mscLecArpRequestsIn OBJECT-TYPE
   SYNTAX     Counter32 
   ACCESS     read-only
   STATUS     mandatory
   DESCRIPTION
     "This attribute counts the LE_ARP_REQUESTS received by this 
      LEC. This counter wraps to zero when the maximum value is 
      reached."
::= { mscLecStatsEntry 3 }

mscLecArpRepliesOut OBJECT-TYPE
   SYNTAX     Counter32 
   ACCESS     read-only
   STATUS     mandatory
   DESCRIPTION
     "This attribute counts the LE_ARP_RESPONSES sent by this LEC. 
      This counter wraps to zero when the maximum value is reached."
::= { mscLecStatsEntry 4 }

mscLecControlFramesOut OBJECT-TYPE
   SYNTAX     Counter32 
   ACCESS     read-only
   STATUS     mandatory
   DESCRIPTION
     "This attribute counts the control packets sent by this LEC. This 
      counter wraps to zero when the maximum value is reached."
::= { mscLecStatsEntry 5 }

mscLecControlFramesIn OBJECT-TYPE
   SYNTAX     Counter32 
   ACCESS     read-only
   STATUS     mandatory
   DESCRIPTION
     "This attribute counts the control packets received by this LEC. This 
      counter wraps to zero when the maximum value is reached."
::= { mscLecStatsEntry 6 }

mscLecSvcFailures OBJECT-TYPE
   SYNTAX     Counter32 
   ACCESS     read-only
   STATUS     mandatory
   DESCRIPTION
     "This attribute counts the number of SVCs that could not be set up. 
      The reasons for failure are:
      - outgoing SVCs that this LEC failed to establish;
      - incoming SVCs that this LEC failed to establish; and
      - incoming SVCs that this LEC rejected for protocol or security 
      reasons.
      This counter wraps to zero when the maximum value is reached."
::= { mscLecStatsEntry 7 }

mscLecCurrDataSvcs OBJECT-TYPE
   SYNTAX     Unsigned32 (0..4292967295)
   ACCESS     read-only
   STATUS     mandatory
   DESCRIPTION
     "This attribute counts the number of Data Direct SVCs that this LEC 
      has in service."
::= { mscLecStatsEntry 8 }

mscLecPeakDataSvcs OBJECT-TYPE
   SYNTAX     Unsigned32 (0..4292967295)
   ACCESS     read-only
   STATUS     mandatory
   DESCRIPTION
     "The attribute is the peak value of currDataSvcs. In other words, this 
      value is the maximum number of Data Direct SVCs that this LEC 
      had in service at any one time."
::= { mscLecStatsEntry 9 }

mscLecCurrArpEntries OBJECT-TYPE
   SYNTAX     Unsigned32 (0..4292967295)
   ACCESS     read-only
   STATUS     mandatory
   DESCRIPTION
     "This attribute counts the current number of entries that this LEC has 
      in its LE ARP table."
::= { mscLecStatsEntry 10 }

mscLecPeakArpEntries OBJECT-TYPE
   SYNTAX     Unsigned32 (0..4292967295)
   ACCESS     read-only
   STATUS     mandatory
   DESCRIPTION
     "The attribute is the peak value currArpEntries. In other words, this 
      value is the maximum number of entries that this LEC had in its LE 
      ARP table at any one time."
::= { mscLecStatsEntry 11 }

mscLecBadControlFrames OBJECT-TYPE
   SYNTAX     Counter32 
   ACCESS     read-only
   STATUS     mandatory
   DESCRIPTION
     "This attribute counts the control frames discarded by the LEC due 
      to invalid or illegal frame format, and those frames with a STATUS 
      code other than 'Success'. This counter wraps to zero when the 
      maximum value is reached."
::= { mscLecStatsEntry 12 }

mscLecProtocolViolations OBJECT-TYPE
   SYNTAX     Counter32 
   ACCESS     read-only
   STATUS     mandatory
   DESCRIPTION
     "This attribute counts the number of responses received by
      the LEC that contained invalid data or non-protocol compliant data.
      This counter wraps to zero when the maximum value is reached."
::= { mscLecStatsEntry 13 }

mscLecUnsupportedTlvs OBJECT-TYPE
   SYNTAX     Counter32 
   ACCESS     read-only
   STATUS     mandatory
   DESCRIPTION
     "This attribute counts the number of times an unsupported TLV was 
      received by the LEC in either the Configuration or Join response.
      This counter wraps to zero when the maximum value is reached."
::= { mscLecStatsEntry 14 }

-- 
-- *** THIS SUBTREE CURRENTLY NOT IMPLEMENTED ***
-- 

-- Lec/n LeArpEntry/<Mac Address>
-- This component defines an entry in the LE_ARP table. Each entry 
-- contains information about the binding of one MAC address to one 
-- ATM address.

mscLecLeArp OBJECT IDENTIFIER ::= { mscLec 2 }



mscLecLeArpRowStatusTable OBJECT-TYPE
   SYNTAX     SEQUENCE OF MscLecLeArpRowStatusEntry
   ACCESS     not-accessible
   STATUS     mandatory
   DESCRIPTION
     "*** THIS TABLE CURRENTLY NOT IMPLEMENTED ***

      This entry controls the addition and deletion of 
      mscLecLeArp components."
::= { mscLecLeArp 1 }

mscLecLeArpRowStatusEntry OBJECT-TYPE
   SYNTAX     MscLecLeArpRowStatusEntry
   ACCESS     not-accessible
   STATUS     mandatory
   DESCRIPTION
     "A single entry in the table represents a single 
      mscLecLeArp component."
   INDEX {
      mscLecIndex,
      mscLecLeArpIndex }
::= { mscLecLeArpRowStatusTable 1 }

MscLecLeArpRowStatusEntry ::= SEQUENCE {
   mscLecLeArpRowStatus
      RowStatus,
   mscLecLeArpComponentName
      DisplayString,
   mscLecLeArpStorageType
      StorageType,
   mscLecLeArpIndex
      DashedHexString }

mscLecLeArpRowStatus OBJECT-TYPE
   SYNTAX     RowStatus 
   ACCESS     read-only
   STATUS     mandatory
   DESCRIPTION
     "This variable is used as the basis for SNMP naming of
      mscLecLeArp components.
      These components cannot be added nor deleted."
::= { mscLecLeArpRowStatusEntry 1 }

mscLecLeArpComponentName OBJECT-TYPE
   SYNTAX     DisplayString 
   ACCESS     read-only
   STATUS     mandatory
   DESCRIPTION
     "This variable provides the component's string name for
      use with the ASCII Console Interface"
::= { mscLecLeArpRowStatusEntry 2 }

mscLecLeArpStorageType OBJECT-TYPE
   SYNTAX     StorageType 
   ACCESS     read-only
   STATUS     mandatory
   DESCRIPTION
     "This variable represents the storage type value for the
      mscLecLeArp tables."
::= { mscLecLeArpRowStatusEntry 4 }

mscLecLeArpIndex OBJECT-TYPE
   SYNTAX     DashedHexString (SIZE (6))
   ACCESS     not-accessible
   STATUS     mandatory
   DESCRIPTION
     "This variable represents the index for the mscLecLeArp tables."
::= { mscLecLeArpRowStatusEntry 10 }

mscLecLeArpOperTable OBJECT-TYPE
   SYNTAX     SEQUENCE OF MscLecLeArpOperEntry
   ACCESS     not-accessible
   STATUS     mandatory
   DESCRIPTION
     "*** THIS TABLE CURRENTLY NOT IMPLEMENTED ***

      This group contains the operational attributes of the LeArpEntry 
      component."
::= { mscLecLeArp 10 }

mscLecLeArpOperEntry OBJECT-TYPE
   SYNTAX     MscLecLeArpOperEntry
   ACCESS     not-accessible
   STATUS     mandatory
   DESCRIPTION
     "An entry in the mscLecLeArpOperTable."
   INDEX {
      mscLecIndex,
      mscLecLeArpIndex }
::= { mscLecLeArpOperTable 1 }

MscLecLeArpOperEntry ::= SEQUENCE {
   mscLecLeArpAtmAddress
      HexString,
   mscLecLeArpIsRemoteAddress
      INTEGER,
   mscLecLeArpConnectionId
      Unsigned32 }

mscLecLeArpAtmAddress OBJECT-TYPE
   SYNTAX     HexString (SIZE (20))
   ACCESS     read-only
   STATUS     mandatory
   DESCRIPTION
     "This attribute indicates the ATM address of the BUS or LEC 
      associated with the MAC address of this entry. If the MAC address 
      is the all-ones broadcast address, the entry is for the BUS."
::= { mscLecLeArpOperEntry 1 }

mscLecLeArpIsRemoteAddress OBJECT-TYPE
   SYNTAX     INTEGER  {
                 yes(1),
                 no(2) }
   ACCESS     read-only
   STATUS     mandatory
   DESCRIPTION
     "This attribute indicates whether this entry is for a local or remote 
      MAC address. In this context, 'local' means a MAC address that is 
      local to a LEC, and 'remote' means a MAC address for which the 
      LEC is proxy.
      If yes, the address is believed to be remote, or its local/remote status 
      is unknown.
      If no, the address is believed to be local; that is, registered with the 
      LES by the LEC whose ATM address is atmAddress."
::= { mscLecLeArpOperEntry 2 }

mscLecLeArpConnectionId OBJECT-TYPE
   SYNTAX     Unsigned32 (0..1022)
   ACCESS     read-only
   STATUS     mandatory
   DESCRIPTION
     "This attribute indicates the connection identifier associated with this 
      entry. The connection identifier is the instance of the Connection 
      component."
::= { mscLecLeArpOperEntry 3 }

-- 
-- *** THIS SUBTREE CURRENTLY NOT IMPLEMENTED ***
-- 

-- Lec/n Connection/n
-- This component defines an ATM connection (SVC) that is used by 
-- the LEC.

mscLecConn OBJECT IDENTIFIER ::= { mscLec 3 }



mscLecConnRowStatusTable OBJECT-TYPE
   SYNTAX     SEQUENCE OF MscLecConnRowStatusEntry
   ACCESS     not-accessible
   STATUS     mandatory
   DESCRIPTION
     "*** THIS TABLE CURRENTLY NOT IMPLEMENTED ***

      This entry controls the addition and deletion of 
      mscLecConn components."
::= { mscLecConn 1 }

mscLecConnRowStatusEntry OBJECT-TYPE
   SYNTAX     MscLecConnRowStatusEntry
   ACCESS     not-accessible
   STATUS     mandatory
   DESCRIPTION
     "A single entry in the table represents a single 
      mscLecConn component."
   INDEX {
      mscLecIndex,
      mscLecConnIndex }
::= { mscLecConnRowStatusTable 1 }

MscLecConnRowStatusEntry ::= SEQUENCE {
   mscLecConnRowStatus
      RowStatus,
   mscLecConnComponentName
      DisplayString,
   mscLecConnStorageType
      StorageType,
   mscLecConnIndex
      Integer32 }

mscLecConnRowStatus OBJECT-TYPE
   SYNTAX     RowStatus 
   ACCESS     read-only
   STATUS     mandatory
   DESCRIPTION
     "This variable is used as the basis for SNMP naming of
      mscLecConn components.
      These components cannot be added nor deleted."
::= { mscLecConnRowStatusEntry 1 }

mscLecConnComponentName OBJECT-TYPE
   SYNTAX     DisplayString 
   ACCESS     read-only
   STATUS     mandatory
   DESCRIPTION
     "This variable provides the component's string name for
      use with the ASCII Console Interface"
::= { mscLecConnRowStatusEntry 2 }

mscLecConnStorageType OBJECT-TYPE
   SYNTAX     StorageType 
   ACCESS     read-only
   STATUS     mandatory
   DESCRIPTION
     "This variable represents the storage type value for the
      mscLecConn tables."
::= { mscLecConnRowStatusEntry 4 }

mscLecConnIndex OBJECT-TYPE
   SYNTAX     Integer32 (0..1022)
   ACCESS     not-accessible
   STATUS     mandatory
   DESCRIPTION
     "This variable represents the index for the mscLecConn tables."
::= { mscLecConnRowStatusEntry 10 }

mscLecConnOperTable OBJECT-TYPE
   SYNTAX     SEQUENCE OF MscLecConnOperEntry
   ACCESS     not-accessible
   STATUS     mandatory
   DESCRIPTION
     "*** THIS TABLE CURRENTLY NOT IMPLEMENTED ***

      This group contains the operational status attributes of the 
      Connection component."
::= { mscLecConn 10 }

mscLecConnOperEntry OBJECT-TYPE
   SYNTAX     MscLecConnOperEntry
   ACCESS     not-accessible
   STATUS     mandatory
   DESCRIPTION
     "An entry in the mscLecConnOperTable."
   INDEX {
      mscLecIndex,
      mscLecConnIndex }
::= { mscLecConnOperTable 1 }

MscLecConnOperEntry ::= SEQUENCE {
   mscLecConnRemoteAtmAddress
      HexString,
   mscLecConnAge
      Unsigned32,
   mscLecConnType
      INTEGER }

mscLecConnRemoteAtmAddress OBJECT-TYPE
   SYNTAX     HexString (SIZE (20))
   ACCESS     read-only
   STATUS     mandatory
   DESCRIPTION
     "This attribute indicates the ATM address of the far end."
::= { mscLecConnOperEntry 1 }

mscLecConnAge OBJECT-TYPE
   SYNTAX     Unsigned32 (0..4292967295)
   ACCESS     read-only
   STATUS     mandatory
   DESCRIPTION
     "This attribute indicates the age of this connection."
::= { mscLecConnOperEntry 2 }

mscLecConnType OBJECT-TYPE
   SYNTAX     INTEGER  {
                 configurationDirectVcc(1),
                 controlDirectVcc(2),
                 controlDistributeVcc(3),
                 dataDirectVcc(4),
                 defaultMulticastSendVcc(5),
                 multicastForward(6) }
   ACCESS     read-only
   STATUS     mandatory
   DESCRIPTION
     "This attribute indicates the type of this connection."
::= { mscLecConnOperEntry 3 }

mscLecConnStatsTable OBJECT-TYPE
   SYNTAX     SEQUENCE OF MscLecConnStatsEntry
   ACCESS     not-accessible
   STATUS     mandatory
   DESCRIPTION
     "*** THIS TABLE CURRENTLY NOT IMPLEMENTED ***

      This group contains the statistical attributes of the Connection 
      component."
::= { mscLecConn 11 }

mscLecConnStatsEntry OBJECT-TYPE
   SYNTAX     MscLecConnStatsEntry
   ACCESS     not-accessible
   STATUS     mandatory
   DESCRIPTION
     "An entry in the mscLecConnStatsTable."
   INDEX {
      mscLecIndex,
      mscLecConnIndex }
::= { mscLecConnStatsTable 1 }

MscLecConnStatsEntry ::= SEQUENCE {
   mscLecConnOutFrames
      Counter32,
   mscLecConnInFrames
      Counter32 }

mscLecConnOutFrames OBJECT-TYPE
   SYNTAX     Counter32 
   ACCESS     read-only
   STATUS     mandatory
   DESCRIPTION
     "This attribute counts the frames sent over this connection. This 
      counter wraps to zero when the maximum value is reached."
::= { mscLecConnStatsEntry 1 }

mscLecConnInFrames OBJECT-TYPE
   SYNTAX     Counter32 
   ACCESS     read-only
   STATUS     mandatory
   DESCRIPTION
     "This attribute counts the frames received over this connection. This 
      counter wraps to zero when the maximum value is reached."
::= { mscLecConnStatsEntry 2 }

-- 
-- *** THIS SUBTREE CURRENTLY NOT IMPLEMENTED ***
-- 

-- An AtmConnection component is created for each ATM connection 
-- established by an application. It shows where the data traffic for this 
-- connection is directed.

mscLecConnAtmCon OBJECT IDENTIFIER ::= { mscLecConn 2 }



mscLecConnAtmConRowStatusTable OBJECT-TYPE
   SYNTAX     SEQUENCE OF MscLecConnAtmConRowStatusEntry
   ACCESS     not-accessible
   STATUS     mandatory
   DESCRIPTION
     "*** THIS TABLE CURRENTLY NOT IMPLEMENTED ***

      This entry controls the addition and deletion of 
      mscLecConnAtmCon components."
::= { mscLecConnAtmCon 1 }

mscLecConnAtmConRowStatusEntry OBJECT-TYPE
   SYNTAX     MscLecConnAtmConRowStatusEntry
   ACCESS     not-accessible
   STATUS     mandatory
   DESCRIPTION
     "A single entry in the table represents a single 
      mscLecConnAtmCon component."
   INDEX {
      mscLecIndex,
      mscLecConnIndex,
      mscLecConnAtmConIndex }
::= { mscLecConnAtmConRowStatusTable 1 }

MscLecConnAtmConRowStatusEntry ::= SEQUENCE {
   mscLecConnAtmConRowStatus
      RowStatus,
   mscLecConnAtmConComponentName
      DisplayString,
   mscLecConnAtmConStorageType
      StorageType,
   mscLecConnAtmConIndex
      NonReplicated }

mscLecConnAtmConRowStatus OBJECT-TYPE
   SYNTAX     RowStatus 
   ACCESS     read-only
   STATUS     mandatory
   DESCRIPTION
     "This variable is used as the basis for SNMP naming of
      mscLecConnAtmCon components.
      These components cannot be added nor deleted."
::= { mscLecConnAtmConRowStatusEntry 1 }

mscLecConnAtmConComponentName OBJECT-TYPE
   SYNTAX     DisplayString 
   ACCESS     read-only
   STATUS     mandatory
   DESCRIPTION
     "This variable provides the component's string name for
      use with the ASCII Console Interface"
::= { mscLecConnAtmConRowStatusEntry 2 }

mscLecConnAtmConStorageType OBJECT-TYPE
   SYNTAX     StorageType 
   ACCESS     read-only
   STATUS     mandatory
   DESCRIPTION
     "This variable represents the storage type value for the
      mscLecConnAtmCon tables."
::= { mscLecConnAtmConRowStatusEntry 4 }

mscLecConnAtmConIndex OBJECT-TYPE
   SYNTAX     NonReplicated 
   ACCESS     not-accessible
   STATUS     mandatory
   DESCRIPTION
     "This variable represents the index for the mscLecConnAtmCon tables."
::= { mscLecConnAtmConRowStatusEntry 10 }

mscLecConnAtmConOperTable OBJECT-TYPE
   SYNTAX     SEQUENCE OF MscLecConnAtmConOperEntry
   ACCESS     not-accessible
   STATUS     mandatory
   DESCRIPTION
     "*** THIS TABLE CURRENTLY NOT IMPLEMENTED ***

      This attribute group contains the operational attributes for the 
      NapAtmConnection component."
::= { mscLecConnAtmCon 10 }

mscLecConnAtmConOperEntry OBJECT-TYPE
   SYNTAX     MscLecConnAtmConOperEntry
   ACCESS     not-accessible
   STATUS     mandatory
   DESCRIPTION
     "An entry in the mscLecConnAtmConOperTable."
   INDEX {
      mscLecIndex,
      mscLecConnIndex,
      mscLecConnAtmConIndex }
::= { mscLecConnAtmConOperTable 1 }

MscLecConnAtmConOperEntry ::= SEQUENCE {
   mscLecConnAtmConNextHop
      RowPointer }

mscLecConnAtmConNextHop OBJECT-TYPE
   SYNTAX     RowPointer 
   ACCESS     read-only
   STATUS     mandatory
   DESCRIPTION
     "This attribute shows the component name of the AtmIf Vcc Ep or 
      AtmCon component to which this switched connection is 
      established."
::= { mscLecConnAtmConOperEntry 1 }




-- 
-- Version and Compliance statements
-- 



-- Object-Group Statement:
-- A list of all current accessible leaf objects.

-- OBJECTS { mscLecArpRequestsIn,
--           mscLecMaxFrameSize,
--           mscLecLeArpConnectionId,
--           mscLecConnStorageType,
--           mscLecAdminState,
--           mscLecMaxArpEntries,
--           mscLecLeArpComponentName,
--           mscLecLecsAddress,
--           mscLecInterfaceState,
--           mscLecElanId,
--           mscLecLeArpAtmAddress,
--           mscLecBadControlFrames,
--           mscLecConnType,
--           mscLecCustomerIdentifier,
--           mscLecPeakDataSvcs,
--           mscLecMacAddress,
--           mscLecLeArpIsRemoteAddress,
--           mscLecSvcFailures,
--           mscLecOperationalState,
--           mscLecUsageState,
--           mscLecArpRequestsOut,
--           mscLecActualV2Capable,
--           mscLecArpRepliesOut,
--           mscLecComponentName,
--           mscLecCurrArpEntries,
--           mscLecPeakArpEntries,
--           mscLecConnInFrames,
--           mscLecAtmAddress,
--           mscLecUnsupportedTlvs,
--           mscLecLanName,
--           mscLecLecId,
--           mscLecLastFailureResponseCode,
--           mscLecLesAddress,
--           mscLecMaxDataSvcs,
--           mscLecActualLesAddress,
--           mscLecActualMaxFrameSize,
--           mscLecLanType,
--           mscLecConnComponentName,
--           mscLecActualLecsAddress,
--           mscLecConnAtmConRowStatus,
--           mscLecActualLanType,
--           mscLecConnAge,
--           mscLecConnAtmConNextHop,
--           mscLecLinkToProtocolPort,
--           mscLecConnOutFrames,
--           mscLecConnAtmConStorageType,
--           mscLecLeArpStorageType,
--           mscLecCurrDataSvcs,
--           mscLecProtocolViolations,
--           mscLecV2Capable,
--           mscLecConfigurationSource,
--           mscLecArpRepliesIn,
--           mscLecSnmpOperStatus,
--           mscLecLastFailureState,
--           mscLecConnAtmConComponentName,
--           mscLecIfIndex,
--           mscLecConnRemoteAtmAddress,
--           mscLecActualLanName,
--           mscLecIfAdminStatus,
--           mscLecIlsForwarder,
--           mscLecRowStatus,
--           mscLecConnRowStatus,
--           mscLecControlFramesOut,
--           mscLecStorageType,
--           mscLecLeArpRowStatus,
--           mscLecControlFramesIn }
-- STATUS  mandatory
-- DESCRIPTION
--   "A list of all current accessible leaf objects."

laneClientGroup OBJECT IDENTIFIER ::= { laneClientMIB 1 }
laneClientGroupCA OBJECT IDENTIFIER ::= { laneClientGroup 1 }
laneClientGroupCA02 OBJECT IDENTIFIER ::= { laneClientGroupCA 3 }
laneClientGroupCA02A OBJECT IDENTIFIER ::= { laneClientGroupCA02 2 }



-- Agent-Capabilities Statement:

-- PRODUCT-RELEASE "MscPassport Release 1.2 LaneClient."
-- STATUS          mandatory
-- DESCRIPTION     "Carrier Passport LaneClient MIB: MIB Version CA02A,
--                  Software Version CA02S9C."
-- SUPPORTS        Nortel-MsCarrier-MscPassport-LaneClientMIB
--    INCLUDES     { laneClientGroupCA02A }

laneClientCapabilities OBJECT IDENTIFIER ::= { laneClientMIB 3 }
laneClientCapabilitiesCA OBJECT IDENTIFIER ::= { laneClientCapabilities 1 }
laneClientCapabilitiesCA02 OBJECT IDENTIFIER ::= { laneClientCapabilitiesCA 3 }
laneClientCapabilitiesCA02A OBJECT IDENTIFIER ::= { laneClientCapabilitiesCA02 2 }





END
