--			Ascend miboc3atmnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBOC3ATMNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    miboc3AtmNetworkProfile  OBJECT IDENTIFIER ::= { configuration 11}

	-- The miboc3AtmNetworkProfile table
	--
	-- This table contains parameters for the miboc3AtmNetworkProfile profile
	--

    miboc3AtmNetworkProfileTable	OBJECT-TYPE
	SYNTAX		SEQUENCE OF Miboc3AtmNetworkProfileEntry
	ACCESS		not-accessible
	STATUS		mandatory
	DESCRIPTION	"A list of miboc3AtmNetworkProfile profile entries."
	::= { miboc3AtmNetworkProfile 1 }

    miboc3AtmNetworkProfileEntry	OBJECT-TYPE
	SYNTAX		Miboc3AtmNetworkProfileEntry
	ACCESS		not-accessible
	STATUS		mandatory
	DESCRIPTION	"A miboc3AtmNetworkProfile entry containing objects that
			 maps to the parameters of miboc3AtmNetworkProfile profile."
	INDEX		{ oc3AtmNetworkProfile-Shelf-o, oc3AtmNetworkProfile-Slot-o, oc3AtmNetworkProfile-Item-o }
	::= { miboc3AtmNetworkProfileTable 1 }

    Miboc3AtmNetworkProfileEntry ::=
	SEQUENCE {
	    oc3AtmNetworkProfile-Shelf-o
		INTEGER,
	    oc3AtmNetworkProfile-Slot-o
		INTEGER,
	    oc3AtmNetworkProfile-Item-o
		INTEGER,
	    oc3AtmNetworkProfile-Name
		DisplayString,
	    oc3AtmNetworkProfile-PhysicalAddress-Shelf
		INTEGER,
	    oc3AtmNetworkProfile-PhysicalAddress-Slot
		INTEGER,
	    oc3AtmNetworkProfile-PhysicalAddress-ItemNumber
		INTEGER,
	    oc3AtmNetworkProfile-Enabled
		INTEGER,
	    oc3AtmNetworkProfile-SparePhysicalAddress-Shelf
		INTEGER,
	    oc3AtmNetworkProfile-SparePhysicalAddress-Slot
		INTEGER,
	    oc3AtmNetworkProfile-SparePhysicalAddress-ItemNumber
		INTEGER,
	    oc3AtmNetworkProfile-SparingMode
		INTEGER,
	    oc3AtmNetworkProfile-ProfileNumber
		INTEGER,
	    oc3AtmNetworkProfile-IgnoreLineup
		INTEGER,
	    oc3AtmNetworkProfile-ApsConfigName
		DisplayString,
	    oc3AtmNetworkProfile-LineConfig-TrunkGroup
		INTEGER,
	    oc3AtmNetworkProfile-LineConfig-NailedGroup
		INTEGER,
	    oc3AtmNetworkProfile-LineConfig-Loopback
		INTEGER,
	    oc3AtmNetworkProfile-LineConfig-FramerMode
		INTEGER,
	    oc3AtmNetworkProfile-LineConfig-FramerRate
		INTEGER,
	    oc3AtmNetworkProfile-LineConfig-RxDescrambleDisabled
		INTEGER,
	    oc3AtmNetworkProfile-LineConfig-TxScrambleDisabled
		INTEGER,
	    oc3AtmNetworkProfile-LineConfig-RxCellPayloadDescrambleDisabled
		INTEGER,
	    oc3AtmNetworkProfile-LineConfig-TxCellPayloadScrambleDisabled
		INTEGER,
	    oc3AtmNetworkProfile-LineConfig-LoopTiming
		INTEGER,
	    oc3AtmNetworkProfile-LineConfig-VpiVciRange
		INTEGER,
	    oc3AtmNetworkProfile-LineConfig-ClockSource
		INTEGER,
	    oc3AtmNetworkProfile-LineConfig-ClockPriority
		INTEGER,
	    oc3AtmNetworkProfile-Action-o
		INTEGER
	}

    oc3AtmNetworkProfile-Shelf-o	OBJECT-TYPE
	SYNTAX	INTEGER
	ACCESS	read-only
	STATUS	mandatory
	DESCRIPTION	""
	::= { miboc3AtmNetworkProfileEntry 1 }

    oc3AtmNetworkProfile-Slot-o	OBJECT-TYPE
	SYNTAX	INTEGER
	ACCESS	read-only
	STATUS	mandatory
	DESCRIPTION	""
	::= { miboc3AtmNetworkProfileEntry 2 }

    oc3AtmNetworkProfile-Item-o	OBJECT-TYPE
	SYNTAX	INTEGER
	ACCESS	read-only
	STATUS	mandatory
	DESCRIPTION	""
	::= { miboc3AtmNetworkProfileEntry 3 }

    oc3AtmNetworkProfile-Name	OBJECT-TYPE
	SYNTAX	DisplayString
	ACCESS	read-write
	STATUS	mandatory
	DESCRIPTION	"For future use. The current design does not use the name field but instead references Oc3Atm lines by the physical address; we may in the future support referencing Oc3Atm lines by name as well as by address. The name consists of a null terminated ascii string supplied by the user; it defaults to the ascii form of the Oc3Atm line physical address."
	::= { miboc3AtmNetworkProfileEntry 4 }

    oc3AtmNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { miboc3AtmNetworkProfileEntry 5 }

    oc3AtmNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { miboc3AtmNetworkProfileEntry 6 }

    oc3AtmNetworkProfile-PhysicalAddress-ItemNumber	OBJECT-TYPE
	SYNTAX	INTEGER
	ACCESS	read-write
	STATUS	mandatory
	DESCRIPTION	"A number that specifies an addressable entity within the context of shelf and slot."
	::= { miboc3AtmNetworkProfileEntry 7 }

    oc3AtmNetworkProfile-Enabled	OBJECT-TYPE
	SYNTAX	INTEGER {
		    no (1),
		    yes (2)
		}
	ACCESS	read-write
	STATUS	mandatory
	DESCRIPTION	"TRUE if the line is enabled, otherwise FALSE."
	::= { miboc3AtmNetworkProfileEntry 8 }

    oc3AtmNetworkProfile-SparePhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { miboc3AtmNetworkProfileEntry 9 }

    oc3AtmNetworkProfile-SparePhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { miboc3AtmNetworkProfileEntry 10 }

    oc3AtmNetworkProfile-SparePhysicalAddress-ItemNumber	OBJECT-TYPE
	SYNTAX	INTEGER
	ACCESS	read-write
	STATUS	mandatory
	DESCRIPTION	"A number that specifies an addressable entity within the context of shelf and slot."
	::= { miboc3AtmNetworkProfileEntry 11 }

    oc3AtmNetworkProfile-SparingMode	OBJECT-TYPE
	SYNTAX	INTEGER {
		    inactive (1),
		    manual (2),
		    automatic (3)
		}
	ACCESS	read-write
	STATUS	mandatory
	DESCRIPTION	"Trunk port sparing operational mode for this port."
	::= { miboc3AtmNetworkProfileEntry 12 }

    oc3AtmNetworkProfile-ProfileNumber	OBJECT-TYPE
	SYNTAX	INTEGER
	ACCESS	read-write
	STATUS	mandatory
	DESCRIPTION	"For potential backwards compatibility. The current design consists of one line profile numbered 0."
	::= { miboc3AtmNetworkProfileEntry 13 }

    oc3AtmNetworkProfile-IgnoreLineup	OBJECT-TYPE
	SYNTAX	INTEGER {
		    systemDefined (1),
		    no (2),
		    yes (3)
		}
	ACCESS	read-write
	STATUS	mandatory
	DESCRIPTION	"Ignore line up value for this port."
	::= { miboc3AtmNetworkProfileEntry 31 }

    oc3AtmNetworkProfile-ApsConfigName	OBJECT-TYPE
	SYNTAX	DisplayString
	ACCESS	read-write
	STATUS	mandatory
	DESCRIPTION	"APS Config Profile name, specifies APS configuration profile that defines a protection group for this channel."
	::= { miboc3AtmNetworkProfileEntry 32 }

    oc3AtmNetworkProfile-LineConfig-TrunkGroup	OBJECT-TYPE
	SYNTAX	INTEGER
	ACCESS	read-write
	STATUS	mandatory
	DESCRIPTION	"The trunk group to which this line is assigned. 0 means this line is not part of a trunk group."
	::= { miboc3AtmNetworkProfileEntry 14 }

    oc3AtmNetworkProfile-LineConfig-NailedGroup	OBJECT-TYPE
	SYNTAX	INTEGER
	ACCESS	read-write
	STATUS	mandatory
	DESCRIPTION	"A number that identifies the set of lines that makes up a nailed group. 0 means this line is not part of a nailed group."
	::= { miboc3AtmNetworkProfileEntry 15 }

    oc3AtmNetworkProfile-LineConfig-Loopback	OBJECT-TYPE
	SYNTAX	INTEGER {
		    noLoopback (1),
		    facilityLoopback (2),
		    localLoopback (3),
		    atmLayerLoopback (4)
		}
	ACCESS	read-write
	STATUS	mandatory
	DESCRIPTION	"Loopback mode."
	::= { miboc3AtmNetworkProfileEntry 19 }

    oc3AtmNetworkProfile-LineConfig-FramerMode	OBJECT-TYPE
	SYNTAX	INTEGER {
		    sonet (1),
		    sdh (2)
		}
	ACCESS	read-write
	STATUS	mandatory
	DESCRIPTION	"The Sonet Framer mode."
	::= { miboc3AtmNetworkProfileEntry 30 }

    oc3AtmNetworkProfile-LineConfig-FramerRate	OBJECT-TYPE
	SYNTAX	INTEGER {
		    sTS3c (1),
		    sTS1 (2)
		}
	ACCESS	read-write
	STATUS	mandatory
	DESCRIPTION	"The OC3 ATM framer rate."
	::= { miboc3AtmNetworkProfileEntry 20 }

    oc3AtmNetworkProfile-LineConfig-RxDescrambleDisabled	OBJECT-TYPE
	SYNTAX	INTEGER {
		    no (1),
		    yes (2)
		}
	ACCESS	read-write
	STATUS	mandatory
	DESCRIPTION	"TRUE if the RX side descrambling is disabled, otherwise FALSE."
	::= { miboc3AtmNetworkProfileEntry 21 }

    oc3AtmNetworkProfile-LineConfig-TxScrambleDisabled	OBJECT-TYPE
	SYNTAX	INTEGER {
		    no (1),
		    yes (2)
		}
	ACCESS	read-write
	STATUS	mandatory
	DESCRIPTION	"TRUE if the TX side scrambling is disabled, otherwise FALSE."
	::= { miboc3AtmNetworkProfileEntry 22 }

    oc3AtmNetworkProfile-LineConfig-RxCellPayloadDescrambleDisabled	OBJECT-TYPE
	SYNTAX	INTEGER {
		    no (1),
		    yes (2)
		}
	ACCESS	read-write
	STATUS	mandatory
	DESCRIPTION	"TRUE if the RX side cell payload descrambling is disabled, otherwise FALSE."
	::= { miboc3AtmNetworkProfileEntry 23 }

    oc3AtmNetworkProfile-LineConfig-TxCellPayloadScrambleDisabled	OBJECT-TYPE
	SYNTAX	INTEGER {
		    no (1),
		    yes (2)
		}
	ACCESS	read-write
	STATUS	mandatory
	DESCRIPTION	"TRUE if the TX side cell payload scrambling is disabled, otherwise FALSE."
	::= { miboc3AtmNetworkProfileEntry 24 }

    oc3AtmNetworkProfile-LineConfig-LoopTiming	OBJECT-TYPE
	SYNTAX	INTEGER {
		    no (1),
		    yes (2)
		}
	ACCESS	read-write
	STATUS	mandatory
	DESCRIPTION	"TRUE if the TX timing is derived from the receiver inputs. FALSE if the TX timing is derived from reference clock."
	::= { miboc3AtmNetworkProfileEntry 25 }

    oc3AtmNetworkProfile-LineConfig-VpiVciRange	OBJECT-TYPE
	SYNTAX	INTEGER {
		    n-01-3232767 (1),
		    n-03-3216383 (2),
		    n-07-328191 (3),
		    n-015-324095 (4),
		    n-031-322047 (5),
		    n-063-321023 (6),
		    n-0127-32511 (7),
		    n-0255-32255 (8),
		    vpi0255Vci32255 (9),
		    vpi0255Vci32511 (10),
		    vpi0255Vci321023 (11),
		    vpi0255Vci322047 (12),
		    vpi0255Vci324095 (13),
		    vpi0255Vci328191 (14),
		    vpi0255Vci3216383 (15)
		}
	ACCESS	read-write
	STATUS	mandatory
	DESCRIPTION	"The OC3 ATM valid VPI/VCI value range."
	::= { miboc3AtmNetworkProfileEntry 26 }

    oc3AtmNetworkProfile-LineConfig-ClockSource	OBJECT-TYPE
	SYNTAX	INTEGER {
		    eligible (1),
		    notEligible (2)
		}
	ACCESS	read-write
	STATUS	mandatory
	DESCRIPTION	"Determine whether the 8KHz clock from the OC3-ATM board is eligible to be used as the system-wide TDM clock source."
	::= { miboc3AtmNetworkProfileEntry 27 }

    oc3AtmNetworkProfile-LineConfig-ClockPriority	OBJECT-TYPE
	SYNTAX	INTEGER {
		    highPriority (2),
		    middlePriority (3),
		    lowPriority (4)
		}
	ACCESS	read-write
	STATUS	mandatory
	DESCRIPTION	"Clock priority assigned to the OC3-ATM line. Used to select a particular OC3 line as clock source."
	::= { miboc3AtmNetworkProfileEntry 28 }

    oc3AtmNetworkProfile-Action-o	OBJECT-TYPE
	SYNTAX	INTEGER {
		    noAction (1),
		    createProfile (2),
		    deleteProfile (3)
		}
	ACCESS	read-write
	STATUS	mandatory
	DESCRIPTION	""
	::= { miboc3AtmNetworkProfileEntry 29 }


	-- The miboc3AtmNetworkProfile__line_config__incomingVCCs table
	--
	-- This table contains parameters for the miboc3AtmNetworkProfile__line_config__incomingVCCs profile
	--

    miboc3AtmNetworkProfile-LineConfig-IncomingVCCsTable	OBJECT-TYPE
	SYNTAX		SEQUENCE OF Miboc3AtmNetworkProfile-LineConfig-IncomingVCCsEntry
	ACCESS		not-accessible
	STATUS		mandatory
	DESCRIPTION	"A list of miboc3AtmNetworkProfile__line_config__incomingVCCs profile entries."
	::= { miboc3AtmNetworkProfile 2 }

    miboc3AtmNetworkProfile-LineConfig-IncomingVCCsEntry	OBJECT-TYPE
	SYNTAX		Miboc3AtmNetworkProfile-LineConfig-IncomingVCCsEntry
	ACCESS		not-accessible
	STATUS		mandatory
	DESCRIPTION	"A miboc3AtmNetworkProfile__line_config__incomingVCCs entry containing objects that
			 maps to the parameters of miboc3AtmNetworkProfile__line_config__incomingVCCs profile."
	INDEX		{ oc3AtmNetworkProfile-LineConfig-IncomingVCCs-Shelf-o, oc3AtmNetworkProfile-LineConfig-IncomingVCCs-Slot-o, oc3AtmNetworkProfile-LineConfig-IncomingVCCs-Item-o, oc3AtmNetworkProfile-LineConfig-IncomingVCCs-Index-o }
	::= { miboc3AtmNetworkProfile-LineConfig-IncomingVCCsTable 1 }

    Miboc3AtmNetworkProfile-LineConfig-IncomingVCCsEntry ::=
	SEQUENCE {
	    oc3AtmNetworkProfile-LineConfig-IncomingVCCs-Shelf-o
		INTEGER,
	    oc3AtmNetworkProfile-LineConfig-IncomingVCCs-Slot-o
		INTEGER,
	    oc3AtmNetworkProfile-LineConfig-IncomingVCCs-Item-o
		INTEGER,
	    oc3AtmNetworkProfile-LineConfig-IncomingVCCs-Index-o
		INTEGER,
	    oc3AtmNetworkProfile-LineConfig-IncomingVCCs-Enabled
		INTEGER,
	    oc3AtmNetworkProfile-LineConfig-IncomingVCCs-Vpi
		INTEGER,
	    oc3AtmNetworkProfile-LineConfig-IncomingVCCs-StartVci
		INTEGER,
	    oc3AtmNetworkProfile-LineConfig-IncomingVCCs-EndVci
		INTEGER
	}

    oc3AtmNetworkProfile-LineConfig-IncomingVCCs-Shelf-o	OBJECT-TYPE
	SYNTAX	INTEGER
	ACCESS	read-only
	STATUS	mandatory
	DESCRIPTION	""
	::= { miboc3AtmNetworkProfile-LineConfig-IncomingVCCsEntry 1 }

    oc3AtmNetworkProfile-LineConfig-IncomingVCCs-Slot-o	OBJECT-TYPE
	SYNTAX	INTEGER
	ACCESS	read-only
	STATUS	mandatory
	DESCRIPTION	""
	::= { miboc3AtmNetworkProfile-LineConfig-IncomingVCCsEntry 2 }

    oc3AtmNetworkProfile-LineConfig-IncomingVCCs-Item-o	OBJECT-TYPE
	SYNTAX	INTEGER
	ACCESS	read-only
	STATUS	mandatory
	DESCRIPTION	""
	::= { miboc3AtmNetworkProfile-LineConfig-IncomingVCCsEntry 3 }

    oc3AtmNetworkProfile-LineConfig-IncomingVCCs-Index-o	OBJECT-TYPE
	SYNTAX	INTEGER
	ACCESS	read-only
	STATUS	mandatory
	DESCRIPTION	""
	::= { miboc3AtmNetworkProfile-LineConfig-IncomingVCCsEntry 4 }

    oc3AtmNetworkProfile-LineConfig-IncomingVCCs-Enabled	OBJECT-TYPE
	SYNTAX	INTEGER {
		    no (1),
		    yes (2)
		}
	ACCESS	read-write
	STATUS	mandatory
	DESCRIPTION	"TRUE if the item is enabled, otherwise FALSE."
	::= { miboc3AtmNetworkProfile-LineConfig-IncomingVCCsEntry 5 }

    oc3AtmNetworkProfile-LineConfig-IncomingVCCs-Vpi	OBJECT-TYPE
	SYNTAX	INTEGER
	ACCESS	read-write
	STATUS	mandatory
	DESCRIPTION	"A number that identifies the Virtual Path Identifier of this item."
	::= { miboc3AtmNetworkProfile-LineConfig-IncomingVCCsEntry 6 }

    oc3AtmNetworkProfile-LineConfig-IncomingVCCs-StartVci	OBJECT-TYPE
	SYNTAX	INTEGER
	ACCESS	read-write
	STATUS	mandatory
	DESCRIPTION	"A number that identifies the starting Virtual Channel Identifier of this item."
	::= { miboc3AtmNetworkProfile-LineConfig-IncomingVCCsEntry 7 }

    oc3AtmNetworkProfile-LineConfig-IncomingVCCs-EndVci	OBJECT-TYPE
	SYNTAX	INTEGER
	ACCESS	read-write
	STATUS	mandatory
	DESCRIPTION	"A number that identifies the ending Virtual Channel Identifier of this item."
	::= { miboc3AtmNetworkProfile-LineConfig-IncomingVCCsEntry 8 }


	-- The miboc3AtmNetworkProfile__line_config__traffic_shapers table
	--
	-- This table contains parameters for the miboc3AtmNetworkProfile__line_config__traffic_shapers profile
	--

    miboc3AtmNetworkProfile-LineConfig-TrafficShapersTable	OBJECT-TYPE
	SYNTAX		SEQUENCE OF Miboc3AtmNetworkProfile-LineConfig-TrafficShapersEntry
	ACCESS		not-accessible
	STATUS		mandatory
	DESCRIPTION	"A list of miboc3AtmNetworkProfile__line_config__traffic_shapers profile entries."
	::= { miboc3AtmNetworkProfile 3 }

    miboc3AtmNetworkProfile-LineConfig-TrafficShapersEntry	OBJECT-TYPE
	SYNTAX		Miboc3AtmNetworkProfile-LineConfig-TrafficShapersEntry
	ACCESS		not-accessible
	STATUS		mandatory
	DESCRIPTION	"A miboc3AtmNetworkProfile__line_config__traffic_shapers entry containing objects that
			 maps to the parameters of miboc3AtmNetworkProfile__line_config__traffic_shapers profile."
	INDEX		{ oc3AtmNetworkProfile-LineConfig-TrafficShapers-Shelf-o, oc3AtmNetworkProfile-LineConfig-TrafficShapers-Slot-o, oc3AtmNetworkProfile-LineConfig-TrafficShapers-Item-o, oc3AtmNetworkProfile-LineConfig-TrafficShapers-Index-o }
	::= { miboc3AtmNetworkProfile-LineConfig-TrafficShapersTable 1 }

    Miboc3AtmNetworkProfile-LineConfig-TrafficShapersEntry ::=
	SEQUENCE {
	    oc3AtmNetworkProfile-LineConfig-TrafficShapers-Shelf-o
		INTEGER,
	    oc3AtmNetworkProfile-LineConfig-TrafficShapers-Slot-o
		INTEGER,
	    oc3AtmNetworkProfile-LineConfig-TrafficShapers-Item-o
		INTEGER,
	    oc3AtmNetworkProfile-LineConfig-TrafficShapers-Index-o
		INTEGER,
	    oc3AtmNetworkProfile-LineConfig-TrafficShapers-Enabled
		INTEGER,
	    oc3AtmNetworkProfile-LineConfig-TrafficShapers-BitRate
		INTEGER,
	    oc3AtmNetworkProfile-LineConfig-TrafficShapers-PeakRate
		INTEGER,
	    oc3AtmNetworkProfile-LineConfig-TrafficShapers-MaxBurstSize
		INTEGER,
	    oc3AtmNetworkProfile-LineConfig-TrafficShapers-Aggregate
		INTEGER,
	    oc3AtmNetworkProfile-LineConfig-TrafficShapers-Priority
		INTEGER
	}

    oc3AtmNetworkProfile-LineConfig-TrafficShapers-Shelf-o	OBJECT-TYPE
	SYNTAX	INTEGER
	ACCESS	read-only
	STATUS	mandatory
	DESCRIPTION	""
	::= { miboc3AtmNetworkProfile-LineConfig-TrafficShapersEntry 1 }

    oc3AtmNetworkProfile-LineConfig-TrafficShapers-Slot-o	OBJECT-TYPE
	SYNTAX	INTEGER
	ACCESS	read-only
	STATUS	mandatory
	DESCRIPTION	""
	::= { miboc3AtmNetworkProfile-LineConfig-TrafficShapersEntry 2 }

    oc3AtmNetworkProfile-LineConfig-TrafficShapers-Item-o	OBJECT-TYPE
	SYNTAX	INTEGER
	ACCESS	read-only
	STATUS	mandatory
	DESCRIPTION	""
	::= { miboc3AtmNetworkProfile-LineConfig-TrafficShapersEntry 3 }

    oc3AtmNetworkProfile-LineConfig-TrafficShapers-Index-o	OBJECT-TYPE
	SYNTAX	INTEGER
	ACCESS	read-only
	STATUS	mandatory
	DESCRIPTION	""
	::= { miboc3AtmNetworkProfile-LineConfig-TrafficShapersEntry 4 }

    oc3AtmNetworkProfile-LineConfig-TrafficShapers-Enabled	OBJECT-TYPE
	SYNTAX	INTEGER {
		    no (1),
		    yes (2)
		}
	ACCESS	read-write
	STATUS	mandatory
	DESCRIPTION	"TRUE if the shaper is enabled, otherwise FALSE."
	::= { miboc3AtmNetworkProfile-LineConfig-TrafficShapersEntry 5 }

    oc3AtmNetworkProfile-LineConfig-TrafficShapers-BitRate	OBJECT-TYPE
	SYNTAX	INTEGER
	ACCESS	read-write
	STATUS	mandatory
	DESCRIPTION	"What is the sustained rate in Kilobits per second that can be transmitted by the VC(s) when using this shaper. Limited by the framer mode and the interface type."
	::= { miboc3AtmNetworkProfile-LineConfig-TrafficShapersEntry 6 }

    oc3AtmNetworkProfile-LineConfig-TrafficShapers-PeakRate	OBJECT-TYPE
	SYNTAX	INTEGER
	ACCESS	read-write
	STATUS	mandatory
	DESCRIPTION	"What is the peak rate in Kilobits per second that can be transmitted by the VC(s) when using this shaper. Limited by the framer mode and the interface type."
	::= { miboc3AtmNetworkProfile-LineConfig-TrafficShapersEntry 7 }

    oc3AtmNetworkProfile-LineConfig-TrafficShapers-MaxBurstSize	OBJECT-TYPE
	SYNTAX	INTEGER
	ACCESS	read-write
	STATUS	mandatory
	DESCRIPTION	"What is the maximum burst size in cell that can be transmitted during the peak rate by the VC(s) when using this shaper."
	::= { miboc3AtmNetworkProfile-LineConfig-TrafficShapersEntry 8 }

    oc3AtmNetworkProfile-LineConfig-TrafficShapers-Aggregate	OBJECT-TYPE
	SYNTAX	INTEGER {
		    no (1),
		    yes (2)
		}
	ACCESS	read-write
	STATUS	mandatory
	DESCRIPTION	"If FALSE each individual VC gets the bit rate that is assigned to this shaper. If TRUE the VCs share the bit rate that is assigned to this shaper equally."
	::= { miboc3AtmNetworkProfile-LineConfig-TrafficShapersEntry 9 }

    oc3AtmNetworkProfile-LineConfig-TrafficShapers-Priority	OBJECT-TYPE
	SYNTAX	INTEGER
	ACCESS	read-write
	STATUS	mandatory
	DESCRIPTION	"A number that represent the prioriy of the shaper in respect to other shapers. 0 is the highest priority and 15 is the lowest."
	::= { miboc3AtmNetworkProfile-LineConfig-TrafficShapersEntry 10 }


	-- The miboc3AtmNetworkProfile__line_config__vc_switching_vpi table
	--
	-- This table contains parameters for the miboc3AtmNetworkProfile__line_config__vc_switching_vpi profile
	--

    miboc3AtmNetworkProfile-LineConfig-VcSwitchingVpiTable	OBJECT-TYPE
	SYNTAX		SEQUENCE OF Miboc3AtmNetworkProfile-LineConfig-VcSwitchingVpiEntry
	ACCESS		not-accessible
	STATUS		mandatory
	DESCRIPTION	"A list of miboc3AtmNetworkProfile__line_config__vc_switching_vpi profile entries."
	::= { miboc3AtmNetworkProfile 4 }

    miboc3AtmNetworkProfile-LineConfig-VcSwitchingVpiEntry	OBJECT-TYPE
	SYNTAX		Miboc3AtmNetworkProfile-LineConfig-VcSwitchingVpiEntry
	ACCESS		not-accessible
	STATUS		mandatory
	DESCRIPTION	"A miboc3AtmNetworkProfile__line_config__vc_switching_vpi entry containing objects that
			 maps to the parameters of miboc3AtmNetworkProfile__line_config__vc_switching_vpi profile."
	INDEX		{ oc3AtmNetworkProfile-LineConfig-VcSwitchingVpi-Shelf-o, oc3AtmNetworkProfile-LineConfig-VcSwitchingVpi-Slot-o, oc3AtmNetworkProfile-LineConfig-VcSwitchingVpi-Item-o, oc3AtmNetworkProfile-LineConfig-VcSwitchingVpi-Index-o }
	::= { miboc3AtmNetworkProfile-LineConfig-VcSwitchingVpiTable 1 }

    Miboc3AtmNetworkProfile-LineConfig-VcSwitchingVpiEntry ::=
	SEQUENCE {
	    oc3AtmNetworkProfile-LineConfig-VcSwitchingVpi-Shelf-o
		INTEGER,
	    oc3AtmNetworkProfile-LineConfig-VcSwitchingVpi-Slot-o
		INTEGER,
	    oc3AtmNetworkProfile-LineConfig-VcSwitchingVpi-Item-o
		INTEGER,
	    oc3AtmNetworkProfile-LineConfig-VcSwitchingVpi-Index-o
		INTEGER,
	    oc3AtmNetworkProfile-LineConfig-VcSwitchingVpi
		INTEGER
	}

    oc3AtmNetworkProfile-LineConfig-VcSwitchingVpi-Shelf-o	OBJECT-TYPE
	SYNTAX	INTEGER
	ACCESS	read-only
	STATUS	mandatory
	DESCRIPTION	""
	::= { miboc3AtmNetworkProfile-LineConfig-VcSwitchingVpiEntry 1 }

    oc3AtmNetworkProfile-LineConfig-VcSwitchingVpi-Slot-o	OBJECT-TYPE
	SYNTAX	INTEGER
	ACCESS	read-only
	STATUS	mandatory
	DESCRIPTION	""
	::= { miboc3AtmNetworkProfile-LineConfig-VcSwitchingVpiEntry 2 }

    oc3AtmNetworkProfile-LineConfig-VcSwitchingVpi-Item-o	OBJECT-TYPE
	SYNTAX	INTEGER
	ACCESS	read-only
	STATUS	mandatory
	DESCRIPTION	""
	::= { miboc3AtmNetworkProfile-LineConfig-VcSwitchingVpiEntry 3 }

    oc3AtmNetworkProfile-LineConfig-VcSwitchingVpi-Index-o	OBJECT-TYPE
	SYNTAX	INTEGER
	ACCESS	read-only
	STATUS	mandatory
	DESCRIPTION	""
	::= { miboc3AtmNetworkProfile-LineConfig-VcSwitchingVpiEntry 4 }

    oc3AtmNetworkProfile-LineConfig-VcSwitchingVpi	OBJECT-TYPE
	SYNTAX	INTEGER
	ACCESS	read-write
	STATUS	mandatory
	DESCRIPTION	"VPI(s) to be used for the VC switching (VCC). It should always contain VPI 0 for VC switching. All VC switching VPI have similar valid VCI range which is determined by 'vpi-vci-range' attribute. Rest of the VPIs will be used for the VP switching. The user needs to understand that adding a VPI in a list of VC switching VPI will allocate more VCCs for this port. The user needs to make sure that VCCs for the other ports have been reduced to accommodate increase in VCC for this port because system can support only 32k VCCs on all trunk ports combined. If vci-range is 4k and VPI 0 is the only VPI doing VC switching for this port than this port occupies 4k VCCs. If user adds VPI 1 to the list of VPIs to do VCC then total 8k VCCs are occupied for this port. System will reject the configuration if user tries to use more than 32k VCCs for all trunk ports combined. ANY CHANGES IN A LIST OF VPIs WILL BE EFFECTIVE IMMEDIATLY. IN ORDER TO DO THAT ALL CONNECTIONS WITHIN THIS SYSTEM WILL BE DROPPED AND REESTABLISHED."
	::= { miboc3AtmNetworkProfile-LineConfig-VcSwitchingVpiEntry 5 }

END
