CIG-SERVERS-MIB DEFINITIONS ::= BEGIN
   IMPORTS
     OBJECT-GROUP, NOTIFICATION-GROUP, MODULE-COMPLIANCE
         FROM SNMPv2-CONF
     Integer32, Unsigned32, enterprises, Gauge32, Counter32, OBJECT-TYPE, 
      MODULE-IDENTITY, NOTIFICATION-TYPE
         FROM SNMPv2-SMI
      RowStatus, TEXTUAL-CONVENTION, TruthValue, DateAndTime, TimeInterval, DisplayString
         FROM SNMPv2-TC      
      IpAddress
         FROM RFC1155-SMI;
      


     cigServers MODULE-IDENTITY
       LAST-UPDATED "200405180701Z"   
     ORGANIZATION
                       "Avaya"
     CONTACT-INFO
     "
       Avaya Customer Services
       Postal: Avaya, Inc.
       211 Mt Airy Rd.
       Basking Ridge, NJ 07920
       USA
       Tel:	+1 908 953 6000
       WWW: 	http://www.avaya.com
     "
     DESCRIPTION
     "              
     This module defines an interface configure Servers as Tftp and Dhcp servers.
     Copyright notice:
     
     This AVAYA SNMP Management Information Base Specification (Specification) embodies
     AVAYA confidential and Proprietary intellectual property.  AVAYA retains all Title
     and ownership in the Specification, including any revisionsIt is AVAYA's intent to
     encourage the widespread use of this Specification in connection with the management
     of AVAYA products. AVAYA grants vendors, end-users, and other interested parties a
     non-exclusive license to use this Specification in connection with the management 
     of AVAYA products.This Specification is supplied 'as is', and AVAYA makes no warranty,
     either express or implied, as to the use, operation, condition, or performance of the
     Specification.     
     "
           ::= { lsg 16  } 



-- Version 200412230908Z  
-- Adding cigTftpServersDownloadTimeouts to Statistics for cases where are timeouts during 
-- download operations.                                   

-- Version 200409280717Z  
-- Adding TFTP server Traps and statistics.                                    

-- Version 200408081441Z  
-- Updating the length of cigDhcpServersPoolName to be 16 Bytes only instead of 32 Bytes.
-- This is VxWorks DHCP server limitations.                                      
-- Updating the description of cigDhcpServersPoolDefaultGateway, cigDhcpServersPoolDnsServer
-- and cigDhcpServersOptionType to be array of IP addresses without "," delimiters but with " "
-- delimiters.

-- Version 200408081441Z  
-- Changing the status of the leafs under cigDhcpServersNotificationPacket to 
-- accessible-for-notify instead of read-only


-- Version 200407261528Z  
-- cigDhcpServersVendorSpecificOptionString was changed to 
-- cigDhcpServersVendorSpecificClassIdentifier which reflects option 60 (Vendor specific
-- class identifier).
-- Adding note to cigDhcpServersPoolMode about Active/Inactive terms instead of Ensable/Disable.
-- Adding note to cigDhcpServersPoolStartIPAddr and cigDhcpServersPoolEndIPAddr that the users
-- are not allowed to create pools with overlapped IP addresses.
-- Adding note to cigDhcpServersPoolClientID that ClientIdentifier can only configured when 
-- cigDhcpServersPoolStartIPAddr is equal to cigDhcpServersPoolEndIPAddr.
-- Adding note to cigDhcpServersPoolEndIPAddr and cigDhcpServersPoolStartIPAddr
-- that StartIPaddress can be configured different than EndIPAddress only when Client 
-- identifier is not set.
-- Adding note to cigDhcpServersPoolMode that the user can not activate pool 
-- with start-ip-addr or end-ip-addr == 0.0.0.0. 

-- Version 200407260745Z  
-- Adding two MIB items cigDhcpServersPingDetectionMode and cigDhcpServersPingDetectionTimeout
-- for Disable/Enable the ping packet sending by the DHCP server just before allocating new IP
-- address in order to detect conflicts. The Timeout can be used differently according the Hosts 
-- connection to the DHCP server on the LAN/WAN.
-- Adding remarks to cigDhcpServersPoolStartIPAddr and cigDhcpServersPoolEndIPAddr of how changing
-- these parameters when user wants to change the IP address range to distinctive range (larger then
-- up to the free number of IP addresses - in the G350/G250 the number is maximum 256 IPs).

-- Version 200407180808Z  
-- Updating cigDhcpServersPoolStopIPAddr to be cigDhcpServersPoolEndIPAddr.
-- cigDhcpServersPoolLeaseTime has no limit to any minimum threshold (1800 seconds). 

-- Version 200407061017Z  
-- Updating the default of cigDhcpServersOptionName to be 'Option #Option Number' instead of
-- 'DHCP Option #Option Number'		
-- Updating the default of cigDhcpServersVendorSpecificOptionName to 
-- 'Vendor Specififc Option #Index Number' instead of 'Dhcp Vendor Specific Option #'
           
-- Version 200406290951Z  
-- Updating the description of cigDhcpServersNotificationConflictDetectionMethod and
-- cigDhcpServersNotificationPoolNetwork

-- Version 200406281754Z        
-- Updating the default values of cigDhcpServersOptionType and
-- cigDhcpServersVendorSpecificOptionType to be hex instead of
-- hexString
-- Removing cigDhcpServersTrapMode - Using General Trap manager MIB.

-- Version 200406271210Z        
-- Changing the length of the Names to 31 as As ACL/QOS/PBR List names length.    
-- Changing the default of the lease to 8 days. MIN lease is 0.5 hours.    
-- Changing the length of cigDhcpServersPoolBootFile to 128Bytes.    
-- Changing the maximum length of cigDhcpServersPoolDefaultGateway and 
-- cigDhcpServersPoolDnsServer to 145B.  
-- Swapping the place of cigDhcpServersPoolServerName and cigDhcpServersPoolRowStatus.        
-- Changing the values of cigDhcpServersVendorSpecificOptionType and 
-- cigDhcpServersVendorSpecificOptionType to be ascii(1) and hex(2) instead of string(1) 
-- and hexString(2).  
-- Specifying the length of cigDhcpServersVendorSpecificOptionValue and 
-- cigDhcpServersOptionValue.

-- Version 200406201555Z        
-- cigDhcpServersVendorSpecificOptionType and cigDhcpServersOptionType explanation
-- was fixed to include hex string format: aa:bb:cc:dd:12:34:56 instead of
-- aabbccdd123456 as the CLI.    
-- cigDhcpServersNotificationClientHostName is in fact the Server configuration of 
-- option 12 - Host name and not the option 12 that client may send!.   
-- This parameter is not relevant in the cigDhcpServersServerNacksTrap and 
-- cigDhcpServersNoIpAddressLeft.

-- Version 200406161533Z        
-- Adding new Mib Item to cigDhcpServersClientConflictDetectionTrap 
-- the argument cigDhcpServersNotificationConflictDetectionMethod.
-- Adding new Trap cigDhcpServersNoIpAddressLeft to indicate no IP address
-- left for specific pool.      
-- Updating the explanation for cigDhcpServersPoolMode.  
-- Updating the default of cigDhcpServersPoolClientID.                         
-- Updating the default of cigDhcpServersPoolDefaultGateway.
-- Updating the default of cigDhcpServersPoolDnsServer.     
-- Adding cigDhcpServersNotificationClientHostName to the traps.

-- Version 200406070847Z        
-- Increasing number of pools to 32 instead of 20.
-- Adding new mib item cigDhcpServersPoolServerName to CigDhcpServersPoolEntry.


-- Version 200405301118Z        
-- Fixing Hagai reamrks to be compatible with embedded compiler.

-- Version 200405240719Z        
-- Adding cigDhcpServersResetStatCounters.

-- Version 200405240530Z        
-- Removing the Traps cigDhcpServersClientReleaseTrap and
-- cigDhcpServersServerAcksTrap. They represent normal operation. 
-- Therefore they will be added to SysLog only.
-- Removing cigDhcpServersNotificationMessage.
-- Adding defaults to all Mib Items.

-- Version 200405230000Z        
-- 	Adding Row statuses to the Pool and Vendor Specific Tables.
--	Adding DHCP Server Statistics
--  Adding DHCP Server Traps

-- Version 200405180000Z
--   Initial Version
 

avaya OBJECT IDENTIFIER ::= { enterprises 6889 }
       
mibs OBJECT IDENTIFIER ::= { avaya 2 }  

lsg  OBJECT IDENTIFIER ::= { mibs 1 }       

cigTftpServers OBJECT IDENTIFIER ::= { cigServers 1 }

cigDhcpServers OBJECT IDENTIFIER ::= { cigServers 2 }
                                                                     
cigTftpServersNotification OBJECT IDENTIFIER ::= { cigTftpServers 0 }  

cigTftpServersDownloadFailureTrap NOTIFICATION-TYPE
            OBJECTS { cigTftpServersNotificationClientIpAddr, cigTftpServersNotificationFilename, 
            cigTftpServersNotificationErrorString}
            STATUS current
            DESCRIPTION
                "Trap based on TFTP client failure to download file from gateway TFTP server.
                The Error code message strings are according RFC 1350:
                0 Not defined
                1 File not found.
                2 Access violation.
                3 Disk full or allocation exceeded.
                4 Illegal TFTP operation.
                5 Unknown transfer ID.
                6 File already exists.
                7 No such user."
            ::= { cigTftpServersNotification 1 }   
                                                                   
cigTftpServersUploadFailureTrap NOTIFICATION-TYPE
            OBJECTS { cigTftpServersNotificationClientIpAddr, cigTftpServersNotificationFilename, 
            cigTftpServersNotificationErrorString}
            STATUS current
            DESCRIPTION
                "Trap based on TFTP client failure to upload file to gateway TFTP server.
                The Error code message strings are according RFC 1350:
                0 Not defined
                1 File not found.
                2 Access violation.
                3 Disk full or allocation exceeded.
                4 Illegal TFTP operation.
                5 Unknown transfer ID.
                6 File already exists.
                7 No such user.
                please note that the gateway TFTP server prevents uploading files to the device
                using TFTP client, pnly downloading files from the device. The upload files to the 
                gateway TFTP server is by using LOAD-MIB."
            ::= { cigTftpServersNotification 2 } 

cigTftpServersGenConfig	OBJECT IDENTIFIER ::= { cigTftpServers 1 } 

cigTftpServersMode  OBJECT-TYPE
            SYNTAX TruthValue
            MAX-ACCESS read-write
            STATUS current
            DESCRIPTION
                "Enable Tftp Server in the device. Default = False (Disable)."
            DEFVAL { false }
            ::= { cigTftpServersGenConfig 1 }

cigTftpServersResetStatCounters  OBJECT-TYPE
            SYNTAX  INTEGER  {
        	reset (1) 
        	}
            MAX-ACCESS read-write
            STATUS current
            DESCRIPTION
                "reset (1) 	- Reset the TFTP Server Statistics.  
                 This object should be treated as write-only."
            ::= { cigTftpServersGenConfig 2 }

cigTftpServersMemoryAllocation	OBJECT IDENTIFIER ::= { cigTftpServers 2 } 

cigTftpServersTotalBytesUsedInNvram  OBJECT-TYPE
            SYNTAX Unsigned32
            MAX-ACCESS read-only
            STATUS current
            DESCRIPTION
                "Number of bytes used in nvram.  Default = 0."
            DEFVAL {0 }
            ::= { cigTftpServersMemoryAllocation 1 }
            
cigTftpServersTotalBytesCapacityInNvram  OBJECT-TYPE
            SYNTAX Unsigned32
            MAX-ACCESS read-only
            STATUS current
            DESCRIPTION
                "Number of bytes capacity in nvram.  Default = 131072."
            DEFVAL {131072 }
            ::= { cigTftpServersMemoryAllocation 2 }
            
cigTftpServersTotalBytesUsedInRam  OBJECT-TYPE
            SYNTAX Unsigned32
            MAX-ACCESS read-only
            STATUS current
            DESCRIPTION
                "Number of bytes used in ram.  Default = 0."
            DEFVAL {0 }
            ::= { cigTftpServersMemoryAllocation 3 }
            
cigTftpServersTotalBytesCapacityInRam  OBJECT-TYPE
            SYNTAX Unsigned32
            MAX-ACCESS read-only
            STATUS current
            DESCRIPTION
                "Number of bytes capacity in ram.  Default = 20971520."
            DEFVAL {20971520  }
            ::= { cigTftpServersMemoryAllocation 4 }

cigTftpServersGenStats	OBJECT IDENTIFIER ::= { cigTftpServers 3 } 

cigTftpServersSuccessfulDownloads  OBJECT-TYPE
            SYNTAX Unsigned32
            MAX-ACCESS read-only
            STATUS current
            DESCRIPTION
                "Number of tftp successful downloads.  Default = 0."
            DEFVAL {0 }
            ::= { cigTftpServersGenStats 1 }
         
cigTftpServersNotDefinedErrors OBJECT-TYPE
            SYNTAX Unsigned32
            MAX-ACCESS read-only
            STATUS current
            DESCRIPTION
                "Number of tftp errors not defined - Error code==0.  Default = 0."
            DEFVAL {0 }
            ::= { cigTftpServersGenStats 2 }

cigTftpServersFileNotFoundErrors  OBJECT-TYPE
            SYNTAX Unsigned32
            MAX-ACCESS read-only
            STATUS current
            DESCRIPTION
                "Number of tftp errors of file not found - Error code == 1.  Default = 0."
            DEFVAL {0 }
            ::= { cigTftpServersGenStats 3 }

cigTftpServersAccessViolationErrors  OBJECT-TYPE
            SYNTAX Unsigned32
            MAX-ACCESS read-only
            STATUS current
            DESCRIPTION
                "Number of tftp errors of Access violation - Error code  == 2.  Default = 0."
            DEFVAL {0 }
            ::= { cigTftpServersGenStats 4 }

cigTftpServersDiskFullErrors  OBJECT-TYPE
            SYNTAX Unsigned32
            MAX-ACCESS read-only
            STATUS current
            DESCRIPTION
                "Number of tftp errors of disk full - Error code == 3.  Default = 0."
            DEFVAL {0 }
            ::= { cigTftpServersGenStats 5 }

cigTftpServersIllegalTFTPOperationErrors  OBJECT-TYPE
            SYNTAX Unsigned32
            MAX-ACCESS read-only
            STATUS current
            DESCRIPTION
                "Number of tftp errors of illegal TFTP operation - Error code == 4.  Default = 0."
            DEFVAL {0 }
            ::= { cigTftpServersGenStats 6 }

cigTftpServersUnknownTransferIdErrors  OBJECT-TYPE
            SYNTAX Unsigned32
            MAX-ACCESS read-only
            STATUS current
            DESCRIPTION
                "Number of tftp errors of unknown transfer Id - Error code == 5.  Default = 0."
            DEFVAL {0 }
            ::= { cigTftpServersGenStats 7 }

cigTftpServersFileAlreadyExistsErrors  OBJECT-TYPE
            SYNTAX Unsigned32
            MAX-ACCESS read-only
            STATUS current
            DESCRIPTION
                "Number of tftp errors of file already exists - Error code == 6.  Default = 0."
            DEFVAL {0 }
            ::= { cigTftpServersGenStats 8 }

cigTftpServersNoSuchUserErrors  OBJECT-TYPE
            SYNTAX Unsigned32
            MAX-ACCESS read-only
            STATUS current
            DESCRIPTION
                "Number of tftp errors of no such user - Error code == 7.  Default = 0."
            DEFVAL {0 }
            ::= { cigTftpServersGenStats 9 }                                       
            
cigTftpServersDownloadTimeouts  OBJECT-TYPE
            SYNTAX Unsigned32
            MAX-ACCESS read-only
            STATUS current
            DESCRIPTION
                "Number of tftp downloads timeouts. Timeouts occurs when ACK packets from client
                to Server did not reach the server."
            DEFVAL {0 }
            ::= { cigTftpServersGenStats 10 }

cigTftpServersNotificationPacket	OBJECT IDENTIFIER ::= { cigTftpServers 4 } 

cigTftpServersNotificationClientIpAddr  OBJECT-TYPE
            SYNTAX IpAddress
            MAX-ACCESS accessible-for-notify
            STATUS current
            DESCRIPTION
                "The TFTP client IP address.  Default = 0.0.0.0"
            DEFVAL {'00000000'h }
            ::= { cigTftpServersNotificationPacket 1 }

cigTftpServersNotificationFilename  OBJECT-TYPE
            SYNTAX DisplayString (SIZE (0..63))
            MAX-ACCESS accessible-for-notify
            STATUS current
            DESCRIPTION
                "The filename that the TFTP client tried to upload/download.  Default = ''"
            DEFVAL {"" }
            ::= { cigTftpServersNotificationPacket 2 }

cigTftpServersNotificationErrorString  OBJECT-TYPE
            SYNTAX DisplayString (SIZE (0..63))
            MAX-ACCESS accessible-for-notify
            STATUS current
            DESCRIPTION
                "The error string relevant to the Error occured during the last upload/download
                operation.  Default = ''"
            DEFVAL {"" }
            ::= { cigTftpServersNotificationPacket 3 }
   
   
cigDhcpServersNotification OBJECT IDENTIFIER ::= { cigDhcpServers 0 }

        
cigDhcpServersClientConflictDetectionTrap NOTIFICATION-TYPE
            OBJECTS { cigDhcpServersNotificationIpAddr, cigDhcpServersNotificationClientHostName,
            cigDhcpServersNotificationClientIdentifier, 
            cigDhcpServersNotificationConflictDetectionMethod}
            STATUS current
            DESCRIPTION
                "DHCP IP address conflict detection. This trap is based on:                          
                1. DHCP server send Ping packets before allocating new IP address. 
                2. The Client Decline Packets after the client sent gratuitous Arp and get response."
            ::= { cigDhcpServersNotification 1 }   

cigDhcpServersServerNacksTrap NOTIFICATION-TYPE
            OBJECTS { cigDhcpServersNotificationIpAddr,
            cigDhcpServersNotificationClientIdentifier }
            STATUS current
            DESCRIPTION
                "Server refusal to extend lease or for other clients requests."
            ::= { cigDhcpServersNotification 2 } 

cigDhcpServersNoIpAddressLeft NOTIFICATION-TYPE
            OBJECTS { cigDhcpServersNotificationClientIdentifier,
            cigDhcpServersNotificationPoolNetwork }
            STATUS current
            DESCRIPTION
                "Notification for no IP address left for specific network."
            ::= { cigDhcpServersNotification 3 }            

--cigDhcpServersClientReleaseTrap NOTIFICATION-TYPE
--            OBJECTS { cigDhcpServersNotificationIpAddr, cigDhcpServersNotificationClientIdentifier, 
--            cigDhcpServersNotificationMessage }
--            STATUS current
--            DESCRIPTION
--                "Notification for release of IP address by specific client."
--            ::= { cigDhcpServersNotification 3 }            

--cigDhcpServersServerAcksTrap NOTIFICATION-TYPE
--            OBJECTS { cigDhcpServersNotificationIpAddr, cigDhcpServersNotificationClientIdentifier, 
--            cigDhcpServersNotificationMessage }
--            STATUS current
--            DESCRIPTION
--                "Server Acks for extending lease or allocating new address."
--            ::= { cigDhcpServersNotification 4 } 

cigDhcpServersGenConfig	OBJECT IDENTIFIER ::= { cigDhcpServers 1 } 

cigDhcpServersMode  OBJECT-TYPE
            SYNTAX TruthValue
            MAX-ACCESS read-write
            STATUS current
            DESCRIPTION
                "Enable Dhcp Server in the device.  Default = False (Disable)."
            DEFVAL { false }
            ::= { cigDhcpServersGenConfig 1 }

--cigDhcpServersTrapMode  OBJECT-TYPE
--            SYNTAX TruthValue
--            MAX-ACCESS read-write
--            STATUS current
--            DESCRIPTION
--                "Enable Dhcp Server Traps in the device.  Default = False (Disable)."
--            DEFVAL { false }
--            ::= { cigDhcpServersGenConfig 2 }

cigDhcpServersResetStatCounters  OBJECT-TYPE
            SYNTAX  INTEGER  {
        	reset (1) 
        	}
            MAX-ACCESS read-write
            STATUS current
            DESCRIPTION
                "reset (1) 	- Reset the DHCP Server Statistics.  
                 This object should be treated as write-only."
            ::= { cigDhcpServersGenConfig 2 }

cigDhcpServersPingDetectionMode  OBJECT-TYPE
            SYNTAX TruthValue
            MAX-ACCESS read-write
            STATUS current
            DESCRIPTION
                "Enable Dhcp Server sending one ping packet in order to detect IP address conflict.
                Default = False (Disable)."
            DEFVAL { false }
            ::= { cigDhcpServersGenConfig 3 }

cigDhcpServersPingDetectionTimeout  OBJECT-TYPE
        SYNTAX 	Unsigned32
        MAX-ACCESS read-write
        STATUS current
        DESCRIPTION
        "The timeout in milliseconds of the ping packet send by the DHCP server to detect IP address conflict
        before allocating new IP address. The user can lower this timeout in case the hosts that recieved
        IP addresses are on the LAN. Otherwise if the hosts are on the WAN side then the timeout shall be 
        higher the LAN.
        default 500 milliseconds"     
        DEFVAL { 500 }             
        ::= { cigDhcpServersGenConfig 4 }

cigDhcpServersPool	OBJECT IDENTIFIER ::= { cigDhcpServers 2 } 


cigDhcpServersPoolTable OBJECT-TYPE
	SYNTAX	   SEQUENCE OF CigDhcpServersPoolEntry
	MAX-ACCESS not-accessible
	STATUS	   current
	DESCRIPTION
	    "Dhcp Pool General configuration table"
	::= { cigDhcpServersPool 1 }
	
	cigDhcpServersPoolEntry OBJECT-TYPE
	SYNTAX	   CigDhcpServersPoolEntry
	MAX-ACCESS not-accessible
	STATUS	   current
	DESCRIPTION
	    "The pool general configuration table entry. "
	INDEX {
	     cigDhcpServersPoolIndex
	}
	::= { cigDhcpServersPoolTable 1 }

    CigDhcpServersPoolEntry ::= SEQUENCE {
      cigDhcpServersPoolIndex Integer32,
      cigDhcpServersPoolStartIPAddr IpAddress,
      cigDhcpServersPoolEndIPAddr IpAddress, 
      cigDhcpServersPoolMode  TruthValue,
      cigDhcpServersPoolName  DisplayString,
      cigDhcpServersPoolClientID OCTET STRING,
      cigDhcpServersPoolLeaseTime Unsigned32, 
      cigDhcpServersPoolBootFile DisplayString,
      cigDhcpServersPoolNextServer IpAddress,
      cigDhcpServersPoolSubnetMask IpAddress, 
      cigDhcpServersPoolDefaultGateway DisplayString,
      cigDhcpServersPoolDnsServer DisplayString,
      cigDhcpServersPoolDomainName DisplayString,  
      cigDhcpServersPoolServerName DisplayString,
      cigDhcpServersPoolRowStatus  RowStatus
          }
      
    cigDhcpServersPoolIndex OBJECT-TYPE
            SYNTAX Integer32
            MAX-ACCESS read-only
            STATUS current
            DESCRIPTION
              "The Pool Index.
              G250/G350 - Up to 20 Pools are allowed."    
            ::= { cigDhcpServersPoolEntry 1 }
	
    cigDhcpServersPoolStartIPAddr OBJECT-TYPE           
        SYNTAX IpAddress     
        MAX-ACCESS read-write
        STATUS current            
        DESCRIPTION
         "The Start IP Address of the pool.  Default = 0.0.0.0.
         Stop IP address shall be large or equal to start IP address.
         The user shall be aware that for G350/G250 the number of IP addresses to be allocated in up
         to 256 IPs total in all the pools. Also if the user wants to completely change the 
         start IP address/end IP address then the pool shall be Disabled and then by setting both these
         addresses (start/end) to default the user can set the new values. No need to erase the configuration
         of the pool for this case (I.e. in order not to loose all the DHCP options configuration).
         The user is not able to ocnfigure pools with overlapped IP addresses. 
         StartIPaddress can be configured different than EndIPAddress only when Client identifier is not set.
         "
        DEFVAL {'00000000'h }
        ::= { cigDhcpServersPoolEntry 2}

    cigDhcpServersPoolEndIPAddr OBJECT-TYPE           
        SYNTAX IpAddress     
        MAX-ACCESS read-write
        STATUS current            
        DESCRIPTION
         "The End IP Address of the pool.  Default = 0.0.0.0.
         End IP address shall be large or equal to start IP address.
         The user shall be aware that for G350/G250 the number of IP addresses to be allocated in up
         to 256 IPs total in all the pools. Also if the user wants to complete change the 
         start IP address/end IP address then the pool shall be Disabled and then by setting both these
         addresses (start/end) to default the user can set the new values. No need to erase the configuration
         of the pool for this case (I.e. in order not to loose all the DHCP options configuration).
         The user is not able to ocnfigure pools with overlapped IP addresses.    
         EndIPaddress can be configured different than StartIPAddress only when Client identifier is not set.
         "
        DEFVAL {'00000000'h }
        ::= { cigDhcpServersPoolEntry 3}
        
	cigDhcpServersPoolMode  OBJECT-TYPE
        SYNTAX TruthValue
        MAX-ACCESS read-write
        STATUS current
        DESCRIPTION
         "Enable Dhcp Pool in the device. Default = False (Disable,Inactive). It is recommended to enable/activate
         the pool only after the user configures all the DHCP pool parameters. The user can changes the parameters
         when the pool is Enable/active. However part of the clients will have different configuration.
         After enabling the user will Disable the pool only before deleting it or keeping its ocnfiguration
         for later use. In Disable mode the binding information is lost.
         The user can not activate pool with start-ip-addr or end-ip-addr == 0.0.0.0. 
         "
        DEFVAL { false }
        ::= { cigDhcpServersPoolEntry 4 }
        
	cigDhcpServersPoolName OBJECT-TYPE
	    SYNTAX DisplayString (SIZE (0..15))
		MAX-ACCESS read-write
		STATUS current
		DESCRIPTION
		"Name of this Pool.
		 Pool Default Name: 'Dhcp Pool #Pool Number'   "
        DEFVAL { "Dhcp Pool #" }
		::= { cigDhcpServersPoolEntry 5 }
    
	cigDhcpServersPoolClientID OBJECT-TYPE
	    SYNTAX OCTET STRING (SIZE (0..255))
		MAX-ACCESS read-write
		STATUS current
		DESCRIPTION
		"Client identifier used for manual leased. The strcuture of the client identifier is 
		 as follows: combination of TYPE and Data. Where Type = 01 if for Ethernet MACs and Data for 
		 this case if Ethernet MAC address. 
		 Default: '' - Null String. In this case no client identifier is defined.
		 ClientIdentifier can only configured when cigDhcpServersPoolStartIPAddr is equal to
		 cigDhcpServersPoolEndIPAddr.
		 "
        DEFVAL {"" }
		::= { cigDhcpServersPoolEntry 6 }
    
    cigDhcpServersPoolLeaseTime OBJECT-TYPE
        SYNTAX 	Unsigned32
        MAX-ACCESS read-write
        STATUS current
        DESCRIPTION
        "The Pool leased time in seconds. Infinite is defined as 0xffffffff.
         default 691200 seconds = 8 days."     
        DEFVAL { 691200 }        
        ::= { cigDhcpServersPoolEntry 7 }
    
	cigDhcpServersPoolBootFile OBJECT-TYPE
	    SYNTAX DisplayString (SIZE (0..128))
		MAX-ACCESS read-write
		STATUS current
		DESCRIPTION
		"BootFile Field in the Dhcp packet. Default Null String."
        DEFVAL {"" }
		::= { cigDhcpServersPoolEntry 8 }
        
    cigDhcpServersPoolNextServer OBJECT-TYPE           
        SYNTAX IpAddress     
        MAX-ACCESS read-write
        STATUS current            
        DESCRIPTION
         "Next Server Field in the Dhcp Packet.  Default = 0.0.0.0"
        DEFVAL {'00000000'h }
        ::= { cigDhcpServersPoolEntry 9}
    
    cigDhcpServersPoolSubnetMask OBJECT-TYPE           
        SYNTAX IpAddress     
        MAX-ACCESS read-write
        STATUS current            
        DESCRIPTION
         "Subnet Mask is Dhcp option 1.  Default = 255.255.255.0
         There is no ability to configure this option in the general option table."
        DEFVAL {'ffffff00'h }
        ::= { cigDhcpServersPoolEntry 10}

    cigDhcpServersPoolDefaultGateway OBJECT-TYPE           
        SYNTAX DisplayString (SIZE (0..145))     
        MAX-ACCESS read-write
        STATUS current            
        DESCRIPTION
         "Default Gateway is Dhcp option 3.  Default = '' = Null String.
         The format of the string can be up to 8 IP addresses, for exapmle:
         '121.23.1.12 135.64.13.190 192.123.242.230'
         There is no ability to configure this option in the general option table."
        DEFVAL {"" }
        ::= { cigDhcpServersPoolEntry 11}
        
    cigDhcpServersPoolDnsServer OBJECT-TYPE           
        SYNTAX DisplayString (SIZE (0..145))     
        MAX-ACCESS read-write
        STATUS current            
        DESCRIPTION
         "DNS Server is Dhcp option 6.  Default = '' = Null String.
         The format of the string can be up to 8 IP addresses, for exapmle:
         '121.23.1.12 135.64.13.190 192.123.242.230'         
         There is no ability to configure this option in the general option table."
         DEFVAL {"" }
        ::= { cigDhcpServersPoolEntry 12}
    
    cigDhcpServersPoolDomainName OBJECT-TYPE           
        SYNTAX DisplayString (SIZE (0..128))     
        MAX-ACCESS read-write
        STATUS current            
        DESCRIPTION
         "DNS Server is Dhcp option 15.  Default = Null String
         The format of the string can be: 'avaya'
         There is no ability to configure this option in the general option table.
         "                  
        DEFVAL {"" }
        ::= { cigDhcpServersPoolEntry 13}
    
    cigDhcpServersPoolServerName OBJECT-TYPE
	    SYNTAX DisplayString (SIZE (0..64))
		MAX-ACCESS read-write
		STATUS current
		DESCRIPTION
		"Optional Server Name. Default Null String."
        DEFVAL {"" }
		::= { cigDhcpServersPoolEntry 14 }

    cigDhcpServersPoolRowStatus OBJECT-TYPE
            SYNTAX RowStatus
            MAX-ACCESS read-write
            STATUS current
            DESCRIPTION
                "Used to create/delete a DHCP pool entry.
                 The following values will be supported:
                 
                - `active', which indicates that the conceptual row is
      				available for use by the managed device;

      			- `createAndGo', which is supplied by a management
      				station wishing to create a new instance of a
      				conceptual row and to have its status automatically set
      				to active, making it available for use by the managed
      				device;

      			- `destroy', which is supplied by a management station
      				wishing to delete all of the instances associated with
      				an existing conceptual row.
                "
            ::= { cigDhcpServersPoolEntry 15 }
	
	cigDhcpServersPoolGenOptionTable OBJECT-TYPE
		SYNTAX	   SEQUENCE OF CigDhcpServersPoolGenOptionEntry
		MAX-ACCESS not-accessible
		STATUS	   current
		DESCRIPTION
	    "Dhcp Pool General Option configuration table"
		::= { cigDhcpServersPool 2 }
	
	cigDhcpServersPoolGenOptionEntry OBJECT-TYPE
		SYNTAX	   CigDhcpServersPoolGenOptionEntry
		MAX-ACCESS not-accessible
		STATUS	   current
		DESCRIPTION
	    "The pool general option configuration table entry. 
	    
	    The following option numbers are not configurable:
	    Specific Options defined in the pool table:
	    Option 1 	- Subnet Mask
	    Option 3 	- Default Gateway
	    Option 6 	- Dns Servers
	    Option 15 	- Dns Name
	    
	    General Options that are not configurable according RFC2131, 2132:
	    Option 0 	- Pad Option
	    Option 50 	- Requested IP Address
	    Option 51	- IP address Lease Time
		Option 52	- Option Overload
		Option 53	- Message Type
		Option 54	- Server Identifier
		Option 55	- Parameter Request List
		Option 56	- Message
        Option 57	- Maximum DHCP Message Size
		Option 58	- Renewal (T1) Time Value
		Option 59	- Rebinding (T2) Time Value
		Option 60 	- Vendor Class Identifier
		Option 61	- Client Identifier
		Option 255	- End Option
	    "
		INDEX {
	     	cigDhcpServersOptionPoolIndex, cigDhcpServersOptionIndex
		}
		::= { cigDhcpServersPoolGenOptionTable 1 }

    CigDhcpServersPoolGenOptionEntry ::= SEQUENCE {
      	cigDhcpServersOptionPoolIndex Integer32,      
      	cigDhcpServersOptionIndex Integer32, 
      	cigDhcpServersOptionName  DisplayString,
      	cigDhcpServersOptionType INTEGER, 
     	cigDhcpServersOptionValue OCTET STRING,
     	cigDhcpServersOptionRowStatus RowStatus
    }
      
    cigDhcpServersOptionPoolIndex OBJECT-TYPE
    	SYNTAX Integer32
        MAX-ACCESS read-only
        STATUS current
        DESCRIPTION
        "The DHCP Pool Index"    
        ::= { cigDhcpServersPoolGenOptionEntry 1 }

    cigDhcpServersOptionIndex OBJECT-TYPE
        SYNTAX Integer32
        MAX-ACCESS read-only
        STATUS current
        DESCRIPTION
        "The DHCP Option Index."    
        ::= { cigDhcpServersPoolGenOptionEntry 2 }

	cigDhcpServersOptionName OBJECT-TYPE
	    SYNTAX DisplayString (SIZE (0..31))
		MAX-ACCESS read-write
		STATUS current
		DESCRIPTION
		"Name of this DHCP option.
		 Option Default Name: 'Option #Option Number'   "
		DEFVAL {"Option #" }
		::= { cigDhcpServersPoolGenOptionEntry 3 }

    cigDhcpServersOptionType OBJECT-TYPE            
        SYNTAX  INTEGER  {
        	ascii (1), 
        	hex(2), 
        	ipAddresses(3),
        	integer(4),
        	word(5)
        	}
        MAX-ACCESS read-write
        STATUS current            
        DESCRIPTION
         "The type of the DHCP option:
         ascii(1) is ASCII String as 'Avaya'
         hex(2) is HEX String as 'aa:bb:cc:dd:12:34:56'
         ipAddresses(3) can be array of up to 8 IP addresses with the structure as:
         '121.23.1.12 135.64.13.190 192.123.242.230' 
         integer(4) - unsigned 32 bits integer 
         word(5) - unsigned 16 bits integer                                           
         
         The defaults of cigDhcpServersOptionValue shall be changed according setting the type. 
         If setting Type == ascii(1) then the default is ''
         If setting Type == hex(2) then the default is ''
         If setting Type == ipAddresses(3) then the default is '0.0.0.0'
         If setting Type == integer(4) then the default is '00000000' 
         If setting Type == word(5) then the default is '0000'
         "                    
         DEFVAL {hex }
        ::= { cigDhcpServersPoolGenOptionEntry 4} 
        
	cigDhcpServersOptionValue OBJECT-TYPE
	    SYNTAX OCTET STRING (SIZE (0..255))
		MAX-ACCESS read-write
		STATUS current
		DESCRIPTION
		"The Value of the DHCP option according the TYPE field.
		Maximum length is 255B in case of ascii or hex, 145B for ipaddresses, 4B for integer
		and 2B for word.
		"              
		DEFVAL {''h }
		::= { cigDhcpServersPoolGenOptionEntry 5 }
        

    cigDhcpServersOptionRowStatus OBJECT-TYPE
            SYNTAX RowStatus
            MAX-ACCESS read-write
            STATUS current
            DESCRIPTION
                "Used to create/delete a DHCP option entry.
                 The following values will be supported:
                 
                - `active', which indicates that the conceptual row is
      				available for use by the managed device;

      			- `createAndGo', which is supplied by a management
      				station wishing to create a new instance of a
      				conceptual row and to have its status automatically set
      				to active, making it available for use by the managed
      				device;

      			- `destroy', which is supplied by a management station
      				wishing to delete all of the instances associated with
      				an existing conceptual row.
				"
            ::= { cigDhcpServersPoolGenOptionEntry 6 }


	cigDhcpServersPoolVendorSpecificOptionTable OBJECT-TYPE
		SYNTAX	   SEQUENCE OF CigDhcpServersPoolVendorSpecificOptionEntry
		MAX-ACCESS not-accessible
		STATUS	   current
		DESCRIPTION
	    "Dhcp Pool Vendor Specific Option configuration table"
		::= { cigDhcpServersPool 3 }
	
	cigDhcpServersPoolVendorSpecificOptionEntry OBJECT-TYPE
		SYNTAX	   CigDhcpServersPoolVendorSpecificOptionEntry
		MAX-ACCESS not-accessible
		STATUS	   current
		DESCRIPTION
	    "The pool Vendor Specific option configuration table entry. "
		INDEX {
	     	cigDhcpServersVendorSpecificOptionPoolIndex, cigDhcpServersVendorSpecificOptionIndex
		}
		::= { cigDhcpServersPoolVendorSpecificOptionTable 1 }

    CigDhcpServersPoolVendorSpecificOptionEntry ::= SEQUENCE {
      	cigDhcpServersVendorSpecificOptionPoolIndex Integer32,      
      	cigDhcpServersVendorSpecificOptionIndex Integer32, 
      	cigDhcpServersVendorSpecificOptionName  DisplayString,
      	cigDhcpServersVendorSpecificClassIdentifier DisplayString,
      	cigDhcpServersVendorSpecificOptionType INTEGER, 
     	cigDhcpServersVendorSpecificOptionValue OCTET STRING,
     	cigDhcpServersVendorSpecificOptionRowStatus RowStatus
     	}
      
    cigDhcpServersVendorSpecificOptionPoolIndex OBJECT-TYPE
    	SYNTAX Integer32
        MAX-ACCESS read-only
        STATUS current
        DESCRIPTION
        "The DHCP Pool Index"    
        ::= { cigDhcpServersPoolVendorSpecificOptionEntry 1 }

    cigDhcpServersVendorSpecificOptionIndex OBJECT-TYPE
        SYNTAX Integer32
        MAX-ACCESS read-only
        STATUS current
        DESCRIPTION
        "The DHCP Vendor Specific Option Index. 
        G250/G350 - Up to 10 Vendor Specific options are allowed."    
        ::= { cigDhcpServersPoolVendorSpecificOptionEntry 2 }

   	cigDhcpServersVendorSpecificOptionName OBJECT-TYPE
	    SYNTAX DisplayString (SIZE (0..31))
		MAX-ACCESS read-write
		STATUS current
		DESCRIPTION
		"Name of this DHCP Vednor specififc option.
		 Vendor Specific Option Default Name: 
		 'Vendor Specififc Option #Index Number'   "
		DEFVAL {"Vendor Specific Option #" }
		::= { cigDhcpServersPoolVendorSpecificOptionEntry 3 } 

   	cigDhcpServersVendorSpecificClassIdentifier OBJECT-TYPE
	    SYNTAX DisplayString (SIZE (0..255))
		MAX-ACCESS read-write
		STATUS current
		DESCRIPTION
		"The vendor specific class identifier which transmit in option 60 by the client.
		Default is null string"
		DEFVAL {''h }
		::= { cigDhcpServersPoolVendorSpecificOptionEntry 4 } 		

    cigDhcpServersVendorSpecificOptionType OBJECT-TYPE            
        SYNTAX  INTEGER  {
        	ascii (1), 
        	hex(2)        	
        	}
        MAX-ACCESS read-write
        STATUS current            
        DESCRIPTION
         "The type of the DHCP vendor specififc option:
         ascii(1) is ASCII String as 'Avaya'
         hex(2) is HEX String as 'aa:bb:cc:dd:12:34:56'
         
         The defaults of cigDhcpServersVendorSpecificOptionValue
         shall be changed according setting the type. 
         If setting Type == ascii(1) then the default is ''
         If setting Type == hex(2) then the default is ''
         "        
         DEFVAL {hex }
        ::= { cigDhcpServersPoolVendorSpecificOptionEntry 5} 
        
	cigDhcpServersVendorSpecificOptionValue OBJECT-TYPE
	    SYNTAX OCTET STRING (SIZE (0..255))
		MAX-ACCESS read-write
		STATUS current
		DESCRIPTION
		"The Value of the DHCP vendor specififc option according the Type field.
		Maximum length is 255B in case of ascii or hex."
		DEFVAL {''h }
		::= { cigDhcpServersPoolVendorSpecificOptionEntry 6 }    
		
    cigDhcpServersVendorSpecificOptionRowStatus OBJECT-TYPE
            SYNTAX RowStatus
            MAX-ACCESS read-write
            STATUS current
            DESCRIPTION
                "Used to create/delete a DHCP Vendor Specific option entry.
                The following values will be supported:
                 
                - `active', which indicates that the conceptual row is
      				available for use by the managed device;

      			- `createAndGo', which is supplied by a management
      				station wishing to create a new instance of a
      				conceptual row and to have its status automatically set
      				to active, making it available for use by the managed
      				device;

      			- `destroy', which is supplied by a management station
      				wishing to delete all of the instances associated with
      				an existing conceptual row.
                "
            ::= { cigDhcpServersPoolVendorSpecificOptionEntry 7 }
		
	cigDhcpServersGenStats	OBJECT IDENTIFIER ::= { cigDhcpServers 3 } 

	cigDhcpServersBootRequests  OBJECT-TYPE
            SYNTAX Unsigned32
            MAX-ACCESS read-only
            STATUS current
            DESCRIPTION
                "Number of Boot Requests packets.  Default = 0."
            DEFVAL {0 }
            ::= { cigDhcpServersGenStats 1 }

	cigDhcpServersDhcpDiscovers  OBJECT-TYPE
            SYNTAX Unsigned32
            MAX-ACCESS read-only
            STATUS current
            DESCRIPTION
                "Number of Dhcp Discovers packets.  Default = 0."
            DEFVAL {0 }
            ::= { cigDhcpServersGenStats 2 }

	cigDhcpServersDhcpRequests  OBJECT-TYPE
            SYNTAX Unsigned32
            MAX-ACCESS read-only
            STATUS current
            DESCRIPTION
                "Number of Dhcp Requests packets.  Default = 0."
            DEFVAL {0 }
            ::= { cigDhcpServersGenStats 3 }


	cigDhcpServersDhcpDeclines  OBJECT-TYPE
            SYNTAX Unsigned32
            MAX-ACCESS read-only
            STATUS current
            DESCRIPTION
                "Number of Dhcp Declines packets.  Default = 0."
            DEFVAL {0 }
            ::= { cigDhcpServersGenStats 4 }


	cigDhcpServersDhcpReleases  OBJECT-TYPE
            SYNTAX Unsigned32
            MAX-ACCESS read-only
            STATUS current
            DESCRIPTION
                "Number of Dhcp Releases packets.  Default = 0."
            DEFVAL {0 }
            ::= { cigDhcpServersGenStats 5 }


	cigDhcpServersDhcpInforms  OBJECT-TYPE
            SYNTAX Unsigned32
            MAX-ACCESS read-only
            STATUS current
            DESCRIPTION
                "Number of Dhcp Informs packets.  Default = 0."
            DEFVAL {0 }
            ::= { cigDhcpServersGenStats 6 }


	cigDhcpServersBootReplies  OBJECT-TYPE
            SYNTAX Unsigned32
            MAX-ACCESS read-only
            STATUS current
            DESCRIPTION
                "Number of Boot Replies packets.  Default = 0."
            DEFVAL {0 }
            ::= { cigDhcpServersGenStats 7 }


	cigDhcpServersDhcpOffers  OBJECT-TYPE
            SYNTAX Unsigned32
            MAX-ACCESS read-only
            STATUS current
            DESCRIPTION
                "Number of Dhcp Offers packets.  Default = 0."
            DEFVAL {0 }
            ::= { cigDhcpServersGenStats 8 }


	cigDhcpServersDhcpAcks  OBJECT-TYPE
            SYNTAX Unsigned32
            MAX-ACCESS read-only
            STATUS current
            DESCRIPTION
                "Number of Dhcp Acknowledges packets.  Default = 0."
            DEFVAL {0 }
            ::= { cigDhcpServersGenStats 9 }


	cigDhcpServersDhcpNacks  OBJECT-TYPE
            SYNTAX Unsigned32
            MAX-ACCESS read-only
            STATUS current
            DESCRIPTION
                "Number of Dhcp Nacks packets.  Default = 0."
            DEFVAL {0 }
            ::= { cigDhcpServersGenStats 10 }

	cigDhcpServersNotificationPacket	OBJECT IDENTIFIER ::= { cigDhcpServers 4 } 

	cigDhcpServersNotificationIpAddr  OBJECT-TYPE
            SYNTAX IpAddress
            MAX-ACCESS accessible-for-notify
            STATUS current
            DESCRIPTION
                "The relevant allocated IP address in DHCP/Bootp packet.  Default = 0.0.0.0"
            DEFVAL {'00000000'h }
            ::= { cigDhcpServersNotificationPacket 1 }

	cigDhcpServersNotificationClientIdentifier  OBJECT-TYPE
	    	SYNTAX OCTET STRING (SIZE (0..255))
            MAX-ACCESS accessible-for-notify
            STATUS current
            DESCRIPTION
			"The Client identifier used in the DHCP packet. The strcuture of the client identifier is 
		 	as follows: combination of TYPE and Data. Where Type = 01 if for Ethernet MACs and Data for 
		 	this case if Ethernet MAC address. Default: 01000000000000"
		 	DEFVAL {'01000000000000'h }
            ::= { cigDhcpServersNotificationPacket 2 }

	cigDhcpServersNotificationClientHostName OBJECT-TYPE
			SYNTAX OCTET STRING (SIZE (0..255))
			MAX-ACCESS accessible-for-notify
            STATUS current
            DESCRIPTION
			"This mib item presents the Client Host name as send by client packet in option 12."
		 	DEFVAL {"" }
            ::= { cigDhcpServersNotificationPacket 3 }

	cigDhcpServersNotificationConflictDetectionMethod  OBJECT-TYPE
			SYNTAX  INTEGER  {
        	ping(1), 
        	gratuitousArp(2),
        	notSupported(255)        	
        	}
			MAX-ACCESS accessible-for-notify
            STATUS current
            DESCRIPTION
			"The method which the DHCP server detect conflict. Using ping message by DHCP server
			or recieving Decline packet from the client as response to client gratuitous ARP."
		 	DEFVAL {notSupported }
            ::= { cigDhcpServersNotificationPacket 4 }
            
	cigDhcpServersNotificationPoolNetwork  OBJECT-TYPE
			SYNTAX IpAddress             
			MAX-ACCESS accessible-for-notify
            STATUS current
            DESCRIPTION
            "This mib item presents cases where no IP address left for specific network.
			The network exhausted is the pool start/stop IP address AND subnet mask"
			DEFVAL {'00000000'h}
            ::= { cigDhcpServersNotificationPacket 5 }
            

--	cigDhcpServersNotificationMessage OBJECT-TYPE
--	    SYNTAX DisplayString (SIZE (0..255))
--		MAX-ACCESS read-only
--		STATUS current
--		DESCRIPTION
--		"The relevant Notification Messgae" 
--		::= { cigDhcpServersNotificationPacket 3 }


END
