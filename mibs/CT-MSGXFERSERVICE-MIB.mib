CT-MSGXFERSERVICE-MIB DEFINITIONS ::= BEGIN

   --  ct-msgxferservice-mib.txt
   --  Revision: 00.00.02
   --  Part Number:
   --  Date: June 4, 1999

   --  Cabletron Systems, Inc.
   --  35 Industrial Way, P.O. Box 5005
   --  Rochester, NH 03867-0505
   --  (603) 332-9400
   --  support@ctron.com

   --  This module provides an enterprise-specific messaging service MIB.
   --
   --  This module will be extended, as needed.
   --

   --  Cabletron Systems reserves the right to make changes in
   --  specification and other information contained in this document
   --  without prior notice.  The reader should consult Cabletron Systems
   --  to determine whether any such changes have been made.
   --
   --  In no event shall Cabletron Systems be liable for any incidental,
   --  indirect, special, or consequential damages whatsoever (including
   --  but not limited to lost profits) arising out of or related to this
   --  document or the information contained in it, even if Cabletron
   --  Systems has been advised of, known, or should have known, the
   --  possibility of such damages.
   --
   --  Cabletron grants vendors, end-users, and other interested parties
   --  a non-exclusive license to use this Specification in connection
   --  with the management of Cabletron products.

   -- Copyright March 98 Cabletron Systems
   --
   -- This MIB is intended to allow quantitative & qualitative measurement
   -- of the flow of both control & data messages sent across a shared memory
   -- processor interface via the Message Transfer Service. In specific, it
   -- will provide the ability to:
   -- 1) determine if the amount of shared memory used for interprocessor
   --    messaging is being fully utilized
   -- 2) determine if the users of the shared memory are making efficient
   --    use of the message transferral service
   -- 3) determine if the Message Transfer Service is making efficient use
   --    of the shared memory interface

   IMPORTS
      Counter, Gauge
         FROM RFC1155-SMI
      OBJECT-TYPE
         FROM RFC-1212
      cabletron
         FROM CTRON-OIDS;

   --===============   Group Definitions          ===================

   ctSSA          OBJECT IDENTIFIER  ::=  { cabletron 4497 }

   --================================================================

   --  This MIB module uses the extended OBJECT-TYPE macro as defined
   --  RFC 1212

   --================= HSIM Info ===================

   ctMessageTransferService  OBJECT IDENTIFIER ::= { ctSSA 7 }

   numberOfMTSInstances OBJECT-TYPE
         SYNTAX  INTEGER
         ACCESS  read-only
         STATUS  mandatory
         DESCRIPTION
        "The value of this object is the number of instances of the
         Message Transfer Serive (MTS) represented in the table."
      ::= { ctMessageTransferService 1 }

   messageTransferServiceTable  OBJECT-TYPE
         SYNTAX  SEQUENCE OF MessageTransferServiceEntry
         ACCESS  not-accessible
         STATUS  mandatory
         DESCRIPTION
        "A list of MBus modules present in this unit"
      ::= { ctMessageTransferService 2 }

   messageTransferServiceEntry  OBJECT-TYPE
         SYNTAX  MessageTransferServiceEntry
         ACCESS  not-accessible
         STATUS  mandatory
         DESCRIPTION
        "The value of this object is an MBus module that is
         present in this unit"
         INDEX   { mtsInstanceID }
      ::= { messageTransferServiceTable 1 }

   MessageTransferServiceEntry ::=
         SEQUENCE {
                  mtsInstanceID                       INTEGER,
                  mtsMBusID                           INTEGER,
                  mtsNumberOfMTSUsers                 INTEGER,
                  mtsNumberOfMTSBuffers               INTEGER,
                  mtsSizeOfMTSBuffers                 INTEGER,
                  mtsNumberOfPostedMsgs               Counter,
                  mtsNumberOfPostedBytes              Counter, 
                  mtsNumberOfPostedPriorityMsgs       Counter,
                  mtsNumberOfPostedPriorityBytes      Counter,
                  mtsNumberOfSentMsgs                 Counter,
                  mtsNumberOfSentBytes                Counter,
                  mtsNumberOfPendingMsgs              Gauge,
                  mtsNumberOfPendingBytes             Gauge,
                  mtsHighWaterForPendingMsgs          INTEGER,
                  mtsHighWaterForPendingBytes         INTEGER,
                  mtsNumberOfTransmissions            Counter,
                  mtsNumberOfReceptions               Counter,
                  mtsNumberOfReceivedMsgs             Counter,
                  mtsNumberOfRcvNoBufs                Counter,
                  mtsNumberOfRcvNoUsers               Counter,
                  mtsNumberOfSentPriorityMsgs         Counter,
                  mtsNumberOfSentPriorityBytes        Counter,
                  mtsNumberOfReceivedBytes            Counter,
                  mtsNumberOfReceivedPriorityMsgs     Counter,
                  mtsNumberOfReceivedPriorityBytes    Counter,
                  mtsNumberOfAckdMsgs                 Counter,
                  mtsNumberOfAckdPriorityMsgs         Counter,
                  mtsHighWaterForMsgsPerTransmission  INTEGER,
                  mtsHighWaterForMsgsPerReception     INTEGER
                  }

   mtsInstanceID OBJECT-TYPE
         SYNTAX  INTEGER
         ACCESS  read-only
         STATUS  mandatory
         DESCRIPTION
        "The value of this object is an index that uniquely
         identifies this instance of the Message Transfer Service."
      ::= { messageTransferServiceEntry 1 }

   mtsMBusID OBJECT-TYPE
         SYNTAX  INTEGER
         ACCESS  read-only
         STATUS  mandatory
         DESCRIPTION
        "The value of this object is an index that uniquely
         identifies the MBus module on which this instance of
         the MTS runs."
      ::= { messageTransferServiceEntry 2 }

   mtsNumberOfMTSUsers OBJECT-TYPE
         SYNTAX  INTEGER
         ACCESS  read-only
         STATUS  mandatory
         DESCRIPTION
        "The value of this object defines the number of users
         currently subscribed to use this instance of the MTS."
      ::= { messageTransferServiceEntry 3 }

   mtsNumberOfMTSBuffers OBJECT-TYPE
         SYNTAX  INTEGER
         ACCESS  read-only
         STATUS  mandatory
         DESCRIPTION
        "The value of this object defines the number of buffers
         in the shared memory interface available for transferring
         user messages."
      ::= { messageTransferServiceEntry 4 }

   mtsSizeOfMTSBuffers OBJECT-TYPE
         SYNTAX  INTEGER
         ACCESS  read-only
         STATUS  mandatory
         DESCRIPTION
        "The value of this object defines the size of buffers used
         in the shared memory interface available for transferring
         user messages."
      ::= { messageTransferServiceEntry 5 }

   mtsNumberOfPostedMsgs  OBJECT-TYPE
         SYNTAX  Counter
         ACCESS  read-write
         STATUS  mandatory
         DESCRIPTION
        "The value of this object defines the number of messages
         posted to the MTS for transfer via the shared memory
         interface."
      ::= { messageTransferServiceEntry 6 }

   mtsNumberOfPostedBytes  OBJECT-TYPE
         SYNTAX  Counter
         ACCESS  read-write
         STATUS  mandatory
         DESCRIPTION
        "The value of this object defines the number of user data
         bytes posted to the MTS for transfer via the shared memory
         interface."
      ::= { messageTransferServiceEntry 7 }

   mtsNumberOfPostedPriorityMsgs  OBJECT-TYPE
         SYNTAX  Counter
         ACCESS  read-write
         STATUS  mandatory
         DESCRIPTION
        "The value of this object defines the number of high
         priority messages posted to the MTS for transfer via
         the shared memory interface."
      ::= { messageTransferServiceEntry 8 }

   mtsNumberOfPostedPriorityBytes  OBJECT-TYPE
         SYNTAX  Counter
         ACCESS  read-write
         STATUS  mandatory
         DESCRIPTION
        "The value of this object defines the number of high
         priority user data bytes posted to the MTS for transfer
         via the shared memory interface."
      ::= { messageTransferServiceEntry 9 }

   mtsNumberOfSentMsgs  OBJECT-TYPE
         SYNTAX  Counter
         ACCESS  read-write
         STATUS  mandatory
         DESCRIPTION
        "The value of this object defines the number of messages
         sent by the MTS via the shared memory interface."
      ::= { messageTransferServiceEntry 10 }

   mtsNumberOfSentBytes  OBJECT-TYPE
         SYNTAX  Counter
         ACCESS  read-write
         STATUS  mandatory
         DESCRIPTION
        "The value of this object defines the number of user data
         bytes sent by the MTS via the shared memory interface."
      ::= { messageTransferServiceEntry 11 }

   mtsNumberOfPendingMsgs  OBJECT-TYPE
         SYNTAX  Gauge
         ACCESS  read-only
         STATUS  mandatory
         DESCRIPTION
        "The value of this object defines the current value for
         the number of messages waiting to be transferred via
         this instance of the MTS."
      ::= { messageTransferServiceEntry 12 }

   mtsNumberOfPendingBytes  OBJECT-TYPE
         SYNTAX  Gauge
         ACCESS  read-only
         STATUS  mandatory
         DESCRIPTION
        "The value of this object defines the current value for
         the number of bytes of user data waiting to be transferred
         via this instance of the MTS."
      ::= { messageTransferServiceEntry 13 }

   mtsHighWaterForPendingMsgs  OBJECT-TYPE
         SYNTAX  INTEGER
         ACCESS  read-write
         STATUS  mandatory
         DESCRIPTION
        "The value of this object defines the highest value for
         the number of messages waiting to be transferred via
         this instance of the MTS."
      ::= { messageTransferServiceEntry 14 }

   mtsHighWaterForPendingBytes  OBJECT-TYPE
         SYNTAX  INTEGER
         ACCESS  read-write
         STATUS  mandatory
         DESCRIPTION
        "The value of this object defines the highest value for
         the number of bytes of user data waiting to be transferred
         via this instance of the MTS."
      ::= { messageTransferServiceEntry 15 }

   mtsNumberOfTransmissions  OBJECT-TYPE
         SYNTAX  Counter
         ACCESS  read-write
         STATUS  mandatory
         DESCRIPTION
        "The value of this object defines the number of times
         a message or messages were sent by this instance of the
         MTS via the shared memory interface."
      ::= { messageTransferServiceEntry 16 }

   mtsNumberOfReceptions  OBJECT-TYPE
         SYNTAX  Counter
         ACCESS  read-write
         STATUS  mandatory
         DESCRIPTION
        "The value of this object defines the number of times
         a message or messages were received by this instance of
         the MTS via the shared memory interface."
      ::= { messageTransferServiceEntry 17 }

   mtsNumberOfReceivedMsgs  OBJECT-TYPE
         SYNTAX  Counter
         ACCESS  read-write
         STATUS  mandatory
         DESCRIPTION
        "The value of this object defines the number of messages
         received by this instance of the MTS via the shared memory
         interface."
      ::= { messageTransferServiceEntry 18 }


   mtsNumberOfRcvNoBufs  OBJECT-TYPE
         SYNTAX  Counter
         ACCESS  read-write
         STATUS  mandatory
         DESCRIPTION
        "The value of this object defines the number of messages
         discarded due to a lack of a system receive buffers
         available to hold the received message for this instance
         of the shared memory interface."
      ::= { messageTransferServiceEntry 19 }

   mtsNumberOfRcvNoUsers  OBJECT-TYPE
         SYNTAX  Counter
         ACCESS  read-write
         STATUS  mandatory
         DESCRIPTION
        "The value of this object defines the number of messages
         discarded as a result of no user registered for the
         received message type for this instance of the shared
         memory interface."
      ::= { messageTransferServiceEntry 20 }

   mtsNumberOfSentPriorityMsgs  OBJECT-TYPE
         SYNTAX  Counter
         ACCESS  read-write
         STATUS  mandatory
         DESCRIPTION
        "The value of this object defines the number of priority
         messages sent by the MTS via the shared memory interface."
      ::= { messageTransferServiceEntry 21 }

   mtsNumberOfSentPriorityBytes  OBJECT-TYPE
         SYNTAX  Counter
         ACCESS  read-write
         STATUS  mandatory
         DESCRIPTION
        "The value of this object defines the number of bytes
         of priority messages sent by the MTS via the shared 
         memory interface."
      ::= { messageTransferServiceEntry 22 }

    mtsNumberOfReceivedBytes  OBJECT-TYPE
         SYNTAX  Counter
         ACCESS  read-write
         STATUS  mandatory
         DESCRIPTION
        "The value of this object defines the number of bytes
         received by this instance of the MTS via the shared memory
         interface."
      ::= { messageTransferServiceEntry 23 }

   mtsNumberOfReceivedPriorityMsgs  OBJECT-TYPE
         SYNTAX  Counter
         ACCESS  read-write
         STATUS  mandatory
         DESCRIPTION
        "The value of this object defines the number of priority
         messages received by this instance of the MTS via the 
         shared memory interface."
      ::= { messageTransferServiceEntry 24 }

   mtsNumberOfReceivedPriorityBytes  OBJECT-TYPE
         SYNTAX  Counter
         ACCESS  read-write
         STATUS  mandatory
         DESCRIPTION
        "The value of this object defines the number of bytes of
         priority messages received by this instance of the MTS via 
         the shared memory interface."
      ::= { messageTransferServiceEntry 25 }

   mtsNumberOfAckdMsgs  OBJECT-TYPE
         SYNTAX  Counter
         ACCESS  read-write
         STATUS  mandatory
         DESCRIPTION
        "The value of this object defines the number of messages
         acknowledged by this instance of the MTS via the shared memory
         interface."
      ::= { messageTransferServiceEntry 26 }

   mtsNumberOfAckdPriorityMsgs  OBJECT-TYPE
         SYNTAX  Counter
         ACCESS  read-write
         STATUS  mandatory
         DESCRIPTION
        "The value of this object defines the number of priority messages
         acknowledged by this instance of the MTS via the shared memory
         interface."
      ::= { messageTransferServiceEntry 27 }

   mtsHighWaterForMsgsPerTransmission  OBJECT-TYPE
         SYNTAX  INTEGER
         ACCESS  read-write
         STATUS  mandatory
         DESCRIPTION
        "The value of this object defines the highest value for the
         number of messages that were sent per transmission by this 
         instance of the MTS via the shared memory interface."
      ::= { messageTransferServiceEntry 28 }

   mtsHighWaterForMsgsPerReception  OBJECT-TYPE
         SYNTAX  INTEGER
         ACCESS  read-write
         STATUS  mandatory
         DESCRIPTION
        "The value of this object defines the highest value for the
         number of messages that were received per reception by this
         instance of the MTS via the shared memory interface."
      ::= { messageTransferServiceEntry 29 }
   END
