USR-TFTP-MIB DEFINITIONS ::= BEGIN
	IMPORTS
            OBJECT-TYPE, MODULE-IDENTITY,
    		IpAddress, Integer32
                  FROM SNMPv2-SMI
            common, DisplayString, UsrConfigStatus
                  FROM USR-DEFINITIONS-MIB;
usrTftp MODULE-IDENTITY
        LAST-UPDATED "200205051800Z"
        ORGANIZATION "CommWorks Corporation, a 3Com Company"
        CONTACT-INFO "Customer Support"
        DESCRIPTION
           "The commWorks enterprise defined MIB objects  for TFTP"
--      REVISION  "200205051800Z"
--      DESCRIPTION "Converted to SNMPv2"
       ::= { common 24 }
   -- textual conventions
   -- 
   -- textual conventions are like pre-processor macro in 'C'
   --        (i.e. #define statements)
   -- Use them to define your own 'datatypes'
   -- memory size, expressed in units of 1024bytes
	-- A sample Table definiton.
	usrTftpConfigFileName OBJECT-TYPE
		SYNTAX          DisplayString
		MAX-ACCESS      read-only
		STATUS          current
		DESCRIPTION		
		  "The name of a ConfigFile to read/write permanent database records.
		   If the value of this object is an empty string, then the
		   TFTP process uses the default name `@file://TftpProcess.cfg'. "
	::= { usrTftp 1 }
	usrTftpCFMStatusFlag  OBJECT-TYPE
	 	SYNTAX	  UsrConfigStatus
		MAX-ACCESS      read-write
		STATUS          current
		DESCRIPTION
		  "Setting the value of this object to `save' causes the values
		   of the TFTP Group to be written out to the current config
		   file, which is stored in the usrTftpConfigFileName object.
		   While the new ConfigFile is being written, the TFTP process
		   will set the value of this flag to `saving''. Any
		   attempts to set the value while it is not `normal'
		   (i.e. the file is currently being written to the
		   ConfigFile) while result in a badValue error being
		   returned. Setting the value to `normal' will result in no
		   action."
	::= { usrTftp 2 }
     usrTftpAccessTable OBJECT-TYPE
		SYNTAX  SEQUENCE OF UsrTftpAccessEntry
         	MAX-ACCESS  not-accessible
         	STATUS      current
         	DESCRIPTION
            "The TFTP access table"
	::= { usrTftp 3 }
	usrTftpAccessEntry OBJECT-TYPE
         	SYNTAX  UsrTftpAccessEntry
         	MAX-ACCESS  not-accessible
         	STATUS      current
         	DESCRIPTION
            ""
         INDEX   { usrTftpAccessIpAddr }
	::= { usrTftpAccessTable 1 }
	UsrTftpAccessEntry ::=
         	SEQUENCE {
         	usrTftpAccessIpAddr
            IpAddress,
         	usrTftpAccessStatus
            INTEGER
         }
	usrTftpAccessIpAddr OBJECT-TYPE
         	SYNTAX  IpAddress
         	MAX-ACCESS  not-accessible
         	STATUS      current
         	DESCRIPTION
            "The IP Address of the station allowed to perform TFTP file
             transfers."
	::= { usrTftpAccessEntry 1 }
	usrTftpAccessStatus OBJECT-TYPE
	 	SYNTAX   INTEGER {
			add(1),
			normal(2),
			delete(3)
			}
         	MAX-ACCESS   read-write
         	STATUS       current
         	DESCRIPTION
            "The status of the entry for this address."
          --CONFIGURABLE
         ::= { usrTftpAccessEntry 2 }
     -- TFTP Client Request Table
     usrTftpClientRequestTable OBJECT-TYPE
          SYNTAX  SEQUENCE OF UsrTftpClientRequestEntry
          MAX-ACCESS  not-accessible
          STATUS      current
          DESCRIPTION
            "The TFTP Client Request Table"
     ::= { usrTftp 4 }
     usrTftpClientRequestEntry OBJECT-TYPE
          SYNTAX  UsrTftpClientRequestEntry
          MAX-ACCESS  not-accessible
          STATUS      current
          DESCRIPTION
            ""
         INDEX   { usrTftpClientRequestFileName }
     ::= { usrTftpClientRequestTable 1 }
     UsrTftpClientRequestEntry ::=
          SEQUENCE {
               usrTftpClientRequestFileName
                    DisplayString,
               usrTftpClientRequestServer
                    OCTET STRING,
               usrTftpClientRequestAction
                    INTEGER,
               usrTftpClientRequestMode
                    INTEGER,
               usrTftpClientRequestRexmtTimeout
                    Integer32,
               usrTftpClientRequestMaxTimeout
                    Integer32,
               usrTftpClientRequestStatus
                    INTEGER,
               usrTftpClientRequestErrorString
                    DisplayString
         }
     usrTftpClientRequestFileName OBJECT-TYPE
         	SYNTAX  DisplayString (SIZE(0..64))
         	MAX-ACCESS  not-accessible
         	STATUS      current
         	DESCRIPTION
            "The name of the file which will either be requested from or
             sent to the TFTP server."
     ::= { usrTftpClientRequestEntry 1 }
     usrTftpClientRequestServer OBJECT-TYPE
          SYNTAX  OCTET STRING (SIZE(0..255))
          MAX-ACCESS  read-write
          STATUS      current
          DESCRIPTION
            "The name or IP address of the TFTP server. I name it is
             a domain name of type DnsName (rfc1611)"
          REFERENCE
            "RFC-1034 section 3.1"
          --CONFIGURABLE
         ::= { usrTftpClientRequestEntry 2 }
     usrTftpClientRequestAction OBJECT-TYPE
          SYNTAX  INTEGER {
                    get(1),
                    put(2)
                    }
          MAX-ACCESS  read-write
          STATUS      current
          DESCRIPTION
            "The type of request that will be sent to the TFTP server."
          --CONFIGURABLE
         ::= { usrTftpClientRequestEntry 3 }
     usrTftpClientRequestMode OBJECT-TYPE
          SYNTAX  INTEGER {
                    netascii(1),
                    octet(2)
                    }
          MAX-ACCESS  read-write
          STATUS      current
          DESCRIPTION
            "The mode in which the file will be transferred."
          DEFVAL { netascii }
          --CONFIGURABLE
         ::= { usrTftpClientRequestEntry 4 }
     usrTftpClientRequestRexmtTimeout OBJECT-TYPE
          SYNTAX  Integer32 (1..60)
          MAX-ACCESS  read-write
          STATUS      current
          DESCRIPTION
            "The retransmission time-out."
          DEFVAL { 5 }
          --CONFIGURABLE
         ::= { usrTftpClientRequestEntry 5 }
     usrTftpClientRequestMaxTimeout OBJECT-TYPE
          SYNTAX  Integer32 (1..300)
          MAX-ACCESS  read-write
          STATUS      current
          DESCRIPTION
            "The maximum number of seconds to wait for a response from
             the TFTP server. If this value is reached, the TFTP request
             will be timed out."
          DEFVAL { 25 }
          --CONFIGURABLE
         ::= { usrTftpClientRequestEntry 6 }
     usrTftpClientRequestStatus OBJECT-TYPE
          SYNTAX  INTEGER {
                    normal(1),
                    enable(2),
                    getting(3),
                    putting(4),
                    delete(5),
                    error(6)
                    }
          MAX-ACCESS  read-write
          STATUS      current
          DESCRIPTION
            "The status of this row. Setting this object to enable(2)
             will cause a request (defined by usrTftpClientRequestAction)
             to be sent to the TFTP server. Depending on the type of
             request, this object will then be set to either getting(3)
             or putting(4). When the request is completed, this object
             will be set to normal(1) which indicates success. If an
             error occurred, this object will be set to error(5) and
             the usrTftpClientRequestErrorString will indicate the
             type of error."
         ::= { usrTftpClientRequestEntry 7 }
     usrTftpClientRequestErrorString OBJECT-TYPE
          SYNTAX      DisplayString
          MAX-ACCESS  read-only
          STATUS      current
          DESCRIPTION
            "This object will indicate what type of error occurred when
             the object usrTftpClientRequestStatus is set to error(5)."
         ::= { usrTftpClientRequestEntry 8 }
END  -- End of USR-TFTP-MIB DEFINITIONS
-- ************************************************************************
--
--	usr_dialout.mib - The Commworks Dial-out MIB module
--
-- Author:         Peter Dobransky
--
