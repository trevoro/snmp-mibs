SALIX-MIB DEFINITIONS ::= BEGIN

-- Note: Compile with SMICNG using options below to product intermediate
--                      file output.
--
--                       SMICNG /Y /Z /F <filename.imf> salix.inc

IMPORTS
          MODULE-IDENTITY, OBJECT-IDENTITY,
          enterprises                                   FROM SNMPv2-SMI

          MODULE-COMPLIANCE                             FROM SNMPv2-CONF;

-- Define the SALIX Technologies node
salixTechnologies MODULE-IDENTITY
          LAST-UPDATED "9810130000Z"
          ORGANIZATION "SALIX Technologies"
          CONTACT-INFO "904 Wind River Lane
                   Suite 101
                   Gaithersburg, MD  20878
                   (301)-417-0017"
          DESCRIPTION   "The root of the SALIX Technologies enterprise"
          ::= { enterprises 2158 }
          
   salixMIBCompliance   OBJECT IDENTIFIER ::= { salixTechnologies 6 }          
   
   salixExperimental    OBJECT-IDENTITY
      STATUS      current
      DESCRIPTION
         "Provides a root for experimental MIB's"
   ::= { salixTechnologies 1 }
   
   salixGeneric        OBJECT-IDENTITY
      STATUS      current
      DESCRIPTION
         "Provides a root for Generic Mibs that
          hold objects common to more than one
          product"
      ::= { salixTechnologies 2 }
      
   salixProducts        OBJECT-IDENTITY
      STATUS      current
      DESCRIPTION
         "Provides a root for Product Specific MIBS"
      ::= { salixTechnologies 3 }
      
   salixRegistrations   OBJECT-IDENTITY
      STATUS      current
      DESCRIPTION
         "Provides Product Registrations for SALIX Technologies"
      ::= { salixTechnologies 4 }
      
   salixPlatforms       OBJECT-IDENTITY
      STATUS      current
      DESCRIPTION
         "Provides a root for MIBS specific to SALIX platforms"
      ::= { salixTechnologies 5 }
      
      
   -- Products Groups
   
      hybridSwitch      OBJECT-IDENTITY
         STATUS      current
         DESCRIPTION
            "All MIBS that are specific to the hybridSwitch family
             can be found here"
         ::= { salixProducts 1 }    
           
      voip              OBJECT-IDENTITY
         STATUS      current
         DESCRIPTION
            "All MIBS that are specific to the voip family
             can be found here"
         ::= { salixProducts 2 }      
   
   -- Platform Groups
   
      platform1         OBJECT-IDENTITY
      STATUS      current
      DESCRIPTION
         "All MIBS that are specific to the platform1 platform can
          be found here"
      ::= { salixPlatforms 1 }   

-- Conformance Statements

salixGroups          OBJECT IDENTIFIER    ::= {salixMIBCompliance 1 }
salixCompliances     OBJECT IDENTIFIER    ::= {salixMIBCompliance 2 }

-- Compliance Statements

salixCompliance MODULE-COMPLIANCE
     STATUS       current
     DESCRIPTION
                  "The basic implementation requirements for the SALIX-MIB."
     MODULE       -- This module
--     MANDATORY-GROUPS { salixProductGroup }
     ::= { salixCompliances 1 }

END
