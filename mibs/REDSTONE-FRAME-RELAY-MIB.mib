-- *****************************************************************
-- REDSTONE-FRAME-RELAY-MIB
--
-- Redstone Communications Inc. Enterprise MIB
-- Frame Relay MIB
--
-- Copyright 1998 Redstone Communications, Incorporated.
-- All Rights Reserved.
-- *****************************************************************

REDSTONE-FRAME-RELAY-MIB DEFINITIONS ::= BEGIN

IMPORTS
	MODULE-IDENTITY,
	OBJECT-TYPE,
	Integer32,
    Counter32,
    TimeTicks
		FROM SNMPv2-SMI
	OBJECT-GROUP, MODULE-COMPLIANCE FROM SNMPv2-CONF

	RowStatus,
    TimeStamp
		FROM SNMPv2-TC

    InterfaceIndex, InterfaceIndexOrZero
        FROM IF-MIB

    DLCI
        FROM FRAME-RELAY-DTE-MIB

	rsMgmt
		FROM REDSTONE-SMI

    RsNextIfIndex
        FROM REDSTONE-TC;


rsFrameRelayMIB  MODULE-IDENTITY
	LAST-UPDATED "9906010000Z"
	ORGANIZATION "Redstone Communications, Inc."
	CONTACT-INFO
        "
        Redstone Communications, Inc.
		5 Carlisle Road
        Westford MA 01886
        USA
        Tel:    +1-978-692-1999
		Email:  mib@redstonecom.com
        "
	DESCRIPTION
		"The Frame Relay MIB for the 
		Redstone Communications Inc. enterprise."
	REVISION      "9906010000Z"
	DESCRIPTION
		"Add support for NNI behavior."
	REVISION      "9801010000Z"
	DESCRIPTION
		"Initial version of this MIB module."
	::= { rsMgmt 10 }

-- ++++++++++++++++++++++++++++++++++++++++++++++++++++++++++++++++++++++
-- Textual conventions
-- ++++++++++++++++++++++++++++++++++++++++++++++++++++++++++++++++++++++

-- No textual conventions are defined in this MIB.


-- ++++++++++++++++++++++++++++++++++++++++++++++++++++++++++++++++++++++
-- Managed objects
-- ++++++++++++++++++++++++++++++++++++++++++++++++++++++++++++++++++++++

rsFrObjects     OBJECT IDENTIFIER ::= { rsFrameRelayMIB 1 }

-- 
-- This MIB contains managed objects for each of two interface
-- layers: Frame Relay interfaces, and Frame Relay subinterfaces. 
-- For each of these layers, management objects are provided to 
-- query for an available interface index, and to create/delete 
-- interfaces of that type. Creating/deleting these interface 
-- types using this MIB has the side effect of creating/deleting 
-- corresponding entries in the Interface MIB ifTable/ifXTable, 
-- and in the Redstone Enterprise Interface MIB rsIfTable.
--
-- 
--

rsFrIfLayer        OBJECT IDENTIFIER ::= { rsFrObjects 1 }
rsFrSubIfLayer     OBJECT IDENTIFIER ::= { rsFrObjects 2 }


-- //////////////////////////////////////////////////////////////////////
--
-- Frame Relay Interface Layer
--
-- This layer is managed with the following elements:
--
--  o NextIfIndex (generator for Frame Relay IfIndex selection)
--  o Dlcmi Table (creation/configuration/deletion of Frame Relay interfaces)
--  o Dlcmi Statistics Table (Frame Relay interface statistics)
--  o Circuit Table (status of Frame Relay circuits)
--
-- //////////////////////////////////////////////////////////////////////

--
-- IfIndex selection for creating new Frame Relay interfaces
--

rsFrNextIfIndex OBJECT-TYPE
    SYNTAX      RsNextIfIndex
    MAX-ACCESS  read-only
    STATUS      current
    DESCRIPTION
        "Coordinate ifIndex value allocation for entries
        in rsFrDlcmiTable.

        A GET of this object returns the next available ifIndex 
        value to be used to create an entry in the associated
        interface table; or zero, if no valid ifIndex value is
        available. This object also returns a value of zero when 
        it is the lexicographic successor of a varbind presented 
        in an SNMP GETNEXT or GETBULK request, for which circumstance
        it is assumed that ifIndex allocation is unintended.

        Successive GETs will typically return different
        values, thus avoiding collisions among cooperating
        management clients seeking to create table entries
        simultaneously.
        "
    ::= { rsFrIfLayer 1 }

--
-- The Frame Relay Dlcmi Table
--

rsFrDlcmiTable OBJECT-TYPE
    SYNTAX      SEQUENCE OF RsFrDlcmiEntry
    MAX-ACCESS  not-accessible
    STATUS      current
    DESCRIPTION
        "The Parameters for the Data Link Connection Management
        Interface for the frame relay service on this interface.
        
        This table represents a superset of functionality specified in
        RFC2115 FRAME-RELAY-DTE-MIB. In particular, it adds attributes
        that permit the interface to operate as a network-side (DCE)
        interface."
    REFERENCE
        "American National Standard T1.617-1991, Annex D"
    ::= { rsFrIfLayer 2 }

rsFrDlcmiEntry OBJECT-TYPE
    SYNTAX      RsFrDlcmiEntry
    MAX-ACCESS  not-accessible
    STATUS      current
    DESCRIPTION
        "The Parameters for a particular Data Link Connection
        Management Interface.

        Creating/deleting entries in this table causes corresponding 
        entries for be created/deleted in ifTable/ifXTable/rsIfTable,
        and rsFrDlcmiStatsTable.

        Creating/deleting user-side (DTE) entries in this table also causes
        coresponding entries to be created/deleted in RFC2115 frDlcmiTable.

        The organization and definitions of objects in this table are 
        intentionally aligned closely to those in RFC2115."
    INDEX   { rsFrDlcmiIfIndex }
    ::= { rsFrDlcmiTable 1 }

RsFrDlcmiEntry ::= SEQUENCE {
    rsFrDlcmiIfIndex                        InterfaceIndex,
    rsFrDlcmiState                          INTEGER,
    rsFrDlcmiAddress                        INTEGER,
    rsFrDlcmiAddressLen                     INTEGER,
    rsFrDlcmiPollingInterval                Integer32,
    rsFrDlcmiFullEnquiryInterval            Integer32,
    rsFrDlcmiErrorThreshold                 Integer32,
    rsFrDlcmiMonitoredEvents                Integer32,
    rsFrDlcmiMaxSupportedVCs                DLCI,
    rsFrDlcmiMulticast                      INTEGER,
    rsFrDlcmiStatus                         INTEGER,
    rsFrDlcmiRowStatus                      RowStatus,
    rsFrDlcmiLowerIfIndex                   InterfaceIndexOrZero,
    rsFrDlcmiRole                           INTEGER,
    rsFrDlcmiDcePollingInterval             Integer32,
    rsFrDlcmiDceErrorThreshold              Integer32,
    rsFrDlcmiDceMonitoredEvents             Integer32
}


rsFrDlcmiIfIndex OBJECT-TYPE
    SYNTAX      InterfaceIndex
    MAX-ACCESS  read-only
    STATUS      current
    DESCRIPTION
        "The ifIndex value of the corresponding ifEntry."
    ::= { rsFrDlcmiEntry 1 }


rsFrDlcmiState OBJECT-TYPE
    SYNTAX      INTEGER {
                    noLmiConfigured (1),
                    lmiRev1         (2),
                    ansiT1617D      (3),  -- ANSI T1.617 Annex D
                    ansiT1617B      (4),  -- ANSI T1.617 Annex B
                    itut933A        (5),  -- CCITT Q933 Annex A
                    ansiT1617D1994  (6)   -- ANSI T1.617a-1994 Annex D
                }
    MAX-ACCESS  read-create
    STATUS      current
    DESCRIPTION
        "This variable states which Data Link Connection
        Management scheme is active (and by implication, what
        DLCI it uses) on the Frame Relay interface."
    REFERENCE
        "American National Standard T1.617-1991, American
        National Standard T1.617a-1994, ITU-T Recommendation
        Q.933 (03/93)."
    ::= { rsFrDlcmiEntry 2 }

rsFrDlcmiAddress OBJECT-TYPE
    SYNTAX      INTEGER {
                    q921           (1),  -- 13 bit DLCI
                    q922March90    (2),  -- 11 bit DLCI
                    q922November90 (3),  -- 10 bit DLCI
                    q922           (4)   -- Final Standard
                }
    MAX-ACCESS  read-create
    STATUS      current
    DESCRIPTION
        "This variable states which address format is in use on
        the Frame Relay interface."
    DEFVAL { q922 }
    ::= { rsFrDlcmiEntry 3 }


rsFrDlcmiAddressLen OBJECT-TYPE
    SYNTAX      INTEGER     {
                    twoOctets (2),
                    threeOctets (3),
                    fourOctets (4)
                }
    MAX-ACCESS  read-create
    STATUS      current
    DESCRIPTION
        "This variable states the address length in octets.  In
        the case of Q922 format, the length indicates the
        entire length of the address including the control
        portion."
    DEFVAL { twoOctets }
    ::= { rsFrDlcmiEntry 4 }


rsFrDlcmiPollingInterval OBJECT-TYPE
    SYNTAX      Integer32 (5..30)
    UNITS       "seconds"
    MAX-ACCESS  read-create
    STATUS      current
    DESCRIPTION
        "This is the number of seconds between successive
        status enquiry messages sent by the DTE.

        Pertains to DTE/NNI operation only. This parameter can
        be reconfigured only when the Frame Relay interface 
        is acting as a DTE or NNI."
    REFERENCE
        "American National Standard T1.617-1991, Section D.7
        Timer T391."
    DEFVAL  { 10 }
    ::= { rsFrDlcmiEntry 5 }

rsFrDlcmiFullEnquiryInterval OBJECT-TYPE
    SYNTAX      Integer32 (1..255)
    MAX-ACCESS  read-create
    STATUS      current
    DESCRIPTION
        "Number of status enquiry intervals that pass before
        issuance of a full status enquiry message.

        Pertains to DTE/NNI operation only. This parameter can
        be reconfigured only when the Frame Relay interface 
        is acting as a DTE or NNI."
    REFERENCE
        "American National Standard T1.617-1991, Section D.7
        Counter N391."
    DEFVAL  { 6 }
    ::= { rsFrDlcmiEntry 6 }


rsFrDlcmiErrorThreshold OBJECT-TYPE
    SYNTAX      Integer32 (1..10)
    MAX-ACCESS  read-create
    STATUS      current
    DESCRIPTION
        "The minimum number of errors that must be observed 
        within the number of events specified by rsFrDlcmiMonitoredEvents,
        to declare the interface down.
        
        'error' is lack of receipt of a Status, in response to an 
        issued Status Enquiry, within the Polling Interval (T391).

        Pertains to DTE/NNI operation only. This parameter can
        be reconfigured only when the Frame Relay interface 
        is acting as a DTE or NNI."
    REFERENCE
        "American National Standard T1.617-1991, Section D.5.1
        Counter N392."
    DEFVAL  { 3 }
    ::= { rsFrDlcmiEntry 7 }


rsFrDlcmiMonitoredEvents OBJECT-TYPE
    SYNTAX      Integer32 (1..10)
    MAX-ACCESS  read-create
    STATUS      current
    DESCRIPTION
        "The number of status polling intervals over which the 
        error threshold is counted.  For example, if within 
        'MonitoredEvents' number of events the station receives 
        'ErrorThreshold' number of errors, the interface is 
        marked as down.

        'status polling interval' is specified by
        rsFrDlcmiPollingInterval.

        Pertains to DTE/NNI operation only. This parameter can
        be reconfigured only when the Frame Relay interface 
        is acting as a DTE or NNI."
    REFERENCE
        "American National Standard T1.617-1991, Section D.5.2
        Counter N393."
    DEFVAL  { 4 }
    ::= { rsFrDlcmiEntry 8 }

rsFrDlcmiMaxSupportedVCs OBJECT-TYPE
    SYNTAX      DLCI
    MAX-ACCESS  read-create
    STATUS      current
    DESCRIPTION
        "The maximum number of Virtual Circuits allowed for
        this interface.  Usually dictated by the Frame Relay
        network.

        In response to a SET, if a value less than zero or
        higher than the agent's maximal capability is
        configured, the agent should respond badValue."
    ::= { rsFrDlcmiEntry 9 }


rsFrDlcmiMulticast OBJECT-TYPE
    SYNTAX      INTEGER {
                    nonBroadcast (1),
                    broadcast (2)
                }
    MAX-ACCESS  read-create
    STATUS      current
    DESCRIPTION
        "This indicates whether the Frame Relay interface is
        using a multicast service."
    DEFVAL { nonBroadcast }
    ::= { rsFrDlcmiEntry 10 }


rsFrDlcmiStatus OBJECT-TYPE
    SYNTAX      INTEGER {
                    running      (1),    -- init complete, system running
                    fault        (2),    -- error threshold exceeded
                    initializing (3)     -- system start up
                }
    MAX-ACCESS  read-only
    STATUS      current
    DESCRIPTION
        "This indicates the status of the Frame Relay interface
        as determined by the performance of the dlcmi.  If no
        dlcmi is running, the Frame Relay interface will stay
        in the running state indefinitely."
    ::= { rsFrDlcmiEntry 11 }

rsFrDlcmiRowStatus OBJECT-TYPE
    SYNTAX      RowStatus
    MAX-ACCESS  read-create
    STATUS      current
    DESCRIPTION
        "Controls creation/deletion of entries in this table
        according to the RowStatus textual convention, 
        constrained to support the following values only:

            createAndGo
            destroy
            
        To create an entry in this table, the following 
        entry objects MUST be explicitly configured:

            rsFrDlcmiRowStatus
            rsFrDlcmiState
            rsFrDlcmiMaxSupportedVCs
            rsFrDlcmiLowerIfIndex
            rsFrDlcmiRole

        In addition, when creating an entry the following
        conditions must hold:

            A value for rsFrDlcmiIndex must have been determined
            previously, by reading rsFrNextIfIndex. 

            The interface identified by rsFrDlcmiLowerIfIndex
            must exist, and must be an interface type that
            permits layering of Frame Relay above it.

        A corresponding entry in ifTable/ifXTable/rsIfTable is 
        created/destroyed as a result of creating/destroying an entry 
        in this table. If rsFrDlcmiRole is dte(0), a corresponding
        entry is created/deleted in frDlcmiTable."
    ::= { rsFrDlcmiEntry 12 }


rsFrDlcmiLowerIfIndex OBJECT-TYPE
    SYNTAX      InterfaceIndexOrZero
    MAX-ACCESS  read-create
    STATUS      current
    DESCRIPTION
        "The ifIndex of an interface over which this Frame Relay interface 
        is to be layered. A value of zero indicates no layering.
        An implementation may choose to require that a nonzero value
        be configured at entry creation."
    ::= { rsFrDlcmiEntry 13 }


rsFrDlcmiRole OBJECT-TYPE
    SYNTAX      INTEGER {
                    dte(0),
                    dce(1),
                    nni(2)
                }
    MAX-ACCESS  read-create
    STATUS      current
    DESCRIPTION
        "Specifies the role this interface assumes with respect 
        to the remote end.
        
        When acting as a DTE, the following objects are not relevant:

            rsFrDlcmiDcePollingInterval
            rsFrDlcmiDceErrorThreshold
            rsFrDlcmiDceMonitoredEvents

        When acting as a DCE, the following objects are not relevant:

            rsFrDlcmiPollingInterval
            rsFrDlcmiFullEnquiryInterval
            rsFrDlcmiErrorThreshold
            rsFrDlcmiMonitoredEvents
        "
    ::= { rsFrDlcmiEntry 14 }

rsFrDlcmiDcePollingInterval OBJECT-TYPE
    SYNTAX      Integer32 (5..30)
    UNITS       "seconds"
    MAX-ACCESS  read-create
    STATUS      current
    DESCRIPTION
        "The number of seconds within which a DCE
        expects to receive a Status Enquiry from the DTE.

        This value corresponds to the T392 timer.

        Pertains to DCE/NNI operation only. This parameter can
        be reconfigured only when the Frame Relay interface
        is acting as a DCE or NNI."
    DEFVAL  { 15 }
    ::= { rsFrDlcmiEntry 15 }


rsFrDlcmiDceErrorThreshold OBJECT-TYPE
    SYNTAX      Integer32 (1..10)
    MAX-ACCESS  read-create
    STATUS      current
    DESCRIPTION
        "The minimum number of errors that must be observed 
        within the number of events specified by 
        rsFrDlcmiDceMonitoredEvents, to declare the interface down.
        
        'error' is lack of receipt of a Status Enquiry within the 
        interval specified by rsFrDlcmiDcePollingInterval (T392).

        Pertains to DCE/NNI operation only. This parameter can
        be reconfigured only when the Frame Relay interface
        is acting as a DCE or NNI."
    DEFVAL  { 2 }
    ::= { rsFrDlcmiEntry 16 }


rsFrDlcmiDceMonitoredEvents OBJECT-TYPE
    SYNTAX      Integer32 (1..10)
    MAX-ACCESS  read-create
    STATUS      current
    DESCRIPTION
        "The number of DCE polling intervals over which
        accumulated errors are counted against the threshold 
        specified in rsFrDlcmiDceErrorThreshold. 

        If, within this number of events, the number of errors
        equals or exceeds the threshold, the interface is
        declared down.

        The 'DCE polling interval' is specified by
        rsFrDlcmiDcePollingInterval.

        Pertains to DCE/NNI operation only. This parameter can
        be reconfigured only when the Frame Relay interface
        is acting as a DCE or NNI."
    DEFVAL  { 2 }
    ::= { rsFrDlcmiEntry 17 }

--
-- The Frame Relay Dlcmi Statistics Table
--

rsFrDlcmiStatsTable OBJECT-TYPE
    SYNTAX      SEQUENCE OF RsFrDlcmiStatsEntry
    MAX-ACCESS  not-accessible
    STATUS      current
    DESCRIPTION
        "The statistics for the Data Link Connection Management
        Interface for the frame relay service on this interface."
    ::= { rsFrIfLayer 3 }

rsFrDlcmiStatsEntry OBJECT-TYPE
    SYNTAX      RsFrDlcmiStatsEntry
    MAX-ACCESS  not-accessible
    STATUS      current
    DESCRIPTION
        "The statistics for a particular Data Link Connection
        Management Interface.

        Statistics are not relevant while the rsFrDlcmiState
        has the value 'noLmiConfigured'.

        The DTE statistics are relevant when the corresponding
        rsFrDlcmiRole is DTE.

        The DTE statistics are relevant when the corresponding
        rsFrDlcmiRole is DCE."
    INDEX   { rsFrDlcmiIfIndex }
    ::= { rsFrDlcmiStatsTable 1 }

RsFrDlcmiStatsEntry ::= SEQUENCE {
        rsFrDlcmiStatsDteEnquiries                 Counter32,
        rsFrDlcmiStatsDteFullEnquiries             Counter32,
        rsFrDlcmiStatsDteEnquiryResponses          Counter32,
        rsFrDlcmiStatsDteFullEnquiryResponses      Counter32,
        rsFrDlcmiStatsDteAsyncUpdates              Counter32,
        rsFrDlcmiStatsDteUnknownRxMessages         Counter32,
        rsFrDlcmiStatsDteLossOfSequences           Counter32,
        rsFrDlcmiStatsDteNoResponseTimeouts        Counter32,

        rsFrDlcmiStatsDceEnquiries                 Counter32,
        rsFrDlcmiStatsDceFullEnquiries             Counter32,
        rsFrDlcmiStatsDceEnquiryResponses          Counter32,
        rsFrDlcmiStatsDceFullEnquiryResponses      Counter32,
        rsFrDlcmiStatsDceAsyncUpdates              Counter32,
        rsFrDlcmiStatsDceUnknownRxMessages         Counter32,
        rsFrDlcmiStatsDceLossOfSequences           Counter32,
        rsFrDlcmiStatsDceNoResponseTimeouts        Counter32,

        rsFrDlcmiStatsDiscontinuityTime            TimeTicks
}


rsFrDlcmiStatsDteEnquiries OBJECT-TYPE
    SYNTAX      Counter32
    MAX-ACCESS  read-only
    STATUS      current
    DESCRIPTION
        "Number of Status Enquiries sent (as DTE)."
    ::= { rsFrDlcmiStatsEntry 1 }

rsFrDlcmiStatsDteFullEnquiries OBJECT-TYPE
    SYNTAX      Counter32
    MAX-ACCESS  read-only
    STATUS      current
    DESCRIPTION
        "Number of Full Enquiries sent (as DTE)."
    ::= { rsFrDlcmiStatsEntry 2 }

rsFrDlcmiStatsDteEnquiryResponses OBJECT-TYPE
    SYNTAX      Counter32
    MAX-ACCESS  read-only
    STATUS      current
    DESCRIPTION
        "Number of Status Enquiry responses received (as DTE)."
    ::= { rsFrDlcmiStatsEntry 3 }

rsFrDlcmiStatsDteFullEnquiryResponses OBJECT-TYPE
    SYNTAX      Counter32
    MAX-ACCESS  read-only
    STATUS      current
    DESCRIPTION
        "Number of Full Enquiry responses received (as DTE)."
    ::= { rsFrDlcmiStatsEntry 4 }

rsFrDlcmiStatsDteAsyncUpdates OBJECT-TYPE
    SYNTAX      Counter32
    MAX-ACCESS  read-only
    STATUS      current
    DESCRIPTION
        "Number of Asynchronous Updates received (as DTE)."
    ::= { rsFrDlcmiStatsEntry 5 }

rsFrDlcmiStatsDteUnknownRxMessages OBJECT-TYPE
    SYNTAX      Counter32
    MAX-ACCESS  read-only
    STATUS      current
    DESCRIPTION
        "Number of unknown messages received (as DTE)."
    ::= { rsFrDlcmiStatsEntry 6 }

rsFrDlcmiStatsDteLossOfSequences OBJECT-TYPE
    SYNTAX      Counter32
    MAX-ACCESS  read-only
    STATUS      current
    DESCRIPTION
        "Number of times a discontinuity in sequence numbering of received messages 
        was detected (as DTE)."
    ::= { rsFrDlcmiStatsEntry 7 }

rsFrDlcmiStatsDteNoResponseTimeouts OBJECT-TYPE
    SYNTAX      Counter32
    MAX-ACCESS  read-only
    STATUS      current
    DESCRIPTION
        "Number of timer expirations awaiting a Status message (as DTE)."
    ::= { rsFrDlcmiStatsEntry 8 }

rsFrDlcmiStatsDceEnquiries OBJECT-TYPE
    SYNTAX      Counter32
    MAX-ACCESS  read-only
    STATUS      current
    DESCRIPTION
        "Number of Status Enquiries received (as DCE.)"
    ::= { rsFrDlcmiStatsEntry 9 }

rsFrDlcmiStatsDceFullEnquiries OBJECT-TYPE
    SYNTAX      Counter32
    MAX-ACCESS  read-only
    STATUS      current
    DESCRIPTION
        "Number of Full Enquiries received (as DCE)."
    ::= { rsFrDlcmiStatsEntry 10 }

rsFrDlcmiStatsDceEnquiryResponses OBJECT-TYPE
    SYNTAX      Counter32
    MAX-ACCESS  read-only
    STATUS      current
    DESCRIPTION
        "Number of Status Enquiry responses sent (as DCE)."
    ::= { rsFrDlcmiStatsEntry 11 }

rsFrDlcmiStatsDceFullEnquiryResponses OBJECT-TYPE
    SYNTAX      Counter32
    MAX-ACCESS  read-only
    STATUS      current
    DESCRIPTION
        "Number of Full Enquiry responses sent (as DCE)."
    ::= { rsFrDlcmiStatsEntry 12 }

rsFrDlcmiStatsDceAsyncUpdates OBJECT-TYPE
    SYNTAX      Counter32
    MAX-ACCESS  read-only
    STATUS      current
    DESCRIPTION
        "Number of Asynchronous Updates sent (as DCE)."
    ::= { rsFrDlcmiStatsEntry 13 }

rsFrDlcmiStatsDceUnknownRxMessages OBJECT-TYPE
    SYNTAX      Counter32
    MAX-ACCESS  read-only
    STATUS      current
    DESCRIPTION
        "Number of unknown messages received (as DCE)."
    ::= { rsFrDlcmiStatsEntry 14 }

rsFrDlcmiStatsDceLossOfSequences OBJECT-TYPE
    SYNTAX      Counter32
    MAX-ACCESS  read-only
    STATUS      current
    DESCRIPTION
        "Number of times a discontinuity in sequence numbering of received messages 
        was detected (as DCE)."
    ::= { rsFrDlcmiStatsEntry 15 }

rsFrDlcmiStatsDceNoResponseTimeouts OBJECT-TYPE
    SYNTAX      Counter32
    MAX-ACCESS  read-only
    STATUS      current
    DESCRIPTION
        "Number of timer expirations awaiting a Status Enquiry (as DCE)."
    ::= { rsFrDlcmiStatsEntry 16 }

rsFrDlcmiStatsDiscontinuityTime OBJECT-TYPE
    SYNTAX      TimeTicks
    MAX-ACCESS  read-only
    STATUS      current
    DESCRIPTION
        "Value of sysUpTime at the most recent event that caused a 
        discontinuity in the monotonic operation of any of the
        counters in this entry. Such disruption might be caused by:

            Hardware insertion/removal.
            Reconfiguration of rsFrDlcmiState.
            Reconfiguration of rsFrDlcmiRole.

        Conclusions can be drawn from successive polls of an entry's
        counters only if the value of this object, simultaneously
        retrieved in those polls, remains unchanged."
    ::= { rsFrDlcmiStatsEntry 17 }

--
-- Frame Relay Circuit Table
-- 
rsFrCircuitTable OBJECT-TYPE
    SYNTAX      SEQUENCE OF RsFrCircuitEntry
    MAX-ACCESS  not-accessible
    STATUS      current
    DESCRIPTION
       "A table containing information about specific Data
       Link Connections (DLC) or virtual circuits.

       This table mirrors the structure of RFC2115 FRAME-RELAY-DTE-MIB
       frCircuitTable, for the purpose of enumerating circuits on both
       DTE and DCE Frame Relay interfaces."
    ::= { rsFrIfLayer 4 }

rsFrCircuitEntry OBJECT-TYPE
    SYNTAX      RsFrCircuitEntry
    MAX-ACCESS  not-accessible
    STATUS      current
    DESCRIPTION
       "The information regarding a single Data Link
       Connection.  Discontinuities in the counters contained
       in this table are indicated by the value in
       rsFrCircuitCreationTime."
    INDEX { rsFrCircuitIfIndex, rsFrCircuitDlci }
    ::= { rsFrCircuitTable 1 }


RsFrCircuitEntry ::= SEQUENCE {
        rsFrCircuitIfIndex                InterfaceIndex,
        rsFrCircuitDlci                   DLCI,
        rsFrCircuitState                  INTEGER,
        rsFrCircuitReceivedFECNs          Counter32,
        rsFrCircuitReceivedBECNs          Counter32,
        rsFrCircuitSentFrames             Counter32,
        rsFrCircuitSentOctets             Counter32,
        rsFrCircuitReceivedFrames         Counter32,
        rsFrCircuitReceivedOctets         Counter32,
        rsFrCircuitCreationTime           TimeStamp,
        rsFrCircuitLastTimeChange         TimeStamp,
        rsFrCircuitCommittedBurst         Integer32,
        rsFrCircuitExcessBurst            Integer32,
        rsFrCircuitThroughput             Integer32,
        rsFrCircuitMulticast              INTEGER,
        rsFrCircuitType                   INTEGER,
        rsFrCircuitDiscards               Counter32,
        rsFrCircuitReceivedDEs            Counter32,
        rsFrCircuitSentDEs                Counter32,
        rsFrCircuitLogicalIfIndex         InterfaceIndex,
        rsFrCircuitRowStatus              RowStatus,
        rsFrCircuitSentFECNs              Counter32,
        rsFrCircuitSentBECNs              Counter32
}


rsFrCircuitIfIndex OBJECT-TYPE
    SYNTAX      InterfaceIndex
    MAX-ACCESS  not-accessible
    STATUS      current
    DESCRIPTION
        "The ifIndex Value of the ifEntry this virtual circuit
        is layered onto."
    ::= { rsFrCircuitEntry 1 }

rsFrCircuitDlci OBJECT-TYPE
    SYNTAX      DLCI
    MAX-ACCESS  not-accessible
    STATUS      current
    DESCRIPTION
        "The Data Link Connection Identifier for this virtual
        circuit."
    REFERENCE
        "American National Standard T1.618-1991, Section 3.3.6"
    ::= { rsFrCircuitEntry 2 }

rsFrCircuitState OBJECT-TYPE
    SYNTAX      INTEGER {
                    invalid (1),
                    active (2),
                    inactive (3)
                }
    MAX-ACCESS  read-create
    STATUS      current
    DESCRIPTION
        "Indicates whether the particular virtual circuit is
        operational.  In the absence of a Data Link Connection
        Management Interface, virtual circuit entries (rows)
        may be created by setting virtual circuit state to
        'active', or deleted by changing Circuit state to
        'invalid'.

        Whether or not the row actually disappears is left to
        the implementation, so this object may actually read as
        'invalid' for some arbitrary length of time.  It is
        also legal to set the state of a virtual circuit to
        'inactive' to temporarily disable a given circuit.

        The use of 'invalid' is deprecated in this SNMP Version
        2 MIB, in favor of rsFrCircuitRowStatus."
    DEFVAL { active }
    ::= { rsFrCircuitEntry 3 }

rsFrCircuitReceivedFECNs OBJECT-TYPE
    SYNTAX      Counter32
    MAX-ACCESS  read-only
    STATUS      current
    DESCRIPTION
        "Number of frames received from the network indicating
        forward congestion since the virtual circuit was
        created.  This occurs when the remote DTE sets the FECN
        flag, or when a switch in the network enqueues the
        frame to a trunk whose transmission queue is
        congested."
    REFERENCE
        "American National Standard T1.618-1991, Section 3.3.3"
    ::= { rsFrCircuitEntry 4 }


rsFrCircuitReceivedBECNs OBJECT-TYPE
    SYNTAX      Counter32
    MAX-ACCESS  read-only
    STATUS      current
    DESCRIPTION
        "Number of frames received from the network indicating
        backward congestion since the virtual circuit was
        created.  This occurs when the remote DTE sets the BECN
        flag, or when a switch in the network receives the
        frame from a trunk whose transmission queue is
        congested."
    REFERENCE
        "American National Standard T1.618-1991, Section 3.3.4"
    ::= { rsFrCircuitEntry 5 }


rsFrCircuitSentFrames OBJECT-TYPE
    SYNTAX      Counter32
    MAX-ACCESS  read-only
    STATUS      current
    DESCRIPTION
        "The number of frames sent from this virtual circuit
        since it was created."
    ::= { rsFrCircuitEntry 6 }


rsFrCircuitSentOctets OBJECT-TYPE
    SYNTAX      Counter32
    MAX-ACCESS  read-only
    STATUS      current
    DESCRIPTION
        "The number of octets sent from this virtual circuit
        since it was created.  Octets counted are the full
        frame relay header and the payload, but do not include
        the flag characters or CRC."
    ::= { rsFrCircuitEntry 7 }


rsFrCircuitReceivedFrames OBJECT-TYPE
    SYNTAX      Counter32
    MAX-ACCESS  read-only
    STATUS      current
    DESCRIPTION
        "Number of frames received over this virtual circuit
        since it was created."
    ::= { rsFrCircuitEntry 8 }


rsFrCircuitReceivedOctets OBJECT-TYPE
    SYNTAX      Counter32
    MAX-ACCESS  read-only
    STATUS      current
    DESCRIPTION
        "Number of octets received over this virtual circuit
        since it was created.  Octets counted include the full
        frame relay header, but do not include the flag
        characters or the CRC."
    ::= { rsFrCircuitEntry 9 }


rsFrCircuitCreationTime OBJECT-TYPE
    SYNTAX      TimeStamp
    MAX-ACCESS  read-only
    STATUS      current
    DESCRIPTION
        "The value of sysUpTime when the virtual circuit was
        created, whether by the Data Link Connection Management
        Interface or by a SetRequest."
    ::= { rsFrCircuitEntry 10 }

rsFrCircuitLastTimeChange OBJECT-TYPE
    SYNTAX      TimeStamp
    MAX-ACCESS  read-only
    STATUS      current
    DESCRIPTION
        "The value of sysUpTime when last there was a change in
        the virtual circuit state"
    ::= { rsFrCircuitEntry 11 }


rsFrCircuitCommittedBurst OBJECT-TYPE
    SYNTAX      Integer32(0..2147483647)
    MAX-ACCESS  read-create
    STATUS      current
    DESCRIPTION
        "This variable indicates the maximum amount of data, in
        bits, that the network agrees to transfer under normal
        conditions, during the measurement interval."
    REFERENCE
        "American National Standard T1.617-1991, Section
        6.5.19"
    DEFVAL  { 0 }  -- the default indicates no commitment
    ::= { rsFrCircuitEntry 12 }


rsFrCircuitExcessBurst OBJECT-TYPE
    SYNTAX      Integer32(0..2147483647)
    MAX-ACCESS  read-create
    STATUS      current
    DESCRIPTION
        "This variable indicates the maximum amount of
        uncommitted data bits that the network will attempt to
        deliver over the measurement interval.

        By default, if not configured when creating the entry,
        the Excess Information Burst Size is set to the value
        of ifSpeed."
    REFERENCE
        "American National Standard T1.617-1991, Section
        6.5.19"
    ::= { rsFrCircuitEntry 13 }


rsFrCircuitThroughput OBJECT-TYPE
    SYNTAX      Integer32(0..2147483647)
    MAX-ACCESS  read-create
    STATUS      current
    DESCRIPTION
        "Throughput is the average number of 'Frame Relay
        Information Field' bits transferred per second across a
        user network interface in one direction, measured over
        the measurement interval.

        If the configured committed burst rate and throughput
        are both non-zero, the measurement interval, T, is

            T=rsFrCircuitCommittedBurst/rsFrCircuitThroughput.

        If the configured committed burst rate and throughput
        are both zero, the measurement interval, T, is

            T=rsFrCircuitExcessBurst/ifSpeed."
    REFERENCE
        "American National Standard T1.617-1991, Section
        6.5.19"
    DEFVAL  {0}  -- the default value of Throughput is "no commitment".
    ::= { rsFrCircuitEntry 14 }


rsFrCircuitMulticast OBJECT-TYPE
    SYNTAX      INTEGER {
                    unicast   (1),
                    oneWay    (2),
                    twoWay    (3),
                    nWay      (4)
                }
    MAX-ACCESS  read-create
    STATUS      current
    DESCRIPTION
        "This indicates whether this VC is used as a unicast VC
        (i.e. not multicast) or the type of multicast service
        subscribed to"
    REFERENCE
        "Frame Relay PVC Multicast Service and Protocol
        Description Implementation: FRF.7 Frame Relay Forum
        Technical Committe October 21, 1994"
    DEFVAL  {unicast}
    ::= { rsFrCircuitEntry 15 }


rsFrCircuitType OBJECT-TYPE
    SYNTAX      INTEGER {
                    static  (1),
                    dynamic (2)
                }
    MAX-ACCESS  read-only
    STATUS      current
    DESCRIPTION
        "Indication of whether the VC was manually created
        (static), or dynamically created (dynamic) via the data
        link control management interface."
    ::= { rsFrCircuitEntry 16 }


rsFrCircuitDiscards OBJECT-TYPE
    SYNTAX      Counter32
    MAX-ACCESS  read-only
    STATUS      current
    DESCRIPTION
        "The number of inbound frames dropped because of format
        errors, or because the VC is inactive."
    ::= { rsFrCircuitEntry 17 }


rsFrCircuitReceivedDEs OBJECT-TYPE
    SYNTAX      Counter32
    MAX-ACCESS  read-only
    STATUS      current
    DESCRIPTION
        "Number of frames received from the network indicating
        that they were eligible for discard since the virtual
        circuit was created.  This occurs when the remote DTE
        sets the DE flag, or when in remote DTE's switch
        detects that the frame was received as Excess Burst
        data."
    REFERENCE
        "American National Standard T1.618-1991, Section 3.3.4"
    ::= { rsFrCircuitEntry 18 }


rsFrCircuitSentDEs OBJECT-TYPE
    SYNTAX      Counter32
    MAX-ACCESS  read-only
    STATUS      current
    DESCRIPTION
        "Number of frames sent to the network indicating that
        they were eligible for discard since the virtual
        circuit was created.   This occurs when the local DTE
        sets the DE flag, indicating that during Network
        congestion situations those frames should be discarded
        in preference of other frames sent without the DE bit
        set."
    REFERENCE
        "American National  Standard  T1.618-1991, Section
        3.3.4"
   ::= { rsFrCircuitEntry 19 }

rsFrCircuitLogicalIfIndex OBJECT-TYPE
    SYNTAX      InterfaceIndex
    MAX-ACCESS  read-create
    STATUS      current
    DESCRIPTION
        "Normally the same value as frDlcmiIfIndex, but
        different when an implementation associates a virtual
        ifEntry with a DLC or set of DLCs in order to associate
        higher layer objects such as the ipAddrEntry with a
        subset of the virtual circuits on a Frame Relay
        interface. The type of such ifEntries is defined by the
        higher layer object; for example, if PPP/Frame Relay is
        implemented, the ifType of this ifEntry would be PPP.
        If it is not so defined, as would be the case with an
        ipAddrEntry, it should be of type Other."
    ::= { rsFrCircuitEntry 20 }

rsFrCircuitRowStatus OBJECT-TYPE
    SYNTAX      RowStatus
    MAX-ACCESS  read-create
    STATUS      current
    DESCRIPTION
        "This object is used to create a new row or modify or
        destroy an existing row in the manner described in the
        definition of the RowStatus textual convention.
        Writable objects in the table may be written in any
        RowStatus state."
    ::= { rsFrCircuitEntry 21 }

rsFrCircuitSentFECNs OBJECT-TYPE
    SYNTAX      Counter32
    MAX-ACCESS  read-only
    STATUS      current
    DESCRIPTION
        "Number of frames sent to the network indicating
        forward congestion since the virtual circuit was
        created.  This occurs when the remote DTE sets the FECN
        flag, or when a switch in the network enqueues the
        frame to a trunk whose transmission queue is
        congested."
    REFERENCE
        "American National Standard T1.618-1991, Section 3.3.3"
    ::= { rsFrCircuitEntry 22 }


rsFrCircuitSentBECNs OBJECT-TYPE
    SYNTAX      Counter32
    MAX-ACCESS  read-only
    STATUS      current
    DESCRIPTION
        "Number of frames sent to the network indicating
        backward congestion since the virtual circuit was
        created.  This occurs when the remote DTE sets the BECN
        flag, or when a switch in the network receives the
        frame from a trunk whose transmission queue is
        congested."
    REFERENCE
        "American National Standard T1.618-1991, Section 3.3.4"
    ::= { rsFrCircuitEntry 23 }




-- //////////////////////////////////////////////////////////////////////
--
-- Frame Relay Subinterface Layer
--
-- This layer is managed with the following elements:
--
--  o NextIfIndex (generator for Frame Relay subinterface IfIndex selection)
--  o SubIf Table (creation/configuration/deletion of Frame Relay subinterfaces)
--  o SubIf Circuit Table (creation/deletion of circuits assoc. w/ subinterfaces)
--
-- //////////////////////////////////////////////////////////////////////

--
-- IfIndex selection for creating new Frame Relay Subinterfaces
--

rsFrSubIfNextIfIndex OBJECT-TYPE
    SYNTAX      RsNextIfIndex
    MAX-ACCESS  read-only
    STATUS      current
    DESCRIPTION
        "Coordinate ifIndex value allocation for entries
        in rsFrSubIfTable.

        A GET of this object returns the next available ifIndex 
        value to be used to create an entry in the associated
        interface table; or zero, if no valid ifIndex value is
        available. This object also returns a value of zero when 
        it is the lexicographic successor of a varbind presented 
        in an SNMP GETNEXT or GETBULK request, for which circumstance
        it is assumed that ifIndex allocation is unintended.

        Successive GETs will typically return different
        values, thus avoiding collisions among cooperating
        management clients seeking to create table entries
        simultaneously.
        "
    ::= { rsFrSubIfLayer 1 }

--
-- The Frame Relay Subinterface Table
--

rsFrSubIfTable OBJECT-TYPE
    SYNTAX      SEQUENCE OF RsAtmSubIfEntry
    MAX-ACCESS  not-accessible
    STATUS      current
    DESCRIPTION
        "This table contains entries for Frame Relay Subinterfaces present 
        in the system."
    ::= { rsFrSubIfLayer 2 }

rsFrSubIfEntry OBJECT-TYPE
    SYNTAX      RsAtmSubIfEntry
    MAX-ACCESS  not-accessible
    STATUS      current
    DESCRIPTION
        "Each entry describes the characteristics of a Frame Relay Subinterface. 
        Creating/deleting entries in this table causes corresponding 
        entries for be created /deleted in ifTable/ifXTable/rsIfTable."
    INDEX   { rsFrSubIfIndex }
    ::= { rsFrSubIfTable 1 }

RsAtmSubIfEntry ::= SEQUENCE {
    rsFrSubIfIndex
        InterfaceIndex,
    rsFrSubIfRowStatus
        RowStatus,
    rsFrSubIfLowerIfIndex
        InterfaceIndexOrZero,
    rsFrSubIfId
        Integer32
    }


rsFrSubIfIndex OBJECT-TYPE
    SYNTAX      InterfaceIndex
    MAX-ACCESS  not-accessible
    STATUS      current
    DESCRIPTION
        "The ifIndex of the Frame Relay Subinterface. When 
        creating entries in this table, suitable values
        for this object are determined by reading
        rsFrSubNextIfIndex."
    ::= { rsFrSubIfEntry 1 }

rsFrSubIfRowStatus OBJECT-TYPE
    SYNTAX      RowStatus
    MAX-ACCESS  read-create
    STATUS      current
    DESCRIPTION
        "Controls creation/deletion of entries in this table
        according to the RowStatus textual convention, 
        constrained to support the following values only:

            createAndGo
            destroy
            
        To create an entry in this table, the following 
        entry objects MUST be explicitly configured:

            rsFrSubIfRowStatus
            rsFrSubIfLowerIfIndex

        In addition, when creating an entry the following
        conditions must hold:

            A value for rsFrSubIfIndex must have been determined
            previously, by reading rsFrSubIfNextIfIndex. 

            The interface identified by rsFrSubIfLowerIfIndex
            must exist, and must be a Frame Relay interface.

            A positive value configured for rsFrSubIfId must not
            already be assigned to another subinterface layered
            onto the same underlying Frame Relay interface.

        A corresponding entry in ifTable/ifXTable/rsIfTable is 
        created/destroyed as a result of creating/destroying an entry 
        in this table.
        "
    ::= { rsFrSubIfEntry 2 }

rsFrSubIfLowerIfIndex OBJECT-TYPE
    SYNTAX      InterfaceIndexOrZero
    MAX-ACCESS  read-create
    STATUS      current
    DESCRIPTION
        "The ifIndex of a Frame Relay interface over which this 
        Frame Relay Subinterface is to be layered. A value of zero 
        indicates no layering. An implementation may choose to require 
        that a nonzero value be configured at entry creation."
    ::= { rsFrSubIfEntry 3 }


rsFrSubIfId OBJECT-TYPE
    SYNTAX      Integer32 (-1..2147483647)
    MAX-ACCESS  read-create
    STATUS      current
    DESCRIPTION
        "An integer identifier for the Frame Relay subinterface, 
        used in conjunction with the command-line interface. 
        It is provided here for cross-reference purposes only.

        The value must be unique among subinterfaces configured on the same 
        underlying Frame Relay interface.
        
        If this object is not configured, or is configured with a 
        value of -1, a nonzero value will be allocated internally
        and can be retrieved from this object after table entry creation 
        has succeeded.

        A value of zero for this object is reserved for future use."
    DEFVAL { -1 }
    ::= { rsFrSubIfEntry 4 }

--
-- The Frame Relay Subinterface Circuit Table
--

rsFrSubIfCktTable OBJECT-TYPE
    SYNTAX      SEQUENCE OF RsFrSubIfCktEntry
    MAX-ACCESS  not-accessible
    STATUS      current
    DESCRIPTION
        "This table contains entries for Frame Relay circuits configured on 
        Frame Relay Subinterfaces present in the system.

        An implementation may constrain the number of circuits permitted
        to be configured per Frame Relay Subinterface; in particular,
        an implementation may restrict each Frame Relay Subinterface to
        have a single circuit.
        
        Attributes in this entry can only be configured at entry creation,
        and remain fixed for the lifetime of the entry.
        "
    ::= { rsFrSubIfLayer 3 }

rsFrSubIfCktEntry OBJECT-TYPE
    SYNTAX      RsFrSubIfCktEntry
    MAX-ACCESS  not-accessible
    STATUS      current
    DESCRIPTION
        "Each entry describes the characteristics of a Frame Relay Subinterface circuit."
    INDEX   { rsFrSubIfIndex, rsFrSubIfCktDlci }
    ::= { rsFrSubIfCktTable 1 }

RsFrSubIfCktEntry ::= SEQUENCE {
    rsFrSubIfCktDlci
        DLCI,
    rsFrSubIfCktRowStatus
        RowStatus
    }


rsFrSubIfCktDlci OBJECT-TYPE
    SYNTAX      DLCI
    MAX-ACCESS  not-accessible
    STATUS      current
    DESCRIPTION
        "The DLCI of the Frame Relay circuit used by this subinterface."
    ::= { rsFrSubIfCktEntry 1 }

rsFrSubIfCktRowStatus OBJECT-TYPE
    SYNTAX      RowStatus
    MAX-ACCESS  read-create
    STATUS      current
    DESCRIPTION
        "Controls creation/deletion of entries in this table
        according to the RowStatus textual convention, 
        constrained to support the following values only:

            createAndGo
            destroy
            
        To create an entry in this table, the following 
        entry objects MUST be explicitly configured:

            rsFrSubIfCktRowStatus
        "
    ::= { rsFrSubIfCktEntry 2 }


-- ++++++++++++++++++++++++++++++++++++++++++++++++++++++++++++++++++++++
-- Notification control objects
-- ++++++++++++++++++++++++++++++++++++++++++++++++++++++++++++++++++++++

-- No notifications are defined in this MIB. Placeholder follows.

-- rsFrTrapControl      OBJECT IDENTIFIER ::= { rsFrameRelayMIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- rsFrTraps            OBJECT IDENTIFIER ::= { rsFrameRelayMIB 3 }
-- rsFrTrapPrefix       OBJECT IDENTIFIER ::= { rsFrTraps 0 }



-- ++++++++++++++++++++++++++++++++++++++++++++++++++++++++++++++++++++++
-- Conformance information
-- ++++++++++++++++++++++++++++++++++++++++++++++++++++++++++++++++++++++

rsFrConformance OBJECT IDENTIFIER ::= { rsFrameRelayMIB 4 }
rsFrCompliances OBJECT IDENTIFIER ::= { rsFrConformance 1 }
rsFrGroups      OBJECT IDENTIFIER ::= { rsFrConformance 2 }

-- compliance statements

rsFrCompliance MODULE-COMPLIANCE
        STATUS  current
        DESCRIPTION
                "The compliance statement for entities which implement
                the Redstone Frame Relay MIB."
        MODULE  -- this module
                MANDATORY-GROUPS { rsFrGroup, rsFrSubIfGroup }
        ::= { rsFrCompliances 1 }

-- units of conformance

rsFrGroup OBJECT-GROUP
        OBJECTS {
		rsFrNextIfIndex,

        rsFrDlcmiIfIndex,
        rsFrDlcmiState,
        rsFrDlcmiAddress,
        rsFrDlcmiAddressLen,
        rsFrDlcmiPollingInterval,
        rsFrDlcmiFullEnquiryInterval,
        rsFrDlcmiErrorThreshold,
        rsFrDlcmiMonitoredEvents,
        rsFrDlcmiMaxSupportedVCs,
        rsFrDlcmiMulticast,
        rsFrDlcmiStatus,
        rsFrDlcmiRowStatus,
        rsFrDlcmiLowerIfIndex,
        rsFrDlcmiRole,
        rsFrDlcmiDcePollingInterval,
        rsFrDlcmiDceErrorThreshold,
        rsFrDlcmiDceMonitoredEvents,

        rsFrDlcmiStatsDteEnquiries,
        rsFrDlcmiStatsDteFullEnquiries,
        rsFrDlcmiStatsDteEnquiryResponses,
        rsFrDlcmiStatsDteFullEnquiryResponses,
        rsFrDlcmiStatsDteAsyncUpdates,
        rsFrDlcmiStatsDteUnknownRxMessages,
        rsFrDlcmiStatsDteLossOfSequences,
        rsFrDlcmiStatsDteNoResponseTimeouts,
        rsFrDlcmiStatsDceEnquiries,
        rsFrDlcmiStatsDceFullEnquiries,
        rsFrDlcmiStatsDceEnquiryResponses,
        rsFrDlcmiStatsDceFullEnquiryResponses,
        rsFrDlcmiStatsDceAsyncUpdates,
        rsFrDlcmiStatsDceUnknownRxMessages,
        rsFrDlcmiStatsDceLossOfSequences,
        rsFrDlcmiStatsDceNoResponseTimeouts,
        rsFrDlcmiStatsDiscontinuityTime,

        rsFrCircuitState,
        rsFrCircuitReceivedFECNs,
        rsFrCircuitReceivedBECNs,
        rsFrCircuitSentFrames,
        rsFrCircuitSentOctets,
        rsFrCircuitReceivedFrames,
        rsFrCircuitReceivedOctets,
        rsFrCircuitCreationTime,
        rsFrCircuitLastTimeChange,
        rsFrCircuitCommittedBurst,
        rsFrCircuitExcessBurst,
        rsFrCircuitThroughput,
        rsFrCircuitMulticast,
        rsFrCircuitType,
        rsFrCircuitDiscards,
        rsFrCircuitReceivedDEs,
        rsFrCircuitSentDEs,
        rsFrCircuitLogicalIfIndex,
        rsFrCircuitRowStatus,
        rsFrCircuitSentFECNs,
        rsFrCircuitSentBECNs
	}
	STATUS  current
	DESCRIPTION
		"A collection of objects providing management of Frame Relay interfaces
		in a Redstone product."
    ::= { rsFrGroups 1 }

rsFrSubIfGroup OBJECT-GROUP
        OBJECTS {
		rsFrSubIfNextIfIndex,

		rsFrSubIfRowStatus,
		rsFrSubIfLowerIfIndex,
        rsFrSubIfId,

        rsFrSubIfCktRowStatus
	}
	STATUS  current
	DESCRIPTION
		"A collection of objects providing management of Frame Relay subinterfaces
		in a Redstone product."
    ::= { rsFrGroups 2 }

END
