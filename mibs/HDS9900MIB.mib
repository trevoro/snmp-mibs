-- MIB Specification for Hitachi Data Systems 9900 Storage Array 
-- Version 4.04
-- Supports extended MIB functionality.
-- 
-- ************************************************************************
-- Notice Statement:
-- 
-- Copyright, Hitachi, Ltd., Hitachi Data Systems Corporation, 2000.  
-- All rights reserved.
-- 
-- This document contains information which is owned by and proprietary to 
-- Hitachi, Ltd. and Hitachi Data Systems Corporation.  End users, resellers, 
-- distributors and other authorized parties are granted a non-exclusive 
-- license to: 
-- 
--		Use this document solely in connection with the management of 
--		Hitachi, Ltd. and Hitachi Data Systems products;  and
-- 
--		Reproduce this document in conjunction with such licensed use on the 
--		strict conditions that (a) this Notice Statement is included in its 
--		entirety in all such reproductions and (b) the document is reproduced 
--		unchanged and in its entirety.
-- 
-- This license terminates immediately and without notice on the violation of 
-- any of the terms of this Notice Statement.
-- 
-- THIS DOCUMENT IS PROVIDED "AS IS" WITHOUT ANY WARRANTY OF ANY KIND, EXPRESS 
-- OR IMPLIED, INCLUDING, WITHOUT LIMITATION, THE IMPLIED WARRANTIES OF 
-- MERCHANTABILITY, FITNESS FOR A PARTICULAR PURPOSE OR NON-INFRINGEMENT.
-- 
-- USERS OF THIS DOCUMENT ARE SOLELY RESPONSIBLE FOR ITS USE AND ANY RESULTS, 
-- DIRECT OR INDIRECT, OF SUCH USE.  HITACHI, LTD. AND HITACHI DATA SYSTEMS 
-- DISCLAIM ANY LIABILITY FOR ANY DAMAGES, DIRECT, INDIRECT, INCIDENTAL, 
-- CONSEQUENTIAL OR OTHERWISE RESULTING, DIRECTLY OR INDIRECTLY, FROM USE OF 
-- THE INFORMATION IN THIS DOCUMENT. 
-- 
-- This document may contain technical or editorial errors or omissions.  
-- Hitachi, Ltd. and Hitachi Data Systems disclaim any liability for such 
-- errors or omissions.
-- 
-- This document is subject to change without notice.
-- 
-- Not all product features described in this document may be currently 
-- available.  Contact your local Hitachi Data Systems sales office for 
-- information on feature and product availability.
-- ************************************************************************
-- 
-- 



HDS9900MIB DEFINITIONS ::= BEGIN

IMPORTS
	Counter FROM RFC1155-SMI
	OBJECT-TYPE		FROM RFC-1212
	TRAP-TYPE		FROM RFC-1215
	DisplayString	FROM RFC1213-MIB
	enterprises		FROM RFC1155-SMI;

--
-- Hitachi and RAID sub-tree
--

	hitachi			OBJECT IDENTIFIER ::= { enterprises 116 }
	system			OBJECT IDENTIFIER ::= { hitachi 3 }
	storage			OBJECT IDENTIFIER ::= { system 11 }
	raid			OBJECT IDENTIFIER ::= { storage 4 }
	raidDummy		OBJECT IDENTIFIER ::= { raid 1 }
	raidRoot			OBJECT IDENTIFIER ::= { raidDummy 1 }

	systemExMib		OBJECT IDENTIFIER ::= { hitachi 5 }
	storageExMib		OBJECT IDENTIFIER ::= { systemExMib 11 }
	raidExMib		OBJECT IDENTIFIER ::= { storageExMib 4 }
	raidExMibDummy		OBJECT IDENTIFIER ::= { raidExMib 1 }
	raidExMibRoot		OBJECT IDENTIFIER ::= { raidExMibDummy 1 }

--
-- Basic information
--

	raidExMibName		OBJECT-TYPE
		SYNTAX		DisplayString
		ACCESS		read-only
		STATUS		mandatory
		DESCRIPTION
			"Product name of the SVP."
		::= { raidExMibRoot 1 }

	raidExMibVersion	OBJECT-TYPE
		SYNTAX		DisplayString
		ACCESS		read-only
		STATUS		mandatory
		DESCRIPTION
			"SVP micro-program version."
		::= { raidExMibRoot 2 }

	raidExMibAgentVersion	OBJECT-TYPE
		SYNTAX		DisplayString
		ACCESS		read-only
		STATUS		mandatory
		DESCRIPTION
			"Extension Agent version."
		::= { raidExMibRoot 3 }

	raidExMibDkcCount	OBJECT-TYPE
		SYNTAX		INTEGER
		ACCESS		read-only
		STATUS		mandatory
		DESCRIPTION
			"Number of DKC registered on the SVP."
		::= { raidExMibRoot 4 }

--
-- Raid list
--

	raidExMibRaidListTable	OBJECT-TYPE
		SYNTAX		SEQUENCE OF RaidExMibRaidListEntry
		ACCESS		not-accessible
		STATUS		mandatory
		DESCRIPTION
			"List of DKC registered on the SVP."
		::= { raidExMibRoot 5 }

	raidExMibRaidListEntry		OBJECT-TYPE
		SYNTAX		RaidExMibRaidListEntry
		ACCESS		not-accessible
		STATUS		mandatory
		DESCRIPTION
			"Entry of DKC list."
		INDEX {
			raidlistSerialNumber
		}
		::= { raidExMibRaidListTable 1 }

	RaidExMibRaidListEntry ::=
		SEQUENCE {
		raidlistSerialNumber	INTEGER,
		raidlistMibNickName	DisplayString (SIZE(0..18)),
		raidlistDKCMainVersion	DisplayString,
		raidlistDKCProductName	DisplayString
		}

	raidlistSerialNumber	OBJECT-TYPE
		SYNTAX		INTEGER
		ACCESS		read-only
		STATUS		mandatory
		DESCRIPTION
			"Serial Number of the DKC."
		::= { raidExMibRaidListEntry 1 }

	raidlistMibNickName	OBJECT-TYPE
		SYNTAX		DisplayString (SIZE(0..18))
		ACCESS		read-only
		STATUS		mandatory
		DESCRIPTION	
			"Nickname of the DKC."
		::= { raidExMibRaidListEntry 2 }

	raidlistDKCMainVersion	OBJECT-TYPE
		SYNTAX		DisplayString
		ACCESS		read-only
		STATUS		mandatory
		DESCRIPTION	
			"DKC Firmware Version."
		::= { raidExMibRaidListEntry 3 }

	raidlistDKCProductName	OBJECT-TYPE
		SYNTAX		DisplayString
		ACCESS		read-only
		STATUS		mandatory
		DESCRIPTION	
			"DKC Product Name."
		::= { raidExMibRaidListEntry 4 }

--
-- Disk controller information
--

	raidExMibDKCHWTable		OBJECT-TYPE
		SYNTAX		SEQUENCE OF RaidExMibDKCHWEntry
		ACCESS		not-accessible 
		STATUS		mandatory
		DESCRIPTION	
			"Error information of the DKC."
		::= { raidExMibRoot 6 }

	raidExMibDKCHWEntry		OBJECT-TYPE
		SYNTAX		RaidExMibDKCHWEntry
		ACCESS		not-accessible
		STATUS		mandatory
		DESCRIPTION	
			"Entry of DKC information."
		INDEX		{
			dkcRaidListIndexSerialNumber
		}
		::= { raidExMibDKCHWTable 1 }
		
	RaidExMibDKCHWEntry ::=
		SEQUENCE	{
			dkcRaidListIndexSerialNumber	INTEGER,
			dkcHWProcessor			INTEGER,
			dkcHWCSW				INTEGER,
			dkcHWCache			INTEGER,
			dkcHWSM				INTEGER,
			dkcHWPS				INTEGER,
			dkcHWBattery			INTEGER,
			dkcHWFan				INTEGER,
			dkcHWEnvironment			INTEGER
		}

	dkcRaidListIndexSerialNumber	OBJECT-TYPE
		SYNTAX		INTEGER
		ACCESS		read-only
		STATUS		mandatory
		DESCRIPTION	
			"Serial Number the DKC."
		::= { raidExMibDKCHWEntry 1 }

	dkcHWProcessor		OBJECT-TYPE
		SYNTAX		INTEGER {
					noError(1),
					acute(2),
					serious(3),
					moderate(4),
					service(5)
		}
		ACCESS		read-only
		STATUS		mandatory
		DESCRIPTION
			"Information of processor."
		::= { raidExMibDKCHWEntry 2 }

	dkcHWCSW		OBJECT-TYPE
		SYNTAX		INTEGER {
					noError(1),
					acute(2),
					serious(3),
					moderate(4),
					service(5)
		}
		ACCESS		read-only
		STATUS		mandatory
		DESCRIPTION
			"Information of internal bus."
		::= { raidExMibDKCHWEntry 3 }

	dkcHWCache		OBJECT-TYPE
		SYNTAX		INTEGER {
					noError(1),
					acute(2),
					serious(3),
					moderate(4),
					service(5)
		}
		ACCESS		read-only
		STATUS		mandatory
		DESCRIPTION
			"Information of cache."
		::= { raidExMibDKCHWEntry 4 }

	dkcHWSM			OBJECT-TYPE
		SYNTAX		INTEGER {
					noError(1),
					acute(2),
					serious(3),
					moderate(4),
					service(5)
		}
		ACCESS		read-only
		STATUS		mandatory
		DESCRIPTION
			"Information of shared memory."
		::= { raidExMibDKCHWEntry 5 }

	dkcHWPS		OBJECT-TYPE
		SYNTAX		INTEGER {
					noError(1),
					acute(2),
					serious(3),
					moderate(4),
					service(5)
		}
		ACCESS		read-only
		STATUS		mandatory
		DESCRIPTION
			"Information of power supply."
		::= { raidExMibDKCHWEntry 6 }

	dkcHWBattery		OBJECT-TYPE
		SYNTAX		INTEGER {
					noError(1),
					acute(2),
					serious(3),
					moderate(4),
					service(5)
		}
		ACCESS		read-only
		STATUS		mandatory
		DESCRIPTION
			"Information of battery."
		::= { raidExMibDKCHWEntry 7 }

	dkcHWFan		OBJECT-TYPE
		SYNTAX		INTEGER {
					noError(1),
					acute(2),
					serious(3),
					moderate(4),
					service(5)
		}
		ACCESS		read-only
		STATUS		mandatory
		DESCRIPTION
			"Information of fan."
		::= { raidExMibDKCHWEntry 8 }

	dkcHWEnvironment	OBJECT-TYPE
		SYNTAX		INTEGER {
					noError(1),
					acute(2),
					serious(3),
					moderate(4),
					service(5)
		}
		ACCESS		read-only
		STATUS		mandatory
		DESCRIPTION
			"Information of Environment."
		::= { raidExMibDKCHWEntry 9}

--
-- Disk unit information
--

	raidExMibDKUHWTable		OBJECT-TYPE
		SYNTAX		SEQUENCE OF RaidExMibDKUHWEntry
		ACCESS		not-accessible
		STATUS		mandatory
		DESCRIPTION	
			"Error information of the DKU."
		::= { raidExMibRoot 7 }

	raidExMibDKUHWEntry		OBJECT-TYPE
		SYNTAX		RaidExMibDKUHWEntry
		ACCESS		not-accessible
		STATUS		mandatory
		DESCRIPTION
			"Entry of DKU information."
		INDEX {
			dkuRaidListIndexSerialNumber
		}
		::= { raidExMibDKUHWTable 1 }

	RaidExMibDKUHWEntry ::=
		SEQUENCE	{
			dkuRaidListIndexSerialNumber	INTEGER,
			dkuHWPS				INTEGER,
			dkuHWFan				INTEGER,
			dkuHWEnvironment			INTEGER,
			dkuHWDrive			INTEGER
		}

	dkuRaidListIndexSerialNumber	OBJECT-TYPE
		SYNTAX		INTEGER
		ACCESS		read-only
		STATUS		mandatory
		DESCRIPTION
			"Serial Number of the DKC."
		::= { raidExMibDKUHWEntry 1 }

	dkuHWPS			OBJECT-TYPE
		SYNTAX		INTEGER {
					noError(1),
					acute(2),
					serious(3),
					moderate(4),
					service(5)
		}
		ACCESS		read-only
		STATUS		mandatory
		DESCRIPTION
			"Information of DKU power supply."
		::= { raidExMibDKUHWEntry 2 }

	dkuHWFan		OBJECT-TYPE
		SYNTAX		INTEGER {
					noError(1),
					acute(2),
					serious(3),
					moderate(4),
					service(5)
		}
		ACCESS		read-only
		STATUS		mandatory
		DESCRIPTION
			"Information of DKU fan."
		::= { raidExMibDKUHWEntry 3 }

	dkuHWEnvironment	OBJECT-TYPE
		SYNTAX		INTEGER	{
					noError(1),
					acute(2),
					serious(3),
					moderate(4),
					service(5)
		}
		ACCESS		read-only
		STATUS		mandatory
		DESCRIPTION
			"Information of DKU Environment."
		::= { raidExMibDKUHWEntry 4 }

	dkuHWDrive		OBJECT-TYPE
		SYNTAX		INTEGER	{
					noError(1),
					acute(2),
					serious(3),
					moderate(4),
					service(5)
		}
		ACCESS		read-only
		STATUS		mandatory
		DESCRIPTION
			"Information of Drive."
		::= { raidExMibDKUHWEntry 5 }

--
-- Trap List
--

	raidExMibTrapListTable	OBJECT-TYPE
		SYNTAX		SEQUENCE OF RaidExMibTrapListEntry
		ACCESS		not-accessible 
		STATUS		mandatory
		DESCRIPTION
			"Trap list Table."
		::= { raidExMibRoot 8 }

	raidExMibTrapListEntry		OBJECT-TYPE
		SYNTAX		RaidExMibTrapListEntry
		ACCESS		not-accessible
		STATUS		mandatory
		DESCRIPTION
			"Trap list Table index."
		INDEX {
			eventListIndexSerialNumber,
			eventListIndexRecordNo
		}
		::= { raidExMibTrapListTable 1 }

	RaidExMibTrapListEntry ::=
		SEQUENCE {
		eventListIndexSerialNumber	INTEGER,
		eventListNickname		DisplayString (SIZE(0..18)),
		eventListIndexRecordNo		Counter,
		eventListREFCODE			DisplayString (SIZE(6))
		}

	eventListIndexSerialNumber	OBJECT-TYPE
		SYNTAX		INTEGER
		ACCESS		read-only
		STATUS		mandatory
		DESCRIPTION
			"Serial Number of the DKC."
		::= { raidExMibTrapListEntry 1 }

	eventListNickname	OBJECT-TYPE
		SYNTAX		DisplayString (SIZE(0..18))
		ACCESS		read-only
		STATUS		mandatory
		DESCRIPTION
			"Nickname of the DKC."
		::= { raidExMibTrapListEntry 2 }

	eventListIndexRecordNo	OBJECT-TYPE
		SYNTAX		Counter
		ACCESS		read-only
		STATUS		mandatory
		DESCRIPTION
			" The record number of the event trap list."
		::= { raidExMibTrapListEntry 3 }

	eventListREFCODE	OBJECT-TYPE
		SYNTAX		DisplayString (SIZE(6))
		ACCESS		read-only
		STATUS		mandatory
		DESCRIPTION
"The Sim21&Sim22&Sim13 in the SIM sense data which is called the reference code. "
		::= { raidExMibTrapListEntry 4 }

--
-- Command request
--

	raidExMibCommandTable	OBJECT-TYPE
		SYNTAX		SEQUENCE OF RaidExMibCommandEntry
		ACCESS		not-accessible 
		STATUS		mandatory
		DESCRIPTION
			"Command Request for the DKC."
		::= { raidExMibRoot 9 }

	raidExMibCommandEntry		OBJECT-TYPE
		SYNTAX		RaidExMibCommandEntry
		ACCESS		not-accessible
		STATUS		mandatory
		DESCRIPTION
			"Entry of command."
		INDEX {
			commandSerialNumber
		}
		::= { raidExMibCommandTable 1 }

	RaidExMibCommandEntry ::=
		SEQUENCE {
			commandSerialNumber	INTEGER,
			commandManagerName	DisplayString (SIZE(0..31)),
			commandKind		INTEGER,
			commandStatus		INTEGER,
			commandProgress		INTEGER,
			commandRefreshTarget	INTEGER,
			commandRefreshTarget2	OCTET STRING
		}

	commandSerialNumber	OBJECT-TYPE
		SYNTAX		INTEGER
		ACCESS		read-only
		STATUS		mandatory
		DESCRIPTION
			"Serial Number of the DKC."
		::= { raidExMibCommandEntry 1 }

	commandManagerName	OBJECT-TYPE
		SYNTAX		DisplayString (SIZE(0..31))
		ACCESS		read-write
		STATUS		mandatory
		DESCRIPTION	
			"Name of manager who has lock."
		::= { raidExMibCommandEntry 2 }

	commandKind		OBJECT-TYPE
		SYNTAX		INTEGER
		ACCESS		read-write
		STATUS		mandatory
		DESCRIPTION	
			"Request Command.

			Value	Mean
			1	Request to refresh the configuration information.
			2	Request to set the LUNM/LUSE configuration.
			3	Request to set the LUN Security configuration.
			4	Request to get the exclusive lock.
			5	Request to free the exclusive locks.
			6	Request to check the health.
			7	Request to set the CVS configuration.
			8	Request to set the DCR configuration.
			9	Request to set the HIHSM configuration.
			"
		::= { raidExMibCommandEntry 3 }

	commandStatus		OBJECT-TYPE
		SYNTAX		INTEGER
		ACCESS		read-write
		STATUS		mandatory
		DESCRIPTION	
			"Status of Requested Command.

			Value	Mean
			1	Normal state. (The command ended normally.)
			2	Command execution request. (now executing.)
			other	Abnormal state (Error occurred). 
			"
		::= { raidExMibCommandEntry 4 }

	commandProgress		OBJECT-TYPE
		SYNTAX		INTEGER
		ACCESS		read-only
		STATUS		mandatory
		DESCRIPTION	
			"Progress situation of Requested Command.
			(This is effective only to the CVS requesting.)"
		::= { raidExMibCommandEntry 5 }

	commandRefreshTarget	OBJECT-TYPE
		SYNTAX		INTEGER
		ACCESS		read-write
		STATUS		mandatory
		DESCRIPTION	
			"The limits of Requested Command."
		::= { raidExMibCommandEntry 6 }

	commandRefreshTarget2	OBJECT-TYPE
		SYNTAX		OCTET STRING
		ACCESS		read-write
		STATUS		mandatory
		DESCRIPTION	
			"The limits of Requested Command."
		::= { raidExMibCommandEntry 7 }

--
-- Logical device configuration
--

	raidExMibLDev		OBJECT IDENTIFIER ::= { raidExMibRoot 10 }

--
-- Logical device information
--

	raidExMibLogicalDeviceTable	OBJECT-TYPE
		SYNTAX		SEQUENCE OF RaidExMibLogicalDeviceEntry
		ACCESS		not-accessible 
		STATUS		mandatory
		DESCRIPTION
			"Logical device information."
		::= { raidExMibLDev 1 }

	raidExMibLogicalDeviceEntry	OBJECT-TYPE
		SYNTAX		RaidExMibLogicalDeviceEntry
		ACCESS		not-accessible
		STATUS		mandatory
		DESCRIPTION
			"Entry of logical device information."
		INDEX {
			logicalDeviceSerialNumber,
			logicalDeviceCU,
			logicalDeviceLDEV
		}
		::= { raidExMibLogicalDeviceTable 1 }

	RaidExMibLogicalDeviceEntry ::=
		SEQUENCE {
			logicalDeviceSerialNumber	INTEGER,
			logicalDeviceCU			INTEGER,
			logicalDeviceLDEV		INTEGER,
			logicalDeviceEmulation		DisplayString,
			logicalDeviceCylinder		INTEGER,
			logicalDeviceLUExpand		INTEGER,
			logicalDeviceLUPath		INTEGER,
			logicalDeviceSize		INTEGER,
			logicalDeviceLBA		INTEGER,
			logicalDeviceHIHSMReserve	INTEGER,
			logicalDeviceControlStatus	INTEGER,
			logicalDeviceRAIDLevel		DisplayString,
			logicalDeviceSlotSize		INTEGER
		}

	logicalDeviceSerialNumber	OBJECT-TYPE
		SYNTAX		INTEGER
		ACCESS		read-only
		STATUS		mandatory
		DESCRIPTION
			"Serial Number of the DKC."
		::= { raidExMibLogicalDeviceEntry 1 }

	logicalDeviceCU		OBJECT-TYPE
		SYNTAX		INTEGER
		ACCESS		read-only
		STATUS		mandatory
		DESCRIPTION
			"CU# of logical device."
		::= { raidExMibLogicalDeviceEntry 2 }

	logicalDeviceLDEV	OBJECT-TYPE
		SYNTAX		INTEGER
		ACCESS		read-only
		STATUS		mandatory
		DESCRIPTION
			"LDEV# of logical device"
		::= { raidExMibLogicalDeviceEntry 3 }

	logicalDeviceEmulation	OBJECT-TYPE
		SYNTAX		DisplayString
		ACCESS		read-only
		STATUS		mandatory
		DESCRIPTION
			"Device emulation type.

			Value	Mean
			6586-J	for mainframe only.
			6586-G	for mainframe only.
			6586-K	for mainframe only.
			6588-1	for mainframe only.
			6588-3	for mainframe only.
			6588-9	for mainframe only.
			6558-1	for mainframe only.
			3380-J	for mainframe only.
			3380-E	for mainframe only.
			3380-K	for mainframe only.
			3390-1	for mainframe only.
			3390-2	for mainframe only.
			3390-3	for mainframe only.
			3390-3R	for mainframe only.
			3390-6	for mainframe only.
			3390-9	for mainframe only.
			NF80-J	for mainframe only.
			NF80-E	for mainframe only.
			NF80-K	for mainframe only.
			6588-3A	for shared disk. (both mainframe and open system)
			6588-3B	for shared disk. (both mainframe and open system)
			6588-3C	for shared disk. (both mainframe and open system)
			6588-KA	for shared disk. (both mainframe and open system)
			6588-KB	for shared disk. (both mainframe and open system)
			6588-KC	for shared disk. (both mainframe and open system)
			3390-3A	for shared disk. (both mainframe and open system)
			3390-3B	for shared disk. (both mainframe and open system)
			3390-3C	for shared disk. (both mainframe and open system)
			3380-KA	for shared disk. (both mainframe and open system)
			3380-KB	for shared disk. (both mainframe and open system)
			3380-KC	for shared disk. (both mainframe and open system)
			NF80-KA	for shared disk. (both mainframe and open system)
			NF80-KB	for shared disk. (both mainframe and open system)
			NF80-KC	for shared disk. (both mainframe and open system)
			OPEN-3	for open system only.
			OPEN-8	for open system only.
			OPEN-9	for open system only.
			OPEN-K	for open system only.
			NFOP-K	for open system only.
			"
		::= { raidExMibLogicalDeviceEntry 4 }

	logicalDeviceCylinder	OBJECT-TYPE
		SYNTAX		INTEGER
		ACCESS		read-only
		STATUS		mandatory
		DESCRIPTION
			"Number of cylinders"
		::= { raidExMibLogicalDeviceEntry 5 }

	logicalDeviceLUExpand	OBJECT-TYPE
		SYNTAX		INTEGER
		ACCESS		read-only
		STATUS		mandatory
		DESCRIPTION
			"Relation to LUSE.
			 (LUSE: logical unit size expansion).

			Value	Mean
			1	Non LUSE.
			2	Top of LUSE.
			3	Element of LUSE.
			"
		::= { raidExMibLogicalDeviceEntry 6 }

	logicalDeviceLUPath	OBJECT-TYPE
		SYNTAX		INTEGER
		ACCESS		read-only
		STATUS		mandatory
		DESCRIPTION
			"Existence of LU path.

			Value	Mean
			0	Not exist.
			1	Exist.
			"
		::= { raidExMibLogicalDeviceEntry 7 }

	logicalDeviceSize	OBJECT-TYPE
		SYNTAX		INTEGER
		ACCESS		read-only
		STATUS		mandatory
		DESCRIPTION
			"Size of device."
		::= { raidExMibLogicalDeviceEntry 8 }

	logicalDeviceLBA	OBJECT-TYPE
		SYNTAX		INTEGER
		ACCESS		read-only
		STATUS		mandatory
		DESCRIPTION
			"LBA Size of device."
		::= { raidExMibLogicalDeviceEntry 9 }

	logicalDeviceHIHSMReserve	OBJECT-TYPE
		SYNTAX		INTEGER
		ACCESS		read-write
		STATUS		mandatory
		DESCRIPTION
				"Reserve Volume of HIHSM.

				Value	Mean
				0	Normal Volume.
				1	Reserve Volume.
				"
		::= { raidExMibLogicalDeviceEntry 10 }

	logicalDeviceControlStatus	OBJECT-TYPE
		SYNTAX		INTEGER
		ACCESS		read-write
		STATUS		mandatory
		DESCRIPTION
				"Control flag.

				Value	Mean
				1	Return value.
				2	Set request.
				"
		::= { raidExMibLogicalDeviceEntry 11 }

	logicalDeviceRAIDLevel	OBJECT-TYPE
		SYNTAX		DisplayString
		ACCESS		read-only
		STATUS		mandatory
		DESCRIPTION
				"RAID Level."
		::= { raidExMibLogicalDeviceEntry 12 }

	logicalDeviceSlotSize	OBJECT-TYPE
		SYNTAX		INTEGER
		ACCESS		read-only
		STATUS		mandatory
		DESCRIPTION
				"Slot Size."
		::= { raidExMibLogicalDeviceEntry 13 }

--
-- Logical unit configuration
--

	raidExMibLUConfiguration	 OBJECT IDENTIFIER ::= { raidExMibRoot 11 }

--
-- Port information
--

	raidExMibPortTable	OBJECT-TYPE
		SYNTAX		SEQUENCE OF RaidExMibPortEntry
		ACCESS		not-accessible 
		STATUS		mandatory
		DESCRIPTION
			"Port information."
		::= { raidExMibLUConfiguration 1 }

	raidExMibPortEntry		OBJECT-TYPE
		SYNTAX		RaidExMibPortEntry
		ACCESS		not-accessible
		STATUS		mandatory
		DESCRIPTION
			"Entry of port information."
		INDEX {
			portSerialNumber,
			portID
		}
		::= { raidExMibPortTable 1 }

	RaidExMibPortEntry ::=
		SEQUENCE {
			portSerialNumber	INTEGER,
			portID				INTEGER,
			portKind			DisplayString,
			portHostMode		OCTET STRING (SIZE(1)),
			portFibreAddress	INTEGER,
			portFibreTopology	INTEGER,
			portControlStatus	INTEGER,
			portDisplayName		DisplayString,
			portWWN			OCTET STRING (SIZE(8))
		}

	portSerialNumber		OBJECT-TYPE
		SYNTAX		INTEGER
		ACCESS		read-only
		STATUS		mandatory
		DESCRIPTION
			"Serial Number of the DKC."
		::= { raidExMibPortEntry 1 }

	portID			OBJECT-TYPE
		SYNTAX		INTEGER
		ACCESS		read-only
		STATUS		mandatory
		DESCRIPTION
			"Port ID."
		::= { raidExMibPortEntry 2 }

	portKind		OBJECT-TYPE
		SYNTAX		DisplayString
		ACCESS		read-only
		STATUS		mandatory
		DESCRIPTION
			"Kind of port.

			Value	Mean
			LCP	mainframe port only.
			MCP	mainframe port only.
			SCSI	SCSI port.
			Fibre	Fibre port.
			"
		::= { raidExMibPortEntry 3 }

	portHostMode		OBJECT-TYPE
		SYNTAX		OCTET STRING (SIZE(1))
		ACCESS		read-write
		STATUS		mandatory
		DESCRIPTION
			"Host mode of the port.

			Upper 4 bits. - Each bit has the meaning.
			Bit	Mean
			0	Not used. (For reservation. Always 0.)
			1	Not used. (For reservation. Always 0.)
			2	Not used. (For reservation. Always 0.)
			3	Ultra-SCSI mode.

			Lower 4 bits. - Numerical value shown by four bits.
			Value	Mean
			0	Normal setting.
			1	IBM-7135 mode.
			2	NCR mode.
			3	Not used. (Reserved)
			4	Sequent mode.
			5	DEC OPEN VMS mode.
			6	UNISYS-NX mode
			7	UNISYS-IX mode.
			8	HP mode.
			9	VxVM-DMP mode.
			10	Not used. (Reserved)
			11	MPE mode.
			other	Not used. (Reserved)

			Note: The following value has a special meaning.
			Value	Mean
			0xFF	Out of the host mode setting object.
			"
		::= { raidExMibPortEntry 4 }

	portFibreAddress		OBJECT-TYPE
		SYNTAX		INTEGER
		ACCESS		read-only
		STATUS		mandatory
		DESCRIPTION
			"Fibre address.

	Value & Mean - describes by the format of Value(Address).		  
	  1:(EF)  17:(CD)  33:(B2)  49:(98)  65:(72)  81:(55)  97:(3A) 113:(25)
	  2:(E8)  18:(CC)  34:(B1)  50:(97)  66:(71)  82:(54)  98:(39) 114:(23)
	  3:(E4)  19:(CB)  35:(AE)  51:(90)  67:(6E)  83:(53)  99:(36) 115:(1F)
	  4:(E2)  20:(CA)  36:(AD)  52:(8F)  68:(6D)  84:(52) 100:(35) 116:(1E)
	  5:(E1)  21:(C9)  37:(AC)  53:(88)  69:(6C)  85:(51) 101:(34) 117:(1D)
	  6:(E0)  22:(C7)  38:(AB)  54:(84)  70:(6B)  86:(4E) 102:(33) 118:(1B)
	  7:(DC)  23:(C6)  39:(AA)  55:(82)  71:(6A)  87:(4D) 103:(32) 119:(18)
	  8:(DA)  24:(C5)  40:(A9)  56:(81)  72:(69)  88:(4C) 104:(31) 120:(17)
	  9:(D9)  25:(C3)  41:(A7)  57:(80)  73:(67)  89:(4B) 105:(2E) 121:(10)
	 10:(D6)  26:(BC)  42:(A6)  58:(7C)  74:(66)  90:(4A) 106:(2D) 122:(0F)
	 11:(D5)  27:(BA)  43:(A5)  59:(7A)  75:(65)  91:(49) 107:(2C) 123:(08)
	 12:(D4)  28:(B9)  44:(A3)  60:(79)  76:(63)  92:(47) 108:(2B) 124:(04)
	 13:(D3)  29:(B6)  45:(9F)  61:(76)  77:(5C)  93:(46) 109:(2A) 125:(02)
	 14:(D2)  30:(B5)  46:(9E)  62:(75)  78:(5A)  94:(45) 110:(29) 126:(01)
	 15:(D1)  31:(B4)  47:(9D)  63:(74)  79:(59)  95:(43) 111:(27) 
	 16:(CE)  32:(B3)  48:(9B)  64:(73)  80:(56)  96:(3C) 112:(26) 

			Note: The following value has a special meaning.
			Value	Mean
			0	Out of the Fibre address setting object.
			"
		::= { raidExMibPortEntry 5 }

	portFibreTopology	OBJECT-TYPE
		SYNTAX		INTEGER
		ACCESS		read-write
		STATUS		mandatory
		DESCRIPTION
			"Topology information.

			Value	Mean
			1	Fabric(on)&FCAL
			2	Fabric(off)&FCAL
			3	Fabric(on)&PointToPoint
			4	Fabric(off)&PointToPoint
			5	Not Fibre
			"
		::= { raidExMibPortEntry 6 }

	portControlStatus	OBJECT-TYPE
		SYNTAX		INTEGER
		ACCESS		read-write
		STATUS		mandatory
		DESCRIPTION
			"Control flag.

			Value	Mean
			1	Return value.
			2	Set request.
			"
		::= { raidExMibPortEntry 7 }

	portDisplayName		OBJECT-TYPE
		SYNTAX		DisplayString
		ACCESS		read-only
		STATUS		mandatory
		DESCRIPTION
			"Display name of the port."
		::= { raidExMibPortEntry 8 }

	portWWN			OBJECT-TYPE
		SYNTAX		OCTET STRING (SIZE(8))
		ACCESS		read-only
		STATUS		mandatory
		DESCRIPTION
			"WWN of the port."
		::= { raidExMibPortEntry 9 }

--
-- Logical unit configuration
--

  raidExMibLU OBJECT IDENTIFIER ::= { raidExMibLUConfiguration 2 }

--
-- Logical unit information
--

	raidExMibLUInformationLUTable	OBJECT-TYPE
		SYNTAX		SEQUENCE OF RaidExMibLUInformationLUEntry 
		ACCESS		not-accessible 
		STATUS		mandatory
		DESCRIPTION
			"Logical unit information."
		::= { raidExMibLU 1 }

	raidExMibLUInformationLUEntry			OBJECT-TYPE
		SYNTAX		RaidExMibLUInformationLUEntry 
		ACCESS		not-accessible
		STATUS		mandatory
		DESCRIPTION
			"Entry of logical unit information."
		INDEX {
			luSerialNumber,
			luDeviceCU,
			luDeviceLDEV
		}
		::= { raidExMibLUInformationLUTable 1 }

	RaidExMibLUInformationLUEntry ::=
		SEQUENCE {
			luSerialNumber	INTEGER,
			luDeviceCU		INTEGER,
			luDeviceLDEV	INTEGER,
			luEmuID			DisplayString,
			luCount			INTEGER,
			luSize			INTEGER,
			luPath			INTEGER,
			luCommandDev	INTEGER,
			luControlStatus	INTEGER
		}

	luSerialNumber		OBJECT-TYPE
		SYNTAX		INTEGER
		ACCESS		read-only
		STATUS		mandatory
		DESCRIPTION
			"Serial Number of the DKC."
		::= { raidExMibLUInformationLUEntry 1 }

	luDeviceCU		OBJECT-TYPE
		SYNTAX		INTEGER
		ACCESS		read-only
		STATUS		mandatory
		DESCRIPTION
			"CU# of logical device."
		::= { raidExMibLUInformationLUEntry 2 }

	luDeviceLDEV		OBJECT-TYPE
		SYNTAX		INTEGER
		ACCESS		read-only
		STATUS		mandatory
		DESCRIPTION
			"LDEV# of logical device."
		::= { raidExMibLUInformationLUEntry 3 }

	luEmuID			OBJECT-TYPE
		SYNTAX		DisplayString
		ACCESS		read-only
		STATUS		mandatory
		DESCRIPTION
			"Device emulation type."
		::= { raidExMibLUInformationLUEntry 4 }

	luCount			OBJECT-TYPE
		SYNTAX		INTEGER
		ACCESS		read-only
		STATUS		mandatory
		DESCRIPTION
			"Number of expansion devices."
		::= { raidExMibLUInformationLUEntry 5 }

	luSize			OBJECT-TYPE
		SYNTAX		INTEGER
		ACCESS		read-only
		STATUS		mandatory
		DESCRIPTION
			"Storage capacity. (The unit is KB)"
		::= { raidExMibLUInformationLUEntry 6 }

	luPath			OBJECT-TYPE
		SYNTAX		INTEGER
		ACCESS		read-only
		STATUS		mandatory
		DESCRIPTION
			"existence of LU path.

			Value	Mean
			0	Not exist.
			1	Exist.
			"
		::= { raidExMibLUInformationLUEntry 7 }

	luCommandDev		OBJECT-TYPE
		SYNTAX		INTEGER
		ACCESS		read-write
		STATUS		mandatory
		DESCRIPTION
			"Setting of command device.

			Value	Mean
			0	This is not a command device.
			1	This is a command device.
			"
		::= { raidExMibLUInformationLUEntry 8 }

	luControlStatus		OBJECT-TYPE
		SYNTAX		INTEGER
		ACCESS		read-write
		STATUS		mandatory
		DESCRIPTION
			"Control flag.

			Value	Mean
			1	Return value.
			2	Set request.
			"
		::= { raidExMibLUInformationLUEntry 9 }

--
-- Logical unit path information
--

	raidExMibLUPathTable		OBJECT-TYPE
		SYNTAX		SEQUENCE OF RaidExMibLUPathEntry
		ACCESS		not-accessible 
		STATUS		mandatory
		DESCRIPTION
			"Logical unit path information."
		::= { raidExMibLU 2 }

	raidExMibLUPathEntry		OBJECT-TYPE
		SYNTAX		RaidExMibLUPathEntry
		ACCESS		not-accessible
		STATUS		mandatory
		DESCRIPTION
			"Entry of logical unit path information."
		INDEX {
			luPathSerialNumber,
			luPathControlIndex
		}
		::= { raidExMibLUPathTable 1 }

	RaidExMibLUPathEntry ::=
		SEQUENCE {
			luPathSerialNumber	INTEGER,
			luPathControlIndex	INTEGER,
			luPathPortID		INTEGER,
			luPathSCSIID		INTEGER,
			luPathLUN			INTEGER,
			luPathDeviceCU		INTEGER,
			luPathDeviceLDEV	INTEGER,
			luPathControlStatus	INTEGER
		}

	luPathSerialNumber	OBJECT-TYPE
		SYNTAX		INTEGER
		ACCESS		read-only
		STATUS		mandatory
		DESCRIPTION
			"Serial Number of the DKC."
		::= { raidExMibLUPathEntry 1 }

	luPathControlIndex	OBJECT-TYPE
		SYNTAX		INTEGER
		ACCESS		read-only
		STATUS		mandatory
		DESCRIPTION
			"Index for Path Control."
		::= { raidExMibLUPathEntry 2 }

	luPathPortID		OBJECT-TYPE
		SYNTAX		INTEGER
		ACCESS		read-write
		STATUS		mandatory
		DESCRIPTION
			"Port ID of the LU path."
		::= { raidExMibLUPathEntry 3 }

	luPathSCSIID		OBJECT-TYPE
		SYNTAX		INTEGER
		ACCESS		read-write
		STATUS		mandatory
		DESCRIPTION
			"SCSI ID of the LU path."
		::= { raidExMibLUPathEntry 4 }

	luPathLUN		OBJECT-TYPE
		SYNTAX		INTEGER
		ACCESS		read-write
		STATUS		mandatory
		DESCRIPTION
			"LUN of the LU path."
		::= { raidExMibLUPathEntry 5 }

	luPathDeviceCU		OBJECT-TYPE
		SYNTAX		INTEGER
		ACCESS		read-write
		STATUS		mandatory
		DESCRIPTION
			"Target device CU# of the LU path."
		::= { raidExMibLUPathEntry 6 }

	luPathDeviceLDEV	OBJECT-TYPE
		SYNTAX		INTEGER
		ACCESS		read-write
		STATUS		mandatory
		DESCRIPTION
			"Target device LDEV# of the LU path."
		::= { raidExMibLUPathEntry 7 }

	luPathControlStatus	OBJECT-TYPE
		SYNTAX		INTEGER
		ACCESS		read-write
		STATUS		mandatory
		DESCRIPTION
			"Control flag.

			Value	Mean
			1	Return value.
			2	Add request.
			3	Delete request.
			"
		::= { raidExMibLUPathEntry 8 }

--
-- LUSE configuration
--  (LUSE: logical unit size expansion)
--

 raidExMibLUSE	OBJECT IDENTIFIER ::= { raidExMibLUConfiguration 3 }

--
-- LUSE information
--

	raidExMibLUSEStructureTable	OBJECT-TYPE
		SYNTAX		SEQUENCE OF RaidExMibLUSEStructureEntry
		ACCESS		not-accessible 
		STATUS		mandatory
		DESCRIPTION
			"LUSE information."
		::= { raidExMibLUSE 1 }

	raidExMibLUSEStructureEntry		OBJECT-TYPE
		SYNTAX		RaidExMibLUSEStructureEntry
		ACCESS		not-accessible
		STATUS		mandatory
		DESCRIPTION
			"Entry of LUSE information."
		INDEX {
			luSEStructSerialNumber,
			luSEStructControlIndex,
			luSEStructOffset
		}
		::= { raidExMibLUSEStructureTable 1 }

	RaidExMibLUSEStructureEntry ::=
		SEQUENCE {
			luSEStructSerialNumber		INTEGER,
			luSEStructControlIndex		INTEGER,
			luSEStructOffset		Counter,
			luSEStructTopDeviceCU		INTEGER,
			luSEStructTopDeviceLDEV		INTEGER,
			luSEStructDeviceCU		INTEGER,
			luSEStructDeviceLDEV		INTEGER,
			luSEStructControlStatus 	INTEGER
		}

	luSEStructSerialNumber	OBJECT-TYPE
		SYNTAX		INTEGER
		ACCESS		read-only
		STATUS		mandatory
		DESCRIPTION
			"Serial Number of the DKC."
		::= { raidExMibLUSEStructureEntry 1 }

	luSEStructControlIndex	OBJECT-TYPE
		SYNTAX		INTEGER
		ACCESS		read-only
		STATUS		mandatory
		DESCRIPTION
			"Index for LUSE Control."
		::= { raidExMibLUSEStructureEntry 2 }

	luSEStructOffset	OBJECT-TYPE
		SYNTAX		Counter
		ACCESS		read-only
		STATUS		mandatory
		DESCRIPTION
			"LDEV offset in the LUSE."
		::= { raidExMibLUSEStructureEntry 3 }

	luSEStructTopDeviceCU	OBJECT-TYPE
		SYNTAX		INTEGER
		ACCESS		read-write
		STATUS		mandatory
		DESCRIPTION
			"Top CU# of the LUSE."
		::= { raidExMibLUSEStructureEntry 4 }

	luSEStructTopDeviceLDEV	OBJECT-TYPE
		SYNTAX		INTEGER
		ACCESS		read-write
		STATUS		mandatory
		DESCRIPTION
			"Top LDEV# of the LUSE."
		::= { raidExMibLUSEStructureEntry 5 }

	luSEStructDeviceCU	OBJECT-TYPE
		SYNTAX		INTEGER
		ACCESS		read-write
		STATUS		mandatory
		DESCRIPTION
			"Target CU# of the LUSE."
		::= { raidExMibLUSEStructureEntry 6 }

	luSEStructDeviceLDEV	OBJECT-TYPE
		SYNTAX		INTEGER
		ACCESS		read-write
		STATUS		mandatory
		DESCRIPTION
			"Target LDEV# of the LUSE."
		::= { raidExMibLUSEStructureEntry 7 }

	luSEStructControlStatus	OBJECT-TYPE
		SYNTAX		INTEGER
		ACCESS		read-write
		STATUS		mandatory
		DESCRIPTION
			"Control flag.

			Value	Mean
			1	Return value.
			2	Add request.
			3	Delete request.
			"
		::= { raidExMibLUSEStructureEntry 8 }

--
-- LUN Security information
--

 raidExMibLUNS 	OBJECT IDENTIFIER ::= { raidExMibLUConfiguration 4 }

--
-- Security switch
--

	raidExMibLUNSSwitchTable		OBJECT-TYPE
		SYNTAX		SEQUENCE OF RaidExMibLUNSSwitchEntry
		ACCESS		not-accessible 
		STATUS		mandatory
		DESCRIPTION
			"LUN security switch."
		::= { raidExMibLUNS 1 }

	raidExMibLUNSSwitchEntry		OBJECT-TYPE
		SYNTAX		RaidExMibLUNSSwitchEntry
		ACCESS		not-accessible
		STATUS		mandatory
		DESCRIPTION
			"Entry of LUN security switch."
		INDEX {
			switchSerialNumber,
			switchPortID
		}
		::= { raidExMibLUNSSwitchTable 1 }

	RaidExMibLUNSSwitchEntry ::= 
		SEQUENCE {
			switchSerialNumber	INTEGER,
			switchPortID		INTEGER,
			switchOnOff		INTEGER,
			switchControlStatus	INTEGER
		}

	switchSerialNumber	OBJECT-TYPE
		SYNTAX		INTEGER
		ACCESS		read-only
		STATUS		mandatory
		DESCRIPTION
			"Serial Number of the DKC."
		::= { raidExMibLUNSSwitchEntry 1 }

	switchPortID		OBJECT-TYPE
		SYNTAX		INTEGER
		ACCESS		read-only
		STATUS		mandatory
		DESCRIPTION
			"Port ID of the DKC."
		::= { raidExMibLUNSSwitchEntry 2 }

	switchOnOff		OBJECT-TYPE
		SYNTAX		INTEGER
		ACCESS		read-write
		STATUS		mandatory
		DESCRIPTION
			"Functional switch.

			Value	Mean
			0	off (LUN Security unused)
			1	on (Use LUN Security)
			"
		::= { raidExMibLUNSSwitchEntry 3 }

	switchControlStatus	OBJECT-TYPE
		SYNTAX		INTEGER
		ACCESS		read-write
		STATUS		mandatory
		DESCRIPTION
			"Control flag.

			Value	Mean
			1	Return value.
			2	Set request.
			"
		::= { raidExMibLUNSSwitchEntry 4 }

--
-- WWN information
--

	raidExMibLUNSWWNTable		OBJECT-TYPE
		SYNTAX		SEQUENCE OF RaidExMibLUNSWWNEntry
		ACCESS		not-accessible 
		STATUS		mandatory
		DESCRIPTION
			"WWN information."
		::= { raidExMibLUNS 2 }

	raidExMibLUNSWWNEntry		OBJECT-TYPE
		SYNTAX		RaidExMibLUNSWWNEntry
		ACCESS		not-accessible
		STATUS		mandatory
		DESCRIPTION
			"Entry of WWN information."
		INDEX {
			wwnSerialNumber,
			wwnPortID,
			wwnControlIndex
		}
		::= { raidExMibLUNSWWNTable 1 }

	RaidExMibLUNSWWNEntry ::= 
		SEQUENCE {
			wwnSerialNumber		INTEGER,
			wwnPortID		INTEGER,
			wwnControlIndex		INTEGER,
			wwnWWN			OCTET STRING (SIZE(8)),
			wwnID			INTEGER,
			wwnNickname		DisplayString (SIZE(0..8)),
			wwnUseNickname		INTEGER,
			wwnControlStatus	INTEGER
		}

	wwnSerialNumber		OBJECT-TYPE
		SYNTAX		INTEGER
		ACCESS		read-only
		STATUS		mandatory
		DESCRIPTION
			"Serial number of the DKC."
		::= { raidExMibLUNSWWNEntry 1 }

	wwnPortID		OBJECT-TYPE
		SYNTAX		INTEGER
		ACCESS		read-only
		STATUS		mandatory
		DESCRIPTION
			"Port ID of the DKC."
		::= { raidExMibLUNSWWNEntry 2 }

	wwnControlIndex		OBJECT-TYPE
		SYNTAX		INTEGER
		ACCESS		read-only
		STATUS		mandatory
		DESCRIPTION
			"Index for WWN control."
		::= { raidExMibLUNSWWNEntry 3 }

	wwnWWN			OBJECT-TYPE
		SYNTAX		OCTET STRING (SIZE(8))
		ACCESS		read-write
		STATUS		mandatory
		DESCRIPTION
			"WWN. (World Wide Name)"
		::= { raidExMibLUNSWWNEntry 4 }

	wwnID			OBJECT-TYPE
		SYNTAX		INTEGER
		ACCESS		read-write
		STATUS		mandatory
		DESCRIPTION
			"ID of the WWN."
		::= { raidExMibLUNSWWNEntry 5 }

	wwnNickname		OBJECT-TYPE
		SYNTAX		DisplayString (SIZE(0..8))
		ACCESS		read-write
		STATUS		deprecated
		DESCRIPTION
			"Nickname of the WWN."
		::= { raidExMibLUNSWWNEntry 6 }

	wwnUseNickname		OBJECT-TYPE
		SYNTAX		INTEGER
		ACCESS		read-write
		STATUS		mandatory
		DESCRIPTION
			"Using of nickname.

			Values	Mean
			0	Nickname Unused.
			1	Use nickname.
			"
		::= { raidExMibLUNSWWNEntry 7 }

	wwnControlStatus	OBJECT-TYPE
		SYNTAX		INTEGER
		ACCESS		read-write
		STATUS		mandatory
		DESCRIPTION
			"Control flag.

			Value	Mean
			1	Return value.
			2	Add request.
			3	Delete request.
			4	Set request. 
			"
		::= { raidExMibLUNSWWNEntry 8 }

--
-- WWN group information
--

	raidExMibLUNSWWNGroupTable	OBJECT-TYPE
		SYNTAX		SEQUENCE OF RaidExMibLUNSWWNGroupEntry
		ACCESS		not-accessible 
		STATUS		mandatory
		DESCRIPTION
			"WWN group information."
		::= { raidExMibLUNS 3 }

	raidExMibLUNSWWNGroupEntry		OBJECT-TYPE
		SYNTAX		RaidExMibLUNSWWNGroupEntry
		ACCESS		not-accessible 
		STATUS		mandatory
		DESCRIPTION
			"Entry of WWN group information."
		INDEX {
			wwnGroupSerialNumber,
			wwnGroupPortID,
			wwnGroupControlIndex
		}
		::= { raidExMibLUNSWWNGroupTable 1 }

	RaidExMibLUNSWWNGroupEntry ::= 
		SEQUENCE {
			wwnGroupSerialNumber	INTEGER,
			wwnGroupPortID		INTEGER,
			wwnGroupControlIndex	INTEGER,
			wwnGroupID		INTEGER,
			wwnGroupNickname	DisplayString (SIZE(0..8)),
--			wwnGroupedWWNs		OCTET STRING (SIZE(4)),
			wwnGroupControlStatus	INTEGER,
			wwnGroupedWWNsVL	OCTET STRING
		}

	wwnGroupSerialNumber	OBJECT-TYPE
		SYNTAX		INTEGER
		ACCESS		read-only
		STATUS		mandatory
		DESCRIPTION
			"Serial number of the DKC."
		::= { raidExMibLUNSWWNGroupEntry 1 }

	wwnGroupPortID		OBJECT-TYPE
		SYNTAX		INTEGER
		ACCESS		read-only
		STATUS		mandatory
		DESCRIPTION
			"Port ID of the DKC."
		::= { raidExMibLUNSWWNGroupEntry 2 }

	wwnGroupControlIndex	OBJECT-TYPE
		SYNTAX		INTEGER
		ACCESS		read-only
		STATUS		mandatory
		DESCRIPTION
			"Index for WWN group control."
		::= { raidExMibLUNSWWNGroupEntry 3 }

	wwnGroupID		OBJECT-TYPE
		SYNTAX		INTEGER
		ACCESS		read-write
		STATUS		mandatory
		DESCRIPTION
			"ID of the WWN."
		::= { raidExMibLUNSWWNGroupEntry 4 }

	wwnGroupNickname	OBJECT-TYPE
		SYNTAX		DisplayString (SIZE(0..8))
		ACCESS		read-write
		STATUS		mandatory
		DESCRIPTION
			"Nickname of the WWN group."
		::= { raidExMibLUNSWWNGroupEntry 5 }

--	wwnGroupedWWNs		OBJECT-TYPE
--		SYNTAX		OCTET STRING (SIZE(4))
--		ACCESS		read-write
--		STATUS		mandatory
--		DESCRIPTION
--			"Grouped WWNs.
--
--			It is shown whether the bit at the position corresponding 
--			to WWNID belongs to the group.
--
--			Value	Mean
--			0	Does not belong.
--			1	Belongs.
--			"
--		::= { raidExMibLUNSWWNGroupEntry 6 }

	wwnGroupControlStatus	OBJECT-TYPE
		SYNTAX		INTEGER
		ACCESS		read-write
		STATUS		mandatory
		DESCRIPTION
			"Control flag.

			Value	Mean
			1	Return value.
			2	Add request.
			3	Delete request.
			4	Set request. 
			"
		::= { raidExMibLUNSWWNGroupEntry 7 }

	wwnGroupedWWNsVL	OBJECT-TYPE
		SYNTAX		OCTET STRING
		ACCESS		read-write
		STATUS		mandatory
		DESCRIPTION
			"Grouped WWNs. (variable length)

			The bit at the position corresponding to WWNID 
			shows belongs in this WWN group.
			
			Value	Mean
			0	Does not belong.
			1	Belongs.
			"
		::= { raidExMibLUNSWWNGroupEntry 8 }

--
-- LUN information
--

	raidExMibLUNSLUNTable		OBJECT-TYPE
		SYNTAX		SEQUENCE OF RaidExMibLUNSLUNEntry
		ACCESS		not-accessible 
		STATUS		mandatory
		DESCRIPTION
			"LUN information."
		::= { raidExMibLUNS 4 }

	raidExMibLUNSLUNEntry		OBJECT-TYPE
		SYNTAX		RaidExMibLUNSLUNEntry
		ACCESS		not-accessible
		STATUS		mandatory
		DESCRIPTION
			"Entry of LUN information."
		INDEX {
			lunSerialNumber,
			lunPortID,
			lunLUN
		}
		::= { raidExMibLUNSLUNTable 1 }

	RaidExMibLUNSLUNEntry ::= 
		SEQUENCE {
			lunSerialNumber		INTEGER,
			lunPortID		INTEGER,
			lunLUN			INTEGER,
--			lunWWNSecurity		OCTET STRING (SIZE(4)),
--			lunWWNGroupSecurity	OCTET STRING (SIZE(2)),
			lunControlStatus	INTEGER,
			lunWWNSecurityVL	OCTET STRING,
			lunWWNGroupSecurityVL	OCTET STRING
		}

	lunSerialNumber		OBJECT-TYPE
		SYNTAX		INTEGER
		ACCESS		read-only
		STATUS		mandatory
		DESCRIPTION
			"Serial number of the DKC."
		::= { raidExMibLUNSLUNEntry 1 }

	lunPortID		OBJECT-TYPE
		SYNTAX		INTEGER
		ACCESS		read-only
		STATUS		mandatory
		DESCRIPTION
			"Port ID of the DKC."
		::= { raidExMibLUNSLUNEntry 2 }

	lunLUN			OBJECT-TYPE
		SYNTAX		INTEGER
		ACCESS		read-only
		STATUS		mandatory
		DESCRIPTION
			"LUN of the Port."
		::= { raidExMibLUNSLUNEntry 3 }

--	lunWWNSecurity		OBJECT-TYPE
--		SYNTAX		OCTET STRING (SIZE(4))
--		ACCESS		read-write
--		STATUS		mandatory
--		DESCRIPTION
--			"WWN security setting.
--
--			The bit at the position corresponding to WWNID 
--			shows the state of the access permits.
--			
--			Value	Mean
--			0	Does not accessible.
--			1	Accessible.
--			"
--		::= { raidExMibLUNSLUNEntry 4 }
--
--	lunWWNGroupSecurity	OBJECT-TYPE
--		SYNTAX		OCTET STRING (SIZE(2))
--		ACCESS		read-write
--		STATUS		mandatory
--		DESCRIPTION
--			"WWN group Security setting.
--
--			The bit at the position corresponding to WWNGroupID 
--			shows the state of the access permits.
--			
--			Value	Mean
--			0	Does not accessible.
--			1	Accessible.
--			"
--		::= { raidExMibLUNSLUNEntry 5 }

	lunControlStatus		OBJECT-TYPE
		SYNTAX		INTEGER
		ACCESS		read-write
		STATUS		mandatory
		DESCRIPTION
			"Control flag.

			Value	Mean
			1	Return value.
			2	Set request.
			"
		::= { raidExMibLUNSLUNEntry 6 }

	lunWWNSecurityVL		OBJECT-TYPE
		SYNTAX		OCTET STRING
		ACCESS		read-write
		STATUS		mandatory
		DESCRIPTION
			"WWN security setting. (variable length)

			The bit at the position corresponding to WWNID 
			shows the state of the access permits.
			
			Value	Mean
			0	Does not accessible.
			1	Accessible.
			"
		::= { raidExMibLUNSLUNEntry 7 }

	lunWWNGroupSecurityVL	OBJECT-TYPE
		SYNTAX		OCTET STRING
		ACCESS		read-write
		STATUS		mandatory
		DESCRIPTION
			"WWN group Security setting. (variable length)

			The bit at the position corresponding to WWNGroupID 
			shows the state of the access permits.
			
			Value	Mean
			0	Does not accessible.
			1	Accessible.
			"
		::= { raidExMibLUNSLUNEntry 8 }

--
-- LUN group information
--

	raidExMibLUNSLUNGroupTable	OBJECT-TYPE
		SYNTAX		SEQUENCE OF RaidExMibLUNSLUNGroupEntry
		ACCESS		not-accessible 
		STATUS		mandatory
		DESCRIPTION
			"LUN group information."
		::= { raidExMibLUNS 5 }

	raidExMibLUNSLUNGroupEntry		OBJECT-TYPE
		SYNTAX		RaidExMibLUNSLUNGroupEntry
		ACCESS		not-accessible
		STATUS		mandatory
		DESCRIPTION
			"Entry of LUN group information."
		INDEX {
			lunGroupSerialNumber,
			lunGroupPortID,
			lunGroupControlIndex
		}
		::= { raidExMibLUNSLUNGroupTable 1 }

	RaidExMibLUNSLUNGroupEntry ::= 
		SEQUENCE {
			lunGroupSerialNumber		INTEGER,
			lunGroupPortID			INTEGER,
			lunGroupControlIndex		INTEGER,
			lunGroupID			INTEGER,
			lunGroupNickname		DisplayString (SIZE(0..8)),
--			lunGroupedluNs			OCTET STRING (SIZE(15)),
--			lunGroupWWNSecurity		OCTET STRING (SIZE(4)),
--			lunGroupWWNGroupSecurity	OCTET STRING (SIZE(2)),
			lunGroupControlStatus		INTEGER,
			lunGroupedLUNsVL		OCTET STRING,
			lunGroupWWNSecurityVL		OCTET STRING,
			lunGroupWWNGroupSecurityVL	OCTET STRING
		}

	lunGroupSerialNumber	OBJECT-TYPE
		SYNTAX		INTEGER
		ACCESS		read-only
		STATUS		mandatory
		DESCRIPTION
			"Serial number of the DKC."
		::= { raidExMibLUNSLUNGroupEntry 1 }

	lunGroupPortID		OBJECT-TYPE
		SYNTAX		INTEGER
		ACCESS		read-only
		STATUS		mandatory
		DESCRIPTION
			"Port ID of the DKC."
		::= { raidExMibLUNSLUNGroupEntry 2 }

	lunGroupControlIndex	OBJECT-TYPE
		SYNTAX		INTEGER
		ACCESS		read-only
		STATUS		mandatory
		DESCRIPTION
			"Index for LUN group control."
		::= { raidExMibLUNSLUNGroupEntry 3 }

	lunGroupID		OBJECT-TYPE
		SYNTAX		INTEGER
		ACCESS		read-write
		STATUS		mandatory
		DESCRIPTION
			"ID of the WWN group."
		::= { raidExMibLUNSLUNGroupEntry 4 }

	lunGroupNickname	OBJECT-TYPE
		SYNTAX		DisplayString (SIZE(0..8))
		ACCESS		read-write
		STATUS		deprecated
		DESCRIPTION
			"Nickname of the LUN group."
		::= { raidExMibLUNSLUNGroupEntry 5 }

--	lunGroupedLUNs		OBJECT-TYPE
--		SYNTAX		OCTET STRING (SIZE(15))
--		ACCESS		read-write
--		STATUS		mandatory
--		DESCRIPTION
--			"Grouped LUNs.
--
--		It is shown whether the bit at the position corresponding 
--		to LUNLUN belongs to the group. (0:does not belong 1:belongs)
--
--			Value	Mean
--			0	Does not belong.
--			1	Belongs.
--			"
--		::= { raidExMibLUNSLUNGroupEntry 6 }
--
--	lunGroupWWNSecurity	OBJECT-TYPE
--		SYNTAX		OCTET STRING (SIZE(4))
--		ACCESS		read-write
--		STATUS		mandatory
--		DESCRIPTION
--			"WWN Security setting.
--
--			The bit at the position corresponding to WWNID 
--			shows the state of the access permits.
--			
--			Value	Mean
--			0	Does not accessible.
--			1	Accessible.
--			"
--		::= { raidExMibLUNSLUNGroupEntry 7 }
--
--	lunGroupWWNGroupSecurity	OBJECT-TYPE
--		SYNTAX		OCTET STRING (SIZE(2))
--		ACCESS		read-write
--		STATUS		mandatory
--		DESCRIPTION
--			"WWN group Security setting.
--
--			The bit at the position corresponding to WWNGroupID 
--			shows the state of the access permits.
--			
--			Value	Mean
--			0	Does not accessible.
--			1	Accessible.
--			"
--		::= { raidExMibLUNSLUNGroupEntry 8 }

	lunGroupControlStatus	OBJECT-TYPE
		SYNTAX		INTEGER
		ACCESS		read-write
		STATUS		mandatory
		DESCRIPTION
			"Control flag.

			Value	Mean
			1	Return value.
			2	Add request.
			3	Delete request.
			4	Set request.
			"
		::= { raidExMibLUNSLUNGroupEntry 9 }

	lunGroupedLUNsVL		OBJECT-TYPE
		SYNTAX		OCTET STRING
		ACCESS		read-write
		STATUS		mandatory
		DESCRIPTION
			"Grouped LUNs. (variable length)

		It is shown whether the bit at the position corresponding 
		to LUNLUN belongs to the group. (0:does not belong 1:belongs)

			Value	Mean
			0	Does not belong.
			1	Belongs.
			"
		::= { raidExMibLUNSLUNGroupEntry 10 }

	lunGroupWWNSecurityVL	OBJECT-TYPE
		SYNTAX		OCTET STRING
		ACCESS		read-write
		STATUS		mandatory
		DESCRIPTION
			"WWN Security setting. (variable length)

			The bit at the position corresponding to WWNID 
			shows the state of the access permits.
			
			Value	Mean
			0	Does not accessible.
			1	Accessible.
			"
		::= { raidExMibLUNSLUNGroupEntry 11 }

	lunGroupWWNGroupSecurityVL	OBJECT-TYPE
		SYNTAX		OCTET STRING
		ACCESS		read-write
		STATUS		mandatory
		DESCRIPTION
			"WWN group Security setting. (variable length)

			The bit at the position corresponding to WWNGroupID 
			shows the state of the access permits.
			
			Value	Mean
			0	Does not accessible.
			1	Accessible.
			"
		::= { raidExMibLUNSLUNGroupEntry 12 }

--
-- DCR configuration
--

	raidExMibDCRConfiguration	OBJECT IDENTIFIER ::= { raidExMibRoot 12 }

--
-- Cache size information
--

	raidExMibCacheSizeTable	OBJECT-TYPE
		SYNTAX		SEQUENCE OF RaidExMibCacheSizeEntry
		ACCESS		not-accessible
		STATUS		mandatory
		DESCRIPTION
			"Cache size information."
		::= { raidExMibDCRConfiguration 1 }

	raidExMibCacheSizeEntry		OBJECT-TYPE
		SYNTAX		RaidExMibCacheSizeEntry
		ACCESS		not-accessible
		STATUS		mandatory
		DESCRIPTION
			"Entry of cache size information."
		INDEX {
			cacheSizeSerialNumber
		}
		::= { raidExMibCacheSizeTable 1 }

	RaidExMibCacheSizeEntry ::= 
		SEQUENCE {
			cacheSizeSerialNumber		INTEGER,
			cacheSizeTotalCacheSize		INTEGER,
			cacheSizeUseCacheSize		INTEGER,
			cacheSizeRemainCacheSize	INTEGER
		}

	cacheSizeSerialNumber	OBJECT-TYPE
		SYNTAX		INTEGER
		ACCESS		read-only
		STATUS		mandatory
		DESCRIPTION
			"Serial number of the DKC."
		::= { raidExMibCacheSizeEntry 1 }

	cacheSizeTotalCacheSize	OBJECT-TYPE
		SYNTAX		INTEGER
		ACCESS		read-only
		STATUS		mandatory
		DESCRIPTION
			"TOTAL Cache Size(KB)."
		::= { raidExMibCacheSizeEntry 2 }

	cacheSizeUseCacheSize	OBJECT-TYPE
		SYNTAX		INTEGER
		ACCESS		read-only
		STATUS		mandatory
		DESCRIPTION
			"Use Cache Size(KB)."
		::= { raidExMibCacheSizeEntry 3 }

	cacheSizeRemainCacheSize	OBJECT-TYPE
		SYNTAX		INTEGER
		ACCESS		read-only
		STATUS		mandatory
		DESCRIPTION
			"Remain Cache Size(KB)."
		::= { raidExMibCacheSizeEntry 4 }

--
-- DCR information
-- (DCR: Dynamic Cache Residence)
--

	raidExMibCacheDCRTable	OBJECT-TYPE
		SYNTAX		SEQUENCE OF RaidExMibCacheDCREntry
		ACCESS		not-accessible
		STATUS		mandatory
		DESCRIPTION
			"DCR information."
		::= { raidExMibDCRConfiguration 2 }

	raidExMibCacheDCREntry		OBJECT-TYPE
		SYNTAX		RaidExMibCacheDCREntry
		ACCESS		not-accessible
		STATUS		mandatory
		DESCRIPTION
			"Entry of DCR information."
		INDEX {
			cacheDCRSerialNumber,
			cacheDCRCU,
			cacheDCRLDEV,
			cacheDCRControlIndex
		}
		::= { raidExMibCacheDCRTable 1 }

	RaidExMibCacheDCREntry ::= 
		SEQUENCE {
			cacheDCRSerialNumber	INTEGER,
			cacheDCRCU		INTEGER,
			cacheDCRLDEV		INTEGER,
			cacheDCRControlIndex	INTEGER,
			cacheDCRMode		INTEGER,
			cacheDCRAllOfDevice	INTEGER,
			cacheDCRStartCylinder	INTEGER,
			cacheDCRStartHead	INTEGER,
			cacheDCREndCylinder	INTEGER,
			cacheDCREndHead		INTEGER,
			cacheDCRCylinderSize	INTEGER,
			cacheDCRHeadSize	INTEGER,
			cacheDCRStartLBA	INTEGER,
			cacheDCREndLBA		INTEGER,
			cacheDCRLBASize		INTEGER,
			cacheDCRControlStatus	INTEGER
		}

	cacheDCRSerialNumber	OBJECT-TYPE
		SYNTAX		INTEGER
		ACCESS		read-only
		STATUS		mandatory
		DESCRIPTION
			"Serial number of the DKC."
		::= { raidExMibCacheDCREntry 1 }

	cacheDCRCU		OBJECT-TYPE
		SYNTAX		INTEGER
		ACCESS		read-only
		STATUS		mandatory
		DESCRIPTION
			"CU# of target volume."
		::= { raidExMibCacheDCREntry 2 }

	cacheDCRLDEV		OBJECT-TYPE
		SYNTAX		INTEGER
		ACCESS		read-only
		STATUS		mandatory
		DESCRIPTION
			"LDEV# of target volume."
		::= { raidExMibCacheDCREntry 3 }

	cacheDCRControlIndex	OBJECT-TYPE
		SYNTAX		INTEGER
		ACCESS		read-only
		STATUS		mandatory
		DESCRIPTION
			"Index for DCR control."
		::= { raidExMibCacheDCREntry 4 }

	cacheDCRMode		OBJECT-TYPE
		SYNTAX		INTEGER
		ACCESS		read-write
		STATUS		mandatory
		DESCRIPTION
			"Mode of DCR.
			
			Value	Mean
			0	BIND mode.
			1	PRIO mode.
			"
		::= { raidExMibCacheDCREntry 5 }

	cacheDCRAllOfDevice	OBJECT-TYPE
		SYNTAX		INTEGER
		ACCESS		write-only
		STATUS		mandatory
		DESCRIPTION
			"Specified type of size.
			
			Value	Mean
			0	A part of volume.
			1	The entire volume.
			"
		::= { raidExMibCacheDCREntry 6 }

	cacheDCRStartCylinder	OBJECT-TYPE
		SYNTAX		INTEGER
		ACCESS		read-write
		STATUS		mandatory
		DESCRIPTION
			"Start Cylinder of DCR."
		::= { raidExMibCacheDCREntry 7 }

	cacheDCRStartHead	OBJECT-TYPE
		SYNTAX		INTEGER
		ACCESS		read-write
		STATUS		mandatory
		DESCRIPTION
			"Start Head of DCR."
		::= { raidExMibCacheDCREntry 8 }

	cacheDCREndCylinder	OBJECT-TYPE
		SYNTAX		INTEGER
		ACCESS		read-write
		STATUS		mandatory
		DESCRIPTION
			"End Cylinder of DCR."
		::= { raidExMibCacheDCREntry 9 }

	cacheDCREndHead	OBJECT-TYPE
		SYNTAX		INTEGER
		ACCESS		read-write
		STATUS		mandatory
		DESCRIPTION
			"End Head of DCR."
		::= { raidExMibCacheDCREntry 10 }

	cacheDCRCylinderSize	OBJECT-TYPE
		SYNTAX		INTEGER
		ACCESS		read-only
		STATUS		mandatory
		DESCRIPTION
			"Cylinder size of DCR."
		::= { raidExMibCacheDCREntry 11 }

	cacheDCRHeadSize	OBJECT-TYPE
		SYNTAX		INTEGER
		ACCESS		read-only
		STATUS		mandatory
		DESCRIPTION
			"Head size of DCR."
		::= { raidExMibCacheDCREntry 12 }

	cacheDCRStartLBA	OBJECT-TYPE
		SYNTAX		INTEGER
		ACCESS		read-write
		STATUS		mandatory
		DESCRIPTION
			"Start LBA of DCR."
		::= { raidExMibCacheDCREntry 13 }

	cacheDCREndLBA		OBJECT-TYPE
		SYNTAX		INTEGER
		ACCESS		read-write
		STATUS		mandatory
		DESCRIPTION
			"End LBA of DCR."
		::= { raidExMibCacheDCREntry 14 }

	cacheDCRLBASize		OBJECT-TYPE
		SYNTAX		INTEGER
		ACCESS		read-only
		STATUS		mandatory
		DESCRIPTION
			"LBA size of DCR."
		::= { raidExMibCacheDCREntry 15 }

	cacheDCRControlStatus	OBJECT-TYPE
		SYNTAX		INTEGER
		ACCESS		read-write
		STATUS		mandatory
		DESCRIPTION
			"Control flag.

			Value	Mean
			1	Return value.
			2	Setting request.
			3	Release request.
			"
		::= { raidExMibCacheDCREntry 16 }

--
-- CVS configuration
--

	raidExMibCVSConfiguration	OBJECT IDENTIFIER ::= { raidExMibRoot 13 }

--
-- Base Volume information (for RAID300)
--
-- raid300rmsvExMibBaseVolume OBJECT IDENTIFIER ::=
-- { raid300rmsvExMibCVSConfiguration 1 }
--
-- Customized Volume information (for RAID300)
--
-- rai300rmsvExMibCustomizedVolume OBJECT IDENTIFIER ::= 
-- { raid300rmsvExMibCVSConfiguration 2 }
--
--
-- Customized Volume information
--

	raidExMibCustomizedVolumeTable	OBJECT-TYPE
		SYNTAX		SEQUENCE OF RaidExMibCustomizedVolumeEntry
		ACCESS		not-accessible
		STATUS		mandatory
		DESCRIPTION
			"Customized Volume information."
		::= { raidExMibCVSConfiguration 3 }

	raidExMibCustomizedVolumeEntry	OBJECT-TYPE
		SYNTAX		RaidExMibCustomizedVolumeEntry
		ACCESS		not-accessible
		STATUS		mandatory
		DESCRIPTION
			"Entry of Customized Volume information."
		INDEX {
			customizedVolumeSerialNumber,
			customizedVolumeFB4Number,
			customizedVolumePGNumber,
			customizedVolumeCU,
			customizedVolumeLDEV
		}
		::= { raidExMibCustomizedVolumeTable 1 }

	RaidExMibCustomizedVolumeEntry ::= 
		SEQUENCE {
			customizedVolumeSerialNumber	INTEGER,
			customizedVolumeFB4Number	INTEGER,
			customizedVolumePGNumber	INTEGER,
			customizedVolumeCU		INTEGER,
			customizedVolumeLDEV		INTEGER,
			customizedVolumeType		INTEGER,
			customizedVolumeEmulation	DisplayString,
			customizedVolumeUserCylinder	INTEGER,
			customizedVolumeUserSize	INTEGER,
			customizedVolumeControlCylinder	INTEGER,
			customizedVolumeControlSize	INTEGER,
			customizedVolumeControlStatus	INTEGER
		}

	customizedVolumeSerialNumber	OBJECT-TYPE
		SYNTAX		INTEGER
		ACCESS		read-only
		STATUS		mandatory
		DESCRIPTION
			"Serial number of the DKC."
		::= { raidExMibCustomizedVolumeEntry 1 }

	customizedVolumeFB4Number	OBJECT-TYPE
		SYNTAX		INTEGER
		ACCESS		read-only
		STATUS		mandatory
		DESCRIPTION
			"FB4# of Customized Volume."
		::= { raidExMibCustomizedVolumeEntry 2 }

	customizedVolumePGNumber	OBJECT-TYPE
		SYNTAX		INTEGER
		ACCESS		read-only
		STATUS		mandatory
		DESCRIPTION
			"PG# of Customized Volume."
		::= { raidExMibCustomizedVolumeEntry 3 }

	customizedVolumeCU	OBJECT-TYPE
		SYNTAX		INTEGER
		ACCESS		read-only
		STATUS		mandatory
		DESCRIPTION
			"CU# of Customized Volume."
		::= { raidExMibCustomizedVolumeEntry 4 }

	customizedVolumeLDEV	OBJECT-TYPE
		SYNTAX		INTEGER
		ACCESS		read-only
		STATUS		mandatory
		DESCRIPTION
			"LDEV# of Customized Volume."
		::= { raidExMibCustomizedVolumeEntry 5 }

	customizedVolumeType	OBJECT-TYPE
		SYNTAX		INTEGER
		ACCESS		read-only
		STATUS		mandatory
		DESCRIPTION
			"Type of this volume.

			Value	Mean
			1	Normal Volume.
			2	Customized Volume.
			"
		::= { raidExMibCustomizedVolumeEntry 6 }

	customizedVolumeEmulation	OBJECT-TYPE
		SYNTAX		DisplayString
		ACCESS		read-write
		STATUS		mandatory
		DESCRIPTION
			"Device emulation type."
		::= { raidExMibCustomizedVolumeEntry 7 }

	customizedVolumeUserCylinder	OBJECT-TYPE
		SYNTAX		INTEGER
		ACCESS		read-write
		STATUS		mandatory
		DESCRIPTION
			"Number of user cylinders"
		::= { raidExMibCustomizedVolumeEntry 8 }

	customizedVolumeUserSize	OBJECT-TYPE
		SYNTAX		INTEGER
		ACCESS		read-write
		STATUS		mandatory
		DESCRIPTION
			"Number of user KBs."
		::= { raidExMibCustomizedVolumeEntry 9 }

	customizedVolumeControlCylinder	OBJECT-TYPE
		SYNTAX		INTEGER
		ACCESS		read-only
		STATUS		mandatory
		DESCRIPTION
			"Number of control cylinders"
		::= { raidExMibCustomizedVolumeEntry 10 }

	customizedVolumeControlSize	OBJECT-TYPE
		SYNTAX		INTEGER
		ACCESS		read-only
		STATUS		mandatory
		DESCRIPTION
			"Number of control KBs."
		::= { raidExMibCustomizedVolumeEntry 11 }

	customizedVolumeControlStatus	OBJECT-TYPE
		SYNTAX		INTEGER
		ACCESS		read-write
		STATUS		mandatory
		DESCRIPTION
			"Control flag.

			Value	Mean
			1	Return value.
			2	Install CV request.
			3	Volume to Space request.
			"
		::= { raidExMibCustomizedVolumeEntry 12 }

--
-- CVS deleted normal volume information
--

	raidExMibCVSDeletedVolumeTable	OBJECT-TYPE
		SYNTAX		SEQUENCE OF RaidExMibCVSDeletedVolumeEntry
		ACCESS		not-accessible
		STATUS		mandatory
		DESCRIPTION
			"CVS deleted normal volume information."
		::= { raidExMibCVSConfiguration 4 }

	raidExMibCVSDeletedVolumeEntry	OBJECT-TYPE
		SYNTAX		RaidExMibCVSDeletedVolumeEntry
		ACCESS		not-accessible
		STATUS		mandatory
		DESCRIPTION
			"Entry of CVS deleted normal volume information."
		INDEX {
			cvsDVSerialNumber,
			cvsDVFB4Number,
			cvsDVPGNumber,
			cvsDVControlIndex
		}
		::= { raidExMibCVSDeletedVolumeTable 1 }

	RaidExMibCVSDeletedVolumeEntry ::= 
		SEQUENCE {
			cvsDVSerialNumber	INTEGER,
			cvsDVFB4Number		INTEGER,
			cvsDVPGNumber		INTEGER,
			cvsDVControlIndex	INTEGER,
			cvsDVCU			INTEGER,
			cvsDVLDEV		INTEGER,
			cvsDVEmulation		DisplayString,
			cvsDVCylinder		INTEGER,
			cvsDVSize		INTEGER,
			cvsDVControlCylinder	INTEGER,
			cvsDVControlSize	INTEGER,
			cvsDVControlStatus	INTEGER
		}

	cvsDVSerialNumber	OBJECT-TYPE
		SYNTAX		INTEGER
		ACCESS		read-only
		STATUS		mandatory
		DESCRIPTION
			"Serial number of the DKC."
		::= { raidExMibCVSDeletedVolumeEntry 1 }

	cvsDVFB4Number	OBJECT-TYPE
		SYNTAX		INTEGER
		ACCESS		read-only
		STATUS		mandatory
		DESCRIPTION
			"FB4# of deleted volume."
		::= { raidExMibCVSDeletedVolumeEntry 2 }

	cvsDVPGNumber		OBJECT-TYPE
		SYNTAX		INTEGER
		ACCESS		read-only
		STATUS		mandatory
		DESCRIPTION
			"PG# of deleted volume."
		::= { raidExMibCVSDeletedVolumeEntry 3 }

	cvsDVControlIndex	OBJECT-TYPE
		SYNTAX		INTEGER
		ACCESS		read-only
		STATUS		mandatory
		DESCRIPTION
			"Control index of deleted volume."
		::= { raidExMibCVSDeletedVolumeEntry 4 }

	cvsDVCU			OBJECT-TYPE
		SYNTAX		INTEGER
		ACCESS		write-only
		STATUS		mandatory
		DESCRIPTION
			"CU# of deleted volume."
		::= { raidExMibCVSDeletedVolumeEntry 5 }

	cvsDVLDEV		OBJECT-TYPE
		SYNTAX		INTEGER
		ACCESS		write-only
		STATUS		mandatory
		DESCRIPTION
			"LDEV# of deleted volume."
		::= { raidExMibCVSDeletedVolumeEntry 6 }

	cvsDVEmulation		OBJECT-TYPE
		SYNTAX		DisplayString
		ACCESS		read-only
		STATUS		mandatory
		DESCRIPTION
			"Device emulation type."
		::= { raidExMibCVSDeletedVolumeEntry 7 }

	cvsDVCylinder		OBJECT-TYPE
		SYNTAX		INTEGER
		ACCESS		read-only
		STATUS		mandatory
		DESCRIPTION
			"Number of cylinders"
		::= { raidExMibCVSDeletedVolumeEntry 8 }

	cvsDVSize		OBJECT-TYPE
		SYNTAX		INTEGER
		ACCESS		read-only
		STATUS		mandatory
		DESCRIPTION
			"Number of KB."
		::= { raidExMibCVSDeletedVolumeEntry 9 }

	cvsDVControlCylinder	OBJECT-TYPE
		SYNTAX		INTEGER
		ACCESS		read-only
		STATUS		mandatory
		DESCRIPTION
			"Number of control cylinders"
		::= { raidExMibCVSDeletedVolumeEntry 10 }

	cvsDVControlSize	OBJECT-TYPE
		SYNTAX		INTEGER
		ACCESS		read-only
		STATUS		mandatory
		DESCRIPTION
			"Number of control KB."
		::= { raidExMibCVSDeletedVolumeEntry 11 }

	cvsDVControlStatus	OBJECT-TYPE
		SYNTAX		INTEGER
		ACCESS		read-write
		STATUS		mandatory
		DESCRIPTION
			"Control flag.

			Value	Mean
			1	Return value.
			2	Volume initialize request.
			"
		::= { raidExMibCVSDeletedVolumeEntry 12 }

--
-- CVS free space information on PG
--

	raidExMibCVSFreeSpaceTable	OBJECT-TYPE
		SYNTAX		SEQUENCE OF RaidExMibCVSFreeSpaceEntry
		ACCESS		not-accessible
		STATUS		mandatory
		DESCRIPTION
			"CVS free space information on PG."
		::= { raidExMibCVSConfiguration 5 }

	raidExMibCVSFreeSpaceEntry	OBJECT-TYPE
		SYNTAX		RaidExMibCVSFreeSpaceEntry
		ACCESS		not-accessible
		STATUS		mandatory
		DESCRIPTION
			"Entry of CVS free space information in PG."
		INDEX {
			cvsFSSerialNumber,
			cvsFSFB4Number,
			cvsFSPGNumber,
			cvsFSControlIndex
		}
		::= { raidExMibCVSFreeSpaceTable 1 }

	RaidExMibCVSFreeSpaceEntry ::= 
		SEQUENCE {
			cvsFSSerialNumber	INTEGER,
			cvsFSFB4Number		INTEGER,
			cvsFSPGNumber		INTEGER,
			cvsFSControlIndex	INTEGER,
			cvsFSCylinder		INTEGER,
			cvsFSSize		INTEGER
		}

	cvsFSSerialNumber	OBJECT-TYPE
		SYNTAX		INTEGER
		ACCESS		read-only
		STATUS		mandatory
		DESCRIPTION
			"Serial number of the DKC."
		::= { raidExMibCVSFreeSpaceEntry 1 }

	cvsFSFB4Number		OBJECT-TYPE
		SYNTAX		INTEGER
		ACCESS		read-only
		STATUS		mandatory
		DESCRIPTION
			"FB4# of free space."
		::= { raidExMibCVSFreeSpaceEntry 2 }

	cvsFSPGNumber		OBJECT-TYPE
		SYNTAX		INTEGER
		ACCESS		read-only
		STATUS		mandatory
		DESCRIPTION
			"PG# of free space."
		::= { raidExMibCVSFreeSpaceEntry 3 }

	cvsFSControlIndex	OBJECT-TYPE
		SYNTAX		INTEGER
		ACCESS		read-only
		STATUS		mandatory
		DESCRIPTION
			"PG# of free space."
		::= { raidExMibCVSFreeSpaceEntry 4 }

	cvsFSCylinder		OBJECT-TYPE
		SYNTAX		INTEGER
		ACCESS		read-only
		STATUS		mandatory
		DESCRIPTION
			"Number of cylinders"
		::= { raidExMibCVSFreeSpaceEntry 5 }

	cvsFSSize		OBJECT-TYPE
		SYNTAX		INTEGER
		ACCESS		read-only
		STATUS		mandatory
		DESCRIPTION
			"Number of  KB."
		::= { raidExMibCVSFreeSpaceEntry 6 }

--
-- CVS Parity Group information
--

	raidExMibCVSParityGroupTable	OBJECT-TYPE
		SYNTAX		SEQUENCE OF RaidExMibCVSParityGroupEntry
		ACCESS		not-accessible
		STATUS		mandatory
		DESCRIPTION
			"CVS Parity Group Information."
		::= { raidExMibCVSConfiguration 6 }

	raidExMibCVSParityGroupEntry	OBJECT-TYPE
		SYNTAX		RaidExMibCVSParityGroupEntry
		ACCESS		not-accessible
		STATUS		mandatory
		DESCRIPTION
			"Entry of CVS Parity Group Information."
		INDEX {
			cvsPGSerialNumber,
			cvsPGFB4Number,
			cvsPGPGNumber
		}
		::= { raidExMibCVSParityGroupTable 1 }

	RaidExMibCVSParityGroupEntry ::= 
		SEQUENCE {
			cvsPGSerialNumber	INTEGER,
			cvsPGFB4Number		INTEGER,
			cvsPGPGNumber		INTEGER,
			cvsPGDisplayName		DisplayString,
			cvsPGRAIDType		DisplayString,
			cvsPGDriveType		DisplayString,
			cvsPGFreeCylinder	INTEGER,
			cvsPGFreeSize		INTEGER,
			cvsPGControlStatus	INTEGER
		}

	cvsPGSerialNumber	OBJECT-TYPE
		SYNTAX		INTEGER
		ACCESS		read-only
		STATUS		mandatory
		DESCRIPTION
			"Serial number of the DKC."
		::= { raidExMibCVSParityGroupEntry 1 }

	cvsPGFB4Number		OBJECT-TYPE
		SYNTAX		INTEGER
		ACCESS		read-only
		STATUS		mandatory
		DESCRIPTION
			"FB4 Number."
		::= { raidExMibCVSParityGroupEntry 2 }

	cvsPGPGNumber		OBJECT-TYPE
		SYNTAX		INTEGER
		ACCESS		read-only
		STATUS		mandatory
		DESCRIPTION
			"PG Number."
		::= { raidExMibCVSParityGroupEntry 3 }

	cvsPGDisplayName	OBJECT-TYPE
		SYNTAX		DisplayString
		ACCESS		read-only
		STATUS		mandatory
		DESCRIPTION
			"Display name."
		::= { raidExMibCVSParityGroupEntry 4 }

	cvsPGRAIDType		OBJECT-TYPE
		SYNTAX		DisplayString
		ACCESS		read-only
		STATUS		mandatory
		DESCRIPTION
			"RAID type"
		::= { raidExMibCVSParityGroupEntry 5 }

	cvsPGDriveType		OBJECT-TYPE
		SYNTAX		DisplayString
		ACCESS		read-only
		STATUS		mandatory
		DESCRIPTION
			"Drive type."
		::= { raidExMibCVSParityGroupEntry 6 }

	cvsPGFreeCylinder	OBJECT-TYPE
		SYNTAX		INTEGER
		ACCESS		read-only
		STATUS		mandatory
		DESCRIPTION
			"Cylinder size of free space in the PG."
		::= { raidExMibCVSParityGroupEntry 7 }

	cvsPGFreeSize		OBJECT-TYPE
		SYNTAX		INTEGER
		ACCESS		read-only
		STATUS		mandatory
		DESCRIPTION
			"KB size of free space in the PG."
		::= { raidExMibCVSParityGroupEntry 8 }

	cvsPGControlStatus	OBJECT-TYPE
		SYNTAX		INTEGER
		ACCESS		read-write
		STATUS		mandatory
		DESCRIPTION
			"Control flag.

			Value	Mean
			1	Return value.
			2	Volume initialize request.
			"
		::= { raidExMibCVSParityGroupEntry 9 }

--
-- cvs Control Unit information
--

	raidExMibCVSCUInfTable	OBJECT-TYPE
		SYNTAX		SEQUENCE OF RaidExMibCVSCUInfEntry
		ACCESS		not-accessible
		STATUS		mandatory
		DESCRIPTION
			"CVS Control Unit Information."
		::= { raidExMibCVSConfiguration 7 }

	raidExMibCVSCUInfEntry		OBJECT-TYPE
		SYNTAX		RaidExMibCVSCUInfEntry
		ACCESS		not-accessible
		STATUS		mandatory
		DESCRIPTION
			"Entry of CVS Control Unit Information."
		INDEX {
			cvsCUInfSerialNumber
		}
		::= { raidExMibCVSCUInfTable 1 }

	RaidExMibCVSCUInfEntry ::= 
		SEQUENCE {
			cvsCUInfSerialNumber	INTEGER,
			cvsCUInfFreeCUNum	INTEGER
		}

	cvsCUInfSerialNumber	OBJECT-TYPE
		SYNTAX		INTEGER
		ACCESS		read-only
		STATUS		mandatory
		DESCRIPTION
			"Serial number of the DKC."
		::= { raidExMibCVSCUInfEntry 1 }

	cvsCUInfFreeCUNum	OBJECT-TYPE
		SYNTAX		INTEGER
		ACCESS		read-only
		STATUS		mandatory
		DESCRIPTION
			"Available CU Number."
		::= { raidExMibCVSCUInfEntry 2 }

--
-- Subsystem information
--

	raidExMibSubsystemInfo	OBJECT IDENTIFIER ::= { raidExMibRoot 14 }

--
-- Subsystem ID information
--

	raidExMibSubsystemIDTable	OBJECT-TYPE
		SYNTAX		SEQUENCE OF RaidExMibSubsystemIDEntry
		ACCESS		not-accessible
		STATUS		mandatory
		DESCRIPTION
			"Subsystem ID information."
		::= { raidExMibSubsystemInfo 1 }

	raidExMibSubsystemIDEntry	OBJECT-TYPE
		SYNTAX		RaidExMibSubsystemIDEntry
		ACCESS		not-accessible
		STATUS		mandatory
		DESCRIPTION
			"Entry of Subsystem ID information."
		INDEX {
			subsystemIDSerialNumber,
			subsystemIDCU,
			subsystemIDStartLDEV
		}
		::= { raidExMibSubsystemIDTable 1 }

	RaidExMibSubsystemIDEntry ::= 
		SEQUENCE {
			subsystemIDSerialNumber		INTEGER,
			subsystemIDCU			INTEGER,
			subsystemIDStartLDEV		INTEGER,
			subsystemIDEndLDEV		INTEGER,
			subsystemIDSSID			INTEGER,
			subsystemIDControlStatus	INTEGER,
			subsystemIDBoundary		INTEGER
		}

	subsystemIDSerialNumber	OBJECT-TYPE
		SYNTAX		INTEGER
		ACCESS		read-only
		STATUS		mandatory
		DESCRIPTION
			"Serial number of the DKC."
		::= { raidExMibSubsystemIDEntry 1 }

	subsystemIDCU		OBJECT-TYPE
		SYNTAX		INTEGER
		ACCESS		read-only
		STATUS		mandatory
		DESCRIPTION
			"CU# of subsystem."
		::= { raidExMibSubsystemIDEntry 2 }

	subsystemIDStartLDEV	OBJECT-TYPE
		SYNTAX		INTEGER
		ACCESS		read-only
		STATUS		mandatory
		DESCRIPTION
			"Start LDEV# of subsystem."
		::= { raidExMibSubsystemIDEntry 3 }

	subsystemIDEndLDEV	OBJECT-TYPE
		SYNTAX		INTEGER
		ACCESS		read-only
		STATUS		mandatory
		DESCRIPTION
			"End LDEV# of subsystem."
		::= { raidExMibSubsystemIDEntry 4 }

	subsystemIDSSID		OBJECT-TYPE
		SYNTAX		INTEGER
		ACCESS		read-write
		STATUS		mandatory
		DESCRIPTION
			"ID of subsystem."
		::= { raidExMibSubsystemIDEntry 5 }

	subsystemIDControlStatus	OBJECT-TYPE
		SYNTAX		INTEGER
		ACCESS		read-write
		STATUS		mandatory
		DESCRIPTION
			"Control flag.

			Value	Mean
			1	Return value.
			2	Setting request.
			"
		::= { raidExMibSubsystemIDEntry 6 }



--
-- Subsystem ID information
--

	raidExMibSSIDBoundaryTable	OBJECT-TYPE
		SYNTAX		SEQUENCE OF RaidExMibSSIDBoundaryEntry
		ACCESS		not-accessible
		STATUS		mandatory
		DESCRIPTION
			"Subsystem ID Boundary information."
		::= { raidExMibSubsystemInfo 2 }

	raidExMibSSIDBoundaryEntry	OBJECT-TYPE
		SYNTAX		RaidExMibSSIDBoundaryEntry
		ACCESS		not-accessible
		STATUS		mandatory
		DESCRIPTION
			"Entry of Subsystem ID Boundary information."
		INDEX {
			ssidBoundarySerialNumber
		}
		::= { raidExMibSSIDBoundaryTable 1 }

	RaidExMibSSIDBoundaryEntry ::= 
		SEQUENCE {
			ssidBoundarySerialNumber		INTEGER,
			ssidBoundaryBoundary		INTEGER
		}

	ssidBoundarySerialNumber	OBJECT-TYPE
		SYNTAX		INTEGER
		ACCESS		read-only
		STATUS		mandatory
		DESCRIPTION
			"Serial number of the DKC."
		::= { raidExMibSSIDBoundaryEntry 1 }

	ssidBoundaryBoundary		OBJECT-TYPE
		SYNTAX		INTEGER
		ACCESS		read-only
		STATUS		mandatory
		DESCRIPTION
			"The unit of SSID."
		::= { raidExMibSSIDBoundaryEntry 2 }

	
--
-- Environment information
--

	raidExMibEnvironmentInfo	OBJECT IDENTIFIER ::= { raidExMibRoot 15 }

--
-- Time zone information
--
	raidExMibTimeZoneDataTable	OBJECT-TYPE
		SYNTAX		SEQUENCE OF RaidExMibTimeZoneDataEntry
		ACCESS		not-accessible
		STATUS		mandatory
		DESCRIPTION
			"Time Zone information."
		::= { raidExMibEnvironmentInfo 1 }

	raidExMibTimeZoneDataEntry		OBJECT-TYPE
		SYNTAX		RaidExMibTimeZoneDataEntry
		ACCESS		not-accessible
		STATUS		mandatory
		DESCRIPTION
			"Time Zone information."
		INDEX {
			timeZoneSerialNumber
		}
		::= { raidExMibTimeZoneDataTable 1 }

	RaidExMibTimeZoneDataEntry ::=
		SEQUENCE {
			timeZoneSerialNumber	INTEGER,
			timeZoneID		DisplayString
		}

	timeZoneSerialNumber	OBJECT-TYPE
		SYNTAX		INTEGER
		ACCESS		read-only
		STATUS		mandatory
		DESCRIPTION
			"Serial Number of the DKC."
		::= { raidExMibTimeZoneDataEntry 1 }

	timeZoneID		OBJECT-TYPE
		SYNTAX		DisplayString
		ACCESS		read-only
		STATUS		mandatory
		DESCRIPTION	
			"Time Zone ID.
                               zone =	UT/GMT		;Universal Time
							;North American : UT
					/EST/EDT	;Eastern : -5/-4
					/CST/CDT	;Central : -6/-5
					/MST/MDT	;Mountain: -7/-6
					/PST/PDT	;Pacific : -8/-7
					/ 1ALPHA	;Military:Z = UT;
							; A:-1;(J not used)
							; M:-12;N:+1;Y:+12
					/((+/-)4DIGIT	;Local differential
							; hours+min.(HHMM)
                        "
		::= { raidExMibTimeZoneDataEntry 2 }

--
-- Channel Adapter information
--

	raidExMibChannelAdapter	OBJECT IDENTIFIER ::= { raidExMibRoot 16 }

--
-- CHA configuration information
--

	raidExMibCHAConfigurationTable	OBJECT-TYPE
		SYNTAX		SEQUENCE OF RaidExMibCHAConfigurationEntry
		ACCESS		not-accessible 
		STATUS		mandatory
		DESCRIPTION
			"Channel Adapter configuration information."
		::= { raidExMibChannelAdapter 1 }

	raidExMibCHAConfigurationEntry		OBJECT-TYPE
		SYNTAX		RaidExMibCHAConfigurationEntry
		ACCESS		not-accessible
		STATUS		mandatory
		DESCRIPTION
			"Entry of Channel Adapter configuration information."
		INDEX {
			chaSerialNumber,
			chaClusterNumber,
			chaNumber
		}
		::= { raidExMibCHAConfigurationTable 1 }

	RaidExMibCHAConfigurationEntry ::= 
		SEQUENCE {
			chaSerialNumber		INTEGER,
			chaClusterNumber	INTEGER,
			chaNumber		INTEGER,
			chaDisplayName		DisplayString,
			chaPackageType		INTEGER,
			chaMode			INTEGER,
			chaControlStatus	INTEGER
		}

	chaSerialNumber		OBJECT-TYPE
		SYNTAX		INTEGER
		ACCESS		read-only
		STATUS		mandatory
		DESCRIPTION
			"Serial number of the DKC."
		::= { raidExMibCHAConfigurationEntry 1 }

	chaClusterNumber	OBJECT-TYPE
		SYNTAX		INTEGER
		ACCESS		read-only
		STATUS		mandatory
		DESCRIPTION
			"Cluster number."
		::= { raidExMibCHAConfigurationEntry 2 }

	chaNumber		OBJECT-TYPE
		SYNTAX		INTEGER
		ACCESS		read-only
		STATUS		mandatory
		DESCRIPTION
			"Channel Adapter number."
		::= { raidExMibCHAConfigurationEntry 3 }

	chaDisplayName		OBJECT-TYPE
		SYNTAX		DisplayString
		ACCESS		read-only
		STATUS		mandatory
		DESCRIPTION
			"Display name of the CHA."
		::= { raidExMibCHAConfigurationEntry 4 }

	chaPackageType		OBJECT-TYPE
		SYNTAX		INTEGER
		ACCESS		read-only
		STATUS		mandatory
		DESCRIPTION
			"Package type.
			
			Value	Mean
			1	Metal channel.
			2	ESCON channel.
			3	SCSI channel.
			4	Fibre-Tachyon (2 port).
			5	Fibre-Tachyon (4 port).
			"
		::= { raidExMibCHAConfigurationEntry 5 }

	chaMode			OBJECT-TYPE
		SYNTAX		INTEGER
		ACCESS		read-only
		STATUS		mandatory
		DESCRIPTION
			"Operation mode.
			
			Value	Mean
			1	Normal mode.
			2	Hi-Speed mode.
			3	Irregular mode.
			"
		::= { raidExMibCHAConfigurationEntry 6 }

	chaControlStatus	OBJECT-TYPE
		SYNTAX		INTEGER
		ACCESS		read-write
		STATUS		mandatory
		DESCRIPTION
			"Control flag.

			Value	Mean
			1	Return value.
			2	Setting request.
			"
		::= { raidExMibCHAConfigurationEntry 7 }

--
-- CHP configuration information
--

	raidExMibCHPConfigurationTable	OBJECT-TYPE
		SYNTAX		SEQUENCE OF RaidExMibCHPConfigurationEntry
		ACCESS		not-accessible 
		STATUS		mandatory
		DESCRIPTION
			"Channel Processor configuration information."
		::= { raidExMibChannelAdapter 2 }

	raidExMibCHPConfigurationEntry		OBJECT-TYPE
		SYNTAX		RaidExMibCHPConfigurationEntry
		ACCESS		not-accessible
		STATUS		mandatory
		DESCRIPTION
			"Entry of Channel Processor configuration information."
		INDEX {
			chpSerialNumber,
			chpClusterNumber,
			chpCHANumber,
			chpNumber
		}
		::= { raidExMibCHPConfigurationTable 1 }

	RaidExMibCHPConfigurationEntry ::= 
		SEQUENCE {
			chpSerialNumber		INTEGER,
			chpClusterNumber	INTEGER,
			chpCHANumber		INTEGER,
			chpNumber		INTEGER,
			chpDisplayName		DisplayString
		}

	chpSerialNumber		OBJECT-TYPE
		SYNTAX		INTEGER
		ACCESS		read-only
		STATUS		mandatory
		DESCRIPTION
			"Serial number of the DKC."
		::= { raidExMibCHPConfigurationEntry 1 }

	chpClusterNumber	OBJECT-TYPE
		SYNTAX		INTEGER
		ACCESS		read-only
		STATUS		mandatory
		DESCRIPTION
			"Cluster number."
		::= { raidExMibCHPConfigurationEntry 2 }

	chpCHANumber		OBJECT-TYPE
		SYNTAX		INTEGER
		ACCESS		read-only
		STATUS		mandatory
		DESCRIPTION
			"Channel Adapter number."
		::= { raidExMibCHPConfigurationEntry 3 }

	chpNumber		OBJECT-TYPE
		SYNTAX		INTEGER
		ACCESS		read-only
		STATUS		mandatory
		DESCRIPTION
			"Channel Processor number."
		::= { raidExMibCHPConfigurationEntry 4 }

	chpDisplayName		OBJECT-TYPE
		SYNTAX		DisplayString
		ACCESS		read-only
		STATUS		mandatory
		DESCRIPTION
			"Display name of the CHP."
		::= { raidExMibCHPConfigurationEntry 5 }

--
-- Disk Adapter information
--

	raidExMibDiskAdapter	OBJECT IDENTIFIER ::= { raidExMibRoot 17 }

--
-- DKA configuration information
--

	raidExMibDKAConfigurationTable	OBJECT-TYPE
		SYNTAX		SEQUENCE OF RaidExMibDKAConfigurationEntry
		ACCESS		not-accessible 
		STATUS		mandatory
		DESCRIPTION
			"Disk Adapter configuration information."
		::= { raidExMibDiskAdapter 1 }

	raidExMibDKAConfigurationEntry		OBJECT-TYPE
		SYNTAX		RaidExMibDKAConfigurationEntry
		ACCESS		not-accessible
		STATUS		mandatory
		DESCRIPTION
			"Entry of Disk Adapter configuration information."
		INDEX {
			dkaSerialNumber,
			dkaClusterNumber,
			dkaNumber
		}
		::= { raidExMibDKAConfigurationTable 1 }

	RaidExMibDKAConfigurationEntry ::= 
		SEQUENCE {
			dkaSerialNumber		INTEGER,
			dkaClusterNumber	INTEGER,
			dkaNumber		INTEGER,
			dkaDisplayName		DisplayString
		}

	dkaSerialNumber		OBJECT-TYPE
		SYNTAX		INTEGER
		ACCESS		read-only
		STATUS		mandatory
		DESCRIPTION
			"Serial number of the DKC."
		::= { raidExMibDKAConfigurationEntry 1 }

	dkaClusterNumber	OBJECT-TYPE
		SYNTAX		INTEGER
		ACCESS		read-only
		STATUS		mandatory
		DESCRIPTION
			"Cluster number."
		::= { raidExMibDKAConfigurationEntry 2 }

	dkaNumber		OBJECT-TYPE
		SYNTAX		INTEGER
		ACCESS		read-only
		STATUS		mandatory
		DESCRIPTION
			"Disk Adapter number."
		::= { raidExMibDKAConfigurationEntry 3 }

	dkaDisplayName		OBJECT-TYPE
		SYNTAX		DisplayString
		ACCESS		read-only
		STATUS		mandatory
		DESCRIPTION
			"Display name of the DKA."
		::= { raidExMibDKAConfigurationEntry 4 }

--
-- DKP configuration information
--

	raidExMibDKPConfigurationTable	OBJECT-TYPE
		SYNTAX		SEQUENCE OF RaidExMibDKPConfigurationEntry
		ACCESS		not-accessible 
		STATUS		mandatory
		DESCRIPTION
			"Channel Processor configuration information."
		::= { raidExMibDiskAdapter 2 }

	raidExMibDKPConfigurationEntry		OBJECT-TYPE
		SYNTAX		RaidExMibDKPConfigurationEntry
		ACCESS		not-accessible
		STATUS		mandatory
		DESCRIPTION
			"Entry of Channel Processor configuration information."
		INDEX {
			dkpSerialNumber,
			dkpClusterNumber,
			dkpDKANumber,
			dkpNumber
		}
		::= { raidExMibDKPConfigurationTable 1 }

	RaidExMibDKPConfigurationEntry ::= 
		SEQUENCE {
			dkpSerialNumber		INTEGER,
			dkpClusterNumber	INTEGER,
			dkpDKANumber		INTEGER,
			dkpNumber		INTEGER,
			dkpDisplayName		DisplayString
		}

	dkpSerialNumber		OBJECT-TYPE
		SYNTAX		INTEGER
		ACCESS		read-only
		STATUS		mandatory
		DESCRIPTION
			"Serial number of the DKC."
		::= { raidExMibDKPConfigurationEntry 1 }

	dkpClusterNumber	OBJECT-TYPE
		SYNTAX		INTEGER
		ACCESS		read-only
		STATUS		mandatory
		DESCRIPTION
			"Cluster number."
		::= { raidExMibDKPConfigurationEntry 2 }

	dkpDKANumber		OBJECT-TYPE
		SYNTAX		INTEGER
		ACCESS		read-only
		STATUS		mandatory
		DESCRIPTION
			"Disk Adapter number."
		::= { raidExMibDKPConfigurationEntry 3 }

	dkpNumber		OBJECT-TYPE
		SYNTAX		INTEGER
		ACCESS		read-only
		STATUS		mandatory
		DESCRIPTION
			"Disk Processor number."
		::= { raidExMibDKPConfigurationEntry 4 }

	dkpDisplayName		OBJECT-TYPE
		SYNTAX		DisplayString
		ACCESS		read-only
		STATUS		mandatory
		DESCRIPTION
			"Display name of the DKP."
		::= { raidExMibDKPConfigurationEntry 5 }

--
-- DRR configuration information
--

	raidExMibDRRConfigurationTable	OBJECT-TYPE
		SYNTAX		SEQUENCE OF RaidExMibDRRConfigurationEntry
		ACCESS		not-accessible 
		STATUS		mandatory
		DESCRIPTION
			"DRR configuration information."
		::= { raidExMibDiskAdapter 3 }

	raidExMibDRRConfigurationEntry		OBJECT-TYPE
		SYNTAX		RaidExMibDRRConfigurationEntry
		ACCESS		not-accessible
		STATUS		mandatory
		DESCRIPTION
			"Entry of DRR configuration information."
		INDEX {
			drrSerialNumber,
			drrClusterNumber,
			drrDKANumber,
			drrNumber
		}
		::= { raidExMibDRRConfigurationTable 1 }

	RaidExMibDRRConfigurationEntry ::= 
		SEQUENCE {
			drrSerialNumber		INTEGER,
			drrClusterNumber	INTEGER,
			drrDKANumber		INTEGER,
			drrNumber		INTEGER,
			drrDisplayName		DisplayString
		}

	drrSerialNumber		OBJECT-TYPE
		SYNTAX		INTEGER
		ACCESS		read-only
		STATUS		mandatory
		DESCRIPTION
			"Serial number of the DKC."
		::= { raidExMibDRRConfigurationEntry 1 }

	drrClusterNumber	OBJECT-TYPE
		SYNTAX		INTEGER
		ACCESS		read-only
		STATUS		mandatory
		DESCRIPTION
			"Cluster number."
		::= { raidExMibDRRConfigurationEntry 2 }

	drrDKANumber		OBJECT-TYPE
		SYNTAX		INTEGER
		ACCESS		read-only
		STATUS		mandatory
		DESCRIPTION
			"Disk Adapter number."
		::= { raidExMibDRRConfigurationEntry 3 }

	drrNumber		OBJECT-TYPE
		SYNTAX		INTEGER
		ACCESS		read-only
		STATUS		mandatory
		DESCRIPTION
			"DRR Number."
		::= { raidExMibDRRConfigurationEntry 4 }

	drrDisplayName		OBJECT-TYPE
		SYNTAX		DisplayString
		ACCESS		read-only
		STATUS		mandatory
		DESCRIPTION
			"Display name of the DRR."
		::= { raidExMibDRRConfigurationEntry 5 }

--
-- Parity Group information
--

	raidExMibParityGroup	OBJECT IDENTIFIER ::= { raidExMibRoot 18 }

--
-- Parity Group list
--

	raidExMibParityGroupListTable	OBJECT-TYPE
		SYNTAX		SEQUENCE OF RaidExMibParityGroupListEntry
		ACCESS		not-accessible 
		STATUS		mandatory
		DESCRIPTION
			"Parity Group list."
		::= { raidExMibParityGroup 1 }

	raidExMibParityGroupListEntry		OBJECT-TYPE
		SYNTAX		RaidExMibParityGroupListEntry
		ACCESS		not-accessible
		STATUS		mandatory
		DESCRIPTION
			"Entry of Parity Group list."
		INDEX {
			pgSerialNumber,
			pgFB4Number,
			pgNumber
		}
		::= { raidExMibParityGroupListTable 1 }

	RaidExMibParityGroupListEntry ::= 
		SEQUENCE {
			pgSerialNumber		INTEGER,
			pgFB4Number		INTEGER,
			pgNumber		INTEGER,
			pgDisplayName		DisplayString,
			pgRAIDType		DisplayString,
			pgDriveType		DisplayString,
			pgHIHSMFixed		INTEGER,
			pgControlStatus		INTEGER
		}

	pgSerialNumber		OBJECT-TYPE
		SYNTAX		INTEGER
		ACCESS		read-only
		STATUS		mandatory
		DESCRIPTION
			"Serial number of the DKC."
		::= { raidExMibParityGroupListEntry 1 }

	pgFB4Number		OBJECT-TYPE
		SYNTAX		INTEGER
		ACCESS		read-only
		STATUS		mandatory
		DESCRIPTION
			"FB4 number."
		::= { raidExMibParityGroupListEntry 2 }

	pgNumber		OBJECT-TYPE
		SYNTAX		INTEGER
		ACCESS		read-only
		STATUS		mandatory
		DESCRIPTION
			"Parity Group number."
		::= { raidExMibParityGroupListEntry 3 }

	pgDisplayName		OBJECT-TYPE
		SYNTAX		DisplayString
		ACCESS		read-only
		STATUS		mandatory
		DESCRIPTION
			"Display name of the PG."
		::= { raidExMibParityGroupListEntry 4 }

	pgRAIDType		OBJECT-TYPE
		SYNTAX		DisplayString
		ACCESS		read-only
		STATUS		mandatory
		DESCRIPTION
			"RAID Type."
		::= { raidExMibParityGroupListEntry 5 }

	pgDriveType		OBJECT-TYPE
		SYNTAX		DisplayString
		ACCESS		read-only
		STATUS		mandatory
		DESCRIPTION
			"Drive Type."
		::= { raidExMibParityGroupListEntry 6 }

	pgHIHSMFixed		OBJECT-TYPE
		SYNTAX		INTEGER
		ACCESS		read-write
		STATUS		mandatory
		DESCRIPTION
			"HIHSM Fixed attribute.
			
			Value	Mean
			0	Non Fixed.
			1	Fixed.
			"
		::= { raidExMibParityGroupListEntry 7 }

	pgControlStatus		OBJECT-TYPE
		SYNTAX		INTEGER
		ACCESS		read-write
		STATUS		mandatory
		DESCRIPTION
			"Control flag.

			Value	Mean
			1	Return value.
			2	Setting request.
			"
		::= { raidExMibParityGroupListEntry 8 }

--
-- PG Logical Device list
--

	raidExMibParityGroupLDEVTable	OBJECT-TYPE
		SYNTAX		SEQUENCE OF RaidExMibParityGroupLDEVEntry
		ACCESS		not-accessible 
		STATUS		mandatory
		DESCRIPTION
			"Logical Device list in the PG."
		::= { raidExMibParityGroup 2 }

	raidExMibParityGroupLDEVEntry		OBJECT-TYPE
		SYNTAX		RaidExMibParityGroupLDEVEntry
		ACCESS		not-accessible
		STATUS		mandatory
		DESCRIPTION
			"Entry of Parity Group list in the PG."
		INDEX {
			pgLDEVSerialNumber,
			pgLDEVFB4Number,
			pgLDEVPGNumber,
			pgLDEVControlIndex
		}
		::= { raidExMibParityGroupLDEVTable 1 }

RaidExMibParityGroupLDEVEntry ::= 
		SEQUENCE {
			pgLDEVSerialNumber	INTEGER,
			pgLDEVFB4Number		INTEGER,
			pgLDEVPGNumber		INTEGER,
			pgLDEVControlIndex	INTEGER,
			pgLDEVCU		INTEGER,
			pgLDEVLDEV		INTEGER
		}

	pgLDEVSerialNumber	OBJECT-TYPE
		SYNTAX		INTEGER
		ACCESS		read-only
		STATUS		mandatory
		DESCRIPTION
			"Serial number of the DKC."
		::= { raidExMibParityGroupLDEVEntry 1 }

	pgLDEVFB4Number		OBJECT-TYPE
		SYNTAX		INTEGER
		ACCESS		read-only
		STATUS		mandatory
		DESCRIPTION
			"FB4 number."
		::= { raidExMibParityGroupLDEVEntry 2 }

	pgLDEVPGNumber		OBJECT-TYPE
		SYNTAX		INTEGER
		ACCESS		read-only
		STATUS		mandatory
		DESCRIPTION
			"Parity Group number."
		::= { raidExMibParityGroupLDEVEntry 3 }

	pgLDEVControlIndex	OBJECT-TYPE
		SYNTAX		INTEGER
		ACCESS		read-only
		STATUS		mandatory
		DESCRIPTION
			"Control index."
		::= { raidExMibParityGroupLDEVEntry 4 }

	pgLDEVCU		OBJECT-TYPE
		SYNTAX		INTEGER
		ACCESS		read-only
		STATUS		mandatory
		DESCRIPTION
			"CU# of the logical device."
		::= { raidExMibParityGroupLDEVEntry 5 }

	pgLDEVLDEV		OBJECT-TYPE
		SYNTAX		INTEGER
		ACCESS		read-only
		STATUS		mandatory
		DESCRIPTION
			"LDEV# of the logical device."
		::= { raidExMibParityGroupLDEVEntry 6 }

--
-- HIHSM information (for RAID300)
--
--	raid300rmsvExMibHIHSM	OBJECT IDENTIFIER ::= { raid300rmsvExMib 19 }
--

--
-- HIHSM information
--

	raidExMibHIHSM	OBJECT IDENTIFIER ::= { raidExMibRoot 20 }

--
-- HIHSM monitoring parameter information
--

	hihsmMonitoringParameterTable 	OBJECT-TYPE
		SYNTAX		SEQUENCE OF HihsmMonitoringParameterEntry
		ACCESS		not-accessible 
		STATUS		mandatory
		DESCRIPTION
			"HIHSM monitoring parameter information."
		::= { raidExMibHIHSM 1 }

	hihsmMonitoringParameterEntry	OBJECT-TYPE
		SYNTAX		HihsmMonitoringParameterEntry
		ACCESS		not-accessible
		STATUS		mandatory
		DESCRIPTION
			"Entry of HIHSM monitoring parameter information."
		INDEX {
			hihsmMonParamSerialNumber
		}
		::= { hihsmMonitoringParameterTable 1 }

	HihsmMonitoringParameterEntry ::= 
		SEQUENCE {
			hihsmMonParamSerialNumber	INTEGER,
			hihsmMonParamFunctionSwitch	INTEGER,
			hihsmMonParamGatheringTime	DisplayString,
			hihsmMonParamGatheredFromDate	DisplayString,
			hihsmMonParamGatheredFromTime	DisplayString,
			hihsmMonParamGatheredToDate	DisplayString,
			hihsmMonParamGatheredToTime	DisplayString,
			hihsmMonParamControlStatus	INTEGER
		}

	hihsmMonParamSerialNumber	OBJECT-TYPE
		SYNTAX		INTEGER
		ACCESS		read-only
		STATUS		mandatory
		DESCRIPTION
			"Serial number of the DKC."
		::= { hihsmMonitoringParameterEntry 1 }

	hihsmMonParamFunctionSwitch	OBJECT-TYPE
		SYNTAX		INTEGER
		ACCESS		read-write
		STATUS		mandatory
		DESCRIPTION
			"Function switch.
			
			Value	Mean
			0	Off
			1	On
			"
		::= { hihsmMonitoringParameterEntry 2 }

	hihsmMonParamGatheringTime	OBJECT-TYPE
		SYNTAX		DisplayString
		ACCESS		read-write
		STATUS		mandatory
		DESCRIPTION
			"Gathering time."
		::= { hihsmMonitoringParameterEntry 3 }

	hihsmMonParamGatheredFromDate	OBJECT-TYPE
		SYNTAX		DisplayString
		ACCESS		read-only
		STATUS		mandatory
		DESCRIPTION
			"Top gathered date."
		::= { hihsmMonitoringParameterEntry 4 }

	hihsmMonParamGatheredFromTime	OBJECT-TYPE
		SYNTAX		DisplayString
		ACCESS		read-only
		STATUS		mandatory
		DESCRIPTION
			"Top gathered time."
		::= { hihsmMonitoringParameterEntry 5 }

	hihsmMonParamGatheredToDate	OBJECT-TYPE
		SYNTAX		DisplayString
		ACCESS		read-only
		STATUS		mandatory
		DESCRIPTION
			"End gathered date."
		::= { hihsmMonitoringParameterEntry 6 }

	hihsmMonParamGatheredToTime	OBJECT-TYPE
		SYNTAX		DisplayString
		ACCESS		read-only
		STATUS		mandatory
		DESCRIPTION
			"End gathered time."
		::= { hihsmMonitoringParameterEntry 7 }

	hihsmMonParamControlStatus	OBJECT-TYPE
		SYNTAX		INTEGER
		ACCESS		read-write
		STATUS		mandatory
		DESCRIPTION
			"Control flag.

			Value	Mean
			1	Return value.
			2	Setting request.
			"
		::= { hihsmMonitoringParameterEntry 8 }

--
-- hihsm calculation parameter information
--

	hihsmCalculationParameterTable	OBJECT-TYPE
		SYNTAX		SEQUENCE OF HihsmCalculationParameterEntry
		ACCESS		not-accessible 
		STATUS		mandatory
		DESCRIPTION
			"HIHSM calculation parameter information."
		::= { raidExMibHIHSM 2 }

	hihsmCalculationParameterEntry	OBJECT-TYPE
		SYNTAX		HihsmCalculationParameterEntry
		ACCESS		not-accessible
		STATUS		mandatory
		DESCRIPTION
			"Entry of HIHSM monitoring parameter configuration."
		INDEX {
			hihsmCalcParamSerialNumber
		}
		::= { hihsmCalculationParameterTable 1 }

	HihsmCalculationParameterEntry ::= 
		SEQUENCE {
			hihsmCalcParamSerialNumber	INTEGER,
			hihsmCalcParamCalcType		INTEGER,
			hihsmCalcParamFromDate		DisplayString,
			hihsmCalcParamFromTime		DisplayString,
			hihsmCalcParamToDate		DisplayString,
			hihsmCalcParamToTime		DisplayString,
			hihsmCalcParamDataType		INTEGER,
			hihsmCalcParamControlStatus	INTEGER
		}

	hihsmCalcParamSerialNumber	OBJECT-TYPE
		SYNTAX		INTEGER
		ACCESS		read-only
		STATUS		mandatory
		DESCRIPTION
			"Serial number of the DKC."
		::= { hihsmCalculationParameterEntry 1 }

	hihsmCalcParamCalcType	OBJECT-TYPE
		SYNTAX		INTEGER
		ACCESS		read-write
		STATUS		mandatory
		DESCRIPTION
			"Calculation type.
			
			Value	Mean
			0	All of gathered data.
			1	Specified term.
			"
		::= { hihsmCalculationParameterEntry 2 }

	hihsmCalcParamFromDate	OBJECT-TYPE
		SYNTAX		DisplayString
		ACCESS		read-write
		STATUS		mandatory
		DESCRIPTION
			"Start date of calculation term."
		::= { hihsmCalculationParameterEntry 3 }

	hihsmCalcParamFromTime	OBJECT-TYPE
		SYNTAX		DisplayString
		ACCESS		read-write
		STATUS		mandatory
		DESCRIPTION
			"Start time of calculation term."
		::= { hihsmCalculationParameterEntry 4 }

	hihsmCalcParamToDate	OBJECT-TYPE
		SYNTAX		DisplayString
		ACCESS		read-write
		STATUS		mandatory
		DESCRIPTION
			"End date of calculation term."
		::= { hihsmCalculationParameterEntry 5 }

	hihsmCalcParamToTime	OBJECT-TYPE
		SYNTAX		DisplayString
		ACCESS		read-write
		STATUS		mandatory
		DESCRIPTION
			"End time of calculation term."
		::= { hihsmCalculationParameterEntry 6 }

	hihsmCalcParamDataType	OBJECT-TYPE
		SYNTAX		INTEGER
		ACCESS		read-write
		STATUS		mandatory
		DESCRIPTION
			"Data Type.

			Value	Mean
			0	Data on SVP is used.
			1	DKC latest data is used.
			"
		::= { hihsmCalculationParameterEntry 7 }

	hihsmCalcParamControlStatus	OBJECT-TYPE
		SYNTAX		INTEGER
		ACCESS		read-write
		STATUS		mandatory
		DESCRIPTION
			"Control flag.

			Value	Mean
			1	Return value.
			2	Setting request.
			"
		::= { hihsmCalculationParameterEntry 8 }

--
-- HIHSM calculated data information
--

	hihsmCalculatedData	OBJECT IDENTIFIER ::= { raidExMibHIHSM 3 }

--
-- HIHSM CHP utilization information
--

	hihsmCHPUtilizationTable		OBJECT-TYPE
		SYNTAX		SEQUENCE OF HihsmCHPUtilizationEntry
		ACCESS		not-accessible 
		STATUS		mandatory
		DESCRIPTION
			"HIHSM CHP utilization information."
		::= { hihsmCalculatedData 1 }

	hihsmCHPUtilizationEntry		OBJECT-TYPE
		SYNTAX		HihsmCHPUtilizationEntry
		ACCESS		not-accessible
		STATUS		mandatory
		DESCRIPTION
			"Entry of HIHSM CHP utilization information."
		INDEX {
			hihsmCHPUtilSerialNumber,
			hihsmCHPUtilClusterNumber,
			hihsmCHPUtilCHANumber,
			hihsmCHPUtilCHPNumber
		}
		::= { hihsmCHPUtilizationTable 1 }

	HihsmCHPUtilizationEntry ::= 
		SEQUENCE {
			hihsmCHPUtilSerialNumber	INTEGER,
			hihsmCHPUtilClusterNumber	INTEGER,
			hihsmCHPUtilCHANumber		INTEGER,
			hihsmCHPUtilCHPNumber		INTEGER,
			hihsmCHPUtilData		DisplayString
		}

	hihsmCHPUtilSerialNumber	OBJECT-TYPE
		SYNTAX		INTEGER
		ACCESS		read-only
		STATUS		mandatory
		DESCRIPTION
			"Serial number of the DKC."
		::= { hihsmCHPUtilizationEntry	 1 }

	hihsmCHPUtilClusterNumber	OBJECT-TYPE
		SYNTAX		INTEGER
		ACCESS		read-only
		STATUS		mandatory
		DESCRIPTION
			"Cluster number."
		::= { hihsmCHPUtilizationEntry	 2 }

	hihsmCHPUtilCHANumber	OBJECT-TYPE
		SYNTAX		INTEGER
		ACCESS		read-only
		STATUS		mandatory
		DESCRIPTION
			"Channel Adapter number."
		::= { hihsmCHPUtilizationEntry	 3 }

	hihsmCHPUtilCHPNumber	OBJECT-TYPE
		SYNTAX		INTEGER
		ACCESS		read-only
		STATUS		mandatory
		DESCRIPTION
			"Channel Processor number."
		::= { hihsmCHPUtilizationEntry	 4 }

	hihsmCHPUtilData	OBJECT-TYPE
		SYNTAX		DisplayString
		ACCESS		read-only
		STATUS		mandatory
		DESCRIPTION
			"Channel Processor utilization.

			Column	Value
			1	Average.
			2	Maximum.
			"
		::= { hihsmCHPUtilizationEntry	 5 }

--
-- HIHSM DKP utilization information
--

	hihsmDKPUtilizationTable		OBJECT-TYPE
		SYNTAX		SEQUENCE OF HihsmDKPUtilizationEntry
		ACCESS		not-accessible 
		STATUS		mandatory
		DESCRIPTION
			"HIHSM DKP utilization information."
		::= { hihsmCalculatedData 2 }

	hihsmDKPUtilizationEntry		OBJECT-TYPE
		SYNTAX		HihsmDKPUtilizationEntry
		ACCESS		not-accessible
		STATUS		mandatory
		DESCRIPTION
			"Entry of HIHSM DKP utilization information."
		INDEX {
			hihsmDKPUtilSerialNumber,
			hihsmDKPUtilClusterNumber,
			hihsmDKPUtilDKANumber,
			hihsmDKPUtilDKPNumber
		}
		::= { hihsmDKPUtilizationTable 1 }

	HihsmDKPUtilizationEntry ::= 
		SEQUENCE {
			hihsmDKPUtilSerialNumber	INTEGER,
			hihsmDKPUtilClusterNumber	INTEGER,
			hihsmDKPUtilDKANumber		INTEGER,
			hihsmDKPUtilDKPNumber		INTEGER,
			hihsmDKPUtilData		DisplayString
		}

	hihsmDKPUtilSerialNumber	OBJECT-TYPE
		SYNTAX		INTEGER
		ACCESS		read-only
		STATUS		mandatory
		DESCRIPTION
			"Serial number of the DKC."
		::= { hihsmDKPUtilizationEntry 1 }

	hihsmDKPUtilClusterNumber	OBJECT-TYPE
		SYNTAX		INTEGER
		ACCESS		read-only
		STATUS		mandatory
		DESCRIPTION
			"Cluster number."
		::= { hihsmDKPUtilizationEntry 2 }

	hihsmDKPUtilDKANumber	OBJECT-TYPE
		SYNTAX		INTEGER
		ACCESS		read-only
		STATUS		mandatory
		DESCRIPTION
			"Disk Adapter number."
		::= { hihsmDKPUtilizationEntry 3 }

	hihsmDKPUtilDKPNumber	OBJECT-TYPE
		SYNTAX		INTEGER
		ACCESS		read-only
		STATUS		mandatory
		DESCRIPTION
			"Disk Processor number."
		::= { hihsmDKPUtilizationEntry 4 }

	hihsmDKPUtilData	OBJECT-TYPE
		SYNTAX		DisplayString
		ACCESS		read-only
		STATUS		mandatory
		DESCRIPTION
			"Disk Processor utilization.

			Column	Value
			1	Average.
			2	Maximum.
			"
		::= { hihsmDKPUtilizationEntry 5 }

--
-- HIHSM DRR utilization information
--

	hihsmDRRUtilizationTable		OBJECT-TYPE
		SYNTAX		SEQUENCE OF HihsmDRRUtilizationEntry
		ACCESS		not-accessible 
		STATUS		mandatory
		DESCRIPTION
			"HIHSM DRR utilization information."
		::= { hihsmCalculatedData 3 }

	hihsmDRRUtilizationEntry		OBJECT-TYPE
		SYNTAX		HihsmDRRUtilizationEntry
		ACCESS		not-accessible
		STATUS		mandatory
		DESCRIPTION
			"Entry of HIHSM DRR utilization information."
		INDEX {
			hihsmDRRUtilSerialNumber,
			hihsmDRRUtilClusterNumber,
			hihsmDRRUtilDKANumber,
			hihsmDRRUtilDRRNumber
		}
		::= { hihsmDRRUtilizationTable 1 }

	HihsmDRRUtilizationEntry ::= 
		SEQUENCE {
			hihsmDRRUtilSerialNumber	INTEGER,
			hihsmDRRUtilClusterNumber	INTEGER,
			hihsmDRRUtilDKANumber		INTEGER,
			hihsmDRRUtilDRRNumber		INTEGER,
			hihsmDRRUtilData		DisplayString
		}

	hihsmDRRUtilSerialNumber	OBJECT-TYPE
		SYNTAX		INTEGER
		ACCESS		read-only
		STATUS		mandatory
		DESCRIPTION
			"Serial number of the DKC."
		::= { hihsmDRRUtilizationEntry	 1 }

	hihsmDRRUtilClusterNumber	OBJECT-TYPE
		SYNTAX		INTEGER
		ACCESS		read-only
		STATUS		mandatory
		DESCRIPTION
			"Cluster number."
		::= { hihsmDRRUtilizationEntry	 2 }

	hihsmDRRUtilDKANumber	OBJECT-TYPE
		SYNTAX		INTEGER
		ACCESS		read-only
		STATUS		mandatory
		DESCRIPTION
			"Disk Adapter number."
		::= { hihsmDRRUtilizationEntry	 3 }

	hihsmDRRUtilDRRNumber	OBJECT-TYPE
		SYNTAX		INTEGER
		ACCESS		read-only
		STATUS		mandatory
		DESCRIPTION
			"DRR number."
		::= { hihsmDRRUtilizationEntry	 4 }

	hihsmDRRUtilData	OBJECT-TYPE
		SYNTAX		DisplayString
		ACCESS		read-only
		STATUS		mandatory
		DESCRIPTION
			"DRR utilization.

			Column	Value
			1	Average.
			2	Maximum.
			"
		::= { hihsmDRRUtilizationEntry	 5 }

--
-- HIHSM PG utilization information
--

	hihsmPGUtilizationTable	OBJECT-TYPE
		SYNTAX		SEQUENCE OF HihsmPGUtilizationEntry
		ACCESS		not-accessible 
		STATUS		mandatory
		DESCRIPTION
			"HIHSM PG Utilization Information."
		::= { hihsmCalculatedData 4 }

	hihsmPGUtilizationEntry	OBJECT-TYPE
		SYNTAX		HihsmPGUtilizationEntry
		ACCESS		not-accessible
		STATUS		mandatory
		DESCRIPTION
			"Entry of HIHSM PG utilization information."
		INDEX {
			hihsmPGUtilSerialNumber,
			hihsmPGUtilFB4Number,
			hihsmPGUtilPGNumber
		}
		::= { hihsmPGUtilizationTable 1 }

	HihsmPGUtilizationEntry ::= 
		SEQUENCE {
			hihsmPGUtilSerialNumber	INTEGER,
			hihsmPGUtilFB4Number	INTEGER,
			hihsmPGUtilPGNumber	INTEGER,
			hihsmPGUtilData		DisplayString
		}

	hihsmPGUtilSerialNumber	OBJECT-TYPE
		SYNTAX		INTEGER
		ACCESS		read-only
		STATUS		mandatory
		DESCRIPTION
			"Serial number of the DKC."
		::= { hihsmPGUtilizationEntry 1 }

	hihsmPGUtilFB4Number	OBJECT-TYPE
		SYNTAX		INTEGER
		ACCESS		read-only
		STATUS		mandatory
		DESCRIPTION
			"FB4 number."
		::= { hihsmPGUtilizationEntry 2 }

	hihsmPGUtilPGNumber	OBJECT-TYPE
		SYNTAX		INTEGER
		ACCESS		read-only
		STATUS		mandatory
		DESCRIPTION
			"Parity Group number."
		::= { hihsmPGUtilizationEntry 3 }

	hihsmPGUtilData		OBJECT-TYPE
		SYNTAX		DisplayString
		ACCESS		read-only
		STATUS		mandatory
		DESCRIPTION
			"PG utilization.

			Column	Value
			1	Average.
			2	Maximum.
			3	Whether LDEV was moved in the term or not.
				0:	Does not moved.
				1:	Moved.
			"
		::= { hihsmPGUtilizationEntry 4 }

--
-- HIHSM LDEV utilization information
--

	hihsmLDEVUtilizationTable	OBJECT-TYPE
		SYNTAX		SEQUENCE OF HihsmLDEVUtilizationEntry
		ACCESS		not-accessible 
		STATUS		mandatory
		DESCRIPTION
			"HIHSM LDEV utilization information."
		::= { hihsmCalculatedData 5 }

	hihsmLDEVUtilizationEntry	OBJECT-TYPE
		SYNTAX		HihsmLDEVUtilizationEntry
		ACCESS		not-accessible
		STATUS		mandatory
		DESCRIPTION
			"Entry of HIHSM LDEV utilization information."
		INDEX {
			hihsmLDEVUtilSerialNumber,
			hihsmLDEVUtilFB4Number,
			hihsmLDEVUtilPGNumber,
			hihsmLDEVUtilCU,
			hihsmLDEVUtilLDEV
		}
		::= { hihsmLDEVUtilizationTable 1 }

	HihsmLDEVUtilizationEntry ::= 
		SEQUENCE {
			hihsmLDEVUtilSerialNumber	INTEGER,
			hihsmLDEVUtilFB4Number		INTEGER,
			hihsmLDEVUtilPGNumber		INTEGER,
			hihsmLDEVUtilCU			INTEGER,
			hihsmLDEVUtilLDEV		INTEGER,
			hihsmLDEVUtilData		DisplayString
		}

	hihsmLDEVUtilSerialNumber	OBJECT-TYPE
		SYNTAX		INTEGER
		ACCESS		read-only
		STATUS		mandatory
		DESCRIPTION
			"Serial number of the DKC."
		::= { hihsmLDEVUtilizationEntry 1 }

	hihsmLDEVUtilFB4Number	OBJECT-TYPE
		SYNTAX		INTEGER
		ACCESS		read-only
		STATUS		mandatory
		DESCRIPTION
			"FB4 number."
		::= { hihsmLDEVUtilizationEntry 2 }

	hihsmLDEVUtilPGNumber	OBJECT-TYPE
		SYNTAX		INTEGER
		ACCESS		read-only
		STATUS		mandatory
		DESCRIPTION
			"Parity Group number."
		::= { hihsmLDEVUtilizationEntry 3 }

	hihsmLDEVUtilCU		OBJECT-TYPE
		SYNTAX		INTEGER
		ACCESS		read-only
		STATUS		mandatory
		DESCRIPTION
			"CU number."
		::= { hihsmLDEVUtilizationEntry 4 }

	hihsmLDEVUtilLDEV	OBJECT-TYPE
		SYNTAX		INTEGER
		ACCESS		read-only
		STATUS		mandatory
		DESCRIPTION
			"LDEV number."
		::= { hihsmLDEVUtilizationEntry 5 }

	hihsmLDEVUtilData	OBJECT-TYPE
		SYNTAX		DisplayString
		ACCESS		read-only
		STATUS		mandatory
		DESCRIPTION
			"LDEV utilization.

			Column	Value
			1	Average.
			2	Maximum.
			3	Random read ratio.
			4	Sequential read ratio.
			5	Random write ratio.
			6	Random read ratio.
			7	Expectation average utilization after LDEV moves.
			8	Expectation maximum utilization after LDEV moves.
			9	Whether LDEV was moved in the term or not.
				0:	Does not moved.
				1:	Moved.
			"
		::= { hihsmLDEVUtilizationEntry 6 }

--
-- HIHSM CHA to CSW utilization information
--

	hihsmCHAtoCSWUtilizationTable	OBJECT-TYPE
		SYNTAX		SEQUENCE OF HihsmCHAtoCSWUtilizationEntry
		ACCESS		not-accessible 
		STATUS		mandatory
		DESCRIPTION
			"HIHSM CHA to CSW utilization information."
		::= { hihsmCalculatedData 6 }

	hihsmCHAtoCSWUtilizationEntry	OBJECT-TYPE
		SYNTAX		HihsmCHAtoCSWUtilizationEntry
		ACCESS		not-accessible
		STATUS		mandatory
		DESCRIPTION
			"Entry of HIHSM CHA to CSW utilization information."
		INDEX {
			hihsmCHACSWSerialNumber,
			hihsmCHACSWCHAClusterNumber,
			hihsmCHACSWCHANumber,
			hihsmCHACSWCSWClusterNumber,
			hihsmCHACSWCSWNumber
		}
		::= { hihsmCHAtoCSWUtilizationTable 1 }

	HihsmCHAtoCSWUtilizationEntry ::= 
		SEQUENCE {
			hihsmCHACSWSerialNumber		INTEGER,
			hihsmCHACSWCHAClusterNumber	INTEGER,
			hihsmCHACSWCHANumber		INTEGER,
			hihsmCHACSWCSWClusterNumber	INTEGER,
			hihsmCHACSWCSWNumber		INTEGER,
			hihsmCHACSWUtilData		DisplayString
		}

	hihsmCHACSWSerialNumber	OBJECT-TYPE
		SYNTAX		INTEGER
		ACCESS		read-only
		STATUS		mandatory
		DESCRIPTION
			"Serial number of the DKC."
		::= { hihsmCHAtoCSWUtilizationEntry 1 }

	hihsmCHACSWCHAClusterNumber	OBJECT-TYPE
		SYNTAX		INTEGER
		ACCESS		read-only
		STATUS		mandatory
		DESCRIPTION
			"Cluster number of CHA."
		::= { hihsmCHAtoCSWUtilizationEntry 2 }

	hihsmCHACSWCHANumber	OBJECT-TYPE
		SYNTAX		INTEGER
		ACCESS		read-only
		STATUS		mandatory
		DESCRIPTION
			"CHA number."
		::= { hihsmCHAtoCSWUtilizationEntry 3 }

	hihsmCHACSWCSWClusterNumber	OBJECT-TYPE
		SYNTAX		INTEGER
		ACCESS		read-only
		STATUS		mandatory
		DESCRIPTION
			"Cluster number of CSW."
		::= { hihsmCHAtoCSWUtilizationEntry 4 }

	hihsmCHACSWCSWNumber	OBJECT-TYPE
		SYNTAX		INTEGER
		ACCESS		read-only
		STATUS		mandatory
		DESCRIPTION
			"CSW number."
		::= { hihsmCHAtoCSWUtilizationEntry 5 }

	hihsmCHACSWUtilData	OBJECT-TYPE
		SYNTAX		DisplayString
		ACCESS		read-only
		STATUS		mandatory
		DESCRIPTION
			"CHA to CSW utilization.

			Column	Value
			1	Average.
			2	Maximum.
			"
		::= { hihsmCHAtoCSWUtilizationEntry 6 }

--
-- HIHSM DKA to CSW utilization information
--

	hihsmDKAtoCSWUtilizationTable	OBJECT-TYPE
		SYNTAX		SEQUENCE OF HihsmDKAtoCSWUtilizationEntry
		ACCESS		not-accessible 
		STATUS		mandatory
		DESCRIPTION
			"HIHSM DKA to CSW utilization information."
		::= { hihsmCalculatedData 7 }

	hihsmDKAtoCSWUtilizationEntry	OBJECT-TYPE
		SYNTAX		HihsmDKAtoCSWUtilizationEntry
		ACCESS		not-accessible
		STATUS		mandatory
		DESCRIPTION
			"Entry of HIHSM DKA to CSW utilization information."
		INDEX {
			hihsmDKACSWSerialNumber,
			hihsmDKACSWDKAClusterNumber,
			hihsmDKACSWDKANumber,
			hihsmDKACSWCSWClusterNumber,
			hihsmDKACSWCSWNumber
		}
		::= { hihsmDKAtoCSWUtilizationTable 1 }

	HihsmDKAtoCSWUtilizationEntry ::= 
		SEQUENCE {
			hihsmDKACSWSerialNumber		INTEGER,
			hihsmDKACSWDKAClusterNumber	INTEGER,
			hihsmDKACSWDKANumber		INTEGER,
			hihsmDKACSWCSWClusterNumber	INTEGER,
			hihsmDKACSWCSWNumber		INTEGER,
			hihsmDKACSWUtilData		DisplayString
		}

	hihsmDKACSWSerialNumber	OBJECT-TYPE
		SYNTAX		INTEGER
		ACCESS		read-only
		STATUS		mandatory
		DESCRIPTION
			"Serial number of the DKC."
		::= { hihsmDKAtoCSWUtilizationEntry 1 }

	hihsmDKACSWDKAClusterNumber	OBJECT-TYPE
		SYNTAX		INTEGER
		ACCESS		read-only
		STATUS		mandatory
		DESCRIPTION
			"Cluster number of DKA."
		::= { hihsmDKAtoCSWUtilizationEntry 2 }

	hihsmDKACSWDKANumber	OBJECT-TYPE
		SYNTAX		INTEGER
		ACCESS		read-only
		STATUS		mandatory
		DESCRIPTION
			"DKA number."
		::= { hihsmDKAtoCSWUtilizationEntry 3 }

	hihsmDKACSWCSWClusterNumber	OBJECT-TYPE
		SYNTAX		INTEGER
		ACCESS		read-only
		STATUS		mandatory
		DESCRIPTION
			"Cluster number of CSW."
		::= { hihsmDKAtoCSWUtilizationEntry 4 }

	hihsmDKACSWCSWNumber	OBJECT-TYPE
		SYNTAX		INTEGER
		ACCESS		read-only
		STATUS		mandatory
		DESCRIPTION
			"CSW number."
		::= { hihsmDKAtoCSWUtilizationEntry 5 }

	hihsmDKACSWUtilData	OBJECT-TYPE
		SYNTAX		DisplayString
		ACCESS		read-only
		STATUS		mandatory
		DESCRIPTION
			"DKA to CSW utilization.

			Column	Value
			1	Average.
			2	Maximum.
			"
		::= { hihsmDKAtoCSWUtilizationEntry 6 }

--
-- HIHSM CSW to Cache utilization information
--

	hihsmCSWtoCacheUtilizationTable	OBJECT-TYPE
		SYNTAX		SEQUENCE OF HihsmCSWtoCacheUtilizationEntry
		ACCESS		not-accessible 
		STATUS		mandatory
		DESCRIPTION
			"HIHSM CSW to Cache utilization information."
		::= { hihsmCalculatedData 8 }

	hihsmCSWtoCacheUtilizationEntry	OBJECT-TYPE
		SYNTAX		HihsmCSWtoCacheUtilizationEntry
		ACCESS		not-accessible
		STATUS		mandatory
		DESCRIPTION
			"Entry of HIHSM CSW to Cache utilization information."
		INDEX {
			hihsmCSWCacheSerialNumber,
			hihsmCSWCacheCSWClusterNumber,
			hihsmCSWCacheCSWNumber,
			hihsmCSWCacheCacheClusterNumber,
			hihsmCSWCacheCacheNumber
		}
		::= { hihsmCSWtoCacheUtilizationTable 1 }

	HihsmCSWtoCacheUtilizationEntry ::= 
		SEQUENCE {
			hihsmCSWCacheSerialNumber		INTEGER,
			hihsmCSWCacheCSWClusterNumber		INTEGER,
			hihsmCSWCacheCSWNumber			INTEGER,
			hihsmCSWCacheCacheClusterNumber		INTEGER,
			hihsmCSWCacheCacheNumber		INTEGER,
			hihsmCSWCacheUtilData			DisplayString
		}

	hihsmCSWCacheSerialNumber	OBJECT-TYPE
		SYNTAX		INTEGER
		ACCESS		read-only
		STATUS		mandatory
		DESCRIPTION
			"Serial number of the DKC."
		::= { hihsmCSWtoCacheUtilizationEntry 1 }

	hihsmCSWCacheCSWClusterNumber	OBJECT-TYPE
		SYNTAX		INTEGER
		ACCESS		read-only
		STATUS		mandatory
		DESCRIPTION
			"Cluster number of CSW."
		::= { hihsmCSWtoCacheUtilizationEntry 2 }

	hihsmCSWCacheCSWNumber	OBJECT-TYPE
		SYNTAX		INTEGER
		ACCESS		read-only
		STATUS		mandatory
		DESCRIPTION
			"CSW number."
		::= { hihsmCSWtoCacheUtilizationEntry 3 }

	hihsmCSWCacheCacheClusterNumber	OBJECT-TYPE
		SYNTAX		INTEGER
		ACCESS		read-only
		STATUS		mandatory
		DESCRIPTION
			"Cluster number of Cache."
		::= { hihsmCSWtoCacheUtilizationEntry 4 }

	hihsmCSWCacheCacheNumber	OBJECT-TYPE
		SYNTAX		INTEGER
		ACCESS		read-only
		STATUS		mandatory
		DESCRIPTION
			"Cache number."
		::= { hihsmCSWtoCacheUtilizationEntry 5 }

	hihsmCSWCacheUtilData	OBJECT-TYPE
		SYNTAX		DisplayString
		ACCESS		read-only
		STATUS		mandatory
		DESCRIPTION
			"CSW to Cache utilization.

			Column	Value
			1	Average.
			2	Maximum.
			"
		::= { hihsmCSWtoCacheUtilizationEntry 6 }

--
-- HIHSM CHA to SM utilization information
--

	hihsmCHAtoSMUtilizationTable	OBJECT-TYPE
		SYNTAX		SEQUENCE OF HihsmCHAtoSMUtilizationEntry
		ACCESS		not-accessible 
		STATUS		mandatory
		DESCRIPTION
			"HIHSM CHA to SM utilization information."
		::= { hihsmCalculatedData 9 }

	hihsmCHAtoSMUtilizationEntry		OBJECT-TYPE
		SYNTAX		HihsmCHAtoSMUtilizationEntry
		ACCESS		not-accessible
		STATUS		mandatory
		DESCRIPTION
			"Entry of HIHSM CHA to SM utilization information."
		INDEX {
			hihsmCHASMSerialNumber,
			hihsmCHASMCHAClusterNumber,
			hihsmCHASMCHANumber,
			hihsmCHASMSMClusterNumber
		}
		::= { hihsmCHAtoSMUtilizationTable 1 }

	HihsmCHAtoSMUtilizationEntry ::= 
		SEQUENCE {
			hihsmCHASMSerialNumber		INTEGER,
			hihsmCHASMCHAClusterNumber	INTEGER,
			hihsmCHASMCHANumber		INTEGER,
			hihsmCHASMSMClusterNumber		INTEGER,
			hihsmCHASMUtilData		DisplayString
		}

	hihsmCHASMSerialNumber	OBJECT-TYPE
		SYNTAX		INTEGER
		ACCESS		read-only
		STATUS		mandatory
		DESCRIPTION
			"Serial number of the DKC."
		::= { hihsmCHAtoSMUtilizationEntry 1 }

	hihsmCHASMCHAClusterNumber	OBJECT-TYPE
		SYNTAX		INTEGER
		ACCESS		read-only
		STATUS		mandatory
		DESCRIPTION
			"Cluster number of CHA."
		::= { hihsmCHAtoSMUtilizationEntry 2 }

	hihsmCHASMCHANumber	OBJECT-TYPE
		SYNTAX		INTEGER
		ACCESS		read-only
		STATUS		mandatory
		DESCRIPTION
			"CHA number."
		::= { hihsmCHAtoSMUtilizationEntry 3 }

	hihsmCHASMSMClusterNumber	OBJECT-TYPE
		SYNTAX		INTEGER
		ACCESS		read-only
		STATUS		mandatory
		DESCRIPTION
			"Cluster number of SM."
		::= { hihsmCHAtoSMUtilizationEntry 4 }

	hihsmCHASMUtilData	OBJECT-TYPE
		SYNTAX		DisplayString
		ACCESS		read-only
		STATUS		mandatory
		DESCRIPTION
			"CHA to SM utilization.

			Column	Value
			1	Average.
			2	Maximum.
			"
		::= { hihsmCHAtoSMUtilizationEntry 5 }

--
-- HIHSM DKA to SM utilization information
--

	hihsmDKAtoSMUtilizationTable	OBJECT-TYPE
		SYNTAX		SEQUENCE OF HihsmDKAtoSMUtilizationEntry
		ACCESS		not-accessible 
		STATUS		mandatory
		DESCRIPTION
			"HIHSM DKA to SM utilization information."
		::= { hihsmCalculatedData 10 }

	hihsmDKAtoSMUtilizationEntry		OBJECT-TYPE
		SYNTAX		HihsmDKAtoSMUtilizationEntry
		ACCESS		not-accessible
		STATUS		mandatory
		DESCRIPTION
			"Entry of HIHSM DKA to SM utilization information."
		INDEX {
			hihsmDKASMSerialNumber,
			hihsmDKASMDKAClusterNumber,
			hihsmDKASMDKANumber,
			hihsmDKASMSMClusterNumber
		}
		::= { hihsmDKAtoSMUtilizationTable 1 }

	HihsmDKAtoSMUtilizationEntry ::= 
		SEQUENCE {
			hihsmDKASMSerialNumber		INTEGER,
			hihsmDKASMDKAClusterNumber	INTEGER,
			hihsmDKASMDKANumber			INTEGER,
			hihsmDKASMSMClusterNumber	INTEGER,
			hihsmDKASMUtilData			DisplayString
		}

	hihsmDKASMSerialNumber	OBJECT-TYPE
		SYNTAX		INTEGER
		ACCESS		read-only
		STATUS		mandatory
		DESCRIPTION
			"Serial number of the DKC."
		::= { hihsmDKAtoSMUtilizationEntry 1 }

	hihsmDKASMDKAClusterNumber	OBJECT-TYPE
		SYNTAX		INTEGER
		ACCESS		read-only
		STATUS		mandatory
		DESCRIPTION
			"Cluster number of DKA."
		::= { hihsmDKAtoSMUtilizationEntry 2 }

	hihsmDKASMDKANumber	OBJECT-TYPE
		SYNTAX		INTEGER
		ACCESS		read-only
		STATUS		mandatory
		DESCRIPTION
			"DKA number."
		::= { hihsmDKAtoSMUtilizationEntry 3 }

	hihsmDKASMSMClusterNumber	OBJECT-TYPE
		SYNTAX		INTEGER
		ACCESS		read-only
		STATUS		mandatory
		DESCRIPTION
			"Cluster number of SM."
		::= { hihsmDKAtoSMUtilizationEntry 4 }

	hihsmDKASMUtilData	OBJECT-TYPE
		SYNTAX		DisplayString
		ACCESS		read-only
		STATUS		mandatory
		DESCRIPTION
			"DKA to SM utilization.

			Column	Value
			1	Average.
			2	Maximum.
			"
		::= { hihsmDKAtoSMUtilizationEntry 5 }

--
-- HIHSM DKC utilization information
--

	hihsmDKCUtilizationTable		OBJECT-TYPE
		SYNTAX		SEQUENCE OF HihsmDKCUtilizationEntry
		ACCESS		not-accessible 
		STATUS		mandatory
		DESCRIPTION
			"HIHSM DKC utilization information."
		::= { hihsmCalculatedData 11 }

	hihsmDKCUtilizationEntry		OBJECT-TYPE
		SYNTAX		HihsmDKCUtilizationEntry
		ACCESS		not-accessible
		STATUS		mandatory
		DESCRIPTION
			"Entry of HIHSM DKC utilization information."
		INDEX {
			hihsmCHASMSerialNumber
		}
		::= { hihsmDKCUtilizationTable 1 }

	HihsmDKCUtilizationEntry ::= 
		SEQUENCE {
			hihsmDKCUtilSerialNumber	INTEGER,
			hihsmDKCUtilWritePending	DisplayString
		}

	hihsmDKCUtilSerialNumber	OBJECT-TYPE
		SYNTAX		INTEGER
		ACCESS		read-only
		STATUS		mandatory
		DESCRIPTION
			"Serial number of the DKC."
		::= { hihsmDKCUtilizationEntry 1 }

	hihsmDKCUtilWritePending	OBJECT-TYPE
		SYNTAX		DisplayString
		ACCESS		read-only
		STATUS		mandatory
		DESCRIPTION
			"Write Pending ratio.

			Column	Value
			1	Average.
			2	Maximum.
			"
		::= { hihsmDKCUtilizationEntry 2 }

--
-- HIHSM Automatic Migration information
--

	hihsmAutomaticMigration	OBJECT IDENTIFIER ::= { raidExMibHIHSM 4 }

--
-- HIHSM Automatic Migration parameter
--

	hihsmAutomaticMigrationParameterTable	OBJECT-TYPE
	SYNTAX		SEQUENCE OF HihsmAutomaticMigrationParameterEntry
	ACCESS		not-accessible 
	STATUS		mandatory
	DESCRIPTION
			"HIHSM Automatic Migration parameter information."
		::= { hihsmAutomaticMigration 1 }

	hihsmAutomaticMigrationParameterEntry	OBJECT-TYPE
		SYNTAX		HihsmAutomaticMigrationParameterEntry
		ACCESS		not-accessible
		STATUS		mandatory
		DESCRIPTION
		"Entry of hihsm Automatic Migration parameter information."
		INDEX {
			hihsmAutoParamSerialNumber
		}
		::= { hihsmAutomaticMigrationParameterTable 1 }

	HihsmAutomaticMigrationParameterEntry ::= 
		SEQUENCE {
			hihsmAutoParamSerialNumber	INTEGER,
			hihsmAutoParamFunctionSwitch	INTEGER,
			hihsmAutoParamPlanningDay	INTEGER,
			hihsmAutoParamIntervalDay	INTEGER,
			hihsmAutoParamDayOfWeek		INTEGER,
			hihsmAutoParamUseFromTime	DisplayString,
			hihsmAutoParamUseToTime		DisplayString,
			hihsmAutoParamJudgeMethod	INTEGER,
			hihsmAutoParamHightestPoints	INTEGER,
			hihsmAutoParamExecutionTime	DisplayString,
			hihsmAutoParamMaxDuration	INTEGER,
			hihsmAutoParamMaxUtilization	INTEGER,
			hihsmAutoParamMaxVolumes	INTEGER,
			hihsmAutoParamControlStatus	INTEGER,
			hihsmAutoParamDayOfMonth	INTEGER
		}

	hihsmAutoParamSerialNumber	OBJECT-TYPE
		SYNTAX		INTEGER
		ACCESS		read-only
		STATUS		mandatory
		DESCRIPTION
			"Serial number of the DKC."
		::= { hihsmAutomaticMigrationParameterEntry 1 }

	hihsmAutoParamFunctionSwitch	OBJECT-TYPE
		SYNTAX		INTEGER
		ACCESS		read-write
		STATUS		mandatory
		DESCRIPTION
			"Function switch.

			Value	Mean
			0	Off
			1	On
			"
		::= { hihsmAutomaticMigrationParameterEntry 2 }

	hihsmAutoParamPlanningDay	OBJECT-TYPE
		SYNTAX		INTEGER
		ACCESS		read-write
		STATUS		mandatory
		DESCRIPTION
			"Planning day type.

			Value	Mean
			0	None
			1	Every day
			2	Every x day
			3	Select in a week
			4	Once a month
			"
		::= { hihsmAutomaticMigrationParameterEntry 3 }

	hihsmAutoParamIntervalDay	OBJECT-TYPE
		SYNTAX		INTEGER
		ACCESS		read-write
		STATUS		mandatory
		DESCRIPTION
			"Interval day."
		::= { hihsmAutomaticMigrationParameterEntry 4 }

	hihsmAutoParamDayOfWeek	OBJECT-TYPE
		SYNTAX		INTEGER
		ACCESS		read-write
		STATUS		mandatory
		DESCRIPTION
			"Planning day of week.

			Value	Mean
			0	Sunday
			1	Monday
			2	Tuesday
			3	Wednesday
			4	Thursday
			5	Friday
			6	Saturday
			"
		::= { hihsmAutomaticMigrationParameterEntry 5 }

	hihsmAutoParamUseFromTime	OBJECT-TYPE
		SYNTAX		DisplayString
		ACCESS		read-write
		STATUS		mandatory
		DESCRIPTION
			"Top time of monitoring data."
		::= { hihsmAutomaticMigrationParameterEntry 6 }

	hihsmAutoParamUseToTime	OBJECT-TYPE
		SYNTAX		DisplayString
		ACCESS		read-write
		STATUS		mandatory
		DESCRIPTION
			"End time of monitoring data."
		::= { hihsmAutomaticMigrationParameterEntry 7 }

	hihsmAutoParamJudgeMethod	OBJECT-TYPE
		SYNTAX		INTEGER
		ACCESS		read-write
		STATUS		mandatory
		DESCRIPTION
			"Judge method of monitoring data.

			Value	Mean
			0	Average of all data.
			1	Average of top x data.
			"
		::= { hihsmAutomaticMigrationParameterEntry 8 }
    
	hihsmAutoParamHightestPoints	OBJECT-TYPE
		SYNTAX		INTEGER
		ACCESS		read-write
		STATUS		mandatory
		DESCRIPTION
			"Highest points of judge method."
		::= { hihsmAutomaticMigrationParameterEntry 9 }

	hihsmAutoParamExecutionTime	OBJECT-TYPE
		SYNTAX		DisplayString
		ACCESS		read-write
		STATUS		mandatory
		DESCRIPTION
			"Execution time."
		::= { hihsmAutomaticMigrationParameterEntry 10 }

	hihsmAutoParamMaxDuration	OBJECT-TYPE
		SYNTAX		INTEGER
		ACCESS		read-write
		STATUS		mandatory
		DESCRIPTION
			"Maximum limitation duration."
		::= { hihsmAutomaticMigrationParameterEntry 11 }

	hihsmAutoParamMaxUtilization	OBJECT-TYPE
		SYNTAX		INTEGER
		ACCESS		read-write
		STATUS		mandatory
		DESCRIPTION
			"Maximum limitation utilization."
		::= { hihsmAutomaticMigrationParameterEntry 12 }

	hihsmAutoParamMaxVolumes	OBJECT-TYPE
		SYNTAX		INTEGER
		ACCESS		read-write
		STATUS		mandatory
		DESCRIPTION
			"Number of Maximum migration volumes."
		::= { hihsmAutomaticMigrationParameterEntry 13 }

	hihsmAutoParamControlStatus	OBJECT-TYPE
		SYNTAX		INTEGER
		ACCESS		read-write
		STATUS		mandatory
		DESCRIPTION
			"Control Status.

			Value	Mean
			1	Return value.
			2	Parameter setting request.
			3	Default setting request.
			"
		::= { hihsmAutomaticMigrationParameterEntry 14 }

	hihsmAutoParamDayOfMonth	OBJECT-TYPE
		SYNTAX		INTEGER
		ACCESS		read-write
		STATUS		mandatory
		DESCRIPTION
			"Planning day of month."
		::= { hihsmAutomaticMigrationParameterEntry 15 }

--
-- HIHSM Automatic Migration Class
--

hihsmAutomaticMigrationClass OBJECT IDENTIFIER ::= { hihsmAutomaticMigration 2 }

--
-- HIHSM Automatic Migration Class list
--

	hihsmAutomaticMigrationClassListTable	OBJECT-TYPE
	SYNTAX	SEQUENCE OF HihsmAutomaticMigrationClassListEntry
	ACCESS		not-accessible 
	STATUS		mandatory
	DESCRIPTION
	"HIHSM Automatic Migration Class information."
	::= { hihsmAutomaticMigrationClass 1 }

	hihsmAutomaticMigrationClassListEntry	OBJECT-TYPE
		SYNTAX		HihsmAutomaticMigrationClassListEntry
		ACCESS		not-accessible
		STATUS		mandatory
		DESCRIPTION
			"Entry of HIHSM Automatic Migration Class information."
		INDEX {
			hihsmClassListSerialNumber,
			hihsmClassListClassNumber
		}
		::= { hihsmAutomaticMigrationClassListTable 1 }

	HihsmAutomaticMigrationClassListEntry ::= 
		SEQUENCE {
			hihsmClassListSerialNumber	INTEGER,
			hihsmClassListClassNumber	INTEGER,
			hihsmClassListDisplayName	DisplayString,
			hihsmClassListMaxUtilization	INTEGER,
			hihsmClassListControlStatus	INTEGER
		}

	hihsmClassListSerialNumber	OBJECT-TYPE
		SYNTAX		INTEGER
		ACCESS		read-only
		STATUS		mandatory
		DESCRIPTION
			"Serial number of the DKC."
		::= { hihsmAutomaticMigrationClassListEntry 1 }

	hihsmClassListClassNumber	OBJECT-TYPE
		SYNTAX		INTEGER
		ACCESS		read-only
		STATUS		mandatory
		DESCRIPTION
			"Class number."
		::= { hihsmAutomaticMigrationClassListEntry 2 }

	hihsmClassListDisplayName	OBJECT-TYPE
		SYNTAX		DisplayString
		ACCESS		read-only
		STATUS		mandatory
		DESCRIPTION
			"Display name of the class."
		::= { hihsmAutomaticMigrationClassListEntry 3 }

	hihsmClassListMaxUtilization	OBJECT-TYPE
		SYNTAX		INTEGER
		ACCESS		read-write
		STATUS		mandatory
		DESCRIPTION
			"Maximum utilization of the class."
		::= { hihsmAutomaticMigrationClassListEntry 4 }

	hihsmClassListControlStatus	OBJECT-TYPE
		SYNTAX		INTEGER
		ACCESS		read-write
		STATUS		mandatory
		DESCRIPTION
			"Control flag.

			Value	Mean
			1	Return value.
			2	Maximum Utilization setting request.
			"
		::= { hihsmAutomaticMigrationClassListEntry 5 }

--
-- HIHSM PG list in Automatic Migration Class
--

	hihsmAutomaticMigrationClassPGTable	OBJECT-TYPE
		SYNTAX		SEQUENCE OF HihsmAutomaticMigrationClassPGEntry
		ACCESS		not-accessible 
		STATUS		mandatory
		DESCRIPTION
			"HIHSM PG list in Automatic Migration Class."
		::= { hihsmAutomaticMigrationClass 2 }

	hihsmAutomaticMigrationClassPGEntry	OBJECT-TYPE
		SYNTAX		HihsmAutomaticMigrationClassPGEntry
		ACCESS		not-accessible
		STATUS		mandatory
		DESCRIPTION
			"Entry of HIHSM PG list in Automatic Migration Class."
		INDEX {
			hihsmClassPGSerialNumber,
			hihsmClassPGClassNumber,
			hihsmClassPGControlIndex
		}
		::= { hihsmAutomaticMigrationClassPGTable 1 }

	HihsmAutomaticMigrationClassPGEntry ::= 
		SEQUENCE {
			hihsmClassPGSerialNumber		INTEGER,
			hihsmClassPGClassNumber		INTEGER,
			hihsmClassPGControlIndex		INTEGER,
			hihsmClassPGFB4Number		INTEGER,
			hihsmClassPGPGNumber		INTEGER
		}

	hihsmClassPGSerialNumber	OBJECT-TYPE
		SYNTAX		INTEGER
		ACCESS		read-only
		STATUS		mandatory
		DESCRIPTION
			"Serial number of the DKC."
		::= { hihsmAutomaticMigrationClassPGEntry 1 }

	hihsmClassPGClassNumber	OBJECT-TYPE
		SYNTAX		INTEGER
		ACCESS		read-only
		STATUS		mandatory
		DESCRIPTION
			"Class number."
		::= { hihsmAutomaticMigrationClassPGEntry 2 }

	hihsmClassPGControlIndex	OBJECT-TYPE
		SYNTAX		INTEGER
		ACCESS		read-only
		STATUS		mandatory
		DESCRIPTION
			"Control index."
		::= { hihsmAutomaticMigrationClassPGEntry 3 }

	hihsmClassPGFB4Number	OBJECT-TYPE
		SYNTAX		INTEGER
		ACCESS		read-only
		STATUS		mandatory
		DESCRIPTION
			"FB4 number."
		::= { hihsmAutomaticMigrationClassPGEntry 4 }

	hihsmClassPGPGNumber	OBJECT-TYPE
		SYNTAX		INTEGER
		ACCESS		read-only
		STATUS		mandatory
		DESCRIPTION
			"Parity Group number."
		::= { hihsmAutomaticMigrationClassPGEntry 5 }

--
-- HIHSM Automatic Migration Plan
--

hihsmAutomaticMigrationPlan OBJECT IDENTIFIER ::= { hihsmAutomaticMigration 3 }

--
-- HIHSM Automatic Migration Plan status
--

   hihsmAutomaticMigrationPlanStatusTable	OBJECT-TYPE
	SYNTAX		SEQUENCE OF HihsmAutomaticMigrationPlanStatusEntry
	ACCESS		not-accessible 
	STATUS		mandatory
	DESCRIPTION
			"HIHSM Automatic Migration Plan status information."
		::= { hihsmAutomaticMigrationPlan 1 }

	hihsmAutomaticMigrationPlanStatusEntry	OBJECT-TYPE
		SYNTAX		HihsmAutomaticMigrationPlanStatusEntry
		ACCESS		not-accessible
		STATUS		mandatory
		DESCRIPTION
			"Entry of HIHSM Automatic Migration Plan status information."
		INDEX {
			hihsmPlanStatusSerialNumber
		}
		::= { hihsmAutomaticMigrationPlanStatusTable 1 }

	HihsmAutomaticMigrationPlanStatusEntry ::= 
		SEQUENCE {
			hihsmPlanStatusSerialNumber	INTEGER,
			hihsmPlanStatusData		INTEGER,
			hihsmPlanStatusCheckDate	DisplayString,
			hihsmPlanStatusCheckTime	DisplayString,
			hihsmPlanStatusMigrationDate	DisplayString,
			hihsmPlanStatusMigrationTime	DisplayString,
			hihsmPlanStatusControlStatus	INTEGER
		}

	hihsmPlanStatusSerialNumber	OBJECT-TYPE
		SYNTAX		INTEGER
		ACCESS		read-only
		STATUS		mandatory
		DESCRIPTION
			"Serial number of the DKC."
		::= { hihsmAutomaticMigrationPlanStatusEntry 1 }

	hihsmPlanStatusData	OBJECT-TYPE
		SYNTAX		INTEGER
		ACCESS		read-only
		STATUS		mandatory
		DESCRIPTION
			"Automatic Migration Plan status.

			Value	Mean
			1	Not planned yet.
			2	Not performed yet.
			3	Under migration .
			4	Last migration has canceled.
			5	Failed to make a plan.
			"
		::= { hihsmAutomaticMigrationPlanStatusEntry 2 }

	hihsmPlanStatusCheckDate	OBJECT-TYPE
		SYNTAX		DisplayString
		ACCESS		read-only
		STATUS		mandatory
		DESCRIPTION
			"Next checking date."
		::= { hihsmAutomaticMigrationPlanStatusEntry 3 }

	hihsmPlanStatusCheckTime	OBJECT-TYPE
		SYNTAX		DisplayString
		ACCESS		read-only
		STATUS		mandatory
		DESCRIPTION
			"Next checking time."
		::= { hihsmAutomaticMigrationPlanStatusEntry 4 }

	hihsmPlanStatusMigrationDate	OBJECT-TYPE
		SYNTAX		DisplayString
		ACCESS		read-only
		STATUS		mandatory
		DESCRIPTION
			"Next migration date."
		::= { hihsmAutomaticMigrationPlanStatusEntry 5 }

	hihsmPlanStatusMigrationTime	OBJECT-TYPE
		SYNTAX		DisplayString
		ACCESS		read-only
		STATUS		mandatory
		DESCRIPTION
			"Next migration time."
		::= { hihsmAutomaticMigrationPlanStatusEntry 6 }

	hihsmPlanStatusControlStatus	OBJECT-TYPE
		SYNTAX		INTEGER
		ACCESS		read-write
		STATUS		mandatory
		DESCRIPTION
			"Control flag.

			Value	Mean
			1	Return value.
			2	Canceling request.
			3	Plan making request.
			"
		::= { hihsmAutomaticMigrationPlanStatusEntry 7 }

--
-- HIHSM Automatic Migration LDEV information
--

	hihsmAutomaticMigrationPlanLDEVTable 	OBJECT-TYPE
		SYNTAX		SEQUENCE OF HihsmAutomaticMigrationPlanLDEVEntry
		ACCESS		not-accessible 
		STATUS		mandatory
		DESCRIPTION
			"hihsm Automatic Migration LDEV information."
		::= { hihsmAutomaticMigrationPlan 2 }

	hihsmAutomaticMigrationPlanLDEVEntry	OBJECT-TYPE
		SYNTAX		HihsmAutomaticMigrationPlanLDEVEntry
		ACCESS		not-accessible
		STATUS		mandatory
		DESCRIPTION
			"Entry of HIHSM Automatic Migration LDEV information."
		INDEX {
			hihsmPlanLDEVSerialNumber,
			hihsmPlanLDEVControlIndex
		}
		::= { hihsmAutomaticMigrationPlanLDEVTable 1 }

	HihsmAutomaticMigrationPlanLDEVEntry ::= 
		SEQUENCE {
			hihsmPlanLDEVSerialNumber	INTEGER,
			hihsmPlanLDEVControlIndex	INTEGER,
			hihsmPlanLDEVSrcFB4Number	INTEGER,
			hihsmPlanLDEVSrcPGNumber	INTEGER,
			hihsmPlanLDEVSrcCU			INTEGER,
			hihsmPlanLDEVSrcLDEV		INTEGER,
			hihsmPlanLDEVDstFB4Number	INTEGER,
			hihsmPlanLDEVDstPGNumber	INTEGER,
			hihsmPlanLDEVDstCU			INTEGER,
			hihsmPlanLDEVDstLDEV		INTEGER
		}

	hihsmPlanLDEVSerialNumber	OBJECT-TYPE
		SYNTAX		INTEGER
		ACCESS		read-only
		STATUS		mandatory
		DESCRIPTION
			"Serial number of the DKC."
		::= { hihsmAutomaticMigrationPlanLDEVEntry 1 }

	hihsmPlanLDEVControlIndex	OBJECT-TYPE
		SYNTAX		INTEGER
		ACCESS		read-only
		STATUS		mandatory
		DESCRIPTION
			"Control index."
		::= { hihsmAutomaticMigrationPlanLDEVEntry 2 }

	hihsmPlanLDEVSrcFB4Number	OBJECT-TYPE
		SYNTAX		INTEGER
		ACCESS		read-only
		STATUS		mandatory
		DESCRIPTION
			"FB4 number."
		::= { hihsmAutomaticMigrationPlanLDEVEntry 3 }

	hihsmPlanLDEVSrcPGNumber	OBJECT-TYPE
		SYNTAX		INTEGER
		ACCESS		read-only
		STATUS		mandatory
		DESCRIPTION
			"source PG number."
		::= { hihsmAutomaticMigrationPlanLDEVEntry 4 }

	hihsmPlanLDEVSrcCU	OBJECT-TYPE
		SYNTAX		INTEGER
		ACCESS		read-only
		STATUS		mandatory
		DESCRIPTION
			"source CU number."
		::= { hihsmAutomaticMigrationPlanLDEVEntry 5 }

	hihsmPlanLDEVSrcLDEV	OBJECT-TYPE
		SYNTAX		INTEGER
		ACCESS		read-only
		STATUS		mandatory
		DESCRIPTION
			"source LDEV number."
		::= { hihsmAutomaticMigrationPlanLDEVEntry 6 }

	hihsmPlanLDEVDstFB4Number	OBJECT-TYPE
		SYNTAX		INTEGER
		ACCESS		read-only
		STATUS		mandatory
		DESCRIPTION
			"Destination FB4 number."
		::= { hihsmAutomaticMigrationPlanLDEVEntry 7 }

	hihsmPlanLDEVDstPGNumber	OBJECT-TYPE
		SYNTAX		INTEGER
		ACCESS		read-only
		STATUS		mandatory
		DESCRIPTION
			"Destination PG number."
		::= { hihsmAutomaticMigrationPlanLDEVEntry 8 }

	hihsmPlanLDEVDstCU	OBJECT-TYPE
		SYNTAX		INTEGER
		ACCESS		read-only
		STATUS		mandatory
		DESCRIPTION
			"Destination CU number."
		::= { hihsmAutomaticMigrationPlanLDEVEntry 9 }

	hihsmPlanLDEVDstLDEV	OBJECT-TYPE
		SYNTAX		INTEGER
		ACCESS		read-only
		STATUS		mandatory
		DESCRIPTION
			"Destination LDEV number."
		::= { hihsmAutomaticMigrationPlanLDEVEntry 10 }

--
-- HIHSM Automatic Migration History
--

hihsmAutomaticMigrationHistory OBJECT IDENTIFIER ::= { hihsmAutomaticMigration 4 }

--
-- HIHSM Automatic Migration History control
--

	hihsmAutomaticMigrationHistoryCtrlTable	OBJECT-TYPE
	SYNTAX		SEQUENCE OF HihsmAutomaticMigrationHistoryCtrlEntry
	ACCESS		not-accessible 
	STATUS		mandatory
	DESCRIPTION
			"HIHSM Automatic Migration History control."
		::= { hihsmAutomaticMigrationHistory 1 }

	hihsmAutomaticMigrationHistoryCtrlEntry	OBJECT-TYPE
		SYNTAX		HihsmAutomaticMigrationHistoryCtrlEntry
		ACCESS		not-accessible
		STATUS		mandatory
		DESCRIPTION
			"Entry of HIHSM Automatic Migration History control."
		INDEX {
			hihsmAutoHstCtrlSerialNumber

		}
		::= { hihsmAutomaticMigrationHistoryCtrlTable 1 }

	HihsmAutomaticMigrationHistoryCtrlEntry ::= 
		SEQUENCE {
			hihsmAutoHstCtrlSerialNumber	INTEGER,
			hihsmAutoHstCtrlControlStatus	INTEGER
		}

	hihsmAutoHstCtrlSerialNumber	OBJECT-TYPE
		SYNTAX		INTEGER
		ACCESS		read-only
		STATUS		mandatory
		DESCRIPTION
			"Serial number of the DKC."
		::= { hihsmAutomaticMigrationHistoryCtrlEntry 1 }

	hihsmAutoHstCtrlControlStatus	OBJECT-TYPE
		SYNTAX		INTEGER
		ACCESS		read-write
		STATUS		mandatory
		DESCRIPTION
			"Control flag.

			Value	Mean
			1	Return value.
			2	clearing request.
			"
		::= { hihsmAutomaticMigrationHistoryCtrlEntry 2 }

--
-- HIHSM Automatic Migration History List
--

	hihsmAutomaticMigrationHistoryListTable	OBJECT-TYPE
	SYNTAX		SEQUENCE OF HihsmAutomaticMigrationHistoryListEntry
	ACCESS		not-accessible 
	STATUS		mandatory
	DESCRIPTION
			"HIHSM Automatic Migration History List."
		::= { hihsmAutomaticMigrationHistory 2 }

	hihsmAutomaticMigrationHistoryListEntry	OBJECT-TYPE
		SYNTAX		HihsmAutomaticMigrationHistoryListEntry
		ACCESS		not-accessible
		STATUS		mandatory
		DESCRIPTION
			"Entry of HIHSM Automatic Migration History List."
		INDEX {
			hihsmAutoHstListSerialNumber,
			hihsmAutoHstListControlIndex

		}
		::= { hihsmAutomaticMigrationHistoryListTable 1 }

	HihsmAutomaticMigrationHistoryListEntry ::= 
		SEQUENCE {
			hihsmAutoHstListSerialNumber	INTEGER,
			hihsmAutoHstListControlIndex	INTEGER,
			hihsmAutoHstListMessage		DisplayString

		}

	hihsmAutoHstListSerialNumber	OBJECT-TYPE
		SYNTAX		INTEGER
		ACCESS		read-only
		STATUS		mandatory
		DESCRIPTION
			"Serial number of the DKC."
		::= { hihsmAutomaticMigrationHistoryListEntry 1 }

	hihsmAutoHstListControlIndex	OBJECT-TYPE
		SYNTAX		INTEGER
		ACCESS		read-only
		STATUS		mandatory
		DESCRIPTION
			"Control index."
		::= { hihsmAutomaticMigrationHistoryListEntry 2 }

	hihsmAutoHstListMessage	OBJECT-TYPE
		SYNTAX		DisplayString
		ACCESS		read-only
		STATUS		mandatory
		DESCRIPTION
			"Control Status.

			Value	Mean
			1	Return value.
			2	Clearing request.
			"
		::= { hihsmAutomaticMigrationHistoryListEntry 3 }

--
-- HIHSM Volume Migration History
--

 hihsmVolumeMigrationHistory OBJECT IDENTIFIER ::= { hihsmAutomaticMigration 5 }

--
-- HIHSM Volume Migration History Control
--

	hihsmVolumeMigrationHistoryCtrlTable		OBJECT-TYPE
		SYNTAX		SEQUENCE OF HihsmVolumeMigrationHistoryCtrlEntry
		ACCESS		not-accessible 
		STATUS		mandatory
		DESCRIPTION
			"HIHSM Volume Migration History Control."
		::= { hihsmVolumeMigrationHistory 1 }

	hihsmVolumeMigrationHistoryCtrlEntry	OBJECT-TYPE
		SYNTAX		HihsmVolumeMigrationHistoryCtrlEntry
		ACCESS		not-accessible
		STATUS		mandatory
		DESCRIPTION
			"Entry of HIHSM Volume Migration History Control."
		INDEX {
			hihsmVolHstCtrlSerialNumber
		}
		::= { hihsmVolumeMigrationHistoryCtrlTable 1 }

	HihsmVolumeMigrationHistoryCtrlEntry ::= 
		SEQUENCE {
			hihsmVolHstCtrlSerialNumber	INTEGER,
			hihsmVolHstCtrlControlStatus	INTEGER
		}

	hihsmVolHstCtrlSerialNumber	OBJECT-TYPE
		SYNTAX		INTEGER
		ACCESS		read-only
		STATUS		mandatory
		DESCRIPTION
			"Serial number of the DKC."
		::= { hihsmVolumeMigrationHistoryCtrlEntry 1 }

	hihsmVolHstCtrlControlStatus	OBJECT-TYPE
		SYNTAX		INTEGER
		ACCESS		read-write
		STATUS		mandatory
		DESCRIPTION
			"Control flag.

			Value	Mean
			0	Return value.
			1	Clearing request.
			"
		::= { hihsmVolumeMigrationHistoryCtrlEntry 2 }

--
-- HIHSM Volume Migration History List
--

	hihsmVolumeMigrationHistoryListTable		OBJECT-TYPE
		SYNTAX		SEQUENCE OF HihsmVolumeMigrationHistoryListEntry
		ACCESS		not-accessible 
		STATUS		mandatory
		DESCRIPTION
			"HIHSM Volume Migration History List."
		::= { hihsmVolumeMigrationHistory 2 }

	hihsmVolumeMigrationHistoryListEntry	OBJECT-TYPE
		SYNTAX		HihsmVolumeMigrationHistoryListEntry
		ACCESS		not-accessible
		STATUS		mandatory
		DESCRIPTION
			"Entry of HIHSM Volume Migration History List."
		INDEX {
			hihsmVolHstListSerialNumber,
			hihsmVolHstListControlIndex
		}
		::= { hihsmVolumeMigrationHistoryListTable 1 }

	HihsmVolumeMigrationHistoryListEntry ::= 
		SEQUENCE {
			hihsmVolHstListSerialNumber	INTEGER,
			hihsmVolHstListControlIndex	INTEGER,
			hihsmVolHstListDate		DisplayString,
			hihsmVolHstListTime		DisplayString,
			hihsmVolHstListAction		DisplayString,
			hihsmVolHstListSrcFB4Number	INTEGER,
			hihsmVolHstListSrcPGNumber	INTEGER,
			hihsmVolHstListSrcCU		INTEGER,
			hihsmVolHstListSrcLDEV		INTEGER,
			hihsmVolHstListDstFB4Number	INTEGER,
			hihsmVolHstListDstPGNumber	INTEGER,
			hihsmVolHstListDstCU		INTEGER,
			hihsmVolHstListDstLDEV		INTEGER
		}

	hihsmVolHstListSerialNumber	OBJECT-TYPE
		SYNTAX		INTEGER
		ACCESS		read-only
		STATUS		mandatory
		DESCRIPTION
			"Serial number of the DKC."
		::= { hihsmVolumeMigrationHistoryListEntry 1 }

	hihsmVolHstListControlIndex	OBJECT-TYPE
		SYNTAX		INTEGER
		ACCESS		read-only
		STATUS		mandatory
		DESCRIPTION
			"Control index."
		::= { hihsmVolumeMigrationHistoryListEntry 2 }

	hihsmVolHstListDate	OBJECT-TYPE
		SYNTAX		DisplayString
		ACCESS		read-only
		STATUS		mandatory
		DESCRIPTION
			"Date."
		::= { hihsmVolumeMigrationHistoryListEntry 3 }

	hihsmVolHstListTime	OBJECT-TYPE
		SYNTAX		DisplayString
		ACCESS		read-only
		STATUS		mandatory
		DESCRIPTION
			"Time."
		::= { hihsmVolumeMigrationHistoryListEntry 4 }

	hihsmVolHstListAction	OBJECT-TYPE
		SYNTAX		DisplayString
		ACCESS		read-only
		STATUS		mandatory
		DESCRIPTION
			"Action."
		::= { hihsmVolumeMigrationHistoryListEntry 5 }

	hihsmVolHstListSrcFB4Number	OBJECT-TYPE
		SYNTAX		INTEGER
		ACCESS		read-only
		STATUS		mandatory
		DESCRIPTION
			"Source FB4 number."
		::= { hihsmVolumeMigrationHistoryListEntry 6 }

	hihsmVolHstListSrcPGNumber	OBJECT-TYPE
		SYNTAX		INTEGER
		ACCESS		read-only
		STATUS		mandatory
		DESCRIPTION
			"Source PG number."
		::= { hihsmVolumeMigrationHistoryListEntry 7 }

	hihsmVolHstListSrcCU	OBJECT-TYPE
		SYNTAX		INTEGER
		ACCESS		read-only
		STATUS		mandatory
		DESCRIPTION
			"Source CU number."
		::= { hihsmVolumeMigrationHistoryListEntry 8 }

	hihsmVolHstListSrcLDEV	OBJECT-TYPE
		SYNTAX		INTEGER
		ACCESS		read-only
		STATUS		mandatory
		DESCRIPTION
			"Source LDEV number."
		::= { hihsmVolumeMigrationHistoryListEntry 9 }

	hihsmVolHstListDstFB4Number	OBJECT-TYPE
		SYNTAX		INTEGER
		ACCESS		read-only
		STATUS		mandatory
		DESCRIPTION
			"Destination FB4 number."
		::= { hihsmVolumeMigrationHistoryListEntry 10 }

	hihsmVolHstListDstPGNumber	OBJECT-TYPE
		SYNTAX		INTEGER
		ACCESS		read-only
		STATUS		mandatory
		DESCRIPTION
			"Destination PG number."
		::= { hihsmVolumeMigrationHistoryListEntry 11 }

	hihsmVolHstListDstCU	OBJECT-TYPE
		SYNTAX		INTEGER
		ACCESS		read-only
		STATUS		mandatory
		DESCRIPTION
			"Destination CU number."
		::= { hihsmVolumeMigrationHistoryListEntry 12 }

	hihsmVolHstListDstLDEV	OBJECT-TYPE
		SYNTAX		INTEGER
		ACCESS		read-only
		STATUS		mandatory
		DESCRIPTION
			"Destination LDEV number."
		::= { hihsmVolumeMigrationHistoryListEntry 13 }
--
-- HIHSM manual migration information
--

	hihsmManualMigration	OBJECT IDENTIFIER ::= { raidExMibHIHSM 6 }

--
-- HIHSM Manual Volume Migration information
--

	hihsmManualVolumeMigrationTable	OBJECT-TYPE
		SYNTAX		SEQUENCE OF HihsmManualVolumeMigrationEntry
		ACCESS		not-accessible 
		STATUS		mandatory
		DESCRIPTION
			"HIHSM Manual Volume Migration information."
		::= { hihsmManualMigration 1 }

	hihsmManualVolumeMigrationEntry	OBJECT-TYPE
		SYNTAX		HihsmManualVolumeMigrationEntry
		ACCESS		not-accessible
		STATUS		mandatory
		DESCRIPTION
			"Entry of HIHSM Manual Volume Migration information."
		INDEX {
			hihsmManVolMigSerialNumber,
			hihsmManVolMigSrcCU,
			hihsmManVolMigSrcLDEV
		}
		::= { hihsmManualVolumeMigrationTable 1 }

	HihsmManualVolumeMigrationEntry ::=
		SEQUENCE {
			hihsmManVolMigSerialNumber	INTEGER,
			hihsmManVolMigSrcCU		INTEGER,
			hihsmManVolMigSrcLDEV		INTEGER,
			hihsmManVolMigDstCU		INTEGER,
			hihsmManVolMigDstLDEV		INTEGER,
			hihsmManVolMigProgress		INTEGER,
			hihsmManVolMigControlStatus	INTEGER
		}

	hihsmManVolMigSerialNumber	OBJECT-TYPE
		SYNTAX		INTEGER
		ACCESS		read-only
		STATUS		mandatory
		DESCRIPTION
			"Serial number of the DKC."
		::= { hihsmManualVolumeMigrationEntry 1 }

	hihsmManVolMigSrcCU	OBJECT-TYPE
		SYNTAX		INTEGER
		ACCESS		read-only
		STATUS		mandatory
		DESCRIPTION
			"Source CU number."
		::= { hihsmManualVolumeMigrationEntry 2 }

	hihsmManVolMigSrcLDEV	OBJECT-TYPE
		SYNTAX		INTEGER
		ACCESS		read-only
		STATUS		mandatory
		DESCRIPTION
			"Source LDEV number."
		::= { hihsmManualVolumeMigrationEntry 3 }

	hihsmManVolMigDstCU	OBJECT-TYPE
		SYNTAX		INTEGER
		ACCESS		read-write
		STATUS		mandatory
		DESCRIPTION
			"Destination CU number."
		::= { hihsmManualVolumeMigrationEntry 4 }

	hihsmManVolMigDstLDEV	OBJECT-TYPE
		SYNTAX		INTEGER
		ACCESS		read-write
		STATUS		mandatory
		DESCRIPTION
			"Destination LDEV number."
		::= { hihsmManualVolumeMigrationEntry 5 }

	hihsmManVolMigProgress	OBJECT-TYPE
		SYNTAX		INTEGER
		ACCESS		read-only
		STATUS		mandatory
		DESCRIPTION
			"Progress of migration."
		::= { hihsmManualVolumeMigrationEntry 6 }

	hihsmManVolMigControlStatus	OBJECT-TYPE
		SYNTAX		INTEGER
		ACCESS		read-write
		STATUS		mandatory
		DESCRIPTION
			"Control Status.

			Value	Mean
			1	Return value.
			2	Migration request.
			3	Cancel request.
			"
		::= { hihsmManualVolumeMigrationEntry 7 }

--
-- HIHSM migration expectation information
--

	hihsmMigrationExceptation	OBJECT IDENTIFIER ::= { raidExMibHIHSM 7 }

--
-- HIHSM destination parity group utilization expectation
--

	hihsmExpectationPGUtilizationTable	OBJECT-TYPE
		SYNTAX		SEQUENCE OF HihsmExpectationPGUtilizationEntry
		ACCESS		not-accessible 
		STATUS		mandatory
		DESCRIPTION
			"HIHSM destination parity group utilization expectation."
		::= { hihsmMigrationExceptation 1 }

	hihsmExpectationPGUtilizationEntry	OBJECT-TYPE
		SYNTAX		HihsmExpectationPGUtilizationEntry
		ACCESS		not-accessible
		STATUS		mandatory
		DESCRIPTION
			"Entry of HIHSM destination PG utilization expectation."
		INDEX {
			hihsmExpPGUtilSerialNumber,
			hihsmExpPGUtilSrcCU,
			hihsmExpPGUtilSrcLDEV,
			hihsmExpPGUtilDstFB4,
			hihsmExpPGUtilDstPG
		}
		::= { hihsmExpectationPGUtilizationTable 1 }

	HihsmExpectationPGUtilizationEntry ::=
		SEQUENCE {
			hihsmExpPGUtilSerialNumber	INTEGER,
			hihsmExpPGUtilSrcCU		INTEGER,
			hihsmExpPGUtilSrcLDEV		INTEGER,
			hihsmExpPGUtilDstFB4		INTEGER,
			hihsmExpPGUtilDstPG		INTEGER,
			hihsmExpPGUtilData		DisplayString,
			hihsmExpPGUtilControlStatus	INTEGER
		}

	hihsmExpPGUtilSerialNumber	OBJECT-TYPE
		SYNTAX		INTEGER
		ACCESS		read-only
		STATUS		mandatory
		DESCRIPTION
			"Serial number of the DKC."
		::= { hihsmExpectationPGUtilizationEntry 1 }

	hihsmExpPGUtilSrcCU	OBJECT-TYPE
		SYNTAX		INTEGER
		ACCESS		read-only
		STATUS		mandatory
		DESCRIPTION
			"Source volume CU number."
		::= { hihsmExpectationPGUtilizationEntry 2 }

	hihsmExpPGUtilSrcLDEV	OBJECT-TYPE
		SYNTAX		INTEGER
		ACCESS		read-only
		STATUS		mandatory
		DESCRIPTION
			"Source volume LDEV number."
		::= { hihsmExpectationPGUtilizationEntry 3 }

	hihsmExpPGUtilDstFB4	OBJECT-TYPE
		SYNTAX		INTEGER
		ACCESS		read-only
		STATUS		mandatory
		DESCRIPTION
			"Destination FB4 number."
		::= { hihsmExpectationPGUtilizationEntry 4 }

	hihsmExpPGUtilDstPG	OBJECT-TYPE
		SYNTAX		INTEGER
		ACCESS		read-only
		STATUS		mandatory
		DESCRIPTION
			"Destination PG number."
		::= { hihsmExpectationPGUtilizationEntry 5 }

	hihsmExpPGUtilData	OBJECT-TYPE
		SYNTAX		DisplayString
		ACCESS		read-only
		STATUS		mandatory
		DESCRIPTION
			"Expectation Utilization of Destination PG.

			Column	Mean
			1	Average utilization after migrated.
			2	Maximum utilization after migrated.
			"
		::= { hihsmExpectationPGUtilizationEntry 6 }

	hihsmExpPGUtilControlStatus	OBJECT-TYPE
		SYNTAX		INTEGER
		ACCESS		read-write
		STATUS		mandatory
		DESCRIPTION
			"Control Status.

			Value	Mean
			1	Return value.
			2	Expectation request.
			3	Deleting request.
			"
		::= { hihsmExpectationPGUtilizationEntry 7 }

--
-- CSW information
--

	raidExMibCSW		OBJECT IDENTIFIER ::= { raidExMibRoot 21 }

--
-- CSW configuration information
--

	raidExMibCSWConfigurationTable	OBJECT-TYPE
		SYNTAX		SEQUENCE OF RaidExMibCSWConfigurationEntry
		ACCESS		not-accessible 
		STATUS		mandatory
		DESCRIPTION
			"CSW configuration information."
		::= { raidExMibCSW 1 }

	raidExMibCSWConfigurationEntry		OBJECT-TYPE
		SYNTAX		RaidExMibCSWConfigurationEntry
		ACCESS		not-accessible
		STATUS		mandatory
		DESCRIPTION
			"Entry of CSW configuration information."
		INDEX {
			cswSerialNumber,
			cswClusterNumber,
			cswNumber
		}
		::= { raidExMibCSWConfigurationTable 1 }

	RaidExMibCSWConfigurationEntry ::=
		SEQUENCE {
			cswSerialNumber		INTEGER,
			cswClusterNumber	INTEGER,
			cswNumber			INTEGER,
			cswDisplayName		DisplayString
		}

	cswSerialNumber		OBJECT-TYPE
		SYNTAX		INTEGER
		ACCESS		read-only
		STATUS		mandatory
		DESCRIPTION
			"Serial number of the DKC."
		::= { raidExMibCSWConfigurationEntry 1 }

	cswClusterNumber		OBJECT-TYPE
		SYNTAX		INTEGER
		ACCESS		read-only
		STATUS		mandatory
		DESCRIPTION
			"Cluster number."
		::= { raidExMibCSWConfigurationEntry 2 }

	cswNumber		OBJECT-TYPE
		SYNTAX		INTEGER
		ACCESS		read-only
		STATUS		mandatory
		DESCRIPTION
			"CSW number."
		::= { raidExMibCSWConfigurationEntry 3 }

	cswDisplayName		OBJECT-TYPE
		SYNTAX		DisplayString
		ACCESS		read-only
		STATUS		mandatory
		DESCRIPTION
			"Display name of the CSW."
		::= { raidExMibCSWConfigurationEntry 4 }

--
-- Shared Memory information
--

	raidExMibSharedMemory	OBJECT IDENTIFIER ::= { raidExMibRoot 22 }

--
-- Shared Memory configuration information
--

	raidExMibSMConfigurationTable	OBJECT-TYPE
		SYNTAX		SEQUENCE OF RaidExMibSMConfigurationEntry
		ACCESS		not-accessible 
		STATUS		mandatory
		DESCRIPTION
			"Shared Memory configuration information."
		::= { raidExMibSharedMemory 1 }

	raidExMibSMConfigurationEntry		OBJECT-TYPE
		SYNTAX		RaidExMibSMConfigurationEntry
		ACCESS		not-accessible
		STATUS		mandatory
		DESCRIPTION
			"Entry of Shared Memory configuration information."
		INDEX {
			smSerialNumber,
			smClusterNumber
		}
		::= { raidExMibSMConfigurationTable 1 }

	RaidExMibSMConfigurationEntry ::=
		SEQUENCE {
			smSerialNumber		INTEGER,
			smClusterNumber		INTEGER,
			smDisplayName		DisplayString
		}

	smSerialNumber		OBJECT-TYPE
		SYNTAX		INTEGER
		ACCESS		read-only
		STATUS		mandatory
		DESCRIPTION
			"Serial number of the DKC."
		::= { raidExMibSMConfigurationEntry 1 }

	smClusterNumber		OBJECT-TYPE
		SYNTAX		INTEGER
		ACCESS		read-only
		STATUS		mandatory
		DESCRIPTION
			"Cluster number."
		::= { raidExMibSMConfigurationEntry 2 }

	smDisplayName		OBJECT-TYPE
		SYNTAX		DisplayString
		ACCESS		read-only
		STATUS		mandatory
		DESCRIPTION
			"Display name of the SM."
		::= { raidExMibSMConfigurationEntry 3 }

--
-- Cache Memory information
--

	raidExMibCacheMemory	OBJECT IDENTIFIER ::= { raidExMibRoot 23 }

--
-- Cache Memory configuration information
--

	raidExMibCacheConfigurationTable		OBJECT-TYPE
		SYNTAX		SEQUENCE OF RaidExMibCacheConfigurationEntry
		ACCESS		not-accessible 
		STATUS		mandatory
		DESCRIPTION
			"Cache configuration information."
		::= { raidExMibCacheMemory 1 }

	raidExMibCacheConfigurationEntry		OBJECT-TYPE
		SYNTAX		RaidExMibCacheConfigurationEntry
		ACCESS		not-accessible
		STATUS		mandatory
		DESCRIPTION
			"Entry of Cache configuration information."
		INDEX {
			cacheConfSerialNumber,
			cacheConfClusterNumber,
			cacheConfCacheNumber
		}
		::= { raidExMibCacheConfigurationTable 1 }

	RaidExMibCacheConfigurationEntry ::=
		SEQUENCE {
			cacheConfSerialNumber		INTEGER,
			cacheConfClusterNumber		INTEGER,
			cacheConfCacheNumber		INTEGER,
			cacheConfDisplayName		DisplayString
		}

	cacheConfSerialNumber	OBJECT-TYPE
		SYNTAX		INTEGER
		ACCESS		read-only
		STATUS		mandatory
		DESCRIPTION
			"Serial number of the DKC."
		::= { raidExMibCacheConfigurationEntry 1 }

	cacheConfClusterNumber	OBJECT-TYPE
		SYNTAX		INTEGER
		ACCESS		read-only
		STATUS		mandatory
		DESCRIPTION
			"Cluster number."
		::= { raidExMibCacheConfigurationEntry 2 }

	cacheConfCacheNumber	OBJECT-TYPE
		SYNTAX		INTEGER
		ACCESS		read-only
		STATUS		mandatory
		DESCRIPTION
			"Cache number."
		::= { raidExMibCacheConfigurationEntry 3 }

	cacheConfDisplayName	OBJECT-TYPE
		SYNTAX		DisplayString
		ACCESS		read-only
		STATUS		mandatory
		DESCRIPTION
			"Display name of the Cache."
		::= { raidExMibCacheConfigurationEntry 4 }



--
-- Prioritized Port Control
--

  raidExMibPortControlConfiguration OBJECT IDENTIFIER ::= { raidExMibRoot 24 }


--
-- Port Control information
--

	raidExMibPortControlSwitchTable		OBJECT-TYPE
		SYNTAX		SEQUENCE OF RaidExMibPortControlSwitchEntry
		ACCESS		not-accessible 
		STATUS		mandatory
		DESCRIPTION
			"Port Control Switch information."
		::= { raidExMibPortControlConfiguration 1 }

	raidExMibPortControlSwitchEntry		OBJECT-TYPE
		SYNTAX		RaidExMibPortControlSwitchEntry
		ACCESS		not-accessible
		STATUS		mandatory
		DESCRIPTION
			"Entry of port Control Switch information."
		INDEX {
			portControlSwitchSerialNumber
		}
		::= { raidExMibPortControlSwitchTable 1 }

	RaidExMibPortControlSwitchEntry ::=
		SEQUENCE {
			portControlSwitchSerialNumber	INTEGER,
			portControlSwitchOnOff		INTEGER,
			portControlSwitchStatus		INTEGER
		}

	portControlSwitchSerialNumber		OBJECT-TYPE
		SYNTAX		INTEGER
		ACCESS		read-only
		STATUS		mandatory
		DESCRIPTION
			"Serial Number of the DKC."
		::= { raidExMibPortControlSwitchEntry 1 }

	portControlSwitchOnOff			OBJECT-TYPE
		SYNTAX		INTEGER
		ACCESS		read-write
		STATUS		mandatory
		DESCRIPTION
			"Port Control Switch On/Off."
		::= { raidExMibPortControlSwitchEntry 2 }

	portControlSwitchStatus		OBJECT-TYPE
		SYNTAX		INTEGER
		ACCESS		read-write
		STATUS		mandatory
		DESCRIPTION
			"Normal Return code	:1
 			 Set Request		:2
			"
		::= { raidExMibPortControlSwitchEntry 3 }


--
-- Port Control Setup information
--

	raidExMibPortControlSetUpTable	OBJECT-TYPE
		SYNTAX		SEQUENCE OF RaidExMibPortControlSetUpEntry
		ACCESS		not-accessible 
		STATUS		mandatory
		DESCRIPTION
			"Port Control Setup information."
		::= { raidExMibPortControlConfiguration 2 }

	raidExMibPortControlSetUpEntry		OBJECT-TYPE
		SYNTAX		RaidExMibPortControlSetUpEntry
		ACCESS		not-accessible
		STATUS		mandatory
		DESCRIPTION
			"Entry of port Control Setup information."
		INDEX {
			portControlSetUpSerialNumber,
			portControlSetUpPortID
		}
		::= { raidExMibPortControlSetUpTable 1 }

	RaidExMibPortControlSetUpEntry ::=
		SEQUENCE {
			portControlSetUpSerialNumber	INTEGER,
			portControlSetUpPortID		INTEGER,
			portControlSetUpControlIndex	INTEGER,
			portControlSetUpDisplayName	DisplayString,
			portControlSetUpSetting		INTEGER,
			portControlSetUpStatus		INTEGER
		}

	portControlSetUpSerialNumber		OBJECT-TYPE
		SYNTAX		INTEGER
		ACCESS		read-only
		STATUS		mandatory
		DESCRIPTION
			"Serial Number of the DKC."
		::= { raidExMibPortControlSetUpEntry 1 }

	portControlSetUpPortID			OBJECT-TYPE
		SYNTAX		INTEGER
		ACCESS		read-write
		STATUS		mandatory
		DESCRIPTION
			"Port Number "
		::= { raidExMibPortControlSetUpEntry 2 }

	portControlSetUpControlIndex		OBJECT-TYPE
		SYNTAX		INTEGER
		ACCESS		read-write
		STATUS		mandatory
		DESCRIPTION
			"Control Index " 
		::= { raidExMibPortControlSetUpEntry 3 }

	portControlSetUpDisplayName		OBJECT-TYPE
		SYNTAX		DisplayString
		ACCESS		read-write
		STATUS		mandatory
		DESCRIPTION
			"Port Display Name " 
		::= { raidExMibPortControlSetUpEntry 4 }

	portControlSetUpSetting		OBJECT-TYPE
		SYNTAX		INTEGER
		ACCESS		read-write
		STATUS		mandatory
		DESCRIPTION
			"Priority Mode " 
		::= { raidExMibPortControlSetUpEntry 5 }

	portControlSetUpStatus		OBJECT-TYPE
		SYNTAX		INTEGER
		ACCESS		read-write
		STATUS		mandatory
		DESCRIPTION
			"Control Flag " 
		::= { raidExMibPortControlSetUpEntry 6 }


--
-- Port Parameter data for each Port
--

	raidExMibPortControlParameter OBJECT IDENTIFIER ::= { raidExMibPortControlConfiguration 3 }

--
--
--

	raidExMibPortParameterTable	OBJECT-TYPE
		SYNTAX		SEQUENCE OF RaidExMibPortParameterEntry
		ACCESS		not-accessible 
		STATUS		mandatory
		DESCRIPTION
		"Port Control Parameter information."
		::= { raidExMibPortControlParameter 1 }

	raidExMibPortParameterEntry			OBJECT-TYPE
		SYNTAX		RaidExMibPortParameterEntry
		ACCESS		not-accessible
		STATUS		mandatory
		DESCRIPTION
			"Entry of PortControl parameter information."
		INDEX {
			portPrmSerialNumber,
			portPrmPortID,
			portPrmControlIndex
		}
		::= { raidExMibPortParameterTable 1 }

	RaidExMibPortParameterEntry ::=
		SEQUENCE {
			portPrmSerialNumber		INTEGER,
			portPrmPortID		INTEGER,
			portPrmControlIndex	INTEGER,
			portPrmDisplayName	DisplayString,
			portPrmSetting		INTEGER,
			portPrmPrioIOPS		INTEGER,
			portPrmPrioMBS		INTEGER,
			portNPrmnPrioIOPS		INTEGER,
			portNPrmnPrioMBS		INTEGER,
			portPrmThreshold		INTEGER,
			portPrmStatus		INTEGER
		}

	portPrmSerialNumber		OBJECT-TYPE
		SYNTAX		INTEGER
		ACCESS		read-only
		STATUS		mandatory
		DESCRIPTION
			"Serial Number of the DKC."
		::= { raidExMibPortParameterEntry 1 }

	portPrmPortID		OBJECT-TYPE
		SYNTAX		INTEGER
		ACCESS		read-only
		STATUS		mandatory
		DESCRIPTION
			" Port Number."
		::= { raidExMibPortParameterEntry 2 }

	portPrmControlIndex		OBJECT-TYPE
		SYNTAX		INTEGER
		ACCESS		read-only
		STATUS		mandatory
		DESCRIPTION
			"Control Index."
		::= { raidExMibPortParameterEntry 3 }

	portPrmDisplayName		OBJECT-TYPE
		SYNTAX		DisplayString
		ACCESS		read-only
		STATUS		mandatory
		DESCRIPTION
			"Port Display Name."
		::= { raidExMibPortParameterEntry 4 }

	portPrmSetting			OBJECT-TYPE
		SYNTAX		INTEGER
		ACCESS		read-only
		STATUS		mandatory
		DESCRIPTION
			"Priority Mode.
			Value	Mean
			1	Prioritized Mode.
			2	Non-Prioritized Mode.
			"

		::= { raidExMibPortParameterEntry 5 }

	portPrmPrioIOPS			OBJECT-TYPE
		SYNTAX		INTEGER
		ACCESS		read-only
		STATUS		mandatory
		DESCRIPTION
			"Threshold Level of IOPS for Priority "
		::= { raidExMibPortParameterEntry 6 }

	portPrmPrioMBS		OBJECT-TYPE
		SYNTAX		INTEGER
		ACCESS		read-only
		STATUS		mandatory
		DESCRIPTION
			"Threshold Level of MBs for Priority "
		::= { raidExMibPortParameterEntry 7 }

	portNPrmnPrioIOPS		OBJECT-TYPE
		SYNTAX		INTEGER
		ACCESS		read-write
		STATUS		mandatory
		DESCRIPTION
			"Upper Limit of IOPS for Priority "

		::= { raidExMibPortParameterEntry 8 }

	portNPrmnPrioMBS		OBJECT-TYPE
		SYNTAX		INTEGER
		ACCESS		read-write
		STATUS		mandatory
		DESCRIPTION
			"Upper Limit of MBs for Priority "
		::= { raidExMibPortParameterEntry 9 }

	portPrmThreshold		OBJECT-TYPE
		SYNTAX		INTEGER
		ACCESS		read-write
		STATUS		mandatory
		DESCRIPTION
			"Threshold Level Control flag.
			Value	Mean
			0	off.
			1	on.
			"
		::= { raidExMibPortParameterEntry 10 }

	portPrmStatus		OBJECT-TYPE
		SYNTAX		INTEGER
		ACCESS		read-write
		STATUS		mandatory
		DESCRIPTION
			"Control flag.

			Value	Mean
			1	Normal Return code.
			2	Set Request.
			"
		::= { raidExMibPortParameterEntry 11 }

--
-- Total Threshold Level Data for Priority Port
--

	raidExMibPrioAllPortParameterTable		OBJECT-TYPE
		SYNTAX		SEQUENCE OF RaidExMibPrioAllPortParameterEntry
		ACCESS		not-accessible 
		STATUS		mandatory
		DESCRIPTION
			"Priority All Port Parameter information."
		::= { raidExMibPortControlParameter 2 }

	raidExMibPrioAllPortParameterEntry		OBJECT-TYPE
		SYNTAX		RaidExMibPrioAllPortParameterEntry
		ACCESS		not-accessible
		STATUS		mandatory
		DESCRIPTION
			"Entry of Priority All Port Parameter information."
		INDEX {
			prioAllPortPrmSerialNumber
			}
		::= { raidExMibPrioAllPortParameterTable 1 }

	RaidExMibPrioAllPortParameterEntry ::=
		SEQUENCE {
			prioAllPortPrmSerialNumber	INTEGER,
			prioAllPortPrmPrioIOPS		INTEGER,
			prioAllPortPrmPrioMBS		INTEGER,
			prioAllPortPrmThreshold		INTEGER,
			prioAllPortPrmStatus		INTEGER
		}

	prioAllPortPrmSerialNumber	OBJECT-TYPE
		SYNTAX		INTEGER
		ACCESS		read-only
		STATUS		mandatory
		DESCRIPTION
			"Serial Number of the DKC."
		::= { raidExMibPrioAllPortParameterEntry 1 }

	prioAllPortPrmPrioIOPS	OBJECT-TYPE
		SYNTAX		INTEGER
		ACCESS		read-write
		STATUS		mandatory
		DESCRIPTION
			"IOPS for Priority Port."
		::= { raidExMibPrioAllPortParameterEntry 2 }

	prioAllPortPrmPrioMBS		OBJECT-TYPE
		SYNTAX		INTEGER
		ACCESS		read-write
		STATUS		mandatory
		DESCRIPTION
			"MB/S for Priority Port."
		::= { raidExMibPrioAllPortParameterEntry 3 }

	prioAllPortPrmThreshold		OBJECT-TYPE
		SYNTAX		INTEGER
		ACCESS		read-only
		STATUS		mandatory
		DESCRIPTION
			" Threshold Level.
			Value	Mean
			1	Non Control.
			2	Control.
			"
		::= { raidExMibPrioAllPortParameterEntry 4 }

	prioAllPortPrmStatus		OBJECT-TYPE
		SYNTAX		INTEGER
		ACCESS		read-write
		STATUS		mandatory
		DESCRIPTION
			" Control Flag.
			Value	Mean
			1	Normal Return Code.
			2	Set Request.
			3	Release Request
			"
		::= { raidExMibPrioAllPortParameterEntry 5 }

	

--
--  Port Total Parameter Data
--

	raidExMibAllPortParameterTable		OBJECT-TYPE
		SYNTAX		SEQUENCE OF RaidExMibAllPortParameterEntry
		ACCESS		not-accessible 
		STATUS		mandatory
		DESCRIPTION
			"All Port Parameter information."
		::= { raidExMibPortControlParameter 3 }

	raidExMibAllPortParameterEntry		OBJECT-TYPE
		SYNTAX		RaidExMibAllPortParameterEntry
		ACCESS		not-accessible
		STATUS		mandatory
		DESCRIPTION
			"Entry All Port Parameter information."
		INDEX {
			allPortPrmSerialNumber
			}
		::= { raidExMibAllPortParameterTable 1 }

	RaidExMibAllPortParameterEntry ::=
		SEQUENCE {
			allPortPrmSerialNumber	INTEGER,
			allPortPrmStatus		INTEGER
		}

	allPortPrmSerialNumber	OBJECT-TYPE
		SYNTAX		INTEGER
		ACCESS		read-only
		STATUS		mandatory
		DESCRIPTION
			"Serial Number of the DKC."
		::= { raidExMibAllPortParameterEntry 1 }
 
	allPortPrmStatus		OBJECT-TYPE
		SYNTAX		INTEGER
		ACCESS		read-write
		STATUS		mandatory
		DESCRIPTION
			" Control Flag.
			Value	Mean
			1	Normal Return.
			2	Request to Default.
			"
		::= { raidExMibAllPortParameterEntry 2 }

--
--  Real Time Monitoring Data
-- 

 raidExMibRealTimeMonitoringInformation	OBJECT IDENTIFIER ::= { raidExMibPortControlConfiguration 4 }

--
-- Get Operation for Real Time Monitoring
--

	raidExMibRTMonitoringCntlTable	OBJECT-TYPE
		SYNTAX		SEQUENCE OF RaidExMibRTMonitoringCntlEntry
		ACCESS		not-accessible 
		STATUS		mandatory
		DESCRIPTION
			"Monitoring Control Information."
		::= { raidExMibRealTimeMonitoringInformation 1 }

	raidExMibRTMonitoringCntlEntry		OBJECT-TYPE
		SYNTAX		RaidExMibRTMonitoringCntlEntry 
		ACCESS		not-accessible
		STATUS		mandatory
		DESCRIPTION
			"Entry of LUSE information."
		INDEX {
			rTMonitoringCntlSerialNumber
		}
		::= { raidExMibRTMonitoringCntlTable 1 }

	RaidExMibRTMonitoringCntlEntry ::=
		SEQUENCE {
			rTMonitoringCntlSerialNumber		INTEGER,
			rTMonitoringCntlStatus		INTEGER
		}

	rTMonitoringCntlSerialNumber	OBJECT-TYPE
		SYNTAX		INTEGER
		ACCESS		read-only
		STATUS		mandatory
		DESCRIPTION
			"Serial Number of the DKC."
		::= { raidExMibRTMonitoringCntlEntry 1 }

	rTMonitoringCntlStatus	OBJECT-TYPE
		SYNTAX		INTEGER
		ACCESS		read-write
		STATUS		mandatory
		DESCRIPTION
			" Control Flag."
		::= { raidExMibRTMonitoringCntlEntry 2 }

	


--
-- Get Operation for Real Time Monitoring for each Port
--

	raidExMibRTMonitorDataTable	OBJECT-TYPE
		SYNTAX		SEQUENCE OF RaidExMibRTMonitorDataEntry
		ACCESS		not-accessible 
		STATUS		mandatory
		DESCRIPTION
			"Port Monitoring parameter Data Information."
		::= { raidExMibRealTimeMonitoringInformation 2 }

	raidExMibRTMonitorDataEntry		OBJECT-TYPE
		SYNTAX		RaidExMibRTMonitorDataEntry 
		ACCESS		not-accessible
		STATUS		mandatory
		DESCRIPTION
			"Entry of Port Monitoring parameter Data Information."
		INDEX {
			rTMonitorDataSerialNumber,
			rTMonitorDataPortID,
			rTMonitorDataControlIndex
		}
		::= { raidExMibRTMonitorDataTable 1 }

	RaidExMibRTMonitorDataEntry ::=
		SEQUENCE {
			rTMonitorDataSerialNumber	INTEGER,
			rTMonitorDataPortID 		INTEGER,
			rTMonitorDataControlIndex 	INTEGER,
			rTMonitorDataGatheredDate 	DisplayString,
			rTMonitorDataGatheredTime 	DisplayString,
			rTMonitorDataSetting 	INTEGER,
			rTMonitorDataIOPSMax 	INTEGER,
			rTMonitorDataIOPSAve 	INTEGER,
			rTMonitorDataIOPSMin 	INTEGER,
			rTMonitorDataMBSMax 	INTEGER,
			rTMonitorDataMBSAve 	INTEGER,
			rTMonitorDataMBSMin 	INTEGER		}

	rTMonitorDataSerialNumber	OBJECT-TYPE
		SYNTAX		INTEGER
		ACCESS		read-only
		STATUS		mandatory
		DESCRIPTION
			"Serial Number of the DKC."
		::= { raidExMibRTMonitorDataEntry 1 }

	rTMonitorDataPortID	OBJECT-TYPE
		SYNTAX		INTEGER
		ACCESS		read-only
		STATUS		mandatory
		DESCRIPTION
			" Port Number."
		::= { raidExMibRTMonitorDataEntry 2 }

	rTMonitorDataControlIndex	OBJECT-TYPE
		SYNTAX		INTEGER
		ACCESS		read-only
		STATUS		mandatory
		DESCRIPTION
			" Control Index."
		::= { raidExMibRTMonitorDataEntry 3 }

	rTMonitorDataGatheredDate	OBJECT-TYPE
		SYNTAX		DisplayString
		ACCESS		read-only
		STATUS		mandatory
		DESCRIPTION
			" Monitoring Date."
		::= { raidExMibRTMonitorDataEntry 4 }

	rTMonitorDataGatheredTime	OBJECT-TYPE
		SYNTAX		DisplayString 
		ACCESS		read-only
		STATUS		mandatory
		DESCRIPTION
			" Monitoring Time."
		::= { raidExMibRTMonitorDataEntry 5 }

	rTMonitorDataSetting	OBJECT-TYPE
		SYNTAX		INTEGER
		ACCESS		read-only
		STATUS		mandatory
		DESCRIPTION
			" Priority Mode.
			Value	Mean
			1	Prioritized Mode.
			2	Non-Prioritized Mode.
			"
		::= { raidExMibRTMonitorDataEntry 6 }

	rTMonitorDataIOPSMax	OBJECT-TYPE
		SYNTAX		INTEGER
		ACCESS		read-only
		STATUS		mandatory
		DESCRIPTION
			" IOPS Max Value."
		::= { raidExMibRTMonitorDataEntry 7 }

	rTMonitorDataIOPSAve	OBJECT-TYPE
		SYNTAX		INTEGER
		ACCESS		read-only
		STATUS		mandatory
		DESCRIPTION
			" IOPS Average Value."
		::= { raidExMibRTMonitorDataEntry 8 }

	rTMonitorDataIOPSMin	OBJECT-TYPE
		SYNTAX		INTEGER
		ACCESS		read-only
		STATUS		mandatory
		DESCRIPTION
			" IOPS Min Value."
		::= { raidExMibRTMonitorDataEntry 9 }

	rTMonitorDataMBSMax	OBJECT-TYPE
		SYNTAX		INTEGER
		ACCESS		read-only
		STATUS		mandatory
		DESCRIPTION
			" MBS Max Value."
		::= { raidExMibRTMonitorDataEntry 10 }

	rTMonitorDataMBSAve	OBJECT-TYPE
		SYNTAX		INTEGER
		ACCESS		read-only
		STATUS		mandatory
		DESCRIPTION
			" MBS Average Value."
		::= { raidExMibRTMonitorDataEntry 11 }

	rTMonitorDataMBSMin	OBJECT-TYPE
		SYNTAX		INTEGER
		ACCESS		read-only
		STATUS		mandatory
		DESCRIPTION
			" MBS Min Value."
		::= { raidExMibRTMonitorDataEntry 12 }

--
--     Total Real Time Monitoring data in Prioritized Port 
--

	raidExMibPrioRTMonitorDataTable	OBJECT-TYPE
		SYNTAX		SEQUENCE OF RaidExMibPrioRTMonitorDataEntry
		ACCESS		not-accessible 
		STATUS		mandatory
		DESCRIPTION
			"All Port Monitoring parameter Data Information."
		::= { raidExMibRealTimeMonitoringInformation 3 }

	raidExMibPrioRTMonitorDataEntry		OBJECT-TYPE
		SYNTAX		RaidExMibPrioRTMonitorDataEntry 
		ACCESS		not-accessible
		STATUS		mandatory
		DESCRIPTION
			"Entry of All Port Monitoring parameter Data."
		INDEX {
			prioRTMonitorDataSerialNumber
		}
		::= { raidExMibPrioRTMonitorDataTable 1 }

	RaidExMibPrioRTMonitorDataEntry ::=
		SEQUENCE {
			prioRTMonitorDataSerialNumber	INTEGER,
			prioRTMonitorDataGatheredDate 	DisplayString,
			prioRTMonitorDataGatheredTime 	DisplayString,
			prioRTMonitorDataIOPSMax 	INTEGER,
			prioRTMonitorDataIOPSAve 	INTEGER,
			prioRTMonitorDataIOPSMin 	INTEGER,
			prioRTMonitorDataMBSMax 	INTEGER,
			prioRTMonitorDataMBSAve 	INTEGER,
			prioRTMonitorDataMBSMin 	INTEGER		}

	prioRTMonitorDataSerialNumber	OBJECT-TYPE
		SYNTAX		INTEGER
		ACCESS		read-only
		STATUS		mandatory
		DESCRIPTION
			"Serial Number of the DKC."
		::= { raidExMibPrioRTMonitorDataEntry 1 }

	prioRTMonitorDataGatheredDate	OBJECT-TYPE
		SYNTAX		DisplayString
		ACCESS		read-only
		STATUS		mandatory
		DESCRIPTION
			" Monitoring Date."
		::= { raidExMibPrioRTMonitorDataEntry 2 }

	prioRTMonitorDataGatheredTime	OBJECT-TYPE
		SYNTAX		DisplayString 
		ACCESS		read-only
		STATUS		mandatory
		DESCRIPTION
			" Monitoring Time."
		::= { raidExMibPrioRTMonitorDataEntry 3 }

	prioRTMonitorDataIOPSMax	OBJECT-TYPE
		SYNTAX		INTEGER
		ACCESS		read-only
		STATUS		mandatory
		DESCRIPTION
			" IOPS Max Total Value of All Prioritized Port ."
		::= { raidExMibPrioRTMonitorDataEntry 4 }

	prioRTMonitorDataIOPSAve	OBJECT-TYPE
		SYNTAX		INTEGER
		ACCESS		read-only
		STATUS		mandatory
		DESCRIPTION
			" IOPS Average Total Value of All Prioritized Port ."
		::= { raidExMibPrioRTMonitorDataEntry 5 }

	prioRTMonitorDataIOPSMin	OBJECT-TYPE
		SYNTAX		INTEGER
		ACCESS		read-only
		STATUS		mandatory
		DESCRIPTION
			" IOPS Min Total Value of All Prioritized Port ."
		::= { raidExMibPrioRTMonitorDataEntry 6 }

	prioRTMonitorDataMBSMax	OBJECT-TYPE
		SYNTAX		INTEGER
		ACCESS		read-only
		STATUS		mandatory
		DESCRIPTION
			" MBS Max Total Value of All Prioritized Port ."
		::= { raidExMibPrioRTMonitorDataEntry 7 }

	prioRTMonitorDataMBSAve	OBJECT-TYPE
		SYNTAX		INTEGER
		ACCESS		read-only
		STATUS		mandatory
		DESCRIPTION
			" MBS Average Total Value of All Prioritized Port ."
		::= { raidExMibPrioRTMonitorDataEntry 8 }

	prioRTMonitorDataMBSMin	OBJECT-TYPE
		SYNTAX		INTEGER
		ACCESS		read-only
		STATUS		mandatory
		DESCRIPTION
			" MBS Min Total Value of All Prioritized Port ."
		::= { raidExMibPrioRTMonitorDataEntry 9 }


--
--     Total Real Time Monitoring data in Non-Prioritized Port 
--

	raidExMibNPrioRTMonitorDataTable	OBJECT-TYPE
		SYNTAX		SEQUENCE OF RaidExMibNPrioRTMonitorDataEntry
		ACCESS		not-accessible 
		STATUS		mandatory
		DESCRIPTION
		"All Non-Prioritized Port Monitoring parameter Data Information."
		::= { raidExMibRealTimeMonitoringInformation 4 }

	raidExMibNPrioRTMonitorDataEntry		OBJECT-TYPE
		SYNTAX		RaidExMibNPrioRTMonitorDataEntry 
		ACCESS		not-accessible
		STATUS		mandatory
		DESCRIPTION
		"Entry of All Non-Prioritized Port Monitoring parameter Data."
		INDEX {
			nPrioRTMonitorDataSerialNumber
		}
		::= { raidExMibNPrioRTMonitorDataTable 1 }

	RaidExMibNPrioRTMonitorDataEntry ::=
		SEQUENCE {
			nPrioRTMonitorDataSerialNumber	INTEGER,
			nPrioRTMonitorDataGatheredDate 	DisplayString,
			nPrioRTMonitorDataGatheredTime 	DisplayString,
			nPrioRTMonitorDataIOPSMax 	INTEGER,
			nPrioRTMonitorDataIOPSAve 	INTEGER,
			nPrioRTMonitorDataIOPSMin 	INTEGER,
			nPrioRTMonitorDataMBSMax 	INTEGER,
			nPrioRTMonitorDataMBSAve 	INTEGER,
			nPrioRTMonitorDataMBSMin 	INTEGER		}

	nPrioRTMonitorDataSerialNumber	OBJECT-TYPE
		SYNTAX		INTEGER
		ACCESS		read-only
		STATUS		mandatory
		DESCRIPTION
			"Serial Number of the DKC."
		::= { raidExMibNPrioRTMonitorDataEntry 1 }

	nPrioRTMonitorDataGatheredDate	OBJECT-TYPE
		SYNTAX		DisplayString
		ACCESS		read-only
		STATUS		mandatory
		DESCRIPTION
			" Monitoring Date."
		::= { raidExMibNPrioRTMonitorDataEntry 2 }

	nPrioRTMonitorDataGatheredTime	OBJECT-TYPE
		SYNTAX		DisplayString 
		ACCESS		read-only
		STATUS		mandatory
		DESCRIPTION
			" Monitoring Time."
		::= { raidExMibNPrioRTMonitorDataEntry 3 }

	nPrioRTMonitorDataIOPSMax	OBJECT-TYPE
		SYNTAX		INTEGER
		ACCESS		read-only
		STATUS		mandatory
		DESCRIPTION
			" IOPS Max Total Value of All Non-Prioritized Port ."
		::= { raidExMibNPrioRTMonitorDataEntry 4 }

	nPrioRTMonitorDataIOPSAve	OBJECT-TYPE
		SYNTAX		INTEGER
		ACCESS		read-only
		STATUS		mandatory
		DESCRIPTION
			" IOPS Average Total Value of All Non-Prioritized Port ."
		::= { raidExMibNPrioRTMonitorDataEntry 5 }

	nPrioRTMonitorDataIOPSMin	OBJECT-TYPE
		SYNTAX		INTEGER
		ACCESS		read-only
		STATUS		mandatory
		DESCRIPTION
			" IOPS Min Total Value of All Non-Prioritized Port ."
		::= { raidExMibNPrioRTMonitorDataEntry 6 }

	nPrioRTMonitorDataMBSMax	OBJECT-TYPE
		SYNTAX		INTEGER
		ACCESS		read-only
		STATUS		mandatory
		DESCRIPTION
			" MBS Max Total Value of All Non-Prioritized Port ."
		::= { raidExMibNPrioRTMonitorDataEntry 7 }

	nPrioRTMonitorDataMBSAve	OBJECT-TYPE
		SYNTAX		INTEGER
		ACCESS		read-only
		STATUS		mandatory
		DESCRIPTION
			" MBS Average Total Value of All Non-Prioritized Port ."
		::= { raidExMibNPrioRTMonitorDataEntry 8 }

	nPrioRTMonitorDataMBSMin	OBJECT-TYPE
		SYNTAX		INTEGER
		ACCESS		read-only
		STATUS		mandatory
		DESCRIPTION
			" MBS Min Total Value of All Non-Prioritized Port ."
		::= { raidExMibNPrioRTMonitorDataEntry 9 }


--
-- Version MIB Data
--

	raidExMibVersionManagement	OBJECT IDENTIFIER ::= { raidExMibRoot 50 }

--
-- MIB Version data for ALL
--

	mibAllLeafVersionTable	OBJECT-TYPE
		SYNTAX		SEQUENCE OF MibAllLeafVersionEntry
		ACCESS		not-accessible 
		STATUS		mandatory
		DESCRIPTION
			"MIB Version information."
		::= { raidExMibVersionManagement 1 }

	mibAllLeafVersionEntry		OBJECT-TYPE
		SYNTAX		MibAllLeafVersionEntry
		ACCESS		not-accessible
		STATUS		mandatory
		DESCRIPTION
			"Entry of MIB Version."
		INDEX {
			mibAllLeafVersionSerialNumber
		}
		::= { mibAllLeafVersionTable 1 }

	MibAllLeafVersionEntry ::=
		SEQUENCE {
			mibAllLeafVersionSerialNumber	INTEGER,
			mibAllLeafVersionMIBVersionData	DisplayString,
			mibAllLeafVersionMIBVersion	INTEGER
		}

	mibAllLeafVersionSerialNumber		OBJECT-TYPE
		SYNTAX		INTEGER
		ACCESS		read-only
		STATUS		mandatory
		DESCRIPTION
			"Serial Number of the DKC."
		::= { mibAllLeafVersionEntry 1 }

	mibAllLeafVersionMIBVersionData			OBJECT-TYPE
		SYNTAX		DisplayString
		ACCESS		read-only
		STATUS		mandatory
		DESCRIPTION
			"Version data."
		::= { mibAllLeafVersionEntry 2 }

	mibAllLeafVersionMIBVersion		OBJECT-TYPE
		SYNTAX		INTEGER
		ACCESS		read-only
		STATUS		mandatory
		DESCRIPTION
			"Version Number."
		::= { mibAllLeafVersionEntry 3 }


--
-- Logical Device MIB Version data
--

	mibLdevLeafVersionTable	OBJECT-TYPE
		SYNTAX		SEQUENCE OF MibLdevLeafVersionEntry
		ACCESS		not-accessible 
		STATUS		mandatory
		DESCRIPTION
			"MIB Version information."
		::= { raidExMibVersionManagement 10 }

	mibLdevLeafVersionEntry		OBJECT-TYPE
		SYNTAX		MibLdevLeafVersionEntry
		ACCESS		not-accessible
		STATUS		mandatory
		DESCRIPTION
			"Entry of MIB Version."
		INDEX {
			mibLdevVersionSerialNumber
		}
		::= { mibLdevLeafVersionTable 1 }

	MibLdevLeafVersionEntry ::=
		SEQUENCE {
			mibLdevVersionSerialNumber	INTEGER,
			mibLdevVersionMIBVersion		INTEGER,
			mibLdevVersionMIBOID		OBJECT IDENTIFIER
		}

	mibLdevVersionSerialNumber		OBJECT-TYPE
		SYNTAX		INTEGER
		ACCESS		read-only
		STATUS		mandatory
		DESCRIPTION
			"Serial Number of the DKC."
		::= { mibLdevLeafVersionEntry 1 }

	mibLdevVersionMIBVersion			OBJECT-TYPE
		SYNTAX		INTEGER
		ACCESS		read-only
		STATUS		mandatory
		DESCRIPTION
			"Version Number."
		::= { mibLdevLeafVersionEntry 2 }

	mibLdevVersionMIBOID			OBJECT-TYPE
		SYNTAX		OBJECT IDENTIFIER
		ACCESS		read-only
		STATUS		mandatory
		DESCRIPTION
			" OID."
		::= { mibLdevLeafVersionEntry 3 }

--
-- LU MIB Version data
--

  mibLuLeafVersion OBJECT IDENTIFIER ::= { raidExMibVersionManagement 11 }

--
--  Port MIB Version information
--

	mibPortleafVersionTable	OBJECT-TYPE
		SYNTAX		SEQUENCE OF MibPortleafVersionEntry
		ACCESS		not-accessible 
		STATUS		mandatory
		DESCRIPTION
			"LU Port MIB Version Information."
		::= { mibLuLeafVersion 1 }

	mibPortleafVersionEntry			OBJECT-TYPE
		SYNTAX		MibPortleafVersionEntry
		ACCESS		not-accessible
		STATUS		mandatory
		DESCRIPTION
			"Entry of LU Port MIB Version."
		INDEX {
			mibPortVersionSerialNumber
		}
		::= { mibPortleafVersionTable 1 }

	MibPortleafVersionEntry ::=
		SEQUENCE {
			mibPortVersionSerialNumber		INTEGER,
			mibPortVersionMIBVersion			INTEGER,
			mibPortVersionMIBOID		OBJECT IDENTIFIER
		}

	mibPortVersionSerialNumber		OBJECT-TYPE
		SYNTAX		INTEGER
		ACCESS		read-only
		STATUS		mandatory
		DESCRIPTION
			"Serial Number of the DKC."
		::= { mibPortleafVersionEntry 1 }

	mibPortVersionMIBVersion			OBJECT-TYPE
		SYNTAX		INTEGER
		ACCESS		read-only
		STATUS		mandatory
		DESCRIPTION
			"Version Number."
		::= { mibPortleafVersionEntry 2 }

	mibPortVersionMIBOID		OBJECT-TYPE
		SYNTAX		OBJECT IDENTIFIER
		ACCESS		read-only
		STATUS		mandatory
		DESCRIPTION
			"OID."
		::= { mibPortleafVersionEntry 3 }


--
-- Path MIB Version data
--

	mibPathLeafVersionTable		OBJECT-TYPE
		SYNTAX		SEQUENCE OF MibPathLeafVersionEntry
		ACCESS		not-accessible 
		STATUS		mandatory
		DESCRIPTION
			"LU Path MIB Version information."
		::= { mibLuLeafVersion 2 }

	mibPathLeafVersionEntry		OBJECT-TYPE
		SYNTAX		MibPathLeafVersionEntry
		ACCESS		not-accessible
		STATUS		mandatory
		DESCRIPTION
			"Entry of LU Path MIB Version."
		INDEX {
			mibPathVersionSerialNumber
		}
		::= { mibPathLeafVersionTable 1 }

	MibPathLeafVersionEntry ::=
		SEQUENCE {
			mibPathVersionSerialNumber	INTEGER,
			mibPathVersionMIBVersion		INTEGER,
			mibPathVersionMIBOID		OBJECT IDENTIFIER
		}

	mibPathVersionSerialNumber	OBJECT-TYPE
		SYNTAX		INTEGER
		ACCESS		read-only
		STATUS		mandatory
		DESCRIPTION
			"Serial Number of the DKC."
		::= { mibPathLeafVersionEntry 1 }

	mibPathVersionMIBVersion	OBJECT-TYPE
		SYNTAX		INTEGER
		ACCESS		read-only
		STATUS		mandatory
		DESCRIPTION
			"Version Number."
		::= { mibPathLeafVersionEntry 2 }

	mibPathVersionMIBOID		OBJECT-TYPE
		SYNTAX		OBJECT IDENTIFIER 
		ACCESS		read-write
		STATUS		mandatory
		DESCRIPTION
			"OID."
		::= { mibPathLeafVersionEntry 3 }

	

--
-- LUSE MIB Version information
--

	mibLuseLeafVersionTable		OBJECT-TYPE
		SYNTAX		SEQUENCE OF MibLuseLeafVersionEntry
		ACCESS		not-accessible 
		STATUS		mandatory
		DESCRIPTION
			"LUSE MIB Version information."
		::= { mibLuLeafVersion 3 }

	mibLuseLeafVersionEntry		OBJECT-TYPE
		SYNTAX		MibLuseLeafVersionEntry
		ACCESS		not-accessible
		STATUS		mandatory
		DESCRIPTION
			"Entry of LUSE MIB Version."
		INDEX {
			mibLuseVersionSerialNumber
		}
		::= { mibLuseLeafVersionTable 1 }

	MibLuseLeafVersionEntry ::=
		SEQUENCE {
			mibLuseVersionSerialNumber	INTEGER,
			mibLuseVersionMIBVersion		INTEGER,
			mibLuseVersionMIBOID		OBJECT IDENTIFIER
		}

	mibLuseVersionSerialNumber	OBJECT-TYPE
		SYNTAX		INTEGER
		ACCESS		read-only
		STATUS		mandatory
		DESCRIPTION
			"Serial Number of the DKC."
		::= { mibLuseLeafVersionEntry 1 }

	mibLuseVersionMIBVersion		OBJECT-TYPE
		SYNTAX		INTEGER
		ACCESS		read-only
		STATUS		mandatory
		DESCRIPTION
			"Version Number."
		::= { mibLuseLeafVersionEntry 2 }

	mibLuseVersionMIBOID		OBJECT-TYPE
		SYNTAX		OBJECT IDENTIFIER
		ACCESS		read-write
		STATUS		mandatory
		DESCRIPTION
			"OID."
		::= { mibLuseLeafVersionEntry 3 }


	

--
-- LUN Security MIB Version information
--

	mibLunsLeafVersionTable		OBJECT-TYPE
		SYNTAX		SEQUENCE OF MibLunsLeafVersionEntry
		ACCESS		not-accessible 
		STATUS		mandatory
		DESCRIPTION
			"LUN Security MIB Version information."
		::= { mibLuLeafVersion 4 }

	mibLunsLeafVersionEntry		OBJECT-TYPE
		SYNTAX		MibLunsLeafVersionEntry
		ACCESS		not-accessible
		STATUS		mandatory
		DESCRIPTION
			"Entry of LUN Security MIB Version."
		INDEX {
			mibLunsVersionSerialNumber
		}
		::= { mibLunsLeafVersionTable 1 }

	MibLunsLeafVersionEntry ::=
		SEQUENCE {
			mibLunsVersionSerialNumber	INTEGER,
			mibLunsVersionMIBVersion		INTEGER,
			mibLunsVersionMIBOID		OBJECT IDENTIFIER
		}

	mibLunsVersionSerialNumber	OBJECT-TYPE
		SYNTAX		INTEGER
		ACCESS		read-only
		STATUS		mandatory
		DESCRIPTION
			"Serial Number of the DKC."
		::= { mibLunsLeafVersionEntry 1 }

	mibLunsVersionMIBVersion	OBJECT-TYPE
		SYNTAX		INTEGER
		ACCESS		read-only
		STATUS		mandatory
		DESCRIPTION
			"Version Number."
		::= { mibLunsLeafVersionEntry 2 }

	mibLunsVersionMIBOID		OBJECT-TYPE
		SYNTAX		OBJECT IDENTIFIER
		ACCESS		read-write
		STATUS		mandatory
		DESCRIPTION
			"OID."
		::= { mibLunsLeafVersionEntry 3 }


--
-- DCR  MIB Version data
--

	mibDcrLeafVersionTable	OBJECT-TYPE
		SYNTAX		SEQUENCE OF MibDcrLeafVersionEntry
		ACCESS		not-accessible 
		STATUS		mandatory
		DESCRIPTION
			"DCR MIB Version information."
		::= { raidExMibVersionManagement 12 }

	mibDcrLeafVersionEntry		OBJECT-TYPE
		SYNTAX		MibDcrLeafVersionEntry
		ACCESS		not-accessible
		STATUS		mandatory
		DESCRIPTION
			"Entry of DCR MIB Version."
		INDEX {
			mibDcrVersionSerialNumber
		}
		::= { mibDcrLeafVersionTable 1 }

	MibDcrLeafVersionEntry ::=
		SEQUENCE {
			mibDcrVersionSerialNumber	INTEGER,
			mibDcrVersionMIBVersion		INTEGER,
			mibDcrVersionMIBOID		OBJECT IDENTIFIER
		}

	mibDcrVersionSerialNumber		OBJECT-TYPE
		SYNTAX		INTEGER
		ACCESS		read-only
		STATUS		mandatory
		DESCRIPTION
			"Serial Number of the DKC."
		::= { mibDcrLeafVersionEntry 1 }

	mibDcrVersionMIBVersion			OBJECT-TYPE
		SYNTAX		INTEGER
		ACCESS		read-only
		STATUS		mandatory
		DESCRIPTION
			"Version Number."
		::= { mibDcrLeafVersionEntry 2 }

	mibDcrVersionMIBOID		OBJECT-TYPE
		SYNTAX		OBJECT IDENTIFIER
		ACCESS		read-only
		STATUS		mandatory
		DESCRIPTION
			" OID."
		::= { mibDcrLeafVersionEntry 3 }



--
-- CVS  MIB Version data
--

	mibCvsLeafVersionTable	OBJECT-TYPE
		SYNTAX		SEQUENCE OF MibCvsLeafVersionEntry
		ACCESS		not-accessible 
		STATUS		mandatory
		DESCRIPTION
			"CVS MIB Version information."
		::= { raidExMibVersionManagement 13 }

	mibCvsLeafVersionEntry		OBJECT-TYPE
		SYNTAX		MibCvsLeafVersionEntry
		ACCESS		not-accessible
		STATUS		mandatory
		DESCRIPTION
			"Entry of CVS MIB Version."
		INDEX {
			mibCvsLeafVersionSerialNumber
		}
		::= { mibCvsLeafVersionTable 1 }

	MibCvsLeafVersionEntry ::=
		SEQUENCE {
			mibCvsLeafVersionSerialNumber	INTEGER,
			mibCvsLeafVersionMIBVersion		INTEGER,
			mibCvsLeafVersionMIBOID		OBJECT IDENTIFIER
		}

	mibCvsLeafVersionSerialNumber		OBJECT-TYPE
		SYNTAX		INTEGER
		ACCESS		read-only
		STATUS		mandatory
		DESCRIPTION
			"Serial Number of the DKC."
		::= { mibCvsLeafVersionEntry 1 }

	mibCvsLeafVersionMIBVersion			OBJECT-TYPE
		SYNTAX		INTEGER
		ACCESS		read-only
		STATUS		mandatory
		DESCRIPTION
			"Version Number."
		::= { mibCvsLeafVersionEntry 2 }

	mibCvsLeafVersionMIBOID		OBJECT-TYPE
		SYNTAX		OBJECT IDENTIFIER
		ACCESS		read-only
		STATUS		mandatory
		DESCRIPTION
			" OID."
		::= { mibCvsLeafVersionEntry 3 }


--
-- SSID  MIB Version data
--

	mibSsidLeafVersionTable	OBJECT-TYPE
		SYNTAX		SEQUENCE OF MibSsidLeafVersionEntry
		ACCESS		not-accessible 
		STATUS		mandatory
		DESCRIPTION
			"SSID MIB Version information."
		::= { raidExMibVersionManagement 14 }

	mibSsidLeafVersionEntry		OBJECT-TYPE
		SYNTAX		MibSsidLeafVersionEntry
		ACCESS		not-accessible
		STATUS		mandatory
		DESCRIPTION
			"Entry of SSID MIB Version."
		INDEX {
			mibSsidVersionSerialNumber
		}
		::= { mibSsidLeafVersionTable 1 }

	MibSsidLeafVersionEntry ::=
		SEQUENCE {
			mibSsidVersionSerialNumber	INTEGER,
			mibSsidVersionMIBVersion		INTEGER,
			mibSsidVersionMIBOID		OBJECT IDENTIFIER
		}

	mibSsidVersionSerialNumber		OBJECT-TYPE
		SYNTAX		INTEGER
		ACCESS		read-only
		STATUS		mandatory
		DESCRIPTION
			"Serial Number of the DKC."
		::= { mibSsidLeafVersionEntry 1 }

	mibSsidVersionMIBVersion		OBJECT-TYPE
		SYNTAX		INTEGER
		ACCESS		read-only
		STATUS		mandatory
		DESCRIPTION
			"Version Number."
		::= { mibSsidLeafVersionEntry 2 }

	mibSsidVersionMIBOID			OBJECT-TYPE
		SYNTAX		OBJECT IDENTIFIER
		ACCESS		read-only
		STATUS		mandatory
		DESCRIPTION
			" OID."
		::= { mibSsidLeafVersionEntry 3 }



--
-- Environment  MIB Version data
--

	mibEnvLeafVersionTable	OBJECT-TYPE
		SYNTAX		SEQUENCE OF MibEnvLeafVersionEntry
		ACCESS		not-accessible 
		STATUS		mandatory
		DESCRIPTION
			"Environment MIB Version information."
		::= { raidExMibVersionManagement 15 }

	mibEnvLeafVersionEntry		OBJECT-TYPE
		SYNTAX		MibEnvLeafVersionEntry
		ACCESS		not-accessible
		STATUS		mandatory
		DESCRIPTION
			"Entry of Environment MIB Version."
		INDEX {
			mibEnvVersionSerialNumber
		}
		::= { mibEnvLeafVersionTable 1 }

	MibEnvLeafVersionEntry ::=
		SEQUENCE {
			mibEnvVersionSerialNumber	INTEGER,
			mibEnvVersionMIBVersion		INTEGER,
			mibEnvVersionMIBOID		OBJECT IDENTIFIER
		}

	mibEnvVersionSerialNumber		OBJECT-TYPE
		SYNTAX		INTEGER
		ACCESS		read-only
		STATUS		mandatory
		DESCRIPTION
			"Serial Number of the DKC."
		::= { mibEnvLeafVersionEntry 1 }

	mibEnvVersionMIBVersion			OBJECT-TYPE
		SYNTAX		INTEGER
		ACCESS		read-only
		STATUS		mandatory
		DESCRIPTION
			"Version Number."
		::= { mibEnvLeafVersionEntry 2 }

	mibEnvVersionMIBOID		OBJECT-TYPE
		SYNTAX		OBJECT IDENTIFIER
		ACCESS		read-only
		STATUS		mandatory
		DESCRIPTION
			" OID."
		::= { mibEnvLeafVersionEntry 3 }



--
-- CHA  MIB Version data
--

	mibChaLeafVersionTable	OBJECT-TYPE
		SYNTAX		SEQUENCE OF MibChaLeafVersionEntry
		ACCESS		not-accessible 
		STATUS		mandatory
		DESCRIPTION
			"CHA MIB Version information."
		::= { raidExMibVersionManagement 16 }

	mibChaLeafVersionEntry		OBJECT-TYPE
		SYNTAX		MibChaLeafVersionEntry
		ACCESS		not-accessible
		STATUS		mandatory
		DESCRIPTION
			"Entry of CHA MIB Version."
		INDEX {
			mibChaVersionSerialNumber
		}
		::= { mibChaLeafVersionTable 1 }

	MibChaLeafVersionEntry ::=
		SEQUENCE {
			mibChaVersionSerialNumber	INTEGER,
			mibChaVersionMIBVersion		INTEGER,
			mibChaVersionMIBOID		OBJECT IDENTIFIER
		}

	mibChaVersionSerialNumber		OBJECT-TYPE
		SYNTAX		INTEGER
		ACCESS		read-only
		STATUS		mandatory
		DESCRIPTION
			"Serial Number of the DKC."
		::= { mibChaLeafVersionEntry 1 }

	mibChaVersionMIBVersion			OBJECT-TYPE
		SYNTAX		INTEGER
		ACCESS		read-only
		STATUS		mandatory
		DESCRIPTION
			"Version Number."
		::= { mibChaLeafVersionEntry 2 }

	mibChaVersionMIBOID			OBJECT-TYPE
		SYNTAX		OBJECT IDENTIFIER
		ACCESS		read-only
		STATUS		mandatory
		DESCRIPTION
			" OID."
		::= { mibChaLeafVersionEntry 3 }


--
-- DKA MIB Version data
--

	mibDkaLeafVersionTable	OBJECT-TYPE
		SYNTAX		SEQUENCE OF MibDkaLeafVersionEntry
		ACCESS		not-accessible 
		STATUS		mandatory
		DESCRIPTION
			"DKA MIB Version information."
		::= { raidExMibVersionManagement 17 }

	mibDkaLeafVersionEntry		OBJECT-TYPE
		SYNTAX		MibDkaLeafVersionEntry
		ACCESS		not-accessible
		STATUS		mandatory
		DESCRIPTION
			"Entry of DKA MIB Version."
		INDEX {
			mibDkaVersionSerialNumber
		}
		::= { mibDkaLeafVersionTable 1 }

	MibDkaLeafVersionEntry ::=
		SEQUENCE {
			mibDkaVersionSerialNumber	INTEGER,
			mibDkaVersionMIBVersion		INTEGER,
			mibDkaVersionMIBOID		OBJECT IDENTIFIER
		}

	mibDkaVersionSerialNumber		OBJECT-TYPE
		SYNTAX		INTEGER
		ACCESS		read-only
		STATUS		mandatory
		DESCRIPTION
			"Serial Number of the DKC."
		::= { mibDkaLeafVersionEntry 1 }

	mibDkaVersionMIBVersion			OBJECT-TYPE
		SYNTAX		INTEGER
		ACCESS		read-only
		STATUS		mandatory
		DESCRIPTION
			"Version Number."
		::= { mibDkaLeafVersionEntry 2 }

	mibDkaVersionMIBOID		OBJECT-TYPE
		SYNTAX		OBJECT IDENTIFIER
		ACCESS		read-only
		STATUS		mandatory
		DESCRIPTION
			" OID."
		::= { mibDkaLeafVersionEntry 3 }


--
-- PG MIB Version data
--

	mibPgLeafVersionTable	OBJECT-TYPE
		SYNTAX		SEQUENCE OF MibPgLeafVersionEntry
		ACCESS		not-accessible 
		STATUS		mandatory
		DESCRIPTION
			"PG MIB Version information."
		::= { raidExMibVersionManagement 18 }

	mibPgLeafVersionEntry		OBJECT-TYPE
		SYNTAX		MibPgLeafVersionEntry
		ACCESS		not-accessible
		STATUS		mandatory
		DESCRIPTION
			"Entry of PG MIB Version."
		INDEX {
			mibPgVersionSerialNumber
		}
		::= { mibPgLeafVersionTable 1 }

	MibPgLeafVersionEntry ::=
		SEQUENCE {
			mibPgVersionSerialNumber		INTEGER,
			mibPgVersionMIBVersion		INTEGER,
			mibPgVersionMIBOID		OBJECT IDENTIFIER
		}

	mibPgVersionSerialNumber		OBJECT-TYPE
		SYNTAX		INTEGER
		ACCESS		read-only
		STATUS		mandatory
		DESCRIPTION
			"Serial Number of the DKC."
		::= { mibPgLeafVersionEntry 1 }

	mibPgVersionMIBVersion			OBJECT-TYPE
		SYNTAX		INTEGER
		ACCESS		read-only
		STATUS		mandatory
		DESCRIPTION
			"Version Number."
		::= { mibPgLeafVersionEntry 2 }

	mibPgVersionMIBOID		OBJECT-TYPE
		SYNTAX		OBJECT IDENTIFIER
		ACCESS		read-only
		STATUS		mandatory
		DESCRIPTION
			" OID."
		::= { mibPgLeafVersionEntry 3 }


--
-- HIHSM MIB Version data
--

	mibHihsmLeafVersionTable	OBJECT-TYPE
		SYNTAX		SEQUENCE OF MibHihsmLeafVersionEntry
		ACCESS		not-accessible 
		STATUS		mandatory
		DESCRIPTION
			"HIHSM MIB Version information."
		::= { raidExMibVersionManagement 20 }

	mibHihsmLeafVersionEntry		OBJECT-TYPE
		SYNTAX		MibHihsmLeafVersionEntry
		ACCESS		not-accessible
		STATUS		mandatory
		DESCRIPTION
			"Entry of HIHSM MIB Version."
		INDEX {
			mibHihsmVersionSerialNumber
		}
		::= { mibHihsmLeafVersionTable 1 }

	MibHihsmLeafVersionEntry ::=
		SEQUENCE {
			mibHihsmVersionSerialNumber	INTEGER,
			mibHihsmVersionMIBVersion	INTEGER,
			mibHihsmVersionMIBOID		OBJECT IDENTIFIER
		}

	mibHihsmVersionSerialNumber		OBJECT-TYPE
		SYNTAX		INTEGER
		ACCESS		read-only
		STATUS		mandatory
		DESCRIPTION
			"Serial Number of the DKC."
		::= { mibHihsmLeafVersionEntry 1 }

	mibHihsmVersionMIBVersion		OBJECT-TYPE
		SYNTAX		INTEGER
		ACCESS		read-only
		STATUS		mandatory
		DESCRIPTION
			"Version Number."
		::= { mibHihsmLeafVersionEntry 2 }

	mibHihsmVersionMIBOID			OBJECT-TYPE
		SYNTAX		OBJECT IDENTIFIER
		ACCESS		read-only
		STATUS		mandatory
		DESCRIPTION
			" OID."
		::= { mibHihsmLeafVersionEntry 3 }


--
-- CSW MIB Version data
--

	mibCswLeafVersionTable	OBJECT-TYPE
		SYNTAX		SEQUENCE OF MibCswLeafVersionEntry
		ACCESS		not-accessible 
		STATUS		mandatory
		DESCRIPTION
			"CSW MIB Version information."
		::= { raidExMibVersionManagement 21 }

	mibCswLeafVersionEntry		OBJECT-TYPE
		SYNTAX		MibCswLeafVersionEntry
		ACCESS		not-accessible
		STATUS		mandatory
		DESCRIPTION
			"Entry of CSW MIB Version."
		INDEX {
			mibCswVersionSerialNumber
		}
		::= { mibCswLeafVersionTable 1 }

	MibCswLeafVersionEntry ::=
		SEQUENCE {
			mibCswVersionSerialNumber	INTEGER,
			mibCswVersionMIBVersion		INTEGER,
			mibCswVersionMIBOID		OBJECT IDENTIFIER
		}

	mibCswVersionSerialNumber		OBJECT-TYPE
		SYNTAX		INTEGER
		ACCESS		read-only
		STATUS		mandatory
		DESCRIPTION
			"Serial Number of the DKC."
		::= { mibCswLeafVersionEntry 1 }

	mibCswVersionMIBVersion			OBJECT-TYPE
		SYNTAX		INTEGER
		ACCESS		read-only
		STATUS		mandatory
		DESCRIPTION
			"Version Number."
		::= { mibCswLeafVersionEntry 2 }

	mibCswVersionMIBOID			OBJECT-TYPE
		SYNTAX		OBJECT IDENTIFIER
		ACCESS		read-only
		STATUS		mandatory
		DESCRIPTION
			" OID."
		::= { mibCswLeafVersionEntry 3 }



--
-- SM MIB Version data
--

	mibSmLeafVersionTable	OBJECT-TYPE
		SYNTAX		SEQUENCE OF MibSmLeafVersionEntry
		ACCESS		not-accessible 
		STATUS		mandatory
		DESCRIPTION
			"SM MIB Version information."
		::= { raidExMibVersionManagement 22 }

	mibSmLeafVersionEntry		OBJECT-TYPE
		SYNTAX		MibSmLeafVersionEntry
		ACCESS		not-accessible
		STATUS		mandatory
		DESCRIPTION
			"Entry of SM MIB Version."
		INDEX {
			mibSmLeafVersionSerialNumber
		}
		::= { mibSmLeafVersionTable 1 }

	MibSmLeafVersionEntry ::=
		SEQUENCE {
			mibSmLeafVersionSerialNumber		INTEGER,
			mibSmLeafVersionMIBVersion		INTEGER,
			mibSmLeafVersionMIBOID		OBJECT IDENTIFIER
		}

	mibSmLeafVersionSerialNumber			OBJECT-TYPE
		SYNTAX		INTEGER
		ACCESS		read-only
		STATUS		mandatory
		DESCRIPTION
			"Serial Number of the DKC."
		::= { mibSmLeafVersionEntry 1 }

	mibSmLeafVersionMIBVersion			OBJECT-TYPE
		SYNTAX		INTEGER
		ACCESS		read-only
		STATUS		mandatory
		DESCRIPTION
			"Version Number."
		::= { mibSmLeafVersionEntry 2 }

	mibSmLeafVersionMIBOID		OBJECT-TYPE
		SYNTAX		OBJECT IDENTIFIER
		ACCESS		read-only
		STATUS		mandatory
		DESCRIPTION
			" OID."
		::= { mibSmLeafVersionEntry 3 }

--
-- CM MIB Version data
--

	mibCmLeafVersionTable	OBJECT-TYPE
		SYNTAX		SEQUENCE OF MibCmLeafVersionEntry
		ACCESS		not-accessible 
		STATUS		mandatory
		DESCRIPTION
			"CM MIB Version information."
		::= { raidExMibVersionManagement 23 }

	mibCmLeafVersionEntry		OBJECT-TYPE
		SYNTAX		MibCmLeafVersionEntry
		ACCESS		not-accessible
		STATUS		mandatory
		DESCRIPTION
			"Entry of CM MIB Version."
		INDEX {
			mibCmVersionSerialNumber
		}
		::= { mibCmLeafVersionTable 1 }

	MibCmLeafVersionEntry ::=
		SEQUENCE {
			mibCmVersionSerialNumber		INTEGER,
			mibCmVersionMIBVersion		INTEGER,
			mibCmVersionMIBOID		OBJECT IDENTIFIER
		}

	mibCmVersionSerialNumber		OBJECT-TYPE
		SYNTAX		INTEGER
		ACCESS		read-only
		STATUS		mandatory
		DESCRIPTION
			"Serial Number of the DKC."
		::= { mibCmLeafVersionEntry 1 }

	mibCmVersionMIBVersion		OBJECT-TYPE
		SYNTAX		INTEGER
		ACCESS		read-only
		STATUS		mandatory
		DESCRIPTION
			"Version Number."
		::= { mibCmLeafVersionEntry 2 }

	mibCmVersionMIBOID		OBJECT-TYPE
		SYNTAX		OBJECT IDENTIFIER
		ACCESS		read-only
		STATUS		mandatory
		DESCRIPTION
			" OID."
		::= { mibCmLeafVersionEntry 3 }


--
-- PortControl MIB Version data
--

	mibPortControlLeafVersionTable	OBJECT-TYPE
		SYNTAX		SEQUENCE OF MibPortControlLeafVersionEntry
		ACCESS		not-accessible 
		STATUS		mandatory
		DESCRIPTION
			"PortControl MIB Version information."
		::= { raidExMibVersionManagement 24 }

	mibPortControlLeafVersionEntry		OBJECT-TYPE
		SYNTAX		MibPortControlLeafVersionEntry
		ACCESS		not-accessible
		STATUS		mandatory
		DESCRIPTION
			"Entry of PortControl MIB Version."
		INDEX {
			mibPortControlVersionSerialNumber
		}
		::= { mibPortControlLeafVersionTable 1 }

	MibPortControlLeafVersionEntry ::=
		SEQUENCE {
		mibPortControlVersionSerialNumber	INTEGER,
		mibPortControlVersionMIBVersion		INTEGER,
		mibPortControlVersionMIBOID		OBJECT IDENTIFIER
		}

	mibPortControlVersionSerialNumber		OBJECT-TYPE
		SYNTAX		INTEGER
		ACCESS		read-only
		STATUS		mandatory
		DESCRIPTION
			"Serial Number of the DKC."
		::= { mibPortControlLeafVersionEntry 1 }

	mibPortControlVersionMIBVersion			OBJECT-TYPE
		SYNTAX		INTEGER
		ACCESS		read-only
		STATUS		mandatory
		DESCRIPTION
			"Version Number."
		::= { mibPortControlLeafVersionEntry 2 }

	mibPortControlVersionMIBOID		OBJECT-TYPE
		SYNTAX		OBJECT IDENTIFIER
		ACCESS		read-only
		STATUS		mandatory
		DESCRIPTION
			" OID."
		::= { mibPortControlLeafVersionEntry 3 }



--
-- Trap definition
--

	eventTrapSerialNumber		OBJECT-TYPE
		SYNTAX			INTEGER
		ACCESS			read-only
		STATUS			mandatory
		DESCRIPTION
			"Serial Number of RAID300 where an error occurred."
		::= { raidRoot 1 }

	eventTrapNickname			OBJECT-TYPE
		SYNTAX			DisplayString
		ACCESS			read-only
		STATUS			mandatory
		DESCRIPTION
			"Nickname of RAID300 where an error occurred."
		::= { raidRoot 2 }

	eventTrapREFCODE 			OBJECT-TYPE
		SYNTAX			DisplayString
		ACCESS			read-only
		STATUS			mandatory
		DESCRIPTION
			"Error reference code (22nd,23rd,13rd byte in SIM)."
		::= { raidRoot 3 }

	eventTrapPartsID			OBJECT-TYPE
		SYNTAX			INTEGER
		ACCESS			read-only
		STATUS			mandatory
		DESCRIPTION
			"
			Object identifier that does not include the component index where an error occurred.
			(Example) DKC processor error:
			1.3.6.1.4.1.116.5.11.4.1.1.6.1.2.
		"
		::= { raidRoot 4 }

--
-- Command result
--

	raidEventCommandTable	OBJECT-TYPE
		SYNTAX		SEQUENCE OF RaidEventCommandEntry
		ACCESS		not-accessible 
		STATUS		mandatory
		DESCRIPTION
			"Command Response from the DKC."
		::= { raidRoot 9 }

	raidEventCommandEntry		OBJECT-TYPE
		SYNTAX		RaidEventCommandEntry
		ACCESS		not-accessible
		STATUS		mandatory
		DESCRIPTION
			"Entry of command."
		INDEX {
			trapCommandSerialNumber
		}
		::= { raidEventCommandTable 1 }

	RaidEventCommandEntry ::=
		SEQUENCE {
			trapCommandSerialNumber	INTEGER,
			trapCommandManagerName	DisplayString (SIZE(0..31)),
			trapCommandKind		INTEGER,
			trapCommandStatus	INTEGER
		}

	trapCommandSerialNumber	OBJECT-TYPE
		SYNTAX		INTEGER
		ACCESS		read-only
		STATUS		mandatory
		DESCRIPTION
			"Serial Number of the DKC."
		::= { raidEventCommandEntry 1 }

	trapCommandManagerName	OBJECT-TYPE
		SYNTAX		DisplayString (SIZE(0..31))
		ACCESS		read-only
		STATUS		mandatory
		DESCRIPTION	
			"Name of manager who has lock."
		::= { raidEventCommandEntry 2 }

	trapCommandKind		OBJECT-TYPE
		SYNTAX		INTEGER
		ACCESS		read-only
		STATUS		mandatory
		DESCRIPTION	
			"Request Command.

			Value	Mean
			1	Request to refresh the configuration information.
			2	Request to set the LUNM/LUSE configuration.
			3	Request to set the LUN Security configuration.
			4	Request to get the exclusive lock.
			5	Request to free the exclusive lock.
			6	Request to check the health.
			7	Request to set the CVS configuration.
			8	Request to set the DCR configuration.
			9	Request to set the HIHSM configuration.
			"
		::= { raidEventCommandEntry 3 }

	trapCommandStatus		OBJECT-TYPE
		SYNTAX		INTEGER
		ACCESS		read-only
		STATUS		mandatory
		DESCRIPTION	
			"Status of Requested Command.

			Value	Mean
			1	Normal state. (The command ended normally.)
			2	Command execution request. (now executing.)
			other	Abnormal state (Error occurred). 
			"
		::= { raidEventCommandEntry 4 }

	raidEventUserAcute	TRAP-TYPE
		ENTERPRISE	raidRoot
		VARIABLES	{
			eventTrapSerialNumber,
			eventTrapNickname,
			eventTrapREFCODE,
			eventTrapPartsID
		}
		DESCRIPTION	
			"The impact of this event on the subsystem is acute."
		::= 1

	raidEventUserSerious	TRAP-TYPE
		ENTERPRISE	raidRoot
		VARIABLES	{
			eventTrapSerialNumber,
			eventTrapNickname,
			eventTrapREFCODE,
			eventTrapPartsID
		}
		DESCRIPTION	
			"The impact of this event on the subsystem is serious."
		::= 2

	raidEventUserModerate	TRAP-TYPE
		ENTERPRISE	raidRoot
		VARIABLES	{
			eventTrapSerialNumber,
			eventTrapNickname,
			eventTrapREFCODE,
			eventTrapPartsID
		}
		DESCRIPTION	
			"The impact of this event on the subsystem is moderate."
		::= 3

	raidEventUserService	TRAP-TYPE
		ENTERPRISE	raidRoot
		VARIABLES	{
			eventTrapSerialNumber,
			eventTrapNickname,
			eventTrapREFCODE,
			eventTrapPartsID
		}
		DESCRIPTION	
			"The impact of this event on the subsystem is low."
		::= 4

	raidEventCommandFinished	TRAP-TYPE
		ENTERPRISE	raidRoot
		VARIABLES	{
			trapCommandSerialNumber,
			trapCommandManagerName,
			trapCommandKind,
			trapCommandStatus
		}
		DESCRIPTION
			"Required command was finished."
		::= 100

END
