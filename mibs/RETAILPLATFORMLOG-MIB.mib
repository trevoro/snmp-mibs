RETAILPLATFORMLOG-MIB DEFINITIONS ::= BEGIN

-- NCR Retail Platform SNMP Agent, Log Module MIB definitions
-- Copyright (C) 2000 NCR Corporation, All rights reserved.
-- Version 01.00.00.005
 
IMPORTS
		enterprises
			FROM RFC1155-SMI
		OBJECT-TYPE
			FROM RFC-1212
		DisplayString
			FROM RFC1213-MIB;
 
		ncr            OBJECT IDENTIFIER ::= { enterprises 191 }
		ncr-products   OBJECT IDENTIFIER ::= { ncr 1 }
		log            OBJECT IDENTIFIER ::= { ncr-products 33 }

		NTSeverity ::= INTEGER { error(1), warning(2), information(4), auditSuccess(8), auditFailure(16) }

-- log MIB

		logSysLog	OBJECT IDENTIFIER ::= { log 1 }

		logSysLogTable	OBJECT-TYPE
				SYNTAX SEQUENCE OF LogSysLogEntry
				ACCESS	not-accessible
				STATUS	mandatory
				DESCRIPTION
					"The System Log."
				::= { logSysLog 1 }

		logSysLogEntry OBJECT-TYPE
				SYNTAX	LogSysLogEntry
				ACCESS	not-accessible
				STATUS	mandatory
				DESCRIPTION
					"An entry in the System Log."
				INDEX	{ logSysLogIndex }
				::= { logSysLogTable 1 }

		LogSysLogEntry ::=
				SEQUENCE	{
						logSysLogIndex
								INTEGER,
						logSysLogDate
								OCTET STRING,
						logSysLogTime
								OCTET STRING,
						logSysLogUser
								OCTET STRING,
						logSysLogComputer
								OCTET STRING,
						logSysLogEventID
								INTEGER,
						logSysLogSource
								OCTET STRING,
						logSysLogType
								NTSeverity,
						logSysLogCategory
								OCTET STRING,
						logSysLogDescription
								OCTET STRING,
						logSysLogData
								OCTET STRING
					}

		logSysLogIndex		OBJECT-TYPE
				SYNTAX	INTEGER
				ACCESS	read-only
				STATUS	mandatory
				DESCRIPTION
					"The sequence number of the event."
				::= { logSysLogEntry 1 }

		logSysLogDate		OBJECT-TYPE
				SYNTAX	OCTET STRING
				ACCESS	read-only
				STATUS	mandatory
				DESCRIPTION
					"The date the event was logged at the terminal."
				::= { logSysLogEntry 2 }

		logSysLogTime		OBJECT-TYPE
				SYNTAX	OCTET STRING
				ACCESS	read-only
				STATUS	mandatory
				DESCRIPTION
					"The time of day the event was logged at the terminal."
				::= { logSysLogEntry 3 }

		logSysLogUser		OBJECT-TYPE
				SYNTAX	OCTET STRING
				ACCESS	read-only
				STATUS	mandatory
				DESCRIPTION
					"The user name in context of which the
					application logging the event is running."
				::= { logSysLogEntry 4 }

		logSysLogComputer	OBJECT-TYPE
				SYNTAX	OCTET STRING
				ACCESS	read-only
				STATUS	mandatory
				DESCRIPTION
					"The (NetBIOS/Windows computer) name of the
					terminal where the event was logged."
				::= { logSysLogEntry 5 }

		logSysLogEventID	OBJECT-TYPE
				SYNTAX	INTEGER
				ACCESS	read-only
				STATUS	mandatory
				DESCRIPTION
					"A numeric identification of the event."
				::= { logSysLogEntry 6 }

		logSysLogSource		OBJECT-TYPE
				SYNTAX	OCTET STRING
				ACCESS	read-only
				STATUS	mandatory
				DESCRIPTION
					"The name of the application/service that logged
					the event."
				::= { logSysLogEntry 7 }

		logSysLogType		OBJECT-TYPE
				SYNTAX	NTSeverity
				ACCESS	read-only
				STATUS	mandatory
				DESCRIPTION
					"The type (severity) of the event."
				::= { logSysLogEntry 8 }

		logSysLogCategory	OBJECT-TYPE
				SYNTAX	OCTET STRING
				ACCESS	read-only
				STATUS	mandatory
				DESCRIPTION
					"The event category."
				::= { logSysLogEntry 9 }

		logSysLogDescription	OBJECT-TYPE
				SYNTAX	OCTET STRING
				ACCESS	read-only
				STATUS	mandatory
				DESCRIPTION
					"Description of the event."
				::= { logSysLogEntry 10 }

		logSysLogData	OBJECT-TYPE
				SYNTAX	OCTET STRING
				ACCESS	read-only
				STATUS	mandatory
				DESCRIPTION
					"Raw data associated with the event.
					The octet string returned will be formatted with
					two-bytes of length information preceding
					the data."
				::= { logSysLogEntry 11 }

		logSysLogSize		OBJECT-TYPE
				SYNTAX	INTEGER
				ACCESS	read-only
				STATUS	mandatory
				DESCRIPTION
					"Number of entries in the system log."
				::= { logSysLog 2 }

		logSysLogReqSize	OBJECT-TYPE
				SYNTAX	INTEGER
				ACCESS	read-write
				STATUS	mandatory
				DESCRIPTION
					"The number of events to return in the logSysLog
					table (default: 50). To change the default, the desired
					number of event log entries can be written to this
					variable."
				::= { logSysLog 3 }

		logSecLog	OBJECT IDENTIFIER ::= { log 2 }

		logSecLogTable	OBJECT-TYPE
				SYNTAX SEQUENCE OF LogSecLogEntry
				ACCESS	not-accessible
				STATUS	mandatory
				DESCRIPTION
					"The Security Log."
				::= { logSecLog 1 }

		logSecLogEntry OBJECT-TYPE
				SYNTAX	LogSecLogEntry
				ACCESS	not-accessible
				STATUS	mandatory
				DESCRIPTION
					"An entry in the Security Log."
				INDEX	{ logSecLogIndex }
				::= { logSecLogTable 1 }

		LogSecLogEntry ::=
				SEQUENCE	{
						logSecLogIndex
								INTEGER,
						logSecLogDate
								OCTET STRING,
						logSecLogTime
								OCTET STRING,
						logSecLogUser
								OCTET STRING,
						logSecLogComputer
								OCTET STRING,
						logSecLogEventID
								INTEGER,
						logSecLogSource
								OCTET STRING,
						logSecLogType
								NTSeverity,
						logSecLogCategory
								OCTET STRING,
						logSecLogDescription
								OCTET STRING,
						logSecLogData
								OCTET STRING
					}

		logSecLogIndex		OBJECT-TYPE
				SYNTAX	INTEGER
				ACCESS	read-only
				STATUS	mandatory
				DESCRIPTION
					"The sequence number of the event."
				::= { logSecLogEntry 1 }

		logSecLogDate		OBJECT-TYPE
				SYNTAX	OCTET STRING
				ACCESS	read-only
				STATUS	mandatory
				DESCRIPTION
					"The date the event was logged at the terminal."
				::= { logSecLogEntry 2 }

		logSecLogTime		OBJECT-TYPE
				SYNTAX	OCTET STRING
				ACCESS	read-only
				STATUS	mandatory
				DESCRIPTION
					"The time of day the event was logged at the terminal."
				::= { logSecLogEntry 3 }

		logSecLogUser		OBJECT-TYPE
				SYNTAX	OCTET STRING
				ACCESS	read-only
				STATUS	mandatory
				DESCRIPTION
					"The user name in context of which the application
					logging the event is running."
				::= { logSecLogEntry 4 }

		logSecLogComputer	OBJECT-TYPE
				SYNTAX	OCTET STRING
				ACCESS	read-only
				STATUS	mandatory
				DESCRIPTION
					"The (NetBIOS/Windows computer) name of the terminal
					where the event was logged."
				::= { logSecLogEntry 5 }

		logSecLogEventID	OBJECT-TYPE
				SYNTAX	INTEGER
				ACCESS	read-only
				STATUS	mandatory
				DESCRIPTION
					"A numeric identification of the event."
				::= { logSecLogEntry 6 }

		logSecLogSource		OBJECT-TYPE
				SYNTAX	OCTET STRING
				ACCESS	read-only
				STATUS	mandatory
				DESCRIPTION
					"The name of the application/service that logged
					the event."
				::= { logSecLogEntry 7 }

		logSecLogType		OBJECT-TYPE
				SYNTAX	NTSeverity
				ACCESS	read-only
				STATUS	mandatory
				DESCRIPTION
					"The type (severity) of the event."
				::= { logSecLogEntry 8 }

		logSecLogCategory	OBJECT-TYPE
				SYNTAX	OCTET STRING
				ACCESS	read-only
				STATUS	mandatory
				DESCRIPTION
					"The event category."
				::= { logSecLogEntry 9 }

		logSecLogDescription	OBJECT-TYPE
				SYNTAX	OCTET STRING
				ACCESS	read-only
				STATUS	mandatory
				DESCRIPTION
					"Description of the event."
				::= { logSecLogEntry 10 }

		logSecLogData	OBJECT-TYPE
				SYNTAX	OCTET STRING
				ACCESS	read-only
				STATUS	mandatory
				DESCRIPTION
					"The raw data from the event message.
					The octet string returned will be formatted with
					two-bytes of length information preceding
					the data."
				::= { logSecLogEntry 11 }

		logSecLogSize		OBJECT-TYPE
				SYNTAX	INTEGER
				ACCESS	read-only
				STATUS	mandatory
				DESCRIPTION
					"Number of entries in the security log."
				::= { logSecLog 2 }

		logSecLogReqSize	OBJECT-TYPE
				SYNTAX	INTEGER
				ACCESS	read-write
				STATUS	mandatory
				DESCRIPTION
					"The number of events to return in the logSecLog table
					(default: 50). To change the default, he desired number
					of event log entries can be written to this variable. "
				::= { logSecLog 3 }

		logAppLog	OBJECT IDENTIFIER ::= { log 3 }

		logAppLogTable	OBJECT-TYPE
				SYNTAX SEQUENCE OF LogAppLogEntry
				ACCESS	not-accessible
				STATUS	mandatory
				DESCRIPTION
					"The Application Log."
				::= { logAppLog 1 }

		logAppLogEntry OBJECT-TYPE
				SYNTAX	LogAppLogEntry
				ACCESS	not-accessible
				STATUS	mandatory
				DESCRIPTION
					"An entry in the Application Log."
				INDEX	{ logAppLogIndex }
				::= { logAppLogTable 1 }

		LogAppLogEntry ::=
				SEQUENCE	{
						logAppLogIndex
								INTEGER,
						logAppLogDate
								OCTET STRING,
						logAppLogTime
								OCTET STRING,
						logAppLogUser
								OCTET STRING,
						logAppLogComputer
								OCTET STRING,
						logAppLogEventID
								INTEGER,
						logAppLogSource
								OCTET STRING,
						logAppLogType
								NTSeverity,
						logAppLogCategory
								OCTET STRING,
						logAppLogDescription
								OCTET STRING,
						logAppLogData
								OCTET STRING
					}

		logAppLogIndex		OBJECT-TYPE
				SYNTAX	INTEGER
				ACCESS	read-only
				STATUS	mandatory
				DESCRIPTION
					"The sequence number of the event."
				::= { logAppLogEntry 1 }

		logAppLogDate		OBJECT-TYPE
				SYNTAX	OCTET STRING
				ACCESS	read-only
				STATUS	mandatory
				DESCRIPTION
					"The date the event was logged at the Kiosk."
				::= { logAppLogEntry 2 }

		logAppLogTime		OBJECT-TYPE
				SYNTAX	OCTET STRING
				ACCESS	read-only
				STATUS	mandatory
				DESCRIPTION
					"The time of day the event was logged at the Kiosk."
				::= { logAppLogEntry 3 }

		logAppLogUser		OBJECT-TYPE
				SYNTAX	OCTET STRING
				ACCESS	read-only
				STATUS	mandatory
				DESCRIPTION
					"The user name in context of which the application
					logging the event is running."
				::= { logAppLogEntry 4 }

		logAppLogComputer	OBJECT-TYPE
				SYNTAX	OCTET STRING
				ACCESS	read-only
				STATUS	mandatory
				DESCRIPTION
					"The (NetBIOS/Windows computer) name of the
					Kiosk where the event was logged."
				::= { logAppLogEntry 5 }

		logAppLogEventID	OBJECT-TYPE
				SYNTAX	INTEGER
				ACCESS	read-only
				STATUS	mandatory
				DESCRIPTION
					"A numeric identification of the event."
				::= { logAppLogEntry 6 }

		logAppLogSource		OBJECT-TYPE
				SYNTAX	OCTET STRING
				ACCESS	read-only
				STATUS	mandatory
				DESCRIPTION
					"The name of the application/service that logged
					the event."
				::= { logAppLogEntry 7 }

		logAppLogType		OBJECT-TYPE
				SYNTAX	NTSeverity
				ACCESS	read-only
				STATUS	mandatory
				DESCRIPTION
					"The type (severity) of the event."
				::= { logAppLogEntry 8 }

		logAppLogCategory	OBJECT-TYPE
				SYNTAX	OCTET STRING
				ACCESS	read-only
				STATUS	mandatory
				DESCRIPTION
					"The event category."
				::= { logAppLogEntry 9 }

		logAppLogDescription	OBJECT-TYPE
				SYNTAX	OCTET STRING
				ACCESS	read-only
				STATUS	mandatory
				DESCRIPTION
					"Description of the event."
				::= { logAppLogEntry 10 }

		logAppLogData	OBJECT-TYPE
				SYNTAX	OCTET STRING
				ACCESS	read-only
				STATUS	mandatory
				DESCRIPTION
					"The raw data from the event message.
					The octet string returned will be formatted with
					two-bytes of length information preceding
					the data."
				::= { logAppLogEntry 11 }

		logAppLogSize		OBJECT-TYPE
				SYNTAX	INTEGER
				ACCESS	read-only
				STATUS	mandatory
				DESCRIPTION
					"Number of entries in the application log."
				::= { logAppLog 2 }

		logAppLogReqSize	OBJECT-TYPE
				SYNTAX	INTEGER
				ACCESS	read-write
				STATUS	mandatory
				DESCRIPTION
					"The number of events to return in the logAppLog
					table (default: 50). To change the default, the desired
					number of event log entries can be written to
					this variable. "
				::= { logAppLog 3 }

END
