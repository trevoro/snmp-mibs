ACC-XNS DEFINITIONS ::= BEGIN

    IMPORTS
		OBJECT-TYPE, IpAddress, TimeTicks, Gauge, Counter FROM RFC1155-SMI
		TRAP-TYPE FROM RFC-1215
        accTrapLogSeqNum FROM ACC-SYSTEM
	accBRG, DisplayString, RowStatus, IfIndex, SmdsAddress
             FROM ACC-MIB;

-- XNS Group
   accXns         OBJECT IDENTIFIER ::= { accBRG 21 }
     accXnsParms	OBJECT IDENTIFIER ::= { accXns 1 }
       accXnsAdStat  OBJECT-TYPE   
			SYNTAX	INTEGER {
				on(1),
				off(2)
			}
			ACCESS	read-write
			STATUS	mandatory
			DESCRIPTION
                " Administrative status of XNS routing protocol"
			::= { accXnsParms 1 }
	  accXnsCkSum  OBJECT-TYPE   
			SYNTAX	INTEGER {
				off(1),
				packet(2),
				header(3)
			}
			ACCESS	read-write
			STATUS	mandatory
			DESCRIPTION
                " Checksumming of XNS protocol"
			::= { accXnsParms 2 }
	  accXnsSpltHorz  OBJECT-TYPE   
			SYNTAX	INTEGER {
				off(1),
				simple(2),
				poison(3)
			}
			ACCESS	read-write
			STATUS	mandatory
			DESCRIPTION
                " Split horizon mode of XNS protocol"
			::= { accXnsParms 3 }
	  accXnsAllNets  OBJECT-TYPE   
			SYNTAX	INTEGER {
				on(1),
				off(2)
			}
			ACCESS	read-write
			STATUS	mandatory
			DESCRIPTION
                " All nets mode"
			::= { accXnsParms 4 }
	  accXnsMode  OBJECT-TYPE   
			SYNTAX	INTEGER {
				xns(1),
				ub(2)
			}
			ACCESS	read-write
			STATUS	mandatory
			DESCRIPTION
                " RIP protocol type to use"
			::= { accXnsParms 5 }
     accXnsNetTable  OBJECT-TYPE   
			SYNTAX	SEQUENCE OF AccXnsNetEntry
			ACCESS	not-accessible
			STATUS	mandatory
			DESCRIPTION
                " List of XNS Networks.
	          Entries added/deleted by management action."
			::= { accXns 2 }
	  accXnsNetEntry  OBJECT-TYPE   
			SYNTAX	AccXnsNetEntry
			ACCESS	not-accessible
			STATUS	mandatory
			DESCRIPTION
                           " Information on specific network"
                        INDEX { accXnsNetPort }
			::= { accXnsNetTable 1 }
        AccXnsNetEntry ::= SEQUENCE {
			accXnsNetPort		INTEGER,
			accXnsNetNumber		OCTET STRING,
			accXnsNetType		INTEGER,
			accXnsNetEncap		INTEGER,
			accXnsNetSlot		INTEGER,
			accXnsNetAdStat		INTEGER,
			accXnsNetMtu		INTEGER,
			accXnsNetUpdate		TimeTicks,
			accXnsNetHops		INTEGER,
			accXnsNetCost		INTEGER,
			accXnsNetX25InOutAddr	DisplayString,
			accXnsNetX25InAddr	DisplayString,
			accXnsNetX25Idle	TimeTicks,
			accXnsNetX25PktVal	INTEGER,
			accXnsNetX25PktWin	INTEGER,
			accXnsNetEntryStat	INTEGER,
			accXnsNetUbUpdate	TimeTicks,
			accXnsNetUbTtl		TimeTicks,
			accXnsNetUbQT1		TimeTicks,
			accXnsNetUbQT2		TimeTicks,
                        accXnsNetFncAddr	OCTET STRING,
                        accXnsNetSrMode		INTEGER,
			accXnsNetX25FacIndex	INTEGER,
			accXnsNetDlci		INTEGER
 			}
	  accXnsNetPort  OBJECT-TYPE   
			SYNTAX	INTEGER
			ACCESS	read-write
			STATUS	mandatory
			DESCRIPTION
                " XNS logical port number "
			::= { accXnsNetEntry 1 }
	  accXnsNetNumber  OBJECT-TYPE   
			SYNTAX	OCTET STRING
			ACCESS	read-write
			STATUS	mandatory
			DESCRIPTION
                " XNS network number "
			::= { accXnsNetEntry 2 }
	  accXnsNetType  OBJECT-TYPE   
			SYNTAX	INTEGER {
				enet(1),
				token-ring(2),
				lapb(3),
				x25(4),
				ffr(5)
			}
			ACCESS	read-write
			STATUS	mandatory
			DESCRIPTION
                           " Type of network "
			::= { accXnsNetEntry 3 }
	  accXnsNetEncap  OBJECT-TYPE   
			SYNTAX	INTEGER {
				none(0),
				v2(1),
				raw(2),
				llc(3),
				snap(4)
			}
			ACCESS	read-write
			STATUS	mandatory
			DESCRIPTION
                " LAN Encapsulation used (Ethernet).
		"
			::= { accXnsNetEntry 4 }
	  accXnsNetSlot  OBJECT-TYPE   
			SYNTAX	INTEGER {
				j1(1),
				j2(2),
				j3(3),
				b1(4)
			}
			ACCESS	read-write
			STATUS	mandatory
			DESCRIPTION
                " Slot to which the network is attached "
			::= { accXnsNetEntry 5 }
	  accXnsNetAdStat  OBJECT-TYPE   
			SYNTAX	INTEGER {
				on(1),
				off(2)
			}
			ACCESS	read-write
			STATUS	mandatory
			DESCRIPTION
	                  " Administrative status of network "
                        DEFVAL { on }
			::= { accXnsNetEntry 6 }
	  accXnsNetMtu  OBJECT-TYPE   
			SYNTAX	INTEGER (576..65535)
			ACCESS	read-write
			STATUS	mandatory
			DESCRIPTION
	        " Maximum packet size.
	          Object will be defaulted to a network type 
                  dependent value if missing in set PDU which
	          adds entries."
			::= { accXnsNetEntry 7 }
	  accXnsNetUpdate  OBJECT-TYPE   
			SYNTAX	TimeTicks
			ACCESS	read-write
			STATUS	mandatory
			DESCRIPTION
	        " Update interval "
                        DEFVAL { 1500 }
			::= { accXnsNetEntry 8 }
	  accXnsNetHops  OBJECT-TYPE   
			SYNTAX	INTEGER
			ACCESS	read-write
			STATUS	mandatory
			DESCRIPTION
	                    " Hop count"
                        DEFVAL { 1 }
			::= { accXnsNetEntry 9 }
	  accXnsNetCost  OBJECT-TYPE   
			SYNTAX	INTEGER
			ACCESS	read-write
			STATUS	mandatory
			DESCRIPTION
	        " Cost metric
	          Object will be defaulted to network type dependent
                  value if missing in set PDU which
	          adds entries."
			::= { accXnsNetEntry 10 }
	  accXnsNetX25InOutAddr  OBJECT-TYPE   
			SYNTAX  DisplayString	
			ACCESS	read-write
			STATUS	mandatory
			DESCRIPTION
	        " X25 address to send to and to receive packets from."
			::= { accXnsNetEntry 11 }
	  accXnsNetX25InAddr  OBJECT-TYPE   
			SYNTAX  DisplayString	
			ACCESS	read-write
			STATUS	mandatory
			DESCRIPTION
	        " Receive-only X25 address
	          Object not required in set PDU (defaults to In/Out address)"
			::= { accXnsNetEntry 12 }
	  accXnsNetX25Idle  OBJECT-TYPE   
			SYNTAX	TimeTicks 
			ACCESS	read-write
			STATUS	mandatory
			DESCRIPTION
	        " Time X25 connection can be idle before it is 
	          determined to be not busy."
                        DEFVAL { 30000 }
			::= { accXnsNetEntry 13 }
	  accXnsNetX25PktVal  OBJECT-TYPE   
			SYNTAX	INTEGER (0..1024)
			ACCESS	read-write
			STATUS	mandatory
			DESCRIPTION
	        " X25 packet size
	          Object will be defaulted if missing in set PDU which
	          adds entries."
                        DEFVAL { 0 }
			::= { accXnsNetEntry 14 }
	  accXnsNetX25PktWin  OBJECT-TYPE   
			SYNTAX	INTEGER (0..127)
			ACCESS	read-write
			STATUS	mandatory
			DESCRIPTION
	        " X25 packet window "
                        DEFVAL { 0 }
			::= { accXnsNetEntry 15 }
	  accXnsNetEntryStat  OBJECT-TYPE   
			SYNTAX	INTEGER {
				other(1),
				invalid(2)
			    }
			ACCESS	read-write
			STATUS	mandatory
			DESCRIPTION
	        " Status of this table entry
	          Set this object to invalid to remove entry from table"
                        DEFVAL { other }
			::= { accXnsNetEntry 16 }
	  accXnsNetUbUpdate  OBJECT-TYPE   
			SYNTAX	TimeTicks
			ACCESS	read-write
			STATUS	mandatory
			DESCRIPTION
	        " Ungermann-Bass update interval
	          Object will be defaulted if missing in set PDU which
	          adds entries."
			::= { accXnsNetEntry 17 }
	  accXnsNetUbTtl  OBJECT-TYPE   
			SYNTAX	TimeTicks
			ACCESS	read-write
			STATUS	mandatory
			DESCRIPTION
	        " Ungermann-Bass time-to-live
	          Object will be defaulted if missing in set PDU which
	          adds entries."
                        DEFVAL { 1500 }
			::= { accXnsNetEntry 18 }
	  accXnsNetUbQT1  OBJECT-TYPE   
			SYNTAX	TimeTicks
			ACCESS	read-write
			STATUS	mandatory
			DESCRIPTION
	        " Ungermann-Bass QT1 timer
	          Object will be defaulted to a network type
                  dependent value if missing in set PDU which
	          adds entries."
			::= { accXnsNetEntry 19 }
	  accXnsNetUbQT2  OBJECT-TYPE   
			SYNTAX	TimeTicks 
			ACCESS	read-write
			STATUS	mandatory
			DESCRIPTION
	        " Ungermann-Bass QT2 timer
	          Object will be defaulted to a network type
                  dependent value if missing in set PDU which
	          adds entries.
	          This object may be individually adjusted"
			::= { accXnsNetEntry 20 }
	accXnsNetFncAddr OBJECT-TYPE
	    SYNTAX	OCTET STRING  -- (SIZE(6))
	    ACCESS	read-write
	    STATUS	mandatory
		DESCRIPTION
		 " The MAC-layer functional address for sending and
		   receiving multicasts."
		::= { accXnsNetEntry 21 }
	accXnsNetSrMode OBJECT-TYPE
	    SYNTAX	INTEGER { 
			off(1), 
			ape(2), 
			spe(3) 
			}
	    ACCESS	read-write
	    STATUS	mandatory
		DESCRIPTION
		 " The source-routing mode for token-ring networks."
		::= { accXnsNetEntry 22 }
        accXnsNetX25FacIndex OBJECT-TYPE
	           SYNTAX      INTEGER (0..255)
       		   ACCESS      read-write
         	   STATUS      mandatory
           	   DESCRIPTION
            		" Index of optional facility string or 0."
           	   DEFVAL      { 0 }
           	   ::= { accXnsNetEntry 23 }
       accXnsNetDlci       OBJECT-TYPE
                   SYNTAX  INTEGER
                   ACCESS  read-write
                   STATUS  mandatory
                   DESCRIPTION
                   " Frame Relay DLCI for this port"
                   ::= { accXnsNetEntry 24 }
     accXnsRouteTable  OBJECT-TYPE   
			SYNTAX	SEQUENCE OF AccXnsRouteEntry
			ACCESS	not-accessible
			STATUS	mandatory
			DESCRIPTION
                " List of routes to other XNS networks"
			::= { accXns 3 }
        accXnsRouteEntry  OBJECT-TYPE   
			SYNTAX	AccXnsRouteEntry
			ACCESS	not-accessible
			STATUS	mandatory
			DESCRIPTION
                          " Information on route to destination network"
                        INDEX { accXnsRtDest }
			::= { accXnsRouteTable 1 }
        AccXnsRouteEntry ::= SEQUENCE {
			accXnsRtDest		OCTET STRING,
			accXnsRtNxtNet		OCTET STRING,
			accXnsRtRouter		OCTET STRING,
			accXnsRtHops		INTEGER,
			accXnsRtCost		INTEGER,
			accXnsRtType		INTEGER,
			accXnsRtOwner		INTEGER,
			accXnsRtAge		TimeTicks,
			accXnsRtPort		INTEGER
 			}
	  accXnsRtDest  OBJECT-TYPE   
			SYNTAX	OCTET STRING 
			ACCESS	read-only
			STATUS	mandatory
			DESCRIPTION
	        " Destination network."
			::= { accXnsRouteEntry 1 }
	  accXnsRtNxtNet  OBJECT-TYPE   
			SYNTAX	OCTET STRING
			ACCESS	read-only
			STATUS	mandatory
			DESCRIPTION
		 " The next network along the way
		   to the destination network."
			::= { accXnsRouteEntry 2 }
	  accXnsRtRouter  OBJECT-TYPE   
			SYNTAX	OCTET STRING 
			ACCESS	read-only
			STATUS	mandatory
			DESCRIPTION
	        " Router on next XNS network on route"
			::= { accXnsRouteEntry 3 }
	  accXnsRtHops  OBJECT-TYPE   
			SYNTAX	INTEGER
			ACCESS	read-only
			STATUS	mandatory
			DESCRIPTION
	        " Number of hops to remote network"
			::= { accXnsRouteEntry 4 }
	  accXnsRtCost  OBJECT-TYPE   
			SYNTAX	INTEGER
			ACCESS	read-only
			STATUS	mandatory
			DESCRIPTION
	        " Cost to remote network"
			::= { accXnsRouteEntry 5 }
	  accXnsRtType  OBJECT-TYPE   
			SYNTAX	INTEGER {
				public(1),
				direct(2),
				static(3)
			    }
			ACCESS	read-only
			STATUS	mandatory
			DESCRIPTION
	        " Type of route"
			::= { accXnsRouteEntry 6 }
	  accXnsRtOwner  OBJECT-TYPE   
			SYNTAX	INTEGER {
				lli(1),
				nms(2),
				rip(3)
			    }
			ACCESS	read-only
			STATUS	mandatory
			DESCRIPTION
	        " Source of route"
			::= { accXnsRouteEntry 7 }
	  accXnsRtAge  OBJECT-TYPE   
			SYNTAX	TimeTicks
			ACCESS	read-only
			STATUS	mandatory
			DESCRIPTION
	        " Age of route"
			::= { accXnsRouteEntry 8 }
	  accXnsRtPort  OBJECT-TYPE   
			SYNTAX	INTEGER
			ACCESS	read-only
			STATUS	mandatory
			DESCRIPTION
		 " The logical port number through which packets will be
		   forwarded to the destination network."
			::= { accXnsRouteEntry 9 }
    accXnsRipStat   OBJECT IDENTIFIER ::= { accXns 4 }
           accXnsRipReqIns OBJECT-TYPE   
			SYNTAX	Counter
			ACCESS	read-only
			STATUS	mandatory
			DESCRIPTION
	        " XNS RIP requests received"
			::= { accXnsRipStat 1 }
           accXnsRipRespIns OBJECT-TYPE   
			SYNTAX	Counter
			ACCESS	read-only
			STATUS	mandatory
			DESCRIPTION
	        " XNS RIP responses received"
			::= { accXnsRipStat 2 }
           accXnsRipReqOuts OBJECT-TYPE   
			SYNTAX	Counter
			ACCESS	read-only
			STATUS	mandatory
			DESCRIPTION
	        " XNS RIP requests transmitted"
			::= { accXnsRipStat 3 }
           accXnsRipRespOuts OBJECT-TYPE   
			SYNTAX	Counter
			ACCESS	read-only
			STATUS	mandatory
			DESCRIPTION
	        " XNS RIP responses transmitted"
			::= { accXnsRipStat 4 }
           accXnsRipInErrs OBJECT-TYPE   
			SYNTAX	Counter
			ACCESS	read-only
			STATUS	mandatory
			DESCRIPTION
	        " XNS RIP packets received with errors"
			::= { accXnsRipStat 5 }
           accXnsRipOutErrs OBJECT-TYPE   
			SYNTAX	Counter
			ACCESS	read-only
			STATUS	mandatory
			DESCRIPTION
	        " XNS RIP responses transmitted with errors."
			::= { accXnsRipStat 6 }
      accXnsNodeStat  OBJECT IDENTIFIER  ::= { accXns 5 }
           accXnsLocalIns OBJECT-TYPE   
			SYNTAX	Counter
			ACCESS	read-only
			STATUS	mandatory
			DESCRIPTION
	        " Packets received for local usage"
			::= { accXnsNodeStat 1 }
           accXnsLocalOuts OBJECT-TYPE   
			SYNTAX	Counter
			ACCESS	read-only
			STATUS	mandatory
			DESCRIPTION
	        " Locally generated packets"
			::= { accXnsNodeStat 2 }
           accXnsNoSockets OBJECT-TYPE   
			SYNTAX	Counter
			ACCESS	read-only
			STATUS	mandatory
			DESCRIPTION
	        " Packets received for which there was no socket"
			::= { accXnsNodeStat 3 }
           accXnsNoRoutes OBJECT-TYPE   
			SYNTAX	Counter
			ACCESS	read-only
			STATUS	mandatory
			DESCRIPTION
	        " Packets for which no route was found"
			::= { accXnsNodeStat 4 }
           accXnsNodeInErrs OBJECT-TYPE   
			SYNTAX	Counter
			ACCESS	read-only
			STATUS	mandatory
			DESCRIPTION
	        " The number of input packets discarded by this node because
	          of some unspecified internal error."
			::= { accXnsNodeStat 5 }
           accXnsOutErrs OBJECT-TYPE   
			SYNTAX	Counter
			ACCESS	read-only
			STATUS	mandatory
			DESCRIPTION
	        " Output errors"
			::= { accXnsNodeStat 6 }
           accXnsAllNetsIns OBJECT-TYPE   
			SYNTAX	Counter
			ACCESS	read-only
			STATUS	mandatory
			DESCRIPTION
	        " All-nets packets received"
			::= { accXnsNodeStat 7 }
           accXnsAllNetsOuts OBJECT-TYPE   
			SYNTAX	Counter
			ACCESS	read-only
			STATUS	mandatory
			DESCRIPTION
	        " All-nets packets transmitted"
			::= { accXnsNodeStat 8 }
           accXnsAllNetsErrs OBJECT-TYPE   
			SYNTAX	Counter
			ACCESS	read-only
			STATUS	mandatory
			DESCRIPTION
	        " Erroneous All-Nets packets encountered"
			::= { accXnsNodeStat 9 }
     accXnsPortStatTable  OBJECT-TYPE   
			SYNTAX	SEQUENCE OF AccXnsPortStatEntry
			ACCESS	not-accessible
			STATUS	mandatory
			DESCRIPTION
                " XNS Port statistics table"
			::= { accXns 6 }
        accXnsPortStatEntry  OBJECT-TYPE   
			SYNTAX	AccXnsPortStatEntry
			ACCESS	not-accessible
			STATUS	mandatory
			DESCRIPTION
                           " Per-port statistics"
		        INDEX { accXnsPortNumber }
			::= { accXnsPortStatTable 1 }
        AccXnsPortStatEntry ::= SEQUENCE {
			accXnsPortNumber		INTEGER,
			accXnsPortTotalIns		Counter,
			accXnsPorFwdReqIns		Counter,
			accXnsPortNoFwdRts		Counter,
			accXnsPortTotalOuts		Counter,
			accXnsPortHopCnts		Counter,
			accXnsPortNotForMes		Counter,
			accXnsPortFwdReqOuts		Counter,
			accXnsPortFwdErrs		Counter,
			accXnsPortInErrs		Counter,
			accXnsPortTooShorts		Counter,
			accXnsPortCkSums		Counter,
			accXnsPortTooLongs		Counter,
			accXnsPortOutErrs		Counter,
			accXnsPortOpState		INTEGER
 			}
	  accXnsPortNumber  OBJECT-TYPE   
			SYNTAX	INTEGER
			ACCESS	read-only
			STATUS	mandatory
			DESCRIPTION
	        " Port number"
			::= { accXnsPortStatEntry 1 }
	  accXnsPortTotalIns  OBJECT-TYPE   
			SYNTAX	Counter
			ACCESS	read-only
			STATUS	mandatory
			DESCRIPTION
	        " Total number of XNS  Packets received"
			::= { accXnsPortStatEntry 2 }
	  accXnsPorFwdReqIns  OBJECT-TYPE   
			SYNTAX	Counter
			ACCESS	read-only
			STATUS	mandatory
			DESCRIPTION
		  " The number of input packets not addressed to the receiving
		    port, as a result of which an attempt was made to find a
		    route to forward them to the final destination."
			::= { accXnsPortStatEntry 3 }
	  accXnsPortNoFwdRts  OBJECT-TYPE   
			SYNTAX	Counter
			ACCESS	read-only
			STATUS	mandatory
			DESCRIPTION
	        " The number of packets received on this port for which no
	          route to the destination network could be found."
			::= { accXnsPortStatEntry 4 }
	  accXnsPortTotalOuts  OBJECT-TYPE   
			SYNTAX	Counter
			ACCESS	read-only
			STATUS	mandatory
			DESCRIPTION
	        " Total XNS packets transmitted"
			::= { accXnsPortStatEntry 5 }
	  accXnsPortHopCnts  OBJECT-TYPE   
			SYNTAX	Counter
			ACCESS	read-only
			STATUS	mandatory
			DESCRIPTION
		 " The number of packets received on this port whose hop
		   count had reached the maximum value."
			::= { accXnsPortStatEntry 6 }
	  accXnsPortNotForMes  OBJECT-TYPE   
			SYNTAX	Counter
			ACCESS	read-only
			STATUS	mandatory
			DESCRIPTION
		 " The number of packets received on this port which were
		   addressed to another node on the same network."
			::= { accXnsPortStatEntry 7 }
	  accXnsPortFwdReqOuts  OBJECT-TYPE   
			SYNTAX	Counter
			ACCESS	read-only
			STATUS	mandatory
			DESCRIPTION
		 " The number of packets received on this port which were
		   successfully forwarded to another port."
			::= { accXnsPortStatEntry 8 }
	  accXnsPortFwdErrs  OBJECT-TYPE   
			SYNTAX	Counter
			ACCESS	read-only
			STATUS	mandatory
			DESCRIPTION
		 " The number of packets received on this port which could
		   not be forwarded, either because there were transmitted
		   via a MAC-layer broadcast, or because their source or
		   destination network number were unknown."
			::= { accXnsPortStatEntry 9 }
	  accXnsPortInErrs  OBJECT-TYPE   
			SYNTAX	Counter
			ACCESS	read-only
			STATUS	mandatory
			DESCRIPTION
	        " The number of packets received on this port which were
	          discarded because of some unspecified internal error."
			::= { accXnsPortStatEntry 10 }
	  accXnsPortTooShorts  OBJECT-TYPE   
			SYNTAX	Counter
			ACCESS	read-only
			STATUS	mandatory
			DESCRIPTION
		 " The number of packets received on this port which were
		   discarded because they were too short."
			::= { accXnsPortStatEntry 11 }
	  accXnsPortCkSums  OBJECT-TYPE   
			SYNTAX	Counter
			ACCESS	read-only
			STATUS	mandatory
			DESCRIPTION
	        " XNS packet checksum errors detected"
			::= { accXnsPortStatEntry 12 }
	  accXnsPortTooLongs  OBJECT-TYPE   
			SYNTAX	Counter
			ACCESS	read-only
			STATUS	mandatory
			DESCRIPTION
		 " The number of packets received on this port which were
		   discarded because they were too long."
			::= { accXnsPortStatEntry 13 }
	  accXnsPortOutErrs  OBJECT-TYPE   
			SYNTAX	Counter
			ACCESS	read-only
			STATUS	mandatory
			DESCRIPTION
	        " XNS packet output errors detected"
			::= { accXnsPortStatEntry 14 }
	  accXnsPortOpState  OBJECT-TYPE   
			SYNTAX	INTEGER {
				off(0),
				down(1),
				start(2),
				stop(3),
				up(4)
			    }
			ACCESS	read-only
			STATUS	mandatory
			DESCRIPTION
	        " Operational status of this port.
		"
			::= { accXnsPortStatEntry 15 }
     accXnsUbNbrTable  OBJECT-TYPE   
			SYNTAX	SEQUENCE OF AccXnsUbNbrEntry
			ACCESS	not-accessible
			STATUS	mandatory
			DESCRIPTION
                " XNS Neighbor table (Ungermann-Bass)"
			::= { accXns 7 }
        accXnsUbNbrEntry  OBJECT-TYPE   
			SYNTAX	AccXnsUbNbrEntry
			ACCESS	not-accessible
			STATUS	mandatory
			DESCRIPTION
                          "  Information on specific neighbor."
                        INDEX { accXnsUbnRmtNet,
		                accXnsUbnLclNet,
		                accXnsUbnRouter }
			::= { accXnsUbNbrTable 1 }
        AccXnsUbNbrEntry ::= SEQUENCE {
			accXnsUbnRmtNet		OCTET STRING,
			accXnsUbnLclNet		OCTET STRING,
			accXnsUbnRouter		OCTET STRING,
			accXnsUbnHops		INTEGER,
			accXnsUbnCost		INTEGER,
			accXnsUbnState		INTEGER,
			accXnsUbnTtl		TimeTicks
 			}
	  accXnsUbnRmtNet  OBJECT-TYPE   
			SYNTAX	OCTET STRING
			ACCESS	read-only
			STATUS	mandatory
			DESCRIPTION
	        " Remote network"
			::= { accXnsUbNbrEntry 1 }
	  accXnsUbnLclNet  OBJECT-TYPE   
			SYNTAX	OCTET STRING
			ACCESS	read-only
			STATUS	mandatory
			DESCRIPTION
	        " Local network"
			::= { accXnsUbNbrEntry 2 }
	  accXnsUbnRouter  OBJECT-TYPE   
			SYNTAX	OCTET STRING
			ACCESS	read-only
			STATUS	mandatory
			DESCRIPTION
	        " Router"
			::= { accXnsUbNbrEntry 3 }
	  accXnsUbnHops  OBJECT-TYPE   
			SYNTAX	INTEGER
			ACCESS	read-only
			STATUS	mandatory
			DESCRIPTION
	        " Hop count to neighbor"
			::= { accXnsUbNbrEntry 4 }
	  accXnsUbnCost  OBJECT-TYPE   
			SYNTAX	INTEGER
			ACCESS	read-only
			STATUS	mandatory
			DESCRIPTION
	        " Cost to neighbor"
			::= { accXnsUbNbrEntry 5 }
	  accXnsUbnState  OBJECT-TYPE   
			SYNTAX	INTEGER {
				local(0),
				congested(1),
				uncongested(2),
				keepalive(3)
			    }
			ACCESS	read-only
			STATUS	mandatory
			DESCRIPTION
	        " State of neighbor.
		"
			::= { accXnsUbNbrEntry 6 }
	  accXnsUbnTtl  OBJECT-TYPE   
			SYNTAX	TimeTicks
			ACCESS	read-only
			STATUS	mandatory
			DESCRIPTION
	        " Time to live"
			::= { accXnsUbNbrEntry 7 }
      accXnsUbRip   OBJECT IDENTIFIER ::= { accXns 8 }
	  accXnsUbRipRespIns  OBJECT-TYPE   
			SYNTAX	Counter
			ACCESS	read-only
			STATUS	mandatory
			DESCRIPTION
	        " U-B RIP Responses received"
			::= { accXnsUbRip 1 }
	  accXnsUbRipHelloIns  OBJECT-TYPE   
			SYNTAX	Counter
			ACCESS	read-only
			STATUS	mandatory
			DESCRIPTION
	        " U-B RIP Hello packets received"
			::= { accXnsUbRip 2 }
	  accXnsUbRipConHelIns  OBJECT-TYPE   
			SYNTAX	Counter
			ACCESS	read-only
			STATUS	mandatory
			DESCRIPTION
	        " U-B RIP (congested) Hello packets received"
			::= { accXnsUbRip 3 }
	  accXnsUbRipUnConHelIns  OBJECT-TYPE   
			SYNTAX	Counter
			ACCESS	read-only
			STATUS	mandatory
			DESCRIPTION
	        " U-B RIP (uncongested) Hello packets received"
			::= { accXnsUbRip 4 }
	  accXnsUbRipRedirIns  OBJECT-TYPE   
			SYNTAX	Counter
			ACCESS	read-only
			STATUS	mandatory
			DESCRIPTION
	        " U-B RIP redirect  packets received"
			::= { accXnsUbRip 5 }
	  accXnsUbRipRespOuts  OBJECT-TYPE   
			SYNTAX	Counter
			ACCESS	read-only
			STATUS	mandatory
			DESCRIPTION
	        " U-B RIP responses transmitted"
			::= { accXnsUbRip 6 }
	  accXnsUbRipHelloOuts  OBJECT-TYPE   
			SYNTAX	Counter
			ACCESS	read-only
			STATUS	mandatory
			DESCRIPTION
	        " U-B hello packets transmitted"
			::= { accXnsUbRip 7 }
	  accXnsUbRipConHelOuts  OBJECT-TYPE   
			SYNTAX	Counter
			ACCESS	read-only
			STATUS	mandatory
			DESCRIPTION
	        " U-B (congested) hello packets transmitted"
			::= { accXnsUbRip 8 }
	  accXnsUbRipUnConHelOuts  OBJECT-TYPE   
			SYNTAX	Counter
			ACCESS	read-only
			STATUS	mandatory
			DESCRIPTION
	        " U-B (uncongested) hello packets transmitted"
			::= { accXnsUbRip 9 }
	  accXnsUbRipRedirOuts  OBJECT-TYPE   
			SYNTAX	Counter
			ACCESS	read-only
			STATUS	mandatory
			DESCRIPTION
	        " U-B redirect packets transmitted"
			::= { accXnsUbRip 10 }
	  accXnsUbNoRoutes  OBJECT-TYPE   
			SYNTAX	Counter
			ACCESS	read-only
			STATUS	mandatory
			DESCRIPTION
	        " U-B unreachable network"
			::= { accXnsUbRip 11 }
	  accXnsUbInErrs  OBJECT-TYPE   
			SYNTAX	Counter
			ACCESS	read-only
			STATUS	mandatory
			DESCRIPTION
	        " U-B total input errors"
			::= { accXnsUbRip 12 }
	  accXnsUbOutErrs  OBJECT-TYPE   
			SYNTAX	Counter
			ACCESS	read-only
			STATUS	mandatory
			DESCRIPTION
	        " U-B total output errors"
			::= { accXnsUbRip 13 }
--    The following route neighbor filter table has been deprecated.
--    Route neighbor filters are replaced by named route filters
   accXnsRouteFilters OBJECT IDENTIFIER ::= { accXns 9 }
     accXnsRteFltrDefaultAction OBJECT-TYPE
         SYNTAX   INTEGER { 
		     accept(1), 
		     reject(2) 
		     }
         ACCESS   read-write
         STATUS   deprecated
         DESCRIPTION
     " The action taken on route updates from unconfigured neighbors."
         ::= { accXnsRouteFilters 1 }
     accXnsRteNbrTable OBJECT-TYPE
         SYNTAX   SEQUENCE OF AccXnsRteNbrEntry
         ACCESS   not-accessible
         STATUS   deprecated
         DESCRIPTION
            " A list of Host Identifiers for Routing Neighbors."
         ::= { accXnsRouteFilters 2 }
        accXnsRteNbrEntry OBJECT-TYPE
           SYNTAX   AccXnsRteNbrEntry
           ACCESS   not-accessible
           STATUS   deprecated
           DESCRIPTION
              " The host identifier for an individual routing neighbor."
           INDEX { accXnsRteNbrId }
           ::= { accXnsRteNbrTable 1 }
        AccXnsRteNbrEntry ::=
            SEQUENCE {
                accXnsRteNbrId
                    OCTET STRING,
                accXnsRteNbrAction
                    INTEGER,
                accXnsRteNbrStatus
                    INTEGER
                }
           accXnsRteNbrId OBJECT-TYPE
               SYNTAX   OCTET STRING -- (SIZE(6))
               ACCESS   read-write
               STATUS   deprecated
               DESCRIPTION
                 " The Host Identifier of a potential routing neighbor."
               ::= { accXnsRteNbrEntry 1 }
           accXnsRteNbrAction OBJECT-TYPE
               SYNTAX   INTEGER { 
			accept(1), 
			reject(2) 
			}
               ACCESS   read-write
               STATUS   deprecated
               DESCRIPTION
         " The action to be taken on advertisements from this routing neighbor,
           unless overridden by a route filter."
               ::= { accXnsRteNbrEntry 2 }
           accXnsRteNbrStatus OBJECT-TYPE
               SYNTAX   INTEGER {
                invalid(1), 
                valid(2) 
                }
               ACCESS   read-write
               STATUS   deprecated
               DESCRIPTION
          " Writing 'invalid' has the effect of deleting this routing neighbor
            and making its associated route filters of no effect."
               ::= { accXnsRteNbrEntry 3 }
--    The following route filter table has been deprecated in
--    deference to the new named route filter table.
     accXnsRteFltrTable OBJECT-TYPE
         SYNTAX   SEQUENCE OF AccXnsRteFltrEntry
         ACCESS   not-accessible
         STATUS   deprecated
         DESCRIPTION
         " A list of special advertisements that a given neighbor might offer.
           Route Advertisements defaults are overridden using this table"
         ::= { accXnsRouteFilters 3 }
       accXnsRteFltrEntry OBJECT-TYPE
           SYNTAX   AccXnsRteFltrEntry
           ACCESS   not-accessible
           STATUS   deprecated
           DESCRIPTION
          " A single potential advertisement, with information 
            as to its disposition."
           INDEX { accXnsRteFltrNeighbor, 
                   accXnsRteFltrNetwork }
           ::= { accXnsRteFltrTable 1 }
       AccXnsRteFltrEntry ::=
           SEQUENCE {
               accXnsRteFltrNeighbor
                   OCTET STRING,
               accXnsRteFltrNetwork
                   OCTET STRING,
               accXnsRteFltrAction
                   INTEGER,
               accXnsRteFltrStatus
                   INTEGER
	       }
         accXnsRteFltrNeighbor OBJECT-TYPE
             SYNTAX   OCTET STRING -- (SIZE(6))
             ACCESS   read-write 
             STATUS   deprecated
             DESCRIPTION
          " The Host Identifier of the Routing Neighbor that might 
            offer this advertsiement."
             ::= { accXnsRteFltrEntry 1 }
         accXnsRteFltrNetwork OBJECT-TYPE
             SYNTAX   OCTET STRING  -- (SIZE (4))
             ACCESS   read-write
             STATUS   deprecated
             DESCRIPTION
         " The Network Number the neighbor might advertise."
             ::= { accXnsRteFltrEntry 2 }
         accXnsRteFltrAction OBJECT-TYPE
             SYNTAX   INTEGER { 
		         accept(1), 
		         reject(2) 
		         }
             ACCESS   read-write
             STATUS   deprecated
             DESCRIPTION
                   " What is to be done with such an advertisement."
             ::= { accXnsRteFltrEntry 3 }
         accXnsRteFltrStatus OBJECT-TYPE
             SYNTAX   INTEGER {
                         invalid(1), 
                         valid(2) 
                         }
             ACCESS   read-write
             STATUS   deprecated
             DESCRIPTION
                  " Writing 'invalid' has the effect of deleting this filter."
             ::= { accXnsRteFltrEntry 4 }
--	The following network filter table is deprecated in
--      favor of the expanded table immediately subsequent
--	The Network Filter permits traffic to be prioritized based
--      on souce/destination networks and socket numbers and packet type.
   accXnsNetworkFilters OBJECT IDENTIFIER ::= { accXns 10 }
     accXnsNetFltrDefaultAction OBJECT-TYPE
         SYNTAX   INTEGER {
                        discard(0),
                        lowPriority(1),
                        normalPriority(2),
                        highPriority(3)
	     		}
         ACCESS   read-write
         STATUS   deprecated
         DESCRIPTION
             " The action taken on messages not matched.
		"
         ::= { accXnsNetworkFilters 1 }
     oldXnsNetFltrTable OBJECT-TYPE
         SYNTAX   SEQUENCE OF OldXnsNetFltrEntry
         ACCESS   not-accessible
         STATUS   deprecated
         DESCRIPTION
                 " A list of network pairs to specially act on."
         ::= { accXnsNetworkFilters 2 }
     oldXnsNetFltrEntry OBJECT-TYPE
         SYNTAX   OldXnsNetFltrEntry
         ACCESS   not-accessible
         STATUS   deprecated
         DESCRIPTION
                 " A single Network Number pair to be matched."
         INDEX { oldXnsNetFltrDestination, 
                 oldXnsNetFltrSource }
         ::= { oldXnsNetFltrTable 1 }
     OldXnsNetFltrEntry ::=
         SEQUENCE {
             oldXnsNetFltrDestination
                 OCTET STRING,
             oldXnsNetFltrSource
                 OCTET STRING,
             oldXnsNetFltrAction
                 INTEGER,
             oldXnsNetFltrStatus
                 INTEGER
	     }
        oldXnsNetFltrDestination OBJECT-TYPE
            SYNTAX   OCTET STRING   -- (SIZE (4))
            ACCESS   read-write
            STATUS   deprecated
            DESCRIPTION
                " The value to be found in the Destination Network 
                  Field, or 0x00000000."
            ::= { oldXnsNetFltrEntry 1 }
        oldXnsNetFltrSource OBJECT-TYPE
            SYNTAX   OCTET STRING   -- (SIZE (4))
            ACCESS   read-write
            STATUS   deprecated
            DESCRIPTION
        " The value to be found in the Source Network Field, or 0x00000000."
            ::= { oldXnsNetFltrEntry 2 }
        oldXnsNetFltrAction OBJECT-TYPE
            SYNTAX   INTEGER { 
                        discard(0),
                        lowPriority(1),
                        normalPriority(2),
                        highPriority(3)
			} 
            ACCESS   read-write
            STATUS   deprecated
            DESCRIPTION
         " The action to be taken on matching messages.
	"
            ::= { oldXnsNetFltrEntry 3 }
        oldXnsNetFltrStatus OBJECT-TYPE
            SYNTAX   INTEGER {
                invalid(1), 
                valid(2) 
                }
            ACCESS   read-write
            STATUS   deprecated
            DESCRIPTION
            " Writing 'invalid' has the effect of removing this filter entry."
            ::= { oldXnsNetFltrEntry 4 }
--    The following network filter table has been deprecated in
--    deference to the new named network filter table.
--	The Network Filter permits the remote network routing
--	routine to determine whether traffic from or to a
--	particular network/socket of a particular packet type
--      is to be prioritized.
     accXnsNetFltrTable OBJECT-TYPE
         SYNTAX   SEQUENCE OF AccXnsNetFltrEntry
         ACCESS   not-accessible
         STATUS   deprecated
         DESCRIPTION
                 " A list of network filters to specially act on."
         ::= { accXnsNetworkFilters 3 }
     accXnsNetFltrEntry OBJECT-TYPE
         SYNTAX   AccXnsNetFltrEntry
         ACCESS   not-accessible
         STATUS   deprecated
         DESCRIPTION
                 " A single Network filter to be matched."
         INDEX { accXnsNetFltrDestination, 
                 accXnsNetFltrSource,
                 accXnsNetFltrDestSkt,
                 accXnsNetFltrSrcSkt,
                 accXnsNetFltrPktType }
         ::= { accXnsNetFltrTable 1 }
     AccXnsNetFltrEntry ::=
         SEQUENCE {
             accXnsNetFltrDestination
                 OCTET STRING,
             accXnsNetFltrSource
                 OCTET STRING,
             accXnsNetFltrAction
                 INTEGER,
             accXnsNetFltrStatus
                 INTEGER,
             accXnsNetFltrDestSkt
                 OCTET STRING,
             accXnsNetFltrSrcSkt
                 OCTET STRING,
             accXnsNetFltrPktType
                 INTEGER
	     }
        accXnsNetFltrDestination OBJECT-TYPE
            SYNTAX   OCTET STRING   -- (SIZE (4))
            ACCESS   read-write
            STATUS   deprecated
            DESCRIPTION
                " The value to be found in the Destination Network 
                  Field, or 0x00000000."
            ::= { accXnsNetFltrEntry 1 }
        accXnsNetFltrSource OBJECT-TYPE
            SYNTAX   OCTET STRING   -- (SIZE (4))
            ACCESS   read-write
            STATUS   deprecated
            DESCRIPTION
        " The value to be found in the Source Network Field, or 0x00000000."
            ::= { accXnsNetFltrEntry 2 }
        accXnsNetFltrAction OBJECT-TYPE
            SYNTAX   INTEGER {
                        discard(0),
                        lowPriority(1),
                        normalPriority(2),
                        highPriority(3)
	 		}
            ACCESS   read-write
            STATUS   deprecated
            DESCRIPTION
         " The action to be taken on matching messages.
	"
            ::= { accXnsNetFltrEntry 3 }
        accXnsNetFltrStatus OBJECT-TYPE
            SYNTAX   INTEGER {
                invalid(1), 
                valid(2) 
                }
            ACCESS   read-write
            STATUS   deprecated
            DESCRIPTION
            " Writing 'invalid' has the effect of removing this filter entry."
            ::= { accXnsNetFltrEntry 4 }
        accXnsNetFltrDestSkt OBJECT-TYPE
            SYNTAX   OCTET STRING   -- (SIZE (2))
            ACCESS   read-write
            STATUS   deprecated
            DESCRIPTION
                " The value to be found in the Destination Socket 
                  Field, or 0x0000."
            ::= { accXnsNetFltrEntry 5 }
        accXnsNetFltrSrcSkt OBJECT-TYPE
            SYNTAX   OCTET STRING  -- (SIZE (2))
            ACCESS   read-write
            STATUS   deprecated
            DESCRIPTION
		"The value to be found in the Source Socket Field, 
		 or 0x0000"
            ::= { accXnsNetFltrEntry 6 }
        accXnsNetFltrPktType OBJECT-TYPE
            SYNTAX   INTEGER 
            ACCESS   read-write
            STATUS   deprecated
            DESCRIPTION
         " Packet type, or zero "
            ::= { accXnsNetFltrEntry 7 }
--    The following host filter table has been deprecated in
--    deference to the new named host filter table.
--  XNS Host Filters
   accXnsHostFilters OBJECT IDENTIFIER ::= { accXns 11 }
      accXnsHostFltrDefaultAction OBJECT-TYPE
          SYNTAX   INTEGER { 
                        discard(0),
                        lowPriority(1),
                        normalPriority(2),
                        highPriority(3)
	  		}
          ACCESS   read-write
          STATUS   deprecated
          DESCRIPTION
          " The action taken on hosts not listed.
	"
          ::= { accXnsHostFilters 1 }
      accXnsHostFltrTable OBJECT-TYPE
          SYNTAX   SEQUENCE OF AccXnsHostFltrEntry
          ACCESS   not-accessible
          STATUS   deprecated
          DESCRIPTION
             " A list of XNS Hosts to be handled specially."
          ::= { accXnsHostFilters 2 }
         accXnsHostFltrEntry OBJECT-TYPE
             SYNTAX   AccXnsHostFltrEntry
             ACCESS   not-accessible
             STATUS   deprecated
             DESCRIPTION
                   " A single Host Identifier."
             INDEX { accXnsHostFltrId, 
                     accXnsHostFltrSocket, 
                     accXnsHostFltrPepClient }
             ::= { accXnsHostFltrTable 1 }
         AccXnsHostFltrEntry ::=
             SEQUENCE {
                 accXnsHostFltrId
                     OCTET STRING,
	         accXnsHostFltrSocket
	             OCTET STRING,
	         accXnsHostFltrPepClient
	             OCTET STRING,
                 accXnsHostFltrAction
                     INTEGER,
                 accXnsHostFltrStatus
                     INTEGER
                }
           accXnsHostFltrId OBJECT-TYPE
               SYNTAX   OCTET STRING  -- (SIZE(6))
               ACCESS   read-write
               STATUS   deprecated
               DESCRIPTION
                " Host Identifier "
               ::= { accXnsHostFltrEntry 1 }
           accXnsHostFltrSocket OBJECT-TYPE
               SYNTAX   OCTET STRING  -- (SIZE (2))
               ACCESS   read-write
               STATUS   deprecated
               DESCRIPTION
                " The affected socket number, or zero for 'any socket'."
               ::= { accXnsHostFltrEntry 2 }
           accXnsHostFltrPepClient OBJECT-TYPE
               SYNTAX   OCTET STRING  -- (SIZE(2))
               ACCESS   read-write
               STATUS   deprecated
               DESCRIPTION
                    " On PEP traffic, the affected Client Type, 
                      or zero for all IDP traffic."
               ::= { accXnsHostFltrEntry 3 }
           accXnsHostFltrAction OBJECT-TYPE
               SYNTAX   INTEGER  {
                        discard(0),
                        lowPriority(1),
                        normalPriority(2),
                        highPriority(3)
		       }
               ACCESS   read-write
               STATUS   deprecated
               DESCRIPTION
                       " The action to be taken on matching messages.
	"
               ::= { accXnsHostFltrEntry 4 }
           accXnsHostFltrStatus OBJECT-TYPE
               SYNTAX   INTEGER {
                invalid(1), 
                valid(2) 
                }
               ACCESS   read-write
               STATUS   deprecated
               DESCRIPTION
           		"Writing 'invalid' has the effect of deleting the entry"
               ::= { accXnsHostFltrEntry 5 }
   accXnsNamedRteFilters OBJECT IDENTIFIER ::= { accXns 12 }
   accXnsNamedRteFltrDefaultAction OBJECT-TYPE
         SYNTAX   INTEGER { 
		     accept(1), 
		     reject(2) 
		     }
         ACCESS   read-write
         STATUS   mandatory
         DESCRIPTION
	     " The action taken on route updates from unconfigured neighbors."
         ::= { accXnsNamedRteFilters 1 }
	accXnsNamedRteFltrTable	OBJECT-TYPE
		SYNTAX	SEQUENCE OF AccXnsNamedRteFltrEntry
		ACCESS	not-accessible
		STATUS	mandatory
              DESCRIPTION ""
	::= { accXnsNamedRteFilters 2 }
	accXnsNamedRteFltrEntry	OBJECT-TYPE
		SYNTAX	AccXnsNamedRteFltrEntry
		ACCESS	not-accessible
		STATUS	mandatory
		DESCRIPTION
       			"A single IDP named route filter entry"
       		INDEX		{ accXnsNamedRteFltrName }
	::= { accXnsNamedRteFltrTable 1 }
	AccXnsNamedRteFltrEntry	::= SEQUENCE  {
		accXnsNamedRteFltrNeighbor	OCTET STRING,
		accXnsNamedRteFltrNetwork	OCTET STRING,
   		accXnsNamedRteFltrNetMask	OCTET STRING,
		accXnsNamedRteFltrAction	INTEGER,
		accXnsNamedRteFltrStatus	INTEGER,
		accXnsNamedRteFltrName		OCTET STRING,
		accXnsNamedRteFltrPktDir	INTEGER,
		accXnsNamedRteFltrMatches	Counter,
		accXnsNamedRteFltrLastMatch	TimeTicks
		}
     	accXnsNamedRteFltrNeighbor  OBJECT-TYPE
		SYNTAX   OCTET STRING
      		ACCESS   read-write
		STATUS   mandatory
		DESCRIPTION	
			"Host identifier of the routing neighbor that might 
			 offer a  routing advertisement."
	::=  { accXnsNamedRteFltrEntry 1 }
        accXnsNamedRteFltrNetwork  OBJECT-TYPE
		SYNTAX   OCTET STRING
      		ACCESS   read-write
		STATUS   mandatory
		DESCRIPTION	
			"The network number the routing neighbor might 
			 advertise"
	::=  { accXnsNamedRteFltrEntry 2 }
	accXnsNamedRteFltrNetMask  OBJECT-TYPE
		SYNTAX   OCTET STRING -- ( SIZE (4))
      		ACCESS   read-write
		STATUS   mandatory
		DESCRIPTION	
			"Network Mask to describe a range of network numbers 
			 that a neighbor might advertise. Network mask is a 
			 hexadecimal number in the range of 0x0 to 0xffffffff 
			 containing a contiguous stream of 1 bits "
	::=  { accXnsNamedRteFltrEntry 3 }
        accXnsNamedRteFltrAction  OBJECT-TYPE
		SYNTAX   INTEGER {
				accept (1),
				reject (2)
				}
      		ACCESS   read-write
		STATUS   mandatory
		DESCRIPTION	
			"What is to be done with such an advertisement"
	::=  { accXnsNamedRteFltrEntry 4 }
        accXnsNamedRteFltrStatus  OBJECT-TYPE
               	SYNTAX   INTEGER {
				invalid (1),
				valid  (2)
				}
      		ACCESS   read-write
		STATUS   mandatory
		DESCRIPTION	
			"Writing 'invalid' has the effect of deleting this
		 	 filter entry."
	::=  { accXnsNamedRteFltrEntry 5 }
	accXnsNamedRteFltrName  OBJECT-TYPE
		SYNTAX   OCTET STRING
      		ACCESS   read-write
		STATUS   mandatory
		DESCRIPTION	
			"Name of an IDP Route Filter. A string of up to 15 
			 case sensitive ASCII characters." 
	::=  { accXnsNamedRteFltrEntry 6 }
	accXnsNamedRteFltrPktDir  OBJECT-TYPE
		SYNTAX	INTEGER {
				input(1),
				output(2)
				}
		ACCESS	read-write
		STATUS	mandatory	
		DESCRIPTION
			"Traffic direction to which the filter is applied"
	::=  { accXnsNamedRteFltrEntry 7 }
	accXnsNamedRteFltrMatches  OBJECT-TYPE
		SYNTAX   Counter
      		ACCESS   read-only
		STATUS   mandatory
		DESCRIPTION	
			"Number of times an IDP packet matched the filter "
	::=  { accXnsNamedRteFltrEntry 8 }
	accXnsNamedRteFltrLastMatch  OBJECT-TYPE
		SYNTAX   TimeTicks
      		ACCESS   read-only
		STATUS   mandatory
		DESCRIPTION	
			"Time-tick when the last IDP packet matched the filter"
	::=  { accXnsNamedRteFltrEntry 9 }
	accXnsRteFltrApplTable OBJECT-TYPE
		SYNTAX  SEQUENCE OF AccXnsRteFltrApplEntry 
		ACCESS  	not-accessible
		STATUS  	mandatory
		DESCRIPTION
			"This table describes application of IDP Route 
			 filters to IDP ports."
        ::= { accXnsNamedRteFilters 3 }
	AccXnsRteFltrApplEntry  ::= SEQUENCE {
		accXnsRteFltrApplIfIndex	INTEGER,
		accXnsRteFltrApplPktDir	        INTEGER,
		accXnsRteFltrApplSeqNum		INTEGER,
		accXnsRteFltrApplName		DisplayString,
		accXnsRteFltrApplMatches	Counter,
		accXnsRteFltrApplLastMatch	TimeTicks
	}
	accXnsRteFltrApplEntry	OBJECT-TYPE
		SYNTAX	AccXnsRteFltrApplEntry
		ACCESS	not-accessible
		STATUS	mandatory
		DESCRIPTION
			"IDP named route filter application entry."
               	INDEX		{ accXnsRteFltrApplIfIndex,
   				  accXnsRteFltrApplPktDir,
   				  accXnsRteFltrApplSeqNum  }
	::= { accXnsRteFltrApplTable 1 }
	accXnsRteFltrApplIfIndex	OBJECT-TYPE
		SYNTAX	INTEGER
		ACCESS	read-only
		STATUS	mandatory
		DESCRIPTION
			"Interface Index to which the IDP Route filter 
			 is applied"
	::= { accXnsRteFltrApplEntry 1 }
	accXnsRteFltrApplPktDir	OBJECT-TYPE
		SYNTAX	INTEGER  {
				input(1),
				output(2),
				global(3)
				 }
		ACCESS	read-only
		STATUS	mandatory
		DESCRIPTION
			"Traffic direction to which the IDP Route filter 
 			 is applied"
	::= { accXnsRteFltrApplEntry 2 }
	accXnsRteFltrApplSeqNum	OBJECT-TYPE
		SYNTAX	INTEGER
		ACCESS	read-only
		STATUS	mandatory
		DESCRIPTION
			"Internally generated number indicating the sequence 
			 in which the IDP Route filter is applied. Filters 
			 are applied in the order of most specific to least 
			 specific filter"
	::= { accXnsRteFltrApplEntry 3 }
	accXnsRteFltrApplName	OBJECT-TYPE
		SYNTAX	DisplayString
		ACCESS	read-only
		STATUS	mandatory
		DESCRIPTION
			"Name of the IDP Route filter being applied"
	::= { accXnsRteFltrApplEntry 4 }
	accXnsRteFltrApplMatches	OBJECT-TYPE
		SYNTAX	Counter
		ACCESS	read-only
		STATUS	mandatory
		DESCRIPTION
			"Number of times the filter matched an IDP traffic 
			 packet - on the giveninterface"
	::= { accXnsRteFltrApplEntry 5 }
	accXnsRteFltrApplLastMatch	OBJECT-TYPE
		SYNTAX	TimeTicks
		ACCESS	read-only
		STATUS	mandatory
		DESCRIPTION
			"Time tick value when the filter last matched an IDP 
			 traffic packet - on thegiven interface"
	::= { accXnsRteFltrApplEntry 6 }
--	The Network Filter permits traffic to be prioritized based
--      on souce/destination networks and socket numbers and packet type.
     accXnsNamedNetworkFilters	OBJECT IDENTIFIER  ::= { accXns 13 }
     accXnsNamedNetFltrDefaultAction OBJECT-TYPE
         SYNTAX   INTEGER {
                        discard(0),
                        lowPriority(1),
                        normalPriority(2),
                        highPriority(3)
	     		}
         ACCESS   read-write
         STATUS   mandatory
         DESCRIPTION
             " The action taken on messages not matched.
		"
         ::= { accXnsNamedNetworkFilters 1 }
	accXnsNamedNetFltrTable	OBJECT-TYPE
		SYNTAX	SEQUENCE OF AccXnsNamedNetFltrEntry
		ACCESS	not-accessible
		STATUS	mandatory
              DESCRIPTION ""
	::= { accXnsNamedNetworkFilters 2 }
	AccXnsNamedNetFltrEntry	::= SEQUENCE  {
		accXnsNamedNetFltrDestination	OCTET STRING,
		accXnsNamedNetFltrSource	OCTET STRING,
		accXnsNamedNetFltrAction	INTEGER,
		accXnsNamedNetFltrStatus	INTEGER,
		accXnsNamedNetFltrDestSkt	OCTET STRING,
		accXnsNamedNetFltrSrcSkt	OCTET STRING,
		accXnsNamedNetFltrType		INTEGER,
		accXnsNamedNetFltrName		OCTET STRING,
		accXnsNamedNetFltrPktDir	INTEGER,
		accXnsNamedNetFltrMatches	Counter,
		accXnsNamedNetFltrLastMatch	TimeTicks,
		accXnsNamedNetFltrDestMask	OCTET STRING,
		accXnsNamedNetFltrSrcMask	OCTET STRING
		}
	accXnsNamedNetFltrEntry	OBJECT-TYPE
		SYNTAX	AccXnsNamedNetFltrEntry
		ACCESS	not-accessible
		STATUS	mandatory
		DESCRIPTION
                       "A single IDP named network filter entry."
                INDEX		{ accXnsNamedNetFltrName }
	::= { accXnsNamedNetFltrTable 1 }
	accXnsNamedNetFltrDestination  OBJECT-TYPE
		SYNTAX   OCTET STRING   -- ( Size (4) )
      		ACCESS   read-write
		STATUS   mandatory
		DESCRIPTION	
			"The value to be found in the Destination Network Field,
			 or 0x00000000."			
	::=  { accXnsNamedNetFltrEntry 1 }
       	accXnsNamedNetFltrSource  OBJECT-TYPE
		SYNTAX   OCTET STRING   -- ( Size (4) )
      		ACCESS   read-write
		STATUS   mandatory
		DESCRIPTION	
			"The value to be found in the Source Network Field, or 
			 0x00000000."			
	::=  { accXnsNamedNetFltrEntry 2 }
	accXnsNamedNetFltrAction  OBJECT-TYPE
            SYNTAX   INTEGER {
                        discard(0),
                        lowPriority(1),
                        normalPriority(2),
                        highPriority(3)
	 		}
            ACCESS   read-write
            STATUS   mandatory
            DESCRIPTION
		" The action to be taken on matching messages.
	"
	::=  { accXnsNamedNetFltrEntry 3 }
	accXnsNamedNetFltrStatus  OBJECT-TYPE
		SYNTAX   INTEGER  {
				invalid (1),
				valid (2)
				}
      		ACCESS   read-write
		STATUS   mandatory
		DESCRIPTION	
			"Writing invalid has the effect of removing this
			 filter entry"
	::=  { accXnsNamedNetFltrEntry 4 }
	accXnsNamedNetFltrDestSkt  OBJECT-TYPE
		SYNTAX   OCTET STRING   -- ( Size (2) )
      		ACCESS   read-write
		STATUS   mandatory
		DESCRIPTION	
			"The value to be found in the Destination Socket Field,
			 or 0x0000"
	::=  { accXnsNamedNetFltrEntry 5 }
	accXnsNamedNetFltrSrcSkt  OBJECT-TYPE
		SYNTAX   OCTET STRING   -- ( Size (2) )
      		ACCESS   read-write
		STATUS   mandatory
		DESCRIPTION	
			"The value to be found in the Source Socket Field, 
			 or 0x0000"
	::=  { accXnsNamedNetFltrEntry 6 }
	accXnsNamedNetFltrType  OBJECT-TYPE
		SYNTAX   INTEGER
      		ACCESS   read-write
		STATUS   mandatory
		DESCRIPTION	
			"Packet type or zero"
	::=  { accXnsNamedNetFltrEntry 7 }
	accXnsNamedNetFltrName  OBJECT-TYPE
		SYNTAX   OCTET STRING
      		ACCESS   read-write
		STATUS   mandatory
		DESCRIPTION	
			"Name of an IDP Network Filter.  A string of up to 15 
			 case sensitive ASCII characters."
	::=  { accXnsNamedNetFltrEntry 8 }
	accXnsNamedNetFltrPktDir  OBJECT-TYPE
		SYNTAX	INTEGER {
				input(1),
				output(2)
				}
		ACCESS	read-write
		STATUS	mandatory	
		DESCRIPTION
			"Traffic direction to which the filter is applied"
	::=  { accXnsNamedNetFltrEntry 9 }
	accXnsNamedNetFltrMatches  OBJECT-TYPE
		SYNTAX   Counter
      		ACCESS   read-only
		STATUS   mandatory
		DESCRIPTION	
			"Number of times an IDP packet matched the filter"
	::=  { accXnsNamedNetFltrEntry 10 }
	accXnsNamedNetFltrLastMatch  OBJECT-TYPE
		SYNTAX   TimeTicks
      		ACCESS   read-only
		STATUS   mandatory
		DESCRIPTION	
			"Time-tick when the last IDP packet matched the filter"
	::=  { accXnsNamedNetFltrEntry 11 }
	accXnsNamedNetFltrDestMask  OBJECT-TYPE
		SYNTAX   OCTET STRING -- ( SIZE (4))
      		ACCESS   read-write
		STATUS   mandatory
		DESCRIPTION	
			"Network Mask to describe a range of destination 
			 network numbers.  Network mask is a hexadecimal 
			 number in the range of 0x0 to 0xffffffff containing 
			 a contiguous stream of 1 bits "
 	::=  { accXnsNamedNetFltrEntry 12 }
	accXnsNamedNetFltrSrcMask  OBJECT-TYPE
		SYNTAX   OCTET STRING -- ( SIZE (4))
      		ACCESS   read-write
		STATUS   mandatory
		DESCRIPTION	
			"Network Mask to describe a range of source network 
			 numbers. Network mask is a hexadecimal number in the 
			 range of 0x0 to 0xffffffff containing a contiguous 
			 stream of 1 bits "
 	::=  { accXnsNamedNetFltrEntry 13 }
	accXnsNetFltrApplTable OBJECT-TYPE
		SYNTAX  SEQUENCE OF AccXnsNetFltrApplEntry 
		ACCESS  	not-accessible
		STATUS  	mandatory
		DESCRIPTION
			"This table describes application of IDP Net filters 
			 to IDP ports."
	::= { accXnsNamedNetworkFilters 3 }
	AccXnsNetFltrApplEntry  ::= SEQUENCE {
		accXnsNetFltrApplIfIndex        INTEGER,
		accXnsNetFltrApplPktDir	        INTEGER,
		accXnsNetFltrApplSeqNum		INTEGER,
		accXnsNetFltrApplName		DisplayString,
		accXnsNetFltrApplMatches	Counter,
		accXnsNetFltrApplLastMatch	TimeTicks
	}
	accXnsNetFltrApplEntry	OBJECT-TYPE
		SYNTAX	AccXnsNetFltrApplEntry
		ACCESS	not-accessible
		STATUS	mandatory
		DESCRIPTION
			"IDP named network filter application entry."
		INDEX		{ accXnsNetFltrApplIfIndex,
				  accXnsNetFltrApplPktDir,
				  accXnsNetFltrApplSeqNum  }
	::= { accXnsNetFltrApplTable 1 }
	accXnsNetFltrApplIfIndex	OBJECT-TYPE
		SYNTAX	INTEGER
		ACCESS	read-only
		STATUS	mandatory
		DESCRIPTION
			"Interface Index to which the IDP Net filter is applied"
	::= { accXnsNetFltrApplEntry 1 }
	accXnsNetFltrApplPktDir	OBJECT-TYPE
		SYNTAX	INTEGER  {
				input(1),
				output(2),
				global(3)
				}
		ACCESS	read-only
		STATUS	mandatory
		DESCRIPTION
			"Traffic direction to which the IDP Net filter is 
			 applied"
	::= { accXnsNetFltrApplEntry 2 }
	accXnsNetFltrApplSeqNum	OBJECT-TYPE
		SYNTAX	INTEGER
		ACCESS	read-only
		STATUS	mandatory
		DESCRIPTION
			"Internally generated number indicating the sequence in
			 which the IDP Net filter is applied. Filters are 
			 applied in the order of most specific to least 
			 specific filter"
	::= { accXnsNetFltrApplEntry 3 }
	accXnsNetFltrApplName	OBJECT-TYPE
		SYNTAX	DisplayString
		ACCESS	read-only
		STATUS	mandatory
		DESCRIPTION
			"Name of the IDP Net filter being applied"
	::= { accXnsNetFltrApplEntry 4 }
	accXnsNetFltrApplMatches	OBJECT-TYPE
		SYNTAX	Counter
		ACCESS	read-only
		STATUS	mandatory
		DESCRIPTION
			"Number of times the filter matched an IDP traffic 
			 packet - on thegiven interface"
	::= { accXnsNetFltrApplEntry 5 }
	accXnsNetFltrApplLastMatch	OBJECT-TYPE
		SYNTAX	TimeTicks
		ACCESS	read-only
		STATUS	mandatory
		DESCRIPTION
			"Time tick value when the filter last matched an IDP 
			 traffic packet - on the given interface"
	::= { accXnsNetFltrApplEntry 6 }
--  XNS Host Filters
	accXnsNamedHostFilters	OBJECT IDENTIFIER	::= { accXns 14 }
	accXnsNamedHostFltrDefaultAction OBJECT-TYPE
          SYNTAX   INTEGER { 
                        discard(0),
                        lowPriority(1),
                        normalPriority(2),
                        highPriority(3)
	  		}
          ACCESS   read-write
          STATUS   mandatory
          DESCRIPTION
          	" The action taken on hosts not listed.
	        "
          ::= { accXnsNamedHostFilters 1 }
	accXnsNamedHostFltrTable	OBJECT-TYPE
		SYNTAX	SEQUENCE OF AccXnsNamedHostFltrEntry
		ACCESS	not-accessible
		STATUS	mandatory
              DESCRIPTION ""
	::= { accXnsNamedHostFilters 2 }
	AccXnsNamedHostFltrEntry	::= SEQUENCE  {
		accXnsNamedHostFltrId		OCTET STRING,
		accXnsNamedHostFltrSocket	OCTET STRING,
		accXnsNamedHostFltrPepClient	OCTET STRING,
		accXnsNamedHostFltrAction	INTEGER,
		accXnsNamedHostFltrStatus	INTEGER,
		accXnsNamedHostFltrName		OCTET STRING,
		accXnsNamedHostFltrPktDir	INTEGER,
		accXnsNamedHostFltrMatches	Counter,
		accXnsNamedHostFltrLastMatch	TimeTicks
		}
	accXnsNamedHostFltrEntry	OBJECT-TYPE
		SYNTAX	AccXnsNamedHostFltrEntry
		ACCESS	not-accessible
		STATUS	mandatory
		DESCRIPTION
			"A single IDP named host filter entry."
		INDEX		{ accXnsNamedHostFltrName }
	::= { accXnsNamedHostFltrTable 1 }
	accXnsNamedHostFltrId  OBJECT-TYPE
		SYNTAX   OCTET STRING   -- ( Size (6) )
      		ACCESS   read-write
		STATUS   mandatory
		DESCRIPTION	
			"Host Identifier of the destination host in IDP message"
	::=  { accXnsNamedHostFltrEntry 1 }
	accXnsNamedHostFltrSocket  OBJECT-TYPE
		SYNTAX   OCTET STRING   -- ( Size (2) )
      		ACCESS   read-write
		STATUS   mandatory
		DESCRIPTION	
			"Destination socket in IDP message or zero"
	::=  { accXnsNamedHostFltrEntry 2 }
	accXnsNamedHostFltrPepClient  OBJECT-TYPE
		SYNTAX   OCTET STRING   -- ( Size (2) )
      		ACCESS   read-write
		STATUS   mandatory
		DESCRIPTION	
			"On PEP traffic, client type in message or zero for
			 all IPX and IDP traffic"
	::=  { accXnsNamedHostFltrEntry 3 }
	accXnsNamedHostFltrAction  OBJECT-TYPE
               SYNTAX   INTEGER  {
                        discard(0),
                        lowPriority(1),
                        normalPriority(2),
                        highPriority(3)
		       }
               ACCESS   read-write
               STATUS   mandatory
               DESCRIPTION
                       " The action to be taken on matching messages.
	"
	::=  { accXnsNamedHostFltrEntry 4 }
	accXnsNamedHostFltrStatus  OBJECT-TYPE
		SYNTAX   INTEGER  {
				invalid (1),
				valid (2)
			}
      		ACCESS   read-write
		STATUS   mandatory
		DESCRIPTION	
			"Writing 'invalid' has the effet of deleting the entry"
	::=  { accXnsNamedHostFltrEntry 5 }
	accXnsNamedHostFltrName  OBJECT-TYPE
		SYNTAX   OCTET STRING
      		ACCESS   read-write
		STATUS   mandatory
		DESCRIPTION	
			"Name of an IDP Host Filter.  A string of up to 15 
			 case sensitive ASCII characters."
	::=  { accXnsNamedHostFltrEntry 6 }
	accXnsNamedHostFltrPktDir  OBJECT-TYPE
		SYNTAX	INTEGER {
				input(1),
				output(2)
				}
		ACCESS	read-write
		STATUS	mandatory	
		DESCRIPTION
			"Traffic direction to which the filter is applied"
	::=  { accXnsNamedHostFltrEntry 7 }
	accXnsNamedHostFltrMatches  OBJECT-TYPE
		SYNTAX   Counter
      		ACCESS   read-only
		STATUS   mandatory
		DESCRIPTION	
			"Number of times an IDP packet matched the filter"
	::=  { accXnsNamedHostFltrEntry 8 }
	accXnsNamedHostFltrLastMatch  OBJECT-TYPE
		SYNTAX   TimeTicks
      		ACCESS   read-only
		STATUS   mandatory
		DESCRIPTION	
			"Time-tick when the last IDP packet matched the filter"
	::=  { accXnsNamedHostFltrEntry 9 }
--
--		The IDP Host Filter Application Table
--
	accXnsHostFltrApplTable OBJECT-TYPE
		SYNTAX  SEQUENCE OF AccXnsHostFltrApplEntry 
		ACCESS  	not-accessible
		STATUS  	mandatory
		DESCRIPTION
			"This table describes application of IDP Host filters 
			 to IDP ports"
	::= { accXnsNamedHostFilters 3 }
	AccXnsHostFltrApplEntry  ::= SEQUENCE {
		accXnsHostFltrApplIfIndex	INTEGER,
		accXnsHostFltrApplPktDir	INTEGER,
		accXnsHostFltrApplSeqNum	INTEGER,
		accXnsHostFltrApplName		DisplayString,
		accXnsHostFltrApplMatches	Counter,
		accXnsHostFltrApplLastMatch	TimeTicks
	}
	accXnsHostFltrApplEntry	OBJECT-TYPE
		SYNTAX	AccXnsHostFltrApplEntry
		ACCESS	not-accessible
		STATUS	mandatory
		DESCRIPTION
			"IDP named host filter application entry."
		INDEX		{ accXnsHostFltrApplIfIndex,
				  accXnsHostFltrApplPktDir,
				  accXnsHostFltrApplSeqNum  }
	::= { accXnsHostFltrApplTable 1 }
	accXnsHostFltrApplIfIndex	OBJECT-TYPE
		SYNTAX	INTEGER
		ACCESS	read-only
		STATUS	mandatory
		DESCRIPTION
			"Interface Index to which the IDP Host filter is 
			 applied"
	::= { accXnsHostFltrApplEntry 1 }
	accXnsHostFltrApplPktDir	OBJECT-TYPE
		SYNTAX	INTEGER  {
				input(1),
				output(2),
				global(3)
				}
		ACCESS	read-only
		STATUS	mandatory
		DESCRIPTION
			"Traffic direction to which the IDP Host filter is 
			 applied"
	::= { accXnsHostFltrApplEntry 2 }
	accXnsHostFltrApplSeqNum	OBJECT-TYPE
		SYNTAX	INTEGER
		ACCESS	read-only
		STATUS	mandatory
		DESCRIPTION
			"Internally generated number indicating the sequence in
			 which the IDP Host filter is applied. Filters are 
			 applied in the order of most specific to least 
			 specific filter "
	::= { accXnsHostFltrApplEntry 3 }
	accXnsHostFltrApplName	OBJECT-TYPE
		SYNTAX	DisplayString
		ACCESS	read-only
		STATUS	mandatory
		DESCRIPTION
			"Name of the IDP Host filter being applied"
	::= { accXnsHostFltrApplEntry 4 }
	accXnsHostFltrApplMatches	OBJECT-TYPE
		SYNTAX	Counter
		ACCESS	read-only
		STATUS	mandatory
		DESCRIPTION
			"Number of times the filter matched an IDP traffic 
			 packet - on the giveninterface"
	::= { accXnsHostFltrApplEntry 5 }
	accXnsHostFltrApplLastMatch	OBJECT-TYPE
		SYNTAX	TimeTicks
		ACCESS	read-only
		STATUS	mandatory
		DESCRIPTION
			"Time tick value when the filter last matched an IDP 
			 traffic packet - on thegiven interface"
	::= { accXnsHostFltrApplEntry 6 }

END
