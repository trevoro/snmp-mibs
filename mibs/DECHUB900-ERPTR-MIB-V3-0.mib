DECHUB900-ERPTR-MIB-V3-0 DEFINITIONS ::= BEGIN

--  +
--
--
--      Digital Equipment Corporation's DEChub900 Extensions to the 
--    Definitions of Managed Objects for IEEE 802.3 Repeater Devices
--    ______________________________________________________________
--
--
--
--                    Name:    erptr3-0.txt
--                    Version: 3.0
--                    Date:    April, 1997
--                    Company: Digital Equipment Corporation
--                    Mail:    hub900-support@lkg.dec.com
--
--
--
--
--  Status Of This Memo
--                                                                           
--     This Digital Equipment  Corporation SNMP Management Information Base
--     Specification embodies Digital Equipment Corporation's  confidential
--     and   proprietary   intellectual   property.    Digital    Equipment
--     Corporation  retains  all title and ownership in  the Specification,
--     including any revisions.
--  
--     It  is  Digital Equipment  Corporation's  intent  to  encourage  the
--     widespread   use  of  this  Specification  in  connection  with  the
--     management of Digital Equipment Corporation products.
--  
--     Digital Equipment Corporation  grants vendors,  end-users, and other
--     interested parties a non-exclusive license to use this Specification
--     in connection  with the management  of Digital Equipment Corporation
--     products.
--  
--     Digital Equipment Corporation  reserves the right to make changes in
--     this specification and other  information contained in this document
--     without prior notice.
--  
--     Digital Equipment Corporation makes no warranty, either expressed or
--     implied,  as to the use, operation, condition, or performance of the
--     Specification.  In no event shall Digital  Equipment  Corporation be
--     liable  for  any  incidental,  indirect,  special,  or consequential
--     damages whatsoever (including but  not limited to  loss of  profits)
--     arising out  of or  related  to  this document  or  the  information
--     contained in it.
--  
--
--  Abstract
--       
--     This document specifies a vendor-specific portion of the Management
--     Information Base (MIB) for managing DEChub 90 and DEChub 900 IEEE
--     802.3 baseband repeaters in the DEChub 900 platform. The objects
--     defined in this memo together with those defined in RFC 1516 and
--     other standard and vendor-specific MIBs provide a means of managing
--     Digital's repeater products.
--
-- -

-- +
--
--  1  Overview
--                                                                            
--     Instances of the object types defined in this memo represent
--     vendor-specific repeater attributes of Digital Equipment
--     Corporation's DEChub 900 MultiSwitch family and MultiSwitch
--     600 family of IEEE 802.3 (Ethernet-like) repeater products.  
--     The definition of MIB objects representing standard IEEE 802.3 
--     (Ethernet-like) repeater attributes of DEChub 900 or MultiSwtich
--     600 repeaters is outside the scope of this document.
-- 
--     The function and attributes of IEEE 803.3 (Ethernet-like) repeaters are
--     defined in Section 9, "Repeater Unit for 10 Mb/s Baseband Networks"
--     in the IEEE 802.3/ISO 8802-3 CSMA/CD standard [3].
--
--  Digital posts product MIBs on web sites at:
--
--            http://www.networks.digital.com/
--            http://www.networks.europe.digital.com/
--            http://www.networks.digital.com.au/
--  
--  This particular MIB is kept in:
--            
--            http://www.networks.digital.com/dr/hubs/mibs
--
--
--     Inquiries about the contents and use of this MIB may be sent to 
--     hub900-support@lkg.dec.com.
--
--
--  1.1 Terminology
--
-- 
--  1.1.1 DEChub 900 MultiSwitch Platform
--                                                                            
--     The following text defines "DEChub 900 MultiSwitch hub", "DEChub 900
--     module", "MultiSwitch 600", and "MultiSwitch 600 module" in general 
--     terms only.  Consult the DEChub 900 MultiSwitch Owner's Manual for 
--     a more detailed description of the hub and its features.  Consult
--     the MultiSwitch 600 Owner's Manual for a more detailed description
--     of the MultiSwitch 600 platform.
-- 
--     The DEChub 900 MultiSwitch hub is a manageable, multi-slot platform
--     whose backplane supports multiple LAN segments and network technologies
--     (e.g. Ethernet, FDDI, token ring, etc). The hub creates independent LAN
--     segments on its backplane from technology-independent flexible channels
--     or dedicated technology-dependent segments.
--                                                                             
--     The term "DEChub 900 module" refers to any physical device which can
--     operate in the DEChub 900 MultiSwitch hub, regardless of the network
--     technology it supports or the functions it provides. Examples of DEChub
--     900 modules include: IEEE 802.3 repeater, FDDI wiring concentrator, and
--     IEEE 802.5 token ring MAU.  A DEChub 900 module may also have the
--     ability to function as a stand-alone device outside of the DEChub 900
--     MultiSwitch hub. Older DEChub 90-family repeater modules may be
--     managed as DEChub 900 repeater modules.
--
--     The MultiSwitch 600 is a stackable platform is a workgroup/depart-
--     mental solution that integrates 10MB/s and 100Mb/s shared and
--     switched Ethernet products.  The stack contains up to seven Ethernet
--     backplane segments.  It may be unmanaged, or managed by adding a
--     Stack Director to the stack.
--
--     The term "MultiSwitch 600 module" refers to any physical device which
--     can operate in the MultiSwitch 600.  MultiSwitch 600 modules operate
--     in standalone, stackable, and chassis-based configurations for
--     maximum design flexibility and investment protection.  MultiSwitch
--     600 modules snap right into the DEChub 900 MultiSwitch chassis.  
--  
--
--  1.1.2 Repeaters, Groups, Ports, and MAUs
-- 
--     Unless otherwise noted, this memo uses the same definitions for the
--     terms "repeater", "group", "port", and "MAU" as the IETF repeater MIB
--     [6].
-- 
--     An IEEE 802.3 "repeater unit" is a physical layer device used to
--     connect multiple "Ethernet-like" media segments together. It receives
--     data from any of its segments, restores proper signal amplitude and
--     timing, and retransmits the data to all other attached segments. If the
--     repeater detects a collision on any segment, it propagates the
--     collision throughout the local area network.
-- 
--     The IEEE 802.3 standard defines a "repeater set" as the "repeater unit"
--     plus its associated MAUs (and AUIs if present).  The "repeater unit" is
--     defined as the portion of the repeater set that is inboard of the
--     physical media interfaces.  The MAUs may be physically separate from
--     the repeater unit, or they may be integrated into the same physical
--     package.
--
--     A DEChub 900 MultiSwitch or MultiSwitch 600 repeater module divides 
--     its ports into one or more groups. In this context, a group is an 
--     indivisible collection of ports which functions either as a single 
--     independent repeater unit or as part of a larger distributed repeater 
--     unit.
-- 
--     Multiple groups in a single repeater module may connect to separate 
--     independent DEChub 900 MultiSwitch or MultiSwitch 600 backplane LAN 
--     segments.  Groups (from the same module or from different modules) 
--     connected to the same flexible backplane channel operate in concert
--     as a single repeater unit in a hub or stack.
-- 
--     The manner in which a module's groups are configured to operate as a
--     single repeater unit and the manner in which a group is connected to
--     a backplane LAN segment are outside the scope of this memo.  Refer
--     to the product owner's manual for greater detail.
-- 
--     Each repeater module is managed individually as a single repeater 
--     instance, regardless of the configuration of its groups.  Even if
--     a repeater module is operating as part of a distributed repeater 
--     unit, its group and port tables only contain entries for groups 
--     and ports on that physical module. 
-- 
--
--  1.1.3 Internal Ports and MAUs
-- 
--     The IETF repeater mib [6] suggests that repeater ports may be
--     thought of as sources of traffic into the repeater. Such sources
--     include externally visible ports which appear in this MIB's port
--     table, as well as internal ports which are not obvious to the end
--     user but are still sources of traffic into the repeater.
--
--     DEChub 900 repeater modules may include internal ports which may or
--     may not be manageable from this MIB or the IETF repeater MIB [6].
--     Manageable internal ports appear in the relevant MIBs' port table.
--     Unmanageable internal ports do not. Therefore the sum of the input
--     counters for the repeater might not equal the actual output of the
--     repeater.
--
--     Examples of internal ports include internal in-band management ports
--     through which an embedded agent communicates and ports connecting to
--     the DEChub 900 MultiSwitch backplane. Whether or not such ports are
--     manageable is implementation-dependent.
--
--
--  2 Structure of MIB
--
--     Objects in this MIB are arranged into MIB groups.  Each MIB group is
--     organized as a set of related objects.
--
-- 
--  2.1 The Basic Group 
--
--     This mandatory group contains objects applicable to all DEChub 900
--     MultiSwitch and MultiSwitch 600 repeater modules.  It defines general 
--     statistics, configuration, control, and status objects for the repeater
--     as a whole, port-groups within the repeater and individual ports within
--     the groups.
--
--
--  2.2 The Address Database Group
--      
--     This optional group contains objects for keeping track of the MAC
--     addresses of end stations connected to individual repeater ports.
--
--
--  2.3 The Dual Port Redundancy Group
--
--     This optional group contains objects to configure and monitor pairs
--     of repeater ports operating as part of a dual redundant link.
--
--
--  2.4 The Security Package
--
--     This optional group contains configuration, control and status
--     objects to manage the intrusion detection/protection and eavesdrop
--     prevention features of DEChub 900 repeater modules.
--
--
--  2.5 The MAU Group
--
--     This optional group contains configuration, control and status
--     objects for MAUs associated with the repeater's ports.
--
--
--  2.6 The Address Learning Group
--     
--     This optional group contains configuration, control and status
--     objects for learning and recording the first N distinct MAC
--     sources addresses of readable frames received on each repeater port.
--
--
--  2.7 The Monitor Group
--     
--     This optional group contains monitoring statistics for the repeater as
--     a whole and for individual ports.  This group is an extension to the
--     monitoring statistics defined in the Monitor Group of the IETF repeater
--     MIB.
--
--
--  2.8  Relationship to the IETF IEEE 802.3 Repeater MIB
--                                                                             
--     This MIB represents private extensions to the IETF Repeater MIB. 
--                                                                            
--     Group and port table indices defined in this MIB, such as
--     'erptrGroupIndex', 'erptrPortGroupIndex' and 'erptrPortIndex' have
--     the same meaning as similarly named objects (e.g. 'rptrGroupIndex',
--     'rptrPortGroupIndex' and 'rptrPortIndex') defined in RFC 1516. These
--     indices are bound by the 'rptrGroupCapacity' and
--     'rptrGroupPortCapacity' objects defined in RFC 1516.       
--
--       
--  3 Object Synopsis
--
--     All objects in this MIB are prefixed with the object identifier
--     "e", where "e" is:
--
--        iso(1).org(3).dod(6).internet(1).private(4).enterprises(1).
--           dec(36).ema(2).decMIBextention(18).decHub900(11).
--              repeater(5).rptrVersion1(1)  
--
--     "Non-vol" indicates that the value of the settable object is
--     preserved when the DEChub 900 repeater module undergoes a power cycle.
--  
--  Object Name                                   Object ID         Non-vol
--  ===========                                   =========         =======
--  rptrExtensions                                e.1
--    erptrBasicPackage                           e.1.1
--      erptrRptrInfo                             e.1.1.1
--        erptrAutoPartitionAlg                   e.1.1.1.1.0       Non-vol 
--        erptrAutoPartitionReconnectAlg          e.1.1.1.2.0       Non-vol
--        erptrJamBits                            e.1.1.1.3.0       Non-vol
--        erptrHealthTextChanges                  e.1.1.1.4.0
--        erptrTotalPortEvents                    e.1.1.1.5.0
--        erptrTotalRptrErrors                    e.1.1.1.6.0
--        erptrJabberProtectionAdminStatus        e.1.1.1.7.0       Non-vol
--        erptrTotalPorts                         e.1.1.1.8.0
--        erptrPMDCarrierCardType                 e.1.1.1.9.0
--      erptrGroupInfo                            e.1.1.2
--        erptrGroupTable                         e.1.1.2.1
--          erptrGroupEntry                       e.1.1.2.1.1
--            erptrGroupIndex                     e.1.1.2.1.1.1.n
--            erptrGroupTransmitCollisions        e.1.1.2.1.1.2.n
--            erptrGroupReset                     e.1.1.2.1.1.3.n
--            erptrGroupLanTotalOctets            e.1.1.2.1.1.4.n
--      erptrPortInfo                             e.1.1.3
--        erptrPortTable                          e.1.1.3.1
--          erptrPortEntry                        e.1.1.3.1.1 
--            erptrPortGroupIndex                 e.1.1.3.1.1.1.n
--            erptrPortIndex                      e.1.1.3.1.1.2.n
--            erptrPortName                       e.1.1.3.1.1.3.n   Non-vol
--            erptrPortPartitions                 e.1.1.3.1.1.4.n
--            erptrPortPartitionReason            e.1.1.3.1.1.5.n
--            erptrPortMAUType                    e.1.1.3.1.1.6.n
--            erptrPortSQETestError               e.1.1.3.1.1.7.n
--     erptrAddrDBPackage                         e.1.2
--       erptrAddrDBRptrInfo                      e.1.2.1
--         erptrAddrDBTableCapacity               e.1.2.1.1.0
--       erptrAddrDBGroupInfo                     e.1.2.2
--       erptrAddrDBPortInfo                      e.1.2.3
--         erptrAddrDBPortAddrTable               e.1.2.3.1
--           erptrAddrDBPortAddrEntry             e.1.2.3.1.1
--             erptrAddrDBPortPhyAddr             e.1.2.3.1.1.1.n
--             erptrAddrDBPortGroupIndex          e.1.2.3.1.1.2.n
--             erptrAddrDBPortIndex               e.1.2.3.1.1.3.n
--     erptrDprPackage                            e.1.3
--       erptrDprRptrInfo                         e.1.3.1
--         erptrDprTotalStateChanges              e.1.3.1.1.0
--       erptrDprGroupInfo                        e.1.3.2
--       erptrDprPortInfo                         e.1.3.3
--         erptrDprLinkTable                      e.1.3.3.1
--           erptrDprLinkEntry                    e.1.3.3.1.1
--             erptrDprLinkGroupIndex             e.1.3.3.1.1.1.n
--             erptrDprLinkPortIndex              e.1.3.3.1.1.2.n
--             erptrDprLinkType                   e.1.3.3.1.1.3.n   Non-vol
--             erptrDprLinkToggle                 e.1.3.3.1.1.4.n
--             erptrDprLinkOperStatus             e.1.3.3.1.1.5.n
--             erptrDprSecondaryGroupIndex        e.1.3.3.1.1.6.n   Non-vol
--             erptrDprSecondaryPortIndex         e.1.3.3.1.1.7.n   Non-vol
--             erptrDprSecondaryOperStatus        e.1.3.3.1.1.8.n
--             erptrDprLinkName                   e.1.3.3.1.1.9.n   Non-vol
--             erptrDprLinkStateChanges           e.1.3.3.1.1.10.n
--             erptrDprLinkEntryStatus            e.1.3.3.1.1.11.n  Non-vol
--    erptrSecurityPackage                        e.1.4
--      erptrSecurityRptrInfo                     e.1.4.1
--        erptrSecurityRptrSecurityViolations     e.1.4.1.1.0
--        erptrSecurityRptrLogTable               e.1.4.1.2
--          erptrSecurityRptrLogEntry             e.1.4.1.2.1
--            erptrSecurityRptrLogIndex           e.1.4.1.2.1.1.n
--            erptrSecurityRptrLogGroupIndex      e.1.4.1.2.1.2.n
--            erptrSecurityRptrLogPortIndex       e.1.4.1.2.1.3.n
--            erptrSecurityRptrLogTime            e.1.4.1.2.1.4.n
--            erptrSecurityRptrLogPhysAddress     e.1.4.1.2.1.5.n
--        erptrSecurityRptrLogCapacity            e.1.4.1.3.0
--      erptrSecurityGroupInfo                    e.1.4.2
--      erptrSecurityPortInfo                     e.1.4.3
--        erptrSecurityPortCtrlTable              e.1.4.3.1
--          erptrSecurityPortCtrlEntry            e.1.4.3.1.1
--            erptrSecurityPortCtrlGroupIndex     e.1.4.3.1.1.1.n
--            erptrSecurityPortCtrlPortIndex      e.1.4.3.1.1.2.n
--            erptrSecurityPortCtrlEavesDropMode  e.1.4.3.1.1.3.n   Non-vol
--            erptrSecurityPortCtrlIntrusionMode  e.1.4.3.1.1.4.n   Non-vol
--            erptrSecurityPortCtrlOperStatus     e.1.4.3.1.1.5.n
--            erptrSecurityPortCtrlViolations     e.1.4.3.1.1.6.n
--        erptrSecurityPortAddrTable              e.1.4.3.2
--          erptrSecurityPortAddrEntry            e.1.4.3.2.1
--            erptrSecurityPortAddrGroupIndex     e.1.4.3.2.1.1.n   Non-vol
--            erptrSecurityPortAddrPortIndex      e.1.4.3.2.1.2.n   Non-vol
--            erptrSecurityPortAddrPhysAddress    e.1.4.3.2.1.3.n   Non-vol
--            erptrSecurityPortAddrStatus         e.1.4.3.2.1.4.n   Non-vol
--    erptrMauPackage                             e.1.5
--      erptrMauRptrInfo                          e.1.5.1
--        erptrMauTotalMediaUnavailable           e.1.5.1.1.0
--      erptrMauGroupInfo                         e.1.5.2
--      erptrMauPortInfo                          e.1.5.3
--        erptrMauTable                           e.1.5.3.1
--          erptrMauEntry                         e.1.5.3.1.1
--            erptrMauGroupIndex                  e.1.5.3.1.1.1.n
--            erptrMauPortIndex                   e.1.5.3.1.1.2.n
--            erptrMauIndex                       e.1.5.3.1.1.3.n
--            erptrMauLinkTestAdminStatus         e.1.5.3.1.1.4.n   Non-vol
--            erptrMauMediaPolarityStatus         e.1.5.3.1.1.5.n
--            erptrMauMediaAvailable              e.1.5.3.1.1.6.n
--            erptrMauMediaAvailableChanges       e.1.5.3.1.1.7.n
--            erptrMauMaxLinkLength               e.1.5.3.1.1.8.n   Non-vol
--    erptrAddrLearnPackage                       e.1.6
--      erptrAddrLearnRptrInfo                    e.1.6.1
--      erptrAddrLearnGroupInfo                   e.1.6.2
--      erptrAddrLearnPortInfo                    e.1.6.3
--        erptrAddrLearnPortCtrlTable             e.1.6.3.1
--          erptrAddrLearnPortCtrlEntry           e.1.6.3.1.1
--            erptrAddrLearnPortCtrlGroupIndex    e.1.6.3.1.1.1.n
--            erptrAddrLearnPortCtrlPortIndex     e.1.6.3.1.1.2.n
--            erptrAddrLearnPortCtrlCapacity      e.1.6.3.1.1.3.n
--            erptrAddrLearnPortCtrlAdminStatus   e.1.6.3.1.1.4.n
--            erptrAddrLearnPortCtrlOperStatus    e.1.6.3.1.1.5.n
--        erptrAddrLearnPortAddressTable          e.1.6.3.2
--          erptrAddrLearnPortAddressEntry        e.1.6.3.2.1
--            erptrAddrLearnPortAddressGroupIndex e.1.6.3.2.1.1.n
--            erptrAddrLearnPortAddressPortIndex  e.1.6.3.2.1.2.n
--            erptrAddrLearnPortAddressIndex      e.1.6.3.2.1.3.n
--            erptrAddrLearnPortAddress           e.1.6.3.2.1.4.n
--    erptrMonitorPackage                         e.1.7
--      erptrMonitorRptrInfo                      e.1.7.1
--      erptrMonitorGroupInfo                     e.1.7.2
--      erptrMonitorPortInfo                      e.1.7.3
--        erptrMonitorPortTable                   e.1.7.3.1
--          erptrMonitorPortEntry                 e.1.7.3.1.1
--            erptrMonitorPortGroupIndex          e.1.7.3.1.1.1.n
--            erptrMonitorPortIndex               e.1.7.3.1.1.2.n
--            erptrMonitorPortMulticastFrames     e.1.7.3.1.1.3.n
--            erptrMonitorPortBroadcastFrames     e.1.7.3.1.1.4.n
--
-- -

-- +
--
--  4 Definitions
--  
--  -

IMPORTS
    Counter, TimeTicks, Gauge, enterprises
        FROM RFC1155-SMI
    OBJECT-TYPE
        FROM RFC-1212
    DisplayString, PhysAddress
        FROM RFC1213-MIB;

--  Path to the extended repeater MIB.

dec                 OBJECT IDENTIFIER ::= { enterprises 36 }
ema                 OBJECT IDENTIFIER ::= { dec 2 }
decMIBextension     OBJECT IDENTIFIER ::= { ema 18 }
decHub900           OBJECT IDENTIFIER ::= { decMIBextension 11 }
repeater            OBJECT IDENTIFIER ::= { decHub900 5 }
rptrVersion1        OBJECT IDENTIFIER ::= { repeater 1 }
rptrExtensions      OBJECT IDENTIFIER ::= { rptrVersion1 1 }

--  +
--
--     Repeater MIB Groups
--
--  The erptrBasicPackage is mandatory.  All other groups are
--  optional.
--   
--  -
erptrBasicPackage
        OBJECT IDENTIFIER ::= { rptrExtensions 1 }

erptrAddrDBPackage
        OBJECT IDENTIFIER ::= { rptrExtensions 2 }

erptrDprPackage
        OBJECT IDENTIFIER ::= { rptrExtensions 3 }

erptrSecurityPackage 
        OBJECT IDENTIFIER ::= { rptrExtensions 4 }	

erptrMauPackage
        OBJECT IDENTIFIER ::= { rptrExtensions 5 }

erptrAddrLearnPackage
        OBJECT IDENTIFIER ::= { rptrExtensions 6 }

erptrMonitorPackage
        OBJECT IDENTIFIER ::= { rptrExtensions 7 }

--  +
--
--  Object identifiers for organizing the information in the groups by
--  repeater, port-group, and port.
--
--  -
erptrRptrInfo
        OBJECT IDENTIFIER ::= { erptrBasicPackage 1 }

erptrGroupInfo
        OBJECT IDENTIFIER ::= { erptrBasicPackage 2 }

erptrPortInfo
        OBJECT IDENTIFIER ::= { erptrBasicPackage 3 }

erptrAddrDBRptrInfo
        OBJECT IDENTIFIER ::= { erptrAddrDBPackage 1 }

erptrAddrDBGroupInfo      -- ** This subtree is currently unused.
        OBJECT IDENTIFIER ::= { erptrAddrDBPackage 2 }

erptrAddrDBPortInfo
        OBJECT IDENTIFIER ::= { erptrAddrDBPackage 3 }

erptrDprRptrInfo
        OBJECT IDENTIFIER ::= { erptrDprPackage 1 }

erptrDprGroupInfo         -- ** This subtree is currently unused.
        OBJECT IDENTIFIER ::= { erptrDprPackage 2 }

erptrDprPortInfo
        OBJECT IDENTIFIER ::= { erptrDprPackage 3 }

erptrSecurityRptrInfo 
	OBJECT IDENTIFIER ::= { erptrSecurityPackage 1 }

erptrSecurityGroupInfo    -- ** This subtree is currently unused.
	OBJECT IDENTIFIER ::= { erptrSecurityPackage 2 }

erptrSecurityPortInfo 
	OBJECT IDENTIFIER ::= { erptrSecurityPackage 3 }

erptrMauRptrInfo 
        OBJECT IDENTIFIER ::= { erptrMauPackage 1 }

erptrMauGroupInfo         -- ** This subtree is currently unused.
        OBJECT IDENTIFIER ::= { erptrMauPackage 2 }

erptrMauPortInfo 
        OBJECT IDENTIFIER ::= { erptrMauPackage 3 }

erptrAddrLearnRptrInfo          -- ** This subtree is currently unused.
        OBJECT IDENTIFIER ::= { erptrAddrLearnPackage 1 }

erptrAddrLearnGroupInfo         -- ** This subtree is currently unused.
        OBJECT IDENTIFIER ::= { erptrAddrLearnPackage 2 }

erptrAddrLearnPortInfo 
        OBJECT IDENTIFIER ::= { erptrAddrLearnPackage 3 }

erptrMonitorRptrInfo          -- ** This subtree is currently unused.
        OBJECT IDENTIFIER ::= { erptrMonitorPackage 1 }

erptrMonitorGroupInfo         -- ** This subtree is currently unused.
        OBJECT IDENTIFIER ::= { erptrMonitorPackage 2 }

erptrMonitorPortInfo 
        OBJECT IDENTIFIER ::= { erptrMonitorPackage 3 }

--  +
--                      The Basic Package
--
--  Implementation of the Basic Package is mandatory for all managed
--  repeaters.
--
--  -

--  +
--
--		      Basic Repeater Information
-- 
--  Configuration, status and control objects for the overall repeater.
--
--  -

erptrAutoPartitionAlg OBJECT-TYPE
    SYNTAX  INTEGER {
               standard(1),
               enhanced(2)
            }
    ACCESS  read-write                                -- ** Non-volatile
    STATUS  mandatory
    DESCRIPTION
	    "The auto-partition algorithm protects the network from certain
            fault conditions which can halt all LAN communications. A media
            short or break, a faulty connector, or faulty or missing media
            termination, are examples of such conditions.  If a repeater
            detects such faults on any of its ports, it isolates the faulty
            segment from the network.

            A repeater does not respond to input received from an
            auto-partitioned port, except to determine if the fault
            condition has been removed. A repeater continues to transmit
            data to an auto-partitioned port.

            Setting this object to standard(1) causes the repeater to
            implement the IEEE 802.3 standard auto-partitioning algorithm.
            If the repeater detects any of the following conditions on a
            given port, this algorithm isolates that port from the network.

	        1. Excessive length collision
                2. Excessive number of consecutive collisions

            Setting this object to enhanced(2) causes the repeater to
            implement an augmented auto-partitioning algorithm. This option
            protects the LAN from a greater range of fault conditions. If
            the repeater detects any of the following conditions on a given
            port, this algorithm isolates that port from the network.

                1. Excessive length collision
                2. Excessive number of consecutive collisions
                3. No receive activity during transmission (no
                   carrier loop back)
                4. Excessive length input message (jabber)
                5. Transmit carrier drop (one or more lapses in the
                   input message during a single output message
                   without a collision)
                6. Internal detectable port failures

            Some implementations may not support setting this object to all
            defined enumerated values. A badValue error is returned if an
            attempt is made to set this object to an unsupported value.

            Note: The state of this object is preserved when the repeater 
                  undergoes a power-up reset."
    REFERENCE
	    "Reference IEEE 802.3 Std, 9.6.6 Auto-Partitioning/Reconnection."
    ::= { erptrRptrInfo 1 }

erptrAutoPartitionReconnectAlg OBJECT-TYPE
    SYNTAX  INTEGER {
               standard(1),
               txOnly(2)
            }
    ACCESS  read-write                                -- ** Non-volatile
    STATUS  mandatory
    DESCRIPTION
            "The auto-partition reconnection algorithm defines the criteria
            for determining that a malfunction on an auto-partitioned port
            has been cleared. The auto-partitioned port reconnects and
            becomes a fully functional repeater port when these conditions
            are met. Reconnection criteria vary depending upon the
            auto-partition reason and reconnection algorithm.

            Setting this object to standard(1) causes the repeater to
            implement the IEEE 802.3 standard auto-partition reconnection
            algorithm. This algorithm reconnects a port auto-partitioned
            due to excessive length collisions or excessive number of
            consecutive collisions when the port transmits or receives a
            packet without detecting a collision.

            Setting this object to tx_only(2) causes the repeater to
            implement a more stringent auto-partition reconnection
            algorithm. This algorithm reconnects a port auto-partitioned
            due to excessive length collisions or excessive number of
            consecutive collisions only when the port transmits a packet
            without detecting a collision. This algorithm provides a higher
            level of confidence that all faults have been removed,
            resulting in a more robust fault isolation mechanism.

            Some implementations may not support setting this object to all
            defined enumerated values. A badValue error is returned if an
            attempt is made to set this object to an unsupported value.

	    The reconnection criteria for ports auto-partitioned due to no
            receive activity during transmission, excessive length input
            message, transmit carrier drop, and internal detectable port
            failures are not affected by this object's value.

            Note: The state of this object is preserved when the repeater 
                  undergoes a power-up reset."
    REFERENCE
	    "Reference IEEE 802.3 Std, 9.6.6 Auto-Partitioning/Reconnection"
    ::= { erptrRptrInfo 2 }

erptrJamBits OBJECT-TYPE
    SYNTAX  INTEGER {
               jb96(1),
               jb128(2)
            }
    ACCESS  read-write                                -- ** Non-volatile
    STATUS  mandatory
    DESCRIPTION
            "When a repeater detects a collision on any of the ports to
            which it is transmitting, it transmits a jam signal to all of
            the ports to which it is connected. This object specifies the
            minimum amount of time a repeater transmits a jam signal after
            it detects a collision. See the IEEE 802.3 standard for more
            details regarding collision detection and handling.

            Setting this object to jb96(1) causes the repeater to transmit
            jam for at least 96 bit times after it detects a collision.
            This setting complies with the IEEE 802.3 standard
            specification for the minimum jam time.

            Setting this object to jb128(1) causes the repeater to transmit
            jam for at least 128 bits times after it detects a collision.
            Some repeaters, designed prior to the development of the IEEE
            802.3 specification, jam for a minimum of 128 bit times after
            they detect collisions. It may be desirable for all the
            repeaters on the LAN to perform the same collision handling
            function. This setting provides a backwards compatibility mode
            when older repeaters are present in the network.

            Some implementations may not support setting this object to all
            defined enumerated values. A badValue error is returned if an
            attempt is made to set this object to an unsupported value.

            Note: If an implementation supports multiple minimum jam time
                  settings, the default value for this object is 
                  jb96(1).

            Note: The state of this object is preserved when the repeater 
                  undergoes a power-up reset."
    REFERENCE
	    "Reference IEEE 802.3 Std, 9.5.6 Collision Handling"
    ::= { erptrRptrInfo 3 }

erptrHealthTextChanges OBJECT-TYPE
    SYNTAX  Counter
    ACCESS  read-only
    STATUS  mandatory
    DESCRIPTION
            "This counter increments each time the rptrHealthText object
            defined in RFC 1516 is modified."
    REFERENCE
	    "Reference RFC 1516 repeater MIB"
    ::= { erptrRptrInfo 4 }

erptrTotalPortEvents OBJECT-TYPE
    SYNTAX  Counter
    ACCESS  read-only
    STATUS  mandatory
    DESCRIPTION
            "The total number of times any port in the repeater became
            not operational or auto-partitioned, or the media for any
            ports' MAUs became unavailable.  This object is a
            summation of the erptrPortPartitions and
            erptrMauMediaAvailableChanges counters of all the ports
            and MAUs in the repeater."
    REFERENCE
	    "Reference RFC 1516 repeater MIB"
    ::= { erptrRptrInfo 5 }

erptrTotalRptrErrors OBJECT-TYPE
    SYNTAX  Counter
    ACCESS  read-only
    STATUS  mandatory
    DESCRIPTION
            "The total number of errors which have occured on all 
             the groups in a repeater. This object is a summation
             of  the values of the rptMonitorGroupTotalErrors as 
             defined in RFC 1516 for all of the groups in a repeater."
    REFERENCE
	    "Reference RFC 1516 repeater MIB"
    ::= { erptrRptrInfo 6 }

erptrJabberProtectionAdminStatus OBJECT-TYPE
    SYNTAX  INTEGER {
               enabled(1),
               disabled(2)
            }
    ACCESS  read-write                                -- ** Non-volatile
    STATUS  mandatory
    DESCRIPTION
            "The jabber protection function automatically disables a
            port whenever it detects a very long input event (or
            jabber) on that port.  Once disabled, the port will
            neither transmit nor receive data.  The rptrOperStatus
            object for such a port will report notOperational(2).  The
            erptrPortPartitionReason for such a port will report
            jabberAndMgmtPart(7).  The port will remain in this state
            until the port's rptrPortAdminStatus object is set to
            enabled(1).

            Setting this object to enabled(1) enables the jabber
            protection function on all manageable repeater ports.
            Setting this object to disabled(2) disables the jabber
            protection function on all manageable repeater ports.

            Some implementations may not support setting this object to all
            defined enumerated values. A badValue error is returned if an
            attempt is made to set this object to an unsupported value.

            Note: The state of this object is preserved when the repeater 
                  undergoes a power-up reset."
    REFERENCE
	    "Reference RFC 1516 repeater MIB"
    ::= { erptrRptrInfo 7 }

erptrTotalPorts  OBJECT-TYPE
    SYNTAX  Counter
    ACCESS  read-only
    STATUS  mandatory
    DESCRIPTION
            "The total number of front panel ports in the repeater. This
             object is summation of rptrPortCapacity as defined in RFC1516
             for each group. This does not include the thinwire port for
             the repeater"
    ::= { erptrRptrInfo    8}

erptrPMDCarrierCardType  OBJECT-TYPE
    SYNTAX  INTEGER {
                     unknown(1),
                     type10Base(2)
                     }
    ACCESS  read-only
    STATUS  mandatory
    DESCRIPTION
            "The value unknown(1) indicates card that connects to MOD-PMDs
             are not present.

             The value type10Base (2) indicates card that connects to
             MOD-PMDs are present and the PMDS  that can be connected to this 
             card are of type 10base T and belongs to the family of IEEE 
             802.3 (Ethernet-like) repeater products."

   REFERENCE
            "Reference. IEEE 802.3 Std, sections 8, 9.9, 10, 14, 16, 17, 18."

    ::= { erptrRptrInfo    9}

--  +
--
--			Basic Port-Group Table
-- 
--  Configuration, status and control objects for the repeater port-groups.
--
--  -

erptrGroupTable OBJECT-TYPE
    SYNTAX  SEQUENCE OF ErptrGroupEntry
    ACCESS  not-accessible
    STATUS  mandatory
    DESCRIPTION
            "Table of descriptive and status information about the groups
            of ports."
    ::= { erptrGroupInfo 1 }

erptrGroupEntry OBJECT-TYPE
    SYNTAX  ErptrGroupEntry
    ACCESS  not-accessible
    STATUS  mandatory
    DESCRIPTION
            "An entry in the table containing information about a single
            group of ports."
    INDEX   { erptrGroupIndex }
    ::= { erptrGroupTable 1 }

ErptrGroupEntry ::=
    SEQUENCE {
        erptrGroupIndex
            INTEGER,
        erptrGroupTransmitCollisions
            Counter,
	erptrGroupReset
            INTEGER,
	erptrGroupLanTotalOctets
	    Counter
    } 

erptrGroupIndex OBJECT-TYPE
    SYNTAX  INTEGER (1..1024)
    ACCESS  read-only
    STATUS  mandatory
    DESCRIPTION
            "This object identifies the group within the repeater for which
            this entry contains information. This value is never greater
            than the rptrGroupCapacity object defined in RFC 1516."
    REFERENCE
	    "Reference RFC 1516 repeater MIB"
    ::= { erptrGroupEntry 1 }

erptrGroupTransmitCollisions OBJECT-TYPE
    SYNTAX  Counter
    ACCESS  read-only
    STATUS  mandatory
    DESCRIPTION
            "This counter increments every time the port-group's repeater
            state machine enters the TRANSMIT COLLISION state from any
            state other than ONE PORT LEFT. See Figure 9-2 in [3].

	    This object is similar to the rptrMonitorTransmitCollisions
            object defined in the IETF repeater MIB [6]. This counter is
            useful when a repeater module's port-groups are configured to 
            operate as independent repeater units. 

            The minimum rollover time of this counter is approximately 16
            hours."
    REFERENCE
            "Reference IEEE 802.3 Std, Figure 9-2 Repeater Unit State
            Machine. 
            Reference IETF Repeater MIB, RFC 1516."
    ::= { erptrGroupEntry 2 }

erptrGroupReset OBJECT-TYPE
    SYNTAX  INTEGER {
               noReset(1),
               reset(2)
            }
    ACCESS  read-write
    STATUS  mandatory
    DESCRIPTION
            "Setting this object to reset(2) causes the port-group's
            repeater unit state machine to transition to the START state of
            Fig 9-2 in section 9 [3].

            Setting this object to noReset(1) has no effect. The agent
            always returns the value noReset(1) when this object is read.

            This action does not reset management counters defined in
            either RFC 1516 or this document nor does is affect the
            portAdminStatus parameters defined in RFC 1516.

            This object is similar to the rptrReset object defined in RFC
            1516 except that it affects only a single group instance.

	    As a result of this action a rptrResetEvent trap is sent."
    REFERENCE
            "Reference IEEE 802.3 Std, Figure 9-2 Repeater Unit State
            Machine.
            Reference IETF Repeater MIB, RFC 1516."
    ::= { erptrGroupEntry 3 }

erptrGroupLanTotalOctets OBJECT-TYPE
    SYNTAX  Counter
    ACCESS  read-only
    STATUS  mandatory
    DESCRIPTION 
            "This object counts the total number of octets contained in
            non-collision packets transmitted by all the ports in this
            group.  This counter increments by the same amount for all
            groups configured to operate in concert as a single repeater
            unit.

            This counter is the aggregate of traffic received from all
            external and internal ports in this group, including unmanaged
            internal ports which do not appear in this group's port table.
            This object may report a different value than the
            rptrMonitorGroupTotalOctets counter defined in the IETF
            repeater MIB [6], which is defined as the summation of the
            values of the rptrMonitorPortReadableOctets counters for all of
            the ports appearing in this group's port table.

	    This statistic provides an indication of the total data
            transferred. The minimum rollover time of this counter is
            approximately 58 minutes."
    ::= { erptrGroupEntry 4 }

--  +
--
--			 The Basic Port Table
--
--  Configuration, status and control objects for repeater ports.
--
--  -

erptrPortTable OBJECT-TYPE
    SYNTAX  SEQUENCE OF ErptrPortEntry
    ACCESS  not-accessible
    STATUS  mandatory
    DESCRIPTION
            "Table of descriptive and status information about the ports."
    ::= { erptrPortInfo 1 }

erptrPortEntry OBJECT-TYPE
    SYNTAX  ErptrPortEntry
    ACCESS  not-accessible
    STATUS  mandatory
    DESCRIPTION
            "An entry in the table, containing information about a single
            port."
    INDEX    { erptrPortGroupIndex, erptrPortIndex }
    ::= { erptrPortTable 1 }

ErptrPortEntry ::=
    SEQUENCE {
        erptrPortGroupIndex
            INTEGER,
        erptrPortIndex
            INTEGER,
        erptrPortName
            DisplayString,
        erptrPortPartitions
            Counter,
        erptrPortPartitionReason
            INTEGER,
        erptrPortMAUType
            INTEGER,
	erptrPortSQETestError
	    INTEGER
        }

erptrPortGroupIndex OBJECT-TYPE
    SYNTAX  INTEGER (1..1024)
    ACCESS  read-only
    STATUS  mandatory
    DESCRIPTION            
            "This object identifies the group containing the port for which
            this entry contains information. This value is never greater
            than the rptrGroupCapacity object defined in RFC 1516"
    ::= { erptrPortEntry 1 }

erptrPortIndex OBJECT-TYPE
    SYNTAX  INTEGER (1..1024)
    ACCESS  read-only
    STATUS  mandatory
    DESCRIPTION
            "This object identifies the port within the group for which
            this entry contains information.  This value is never greater
            than the rptrGroupPortCapacity object defined in RFC 1516 for
            the associated group."
    ::= { erptrPortEntry 2 }

erptrPortName OBJECT-TYPE
    SYNTAX  DisplayString (SIZE (0..80))   
    ACCESS  read-write                                -- ** Non-volatile
    STATUS  mandatory
    DESCRIPTION
            "An administratively-assigned name for this repeater port.

            Note: The state of this object is preserved when the repeater 
                  undergoes a power-up reset."
    ::= { erptrPortEntry 3 }

erptrPortPartitions OBJECT-TYPE
    SYNTAX  Counter
    ACCESS  read-only
    STATUS  mandatory
    DESCRIPTION 
            "This counter increments by one each time the repeater
            auto-partitions this port or the port becomes disabled or
            otherwise not operational."
    ::= { erptrPortEntry 4 }

erptrPortPartitionReason OBJECT-TYPE
    SYNTAX  INTEGER {
               unknown(1),
               notPartitioned(2),
               managementPartitioned(3),
               excessiveCollision(4),
               excessiveCollisionAndMgmtPart(5),
               consecutiveCollisions(6),
               consecutiveCollisionsAndMgmtPart(7),
               jabber(8),
               jabberAndMgmtPart(9),
               noCarrierLoopback(10),
               noCarrierLoopbackandMgmtPart(11),
               transmitCarrierDropout(12),
               transmitCarrierDropoutAndMgmtPart(13),
               forcedReconnection(14)               
            }
    ACCESS  read-only
    STATUS  mandatory
    DESCRIPTION
            "This object describes the reason why a port is currently
            auto-partitioned or otherwise disabled.

            A value of unknown(1) indicates that the port currently has a
            rptrAutoPartitionState of autoPartitioned(2) and a
            rptrPortOperStatus of operational(1), as defined in RFC 1516,
            but the implementation cannot determine the exact reason why
            the port has auto-partitioned.

            A value of notPartitioned(2) indicates that the port currently
            has a rptrAutoPartitionState of notAutoPartitioned(1) and a
            rptrPortOperStatus of operational(1), as defined in RFC 1516.

            A value of managementPartitioned(3) indicates that the port
            currently has a rptrPortAdminStatus of disabled(2) (or is
            otherwise not operational) and a rptrAutoPartitionState of
            notAutoPartitioned(1), as defined in RFC 1516. However, if the
            port currently has a rptrPortAdminStatus of disabled(2) and a
            rptrAutoPartitionState of autoPartitioned(2), but the
            implementation cannot determine the exact reason why the port
            has auto-partitioned, then a value of managementPartitioned(3)
            is returned.

	    A value of excessiveCollision(4) indicates that the port
            currently has a rptrAutoPartitionState of autoPartitioned(2)
            and a rptrPortOperStatus of operational(1), as defined in RFC
            1516. The repeater auto-partitioned this port because it
            detected an 'excessive length collision' condition.

	    A value of excessiveCollisionAndMgmtPart(5) indicates that the
            port currently has a rptrAutoPartitionState of
            autoPartitioned(2) and a rptrPortOperStatus of
            notOperational(2), as defined in RFC 1516. The repeater
            auto-partitioned this port because it detected an 'excessive
            length collision' condition.

	    A value of consecutiveCollisions(6) indicates that the port
            currently has a rptrAutoPartitionState of autoPartitioned(2)
            and a rptrPortOperStatus of operational(1), as defined in RFC
            1516. The repeater auto-partitioned this port because it
            detected an 'excessive number of consecutive collisions'
            condition.

	    A value of consecutiveCollisionsandMgmtPart(7) indicates that
            the port currently has a rptrAutoPartitionState of
            autoPartitioned(2) and a rptrPortOperStatus of
            notOperational(2), as defined in RFC 1516. The repeater
            auto-partitioned this port because it detected an 'excessive
            number of consecutive collisions' condition.

	    A value of jabber(8) indicates that the port currently has a
            rptrAutoPartitionState of autoPartitioned(2) and a
            rptrPortOperStatus of operational(1), as defined in RFC 1516.
            The repeater auto-partitioned this port because it detected an
            'excessive length input message' condition.

	    A value of jabberAndMgmtPart(9) indicates that the port
            currently has a rptrAutoPartitionState of autoPartitioned(2)
            and a rptrPortOperStatus of notOperational(2), as defined in
            RFC 1516.  The repeater auto-partitioned this port because it
            detected an 'excessive length input message' condition.

	    A value of noCarrierLoopback(10) indicates that the port
            currently has a rptrAutoPartitionState of autoPartitioned(2)
            and a rptrPortOperStatus of operational(1), as defined in RFC
            1516.  The repeater auto-partitioned this port because it
            detected a 'no receive activity during transmission' condition.

	    A value of noCarrierLoopbackAndMgmtPart(11) indicates that the
            port currently has a rptrAutoPartitionState of
            autoPartitioned(2) and a rptrPortOperStatus of
            notOperational(2), as defined in RFC 1516.  The repeater
            auto-partitioned this port because it detected a 'no receive
            activity during transmission' condition.

	    A value of transmitCarrierDropout(12) indicates that the port
            currently has a rptrAutoPartitionState of autoPartitioned(2)
            and a rptrPortOperStatus of operational(1), as defined in RFC
            1516.  The repeater auto-partitioned this port because it
            detected a 'transmit carrier drop' condition.

	    A value of transmitCarrierDropoutAndMgmtPart(13) indicates that
            the port currently has a rptrAutoPartitionState of
            autoPartitioned(2) and a rptrPortOperStatus of
            notOperational(2), as defined in RFC 1516.  The repeater
            auto-partitioned this port because it detected a 'transmit
            carrier drop' condition."
    REFERENCE
	    "Reference IEEE 802.3 Std, 9.6.6 Auto-Partitioning/Reconnection."
    ::= { erptrPortEntry 5 }

erptrPortMAUType OBJECT-TYPE
    SYNTAX  INTEGER {
               unknown(1),
               typeAUI(2),
               type10Base5(3),
               typeFoirl(4),
               type10Base2(5),
               type10BaseT(6),
               type10BaseFP(7),
               type10BaseFB(8),
               type10BaseFL(9),
               typeTelco10BaseT(10),
               typeBackplaneThinwire(11),
               typeRAUI(12)
            }
    ACCESS  read-only
    STATUS  mandatory
    DESCRIPTION 
            "This object indicates the type of Medium Attachment Unit (MAU)
            associated with this port.
               unknown(1) - cannot determine MAU type.
	       typeAUI(2)      - no internal MAU, view from AUI.
               type10Base5(3)  - thick coax MAU (per IEEE 802.3 Std, section 8)
               typeFoirl(4)    - FOIRL MAU (per IEEE 802.3 Std, section 9.9)
               type10Base2(5)  - thin coax MAU (per IEEE 802.3 Std, section 10)
               type10BaseT(6)  - UTP Mau (per IEEE 802.3 Std, section 14) with
                               - a RJ45 style physical connector.
               type10BaseFP(7) - passive fiber MAU (per IEEE 802.3 Std,
                                 section 16)
               type10BaseFB(8) - sync fiber MAU (per IEEE 802.3 Std, 
                                 section 17)
               type10BaseFL(9) - asynch fiber MAU (per IEEE 802.3 Std,
                                 section 18)
               typeTelco10BaseT(10) - UTP Mau (per IEEE 802.3 Std, section 14)
                                      with a 50-pin Telco/champ style physical
                                      connector.
               typeBackplaneThinwire(11) - internal connection to the DEChub
                                           90's, DEChub 900MS, or MS600's 
                                           dedicated Ethernet LAN segment.
	       typeRAUI(12)      - no internal MAU, view from RAUI."

    REFERENCE
            "Reference. IEEE 802.3 Std, sections 8, 9.9, 10, 14, 16, 17, 18."
    ::= { erptrPortEntry 6 }

erptrPortSQETestError OBJECT-TYPE
    SYNTAX  INTEGER {
               unknown(1),
               sqeTestDetected(2),
               sqeTestNotDetected(3),
               sqeTestMasked(4)
            }
    ACCESS  read-only
    STATUS  mandatory
    DESCRIPTION
            "This object indicates whether or not a port has detected SQE
            Test messages from its attached MAU.  The value of this object
            persists between packets. This object is useful in detecting
            configuration errors which could seriously impact network
            performance.

            According to the IEEE 802.3 standard, MAUs associated with
            repeaters must not implement the signal_quality_error (SQE)
            message Test function.  MAUs implementing this function
            generate a short collision announcement to their attachment
            unit interfaces (AUIs) following the transmission of every
            packet. Repeaters may interpret this test message as an actual
            collision event and attempt to propagate the collision by
            transmitting a jam signal to all of its other ports.

            A value of unknown(1) indicates that an implementation does not
            have the ability to determine if it is receiving SQE Test
            messages.

            A value of sqeTestDetected(2) indicates that a SQE Test message
            was detected after the transmission of the last packet out this
            port. This message was interpreted as a collision, extended to
            a full Jam pattern and transmitted out every other repeater port.

            A value of sqeTestNotDetected(3) indicates that a SQE Test
            message was not detected after the transmission of the last
            packet out this port.

            A value of sqeTestMasked(4) indicates that a SQE Test message
            was detected after the transmission of the last packet out this
            port but this message was ignored and not interpreted as a
            collision.  This value is used by those implementations which
            offer SQE Test Masking functions."
    REFERENCE
            "Reference IEEE 802.3 Std., sections 7.2.1.2.3 and 9.4.1."
    ::= { erptrPortEntry 7 }

--  +
--
--                    The Address Database Package
--
--  Implementation of the Address Database Package group is optional.
--
--  -

--  +
--  
--		Address Database Repeater Information
--
--  -

erptrAddrDBTableCapacity  OBJECT-TYPE
    SYNTAX  INTEGER (1..65535)
    ACCESS  read-only
    STATUS  mandatory
    DESCRIPTION
            "This object specifies the maximum number of MAC addresses
            which can be stored in erptrAddrDBPortAddrTable."
    ::= { erptrAddrDBRptrInfo 1 }

--  +
--  
--                  Address Database Port Information
--
--  -

--  +
--		    Address Database Port Address Table
--    
--  This table maintains a database of the source addresses of readable
--  frames received from all repeater ports appearing in the agent's port
--  table. This information reveals the repeater port to which a given
--  station is connected.
--
--  This table augments the information found in the IETF repeater MIB's
--  Address Tracking Group [6]. The Address Tracking Group maps one address
--  per port. A repeater port may actually connect to multiple stations
--  (e.g. a port associated with a 10Base2 MAU). The Address Database
--  Port Address Table can map multiple addresses to a single port.
--
--  The number of entries in this table is dynamic depending upon the
--  number of distinct source addresses learned by the repeater.
--    
--  It is recommended that the agent automatically delete from this table
--  entries for addresses which have not been seen by the repeater for some
--  reasonable amount of time. The method and timeliness in which this is
--  accomplished is implementation dependent.
--
--  -

erptrAddrDBPortAddrTable  OBJECT-TYPE
    SYNTAX  SEQUENCE OF ErptrAddrDBPortAddrEntry
    ACCESS  not-accessible
    STATUS  mandatory
    DESCRIPTION
            "A table of port-mapping information about MAC addresses
            detected by the repeater."
    ::= { erptrAddrDBPortInfo 1 }

erptrAddrDBPortAddrEntry  OBJECT-TYPE
    SYNTAX  ErptrAddrDBPortAddrEntry
    ACCESS  not-accessible
    STATUS  mandatory
    DESCRIPTION
            "An entry in the table containing port-mapping information
            about a single MAC address."
    INDEX   { erptrAddrDBPortPhyAddr }
    ::= { erptrAddrDBPortAddrTable 1 }

ErptrAddrDBPortAddrEntry ::= 
    SEQUENCE {
        erptrAddrDBPortPhyAddr
            PhysAddress,
        erptrAddrDBPortGroupIndex
            INTEGER,
        erptrAddrDBPortIndex
            INTEGER
    }

erptrAddrDBPortPhyAddr OBJECT-TYPE
    SYNTAX  PhysAddress
    ACCESS  read-only
    STATUS  mandatory
    DESCRIPTION
            "This object identifies the source address of a readable frame
            received from a port in the agents port table."
    ::= { erptrAddrDBPortAddrEntry 1 }

erptrAddrDBPortGroupIndex OBJECT-TYPE
    SYNTAX  INTEGER ( 1..1024 )
    ACCESS  read-only
    STATUS  mandatory
    DESCRIPTION
            "This object identifies the group containing the port on which
            this entry's MAC address was seen."
    ::= { erptrAddrDBPortAddrEntry 2 }

erptrAddrDBPortIndex OBJECT-TYPE
    SYNTAX  INTEGER ( 1..1024 )
    ACCESS  read-only
    STATUS  mandatory
    DESCRIPTION
            "This object identifies the port within the group on which this
            entry's MAC address was seen."
    ::= { erptrAddrDBPortAddrEntry 3 }

--  +
--
--		     Dual Port Redundancy Package
--
--     
--  Implementation of the Dual Port Redundancy Package group is
--  optional. It is appropriate for all implementations which have the
--  necessary instrumentation.
-- 
--  A dual-redundant link provides a fault-tolerant network connection
--  which automatically switches traffic from an active link to a
--  backup/standby link when a fault is detected on the active link.
-- 
--  This group includes objects which manage the configuration, status and
--  control of repeater ports comprising one end of a dual-redundant link.
--  The ends of a redundant link are configured separately. 
--                                                                            
--  One end of a redundant link is designated the "master" while the other
--  end is designated the "responder". A repeater configured at the master end
--  of a redundant link pairs two of its ports together to form a master
--  primary link and a master secondary link. A repeater configured at the
--  responder end of a redundant link configures one or more of its ports to
--  operate at the responder end of either the primary link or the secondary
--  link.  Repeater ports configured for redundant responder operation do not
--  necessarily have to belong to the same repeater module.
--
--  The capability to for any repeater port to function as a redundant
--  responder port or as a member of a particular master redundant port pair is
--  implementation-specific.
--
--  -

--  +
--
--              Dual Port Redundancy Repeater-Level Information
--
--  -
erptrDprTotalStateChanges OBJECT-TYPE
    SYNTAX  Counter
    ACCESS  read-only
    STATUS  mandatory
    DESCRIPTION            
            "This counter increments whenever the erptrDprLinkStateChanges
            counter for any entry in erptrDprLinkTable increments. 

            This object is not necessarily the sum of the current values
            of the erptrDprLinkStateChanges objects for all entries in
            erptrDprLinkTable."
    ::= { erptrDprRptrInfo 1 }

--  +
--
--              Dual Port Redundancy Port-level Information
--
--  -
erptrDprLinkTable OBJECT-TYPE
    SYNTAX  SEQUENCE OF ErptrDprLinkEntry
    ACCESS  not-accessible
    STATUS  mandatory
    DESCRIPTION            
            "Table of redundant link configuration and status information."
    ::= { erptrDprPortInfo 1 }

erptrDprLinkEntry OBJECT-TYPE
    SYNTAX  ErptrDprLinkEntry
    ACCESS  not-accessible
    STATUS  mandatory
    DESCRIPTION
            "An entry in the table containing information describing a
            single redundant link's configuration and status."
    INDEX    { erptrDprLinkGroupIndex, erptrDprLinkPortIndex }
    ::= { erptrDprLinkTable 1 }

ErptrDprLinkEntry ::=
    SEQUENCE {
        erptrDprLinkGroupIndex
            INTEGER,
        erptrDprLinkPortIndex
            INTEGER,
        erptrDprLinkType
            INTEGER,
        erptrDprLinkToggle
            INTEGER,
        erptrDprLinkOperStatus
            INTEGER,
	erptrDprSecondaryGroupIndex
            INTEGER,
        erptrDprSecondaryPortIndex
            INTEGER,
        erptrDprSecondaryOperStatus
            INTEGER,
        erptrDprLinkName
            DisplayString,
        erptrDprLinkStateChanges
            Counter,
        erptrDprLinkEntryStatus
            INTEGER
        }

erptrDprLinkGroupIndex OBJECT-TYPE
    SYNTAX  INTEGER (1..1024)
    ACCESS  read-only
    STATUS  mandatory
    DESCRIPTION 
            "This object identifies the group containing the port which is a
            member of the dual-redundant link for which this entry contains
            information.  This value is never greater than
            rptrGroupCapacity."
    ::= { erptrDprLinkEntry 1 }

erptrDprLinkPortIndex OBJECT-TYPE
    SYNTAX  INTEGER (1..1024)
    ACCESS  read-only
    STATUS  mandatory
    DESCRIPTION
            "This object identifies the port within the group which is a
            member of the dual-redundant link for which this entry contains
            information.  If erptrDprLinkType is set to redundantMaster(1)
            this port is the master primary port of the redundant link.  If
            erptrDprLinkType is set to redundantResponder(2) this port is a
            responder port which may be connected to either the primary or
            secondary link. This value is never greater than
            rptrGroupPortCapacity for the associated group."
    ::= { erptrDprLinkEntry 2 }

erptrDprLinkType OBJECT-TYPE
    SYNTAX  INTEGER {
               redundantMaster(1),
               redundantResponder(2)
            }
    ACCESS  read-write                                -- ** Non-volatile
    STATUS  mandatory
    DESCRIPTION 
            "Setting this object to redundantMaster(1) causes the repeater to
            configure the port specified by erptrDprLinkGroupIndex and
            erptrDprLinkPortIndex as a Master port on the primary segment of
            a dual-redundant link.  This also implies that an additional
            port on this repeater module is configured as a Master port on
            the secondary segment of the dual-redundant link (as specified
            by erptrDprSecondaryGroupIndex and erptrDprSecondaryPortIndex).
            This port is in the active state by default following a reset or
            re-initialization.

            Setting this object to redundantResponder(2) causes the repeater to
            configure the port specified by erptrDprLinkGroupIndex and
            erptrDprLinkPortIndex as a responder port in a dual-redundant link.
            This port may be connected to either the primary or secondary
            link.  This port is in the active state by default following a
            reset or re-initialization.

            Note: Once this table entry has been validated
                  (i.e. erptrDprLinkEntryStatus is set to valid(1)), the
                  agent does not allow this object to be set to any value
                  other than the present setting. Any attempt to do
                  otherwise results in a badValue error. 

            Note: The state of this object is preserved when the repeater 
                  undergoes a power-up reset if the value of this entry's
                  erptrDprLinkEntryStatus is set to valid(1)."
    DEFVAL { redundantResponder }
    ::= { erptrDprLinkEntry 3 }

erptrDprLinkToggle OBJECT-TYPE
    SYNTAX  INTEGER {
               noToggle(1),
               toggle(2)
            }
    ACCESS  read-write
    STATUS  mandatory
    DESCRIPTION            
            "If erptrDprLinkType equals redundantMaster, setting this
            object to toggle(2) causes a redundant link specified by this
            table entry to undergo a state change. That is, the repeater
            forces the previously active link segment into the standby
            state and the previously inactive link segment into the active
            state.

            If erptrDprLinkType equals redundantResponder, setting this object
            to toggle(2) has no effect.

            Setting this object to noToggle(1) has no effect.  The agent
            always returns a value of noToggle(1) when this object is read." 
    DEFVAL { noToggle }
    ::= { erptrDprLinkEntry 4 }

erptrDprLinkOperStatus OBJECT-TYPE
    SYNTAX  INTEGER {
               redundancyNotOperational(1),
               masterPrimaryActive(2),
               masterPrimaryStandby(3),
               masterPrimaryLinkFailure(4),
               responderOk(5),
               responderLinkFailure(6)
            }
    ACCESS  read-only
    STATUS  mandatory
    DESCRIPTION            
            "This object reports the operational status of either the
            redundant master primary port or the redundant responder port
            associated with this entry (as specified by erptrDprLinkType).

            A value of redundancyNotOperational(1) indicates that redundancy
            is not operational on the link associated with this entry.

            A value of masterPrimaryActive(2) indicates: 
              - redundancy is operational on the link associated with this
                entry.
              - the port specified by erptrDprLinkGroupIndex and
                erptrDprLinkPortIndex is configured as a master port on the
                primary segment of the redundant link associated with this
                entry.
              - the primary segment of the dual-redundant link is currently
                the active link.
              - No link failures are currently detected on the primary link.

            A value of masterPrimaryStandby(3) indicates:
              - redundancy is operational on the link associated with this
                entry.
              - the port specified by erptrDprLinkGroupIndex and
                erptrDprLinkPortIndex is configured as a master port on the
                primary segment of the redundant link associated with this
                entry.
              - the primary segment of the dual-redundant link is currently
                the standby link.
              - No link failures are currently detected on the primary link.

            A value of masterPrimaryLinkFailure(4) indicates:
              - redundancy is operational on the link associated with this
                entry.
              - the port specified by erptrDprLinkGroupIndex and
                erptrDprLinkPortIndex is configured as a master port on the
                primary segment of the redundant link associated with this
                entry.
              - a link failure condition exists on the primary segment of
                the dual-redundant link (which may have caused a fail-over
                to the secondary link).

            A value of responderOk(5) indicates:
              - redundancy is operational on the link associated with this
                entry.
              - the port specified by erptrDprLinkGroupIndex and
                erptrDprLinkPortIndex is configured as a redundant responder
                port which may be connected to either the primary or the
                secondary segment of the redundant link associated with this
                entry.
              - the redundant responder port has not detected any link failures
                on the segment to which it is connected.

            A value of responderLinkFailure(6) indicates:
              - redundancy is operational on the link associated with this
                entry.
              - the port specified by erptrDprLinkGroupIndex and
                erptrDprLinkPortIndex is configured as a redundant responder
                port which may be connected to either the primary or the
                secondary segment of the redundant link associated with this
                entry.
              - the redundant responder port has detected a link failure on the
                segment to which it is connected."
    ::= { erptrDprLinkEntry 5 }

erptrDprSecondaryGroupIndex OBJECT-TYPE
    SYNTAX  INTEGER (0..1024)
    ACCESS  read-write                                -- ** Non-volatile
    STATUS  mandatory
    DESCRIPTION 
            "This object identifies the group containing the master redundant
            port on the secondary segment of the redundant link associated
            with this entry.

            This secondary redundant port acts in concert with the primary
            redundant port specified in erptrDprLinkGroupIndex and
            erptrDprLinkPortIndex to provide a fault-tolerant dual-redundant
            link when erptrDprLinkType is set to redundantMaster(1). The value
            of this object is irrelevant when erptrDprLinkType is set to any
            other value.

            When erptrDprLinkType is set to redundantMaster(1), the value of
            this object must be between 1 and rptrGroupCapacity for redundancy
            to be operational.

            Note: Once this table entry has been validated
                  (i.e. erptrDprLinkEntryStatus is set to valid(1)), the
                  agent does not allow this object to be set to any value
                  other than the present setting. Any attempt to do
                  otherwise results in a badValue error. 

            Note: The state of this object is preserved when the repeater 
                  undergoes a power-up reset if the value of this entry's
                  erptrDprLinkEntryStatus is set to valid(1)."
    DEFVAL { 0 }
    ::= { erptrDprLinkEntry 6 }

erptrDprSecondaryPortIndex OBJECT-TYPE
    SYNTAX  INTEGER (0..1024)
    ACCESS  read-write                                -- ** Non-volatile
    STATUS  mandatory
    DESCRIPTION 
            "This object identifies the master redundant port (within the
            group) on the secondary segment of the redundant link associated
            with this entry.

            This secondary redundant port acts in concert with the primary
            redundant port specified in erptrDprLinkGroupIndex and
            erptrDprLinkPortIndex to provide a fault-tolerant dual-redundant
            link when erptrDprLinkType is set to redundantMaster(1). The value
            of this object is irrelevant when erptrDprLinkType is set to any
            other value.

            When erptrDprLinkType is set to redundantMaster(1), the value of
            this object must be between 1 and rptrPortCapacity for this group
            for redundancy to be operational.

            Note: Once this table entry has been validated
                  (i.e. erptrDprLinkEntryStatus is set to valid(1)), the
                  agent does not allow this object to be set to any value
                  other than the present setting. Any attempt to do
                  otherwise results in a badValue error. 

            Note: The state of this object is preserved when the repeater 
                  undergoes a power-up reset if the value of this entry's
                  erptrDprLinkEntryStatus is set to valid(1)."
    DEFVAL { 0 }
    ::= { erptrDprLinkEntry 7 }

erptrDprSecondaryOperStatus OBJECT-TYPE
    SYNTAX  INTEGER {
               redundancyNotOperational(1),
               masterSecondaryActive(2),
               masterSecondaryStandby(3),
               masterSecondaryLinkFailure(4)
            }
    ACCESS  read-only
    STATUS  mandatory
    DESCRIPTION 
            "This object reports the operational status of the master redundant
            secondary port associated with this entry (as specified by
            erptrDprSecondaryGroupIndex and erptrDprSecondaryPortIndex).

            A value of redundancyNotOperational(1) indicates:                 
              - redundancy is not operational on the link associated with this
                entry.
              - this table entry is associated with a responder redundant port
                which makes the specification of a master secondary redundant
                port irrelevant.

            A value of masterSecondaryActive(2) indicates:
              - redundancy is operational on the link associated with this
                entry.
              - the port specified by erptrDprLinkGroupIndex and
                erptrDprLinkPortIndex is configured as a master port on the
                primary segment of the redundant link associated with this
                entry.
              - the secondary segment of the dual-redundant link is currently
                the active link.
              - No link failures are detected on the secondary link.

            A value of masterSecondaryStandby(3) indicates:
              - redundancy is operational on the link associated with this
                entry.
              - the port specified by erptrDprLinkGroupIndex and
                erptrDprLinkPortIndex is configured as a master port on the
                primary segment of the redundant link associated with this
                entry.
              - the secondary segment of the dual-redundant link is currently
                the standby link.
              - No link failures are detected on the secondary link.

            A value of masterSecondaryLinkFailure(4) indicates:
              - redundancy is operational on the link associated with this
                entry.
              - the port specified by erptrDprLinkGroupIndex and
                erptrDprLinkPortIndex is configured as a master port on the
                primary segment of the redundant link associated with this
                entry.
              - a link failure condition exists on the secondary segment of
                the dual-redundant link (which may have caused a fail-over
                to the primary link)."
    ::= { erptrDprLinkEntry 8 }

erptrDprLinkName OBJECT-TYPE
    SYNTAX  DisplayString (SIZE (0..16))   
    ACCESS  read-write                                -- ** Non-volatile
    STATUS  mandatory
    DESCRIPTION             
            "An administratively-assigned name for this dual-redundant
            link. 

            The default value for this object is a zero-length string. 

            Note: The state of this object is preserved when the repeater 
                  undergoes a power-up reset if the value of this entry's
                  erptrDprLinkEntryStatus is set to valid(1)."
    ::= { erptrDprLinkEntry 9 }

erptrDprLinkStateChanges OBJECT-TYPE
    SYNTAX  Counter
    ACCESS  read-only
    STATUS  mandatory
    DESCRIPTION 
            "This counter increments by one whenever the value of
            erptrDprLinkOperStatus or erptrDprSecondaryOperStatus changes."
    ::= { erptrDprLinkEntry 10 }

erptrDprLinkEntryStatus OBJECT-TYPE
    SYNTAX INTEGER {
               valid(1),
               createRequest(2),
               underCreation(3),
               invalid(4)
               }
    ACCESS read-write                                -- ** Non-volatile
    STATUS mandatory
    DESCRIPTION
            "The status of this table entry.

            Setting this object to createRequest(2) adds a new entry in this
            table.  Immediately after completing the create operation, the
            agent sets this object to underCreation(3). An existing instance
            of this object cannot be set to createRequest(2).

            Entries exist in the underCreation(3) state until the management
            station sets this object to valid(1) or aborts, setting this
            object to invalid(4).

            The repeater does not use the information in this entry to enforce
            redundancy unless this object is set to valid (1).

            Setting this object to invalid(4) has the effect of deleting this
            entry from the table.

            Note: The state of this object is preserved when the repeater 
                  undergoes a power-up reset if the value of this entry's
                  erptrDprLinkEntryStatus is set to valid(1)."
    ::= { erptrDprLinkEntry 11 }

--  +
--
--                    The Security Package
--
--  Implementation of the Security Package group is optional
--
--     
--  This group contains objects for managing security functions on all
--  repeater ports. To enforce security, a repeater port should be assigned
--  a list of MAC addresses belonging to stations authorized to use that
--  port. The Security Address Table performs this mapping of authorized
--  addresses to repeater ports. 
--
--  The maximum number of addresses that can be assigned to each port is
--  implementation-dependent.  This MIB group assumes that a model
--  implementation has the capability to allow pools of security address
--  resources to be shared among sets of ports.  An example implementation
--  may allow assigning up to 12 security addresses amongst 4 ports that
--  constitute a set.  Here, 12 security addresses may be assigned to one
--  port in the set when no security addresses are assigned to any of the
--  other ports in the set.  Alternatively, 3 security addresses may be
--  assigned to each of the ports in the set.  An implementation that maps
--  only one port to each set does not use shared security address
--  resources.
--
--  The group defines two distinct types of security capabilities, intrusion
--  detection/protection and eavesdrop prevention, each of which can be
--  enabled/disabled on a per port basis. The Security Control Table
--  manages the selection of these security features.
--
--                                  ____________
--                                 |  Repeater  |
--                                 |            |  ______________
--                                 | Authorized | | garbled pkt  | 
--                                 | Addresses  | |______________|   _________
--                                 | __________ |  ++++++++++++>    | Station |
--                                 |      A     []=================[]    A    |
--                 ______________  |            |                   |_________|
--                | garbled pkt  | |_ _ _ _ _ _ |
--    _________   |______________| |            |
--   | Station |   <+++++++++++++  |            |
--   |    B    []=================[]      B     |  
--   |_________|                   |            |  _____________
--                                 |_ _ _ _ _ _ | | garbled pkt |
--                                 |            | |_____________|    _________
--                                 |            |  +++++++++++++>   | Station |
--                                 |      C     []=================[]    C    |
--                                 |            |                   |_________|
--                                 |_ _ _ _ _ _ |
--     _________                   |            |
--    | Station |                  |            |
--    |    X    []================[]      D     |
--    |_________|  ==============> |____________|
--                  ___ ___ ______
--                 | C | X | DATA | 
--                 |___|___|______|
--         !! INTRUSION SECURITY VIOLATION !!
--
--
--                                                                          
--  Intrusion detection/protection prevents a station from transmitting
--  data to any other station from a repeater port it is not authorized to
--  use. To enforce intrusion protection, the repeater compares the source
--  addresses of packets received from a given port with the address(es) in
--  that port's authorized address list. If the addresses do not match, the
--  intrusion is logged in the Security Violations Log Table and
--  appropriate action is taken. Depending upon the intrusion security mode
--  selected, the repeater may take one of the following actions:
--
--       o Automatically disable the port that detected the violation,
--         thereby preventing any further violations.  A port disabled due
--         to a security violation must be manually re-enabled.  
--
--       o Garble the offending packet before repeating it to any other
--         port.
--   
--  An example of an intrusion violation is depicted in the above
--  figure. Here, Station X transmits a packet to Station C from a repeater
--  port which it is not authorized to use.  The repeater prevents Station
--  X from successfully communicating with Station C by either disabling
--  the port to which Station X is connected or garbling Station X's packet
--  before it can be received by Station C.
--     
--  Eavesdrop prevention prevents a station authorized to use a given
--  repeater port from receiving data packets addressed to any station
--  other than itself. To enforce eavesdrop prevention, the repeater
--  compares the unicast destination address of a packet being transmitted
--  out a given repeater port with the address(es) in that port's
--  authorized address list. If the addresses do not match, a garbled
--  version of the packet is transmitted. Otherwise, the packet is
--  transmitted unaltered. Packets with multicast or broadcast destination
--  addresses are never subject to eavesdrop prevention.
--
--                                  ____________
--                                 |  Repeater  |
--                                 |            |  ___ ___ ______
--                                 | Authorized | | B | A | DATA | 
--                                 | Addresses  | |___|___|______|   _________
--                                 | __________ |  <============    | Station |
--                                 |      A     []=================[]    A    |
--                 ___ ___ ______  |            |                   |_________|
--                | B | A | DATA | |_ _ _ _ _ _ |
--    _________   |___|___|______| |            |
--   | Station |   <=============  |            |
--   |    B    []=================[]      B     |  Eavesdrop Prevention
--   |_________|                   |            |  _____________
--                                 |_ _ _ _ _ _ | | garbled pkt |
--                                 |            | |_____________|    _________
--                                 |            |  +++++++++++++>   | Station |
--            Eavesdrop Prevention |      C     []=================[]    C    |
--                  _____________  |            |                   |_________|
--                 | garbled pkt | |_ _ _ _ _ _ |
--     _________   |_____________| |            |
--    | Station |   <++++++++++++  |            |
--    |    D    []================[]      D     |
--    |_________|                  |____________|
--                                 
--
--  An example of eavesdrop prevention is depicted in the above
--  figure. Here, Station A transmits a packet addressed to Station B.
--  Station B receives the packet correctly but Station C and Station D
--  receive a garbled version of the original packet.
--                                                                         
--  If eavesdrop prevention is enabled on a given port but that port's
--  authorized address list is empty, the repeater may optionally enforce
--  eavesdrop prevention based the last source address seen on that port
--  (as indicated by rptrAddrTrackLastSourceAddr or
--  rptrAddrTrackNewLastSrcAddress). 
--
--  -

--  +
--
--		 Security Repeater-Level Information
--
--  Security objects pertaining to the overall repeater.
--
--  -
erptrSecurityRptrSecurityViolations OBJECT-TYPE
    SYNTAX Counter
    ACCESS read-only
    STATUS mandatory
    DESCRIPTION
            "This counter increments by one each time the repeater detects an
            intrusion security violation on any repeater port. This counter is
            the summation of the erptrSecurityPortCtrlViolations counters for
            all the ports in all the groups of the repeater."
    ::= { erptrSecurityRptrInfo 1 }

--  +
--
--              The Security Violations Log Table
--        
--  Objects in this table report, in chronological order, the last "N"
--  intrusion security violations which have occurred on any port since the
--  agent last reset. An entry is added to the table when a repeater port
--  receives a data packet with a source address not found in that port's
--  authorized address list. This indicates that a station has attempted to
--  transmit data into a repeater port to which it is not authorized to be
--  connected.
--
--  The number of entries in the security log table is dynamic, depending
--  upon the number of intrusion security violations detected. The maximum
--  number of entries in this table is implementation dependent. 
--
--  This table is organized as a ring. If a given implementation supports a
--  maximum of 100 entries, the first 100 entries are indexed from 1 to
--  100. The 101st entry overwrites the oldest entry, entry 1, such that
--  the table contains entries indexed from 2 to 101.
--
--  -
erptrSecurityRptrLogTable OBJECT-TYPE
    SYNTAX  SEQUENCE OF ErptrSecurityRptrLogEntry
    ACCESS  not-accessible
    STATUS  mandatory
    DESCRIPTION            
            "A table of intrusion security violations. The maximum number of
            entries saved in the log table is implementation-specific."
    ::= { erptrSecurityRptrInfo 2 }

erptrSecurityRptrLogEntry OBJECT-TYPE
    SYNTAX  ErptrSecurityRptrLogEntry
    ACCESS  not-accessible
    STATUS  mandatory
    DESCRIPTION
            "An entry in the table containing information describing a
            single intrusion security violation."
    INDEX { erptrSecurityRptrLogIndex }
    ::= { erptrSecurityRptrLogTable 1 }

ErptrSecurityRptrLogEntry ::=
    SEQUENCE {
        erptrSecurityRptrLogIndex
            INTEGER,
        erptrSecurityRptrLogGroupIndex
            INTEGER,
        erptrSecurityRptrLogPortIndex
            INTEGER,
        erptrSecurityRptrLogTime
            TimeTicks,
        erptrSecurityRptrLogPhysAddress
            PhysAddress
        }

erptrSecurityRptrLogIndex OBJECT-TYPE
    SYNTAX  INTEGER (1..65535)
    ACCESS  read-only
    STATUS  mandatory
    DESCRIPTION
            "An index that uniquely identifies an entry in the log table."
    ::= { erptrSecurityRptrLogEntry 1 }

erptrSecurityRptrLogGroupIndex OBJECT-TYPE
    SYNTAX  INTEGER (1..1024)
    ACCESS  read-only
    STATUS  mandatory
    DESCRIPTION
            "This object identifies the group containing the port on which
            the intrusion security violation occurred."
    ::= { erptrSecurityRptrLogEntry 2 }

erptrSecurityRptrLogPortIndex OBJECT-TYPE
    SYNTAX INTEGER (1..1024)
    ACCESS read-only
    STATUS mandatory
    DESCRIPTION
            "This object identifies the port within the group on which this
            intrusion security violation occurred."
    ::= { erptrSecurityRptrLogEntry 3 }

erptrSecurityRptrLogTime OBJECT-TYPE
    SYNTAX TimeTicks
    ACCESS read-only
    STATUS mandatory
    DESCRIPTION
            "This object identifies the value of sysUpTime at the time the
            repeater detected the intrusion security violation."
    ::= { erptrSecurityRptrLogEntry 4 }

erptrSecurityRptrLogPhysAddress  OBJECT-TYPE
    SYNTAX PhysAddress
    ACCESS read-only
    STATUS mandatory
    DESCRIPTION
            "An intrusion security violation occurs when a repeater port
            receives a data packet with a source address not found in that
            port's authorized address list. This object identifies the
            unauthorized MAC address which caused the intrusion security
            violation."
    ::= { erptrSecurityRptrLogEntry 5 }

erptrSecurityRptrLogCapacity OBJECT-TYPE
    SYNTAX INTEGER (1..65535)
    ACCESS read-only
    STATUS mandatory
    DESCRIPTION 
            "This object specifies the maximum number of intrusion security
            violation log entries which can appear in
            erptrSecurityRptrLogTable at any one time."
    ::= { erptrSecurityRptrInfo 3 }

--  +
--
--  Security Port Information
--
--  Security configuration, status and control objects pertaining to
--  repeater ports.
--
--  -

--  +
--
--            The Security Control Table
--
--  The Security Control Table controls the operation of security
--  functions on repeater ports.  Each entry in the table specifies the
--  security rules for a repeater port.
--                                                     
--  Combinations of values for objects erptrSecurityPortCtrlEavesdropMode
--  and erptrSecurityPortCtrlIntrusionMode, and resulting security modes
--  are:
--
--   EavesdropMode IntrusionMode
--  +=============+============================================================
--   Disabled (2)  Disabled (1) -> No security
--      "     (2)  Enabled  (2) -> Intrusion Detection/no Eavesdrop Prevention
--      "     (2)      "    (3) -> Intrusion Protection/no Eavesdrop Prevention
--      "     (2)      "    (4) -> Intrusion Protection/no Eavesdrop Prevention
--
--   Enabled  (1)  Disabled (1) -> Eavesdrop Prevention only
--      "     (1)  Enabled  (2) -> Eavesdrop Prevention & Intrusion Detection
--      "     (1)      "    (3) -> Eavesdrop Prevention & Intrusion Protection
--      "     (1)      "    (4) -> Eavesdrop Prevention & Intrusion Protection
--  +=============+============================================================
--
--  -

erptrSecurityPortCtrlTable OBJECT-TYPE
    SYNTAX    SEQUENCE OF ErptrSecurityPortCtrlEntry
    ACCESS    not-accessible
    STATUS    mandatory
    DESCRIPTION             
            "A table of security configuration, control and status
            information."
    ::= { erptrSecurityPortInfo 1 }

erptrSecurityPortCtrlEntry OBJECT-TYPE
    SYNTAX  ErptrSecurityPortCtrlEntry
    ACCESS  not-accessible
    STATUS  mandatory
    DESCRIPTION
            "An entry in the table containing information describing the
            security configuration and status of a single port."
    INDEX  { erptrSecurityPortCtrlGroupIndex, erptrSecurityPortCtrlPortIndex }
    ::= { erptrSecurityPortCtrlTable 1 }

ErptrSecurityPortCtrlEntry ::=
    SEQUENCE {
        erptrSecurityPortCtrlGroupIndex
            INTEGER,
        erptrSecurityPortCtrlPortIndex
            INTEGER,
        erptrSecurityPortCtrlEavesdropMode
            INTEGER,
        erptrSecurityPortCtrlIntrusionMode
            INTEGER,
        erptrSecurityPortCtrlOperStatus
            INTEGER,
        erptrSecurityPortCtrlViolations
            Counter
        }

erptrSecurityPortCtrlGroupIndex OBJECT-TYPE
    SYNTAX INTEGER (1..1024)
    ACCESS read-only
    STATUS mandatory
    DESCRIPTION
            "This object identifies the group containing the port for which
            this entry contains information. This value is never greater
            than rptrGroupCapacity."
    ::= { erptrSecurityPortCtrlEntry 1 }

erptrSecurityPortCtrlPortIndex OBJECT-TYPE
    SYNTAX INTEGER (1..1024)
    ACCESS read-only
    STATUS mandatory
    DESCRIPTION
            "This object identifies the port within the group for which
            this entry contains information.  This value is never greater
            than rptrGroupPortCapacity for the associated group."
    ::= { erptrSecurityPortCtrlEntry 2 }

erptrSecurityPortCtrlEavesdropMode OBJECT-TYPE
    SYNTAX INTEGER {
              enabled (1),
              disabled (2)
           }
    ACCESS read-write                                -- ** Non-volatile
    STATUS mandatory
    DESCRIPTION 
            "Setting this object to enabled (1) enables eavesdrop
            prevention on this port. 

            When eavesdrop prevention is active, the repeater compares
            unicast destination addresses of packets being transmitting out
            this port with the port's authorized address list. The repeater
            jams/garbles those packets whose destination addresses do not
            appear in the port's authorized address list. The length of the
            garbled packet is the same as the length of the original
            packet.  Packets with multicast or broadcast destination
            addresses are not affected by eavesdrop prevention.

            If no authorized addresses are assigned to this port in
            erptrSecurityPortAddrTable when this object equals enabled(1),
            an implementation may optionally enforce eavesdrop prevention
            based upon the (dynamically changing) last source address seen
            (as indicated by rptrAddrTrackLastSourceAddr or
            rptrAddrTrackNewLastSrcAddress). Otherwise, an implementation
            may simply not actively enforce eavesdrop prevention on a port
            with no assigned authorized addresses. 

            Setting this object to disabled (2) disables eavesdrop
            prevention on this port.

            Note: The default value for this object is disabled (2).

            Note: The state of this object is preserved when the repeater 
                  undergoes a power-up reset."
    REFERENCE
	    "Reference RFC 1516 repeater MIB"
    ::= { erptrSecurityPortCtrlEntry 3 }

erptrSecurityPortCtrlIntrusionMode OBJECT-TYPE
    SYNTAX INTEGER {
              disabled (1),
              notifyOnly (2),
              jamUnauthPackets (3),
              disablePort (4)
           }
    ACCESS read-write                                -- ** Non-volatile
    STATUS mandatory
    DESCRIPTION 
            "To detect intrusion security violations, the repeater compares
            source addresses of packets received from this port with the
            addresses in the port's authorized address list (as specified
            in erptrSecurityPortAddrTable). If the addresses do not match,
            the intrusion is counted, logged in erptrSecurityRptrLogTable,
            and and the security rule specified by this object is enforced.
            Intrusion protection is not active unless authorized addresses
            are assigned to this port in erptrSecurityPortAddrTable.

            Setting this object to disabled (1) disables intrusion
            detection/prevention on this port.

            Setting this object to notifyOnly (2) causes the repeater to
            take no action, other than logging entries in
            erptrSecurityRptrLogTable, when it detects intrusion
            violations.

	    Setting this object to jamUnauthPackets (3) causes the repeater
            to jam/garble unauthorized packets before they are repeated to
            all other repeater ports.

            Setting this object to disablePort (4) causes the repeater to
            disable this port if it detects intrusion security violations
            on this port. The port may be re-enabled by setting
            rptrPortAdminStatus to enabled.

            Some implementations may not support setting this object to all
            defined enumerated values. A badValue error is returned if an
            attempt is made to set this object to an unsupported value.

            Note: The default value for this object is disabled (1).

            Note: The state of this object is preserved when the repeater 
                  undergoes a power-up reset."
    ::= { erptrSecurityPortCtrlEntry 4 }

erptrSecurityPortCtrlOperStatus OBJECT-TYPE
    SYNTAX INTEGER {
              securityOperational (1),
              securityNotOperational (2),
              violationPortDisabled (3)
           }
    ACCESS read-only
    STATUS mandatory
    DESCRIPTION 
            "The value securityOperational(1) indicates that eavesdrop
            prevention and/or intrusion detection/protection are enabled
            and actively functioning on this port.

	    The value securityNotOperational(2) indicates that neither
            eavesdrop prevention nor intrusion detection/protection are
            actively functioning on this port. Intrusion
            detection/protection may be enabled on this port but it will
            not be operational unless an authorized address is assigned to
            this port in erptrSecurityPortAddrTable.

	    The value violationPortDisabled (3) indicates that the port is
            disabled due to an intrusion security violation. The port may
            be re-enabled by setting rptrPortAdminStatus to enabled."
    ::= { erptrSecurityPortCtrlEntry 5 }

erptrSecurityPortCtrlViolations OBJECT-TYPE
    SYNTAX Counter
    ACCESS read-only
    STATUS mandatory
    DESCRIPTION
            "A count of the number intrusion security violations detected
            on this port."
    ::= { erptrSecurityPortCtrlEntry 6 }

--  +
--
--			The Security Address Table
--      
--  Objects in this table map authorized MAC addresses to repeater ports.
--  The repeater uses these addresses to enforce intrusion and eavesdrop
--  security.
--
--  Entries to this table may be added dynamically.  The maximum number of
--  entries in the table and the maximum number of addresses assigned to a
--  single port are implementation specific quantities.
--
--  -
erptrSecurityPortAddrTable OBJECT-TYPE
    SYNTAX SEQUENCE OF ErptrSecurityPortAddrEntry
    ACCESS not-accessible
    STATUS mandatory
    DESCRIPTION            
            "A table of authorized MAC addresses mapped to repeater ports.
            The repeater uses these addresses to enforce security."
    ::= { erptrSecurityPortInfo 2 }

erptrSecurityPortAddrEntry OBJECT-TYPE
    SYNTAX ErptrSecurityPortAddrEntry
    ACCESS not-accessible
    STATUS mandatory
    DESCRIPTION
            "An entry in the table containing information to assign a
            single authorized MAC address to a single repeater port."
    INDEX  { erptrSecurityPortAddrGroupIndex,
             erptrSecurityPortAddrPortIndex,
             erptrSecurityPortAddrPhysAddress }
    ::= { erptrSecurityPortAddrTable 1 }

ErptrSecurityPortAddrEntry ::=
    SEQUENCE {
        erptrSecurityPortAddrGroupIndex
            INTEGER,
        erptrSecurityPortAddrPortIndex
            INTEGER,
        erptrSecurityPortAddrPhysAddress
            PhysAddress,
        erptrSecurityPortAddrStatus
            INTEGER
         }

erptrSecurityPortAddrGroupIndex OBJECT-TYPE
    SYNTAX  INTEGER (1..1024)
    ACCESS  read-write                                -- ** Non-volatile
    STATUS  mandatory
    DESCRIPTION
            "This object identifies the group containing the port for which
            this entry contains information.  This value is never greater
            than rptrGroupCapacity.

            Note: The state of this object is preserved when the repeater
                  undergoes a power-up reset if the value of this entry's
                  erptrSecurityPortAddrStatus is valid (1)."
    ::= { erptrSecurityPortAddrEntry 1 }

erptrSecurityPortAddrPortIndex OBJECT-TYPE
    SYNTAX INTEGER (1..1024)
    ACCESS read-write                                -- ** Non-volatile
    STATUS mandatory
    DESCRIPTION            
            "This object identifies the port within the group for which
            this entry contains information.  This value can never be
            greater than rptrGroupPortCapacity for the associated group.

            Note: The state of this object is preserved when the repeater
                  undergoes a power-up reset if the value of this entry's
                  erptrSecurityPortAddrStatus is valid (1)."
    ::= { erptrSecurityPortAddrEntry 2 }

erptrSecurityPortAddrPhysAddress  OBJECT-TYPE
    SYNTAX PhysAddress
    ACCESS read-write                                -- ** Non-volatile
    STATUS mandatory
    DESCRIPTION
            "This object identifies an authorized MAC address assigned to
            this repeater port for use in enforcing eavesdrop prevention
            and intrusion detection/protection.

            Note: The state of this object is preserved when the repeater
                  undergoes a power-up reset if the value of this entry's
                  erptrSecurityPortAddrStatus is valid (1)."
    ::= { erptrSecurityPortAddrEntry 3 }

erptrSecurityPortAddrStatus OBJECT-TYPE
    SYNTAX INTEGER {
               valid(1),
               createRequest(2),
               underCreation(3),
               invalid(4)
               }
    ACCESS read-write                                -- ** Non-volatile
    STATUS mandatory
    DESCRIPTION
            "The status of this table entry.

            Setting this object to createRequest(2) adds a new entry in
            this table mapping the authorized MAC address specified by this
            entry to the port specified by this entry.  Immediately after
            completing the create operation, the agent sets this object to
            underCreation(3). An existing instance of this object cannot be
            set to createRequest(2).

            Entries exist in the underCreation(3) state until the
            management station sets this object to valid(1) or aborts,
            setting this object to invalid(4).

            The repeater does not use the information in this entry to
            enforce security unless this object is set to valid (1).

            Setting this object to invalid(4) has the effect of deleting
            this entry from the table.

            Note: The state of this object is preserved when the repeater
                  undergoes a power-up reset if the value of this entry's
                  erptrSecurityPortAddrStatus is valid (1)."
    ::= { erptrSecurityPortAddrEntry 4 }

--  +
--
--                 The Repeater MAU Package
--
--  Implementation of the MAU Package group is optional.
--
--  Configuration, status and control objects for MAUs attached 
--  to repeater ports.
--
--  -

--  +
--
--		    MAU Repeater-Level Information
--
--  -

erptrMauTotalMediaUnavailable OBJECT-TYPE
    SYNTAX  Gauge
    ACCESS  read-only
    STATUS  mandatory
    DESCRIPTION 
            "This object returns the total number of MAUs in the repeater
            whose erptrMauMediaAvailable objects are equal to
            notAvailable(4), remoteFault(5), or invalidSignal(6)."
    ::= { erptrMauRptrInfo 1 } 

--  +
--
--                 Mau Port Information
--
--  -
erptrMauTable OBJECT-TYPE
    SYNTAX  SEQUENCE OF ErptrMauEntry
    ACCESS  not-accessible
    STATUS  mandatory
    DESCRIPTION            
            "Table of descriptive and status information about MAU(s)
            attached to the ports of a repeater."
    ::= { erptrMauPortInfo 1 }

erptrMauEntry OBJECT-TYPE
    SYNTAX  ErptrMauEntry
    ACCESS  not-accessible
    STATUS  mandatory
    DESCRIPTION
            "An entry in the table containing information about a single
            MAU."
    INDEX    { erptrMauGroupIndex, erptrMauPortIndex, erptrMauIndex }
    ::= { erptrMauTable 1 }

ErptrMauEntry ::=
    SEQUENCE {
        erptrMauGroupIndex
            INTEGER,
        erptrMauPortIndex
            INTEGER,
        erptrMauIndex
            INTEGER,
        erptrMauLinkTestAdminStatus
            INTEGER,
        erptrMauMediaPolarityStatus
            INTEGER,
	erptrMauMediaAvailable
	    INTEGER,
	erptrMauMediaAvailableChanges
	    Counter,
        erptrMauMaxLinkLength
            INTEGER
        }

erptrMauGroupIndex OBJECT-TYPE
    SYNTAX  INTEGER (1..1024)
    ACCESS  read-only
    STATUS  mandatory
    DESCRIPTION
            "This object identifies the group containing the port to which
            the MAU described by this entry is connected."
    ::= { erptrMauEntry 1 }

erptrMauPortIndex OBJECT-TYPE
    SYNTAX  INTEGER (1..1024)
    ACCESS  read-only
    STATUS  mandatory
    DESCRIPTION
            "This object identifies the port within group to which the MAU
            described by this entry is connected."
    ::= { erptrMauEntry 2 }

erptrMauIndex OBJECT-TYPE
    SYNTAX  INTEGER (1..1024)   
    ACCESS  read-only
    STATUS  mandatory
    DESCRIPTION
            "The object uniquely identifies a MAU connected to a port
            within the group that is described by this entry."
    ::= { erptrMauEntry 3 }

erptrMauLinkTestAdminStatus OBJECT-TYPE
    SYNTAX  INTEGER {
               enabled(1),
               disabled(2)
            }
    ACCESS  read-write                                -- ** Non-volatile
    STATUS  mandatory
    DESCRIPTION
            "Link test functions detect certain types of media faults on
            point-to-point link segments connecting pairs of link-type MAUs
            (e.g. 10BASE-T, 10BASE-F, FOIRL). This object controls the link
            test function implemented by some link-type MAUs.

            Setting this object to enabled(1) causes the MAU to enable its
            link test function.

            Setting this object to disabled(2) causes the MAU to disable
            its link test function. Disabling a MAU's link test function
            can be useful for compatibility to link-type MAUs which do not
            implement a link test function.

            Link-type MAUs which implement link test functions but do not
            support software control of the functions allow this object to
            be set to enabled(1).  A badValue error is returned if this
            object is set to any other value.

            Coax type MAUs (e.g. 10BASE5, 10BASE2) or any other MAUs which
            do not implement link test functions return disabled(2) when
            this object is read. These MAUs allow this object to be set to
            disabled(2) but return a badValue error if the object is set to
            any other value.

            Note: The state of this object is preserved when the repeater 
                  undergoes a power-up reset."
    REFERENCE
            "Reference IEEE 802.3 Std., sections 9.9.2.1 and 14.2.1.7."
    ::= { erptrMauEntry 4 }

erptrMauMediaPolarityStatus OBJECT-TYPE
    SYNTAX  INTEGER {
               polarityNotReversed(1),
               polarityReversed(2),
               polarityCorrected(3),
	       unknown(4)
            }
    ACCESS  read-only
    STATUS  mandatory
    DESCRIPTION
            "A value of polarityNotReversed(1) indicates that the MAU
            senses that received data packet waveform polarity is correct.

            A value of polarityReversed(2) indicates that the MAU senses
            that received data packet waveform polarity is incorrect (i.e.
            reversed).  Reversed polarity may indicate a wiring error,
            especially on 10Base-T links.

            A value of polarityCorrected(3) indicates that the MAU senses
            that received data packet waveform polarity is incorrect (i.e
            reversed, perhaps due to a wiring error) but the MAU has
            automatically corrected the polarity error.

            A value of unknown(4) indicates that the MAU does not have the
            ability to detect whether or not received data packet waveform
            polarity is correct."
    ::= { erptrMauEntry 5 }

erptrMauMediaAvailable OBJECT-TYPE
    SYNTAX    INTEGER {
                 other(1),
                 unknown(2),
                 available(3),
                 notAvailable(4),
                 remoteFault(5),
                 invalidSignal(6)
              }
    ACCESS    read-only
    STATUS    mandatory
    DESCRIPTION             
            "If the MAU is link-type (FOIRL, 10BASE-T, 10BASE-F) then this
            object is equivalent to the link test fail state/low light
            function.  For an AUI or a coax MAU this indicates whether or
            not loopback is detected on the DI circuit.  The value of this
            attribute persists between packets for MAU types AUI, 10BASE5,
            10BASE2, and 10BASE-FP.  The value other(1) is returned if the
            mediaAvailable state is not one of 2 through 6.

            The value unknown(2) is returned when the MAU's true state is
            unknown; for example, when it is being initialized.  At
            power-up or following a reset, the value of this attribute is
            unknown for AUI, coax, and 10BASE-FP MAUs.  For these MAUs,
            loopback will be tested on each transmission during which no
            collision is detected.  If DI is receiving input when DO
            returns to IDL after a transmission and there has been no
            collision during the transmission then loopback will be
            detected.  The value of this attribute will only change during
            non-collided transmissions for AUI, coax, and 10BASE-FP MAUs.

            The value available(3) indicates that the link, light, or
            loopback is normal.  The value notAvailable(4) indicates link
            loss, low light, or no loopback.

            The value remoteFault(5) indicates that a fault has been
            detected at the remote end of the link.  The value
            invalidSignal(6) indicates that an invalid signal has been
            received from the other end of the link.  Both remoteFault(5)
            and invalidSignal(6) apply only to MAUs of type 10BASE-FB."
    REFERENCE
            "Reference IEEE 802.3 MAU Mgt, 20.2.3.2, aMediaAvailable."
    ::= { erptrMauEntry 6 }

erptrMauMediaAvailableChanges OBJECT-TYPE
    SYNTAX    Counter
    ACCESS    read-only
    STATUS    mandatory
    DESCRIPTION
            "A count of the number of times that erptrMauMediaAvailable for
            this MAU instance leaves the state available(3)."
    REFERENCE
            "Reference IEEE 802.3 MAU Mgt, 20.2.3.2, lostMediaCount."
    ::= { erptrMauEntry 7 }

erptrMauMaxLinkLength OBJECT-TYPE
    SYNTAX  INTEGER {
               standard(1),
               extended(2)
            }
    ACCESS  read-write                                -- ** Non-volatile
    STATUS  mandatory
    DESCRIPTION
            "Link-type MAU (e.g. 10BASE-T, 10BASE-FL, FOIRL) standards
            define the maximum length of any one point-to-point link
            segment.  Some MAUs may support a mode of operation that allows
            them to reliably communicate over longer link segments. This
            object configures the MAU to run it its standard max link
            length mode of operation or its extended max link length mode
            of operation.  The mechanisms employed to achieve longer link
            segments is implementation-specific. The existence of
            configuration restrictions surrounding using a MAUs extended
            link length mode is implementation-specific.

            Setting this object to standard(1) causes the MAU to support
            only standard max link length configurations.

            Setting this object to extended(2) causes the MAU to support
            extended maximum link length configurations. The maximum link
            length supported by a MAU operating in this mode is
            implementation-specific.

            Any MAUs (including non-link, coax type MAUs) that do not
            support extended maximum link length configurations allow this
            object to be set to standard(1).  A badValue error is returned
            if this object is set to any other value.

            Note: The state of this object is preserved when the repeater 
                  undergoes a power-up reset."
    REFERENCE
            "Reference IEEE 802.3 Std."
    ::= { erptrMauEntry 8 }

--  +
--
--		       The Address Learning Package
--                                                                         
--  Implementation of the Address Learning Package group is optional. It is
--  appropriate for all implementations which have the necessary
--  instrumentation.  
-- 
--  This group manages a repeater's capability to learn and save the first N
--  distinct MAC source addresses seen on each port. The agent can start and
--  stop the learning process on a per-port basis at will (per the request of a
--  network management station).
--
--  - 

--  +
--
--		     Address Learning Port Information
--
--  -

--  +
--
--		    The Address Learning Control Table
--
--  -
erptrAddrLearnPortCtrlTable OBJECT-TYPE
    SYNTAX    SEQUENCE OF ErptrAddrLearnPortCtrlEntry
    ACCESS    not-accessible
    STATUS    mandatory
    DESCRIPTION                                                              
            "A table of configuration, control and status information to
            manage the learning of the first N distinct MAC source addresses
            seen per port."
    ::= { erptrAddrLearnPortInfo 1 }

erptrAddrLearnPortCtrlEntry OBJECT-TYPE
    SYNTAX  ErptrAddrLearnPortCtrlEntry
    ACCESS  not-accessible
    STATUS  mandatory
    DESCRIPTION
            "An entry in the table containing information describing the
            control and status first N distinct MAC source address learning of
            a single port."
    INDEX  {erptrAddrLearnPortCtrlGroupIndex, erptrAddrLearnPortCtrlPortIndex}
    ::= { erptrAddrLearnPortCtrlTable 1 }

ErptrAddrLearnPortCtrlEntry ::=
    SEQUENCE {
        erptrAddrLearnPortCtrlGroupIndex
            INTEGER,
        erptrAddrLearnPortCtrlPortIndex
            INTEGER,
        erptrAddrLearnPortCtrlCapacity
            INTEGER,
        erptrAddrLearnPortCtrlAdminStatus
            INTEGER,
        erptrAddrLearnPortCtrlOperStatus
            INTEGER
        }

erptrAddrLearnPortCtrlGroupIndex OBJECT-TYPE
    SYNTAX INTEGER (1..1024)
    ACCESS read-only
    STATUS mandatory
    DESCRIPTION
            "This object identifies the group containing the port for which
            this entry contains information. This value is never greater
            than rptrGroupCapacity."
    ::= { erptrAddrLearnPortCtrlEntry 1 }

erptrAddrLearnPortCtrlPortIndex OBJECT-TYPE
    SYNTAX INTEGER (1..1024)
    ACCESS read-only
    STATUS mandatory
    DESCRIPTION
            "This object identifies the port within the group for which
            this entry contains information.  This value is never greater
            than rptrGroupPortCapacity for the associated group."
    ::= { erptrAddrLearnPortCtrlEntry 2 }

erptrAddrLearnPortCtrlCapacity OBJECT-TYPE
    SYNTAX INTEGER (0..65535)
    ACCESS read-only
    STATUS mandatory
    DESCRIPTION
            "This object specifies the maximum number of distinct MAC source
            addresses the repeater can learn and save on this port."
    ::= { erptrAddrLearnPortCtrlEntry 3 }

erptrAddrLearnPortCtrlAdminStatus OBJECT-TYPE
    SYNTAX INTEGER {
              other(1),
              enableLearning(2),
              disableLearning(3),
              clearLearnedAddresses(4)
              }
    ACCESS read-write
    STATUS mandatory
    DESCRIPTION                                                   
            "Setting this object to enableLearning(2) causes the agent to
            learn MAC source addresses from readable frames received on this
            port.  The agent records distinct addresses (along with addresses
            previously learned on this port) in erptrAddrLearnAddressTable.
            The agent actively learns addresses on this port until one of the
            following events occurs:

	         - The maximum allowable number of distinct addresses have
	           been learned on this port, as specified by
	           erptrAddrLearnPortCtrlCapacity.

                 - The learning process is disabled by setting this object to
	           disableLearning(3).

            The agent remembers learned addresses until this object is set to
            clearLearnedAddresses(4) or the module undergoes a power-up reset. 

            Setting this object to disableLearning(3) causes the agent to stop
            learning addresses on this port, regardless of the number of
            addresses already learned and saved.  Learning can be restarted on
            the port by setting this object to enableLearning(2).

            Setting this object to clearLearnedAddresses(4) causes the agent
            to delete any entries in erptrAddrLearnAddressTable associated
            with this port. If the value of erptrAddrLearnPortCtrlOperStatus
            for this port is learningEnabledAndActive(1) or
            learningEnabledAndStopped(2) when this object is set to
            clearLearnedAddresses(4), the agent will immediately begin
            learning new addresses on this port. 

            Setting this object to other(1) has no effect. The agent always
            returns the value other(1) when this object is read."
    ::= { erptrAddrLearnPortCtrlEntry 4 }

erptrAddrLearnPortCtrlOperStatus OBJECT-TYPE
    SYNTAX INTEGER {
              learningEnabledAndActive(1),
              learningEnabledAndStopped(2),
              learningDisabled(3)
              }
    ACCESS read-only
    STATUS mandatory
    DESCRIPTION                            
            "A value of learningEnabledAndActive(1) indicates that the agent
            is actively learning MAC source addresses from readable frames
            received on this port and recording them in
            erptrAddrLearnAddrTable.  It implies that
            erptrAddrLearnPortCtrlAdminStatus had previously been set to
            enableLearning(2) and the port has not yet learned and saved the
            maximum allowable number of distinct addresses (as specified by
            erptrAddrLearnPortCtrlCapacity).

            A value of learningEnabledAndStopped(2) indicates that the agent
            is NOT currently actively learning MAC source addresses from
            readable frames received on this port.  It implies that
            erptrAddrLearnPortCtrlAdminStatus had previously been set to
            enableLearning(2) but the port has learned and saved the maximum
            allowable number of distinct addresses (as specified by
            erptrAddrLearnPortCtrlCapacity).

            A value of learningDisabled(3) indicates that the agent is NOT
            actively learning distinct MAC source addresses from readable
            frames received on this port.  It implies that
            erptrAddrLearnPortCtrlAdminStatus had previously been set to
            disableLearning(3)."
    ::= { erptrAddrLearnPortCtrlEntry 5 }

--  +
--
--		      The Address Learning Address Table
--
--  -
erptrAddrLearnPortAddressTable OBJECT-TYPE
    SYNTAX SEQUENCE OF ErptrAddrLearnPortAddressEntry
    ACCESS not-accessible
    STATUS mandatory
    DESCRIPTION             
            "This table records the first N distinct MAC source addresses
            detected on readable frames received on each of the repeater's
            ports since address learning was last initiated. If a given port
            has not learned any addresses then no entries exist in the table
            for that port."
    ::= { erptrAddrLearnPortInfo 2 }

erptrAddrLearnPortAddressEntry OBJECT-TYPE
    SYNTAX ErptrAddrLearnPortAddressEntry
    ACCESS not-accessible
    STATUS mandatory
    DESCRIPTION
            "An entry in the table containing information regarding a single
            MAC address learned on one repeater port."
    INDEX  { erptrAddrLearnPortAddressGroupIndex,
             erptrAddrLearnPortAddressPortIndex,
             erptrAddrLearnPortAddressIndex }
    ::= { erptrAddrLearnPortAddressTable 1 }

ErptrAddrLearnPortAddressEntry ::=
    SEQUENCE {
        erptrAddrLearnPortAddressGroupIndex
            INTEGER,
        erptrAddrLearnPortAddressPortIndex
            INTEGER,
        erptrAddrLearnPortAddressIndex
	    INTEGER,
        erptrAddrLearnPortAddress
            PhysAddress
         }

erptrAddrLearnPortAddressGroupIndex OBJECT-TYPE
    SYNTAX  INTEGER (1..1024)
    ACCESS  read-only
    STATUS  mandatory
    DESCRIPTION
            "This object identifies the group containing the port for which
            this entry contains information.  This value is never greater
            than rptrGroupCapacity."
    ::= { erptrAddrLearnPortAddressEntry 1 }

erptrAddrLearnPortAddressPortIndex OBJECT-TYPE
    SYNTAX INTEGER (1..1024)
    ACCESS read-only
    STATUS mandatory
    DESCRIPTION            
            "This object identifies the port within the group for which
            this entry contains information.  This value can never be
            greater than rptrGroupPortCapacity for the associated group."
    ::= { erptrAddrLearnPortAddressEntry 2 }

erptrAddrLearnPortAddressIndex OBJECT-TYPE
    SYNTAX INTEGER (1..65535)
    ACCESS read-only
    STATUS mandatory
    DESCRIPTION            
            "This object identifies an index corresponding to a distinct
            MAC source address for which this entry contains information.
            This value can never be greater than
            erptrAddrLearnPortCtrlCapacity for the associated port."
    ::= { erptrAddrLearnPortAddressEntry 3 }

erptrAddrLearnPortAddress  OBJECT-TYPE
    SYNTAX PhysAddress
    ACCESS read-only
    STATUS mandatory
    DESCRIPTION
            "This object identifies a distinct MAC source address of a
            readable frame received on the port associated with this entry."
    ::= { erptrAddrLearnPortAddressEntry 4 }

--  +
--
--		       The Monitor Package
--                                                                         
--  Implementation of the Monitor Package group is optional. It is
--  appropriate for all implementations which have the necessary
--  instrumentation.  
-- 
--  This group defines performance monitoring statistics over and above those
--  defined in the IETF repeater MIB's Monitor Group.
--
--  - 

--  +
--
--		     Monitor Port Information
--
--  Performance monitoring statistics for repeater ports
--  
--  -

--  +
--
--		    Port Monitor Table
--
--  -
erptrMonitorPortTable OBJECT-TYPE
    SYNTAX    SEQUENCE OF ErptrMonitorPortEntry
    ACCESS    not-accessible
    STATUS    mandatory
    DESCRIPTION                                                              
            "A table of extended performance and error statistics for the 
             ports."
    ::= { erptrMonitorPortInfo 1 }

erptrMonitorPortEntry OBJECT-TYPE
    SYNTAX  ErptrMonitorPortEntry
    ACCESS  not-accessible
    STATUS  mandatory
    DESCRIPTION
            "An entry in the table containing extended performance and error
             statistics for a single port."
    INDEX  {erptrMonitorPortGroupIndex, erptrMonitorPortIndex}
    ::= { erptrMonitorPortTable 1 }

ErptrMonitorPortEntry ::=
    SEQUENCE {
        erptrMonitorPortGroupIndex
            INTEGER,
        erptrMonitorPortIndex
            INTEGER,
        erptrMonitorPortMulticastFrames
            Counter,
        erptrMonitorPortBroadcastFrames
            Counter
        }

erptrMonitorPortGroupIndex OBJECT-TYPE
    SYNTAX INTEGER (1..1024)
    ACCESS read-only
    STATUS mandatory
    DESCRIPTION
            "This object identifies the group containing the port for which
            this entry contains information. This value is never greater
            than rptrGroupCapacity."
    ::= { erptrMonitorPortEntry 1 }

erptrMonitorPortIndex OBJECT-TYPE
    SYNTAX INTEGER (1..1024)
    ACCESS read-only
    STATUS mandatory
    DESCRIPTION
            "This object identifies the port within the group for which
            this entry contains information.  This value is never greater
            than rptrGroupPortCapacity for the associated group."
    ::= { erptrMonitorPortEntry 2 }

erptrMonitorPortMulticastFrames OBJECT-TYPE
    SYNTAX Counter
    ACCESS read-only
    STATUS mandatory
    DESCRIPTION
            "This object is the number of valid multicast frames that have
             been received on this port.  This counter is incremented by one
             for each frame received on this port whose OctetCount is greater
             than or equal to minFrameSize and less than or equal to 
             maxFrameSize, whose MAC-layer destination address field contains
             a multicast-group address, and for which the FCSError and 
             CollisionEvent signals are not asserted.

             The approximate minimum time for rollover of this counter is 80
             hours."
    REFERENCE
  	    "Reference IEEE 802.3 Std, 3.2.3.1 and 4.4.2.1"
    ::= { erptrMonitorPortEntry 3 }

erptrMonitorPortBroadcastFrames OBJECT-TYPE
    SYNTAX Counter
    ACCESS read-only
    STATUS mandatory
    DESCRIPTION
            "This object is the number of valid broadcast frames that have
             been received on this port.  This counter is incremented by one
             for each frame received on this port whose OctetCount is greater
             than or equal to minFrameSize and less than or equal to 
             maxFrameSize, whose MAC-layer destination address field contains
             a broadcast address, and for which the FCSError and 
             CollisionEvent signals are not asserted.

             The approximate minimum time for rollover of this counter is 80
             hours."
    REFERENCE
  	    "Reference IEEE 802.3 Std, 3.2.3.1 and 4.4.2.1"
    ::= { erptrMonitorPortEntry 4 }

END
