Nortel-Magellan-Passport-DprsMcsEpMIB
DEFINITIONS ::= BEGIN



IMPORTS

      OBJECT-TYPE
   FROM RFC-1212

      passportMIBs
   FROM Nortel-Magellan-Passport-UsefulDefinitionsMIB

      Counter32,
      RowPointer,
      DisplayString,
      StorageType,
      RowStatus,
      PassportCounter64,
      Gauge32,
      Integer32,
      Unsigned32
   FROM Nortel-Magellan-Passport-StandardTextualConventionsMIB

      AsciiString,
      NonReplicated,
      HexString,
      EnterpriseDateAndTime,
      Link
   FROM Nortel-Magellan-Passport-TextualConventionsMIB

      mcsMgrIndex,
      mcsMgr
   FROM Nortel-Magellan-Passport-McsMgrMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     DprsMcsEp Enterprise MIB."

dprsMcsEpMIB OBJECT IDENTIFIER ::= { passportMIBs 125 }










-- McsMgr DprsMcsEndPointGroup/n
-- The DprsMcsEndPointGroup component contains all of the 
-- provisioned End Points or all of the dynamic End Points that share a 
-- common destination NSAP address, thereby terminating on the 
-- same destination node. 
-- This means that there could be at most two 
-- DprsMcsEndPointGroups to the same destination, a provisioned 
-- DprsMcsEpG and a dynamic DprsMcsEpG.
-- The associated group is indicated by the associatedEpGroupName 
-- attribute. 
-- DprsMcsEpG component instances in the 1-4096 range can be 
-- provisioned. 
-- DprsMcsEpG component instances in the 4097-8191 range are 
-- dynamic.

mcsMgrDprsMcsEpG OBJECT IDENTIFIER ::= { mcsMgr 2 }



mcsMgrDprsMcsEpGRowStatusTable OBJECT-TYPE
   SYNTAX     SEQUENCE OF McsMgrDprsMcsEpGRowStatusEntry
   ACCESS     not-accessible
   STATUS     mandatory
   DESCRIPTION
     "This entry controls the addition and deletion of 
      mcsMgrDprsMcsEpG components."
::= { mcsMgrDprsMcsEpG 1 }

mcsMgrDprsMcsEpGRowStatusEntry OBJECT-TYPE
   SYNTAX     McsMgrDprsMcsEpGRowStatusEntry
   ACCESS     not-accessible
   STATUS     mandatory
   DESCRIPTION
     "A single entry in the table represents a single 
      mcsMgrDprsMcsEpG component."
   INDEX {
      mcsMgrIndex,
      mcsMgrDprsMcsEpGIndex }
::= { mcsMgrDprsMcsEpGRowStatusTable 1 }

McsMgrDprsMcsEpGRowStatusEntry ::= SEQUENCE {
   mcsMgrDprsMcsEpGRowStatus
      RowStatus,
   mcsMgrDprsMcsEpGComponentName
      DisplayString,
   mcsMgrDprsMcsEpGStorageType
      StorageType,
   mcsMgrDprsMcsEpGIndex
      Integer32 }

mcsMgrDprsMcsEpGRowStatus OBJECT-TYPE
   SYNTAX     RowStatus 
   ACCESS     read-write
   STATUS     mandatory
   DESCRIPTION
     "This variable is used as the basis for SNMP naming of
      mcsMgrDprsMcsEpG components.
      These components can be added and deleted."
::= { mcsMgrDprsMcsEpGRowStatusEntry 1 }

mcsMgrDprsMcsEpGComponentName OBJECT-TYPE
   SYNTAX     DisplayString 
   ACCESS     read-only
   STATUS     mandatory
   DESCRIPTION
     "This variable provides the component's string name for
      use with the ASCII Console Interface"
::= { mcsMgrDprsMcsEpGRowStatusEntry 2 }

mcsMgrDprsMcsEpGStorageType OBJECT-TYPE
   SYNTAX     StorageType 
   ACCESS     read-only
   STATUS     mandatory
   DESCRIPTION
     "This variable represents the storage type value for the
      mcsMgrDprsMcsEpG tables."
::= { mcsMgrDprsMcsEpGRowStatusEntry 4 }

mcsMgrDprsMcsEpGIndex OBJECT-TYPE
   SYNTAX     Integer32 (1..8191)
   ACCESS     not-accessible
   STATUS     mandatory
   DESCRIPTION
     "This variable represents the index for the mcsMgrDprsMcsEpG tables."
::= { mcsMgrDprsMcsEpGRowStatusEntry 10 }

mcsMgrDprsMcsEpGOperTable OBJECT-TYPE
   SYNTAX     SEQUENCE OF McsMgrDprsMcsEpGOperEntry
   ACCESS     not-accessible
   STATUS     mandatory
   DESCRIPTION
     "This group contains the operational attributes of the DprsMcsEpG
      component."
::= { mcsMgrDprsMcsEpG 10 }

mcsMgrDprsMcsEpGOperEntry OBJECT-TYPE
   SYNTAX     McsMgrDprsMcsEpGOperEntry
   ACCESS     not-accessible
   STATUS     mandatory
   DESCRIPTION
     "An entry in the mcsMgrDprsMcsEpGOperTable."
   INDEX {
      mcsMgrIndex,
      mcsMgrDprsMcsEpGIndex }
::= { mcsMgrDprsMcsEpGOperTable 1 }

McsMgrDprsMcsEpGOperEntry ::= SEQUENCE {
   mcsMgrDprsMcsEpGRemoteAddress
      AsciiString,
   mcsMgrDprsMcsEpGAssociatedEpGroupName
      RowPointer }

mcsMgrDprsMcsEpGRemoteAddress OBJECT-TYPE
   SYNTAX     AsciiString (SIZE (0..44))
   ACCESS     read-only
   STATUS     mandatory
   DESCRIPTION
     "This attribute indicates the NSAP address of the McsMgr at the 
      destination module to which all EndPoints of this group are 
      connected."
::= { mcsMgrDprsMcsEpGOperEntry 1 }

mcsMgrDprsMcsEpGAssociatedEpGroupName OBJECT-TYPE
   SYNTAX     RowPointer 
   ACCESS     read-only
   STATUS     mandatory
   DESCRIPTION
     "For a provisioned DprsMcsEpG, this attribute indicates the name of 
      the DprsMcsEpG that contains the dynamic Eps to the same 
      destination.
      For a dynamic DprsMcsEpG, this attribute indicates the name of the 
      DprsMcsEpG that contains the provisioned Eps to the same 
      destination.
      A null component name indicates that there is no DprsMcsEpG 
      associated with this group."
::= { mcsMgrDprsMcsEpGOperEntry 2 }


-- McsMgr DprsMcsEpG/n Address
-- This component contains the destination NSAP address used by all 
-- Dprs MCS End Points provisioned under a DprsMcsEpG.

mcsMgrDprsMcsEpGAddr OBJECT IDENTIFIER ::= { mcsMgrDprsMcsEpG 2 }



mcsMgrDprsMcsEpGAddrRowStatusTable OBJECT-TYPE
   SYNTAX     SEQUENCE OF McsMgrDprsMcsEpGAddrRowStatusEntry
   ACCESS     not-accessible
   STATUS     mandatory
   DESCRIPTION
     "This entry controls the addition and deletion of 
      mcsMgrDprsMcsEpGAddr components."
::= { mcsMgrDprsMcsEpGAddr 1 }

mcsMgrDprsMcsEpGAddrRowStatusEntry OBJECT-TYPE
   SYNTAX     McsMgrDprsMcsEpGAddrRowStatusEntry
   ACCESS     not-accessible
   STATUS     mandatory
   DESCRIPTION
     "A single entry in the table represents a single 
      mcsMgrDprsMcsEpGAddr component."
   INDEX {
      mcsMgrIndex,
      mcsMgrDprsMcsEpGIndex,
      mcsMgrDprsMcsEpGAddrIndex }
::= { mcsMgrDprsMcsEpGAddrRowStatusTable 1 }

McsMgrDprsMcsEpGAddrRowStatusEntry ::= SEQUENCE {
   mcsMgrDprsMcsEpGAddrRowStatus
      RowStatus,
   mcsMgrDprsMcsEpGAddrComponentName
      DisplayString,
   mcsMgrDprsMcsEpGAddrStorageType
      StorageType,
   mcsMgrDprsMcsEpGAddrIndex
      NonReplicated }

mcsMgrDprsMcsEpGAddrRowStatus OBJECT-TYPE
   SYNTAX     RowStatus 
   ACCESS     read-only
   STATUS     mandatory
   DESCRIPTION
     "This variable is used as the basis for SNMP naming of
      mcsMgrDprsMcsEpGAddr components.
      These components cannot be added nor deleted."
::= { mcsMgrDprsMcsEpGAddrRowStatusEntry 1 }

mcsMgrDprsMcsEpGAddrComponentName OBJECT-TYPE
   SYNTAX     DisplayString 
   ACCESS     read-only
   STATUS     mandatory
   DESCRIPTION
     "This variable provides the component's string name for
      use with the ASCII Console Interface"
::= { mcsMgrDprsMcsEpGAddrRowStatusEntry 2 }

mcsMgrDprsMcsEpGAddrStorageType OBJECT-TYPE
   SYNTAX     StorageType 
   ACCESS     read-only
   STATUS     mandatory
   DESCRIPTION
     "This variable represents the storage type value for the
      mcsMgrDprsMcsEpGAddr tables."
::= { mcsMgrDprsMcsEpGAddrRowStatusEntry 4 }

mcsMgrDprsMcsEpGAddrIndex OBJECT-TYPE
   SYNTAX     NonReplicated 
   ACCESS     not-accessible
   STATUS     mandatory
   DESCRIPTION
     "This variable represents the index for the mcsMgrDprsMcsEpGAddr tables."
::= { mcsMgrDprsMcsEpGAddrRowStatusEntry 10 }

mcsMgrDprsMcsEpGAddrProvTable OBJECT-TYPE
   SYNTAX     SEQUENCE OF McsMgrDprsMcsEpGAddrProvEntry
   ACCESS     not-accessible
   STATUS     mandatory
   DESCRIPTION
     "This group contains the provisionable attributes of the Address 
      component."
::= { mcsMgrDprsMcsEpGAddr 10 }

mcsMgrDprsMcsEpGAddrProvEntry OBJECT-TYPE
   SYNTAX     McsMgrDprsMcsEpGAddrProvEntry
   ACCESS     not-accessible
   STATUS     mandatory
   DESCRIPTION
     "An entry in the mcsMgrDprsMcsEpGAddrProvTable."
   INDEX {
      mcsMgrIndex,
      mcsMgrDprsMcsEpGIndex,
      mcsMgrDprsMcsEpGAddrIndex }
::= { mcsMgrDprsMcsEpGAddrProvTable 1 }

McsMgrDprsMcsEpGAddrProvEntry ::= SEQUENCE {
   mcsMgrDprsMcsEpGAddrRemoteAddress
      AsciiString,
   mcsMgrDprsMcsEpGAddrCommentText
      AsciiString }

mcsMgrDprsMcsEpGAddrRemoteAddress OBJECT-TYPE
   SYNTAX     AsciiString (SIZE (1..44))
   ACCESS     read-write
   STATUS     mandatory
   DESCRIPTION
     "This attribute specifies the NSAP address of the McsMgr at the 
      destination module. This address is used by the EndPoints 
      provisioned under this DprsMcsEpG to establish a Dprs MCS 
      Switched Path."
::= { mcsMgrDprsMcsEpGAddrProvEntry 1 }

mcsMgrDprsMcsEpGAddrCommentText OBJECT-TYPE
   SYNTAX     AsciiString (SIZE (0..60))
   ACCESS     read-write
   STATUS     mandatory
   DESCRIPTION
     "This attribute specifies additional textual information to be added by 
      the network operator. Typical use of this attribute is to specify the 
      destination module name."
   DEFVAL     { ''H }  -- ""
::= { mcsMgrDprsMcsEpGAddrProvEntry 2 }


-- McsMgr DprsMcsEpG/n EndPoint/n
-- The EndPoint component represents the Dprs MCS Switched Path. 
-- It multiplexes multiple Frame Relay DLCIs and transports them 
-- over an underlying PORS or ATM connection.

mcsMgrDprsMcsEpGEp OBJECT IDENTIFIER ::= { mcsMgrDprsMcsEpG 3 }



mcsMgrDprsMcsEpGEpRowStatusTable OBJECT-TYPE
   SYNTAX     SEQUENCE OF McsMgrDprsMcsEpGEpRowStatusEntry
   ACCESS     not-accessible
   STATUS     mandatory
   DESCRIPTION
     "This entry controls the addition and deletion of 
      mcsMgrDprsMcsEpGEp components."
::= { mcsMgrDprsMcsEpGEp 1 }

mcsMgrDprsMcsEpGEpRowStatusEntry OBJECT-TYPE
   SYNTAX     McsMgrDprsMcsEpGEpRowStatusEntry
   ACCESS     not-accessible
   STATUS     mandatory
   DESCRIPTION
     "A single entry in the table represents a single 
      mcsMgrDprsMcsEpGEp component."
   INDEX {
      mcsMgrIndex,
      mcsMgrDprsMcsEpGIndex,
      mcsMgrDprsMcsEpGEpIndex }
::= { mcsMgrDprsMcsEpGEpRowStatusTable 1 }

McsMgrDprsMcsEpGEpRowStatusEntry ::= SEQUENCE {
   mcsMgrDprsMcsEpGEpRowStatus
      RowStatus,
   mcsMgrDprsMcsEpGEpComponentName
      DisplayString,
   mcsMgrDprsMcsEpGEpStorageType
      StorageType,
   mcsMgrDprsMcsEpGEpIndex
      Integer32 }

mcsMgrDprsMcsEpGEpRowStatus OBJECT-TYPE
   SYNTAX     RowStatus 
   ACCESS     read-write
   STATUS     mandatory
   DESCRIPTION
     "This variable is used as the basis for SNMP naming of
      mcsMgrDprsMcsEpGEp components.
      These components can be added and deleted."
::= { mcsMgrDprsMcsEpGEpRowStatusEntry 1 }

mcsMgrDprsMcsEpGEpComponentName OBJECT-TYPE
   SYNTAX     DisplayString 
   ACCESS     read-only
   STATUS     mandatory
   DESCRIPTION
     "This variable provides the component's string name for
      use with the ASCII Console Interface"
::= { mcsMgrDprsMcsEpGEpRowStatusEntry 2 }

mcsMgrDprsMcsEpGEpStorageType OBJECT-TYPE
   SYNTAX     StorageType 
   ACCESS     read-only
   STATUS     mandatory
   DESCRIPTION
     "This variable represents the storage type value for the
      mcsMgrDprsMcsEpGEp tables."
::= { mcsMgrDprsMcsEpGEpRowStatusEntry 4 }

mcsMgrDprsMcsEpGEpIndex OBJECT-TYPE
   SYNTAX     Integer32 (1..256)
   ACCESS     not-accessible
   STATUS     mandatory
   DESCRIPTION
     "This variable represents the index for the mcsMgrDprsMcsEpGEp tables."
::= { mcsMgrDprsMcsEpGEpRowStatusEntry 10 }

mcsMgrDprsMcsEpGEpStateTable OBJECT-TYPE
   SYNTAX     SEQUENCE OF McsMgrDprsMcsEpGEpStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mcsMgrDprsMcsEpGEp 10 }

mcsMgrDprsMcsEpGEpStateEntry OBJECT-TYPE
   SYNTAX     McsMgrDprsMcsEpGEpStateEntry
   ACCESS     not-accessible
   STATUS     mandatory
   DESCRIPTION
     "An entry in the mcsMgrDprsMcsEpGEpStateTable."
   INDEX {
      mcsMgrIndex,
      mcsMgrDprsMcsEpGIndex,
      mcsMgrDprsMcsEpGEpIndex }
::= { mcsMgrDprsMcsEpGEpStateTable 1 }

McsMgrDprsMcsEpGEpStateEntry ::= SEQUENCE {
   mcsMgrDprsMcsEpGEpAdminState
      INTEGER,
   mcsMgrDprsMcsEpGEpOperationalState
      INTEGER,
   mcsMgrDprsMcsEpGEpUsageState
      INTEGER,
   mcsMgrDprsMcsEpGEpAvailabilityStatus
      OCTET STRING,
   mcsMgrDprsMcsEpGEpProceduralStatus
      OCTET STRING,
   mcsMgrDprsMcsEpGEpControlStatus
      OCTET STRING,
   mcsMgrDprsMcsEpGEpAlarmStatus
      OCTET STRING,
   mcsMgrDprsMcsEpGEpStandbyStatus
      INTEGER,
   mcsMgrDprsMcsEpGEpUnknownStatus
      INTEGER }

mcsMgrDprsMcsEpGEpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mcsMgrDprsMcsEpGEpStateEntry 1 }

mcsMgrDprsMcsEpGEpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mcsMgrDprsMcsEpGEpStateEntry 2 }

mcsMgrDprsMcsEpGEpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mcsMgrDprsMcsEpGEpStateEntry 3 }

mcsMgrDprsMcsEpGEpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mcsMgrDprsMcsEpGEpStateEntry 4 }

mcsMgrDprsMcsEpGEpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mcsMgrDprsMcsEpGEpStateEntry 5 }

mcsMgrDprsMcsEpGEpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mcsMgrDprsMcsEpGEpStateEntry 6 }

mcsMgrDprsMcsEpGEpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mcsMgrDprsMcsEpGEpStateEntry 7 }

mcsMgrDprsMcsEpGEpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mcsMgrDprsMcsEpGEpStateEntry 8 }

mcsMgrDprsMcsEpGEpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mcsMgrDprsMcsEpGEpStateEntry 9 }

mcsMgrDprsMcsEpGEpOperTable OBJECT-TYPE
   SYNTAX     SEQUENCE OF McsMgrDprsMcsEpGEpOperEntry
   ACCESS     not-accessible
   STATUS     mandatory
   DESCRIPTION
     "This group contains the operational attributes of the EndPoint 
      component."
::= { mcsMgrDprsMcsEpGEp 11 }

mcsMgrDprsMcsEpGEpOperEntry OBJECT-TYPE
   SYNTAX     McsMgrDprsMcsEpGEpOperEntry
   ACCESS     not-accessible
   STATUS     mandatory
   DESCRIPTION
     "An entry in the mcsMgrDprsMcsEpGEpOperTable."
   INDEX {
      mcsMgrIndex,
      mcsMgrDprsMcsEpGIndex,
      mcsMgrDprsMcsEpGEpIndex }
::= { mcsMgrDprsMcsEpGEpOperTable 1 }

McsMgrDprsMcsEpGEpOperEntry ::= SEQUENCE {
   mcsMgrDprsMcsEpGEpLastTransportConnectionClearCause
      Unsigned32,
   mcsMgrDprsMcsEpGEpType
      INTEGER,
   mcsMgrDprsMcsEpGEpSupportedTransferPriorities
      OCTET STRING,
   mcsMgrDprsMcsEpGEpConnectionTransferPriority
      Unsigned32,
   mcsMgrDprsMcsEpGEpServiceCategory
      INTEGER,
   mcsMgrDprsMcsEpGEpBandwidth
      Unsigned32,
   mcsMgrDprsMcsEpGEpRemoteComponentName
      AsciiString,
   mcsMgrDprsMcsEpGEpRemoteRoutingId
      Unsigned32,
   mcsMgrDprsMcsEpGEpRemoteModuleId
      Unsigned32,
   mcsMgrDprsMcsEpGEpLastTrConnDiagCode
      HexString }

mcsMgrDprsMcsEpGEpLastTransportConnectionClearCause OBJECT-TYPE
   SYNTAX     Unsigned32 (0..1000)
   ACCESS     read-only
   STATUS     mandatory
   DESCRIPTION
     "This attribute indicates the most recent clear cause for the transport 
      connection.
      This indicates the causes provided by the network. 
      A value of zero indicates that the transport connection has never 
      been cleared.
      A value of 1000 indicates that the network has not provided a clear 
      cause for the transport connection clearing.
      Section 5.4.5.15 of the ATMF UNI 3.1 specification lists the clear 
      causes provided by the network."
::= { mcsMgrDprsMcsEpGEpOperEntry 3 }

mcsMgrDprsMcsEpGEpType OBJECT-TYPE
   SYNTAX     INTEGER  {
                 originating(0),
                 terminating(1) }
   ACCESS     read-only
   STATUS     mandatory
   DESCRIPTION
     "This attribute indicates the type of the end point. If the value is 
      originating, this Ep is provisioned and is responsible for initiating 
      the SPVC call to set up the PORS or ATM connection. If the value 
      is terminating, this Ep is created dynamically by the McsMgr at the 
      destination node when it receives a call setup request."
   DEFVAL     { originating }
::= { mcsMgrDprsMcsEpGEpOperEntry 4 }

mcsMgrDprsMcsEpGEpSupportedTransferPriorities OBJECT-TYPE
   SYNTAX     OCTET STRING (SIZE (2))
   ACCESS     read-only
   STATUS     mandatory
   DESCRIPTION
     "This attribute indicates the Frame Relay transfer priorities 
      supported by the transport connection.

      Description of bits:
      n0(0)
      n1(1)
      n2(2)
      n3(3)
      n4(4)
      n5(5)
      n6(6)
      n7(7)
      n8(8)
      n9(9)
      n10(10)
      n11(11)
      n12(12)
      n13(13)
      n14(14)
      n15(15)"
::= { mcsMgrDprsMcsEpGEpOperEntry 5 }

mcsMgrDprsMcsEpGEpConnectionTransferPriority OBJECT-TYPE
   SYNTAX     Unsigned32 (0..15)
   ACCESS     read-only
   STATUS     mandatory
   DESCRIPTION
     "This attribute indicates the transfer priority used to establish the 
      transport connection."
::= { mcsMgrDprsMcsEpGEpOperEntry 6 }

mcsMgrDprsMcsEpGEpServiceCategory OBJECT-TYPE
   SYNTAX     INTEGER  {
                 ubr(0),
                 cbr(1),
                 rtVbr(2),
                 nrtVbr(3) }
   ACCESS     read-only
   STATUS     mandatory
   DESCRIPTION
     "This attribute indicates the ATM service category of the transport 
      connection."
::= { mcsMgrDprsMcsEpGEpOperEntry 7 }

mcsMgrDprsMcsEpGEpBandwidth OBJECT-TYPE
   SYNTAX     Unsigned32 (0..155000000)
   ACCESS     read-only
   STATUS     mandatory
   DESCRIPTION
     "This attribute indicates the bandwidth at which the transport 
      connection agrees to transfer information."
::= { mcsMgrDprsMcsEpGEpOperEntry 8 }

mcsMgrDprsMcsEpGEpRemoteComponentName OBJECT-TYPE
   SYNTAX     AsciiString (SIZE (0..46))
   ACCESS     read-only
   STATUS     mandatory
   DESCRIPTION
     "This attribute indicates the component name of the remote Ep, 
      learned from the remote end.
      For example: 'EM/NODEY2D0 McsMgr DprsMcsEpG/1 Ep/1'.
      The value will be a null string if the transport connection is down."
::= { mcsMgrDprsMcsEpGEpOperEntry 9 }

mcsMgrDprsMcsEpGEpRemoteRoutingId OBJECT-TYPE
   SYNTAX     Unsigned32 (0..126)
   ACCESS     read-only
   STATUS     mandatory
   DESCRIPTION
     "This attribute indicates the routing identifier (RID) associated with 
      the Passport node on which the remote Ep resides. The remote RID 
      is learned from the remote Ep.
      The value is valid when the transport connection is up and zero 
      otherwise."
::= { mcsMgrDprsMcsEpGEpOperEntry 10 }

mcsMgrDprsMcsEpGEpRemoteModuleId OBJECT-TYPE
   SYNTAX     Unsigned32 (0..1909)
   ACCESS     read-only
   STATUS     mandatory
   DESCRIPTION
     "This attribute indicates the module identifier (MID) associated with 
      the Passport node on which the remote Ep resides. The remote MID 
      is learned from the remote Ep.
      The value is valid when the transport connection is up and zero 
      otherwise."
::= { mcsMgrDprsMcsEpGEpOperEntry 11 }

mcsMgrDprsMcsEpGEpLastTrConnDiagCode OBJECT-TYPE
   SYNTAX     HexString (SIZE (0..10))
   ACCESS     read-only
   STATUS     mandatory
   DESCRIPTION
     "This attribute indicates the diagnostic code of the most recently 
      cleared transport connection.
      This indicates the diagnostic code (associated with the 
      lastTransportConnectionClearCause) provided by the network. 
      A string containing only a 0 or 00 (zero) indicates that the network 
      has not provided a diagnostic code for the most recently cleared 
      transport connection.
      Section 5.4.5.15 of the ATMF UNI 3.1 specification lists the 
      diagnostic codes that can be provided by the network."
::= { mcsMgrDprsMcsEpGEpOperEntry 12 }

mcsMgrDprsMcsEpGEpStatsTable OBJECT-TYPE
   SYNTAX     SEQUENCE OF McsMgrDprsMcsEpGEpStatsEntry
   ACCESS     not-accessible
   STATUS     mandatory
   DESCRIPTION
     "This group contains statistics of traffic received on the Dprs MCS 
      Switched Path."
::= { mcsMgrDprsMcsEpGEp 12 }

mcsMgrDprsMcsEpGEpStatsEntry OBJECT-TYPE
   SYNTAX     McsMgrDprsMcsEpGEpStatsEntry
   ACCESS     not-accessible
   STATUS     mandatory
   DESCRIPTION
     "An entry in the mcsMgrDprsMcsEpGEpStatsTable."
   INDEX {
      mcsMgrIndex,
      mcsMgrDprsMcsEpGIndex,
      mcsMgrDprsMcsEpGEpIndex }
::= { mcsMgrDprsMcsEpGEpStatsTable 1 }

McsMgrDprsMcsEpGEpStatsEntry ::= SEQUENCE {
   mcsMgrDprsMcsEpGEpSetupAttempts
      Counter32,
   mcsMgrDprsMcsEpGEpPktDiscErroredFromMcs
      Counter32 }

mcsMgrDprsMcsEpGEpSetupAttempts OBJECT-TYPE
   SYNTAX     Counter32 
   ACCESS     read-only
   STATUS     mandatory
   DESCRIPTION
     "This attribute counts the number of attempts made to set up the 
      transport connection. The counter wraps around to zero when the 
      maximum value is reached."
::= { mcsMgrDprsMcsEpGEpStatsEntry 1 }

mcsMgrDprsMcsEpGEpPktDiscErroredFromMcs OBJECT-TYPE
   SYNTAX     Counter32 
   ACCESS     read-only
   STATUS     mandatory
   DESCRIPTION
     "This attribute counts errored packets received on the Dprs MCS 
      Switched Path that have been discarded. 
      The counter wraps around to zero when the maximum value is 
      reached."
::= { mcsMgrDprsMcsEpGEpStatsEntry 2 }

mcsMgrDprsMcsEpGEpPktFromMcsTable OBJECT-TYPE
   SYNTAX     SEQUENCE OF McsMgrDprsMcsEpGEpPktFromMcsEntry
   ACCESS     not-accessible
   STATUS     mandatory
   DESCRIPTION
     "This attribute counts the packets received on the Dprs MCS 
      Switched Path for each discard priority.
      This attribute is a vector with four entries. Each vector entry is a 
      counter indexed by one of four discard priorities, namely, discard 
      priority 0(dp0), discard priority 1(dp1), discard priority 2(dp2) 
      or discard priority 3(dp3).
      Each entry (counter) wraps around to zero when the maximum 
      value is reached."
::= { mcsMgrDprsMcsEpGEp 402 }

mcsMgrDprsMcsEpGEpPktFromMcsEntry OBJECT-TYPE
   SYNTAX     McsMgrDprsMcsEpGEpPktFromMcsEntry
   ACCESS     not-accessible
   STATUS     mandatory
   DESCRIPTION
     "An entry in the mcsMgrDprsMcsEpGEpPktFromMcsTable."
   INDEX {
      mcsMgrIndex,
      mcsMgrDprsMcsEpGIndex,
      mcsMgrDprsMcsEpGEpIndex,
      mcsMgrDprsMcsEpGEpPktFromMcsIndex }
::= { mcsMgrDprsMcsEpGEpPktFromMcsTable 1 }

McsMgrDprsMcsEpGEpPktFromMcsEntry ::= SEQUENCE {
   mcsMgrDprsMcsEpGEpPktFromMcsIndex
      INTEGER,
   mcsMgrDprsMcsEpGEpPktFromMcsValue
      PassportCounter64 }

mcsMgrDprsMcsEpGEpPktFromMcsIndex OBJECT-TYPE
   SYNTAX     INTEGER  {
                 discardPriority0(0),
                 discardPriority1(1),
                 discardPriority2(2),
                 discardPriority3(3) }
   ACCESS     not-accessible
   STATUS     mandatory
   DESCRIPTION
     "This variable represents the mcsMgrDprsMcsEpGEpPktFromMcsTable
      specific index for the mcsMgrDprsMcsEpGEpPktFromMcsTable."
::= { mcsMgrDprsMcsEpGEpPktFromMcsEntry 1 }

mcsMgrDprsMcsEpGEpPktFromMcsValue OBJECT-TYPE
   SYNTAX     PassportCounter64 
   ACCESS     read-only
   STATUS     mandatory
   DESCRIPTION
     "This variable represents an individual value for the
      mcsMgrDprsMcsEpGEpPktFromMcsTable."
::= { mcsMgrDprsMcsEpGEpPktFromMcsEntry 2 }

mcsMgrDprsMcsEpGEpOctetsFromMcsTable OBJECT-TYPE
   SYNTAX     SEQUENCE OF McsMgrDprsMcsEpGEpOctetsFromMcsEntry
   ACCESS     not-accessible
   STATUS     mandatory
   DESCRIPTION
     "This attribute counts the octets received on the Dprs MCS 
      Switched Path for each discard priority. 
      This attribute is a vector with four entries. Each vector entry is a 
      counter indexed by one of four discard priorities, namely, discard 
      priority 0(dp0), discard priority 1(dp1), discard priority 2(dp2) or 
      discard priority 3(dp3).
      Each entry (counter) wraps around to zero when the maximum 
      value is reached."
::= { mcsMgrDprsMcsEpGEp 403 }

mcsMgrDprsMcsEpGEpOctetsFromMcsEntry OBJECT-TYPE
   SYNTAX     McsMgrDprsMcsEpGEpOctetsFromMcsEntry
   ACCESS     not-accessible
   STATUS     mandatory
   DESCRIPTION
     "An entry in the mcsMgrDprsMcsEpGEpOctetsFromMcsTable."
   INDEX {
      mcsMgrIndex,
      mcsMgrDprsMcsEpGIndex,
      mcsMgrDprsMcsEpGEpIndex,
      mcsMgrDprsMcsEpGEpOctetsFromMcsIndex }
::= { mcsMgrDprsMcsEpGEpOctetsFromMcsTable 1 }

McsMgrDprsMcsEpGEpOctetsFromMcsEntry ::= SEQUENCE {
   mcsMgrDprsMcsEpGEpOctetsFromMcsIndex
      INTEGER,
   mcsMgrDprsMcsEpGEpOctetsFromMcsValue
      PassportCounter64 }

mcsMgrDprsMcsEpGEpOctetsFromMcsIndex OBJECT-TYPE
   SYNTAX     INTEGER  {
                 discardPriority0(0),
                 discardPriority1(1),
                 discardPriority2(2),
                 discardPriority3(3) }
   ACCESS     not-accessible
   STATUS     mandatory
   DESCRIPTION
     "This variable represents the mcsMgrDprsMcsEpGEpOctetsFromMcsTable
      specific index for the mcsMgrDprsMcsEpGEpOctetsFromMcsTable."
::= { mcsMgrDprsMcsEpGEpOctetsFromMcsEntry 1 }

mcsMgrDprsMcsEpGEpOctetsFromMcsValue OBJECT-TYPE
   SYNTAX     PassportCounter64 
   ACCESS     read-only
   STATUS     mandatory
   DESCRIPTION
     "This variable represents an individual value for the
      mcsMgrDprsMcsEpGEpOctetsFromMcsTable."
::= { mcsMgrDprsMcsEpGEpOctetsFromMcsEntry 2 }

mcsMgrDprsMcsEpGEpPktDiscCongestedFromMcsTable OBJECT-TYPE
   SYNTAX     SEQUENCE OF McsMgrDprsMcsEpGEpPktDiscCongestedFromMcsEntry
   ACCESS     not-accessible
   STATUS     mandatory
   DESCRIPTION
     "This attribute counts packets received on the Dprs MCS 
      Switched Path for each discard priority that have been discarded at 
      the transport card due to free list congestion at the access card. 
      This attribute is a vector with four entries. Each vector entry is a 
      counter indexed by one of four discard priorities, namely, discard 
      priority 0(dp0), discard priority 1(dp1), discard priority 2(dp2) or 
      discard priority 3(dp3). 
      Each entry (counter) wraps around to zero when the maximum 
      value is reached."
::= { mcsMgrDprsMcsEpGEp 404 }

mcsMgrDprsMcsEpGEpPktDiscCongestedFromMcsEntry OBJECT-TYPE
   SYNTAX     McsMgrDprsMcsEpGEpPktDiscCongestedFromMcsEntry
   ACCESS     not-accessible
   STATUS     mandatory
   DESCRIPTION
     "An entry in the mcsMgrDprsMcsEpGEpPktDiscCongestedFromMcsTable."
   INDEX {
      mcsMgrIndex,
      mcsMgrDprsMcsEpGIndex,
      mcsMgrDprsMcsEpGEpIndex,
      mcsMgrDprsMcsEpGEpPktDiscCongestedFromMcsIndex }
::= { mcsMgrDprsMcsEpGEpPktDiscCongestedFromMcsTable 1 }

McsMgrDprsMcsEpGEpPktDiscCongestedFromMcsEntry ::= SEQUENCE {
   mcsMgrDprsMcsEpGEpPktDiscCongestedFromMcsIndex
      INTEGER,
   mcsMgrDprsMcsEpGEpPktDiscCongestedFromMcsValue
      Counter32 }

mcsMgrDprsMcsEpGEpPktDiscCongestedFromMcsIndex OBJECT-TYPE
   SYNTAX     INTEGER  {
                 discardPriority0(0),
                 discardPriority1(1),
                 discardPriority2(2),
                 discardPriority3(3) }
   ACCESS     not-accessible
   STATUS     mandatory
   DESCRIPTION
     "This variable represents the mcsMgrDprsMcsEpGEpPktDiscCongestedFromMcsTable
      specific index for the mcsMgrDprsMcsEpGEpPktDiscCongestedFromMcsTable."
::= { mcsMgrDprsMcsEpGEpPktDiscCongestedFromMcsEntry 1 }

mcsMgrDprsMcsEpGEpPktDiscCongestedFromMcsValue OBJECT-TYPE
   SYNTAX     Counter32 
   ACCESS     read-only
   STATUS     mandatory
   DESCRIPTION
     "This variable represents an individual value for the
      mcsMgrDprsMcsEpGEpPktDiscCongestedFromMcsTable."
::= { mcsMgrDprsMcsEpGEpPktDiscCongestedFromMcsEntry 2 }


-- McsMgr DprsMcsEpG/n Ep/n EndPointDescriptor
-- This component establishes the underlying PORS or ATM 
-- connection. 
-- There can only be one Dprs MCS Switched Path per Frame Relay 
-- transfer priority between a pair of nodes.
-- Therefore, the supportedTransferPriorities on this EndPoint must 
-- be mutually exclusive with the supportedTransferPriorities of all 
-- other EndPoints within this DprsMcsEndPointGroup. 

mcsMgrDprsMcsEpGEpEpD OBJECT IDENTIFIER ::= { mcsMgrDprsMcsEpGEp 2 }



mcsMgrDprsMcsEpGEpEpDRowStatusTable OBJECT-TYPE
   SYNTAX     SEQUENCE OF McsMgrDprsMcsEpGEpEpDRowStatusEntry
   ACCESS     not-accessible
   STATUS     mandatory
   DESCRIPTION
     "This entry controls the addition and deletion of 
      mcsMgrDprsMcsEpGEpEpD components."
::= { mcsMgrDprsMcsEpGEpEpD 1 }

mcsMgrDprsMcsEpGEpEpDRowStatusEntry OBJECT-TYPE
   SYNTAX     McsMgrDprsMcsEpGEpEpDRowStatusEntry
   ACCESS     not-accessible
   STATUS     mandatory
   DESCRIPTION
     "A single entry in the table represents a single 
      mcsMgrDprsMcsEpGEpEpD component."
   INDEX {
      mcsMgrIndex,
      mcsMgrDprsMcsEpGIndex,
      mcsMgrDprsMcsEpGEpIndex,
      mcsMgrDprsMcsEpGEpEpDIndex }
::= { mcsMgrDprsMcsEpGEpEpDRowStatusTable 1 }

McsMgrDprsMcsEpGEpEpDRowStatusEntry ::= SEQUENCE {
   mcsMgrDprsMcsEpGEpEpDRowStatus
      RowStatus,
   mcsMgrDprsMcsEpGEpEpDComponentName
      DisplayString,
   mcsMgrDprsMcsEpGEpEpDStorageType
      StorageType,
   mcsMgrDprsMcsEpGEpEpDIndex
      NonReplicated }

mcsMgrDprsMcsEpGEpEpDRowStatus OBJECT-TYPE
   SYNTAX     RowStatus 
   ACCESS     read-only
   STATUS     mandatory
   DESCRIPTION
     "This variable is used as the basis for SNMP naming of
      mcsMgrDprsMcsEpGEpEpD components.
      These components cannot be added nor deleted."
::= { mcsMgrDprsMcsEpGEpEpDRowStatusEntry 1 }

mcsMgrDprsMcsEpGEpEpDComponentName OBJECT-TYPE
   SYNTAX     DisplayString 
   ACCESS     read-only
   STATUS     mandatory
   DESCRIPTION
     "This variable provides the component's string name for
      use with the ASCII Console Interface"
::= { mcsMgrDprsMcsEpGEpEpDRowStatusEntry 2 }

mcsMgrDprsMcsEpGEpEpDStorageType OBJECT-TYPE
   SYNTAX     StorageType 
   ACCESS     read-only
   STATUS     mandatory
   DESCRIPTION
     "This variable represents the storage type value for the
      mcsMgrDprsMcsEpGEpEpD tables."
::= { mcsMgrDprsMcsEpGEpEpDRowStatusEntry 4 }

mcsMgrDprsMcsEpGEpEpDIndex OBJECT-TYPE
   SYNTAX     NonReplicated 
   ACCESS     not-accessible
   STATUS     mandatory
   DESCRIPTION
     "This variable represents the index for the mcsMgrDprsMcsEpGEpEpD tables."
::= { mcsMgrDprsMcsEpGEpEpDRowStatusEntry 10 }

mcsMgrDprsMcsEpGEpEpDProvTable OBJECT-TYPE
   SYNTAX     SEQUENCE OF McsMgrDprsMcsEpGEpEpDProvEntry
   ACCESS     not-accessible
   STATUS     mandatory
   DESCRIPTION
     "This group contains the parameters used to establish the transport 
      connection for this Ep."
::= { mcsMgrDprsMcsEpGEpEpD 10 }

mcsMgrDprsMcsEpGEpEpDProvEntry OBJECT-TYPE
   SYNTAX     McsMgrDprsMcsEpGEpEpDProvEntry
   ACCESS     not-accessible
   STATUS     mandatory
   DESCRIPTION
     "An entry in the mcsMgrDprsMcsEpGEpEpDProvTable."
   INDEX {
      mcsMgrIndex,
      mcsMgrDprsMcsEpGIndex,
      mcsMgrDprsMcsEpGEpIndex,
      mcsMgrDprsMcsEpGEpEpDIndex }
::= { mcsMgrDprsMcsEpGEpEpDProvTable 1 }

McsMgrDprsMcsEpGEpEpDProvEntry ::= SEQUENCE {
   mcsMgrDprsMcsEpGEpEpDBandwidth
      Unsigned32,
   mcsMgrDprsMcsEpGEpEpDConnectionTransferPriority
      Unsigned32,
   mcsMgrDprsMcsEpGEpEpDTransportConnectionPreference
      INTEGER,
   mcsMgrDprsMcsEpGEpEpDProfile
      Link,
   mcsMgrDprsMcsEpGEpEpDPorsManualPath
      Link,
   mcsMgrDprsMcsEpGEpEpDSupportedTransferPriorities
      OCTET STRING }

mcsMgrDprsMcsEpGEpEpDBandwidth OBJECT-TYPE
   SYNTAX     Unsigned32 (56000..155000000)
   ACCESS     read-write
   STATUS     mandatory
   DESCRIPTION
     "This attribute specifies the bandwidth at which the transport 
      connection agrees to transfer information. 
      A conservative value would be the sum of the committed 
      information rates (CIRs) of all individual Frame Relay DLCIs 
      multiplexed on the transport connection.
      For ATM connections, the value is converted to an equivalent Peak 
      Cell Rate (PCR01) for all cells with Cell Loss Priority (CLP), CLP 
      = 0 and CLP = 1. 
      Note that the conversion to an equivalent cell rate for ATM 
      connections may result in some wasted bandwidth depending on the 
      average frame size to cell ratio."
   DEFVAL     { 512000 }
::= { mcsMgrDprsMcsEpGEpEpDProvEntry 1 }

mcsMgrDprsMcsEpGEpEpDConnectionTransferPriority OBJECT-TYPE
   SYNTAX     Unsigned32 (0..15)
   ACCESS     read-write
   STATUS     mandatory
   DESCRIPTION
     "This attribute specifies the transfer priority used to establish the 
      transport connection. It references the ModuleData Frs AtmNet Tpm 
      to determine the ATM service category to be used by the transport 
      connection.
      This attribute is used by the Ep solely for the purpose of 
      determining the service category that should be used to establish the 
      transport connection."
::= { mcsMgrDprsMcsEpGEpEpDProvEntry 2 }

mcsMgrDprsMcsEpGEpEpDTransportConnectionPreference OBJECT-TYPE
   SYNTAX     INTEGER  {
                 atmOnly(1),
                 porsOnly(3) }
   ACCESS     read-write
   STATUS     mandatory
   DESCRIPTION
     "This attribute specifies the preference of routing system to be used 
      to set up the transport connection. 
      If a value of atmOnly is specified, attempts to set up the transport 
      connection will be made using only the ATM routing system's 
      network facilities.
      If a value of porsOnly is specified, attempts to set up the transport 
      connection will be made using only PORS network facilities."
   DEFVAL     { porsOnly }
::= { mcsMgrDprsMcsEpGEpEpDProvEntry 3 }

mcsMgrDprsMcsEpGEpEpDProfile OBJECT-TYPE
   SYNTAX     Link 
   ACCESS     read-write
   STATUS     mandatory
   DESCRIPTION
     "This attribute specifies the PORS profile to be used for the transport 
      connection when it is set up using PORS. This attribute is ignored if 
      the transportConnectionPreference is atmOnly."
::= { mcsMgrDprsMcsEpGEpEpDProvEntry 4 }

mcsMgrDprsMcsEpGEpEpDPorsManualPath OBJECT-TYPE
   SYNTAX     Link 
   ACCESS     read-write
   STATUS     mandatory
   DESCRIPTION
     "This attribute specifies the PORS manual path to be used for the 
      transport connection when it is set up using PORS. The manual path 
      that this attribute is linked to specifies the sequence of Trunks that 
      will be used when PORS chooses and instantiates the route. 
      This attribute is ignored if the transportConnectionPreference is 
      atmOnly."
::= { mcsMgrDprsMcsEpGEpEpDProvEntry 5 }

mcsMgrDprsMcsEpGEpEpDSupportedTransferPriorities OBJECT-TYPE
   SYNTAX     OCTET STRING (SIZE (2))
   ACCESS     read-write
   STATUS     mandatory
   DESCRIPTION
     "This attribute specifies the Frame Relay transfer priorities that are 
      supported through the transport connection. It is used to determine 
      which EndPoint within a DprsMcsEndPointGroup is to multiplex a 
      particular Frame Relay DLCI.
      A particular transfer priority can be specified on at most one 
      EndPoint within a DprsMcsEndPointGroup.

      Description of bits:
      n0(0)
      n1(1)
      n2(2)
      n3(3)
      n4(4)
      n5(5)
      n6(6)
      n7(7)
      n8(8)
      n9(9)
      n10(10)
      n11(11)
      n12(12)
      n13(13)
      n14(14)
      n15(15)"
   DEFVAL     { '8000'H }
::= { mcsMgrDprsMcsEpGEpEpDProvEntry 6 }


-- An AtmConnection component is created for each ATM connection 
-- established by an application. It shows where the data traffic for this 
-- connection is directed.

mcsMgrDprsMcsEpGEpAtmCon OBJECT IDENTIFIER ::= { mcsMgrDprsMcsEpGEp 3 }



mcsMgrDprsMcsEpGEpAtmConRowStatusTable OBJECT-TYPE
   SYNTAX     SEQUENCE OF McsMgrDprsMcsEpGEpAtmConRowStatusEntry
   ACCESS     not-accessible
   STATUS     mandatory
   DESCRIPTION
     "This entry controls the addition and deletion of 
      mcsMgrDprsMcsEpGEpAtmCon components."
::= { mcsMgrDprsMcsEpGEpAtmCon 1 }

mcsMgrDprsMcsEpGEpAtmConRowStatusEntry OBJECT-TYPE
   SYNTAX     McsMgrDprsMcsEpGEpAtmConRowStatusEntry
   ACCESS     not-accessible
   STATUS     mandatory
   DESCRIPTION
     "A single entry in the table represents a single 
      mcsMgrDprsMcsEpGEpAtmCon component."
   INDEX {
      mcsMgrIndex,
      mcsMgrDprsMcsEpGIndex,
      mcsMgrDprsMcsEpGEpIndex,
      mcsMgrDprsMcsEpGEpAtmConIndex }
::= { mcsMgrDprsMcsEpGEpAtmConRowStatusTable 1 }

McsMgrDprsMcsEpGEpAtmConRowStatusEntry ::= SEQUENCE {
   mcsMgrDprsMcsEpGEpAtmConRowStatus
      RowStatus,
   mcsMgrDprsMcsEpGEpAtmConComponentName
      DisplayString,
   mcsMgrDprsMcsEpGEpAtmConStorageType
      StorageType,
   mcsMgrDprsMcsEpGEpAtmConIndex
      NonReplicated }

mcsMgrDprsMcsEpGEpAtmConRowStatus OBJECT-TYPE
   SYNTAX     RowStatus 
   ACCESS     read-only
   STATUS     mandatory
   DESCRIPTION
     "This variable is used as the basis for SNMP naming of
      mcsMgrDprsMcsEpGEpAtmCon components.
      These components cannot be added nor deleted."
::= { mcsMgrDprsMcsEpGEpAtmConRowStatusEntry 1 }

mcsMgrDprsMcsEpGEpAtmConComponentName OBJECT-TYPE
   SYNTAX     DisplayString 
   ACCESS     read-only
   STATUS     mandatory
   DESCRIPTION
     "This variable provides the component's string name for
      use with the ASCII Console Interface"
::= { mcsMgrDprsMcsEpGEpAtmConRowStatusEntry 2 }

mcsMgrDprsMcsEpGEpAtmConStorageType OBJECT-TYPE
   SYNTAX     StorageType 
   ACCESS     read-only
   STATUS     mandatory
   DESCRIPTION
     "This variable represents the storage type value for the
      mcsMgrDprsMcsEpGEpAtmCon tables."
::= { mcsMgrDprsMcsEpGEpAtmConRowStatusEntry 4 }

mcsMgrDprsMcsEpGEpAtmConIndex OBJECT-TYPE
   SYNTAX     NonReplicated 
   ACCESS     not-accessible
   STATUS     mandatory
   DESCRIPTION
     "This variable represents the index for the mcsMgrDprsMcsEpGEpAtmCon tables."
::= { mcsMgrDprsMcsEpGEpAtmConRowStatusEntry 10 }

mcsMgrDprsMcsEpGEpAtmConOperTable OBJECT-TYPE
   SYNTAX     SEQUENCE OF McsMgrDprsMcsEpGEpAtmConOperEntry
   ACCESS     not-accessible
   STATUS     mandatory
   DESCRIPTION
     "This attribute group contains the operational attributes for the 
      NapAtmConnection component."
::= { mcsMgrDprsMcsEpGEpAtmCon 10 }

mcsMgrDprsMcsEpGEpAtmConOperEntry OBJECT-TYPE
   SYNTAX     McsMgrDprsMcsEpGEpAtmConOperEntry
   ACCESS     not-accessible
   STATUS     mandatory
   DESCRIPTION
     "An entry in the mcsMgrDprsMcsEpGEpAtmConOperTable."
   INDEX {
      mcsMgrIndex,
      mcsMgrDprsMcsEpGIndex,
      mcsMgrDprsMcsEpGEpIndex,
      mcsMgrDprsMcsEpGEpAtmConIndex }
::= { mcsMgrDprsMcsEpGEpAtmConOperTable 1 }

McsMgrDprsMcsEpGEpAtmConOperEntry ::= SEQUENCE {
   mcsMgrDprsMcsEpGEpAtmConNextHop
      RowPointer }

mcsMgrDprsMcsEpGEpAtmConNextHop OBJECT-TYPE
   SYNTAX     RowPointer 
   ACCESS     read-only
   STATUS     mandatory
   DESCRIPTION
     "This attribute shows the component name of the AtmIf Vcc Ep or 
      AtmCon component to which this switched connection is 
      established."
::= { mcsMgrDprsMcsEpGEpAtmConOperEntry 1 }


-- ...Lc
-- This component contains all of the operation attributes for a Path 
-- Oriented Logical Connection.

mcsMgrDprsMcsEpGEpLCo OBJECT IDENTIFIER ::= { mcsMgrDprsMcsEpGEp 4 }



mcsMgrDprsMcsEpGEpLCoRowStatusTable OBJECT-TYPE
   SYNTAX     SEQUENCE OF McsMgrDprsMcsEpGEpLCoRowStatusEntry
   ACCESS     not-accessible
   STATUS     mandatory
   DESCRIPTION
     "This entry controls the addition and deletion of 
      mcsMgrDprsMcsEpGEpLCo components."
::= { mcsMgrDprsMcsEpGEpLCo 1 }

mcsMgrDprsMcsEpGEpLCoRowStatusEntry OBJECT-TYPE
   SYNTAX     McsMgrDprsMcsEpGEpLCoRowStatusEntry
   ACCESS     not-accessible
   STATUS     mandatory
   DESCRIPTION
     "A single entry in the table represents a single 
      mcsMgrDprsMcsEpGEpLCo component."
   INDEX {
      mcsMgrIndex,
      mcsMgrDprsMcsEpGIndex,
      mcsMgrDprsMcsEpGEpIndex,
      mcsMgrDprsMcsEpGEpLCoIndex }
::= { mcsMgrDprsMcsEpGEpLCoRowStatusTable 1 }

McsMgrDprsMcsEpGEpLCoRowStatusEntry ::= SEQUENCE {
   mcsMgrDprsMcsEpGEpLCoRowStatus
      RowStatus,
   mcsMgrDprsMcsEpGEpLCoComponentName
      DisplayString,
   mcsMgrDprsMcsEpGEpLCoStorageType
      StorageType,
   mcsMgrDprsMcsEpGEpLCoIndex
      NonReplicated }

mcsMgrDprsMcsEpGEpLCoRowStatus OBJECT-TYPE
   SYNTAX     RowStatus 
   ACCESS     read-only
   STATUS     mandatory
   DESCRIPTION
     "This variable is used as the basis for SNMP naming of
      mcsMgrDprsMcsEpGEpLCo components.
      These components cannot be added nor deleted."
::= { mcsMgrDprsMcsEpGEpLCoRowStatusEntry 1 }

mcsMgrDprsMcsEpGEpLCoComponentName OBJECT-TYPE
   SYNTAX     DisplayString 
   ACCESS     read-only
   STATUS     mandatory
   DESCRIPTION
     "This variable provides the component's string name for
      use with the ASCII Console Interface"
::= { mcsMgrDprsMcsEpGEpLCoRowStatusEntry 2 }

mcsMgrDprsMcsEpGEpLCoStorageType OBJECT-TYPE
   SYNTAX     StorageType 
   ACCESS     read-only
   STATUS     mandatory
   DESCRIPTION
     "This variable represents the storage type value for the
      mcsMgrDprsMcsEpGEpLCo tables."
::= { mcsMgrDprsMcsEpGEpLCoRowStatusEntry 4 }

mcsMgrDprsMcsEpGEpLCoIndex OBJECT-TYPE
   SYNTAX     NonReplicated 
   ACCESS     not-accessible
   STATUS     mandatory
   DESCRIPTION
     "This variable represents the index for the mcsMgrDprsMcsEpGEpLCo tables."
::= { mcsMgrDprsMcsEpGEpLCoRowStatusEntry 10 }

mcsMgrDprsMcsEpGEpLCoPathDataTable OBJECT-TYPE
   SYNTAX     SEQUENCE OF McsMgrDprsMcsEpGEpLCoPathDataEntry
   ACCESS     not-accessible
   STATUS     mandatory
   DESCRIPTION
     "This group contains all operational attributes for the path oriented 
      LCo."
::= { mcsMgrDprsMcsEpGEpLCo 10 }

mcsMgrDprsMcsEpGEpLCoPathDataEntry OBJECT-TYPE
   SYNTAX     McsMgrDprsMcsEpGEpLCoPathDataEntry
   ACCESS     not-accessible
   STATUS     mandatory
   DESCRIPTION
     "An entry in the mcsMgrDprsMcsEpGEpLCoPathDataTable."
   INDEX {
      mcsMgrIndex,
      mcsMgrDprsMcsEpGIndex,
      mcsMgrDprsMcsEpGEpIndex,
      mcsMgrDprsMcsEpGEpLCoIndex }
::= { mcsMgrDprsMcsEpGEpLCoPathDataTable 1 }

McsMgrDprsMcsEpGEpLCoPathDataEntry ::= SEQUENCE {
   mcsMgrDprsMcsEpGEpLCoState
      INTEGER,
   mcsMgrDprsMcsEpGEpLCoOverrideRemoteName
      AsciiString,
   mcsMgrDprsMcsEpGEpLCoEnd
      INTEGER,
   mcsMgrDprsMcsEpGEpLCoCostMetric
      Unsigned32,
   mcsMgrDprsMcsEpGEpLCoDelayMetric
      Unsigned32,
   mcsMgrDprsMcsEpGEpLCoRoundTripDelay
      Unsigned32,
   mcsMgrDprsMcsEpGEpLCoSetupPriority
      Unsigned32,
   mcsMgrDprsMcsEpGEpLCoHoldingPriority
      Unsigned32,
   mcsMgrDprsMcsEpGEpLCoRequiredTxBandwidth
      Gauge32,
   mcsMgrDprsMcsEpGEpLCoRequiredRxBandwidth
      Gauge32,
   mcsMgrDprsMcsEpGEpLCoRequiredTrafficType
      INTEGER,
   mcsMgrDprsMcsEpGEpLCoPermittedTrunkTypes
      OCTET STRING,
   mcsMgrDprsMcsEpGEpLCoRequiredSecurity
      Unsigned32,
   mcsMgrDprsMcsEpGEpLCoRequiredCustomerParameter
      Unsigned32,
   mcsMgrDprsMcsEpGEpLCoEmissionPriority
      Unsigned32,
   mcsMgrDprsMcsEpGEpLCoDiscardPriority
      Unsigned32,
   mcsMgrDprsMcsEpGEpLCoPathType
      INTEGER,
   mcsMgrDprsMcsEpGEpLCoRetryCount
      Unsigned32,
   mcsMgrDprsMcsEpGEpLCoPathFailureCount
      Unsigned32,
   mcsMgrDprsMcsEpGEpLCoReasonForNoRoute
      INTEGER,
   mcsMgrDprsMcsEpGEpLCoLastTearDownReason
      INTEGER,
   mcsMgrDprsMcsEpGEpLCoPathFailureAction
      INTEGER,
   mcsMgrDprsMcsEpGEpLCoBumpPreference
      INTEGER,
   mcsMgrDprsMcsEpGEpLCoOptimization
      INTEGER,
   mcsMgrDprsMcsEpGEpLCoPathUpDateTime
      EnterpriseDateAndTime }

mcsMgrDprsMcsEpGEpLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { mcsMgrDprsMcsEpGEpLCoPathDataEntry 1 }

mcsMgrDprsMcsEpGEpLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { mcsMgrDprsMcsEpGEpLCoPathDataEntry 2 }

mcsMgrDprsMcsEpGEpLCoEnd OBJECT-TYPE
   SYNTAX     INTEGER  {
                 calling(0),
                 called(1) }
   ACCESS     read-only
   STATUS     mandatory
   DESCRIPTION
     "This attribute identifies whether this is the calling or called end of 
      the path."
::= { mcsMgrDprsMcsEpGEpLCoPathDataEntry 3 }

mcsMgrDprsMcsEpGEpLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { mcsMgrDprsMcsEpGEpLCoPathDataEntry 4 }

mcsMgrDprsMcsEpGEpLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { mcsMgrDprsMcsEpGEpLCoPathDataEntry 5 }

mcsMgrDprsMcsEpGEpLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { mcsMgrDprsMcsEpGEpLCoPathDataEntry 6 }

mcsMgrDprsMcsEpGEpLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { mcsMgrDprsMcsEpGEpLCoPathDataEntry 7 }

mcsMgrDprsMcsEpGEpLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { mcsMgrDprsMcsEpGEpLCoPathDataEntry 8 }

mcsMgrDprsMcsEpGEpLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { mcsMgrDprsMcsEpGEpLCoPathDataEntry 9 }

mcsMgrDprsMcsEpGEpLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { mcsMgrDprsMcsEpGEpLCoPathDataEntry 10 }

mcsMgrDprsMcsEpGEpLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { mcsMgrDprsMcsEpGEpLCoPathDataEntry 11 }

mcsMgrDprsMcsEpGEpLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { mcsMgrDprsMcsEpGEpLCoPathDataEntry 12 }

mcsMgrDprsMcsEpGEpLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { mcsMgrDprsMcsEpGEpLCoPathDataEntry 13 }

mcsMgrDprsMcsEpGEpLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { mcsMgrDprsMcsEpGEpLCoPathDataEntry 14 }

mcsMgrDprsMcsEpGEpLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { mcsMgrDprsMcsEpGEpLCoPathDataEntry 15 }

mcsMgrDprsMcsEpGEpLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { mcsMgrDprsMcsEpGEpLCoPathDataEntry 16 }

mcsMgrDprsMcsEpGEpLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { mcsMgrDprsMcsEpGEpLCoPathDataEntry 17 }

mcsMgrDprsMcsEpGEpLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { mcsMgrDprsMcsEpGEpLCoPathDataEntry 18 }

mcsMgrDprsMcsEpGEpLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { mcsMgrDprsMcsEpGEpLCoPathDataEntry 19 }

mcsMgrDprsMcsEpGEpLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { mcsMgrDprsMcsEpGEpLCoPathDataEntry 20 }

mcsMgrDprsMcsEpGEpLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { mcsMgrDprsMcsEpGEpLCoPathDataEntry 21 }

mcsMgrDprsMcsEpGEpLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { mcsMgrDprsMcsEpGEpLCoPathDataEntry 22 }

mcsMgrDprsMcsEpGEpLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { mcsMgrDprsMcsEpGEpLCoPathDataEntry 23 }

mcsMgrDprsMcsEpGEpLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { mcsMgrDprsMcsEpGEpLCoPathDataEntry 24 }

mcsMgrDprsMcsEpGEpLCoPathUpDateTime OBJECT-TYPE
   SYNTAX     EnterpriseDateAndTime (SIZE (0 | 19))
   ACCESS     read-only
   STATUS     mandatory
   DESCRIPTION
     "This is the time stamp when the current path was established or 
      reestablished."
::= { mcsMgrDprsMcsEpGEpLCoPathDataEntry 25 }

mcsMgrDprsMcsEpGEpLCoStatsTable OBJECT-TYPE
   SYNTAX     SEQUENCE OF McsMgrDprsMcsEpGEpLCoStatsEntry
   ACCESS     not-accessible
   STATUS     mandatory
   DESCRIPTION
     "This group contains the operational statistics attributes for the path 
      oriented LCo."
::= { mcsMgrDprsMcsEpGEpLCo 11 }

mcsMgrDprsMcsEpGEpLCoStatsEntry OBJECT-TYPE
   SYNTAX     McsMgrDprsMcsEpGEpLCoStatsEntry
   ACCESS     not-accessible
   STATUS     mandatory
   DESCRIPTION
     "An entry in the mcsMgrDprsMcsEpGEpLCoStatsTable."
   INDEX {
      mcsMgrIndex,
      mcsMgrDprsMcsEpGIndex,
      mcsMgrDprsMcsEpGEpIndex,
      mcsMgrDprsMcsEpGEpLCoIndex }
::= { mcsMgrDprsMcsEpGEpLCoStatsTable 1 }

McsMgrDprsMcsEpGEpLCoStatsEntry ::= SEQUENCE {
   mcsMgrDprsMcsEpGEpLCoPktsToNetwork
      PassportCounter64,
   mcsMgrDprsMcsEpGEpLCoBytesToNetwork
      PassportCounter64,
   mcsMgrDprsMcsEpGEpLCoPktsFromNetwork
      PassportCounter64,
   mcsMgrDprsMcsEpGEpLCoBytesFromNetwork
      PassportCounter64 }

mcsMgrDprsMcsEpGEpLCoPktsToNetwork OBJECT-TYPE
   SYNTAX     PassportCounter64 
   ACCESS     read-only
   STATUS     mandatory
   DESCRIPTION
     "This attribute counts the number of packets transmitted to the 
      network over this Logical Connection."
::= { mcsMgrDprsMcsEpGEpLCoStatsEntry 1 }

mcsMgrDprsMcsEpGEpLCoBytesToNetwork OBJECT-TYPE
   SYNTAX     PassportCounter64 
   ACCESS     read-only
   STATUS     mandatory
   DESCRIPTION
     "This attribute counts the number of bytes sent to the network over 
      this Logical Connection."
::= { mcsMgrDprsMcsEpGEpLCoStatsEntry 2 }

mcsMgrDprsMcsEpGEpLCoPktsFromNetwork OBJECT-TYPE
   SYNTAX     PassportCounter64 
   ACCESS     read-only
   STATUS     mandatory
   DESCRIPTION
     "This attribute counts the number of packets received from the 
      remote LCo via the network."
::= { mcsMgrDprsMcsEpGEpLCoStatsEntry 3 }

mcsMgrDprsMcsEpGEpLCoBytesFromNetwork OBJECT-TYPE
   SYNTAX     PassportCounter64 
   ACCESS     read-only
   STATUS     mandatory
   DESCRIPTION
     "This attribute counts the number of bytes received from the remote 
      LCo via the network."
::= { mcsMgrDprsMcsEpGEpLCoStatsEntry 4 }

mcsMgrDprsMcsEpGEpLCoPathTable OBJECT-TYPE
   SYNTAX     SEQUENCE OF McsMgrDprsMcsEpGEpLCoPathEntry
   ACCESS     not-accessible
   STATUS     mandatory
   DESCRIPTION
     "This attribute contains the trunk component names over which the 
      path has been instantiated and the remote end point name 
      terminating the path."
::= { mcsMgrDprsMcsEpGEpLCo 264 }

mcsMgrDprsMcsEpGEpLCoPathEntry OBJECT-TYPE
   SYNTAX     McsMgrDprsMcsEpGEpLCoPathEntry
   ACCESS     not-accessible
   STATUS     mandatory
   DESCRIPTION
     "An entry in the mcsMgrDprsMcsEpGEpLCoPathTable."
   INDEX {
      mcsMgrIndex,
      mcsMgrDprsMcsEpGIndex,
      mcsMgrDprsMcsEpGEpIndex,
      mcsMgrDprsMcsEpGEpLCoIndex,
      mcsMgrDprsMcsEpGEpLCoPathValue }
::= { mcsMgrDprsMcsEpGEpLCoPathTable 1 }

McsMgrDprsMcsEpGEpLCoPathEntry ::= SEQUENCE {
   mcsMgrDprsMcsEpGEpLCoPathValue
      AsciiString }

mcsMgrDprsMcsEpGEpLCoPathValue OBJECT-TYPE
   SYNTAX     AsciiString (SIZE (0..40))
   ACCESS     read-only
   STATUS     mandatory
   DESCRIPTION
     "This variable represents both the value and the index for the
      mcsMgrDprsMcsEpGEpLCoPathTable."
::= { mcsMgrDprsMcsEpGEpLCoPathEntry 1 }




-- 
-- Version and Compliance statements
-- 



-- Object-Group Statement:
-- A list of all current accessible leaf objects.

-- OBJECTS { mcsMgrDprsMcsEpGEpLCoEmissionPriority,
--           mcsMgrDprsMcsEpGEpLCoLastTearDownReason,
--           mcsMgrDprsMcsEpGEpEpDPorsManualPath,
--           mcsMgrDprsMcsEpGEpLCoDiscardPriority,
--           mcsMgrDprsMcsEpGEpLCoRequiredCustomerParameter,
--           mcsMgrDprsMcsEpGEpLCoRequiredSecurity,
--           mcsMgrDprsMcsEpGEpLCoPathFailureCount,
--           mcsMgrDprsMcsEpGEpRemoteRoutingId,
--           mcsMgrDprsMcsEpGEpOctetsFromMcsValue,
--           mcsMgrDprsMcsEpGEpEpDConnectionTransferPriority,
--           mcsMgrDprsMcsEpGEpBandwidth,
--           mcsMgrDprsMcsEpGEpAvailabilityStatus,
--           mcsMgrDprsMcsEpGEpLCoOptimization,
--           mcsMgrDprsMcsEpGAssociatedEpGroupName,
--           mcsMgrDprsMcsEpGAddrRemoteAddress,
--           mcsMgrDprsMcsEpGRemoteAddress,
--           mcsMgrDprsMcsEpGEpLCoStorageType,
--           mcsMgrDprsMcsEpGEpAlarmStatus,
--           mcsMgrDprsMcsEpGEpLCoRequiredTxBandwidth,
--           mcsMgrDprsMcsEpGEpLCoHoldingPriority,
--           mcsMgrDprsMcsEpGEpLCoPktsToNetwork,
--           mcsMgrDprsMcsEpGEpUnknownStatus,
--           mcsMgrDprsMcsEpGEpStandbyStatus,
--           mcsMgrDprsMcsEpGAddrCommentText,
--           mcsMgrDprsMcsEpGEpLCoBytesFromNetwork,
--           mcsMgrDprsMcsEpGEpLCoPathValue,
--           mcsMgrDprsMcsEpGEpConnectionTransferPriority,
--           mcsMgrDprsMcsEpGEpPktDiscErroredFromMcs,
--           mcsMgrDprsMcsEpGEpLCoBytesToNetwork,
--           mcsMgrDprsMcsEpGEpLCoRoundTripDelay,
--           mcsMgrDprsMcsEpGEpEpDRowStatus,
--           mcsMgrDprsMcsEpGEpSupportedTransferPriorities,
--           mcsMgrDprsMcsEpGEpLastTransportConnectionClearCause,
--           mcsMgrDprsMcsEpGEpLCoState,
--           mcsMgrDprsMcsEpGEpEpDSupportedTransferPriorities,
--           mcsMgrDprsMcsEpGEpType,
--           mcsMgrDprsMcsEpGEpLCoEnd,
--           mcsMgrDprsMcsEpGEpLCoSetupPriority,
--           mcsMgrDprsMcsEpGEpPktDiscCongestedFromMcsValue,
--           mcsMgrDprsMcsEpGEpRemoteComponentName,
--           mcsMgrDprsMcsEpGEpControlStatus,
--           mcsMgrDprsMcsEpGEpAdminState,
--           mcsMgrDprsMcsEpGEpLCoPathFailureAction,
--           mcsMgrDprsMcsEpGEpAtmConStorageType,
--           mcsMgrDprsMcsEpGEpLCoRequiredRxBandwidth,
--           mcsMgrDprsMcsEpGEpEpDComponentName,
--           mcsMgrDprsMcsEpGEpLCoBumpPreference,
--           mcsMgrDprsMcsEpGEpRowStatus,
--           mcsMgrDprsMcsEpGAddrStorageType,
--           mcsMgrDprsMcsEpGEpProceduralStatus,
--           mcsMgrDprsMcsEpGEpLCoRowStatus,
--           mcsMgrDprsMcsEpGEpRemoteModuleId,
--           mcsMgrDprsMcsEpGEpPktFromMcsValue,
--           mcsMgrDprsMcsEpGEpLCoRetryCount,
--           mcsMgrDprsMcsEpGAddrRowStatus,
--           mcsMgrDprsMcsEpGRowStatus,
--           mcsMgrDprsMcsEpGEpLCoDelayMetric,
--           mcsMgrDprsMcsEpGEpUsageState,
--           mcsMgrDprsMcsEpGEpLCoCostMetric,
--           mcsMgrDprsMcsEpGEpLCoRequiredTrafficType,
--           mcsMgrDprsMcsEpGEpLCoPathUpDateTime,
--           mcsMgrDprsMcsEpGEpServiceCategory,
--           mcsMgrDprsMcsEpGEpComponentName,
--           mcsMgrDprsMcsEpGEpLCoReasonForNoRoute,
--           mcsMgrDprsMcsEpGEpAtmConRowStatus,
--           mcsMgrDprsMcsEpGEpSetupAttempts,
--           mcsMgrDprsMcsEpGEpAtmConNextHop,
--           mcsMgrDprsMcsEpGEpLCoPathType,
--           mcsMgrDprsMcsEpGEpLCoComponentName,
--           mcsMgrDprsMcsEpGStorageType,
--           mcsMgrDprsMcsEpGEpLCoOverrideRemoteName,
--           mcsMgrDprsMcsEpGEpEpDTransportConnectionPreference,
--           mcsMgrDprsMcsEpGAddrComponentName,
--           mcsMgrDprsMcsEpGEpOperationalState,
--           mcsMgrDprsMcsEpGEpStorageType,
--           mcsMgrDprsMcsEpGEpEpDBandwidth,
--           mcsMgrDprsMcsEpGEpLastTrConnDiagCode,
--           mcsMgrDprsMcsEpGEpEpDStorageType,
--           mcsMgrDprsMcsEpGEpLCoPermittedTrunkTypes,
--           mcsMgrDprsMcsEpGEpEpDProfile,
--           mcsMgrDprsMcsEpGEpLCoPktsFromNetwork,
--           mcsMgrDprsMcsEpGEpAtmConComponentName,
--           mcsMgrDprsMcsEpGComponentName }
-- STATUS  mandatory
-- DESCRIPTION
--   "A list of all current accessible leaf objects."

dprsMcsEpGroup OBJECT IDENTIFIER ::= { dprsMcsEpMIB 1 }
dprsMcsEpGroupBE OBJECT IDENTIFIER ::= { dprsMcsEpGroup 5 }
dprsMcsEpGroupBE01 OBJECT IDENTIFIER ::= { dprsMcsEpGroupBE 2 }
dprsMcsEpGroupBE01A OBJECT IDENTIFIER ::= { dprsMcsEpGroupBE01 2 }



-- Agent-Capabilities Statement:

-- PRODUCT-RELEASE "Passport Release 7.0 DprsMcsEp."
-- STATUS          mandatory
-- DESCRIPTION     "DprsMcsEp MIB: MIB Version BE01A,
--                  Software Version BG00S4C."
-- SUPPORTS        Nortel-Magellan-Passport-DprsMcsEpMIB
--    INCLUDES     { dprsMcsEpGroupBE01A }

dprsMcsEpCapabilities OBJECT IDENTIFIER ::= { dprsMcsEpMIB 3 }
dprsMcsEpCapabilitiesBE OBJECT IDENTIFIER ::= { dprsMcsEpCapabilities 5 }
dprsMcsEpCapabilitiesBE01 OBJECT IDENTIFIER ::= { dprsMcsEpCapabilitiesBE 2 }
dprsMcsEpCapabilitiesBE01A OBJECT IDENTIFIER ::= { dprsMcsEpCapabilitiesBE01 2 }





END
