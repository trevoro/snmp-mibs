LANCOM-1711-MIB DEFINITIONS ::= BEGIN

IMPORTS
    DisplayString, sysDescr, sysName
      FROM RFC1213-MIB
    MacAddress
      FROM SNMPv2-TC
    CounterBasedGauge64
      FROM HCNUM-TC
    enterprises, OBJECT-TYPE,
    MODULE-IDENTITY, IpAddress, Counter32, Gauge32, TimeTicks, Counter64,
    NOTIFICATION-TYPE
      FROM SNMPv2-SMI;



lancom-1711-plus MODULE-IDENTITY
    LAST-UPDATED "200908121708Z"
    ORGANIZATION "LANCOM Systems"
    CONTACT-INFO "http://www.lancom-systems.de"
    DESCRIPTION "MIB Definitions for LANCOM 1711+ VPN"
    REVISION "200908121708Z"
    DESCRIPTION "Auto-Generated on Apr 04, 2010"
    ::= { enterprises lancom-systems(2356) adsl-systems(500) lan-router(2) 1712 }


sta OBJECT IDENTIFIER ::= { lancom-1711-plus 1 }
set OBJECT IDENTIFIER ::= { lancom-1711-plus 2 }
fir OBJECT IDENTIFIER ::= { lancom-1711-plus 3 }
oth OBJECT IDENTIFIER ::= { lancom-1711-plus 4 }

staOper OBJECT-TYPE
        SYNTAX DisplayString
        MAX-ACCESS read-only
        STATUS current
        DESCRIPTION "Operating-Time"
        ::= {  sta 2 }

staWan OBJECT IDENTIFIER ::= { sta 4}
staWanBytetransTable OBJECT-TYPE
                     SYNTAX SEQUENCE OF StaWanBytetransEntry
                     MAX-ACCESS not-accessible
                     STATUS current
                     DESCRIPTION "Byte-Transport"
                     ::= {  staWan 1 }

staWanBytetransEntry OBJECT-TYPE
                     SYNTAX StaWanBytetransEntry
                     MAX-ACCESS not-accessible
                     STATUS current
                     DESCRIPTION "entry in table"
                     INDEX { staWanBytetransIfc }
                     ::= {  staWanBytetransTable 1 }

StaWanBytetransEntry ::= SEQUENCE {
                     staWanBytetransIfc INTEGER,
                     staWanBytetransCrx Counter32,
                     staWanBytetransRxb Counter32,
                     staWanBytetransTxb Counter32,
                     staWanBytetransCtx Counter32
                    }

staWanBytetransIfc OBJECT-TYPE
                   SYNTAX INTEGER
                   {
                     dsl-ch-1(1),
                     dsl-ch-2(2),
                     dsl-ch-3(3),
                     dsl-ch-4(4),
                     dsl-ch-5(5),
                     dsl-ch-6(6),
                     dsl-ch-7(7),
                     dsl-ch-8(8),
                     ch01(9),
                     ch02(10),
                     ext(11)
                   }
                   MAX-ACCESS read-only
                   STATUS current
                   DESCRIPTION "Ifc"
                   ::= {  staWanBytetransEntry 1 }

staWanBytetransCrx OBJECT-TYPE
                   SYNTAX Counter32
                   MAX-ACCESS read-only
                   STATUS current
                   DESCRIPTION "CRx-Bytes"
                   ::= {  staWanBytetransEntry 2 }

staWanBytetransRxb OBJECT-TYPE
                   SYNTAX Counter32
                   MAX-ACCESS read-only
                   STATUS current
                   DESCRIPTION "Rx-Bytes"
                   ::= {  staWanBytetransEntry 3 }

staWanBytetransTxb OBJECT-TYPE
                   SYNTAX Counter32
                   MAX-ACCESS read-only
                   STATUS current
                   DESCRIPTION "Tx-Bytes"
                   ::= {  staWanBytetransEntry 4 }

staWanBytetransCtx OBJECT-TYPE
                   SYNTAX Counter32
                   MAX-ACCESS read-only
                   STATUS current
                   DESCRIPTION "CTx-Bytes"
                   ::= {  staWanBytetransEntry 5 }

staWanPackettraTable OBJECT-TYPE
                     SYNTAX SEQUENCE OF StaWanPackettraEntry
                     MAX-ACCESS not-accessible
                     STATUS current
                     DESCRIPTION "Packet-Transport"
                     ::= {  staWan 2 }

staWanPackettraEntry OBJECT-TYPE
                     SYNTAX StaWanPackettraEntry
                     MAX-ACCESS not-accessible
                     STATUS current
                     DESCRIPTION "entry in table"
                     INDEX { staWanPackettraIfc }
                     ::= {  staWanPackettraTable 1 }

StaWanPackettraEntry ::= SEQUENCE {
                     staWanPackettraIfc INTEGER,
                     staWanPackettraRx Counter32,
                     staWanPackettraTxt Counter32,
                     staWanPackettraTxn Counter32,
                     staWanPackettraTxr Counter32,
                     staWanPackettraTxu Counter32
                    }

staWanPackettraIfc OBJECT-TYPE
                   SYNTAX INTEGER
                   {
                     dsl-ch-1(1),
                     dsl-ch-2(2),
                     dsl-ch-3(3),
                     dsl-ch-4(4),
                     dsl-ch-5(5),
                     dsl-ch-6(6),
                     dsl-ch-7(7),
                     dsl-ch-8(8),
                     ch01(9),
                     ch02(10),
                     ext(11)
                   }
                   MAX-ACCESS read-only
                   STATUS current
                   DESCRIPTION "Ifc"
                   ::= {  staWanPackettraEntry 1 }

staWanPackettraRx OBJECT-TYPE
                   SYNTAX Counter32
                   MAX-ACCESS read-only
                   STATUS current
                   DESCRIPTION "Rx"
                   ::= {  staWanPackettraEntry 2 }

staWanPackettraTxt OBJECT-TYPE
                   SYNTAX Counter32
                   MAX-ACCESS read-only
                   STATUS current
                   DESCRIPTION "Tx-total"
                   ::= {  staWanPackettraEntry 3 }

staWanPackettraTxn OBJECT-TYPE
                   SYNTAX Counter32
                   MAX-ACCESS read-only
                   STATUS current
                   DESCRIPTION "Tx-normal"
                   ::= {  staWanPackettraEntry 4 }

staWanPackettraTxr OBJECT-TYPE
                   SYNTAX Counter32
                   MAX-ACCESS read-only
                   STATUS current
                   DESCRIPTION "Tx-reliable"
                   ::= {  staWanPackettraEntry 5 }

staWanPackettraTxu OBJECT-TYPE
                   SYNTAX Counter32
                   MAX-ACCESS read-only
                   STATUS current
                   DESCRIPTION "Tx-urgent"
                   ::= {  staWanPackettraEntry 6 }

staWanErrorsTable OBJECT-TYPE
                     SYNTAX SEQUENCE OF StaWanErrorsEntry
                     MAX-ACCESS not-accessible
                     STATUS current
                     DESCRIPTION "Errors"
                     ::= {  staWan 3 }

staWanErrorsEntry OBJECT-TYPE
                     SYNTAX StaWanErrorsEntry
                     MAX-ACCESS not-accessible
                     STATUS current
                     DESCRIPTION "entry in table"
                     INDEX { staWanErrorsIfc }
                     ::= {  staWanErrorsTable 1 }

StaWanErrorsEntry ::= SEQUENCE {
                     staWanErrorsIfc INTEGER,
                     staWanErrorsRxl1 Counter32,
                     staWanErrorsRxl2 Counter32,
                     staWanErrorsRxl3 Counter32,
                     staWanErrorsStac Counter32,
                     staWanErrorsTxer Counter32
                    }

staWanErrorsIfc OBJECT-TYPE
                 SYNTAX INTEGER
                 {
                   dsl-ch-1(1),
                   dsl-ch-2(2),
                   dsl-ch-3(3),
                   dsl-ch-4(4),
                   dsl-ch-5(5),
                   dsl-ch-6(6),
                   dsl-ch-7(7),
                   dsl-ch-8(8),
                   ch01(9),
                   ch02(10),
                   ext(11)
                 }
                 MAX-ACCESS read-only
                 STATUS current
                 DESCRIPTION "Ifc"
                 ::= {  staWanErrorsEntry 1 }

staWanErrorsRxl1 OBJECT-TYPE
                 SYNTAX Counter32
                 MAX-ACCESS read-only
                 STATUS current
                 DESCRIPTION "Rx-l1-Error"
                 ::= {  staWanErrorsEntry 2 }

staWanErrorsRxl2 OBJECT-TYPE
                 SYNTAX Counter32
                 MAX-ACCESS read-only
                 STATUS current
                 DESCRIPTION "Rx-l2-Error"
                 ::= {  staWanErrorsEntry 3 }

staWanErrorsRxl3 OBJECT-TYPE
                 SYNTAX Counter32
                 MAX-ACCESS read-only
                 STATUS current
                 DESCRIPTION "Rx-l3-Error"
                 ::= {  staWanErrorsEntry 4 }

staWanErrorsStac OBJECT-TYPE
                 SYNTAX Counter32
                 MAX-ACCESS read-only
                 STATUS current
                 DESCRIPTION "Stack-Error"
                 ::= {  staWanErrorsEntry 5 }

staWanErrorsTxer OBJECT-TYPE
                 SYNTAX Counter32
                 MAX-ACCESS read-only
                 STATUS current
                 DESCRIPTION "Tx-Error"
                 ::= {  staWanErrorsEntry 6 }

staWanWantxdisc OBJECT-TYPE
                SYNTAX Counter32
                MAX-ACCESS read-only
                STATUS current
                DESCRIPTION "WAN-Tx-Discarded"
                ::= {  staWan 4 }

staWanWanheappa OBJECT-TYPE
                SYNTAX INTEGER
                MAX-ACCESS read-only
                STATUS current
                DESCRIPTION "WAN-Heap-Packets"
                ::= {  staWan 5 }

staWanWanqueuep OBJECT-TYPE
                SYNTAX INTEGER
                MAX-ACCESS read-only
                STATUS current
                DESCRIPTION "WAN-Queue-Packets"
                ::= {  staWan 6 }

staWanWanqueuee OBJECT-TYPE
                SYNTAX Counter32
                MAX-ACCESS read-only
                STATUS current
                DESCRIPTION "WAN-Queue-Errors"
                ::= {  staWan 7 }

staWanWanqueuem OBJECT-TYPE
                SYNTAX Counter32
                MAX-ACCESS read-only
                STATUS current
                DESCRIPTION "WAN-Queue-Mgt-Drop"
                ::= {  staWan 21 }

staWanThroughpuTable OBJECT-TYPE
                     SYNTAX SEQUENCE OF StaWanThroughpuEntry
                     MAX-ACCESS not-accessible
                     STATUS current
                     DESCRIPTION "Throughput"
                     ::= {  staWan 8 }

staWanThroughpuEntry OBJECT-TYPE
                     SYNTAX StaWanThroughpuEntry
                     MAX-ACCESS not-accessible
                     STATUS current
                     DESCRIPTION "entry in table"
                     INDEX { staWanThroughpuIfc }
                     ::= {  staWanThroughpuTable 1 }

StaWanThroughpuEntry ::= SEQUENCE {
                     staWanThroughpuIfc INTEGER,
                     staWanThroughpuRxsc INTEGER,
                     staWanThroughpuTxsc INTEGER,
                     staWanThroughpuRxsa INTEGER,
                     staWanThroughpuTxsa INTEGER
                    }

staWanThroughpuIfc OBJECT-TYPE
                    SYNTAX INTEGER
                    {
                      dsl-ch-1(1),
                      dsl-ch-2(2),
                      dsl-ch-3(3),
                      dsl-ch-4(4),
                      dsl-ch-5(5),
                      dsl-ch-6(6),
                      dsl-ch-7(7),
                      dsl-ch-8(8),
                      ch01(9),
                      ch02(10),
                      ext(11)
                    }
                    MAX-ACCESS read-only
                    STATUS current
                    DESCRIPTION "Ifc"
                    ::= {  staWanThroughpuEntry 1 }

staWanThroughpuRxsc OBJECT-TYPE
                    SYNTAX INTEGER (0..2147483647)
                    MAX-ACCESS read-only
                    STATUS current
                    DESCRIPTION "Rx/s current"
                    ::= {  staWanThroughpuEntry 2 }

staWanThroughpuTxsc OBJECT-TYPE
                    SYNTAX INTEGER (0..2147483647)
                    MAX-ACCESS read-only
                    STATUS current
                    DESCRIPTION "Tx/s current"
                    ::= {  staWanThroughpuEntry 3 }

staWanThroughpuRxsa OBJECT-TYPE
                    SYNTAX INTEGER (0..2147483647)
                    MAX-ACCESS read-only
                    STATUS current
                    DESCRIPTION "Rx/s average"
                    ::= {  staWanThroughpuEntry 4 }

staWanThroughpuTxsa OBJECT-TYPE
                    SYNTAX INTEGER (0..2147483647)
                    MAX-ACCESS read-only
                    STATUS current
                    DESCRIPTION "Tx/s average"
                    ::= {  staWanThroughpuEntry 5 }

staWanDeleteval OBJECT-TYPE
                SYNTAX DisplayString
                MAX-ACCESS read-write
                STATUS current
                DESCRIPTION "Delete-Values"
                ::= {  staWan 9 }

staWanConnectio OBJECT-TYPE
                SYNTAX INTEGER
                MAX-ACCESS read-only
                STATUS current
                DESCRIPTION "Connections"
                ::= {  staWan 10 }

staWanMtuTable OBJECT-TYPE
                     SYNTAX SEQUENCE OF StaWanMtuEntry
                     MAX-ACCESS not-accessible
                     STATUS current
                     DESCRIPTION "MTU"
                     ::= {  staWan 11 }

staWanMtuEntry OBJECT-TYPE
                     SYNTAX StaWanMtuEntry
                     MAX-ACCESS not-accessible
                     STATUS current
                     DESCRIPTION "entry in table"
                     INDEX { staWanMtuPee }
                     ::= {  staWanMtuTable 1 }

StaWanMtuEntry ::= SEQUENCE {
                     staWanMtuPee DisplayString,
                     staWanMtuMtu INTEGER
                    }

staWanMtuPee OBJECT-TYPE
             SYNTAX DisplayString (SIZE(0..16))
             MAX-ACCESS read-write
             STATUS current
             DESCRIPTION "Peer"
             ::= {  staWanMtuEntry 1 }

staWanMtuMtu OBJECT-TYPE
             SYNTAX INTEGER (0..65535)
             MAX-ACCESS read-write
             STATUS current
             DESCRIPTION "MTU"
             ::= {  staWanMtuEntry 2 }

staWanActions OBJECT IDENTIFIER ::= { staWan 20}
staWanActionsActTable OBJECT-TYPE
                      SYNTAX SEQUENCE OF StaWanActionsActEntry
                      MAX-ACCESS not-accessible
                      STATUS current
                      DESCRIPTION "Action-Table"
                      ::= {  staWanActions 1 }

staWanActionsActEntry OBJECT-TYPE
                      SYNTAX StaWanActionsActEntry
                      MAX-ACCESS not-accessible
                      STATUS current
                      DESCRIPTION "entry in table"
                      INDEX { staWanActionsActTim }
                      ::= {  staWanActionsActTable 1 }

StaWanActionsActEntry ::= SEQUENCE {
                      staWanActionsActTim DisplayString,
                      staWanActionsActAct DisplayString,
                      staWanActionsActRes DisplayString
                     }

staWanActionsActTim OBJECT-TYPE
                    SYNTAX DisplayString (SIZE(0..19))
                    MAX-ACCESS read-only
                    STATUS current
                    DESCRIPTION "Time"
                    ::= {  staWanActionsActEntry 1 }

staWanActionsActAct OBJECT-TYPE
                    SYNTAX DisplayString (SIZE(0..255))
                    MAX-ACCESS read-only
                    STATUS current
                    DESCRIPTION "Action"
                    ::= {  staWanActionsActEntry 2 }

staWanActionsActRes OBJECT-TYPE
                    SYNTAX DisplayString (SIZE(0..100))
                    MAX-ACCESS read-only
                    STATUS current
                    DESCRIPTION "Result"
                    ::= {  staWanActionsActEntry 3 }

staWanActionsLocTable OBJECT-TYPE
                      SYNTAX SEQUENCE OF StaWanActionsLocEntry
                      MAX-ACCESS not-accessible
                      STATUS current
                      DESCRIPTION "Lock-Table"
                      ::= {  staWanActions 2 }

staWanActionsLocEntry OBJECT-TYPE
                      SYNTAX StaWanActionsLocEntry
                      MAX-ACCESS not-accessible
                      STATUS current
                      DESCRIPTION "entry in table"
                      INDEX { staWanActionsLocInd }
                      ::= {  staWanActionsLocTable 1 }

StaWanActionsLocEntry ::= SEQUENCE {
                      staWanActionsLocInd INTEGER,
                      staWanActionsLocRem INTEGER
                     }

staWanActionsLocInd OBJECT-TYPE
                    SYNTAX INTEGER (0..65535)
                    MAX-ACCESS read-only
                    STATUS current
                    DESCRIPTION "Index"
                    ::= {  staWanActionsLocEntry 1 }

staWanActionsLocRem OBJECT-TYPE
                    SYNTAX INTEGER (0..2147483647)
                    MAX-ACCESS read-only
                    STATUS current
                    DESCRIPTION "Remaining-Locktime"
                    ::= {  staWanActionsLocEntry 2 }

staLan OBJECT IDENTIFIER ::= { sta 5}
staLanLanh OBJECT-TYPE
           SYNTAX INTEGER
           MAX-ACCESS read-only
           STATUS current
           DESCRIPTION "LAN-Heap-Packets"
           ::= {  staLan 7 }

staLanDele OBJECT-TYPE
           SYNTAX DisplayString
           MAX-ACCESS read-write
           STATUS current
           DESCRIPTION "Delete-Values"
           ::= {  staLan 11 }

staLanLanq OBJECT-TYPE
           SYNTAX Counter32
           MAX-ACCESS read-only
           STATUS current
           DESCRIPTION "LAN-Queue-Mgt-Drop"
           ::= {  staLan 60 }

staLanInteTable OBJECT-TYPE
                SYNTAX SEQUENCE OF StaLanInteEntry
                MAX-ACCESS not-accessible
                STATUS current
                DESCRIPTION "Interfaces"
                ::= {  staLan 51 }

staLanInteEntry OBJECT-TYPE
                SYNTAX StaLanInteEntry
                MAX-ACCESS not-accessible
                STATUS current
                DESCRIPTION "entry in table"
                INDEX { staLanInteIfc }
                ::= {  staLanInteTable 1 }

StaLanInteEntry ::= SEQUENCE {
                staLanInteIfc DisplayString,
                staLanInteQue INTEGER
               }

staLanInteIfc OBJECT-TYPE
              SYNTAX DisplayString (SIZE(0..255))
              MAX-ACCESS read-only
              STATUS current
              DESCRIPTION "Ifc"
              ::= {  staLanInteEntry 1 }

staLanInteQue OBJECT-TYPE
              SYNTAX INTEGER (0..2147483647)
              MAX-ACCESS read-only
              STATUS current
              DESCRIPTION "Queue-Packets"
              ::= {  staLanInteEntry 2 }

staLanByteTable OBJECT-TYPE
                SYNTAX SEQUENCE OF StaLanByteEntry
                MAX-ACCESS not-accessible
                STATUS current
                DESCRIPTION "Byte-Transport"
                ::= {  staLan 52 }

staLanByteEntry OBJECT-TYPE
                SYNTAX StaLanByteEntry
                MAX-ACCESS not-accessible
                STATUS current
                DESCRIPTION "entry in table"
                INDEX { staLanByteIfc }
                ::= {  staLanByteTable 1 }

StaLanByteEntry ::= SEQUENCE {
                staLanByteIfc DisplayString,
                staLanByteTxbyte Counter64,
                staLanByteRxbyte Counter64,
                staLanByteThroug DisplayString,
                staLanByteMaxthr DisplayString,
                staLanByteBytest INTEGER,
                staLanByteBytesm INTEGER
               }

staLanByteIfc OBJECT-TYPE
                 SYNTAX DisplayString (SIZE(0..255))
                 MAX-ACCESS read-only
                 STATUS current
                 DESCRIPTION "Ifc"
                 ::= {  staLanByteEntry 1 }

staLanByteTxbyte OBJECT-TYPE
                 SYNTAX Counter64
                 MAX-ACCESS read-only
                 STATUS current
                 DESCRIPTION "Tx-Bytes"
                 ::= {  staLanByteEntry 2 }

staLanByteRxbyte OBJECT-TYPE
                 SYNTAX Counter64
                 MAX-ACCESS read-only
                 STATUS current
                 DESCRIPTION "Rx-Bytes"
                 ::= {  staLanByteEntry 3 }

staLanByteThroug OBJECT-TYPE
                 SYNTAX DisplayString (SIZE(0..255))
                 MAX-ACCESS read-only
                 STATUS current
                 DESCRIPTION "Throughput"
                 ::= {  staLanByteEntry 4 }

staLanByteMaxthr OBJECT-TYPE
                 SYNTAX DisplayString (SIZE(0..255))
                 MAX-ACCESS read-only
                 STATUS current
                 DESCRIPTION "Max.-Throughput"
                 ::= {  staLanByteEntry 5 }

staLanByteBytest OBJECT-TYPE
                 SYNTAX INTEGER (0..2147483647)
                 MAX-ACCESS read-only
                 STATUS current
                 DESCRIPTION "Bytes-Throughput"
                 ::= {  staLanByteEntry 6 }

staLanByteBytesm OBJECT-TYPE
                 SYNTAX INTEGER (0..2147483647)
                 MAX-ACCESS read-only
                 STATUS current
                 DESCRIPTION "Bytes-Max.-Throughput"
                 ::= {  staLanByteEntry 7 }

staLanPackTable OBJECT-TYPE
                SYNTAX SEQUENCE OF StaLanPackEntry
                MAX-ACCESS not-accessible
                STATUS current
                DESCRIPTION "Packet-Transport"
                ::= {  staLan 53 }

staLanPackEntry OBJECT-TYPE
                SYNTAX StaLanPackEntry
                MAX-ACCESS not-accessible
                STATUS current
                DESCRIPTION "entry in table"
                INDEX { staLanPackIfc }
                ::= {  staLanPackTable 1 }

StaLanPackEntry ::= SEQUENCE {
                staLanPackIfc DisplayString,
                staLanPackRxp Counter32,
                staLanPackTxp Counter32,
                staLanPackRxb Counter32,
                staLanPackRxm Counter32,
                staLanPackRxu Counter32,
                staLanPackTxb Counter32,
                staLanPackTxm Counter32,
                staLanPackTxu Counter32
               }

staLanPackIfc OBJECT-TYPE
              SYNTAX DisplayString (SIZE(0..255))
              MAX-ACCESS read-only
              STATUS current
              DESCRIPTION "Ifc"
              ::= {  staLanPackEntry 1 }

staLanPackRxp OBJECT-TYPE
              SYNTAX Counter32
              MAX-ACCESS read-only
              STATUS current
              DESCRIPTION "Rx-Packets"
              ::= {  staLanPackEntry 2 }

staLanPackTxp OBJECT-TYPE
              SYNTAX Counter32
              MAX-ACCESS read-only
              STATUS current
              DESCRIPTION "Tx-Packets"
              ::= {  staLanPackEntry 3 }

staLanPackRxb OBJECT-TYPE
              SYNTAX Counter32
              MAX-ACCESS read-only
              STATUS current
              DESCRIPTION "Rx-Broadcasts"
              ::= {  staLanPackEntry 4 }

staLanPackRxm OBJECT-TYPE
              SYNTAX Counter32
              MAX-ACCESS read-only
              STATUS current
              DESCRIPTION "Rx-Multicasts"
              ::= {  staLanPackEntry 5 }

staLanPackRxu OBJECT-TYPE
              SYNTAX Counter32
              MAX-ACCESS read-only
              STATUS current
              DESCRIPTION "Rx-Unicasts"
              ::= {  staLanPackEntry 6 }

staLanPackTxb OBJECT-TYPE
              SYNTAX Counter32
              MAX-ACCESS read-only
              STATUS current
              DESCRIPTION "Tx-Broadcasts"
              ::= {  staLanPackEntry 7 }

staLanPackTxm OBJECT-TYPE
              SYNTAX Counter32
              MAX-ACCESS read-only
              STATUS current
              DESCRIPTION "Tx-Multicasts"
              ::= {  staLanPackEntry 8 }

staLanPackTxu OBJECT-TYPE
              SYNTAX Counter32
              MAX-ACCESS read-only
              STATUS current
              DESCRIPTION "Tx-Unicasts"
              ::= {  staLanPackEntry 9 }

staLanErroTable OBJECT-TYPE
                SYNTAX SEQUENCE OF StaLanErroEntry
                MAX-ACCESS not-accessible
                STATUS current
                DESCRIPTION "Errors"
                ::= {  staLan 54 }

staLanErroEntry OBJECT-TYPE
                SYNTAX StaLanErroEntry
                MAX-ACCESS not-accessible
                STATUS current
                DESCRIPTION "entry in table"
                INDEX { staLanErroIfc }
                ::= {  staLanErroTable 1 }

StaLanErroEntry ::= SEQUENCE {
                staLanErroIfc DisplayString,
                staLanErroRxerro Counter32,
                staLanErroTxerro Counter32,
                staLanErroStacke Counter32,
                staLanErroNicerr Counter32,
                staLanErroQueuee Counter32,
                staLanErroRxcrce Counter32,
                staLanErroCollis Counter32,
                staLanErroSingle Counter32,
                staLanErroMultip Counter32,
                staLanErroLateco Counter32,
                staLanErroExcess Counter32,
                staLanErroRxalig Counter32,
                staLanErroRxtoos Counter32,
                staLanErroRxtool Counter32,
                staLanErroTxcarr Counter32,
                staLanErroTxdefe Counter32
               }

staLanErroIfc OBJECT-TYPE
                 SYNTAX DisplayString (SIZE(0..255))
                 MAX-ACCESS read-only
                 STATUS current
                 DESCRIPTION "Ifc"
                 ::= {  staLanErroEntry 1 }

staLanErroRxerro OBJECT-TYPE
                 SYNTAX Counter32
                 MAX-ACCESS read-only
                 STATUS current
                 DESCRIPTION "Rx-Errors"
                 ::= {  staLanErroEntry 2 }

staLanErroTxerro OBJECT-TYPE
                 SYNTAX Counter32
                 MAX-ACCESS read-only
                 STATUS current
                 DESCRIPTION "Tx-Errors"
                 ::= {  staLanErroEntry 3 }

staLanErroStacke OBJECT-TYPE
                 SYNTAX Counter32
                 MAX-ACCESS read-only
                 STATUS current
                 DESCRIPTION "Stack-Errors"
                 ::= {  staLanErroEntry 4 }

staLanErroNicerr OBJECT-TYPE
                 SYNTAX Counter32
                 MAX-ACCESS read-only
                 STATUS current
                 DESCRIPTION "NIC-Errors"
                 ::= {  staLanErroEntry 5 }

staLanErroQueuee OBJECT-TYPE
                 SYNTAX Counter32
                 MAX-ACCESS read-only
                 STATUS current
                 DESCRIPTION "Queue-Errors"
                 ::= {  staLanErroEntry 6 }

staLanErroRxcrce OBJECT-TYPE
                 SYNTAX Counter32
                 MAX-ACCESS read-only
                 STATUS current
                 DESCRIPTION "Rx-CRC-Errors"
                 ::= {  staLanErroEntry 7 }

staLanErroCollis OBJECT-TYPE
                 SYNTAX Counter32
                 MAX-ACCESS read-only
                 STATUS current
                 DESCRIPTION "Collisions"
                 ::= {  staLanErroEntry 8 }

staLanErroSingle OBJECT-TYPE
                 SYNTAX Counter32
                 MAX-ACCESS read-only
                 STATUS current
                 DESCRIPTION "Single-Collisions"
                 ::= {  staLanErroEntry 9 }

staLanErroMultip OBJECT-TYPE
                 SYNTAX Counter32
                 MAX-ACCESS read-only
                 STATUS current
                 DESCRIPTION "Multiple-Collisions"
                 ::= {  staLanErroEntry 10 }

staLanErroLateco OBJECT-TYPE
                 SYNTAX Counter32
                 MAX-ACCESS read-only
                 STATUS current
                 DESCRIPTION "Late-Collisions"
                 ::= {  staLanErroEntry 11 }

staLanErroExcess OBJECT-TYPE
                 SYNTAX Counter32
                 MAX-ACCESS read-only
                 STATUS current
                 DESCRIPTION "Excessive-Collisions"
                 ::= {  staLanErroEntry 12 }

staLanErroRxalig OBJECT-TYPE
                 SYNTAX Counter32
                 MAX-ACCESS read-only
                 STATUS current
                 DESCRIPTION "Rx-Align-Errors"
                 ::= {  staLanErroEntry 13 }

staLanErroRxtoos OBJECT-TYPE
                 SYNTAX Counter32
                 MAX-ACCESS read-only
                 STATUS current
                 DESCRIPTION "Rx-Too-Short"
                 ::= {  staLanErroEntry 14 }

staLanErroRxtool OBJECT-TYPE
                 SYNTAX Counter32
                 MAX-ACCESS read-only
                 STATUS current
                 DESCRIPTION "Rx-Too-Long"
                 ::= {  staLanErroEntry 15 }

staLanErroTxcarr OBJECT-TYPE
                 SYNTAX Counter32
                 MAX-ACCESS read-only
                 STATUS current
                 DESCRIPTION "Tx-Carrier"
                 ::= {  staLanErroEntry 16 }

staLanErroTxdefe OBJECT-TYPE
                 SYNTAX Counter32
                 MAX-ACCESS read-only
                 STATUS current
                 DESCRIPTION "Tx-Deferred"
                 ::= {  staLanErroEntry 17 }

staPpp OBJECT IDENTIFIER ::= { sta 6}
staPppPppTable OBJECT-TYPE
               SYNTAX SEQUENCE OF StaPppPppEntry
               MAX-ACCESS not-accessible
               STATUS current
               DESCRIPTION "PPP-Phases"
               ::= {  staPpp 1 }

staPppPppEntry OBJECT-TYPE
               SYNTAX StaPppPppEntry
               MAX-ACCESS not-accessible
               STATUS current
               DESCRIPTION "entry in table"
               INDEX { staPppPppIfc }
               ::= {  staPppPppTable 1 }

StaPppPppEntry ::= SEQUENCE {
               staPppPppIfc INTEGER,
               staPppPppPha INTEGER,
               staPppPppLcp INTEGER,
               staPppPppIpc INTEGER,
               staPppPppCcp INTEGER,
               staPppPppBac INTEGER
              }

staPppPppIfc OBJECT-TYPE
             SYNTAX INTEGER
             {
               dsl-ch-1(1),
               dsl-ch-2(2),
               dsl-ch-3(3),
               dsl-ch-4(4),
               dsl-ch-5(5),
               dsl-ch-6(6),
               dsl-ch-7(7),
               dsl-ch-8(8),
               ch01(9),
               ch02(10),
               ext(11)
             }
             MAX-ACCESS read-only
             STATUS current
             DESCRIPTION "Ifc"
             ::= {  staPppPppEntry 1 }

staPppPppPha OBJECT-TYPE
             SYNTAX INTEGER
             {
               dead(1),
               establish(2),
               terminate(3),
               authenticate(4),
               callback(5),
               network(6)
             }
             MAX-ACCESS read-only
             STATUS current
             DESCRIPTION "Phase to"
             ::= {  staPppPppEntry 2 }

staPppPppLcp OBJECT-TYPE
             SYNTAX INTEGER
             {
               initial(1),
               startng(2),
               closed(3),
               stopped(4),
               closing(5),
               stoppng(6),
               reqsent(7),
               ackrcvd(8),
               acksent(9),
               opened(10)
             }
             MAX-ACCESS read-only
             STATUS current
             DESCRIPTION "LCP"
             ::= {  staPppPppEntry 3 }

staPppPppIpc OBJECT-TYPE
             SYNTAX INTEGER
             {
               initial(1),
               startng(2),
               closed(3),
               stopped(4),
               closing(5),
               stoppng(6),
               reqsent(7),
               ackrcvd(8),
               acksent(9),
               opened(10)
             }
             MAX-ACCESS read-only
             STATUS current
             DESCRIPTION "IPCP"
             ::= {  staPppPppEntry 4 }

staPppPppCcp OBJECT-TYPE
             SYNTAX INTEGER
             {
               initial(1),
               startng(2),
               closed(3),
               stopped(4),
               closing(5),
               stoppng(6),
               reqsent(7),
               ackrcvd(8),
               acksent(9),
               opened(10)
             }
             MAX-ACCESS read-only
             STATUS current
             DESCRIPTION "CCP"
             ::= {  staPppPppEntry 6 }

staPppPppBac OBJECT-TYPE
             SYNTAX INTEGER
             {
               initial(1),
               startng(2),
               closed(3),
               stopped(4),
               closing(5),
               stoppng(6),
               reqsent(7),
               ackrcvd(8),
               acksent(9),
               opened(10)
             }
             MAX-ACCESS read-only
             STATUS current
             DESCRIPTION "BACP"
             ::= {  staPppPppEntry 7 }

staPppLcp OBJECT IDENTIFIER ::= { staPpp 2}
staPppLcpRxerrors OBJECT-TYPE
                      SYNTAX Counter32
                      MAX-ACCESS read-only
                      STATUS current
                      DESCRIPTION "Rx-Errors"
                      ::= {  staPppLcp 1 }

staPppLcpRxdiscarded OBJECT-TYPE
                      SYNTAX Counter32
                      MAX-ACCESS read-only
                      STATUS current
                      DESCRIPTION "Rx-Discarded"
                      ::= {  staPppLcp 2 }

staPppLcpRxconfigrequ OBJECT-TYPE
                      SYNTAX Counter32
                      MAX-ACCESS read-only
                      STATUS current
                      DESCRIPTION "Rx-Config-Request"
                      ::= {  staPppLcp 3 }

staPppLcpRxconfigack OBJECT-TYPE
                      SYNTAX Counter32
                      MAX-ACCESS read-only
                      STATUS current
                      DESCRIPTION "Rx-Config-Ack."
                      ::= {  staPppLcp 4 }

staPppLcpRxconfignak OBJECT-TYPE
                      SYNTAX Counter32
                      MAX-ACCESS read-only
                      STATUS current
                      DESCRIPTION "Rx-Config-Nak."
                      ::= {  staPppLcp 5 }

staPppLcpRxconfigreje OBJECT-TYPE
                      SYNTAX Counter32
                      MAX-ACCESS read-only
                      STATUS current
                      DESCRIPTION "Rx-Config-Reject"
                      ::= {  staPppLcp 6 }

staPppLcpRxterminater OBJECT-TYPE
                      SYNTAX Counter32
                      MAX-ACCESS read-only
                      STATUS current
                      DESCRIPTION "Rx-Terminate-Request"
                      ::= {  staPppLcp 7 }

staPppLcpRxterminatea OBJECT-TYPE
                      SYNTAX Counter32
                      MAX-ACCESS read-only
                      STATUS current
                      DESCRIPTION "Rx-Terminate-Ack."
                      ::= {  staPppLcp 8 }

staPppLcpRxcodereject OBJECT-TYPE
                      SYNTAX Counter32
                      MAX-ACCESS read-only
                      STATUS current
                      DESCRIPTION "Rx-Code-Reject"
                      ::= {  staPppLcp 9 }

staPppLcpRxprotocolre OBJECT-TYPE
                      SYNTAX Counter32
                      MAX-ACCESS read-only
                      STATUS current
                      DESCRIPTION "Rx-Protocol-Reject"
                      ::= {  staPppLcp 10 }

staPppLcpRxechoreques OBJECT-TYPE
                      SYNTAX Counter32
                      MAX-ACCESS read-only
                      STATUS current
                      DESCRIPTION "Rx-Echo-Request"
                      ::= {  staPppLcp 11 }

staPppLcpRxechoreply OBJECT-TYPE
                      SYNTAX Counter32
                      MAX-ACCESS read-only
                      STATUS current
                      DESCRIPTION "Rx-Echo-Reply"
                      ::= {  staPppLcp 12 }

staPppLcpRxdiscardreq OBJECT-TYPE
                      SYNTAX Counter32
                      MAX-ACCESS read-only
                      STATUS current
                      DESCRIPTION "Rx-Discard-Request"
                      ::= {  staPppLcp 13 }

staPppLcpTxconfigrequ OBJECT-TYPE
                      SYNTAX Counter32
                      MAX-ACCESS read-only
                      STATUS current
                      DESCRIPTION "Tx-Config-Request"
                      ::= {  staPppLcp 14 }

staPppLcpTxconfigack OBJECT-TYPE
                      SYNTAX Counter32
                      MAX-ACCESS read-only
                      STATUS current
                      DESCRIPTION "Tx-Config-Ack."
                      ::= {  staPppLcp 15 }

staPppLcpTxconfignak OBJECT-TYPE
                      SYNTAX Counter32
                      MAX-ACCESS read-only
                      STATUS current
                      DESCRIPTION "Tx-Config-Nak."
                      ::= {  staPppLcp 16 }

staPppLcpTxconfigreje OBJECT-TYPE
                      SYNTAX Counter32
                      MAX-ACCESS read-only
                      STATUS current
                      DESCRIPTION "Tx-Config-Reject"
                      ::= {  staPppLcp 17 }

staPppLcpTxterminater OBJECT-TYPE
                      SYNTAX Counter32
                      MAX-ACCESS read-only
                      STATUS current
                      DESCRIPTION "Tx-Terminate-Request"
                      ::= {  staPppLcp 18 }

staPppLcpTxterminatea OBJECT-TYPE
                      SYNTAX Counter32
                      MAX-ACCESS read-only
                      STATUS current
                      DESCRIPTION "Tx-Terminate-Ack."
                      ::= {  staPppLcp 19 }

staPppLcpTxcodereject OBJECT-TYPE
                      SYNTAX Counter32
                      MAX-ACCESS read-only
                      STATUS current
                      DESCRIPTION "Tx-Code-Reject"
                      ::= {  staPppLcp 20 }

staPppLcpTxprotocolre OBJECT-TYPE
                      SYNTAX Counter32
                      MAX-ACCESS read-only
                      STATUS current
                      DESCRIPTION "Tx-Protocol-Reject"
                      ::= {  staPppLcp 21 }

staPppLcpTxechoreques OBJECT-TYPE
                      SYNTAX Counter32
                      MAX-ACCESS read-only
                      STATUS current
                      DESCRIPTION "Tx-Echo-Request"
                      ::= {  staPppLcp 22 }

staPppLcpTxechoreply OBJECT-TYPE
                      SYNTAX Counter32
                      MAX-ACCESS read-only
                      STATUS current
                      DESCRIPTION "Tx-Echo-Reply"
                      ::= {  staPppLcp 23 }

staPppLcpTxdiscardreq OBJECT-TYPE
                      SYNTAX Counter32
                      MAX-ACCESS read-only
                      STATUS current
                      DESCRIPTION "Tx-Discard-Request"
                      ::= {  staPppLcp 24 }

staPppLcpDeletevalues OBJECT-TYPE
                      SYNTAX DisplayString
                      MAX-ACCESS read-write
                      STATUS current
                      DESCRIPTION "Delete-Values"
                      ::= {  staPppLcp 25 }

staPppPap OBJECT IDENTIFIER ::= { staPpp 3}
staPppPapRxdis OBJECT-TYPE
               SYNTAX Counter32
               MAX-ACCESS read-only
               STATUS current
               DESCRIPTION "Rx-Discarded"
               ::= {  staPppPap 1 }

staPppPapRxreq OBJECT-TYPE
               SYNTAX Counter32
               MAX-ACCESS read-only
               STATUS current
               DESCRIPTION "Rx-Request"
               ::= {  staPppPap 2 }

staPppPapRxsuc OBJECT-TYPE
               SYNTAX Counter32
               MAX-ACCESS read-only
               STATUS current
               DESCRIPTION "Rx-Success"
               ::= {  staPppPap 3 }

staPppPapRxfai OBJECT-TYPE
               SYNTAX Counter32
               MAX-ACCESS read-only
               STATUS current
               DESCRIPTION "Rx-Failure"
               ::= {  staPppPap 4 }

staPppPapTxret OBJECT-TYPE
               SYNTAX Counter32
               MAX-ACCESS read-only
               STATUS current
               DESCRIPTION "Tx-Retry"
               ::= {  staPppPap 5 }

staPppPapTxreq OBJECT-TYPE
               SYNTAX Counter32
               MAX-ACCESS read-only
               STATUS current
               DESCRIPTION "Tx-Request"
               ::= {  staPppPap 6 }

staPppPapTxsuc OBJECT-TYPE
               SYNTAX Counter32
               MAX-ACCESS read-only
               STATUS current
               DESCRIPTION "Tx-Success"
               ::= {  staPppPap 7 }

staPppPapTxfai OBJECT-TYPE
               SYNTAX Counter32
               MAX-ACCESS read-only
               STATUS current
               DESCRIPTION "Tx-Failure"
               ::= {  staPppPap 8 }

staPppPapDelet OBJECT-TYPE
               SYNTAX DisplayString
               MAX-ACCESS read-write
               STATUS current
               DESCRIPTION "Delete-Values"
               ::= {  staPppPap 9 }

staPppCha OBJECT IDENTIFIER ::= { staPpp 4}
staPppChaRxdis OBJECT-TYPE
               SYNTAX Counter32
               MAX-ACCESS read-only
               STATUS current
               DESCRIPTION "Rx-Discarded"
               ::= {  staPppCha 1 }

staPppChaRxcha OBJECT-TYPE
               SYNTAX Counter32
               MAX-ACCESS read-only
               STATUS current
               DESCRIPTION "Rx-Challenge"
               ::= {  staPppCha 2 }

staPppChaRxres OBJECT-TYPE
               SYNTAX Counter32
               MAX-ACCESS read-only
               STATUS current
               DESCRIPTION "Rx-Response"
               ::= {  staPppCha 3 }

staPppChaRxsuc OBJECT-TYPE
               SYNTAX Counter32
               MAX-ACCESS read-only
               STATUS current
               DESCRIPTION "Rx-Success"
               ::= {  staPppCha 4 }

staPppChaRxfai OBJECT-TYPE
               SYNTAX Counter32
               MAX-ACCESS read-only
               STATUS current
               DESCRIPTION "Rx-Failure"
               ::= {  staPppCha 5 }

staPppChaTxret OBJECT-TYPE
               SYNTAX Counter32
               MAX-ACCESS read-only
               STATUS current
               DESCRIPTION "Tx-Retry"
               ::= {  staPppCha 6 }

staPppChaTxcha OBJECT-TYPE
               SYNTAX Counter32
               MAX-ACCESS read-only
               STATUS current
               DESCRIPTION "Tx-Challenge"
               ::= {  staPppCha 7 }

staPppChaTxres OBJECT-TYPE
               SYNTAX Counter32
               MAX-ACCESS read-only
               STATUS current
               DESCRIPTION "Tx-Response"
               ::= {  staPppCha 8 }

staPppChaTxsuc OBJECT-TYPE
               SYNTAX Counter32
               MAX-ACCESS read-only
               STATUS current
               DESCRIPTION "Tx-Success"
               ::= {  staPppCha 9 }

staPppChaTxfai OBJECT-TYPE
               SYNTAX Counter32
               MAX-ACCESS read-only
               STATUS current
               DESCRIPTION "Tx-Failure"
               ::= {  staPppCha 10 }

staPppChaDelet OBJECT-TYPE
               SYNTAX DisplayString
               MAX-ACCESS read-write
               STATUS current
               DESCRIPTION "Delete-Values"
               ::= {  staPppCha 11 }

staPppCbc OBJECT IDENTIFIER ::= { staPpp 7}
staPppCbcRxdis OBJECT-TYPE
               SYNTAX Counter32
               MAX-ACCESS read-only
               STATUS current
               DESCRIPTION "Rx-Discarded"
               ::= {  staPppCbc 1 }

staPppCbcRxreq OBJECT-TYPE
               SYNTAX Counter32
               MAX-ACCESS read-only
               STATUS current
               DESCRIPTION "Rx-Request"
               ::= {  staPppCbc 2 }

staPppCbcRxres OBJECT-TYPE
               SYNTAX Counter32
               MAX-ACCESS read-only
               STATUS current
               DESCRIPTION "Rx-Response"
               ::= {  staPppCbc 3 }

staPppCbcRxack OBJECT-TYPE
               SYNTAX Counter32
               MAX-ACCESS read-only
               STATUS current
               DESCRIPTION "Rx-Acknowledge"
               ::= {  staPppCbc 4 }

staPppCbcTxreq OBJECT-TYPE
               SYNTAX Counter32
               MAX-ACCESS read-only
               STATUS current
               DESCRIPTION "Tx-Request"
               ::= {  staPppCbc 5 }

staPppCbcTxres OBJECT-TYPE
               SYNTAX Counter32
               MAX-ACCESS read-only
               STATUS current
               DESCRIPTION "Tx-Response"
               ::= {  staPppCbc 6 }

staPppCbcTxack OBJECT-TYPE
               SYNTAX Counter32
               MAX-ACCESS read-only
               STATUS current
               DESCRIPTION "Tx-Acknowledge"
               ::= {  staPppCbc 7 }

staPppCbcDelet OBJECT-TYPE
               SYNTAX DisplayString
               MAX-ACCESS read-write
               STATUS current
               DESCRIPTION "Delete-Values"
               ::= {  staPppCbc 8 }

staPppIpc OBJECT IDENTIFIER ::= { staPpp 6}
staPppIpcRxdiscarded OBJECT-TYPE
                      SYNTAX Counter32
                      MAX-ACCESS read-only
                      STATUS current
                      DESCRIPTION "Rx-Discarded"
                      ::= {  staPppIpc 1 }

staPppIpcRxconfigrequ OBJECT-TYPE
                      SYNTAX Counter32
                      MAX-ACCESS read-only
                      STATUS current
                      DESCRIPTION "Rx-Config-Request"
                      ::= {  staPppIpc 2 }

staPppIpcRxconfigack OBJECT-TYPE
                      SYNTAX Counter32
                      MAX-ACCESS read-only
                      STATUS current
                      DESCRIPTION "Rx-Config-Ack."
                      ::= {  staPppIpc 3 }

staPppIpcRxconfignak OBJECT-TYPE
                      SYNTAX Counter32
                      MAX-ACCESS read-only
                      STATUS current
                      DESCRIPTION "Rx-Config-Nak."
                      ::= {  staPppIpc 4 }

staPppIpcRxconfigreje OBJECT-TYPE
                      SYNTAX Counter32
                      MAX-ACCESS read-only
                      STATUS current
                      DESCRIPTION "Rx-Config-Reject"
                      ::= {  staPppIpc 5 }

staPppIpcRxterminater OBJECT-TYPE
                      SYNTAX Counter32
                      MAX-ACCESS read-only
                      STATUS current
                      DESCRIPTION "Rx-Terminate-Request"
                      ::= {  staPppIpc 6 }

staPppIpcRxterminatea OBJECT-TYPE
                      SYNTAX Counter32
                      MAX-ACCESS read-only
                      STATUS current
                      DESCRIPTION "Rx-Terminate-Ack."
                      ::= {  staPppIpc 7 }

staPppIpcRxcodereject OBJECT-TYPE
                      SYNTAX Counter32
                      MAX-ACCESS read-only
                      STATUS current
                      DESCRIPTION "Rx-Code-Reject"
                      ::= {  staPppIpc 8 }

staPppIpcTxconfigrequ OBJECT-TYPE
                      SYNTAX Counter32
                      MAX-ACCESS read-only
                      STATUS current
                      DESCRIPTION "Tx-Config-Request"
                      ::= {  staPppIpc 9 }

staPppIpcTxconfigack OBJECT-TYPE
                      SYNTAX Counter32
                      MAX-ACCESS read-only
                      STATUS current
                      DESCRIPTION "Tx-Config-Ack."
                      ::= {  staPppIpc 10 }

staPppIpcTxconfignak OBJECT-TYPE
                      SYNTAX Counter32
                      MAX-ACCESS read-only
                      STATUS current
                      DESCRIPTION "Tx-Config-Nak."
                      ::= {  staPppIpc 11 }

staPppIpcTxconfigreje OBJECT-TYPE
                      SYNTAX Counter32
                      MAX-ACCESS read-only
                      STATUS current
                      DESCRIPTION "Tx-Config-Reject"
                      ::= {  staPppIpc 12 }

staPppIpcTxterminater OBJECT-TYPE
                      SYNTAX Counter32
                      MAX-ACCESS read-only
                      STATUS current
                      DESCRIPTION "Tx-Terminate-Request"
                      ::= {  staPppIpc 13 }

staPppIpcTxterminatea OBJECT-TYPE
                      SYNTAX Counter32
                      MAX-ACCESS read-only
                      STATUS current
                      DESCRIPTION "Tx-Terminate-Ack."
                      ::= {  staPppIpc 14 }

staPppIpcTxcodereject OBJECT-TYPE
                      SYNTAX Counter32
                      MAX-ACCESS read-only
                      STATUS current
                      DESCRIPTION "Tx-Code-Reject"
                      ::= {  staPppIpc 15 }

staPppIpcDeletevalues OBJECT-TYPE
                      SYNTAX DisplayString
                      MAX-ACCESS read-write
                      STATUS current
                      DESCRIPTION "Delete-Values"
                      ::= {  staPppIpc 16 }

staPppCcp OBJECT IDENTIFIER ::= { staPpp 10}
staPppCcpRxdiscarded OBJECT-TYPE
                      SYNTAX Counter32
                      MAX-ACCESS read-only
                      STATUS current
                      DESCRIPTION "Rx-Discarded"
                      ::= {  staPppCcp 1 }

staPppCcpRxconfigrequ OBJECT-TYPE
                      SYNTAX Counter32
                      MAX-ACCESS read-only
                      STATUS current
                      DESCRIPTION "Rx-Config-Request"
                      ::= {  staPppCcp 2 }

staPppCcpRxconfigack OBJECT-TYPE
                      SYNTAX Counter32
                      MAX-ACCESS read-only
                      STATUS current
                      DESCRIPTION "Rx-Config-Ack."
                      ::= {  staPppCcp 3 }

staPppCcpRxconfignak OBJECT-TYPE
                      SYNTAX Counter32
                      MAX-ACCESS read-only
                      STATUS current
                      DESCRIPTION "Rx-Config-Nak."
                      ::= {  staPppCcp 4 }

staPppCcpRxconfigreje OBJECT-TYPE
                      SYNTAX Counter32
                      MAX-ACCESS read-only
                      STATUS current
                      DESCRIPTION "Rx-Config-Reject"
                      ::= {  staPppCcp 5 }

staPppCcpRxterminater OBJECT-TYPE
                      SYNTAX Counter32
                      MAX-ACCESS read-only
                      STATUS current
                      DESCRIPTION "Rx-Terminate-Request"
                      ::= {  staPppCcp 6 }

staPppCcpRxterminatea OBJECT-TYPE
                      SYNTAX Counter32
                      MAX-ACCESS read-only
                      STATUS current
                      DESCRIPTION "Rx-Terminate-Ack."
                      ::= {  staPppCcp 7 }

staPppCcpRxcodereject OBJECT-TYPE
                      SYNTAX Counter32
                      MAX-ACCESS read-only
                      STATUS current
                      DESCRIPTION "Rx-Code-Reject"
                      ::= {  staPppCcp 8 }

staPppCcpRxresetreque OBJECT-TYPE
                      SYNTAX Counter32
                      MAX-ACCESS read-only
                      STATUS current
                      DESCRIPTION "Rx-Reset-Request"
                      ::= {  staPppCcp 9 }

staPppCcpRxresetack OBJECT-TYPE
                      SYNTAX Counter32
                      MAX-ACCESS read-only
                      STATUS current
                      DESCRIPTION "Rx-Reset-Ack"
                      ::= {  staPppCcp 10 }

staPppCcpTxconfigrequ OBJECT-TYPE
                      SYNTAX Counter32
                      MAX-ACCESS read-only
                      STATUS current
                      DESCRIPTION "Tx-Config-Request"
                      ::= {  staPppCcp 11 }

staPppCcpTxconfigack OBJECT-TYPE
                      SYNTAX Counter32
                      MAX-ACCESS read-only
                      STATUS current
                      DESCRIPTION "Tx-Config-Ack."
                      ::= {  staPppCcp 12 }

staPppCcpTxconfignak OBJECT-TYPE
                      SYNTAX Counter32
                      MAX-ACCESS read-only
                      STATUS current
                      DESCRIPTION "Tx-Config-Nak."
                      ::= {  staPppCcp 13 }

staPppCcpTxconfigreje OBJECT-TYPE
                      SYNTAX Counter32
                      MAX-ACCESS read-only
                      STATUS current
                      DESCRIPTION "Tx-Config-Reject"
                      ::= {  staPppCcp 14 }

staPppCcpTxterminater OBJECT-TYPE
                      SYNTAX Counter32
                      MAX-ACCESS read-only
                      STATUS current
                      DESCRIPTION "Tx-Terminate-Request"
                      ::= {  staPppCcp 15 }

staPppCcpTxterminatea OBJECT-TYPE
                      SYNTAX Counter32
                      MAX-ACCESS read-only
                      STATUS current
                      DESCRIPTION "Tx-Terminate-Ack."
                      ::= {  staPppCcp 16 }

staPppCcpTxcodereject OBJECT-TYPE
                      SYNTAX Counter32
                      MAX-ACCESS read-only
                      STATUS current
                      DESCRIPTION "Tx-Code-Reject"
                      ::= {  staPppCcp 17 }

staPppCcpTxresetreque OBJECT-TYPE
                      SYNTAX Counter32
                      MAX-ACCESS read-only
                      STATUS current
                      DESCRIPTION "Tx-Reset-Request"
                      ::= {  staPppCcp 19 }

staPppCcpTxresetack OBJECT-TYPE
                      SYNTAX Counter32
                      MAX-ACCESS read-only
                      STATUS current
                      DESCRIPTION "Tx-Reset-Ack"
                      ::= {  staPppCcp 20 }

staPppCcpCompressione OBJECT-TYPE
                      SYNTAX Counter32
                      MAX-ACCESS read-only
                      STATUS current
                      DESCRIPTION "Compression-Errors"
                      ::= {  staPppCcp 22 }

staPppCcpDeletevalues OBJECT-TYPE
                      SYNTAX DisplayString
                      MAX-ACCESS read-write
                      STATUS current
                      DESCRIPTION "Delete-Values"
                      ::= {  staPppCcp 21 }

staPppMl OBJECT IDENTIFIER ::= { staPpp 11}
staPppMlBundlec OBJECT-TYPE
                SYNTAX INTEGER
                MAX-ACCESS read-only
                STATUS current
                DESCRIPTION "Bundle-Connections"
                ::= {  staPppMl 1 }

staPppMlRxseqlo OBJECT-TYPE
                SYNTAX Counter32
                MAX-ACCESS read-only
                STATUS current
                DESCRIPTION "Rx-Seq-Lost"
                ::= {  staPppMl 2 }

staPppMlRxseqre OBJECT-TYPE
                SYNTAX Counter32
                MAX-ACCESS read-only
                STATUS current
                DESCRIPTION "Rx-Seq-Repeat"
                ::= {  staPppMl 3 }

staPppMlRxmrrue OBJECT-TYPE
                SYNTAX Counter32
                MAX-ACCESS read-only
                STATUS current
                DESCRIPTION "Rx-Mrru-Exceeded"
                ::= {  staPppMl 4 }

staPppMlRxheade OBJECT-TYPE
                SYNTAX Counter32
                MAX-ACCESS read-only
                STATUS current
                DESCRIPTION "Rx-Header-Error"
                ::= {  staPppMl 5 }

staPppMlRxdisca OBJECT-TYPE
                SYNTAX Counter32
                MAX-ACCESS read-only
                STATUS current
                DESCRIPTION "Rx-Discarded"
                ::= {  staPppMl 6 }

staPppMlRxfrags OBJECT-TYPE
                SYNTAX Counter32
                MAX-ACCESS read-only
                STATUS current
                DESCRIPTION "Rx-Frag-Start"
                ::= {  staPppMl 7 }

staPppMlRxfragm OBJECT-TYPE
                SYNTAX Counter32
                MAX-ACCESS read-only
                STATUS current
                DESCRIPTION "Rx-Frag-Mid"
                ::= {  staPppMl 8 }

staPppMlRxfrage OBJECT-TYPE
                SYNTAX Counter32
                MAX-ACCESS read-only
                STATUS current
                DESCRIPTION "Rx-Frag-End"
                ::= {  staPppMl 9 }

staPppMlRxnotfr OBJECT-TYPE
                SYNTAX Counter32
                MAX-ACCESS read-only
                STATUS current
                DESCRIPTION "Rx-not-Fragmented"
                ::= {  staPppMl 10 }

staPppMlDeletev OBJECT-TYPE
                SYNTAX DisplayString
                MAX-ACCESS read-write
                STATUS current
                DESCRIPTION "Delete-Values"
                ::= {  staPppMl 11 }

staPppBac OBJECT IDENTIFIER ::= { staPpp 12}
staPppBacRxerrors OBJECT-TYPE
                       SYNTAX Counter32
                       MAX-ACCESS read-only
                       STATUS current
                       DESCRIPTION "Rx-Errors"
                       ::= {  staPppBac 1 }

staPppBacRxdiscarded OBJECT-TYPE
                       SYNTAX Counter32
                       MAX-ACCESS read-only
                       STATUS current
                       DESCRIPTION "Rx-Discarded"
                       ::= {  staPppBac 2 }

staPppBacRxcallrequest OBJECT-TYPE
                       SYNTAX Counter32
                       MAX-ACCESS read-only
                       STATUS current
                       DESCRIPTION "Rx-Call-Request"
                       ::= {  staPppBac 3 }

staPppBacRxcallrespons OBJECT-TYPE
                       SYNTAX Counter32
                       MAX-ACCESS read-only
                       STATUS current
                       DESCRIPTION "Rx-Call-Response"
                       ::= {  staPppBac 4 }

staPppBacRxcallbackreq OBJECT-TYPE
                       SYNTAX Counter32
                       MAX-ACCESS read-only
                       STATUS current
                       DESCRIPTION "Rx-Callback-Request"
                       ::= {  staPppBac 5 }

staPppBacRxcallbackres OBJECT-TYPE
                       SYNTAX Counter32
                       MAX-ACCESS read-only
                       STATUS current
                       DESCRIPTION "Rx-Callback-Response"
                       ::= {  staPppBac 6 }

staPppBacRxlinkdropreq OBJECT-TYPE
                       SYNTAX Counter32
                       MAX-ACCESS read-only
                       STATUS current
                       DESCRIPTION "Rx-Link-Drop-Request"
                       ::= {  staPppBac 7 }

staPppBacRxlinkdropres OBJECT-TYPE
                       SYNTAX Counter32
                       MAX-ACCESS read-only
                       STATUS current
                       DESCRIPTION "Rx-Link-Drop-Response"
                       ::= {  staPppBac 8 }

staPppBacRxstatusindic OBJECT-TYPE
                       SYNTAX Counter32
                       MAX-ACCESS read-only
                       STATUS current
                       DESCRIPTION "Rx-Status-Indication"
                       ::= {  staPppBac 9 }

staPppBacRxstatusrespo OBJECT-TYPE
                       SYNTAX Counter32
                       MAX-ACCESS read-only
                       STATUS current
                       DESCRIPTION "Rx-Status-Response"
                       ::= {  staPppBac 10 }

staPppBacTxcallrequest OBJECT-TYPE
                       SYNTAX Counter32
                       MAX-ACCESS read-only
                       STATUS current
                       DESCRIPTION "Tx-Call-Request"
                       ::= {  staPppBac 11 }

staPppBacTxcallrespons OBJECT-TYPE
                       SYNTAX Counter32
                       MAX-ACCESS read-only
                       STATUS current
                       DESCRIPTION "Tx-Call-Response"
                       ::= {  staPppBac 12 }

staPppBacTxcallbackreq OBJECT-TYPE
                       SYNTAX Counter32
                       MAX-ACCESS read-only
                       STATUS current
                       DESCRIPTION "Tx-Callback-Request"
                       ::= {  staPppBac 13 }

staPppBacTxcallbackres OBJECT-TYPE
                       SYNTAX Counter32
                       MAX-ACCESS read-only
                       STATUS current
                       DESCRIPTION "Tx-Callback-Response"
                       ::= {  staPppBac 14 }

staPppBacTxlinkdropreq OBJECT-TYPE
                       SYNTAX Counter32
                       MAX-ACCESS read-only
                       STATUS current
                       DESCRIPTION "Tx-Link-Drop-Request"
                       ::= {  staPppBac 15 }

staPppBacTxlinkdropres OBJECT-TYPE
                       SYNTAX Counter32
                       MAX-ACCESS read-only
                       STATUS current
                       DESCRIPTION "Tx-Link-Drop-Response"
                       ::= {  staPppBac 16 }

staPppBacTxstatusindic OBJECT-TYPE
                       SYNTAX Counter32
                       MAX-ACCESS read-only
                       STATUS current
                       DESCRIPTION "Tx-Status-Indication"
                       ::= {  staPppBac 17 }

staPppBacTxstatusrespo OBJECT-TYPE
                       SYNTAX Counter32
                       MAX-ACCESS read-only
                       STATUS current
                       DESCRIPTION "Tx-Status-Response"
                       ::= {  staPppBac 18 }

staPppBacDeletevalues OBJECT-TYPE
                       SYNTAX DisplayString
                       MAX-ACCESS read-write
                       STATUS current
                       DESCRIPTION "Delete-Values"
                       ::= {  staPppBac 19 }

staPppRxo OBJECT IDENTIFIER ::= { staPpp 8}
staPppRxoLcpTable OBJECT-TYPE
                  SYNTAX SEQUENCE OF StaPppRxoLcpEntry
                  MAX-ACCESS not-accessible
                  STATUS current
                  DESCRIPTION "LCP"
                  ::= {  staPppRxo 1 }

staPppRxoLcpEntry OBJECT-TYPE
                  SYNTAX StaPppRxoLcpEntry
                  MAX-ACCESS not-accessible
                  STATUS current
                  DESCRIPTION "entry in table"
                  INDEX { staPppRxoLcpIfc }
                  ::= {  staPppRxoLcpTable 1 }

StaPppRxoLcpEntry ::= SEQUENCE {
                  staPppRxoLcpIfc INTEGER,
                  staPppRxoLcpMru INTEGER,
                  staPppRxoLcpAcc DisplayString,
                  staPppRxoLcpAut INTEGER,
                  staPppRxoLcpMag DisplayString,
                  staPppRxoLcpPfc INTEGER,
                  staPppRxoLcpAcf INTEGER,
                  staPppRxoLcpCal INTEGER
                 }

staPppRxoLcpIfc OBJECT-TYPE
                SYNTAX INTEGER
                {
                  dsl-ch-1(1),
                  dsl-ch-2(2),
                  dsl-ch-3(3),
                  dsl-ch-4(4),
                  dsl-ch-5(5),
                  dsl-ch-6(6),
                  dsl-ch-7(7),
                  dsl-ch-8(8),
                  ch01(9),
                  ch02(10),
                  ext(11)
                }
                MAX-ACCESS read-only
                STATUS current
                DESCRIPTION "Ifc"
                ::= {  staPppRxoLcpEntry 1 }

staPppRxoLcpMru OBJECT-TYPE
                SYNTAX INTEGER (0..65535)
                MAX-ACCESS read-only
                STATUS current
                DESCRIPTION "MRU"
                ::= {  staPppRxoLcpEntry 2 }

staPppRxoLcpAcc OBJECT-TYPE
                SYNTAX DisplayString (SIZE(0..8))
                MAX-ACCESS read-only
                STATUS current
                DESCRIPTION "ACCM"
                ::= {  staPppRxoLcpEntry 3 }

staPppRxoLcpAut OBJECT-TYPE
                SYNTAX INTEGER
                {
                  none(0),
                  ms-chapv2(32),
                  ms-chap(16),
                  chap(8),
                  pap(4)
                }
                MAX-ACCESS read-only
                STATUS current
                DESCRIPTION "Authent.request"
                ::= {  staPppRxoLcpEntry 4 }

staPppRxoLcpMag OBJECT-TYPE
                SYNTAX DisplayString (SIZE(0..8))
                MAX-ACCESS read-only
                STATUS current
                DESCRIPTION "Magic-Num"
                ::= {  staPppRxoLcpEntry 6 }

staPppRxoLcpPfc OBJECT-TYPE
                SYNTAX INTEGER
                {
                  yes(1),
                  no(0)
                }
                MAX-ACCESS read-only
                STATUS current
                DESCRIPTION "PFC"
                ::= {  staPppRxoLcpEntry 7 }

staPppRxoLcpAcf OBJECT-TYPE
                SYNTAX INTEGER
                {
                  yes(1),
                  no(0)
                }
                MAX-ACCESS read-only
                STATUS current
                DESCRIPTION "ACFC"
                ::= {  staPppRxoLcpEntry 8 }

staPppRxoLcpCal OBJECT-TYPE
                SYNTAX INTEGER
                {
                  none(0),
                  none(255),
                  lcp(1),
                  lcp(2),
                  lcp(3),
                  lcp(4),
                  lcp(5),
                  cbcp(6)
                }
                MAX-ACCESS read-only
                STATUS current
                DESCRIPTION "Call-back"
                ::= {  staPppRxoLcpEntry 5 }

staPppRxoIpcTable OBJECT-TYPE
                  SYNTAX SEQUENCE OF StaPppRxoIpcEntry
                  MAX-ACCESS not-accessible
                  STATUS current
                  DESCRIPTION "IPCP"
                  ::= {  staPppRxo 3 }

staPppRxoIpcEntry OBJECT-TYPE
                  SYNTAX StaPppRxoIpcEntry
                  MAX-ACCESS not-accessible
                  STATUS current
                  DESCRIPTION "entry in table"
                  INDEX { staPppRxoIpcIfc }
                  ::= {  staPppRxoIpcTable 1 }

StaPppRxoIpcEntry ::= SEQUENCE {
                  staPppRxoIpcIfc INTEGER,
                  staPppRxoIpcIpadd IpAddress,
                  staPppRxoIpcDnsde IpAddress,
                  staPppRxoIpcDnsba IpAddress,
                  staPppRxoIpcNbnsd IpAddress,
                  staPppRxoIpcNbnsb IpAddress
                 }

staPppRxoIpcIfc OBJECT-TYPE
                  SYNTAX INTEGER
                  {
                    dsl-ch-1(1),
                    dsl-ch-2(2),
                    dsl-ch-3(3),
                    dsl-ch-4(4),
                    dsl-ch-5(5),
                    dsl-ch-6(6),
                    dsl-ch-7(7),
                    dsl-ch-8(8),
                    ch01(9),
                    ch02(10),
                    ext(11)
                  }
                  MAX-ACCESS read-only
                  STATUS current
                  DESCRIPTION "Ifc"
                  ::= {  staPppRxoIpcEntry 1 }

staPppRxoIpcIpadd OBJECT-TYPE
                  SYNTAX IpAddress
                  MAX-ACCESS read-only
                  STATUS current
                  DESCRIPTION "IP-Address"
                  ::= {  staPppRxoIpcEntry 2 }

staPppRxoIpcDnsde OBJECT-TYPE
                  SYNTAX IpAddress
                  MAX-ACCESS read-only
                  STATUS current
                  DESCRIPTION "DNS-Default"
                  ::= {  staPppRxoIpcEntry 3 }

staPppRxoIpcDnsba OBJECT-TYPE
                  SYNTAX IpAddress
                  MAX-ACCESS read-only
                  STATUS current
                  DESCRIPTION "DNS-Backup"
                  ::= {  staPppRxoIpcEntry 5 }

staPppRxoIpcNbnsd OBJECT-TYPE
                  SYNTAX IpAddress
                  MAX-ACCESS read-only
                  STATUS current
                  DESCRIPTION "NBNS-Default"
                  ::= {  staPppRxoIpcEntry 4 }

staPppRxoIpcNbnsb OBJECT-TYPE
                  SYNTAX IpAddress
                  MAX-ACCESS read-only
                  STATUS current
                  DESCRIPTION "NBNS-Backup"
                  ::= {  staPppRxoIpcEntry 6 }

staPppTxo OBJECT IDENTIFIER ::= { staPpp 9}
staPppTxoLcpTable OBJECT-TYPE
                  SYNTAX SEQUENCE OF StaPppTxoLcpEntry
                  MAX-ACCESS not-accessible
                  STATUS current
                  DESCRIPTION "LCP"
                  ::= {  staPppTxo 1 }

staPppTxoLcpEntry OBJECT-TYPE
                  SYNTAX StaPppTxoLcpEntry
                  MAX-ACCESS not-accessible
                  STATUS current
                  DESCRIPTION "entry in table"
                  INDEX { staPppTxoLcpIfc }
                  ::= {  staPppTxoLcpTable 1 }

StaPppTxoLcpEntry ::= SEQUENCE {
                  staPppTxoLcpIfc INTEGER,
                  staPppTxoLcpMru INTEGER,
                  staPppTxoLcpAcc DisplayString,
                  staPppTxoLcpAut INTEGER,
                  staPppTxoLcpMag DisplayString,
                  staPppTxoLcpPfc INTEGER,
                  staPppTxoLcpAcf INTEGER,
                  staPppTxoLcpCal INTEGER
                 }

staPppTxoLcpIfc OBJECT-TYPE
                SYNTAX INTEGER
                {
                  dsl-ch-1(1),
                  dsl-ch-2(2),
                  dsl-ch-3(3),
                  dsl-ch-4(4),
                  dsl-ch-5(5),
                  dsl-ch-6(6),
                  dsl-ch-7(7),
                  dsl-ch-8(8),
                  ch01(9),
                  ch02(10),
                  ext(11)
                }
                MAX-ACCESS read-only
                STATUS current
                DESCRIPTION "Ifc"
                ::= {  staPppTxoLcpEntry 1 }

staPppTxoLcpMru OBJECT-TYPE
                SYNTAX INTEGER (0..65535)
                MAX-ACCESS read-only
                STATUS current
                DESCRIPTION "MRU"
                ::= {  staPppTxoLcpEntry 2 }

staPppTxoLcpAcc OBJECT-TYPE
                SYNTAX DisplayString (SIZE(0..8))
                MAX-ACCESS read-only
                STATUS current
                DESCRIPTION "ACCM"
                ::= {  staPppTxoLcpEntry 3 }

staPppTxoLcpAut OBJECT-TYPE
                SYNTAX INTEGER
                {
                  none(0),
                  ms-chapv2(32),
                  ms-chap(16),
                  chap(8),
                  pap(4)
                }
                MAX-ACCESS read-only
                STATUS current
                DESCRIPTION "Authent.request"
                ::= {  staPppTxoLcpEntry 4 }

staPppTxoLcpMag OBJECT-TYPE
                SYNTAX DisplayString (SIZE(0..8))
                MAX-ACCESS read-only
                STATUS current
                DESCRIPTION "Magic-Num"
                ::= {  staPppTxoLcpEntry 6 }

staPppTxoLcpPfc OBJECT-TYPE
                SYNTAX INTEGER
                {
                  yes(1),
                  no(0)
                }
                MAX-ACCESS read-only
                STATUS current
                DESCRIPTION "PFC"
                ::= {  staPppTxoLcpEntry 7 }

staPppTxoLcpAcf OBJECT-TYPE
                SYNTAX INTEGER
                {
                  yes(1),
                  no(0)
                }
                MAX-ACCESS read-only
                STATUS current
                DESCRIPTION "ACFC"
                ::= {  staPppTxoLcpEntry 8 }

staPppTxoLcpCal OBJECT-TYPE
                SYNTAX INTEGER
                {
                  none(0),
                  none(255),
                  lcp(1),
                  lcp(2),
                  lcp(3),
                  lcp(4),
                  lcp(5),
                  cbcp(6)
                }
                MAX-ACCESS read-only
                STATUS current
                DESCRIPTION "Call-back"
                ::= {  staPppTxoLcpEntry 5 }

staPppTxoIpcTable OBJECT-TYPE
                  SYNTAX SEQUENCE OF StaPppTxoIpcEntry
                  MAX-ACCESS not-accessible
                  STATUS current
                  DESCRIPTION "IPCP"
                  ::= {  staPppTxo 3 }

staPppTxoIpcEntry OBJECT-TYPE
                  SYNTAX StaPppTxoIpcEntry
                  MAX-ACCESS not-accessible
                  STATUS current
                  DESCRIPTION "entry in table"
                  INDEX { staPppTxoIpcIfc }
                  ::= {  staPppTxoIpcTable 1 }

StaPppTxoIpcEntry ::= SEQUENCE {
                  staPppTxoIpcIfc INTEGER,
                  staPppTxoIpcIpadd IpAddress,
                  staPppTxoIpcDnsde IpAddress,
                  staPppTxoIpcDnsba IpAddress,
                  staPppTxoIpcNbnsd IpAddress,
                  staPppTxoIpcNbnsb IpAddress
                 }

staPppTxoIpcIfc OBJECT-TYPE
                  SYNTAX INTEGER
                  {
                    dsl-ch-1(1),
                    dsl-ch-2(2),
                    dsl-ch-3(3),
                    dsl-ch-4(4),
                    dsl-ch-5(5),
                    dsl-ch-6(6),
                    dsl-ch-7(7),
                    dsl-ch-8(8),
                    ch01(9),
                    ch02(10),
                    ext(11)
                  }
                  MAX-ACCESS read-only
                  STATUS current
                  DESCRIPTION "Ifc"
                  ::= {  staPppTxoIpcEntry 1 }

staPppTxoIpcIpadd OBJECT-TYPE
                  SYNTAX IpAddress
                  MAX-ACCESS read-only
                  STATUS current
                  DESCRIPTION "IP-Address"
                  ::= {  staPppTxoIpcEntry 2 }

staPppTxoIpcDnsde OBJECT-TYPE
                  SYNTAX IpAddress
                  MAX-ACCESS read-only
                  STATUS current
                  DESCRIPTION "DNS-Default"
                  ::= {  staPppTxoIpcEntry 3 }

staPppTxoIpcDnsba OBJECT-TYPE
                  SYNTAX IpAddress
                  MAX-ACCESS read-only
                  STATUS current
                  DESCRIPTION "DNS-Backup"
                  ::= {  staPppTxoIpcEntry 5 }

staPppTxoIpcNbnsd OBJECT-TYPE
                  SYNTAX IpAddress
                  MAX-ACCESS read-only
                  STATUS current
                  DESCRIPTION "NBNS-Default"
                  ::= {  staPppTxoIpcEntry 4 }

staPppTxoIpcNbnsb OBJECT-TYPE
                  SYNTAX IpAddress
                  MAX-ACCESS read-only
                  STATUS current
                  DESCRIPTION "NBNS-Backup"
                  ::= {  staPppTxoIpcEntry 6 }

staPppDel OBJECT-TYPE
          SYNTAX DisplayString
          MAX-ACCESS read-write
          STATUS current
          DESCRIPTION "Delete-Values"
          ::= {  staPpp 13 }

staTcpi OBJECT IDENTIFIER ::= { sta 9}
staTcpiArp OBJECT IDENTIFIER ::= { staTcpi 1}
staTcpiArpLanr OBJECT-TYPE
               SYNTAX Counter32
               MAX-ACCESS read-only
               STATUS current
               DESCRIPTION "LAN-Rx"
               ::= {  staTcpiArp 1 }

staTcpiArpLant OBJECT-TYPE
               SYNTAX Counter32
               MAX-ACCESS read-only
               STATUS current
               DESCRIPTION "LAN-Tx"
               ::= {  staTcpiArp 2 }

staTcpiArpLane OBJECT-TYPE
               SYNTAX Counter32
               MAX-ACCESS read-only
               STATUS current
               DESCRIPTION "LAN-Errors"
               ::= {  staTcpiArp 3 }

staTcpiArpWanr OBJECT-TYPE
               SYNTAX Counter32
               MAX-ACCESS read-only
               STATUS current
               DESCRIPTION "WAN-Rx"
               ::= {  staTcpiArp 4 }

staTcpiArpWant OBJECT-TYPE
               SYNTAX Counter32
               MAX-ACCESS read-only
               STATUS current
               DESCRIPTION "WAN-Tx"
               ::= {  staTcpiArp 5 }

staTcpiArpWane OBJECT-TYPE
               SYNTAX Counter32
               MAX-ACCESS read-only
               STATUS current
               DESCRIPTION "WAN-Errors"
               ::= {  staTcpiArp 6 }

staTcpiArpTablTable OBJECT-TYPE
                    SYNTAX SEQUENCE OF StaTcpiArpTablEntry
                    MAX-ACCESS not-accessible
                    STATUS current
                    DESCRIPTION "Table-ARP"
                    ::= {  staTcpiArp 7 }

staTcpiArpTablEntry OBJECT-TYPE
                    SYNTAX StaTcpiArpTablEntry
                    MAX-ACCESS not-accessible
                    STATUS current
                    DESCRIPTION "entry in table"
                    INDEX { staTcpiArpTablIpa }
                    ::= {  staTcpiArpTablTable 1 }

StaTcpiArpTablEntry ::= SEQUENCE {
                    staTcpiArpTablIpa IpAddress,
                    staTcpiArpTablMac MacAddress,
                    staTcpiArpTablLas INTEGER,
                    staTcpiArpTablCon INTEGER,
                    staTcpiArpTablEth INTEGER,
                    staTcpiArpTablVla INTEGER,
                    staTcpiArpTablPee DisplayString
                   }

staTcpiArpTablIpa OBJECT-TYPE
                  SYNTAX IpAddress
                  MAX-ACCESS read-only
                  STATUS current
                  DESCRIPTION "IP-Address"
                  ::= {  staTcpiArpTablEntry 1 }

staTcpiArpTablMac OBJECT-TYPE
                  SYNTAX MacAddress
                  MAX-ACCESS read-only
                  STATUS current
                  DESCRIPTION "MAC-Address"
                  ::= {  staTcpiArpTablEntry 2 }

staTcpiArpTablLas OBJECT-TYPE
                  SYNTAX INTEGER (0..2147483647)
                  MAX-ACCESS read-only
                  STATUS current
                  DESCRIPTION "Last-access"
                  ::= {  staTcpiArpTablEntry 3 }

staTcpiArpTablCon OBJECT-TYPE
                  SYNTAX INTEGER
                  {
                    lan-1(0),
                    lan-2(1),
                    lan-3(2),
                    lan-4(3),
                    wan(4)
                  }
                  MAX-ACCESS read-only
                  STATUS current
                  DESCRIPTION "Connect"
                  ::= {  staTcpiArpTablEntry 4 }

staTcpiArpTablEth OBJECT-TYPE
                  SYNTAX INTEGER
                  {
                    wan(1),
                    eth-1(2),
                    eth-2(3),
                    eth-3(4),
                    eth-4(5),
                    unknown(0)
                  }
                  MAX-ACCESS read-only
                  STATUS current
                  DESCRIPTION "Ethernet-Port"
                  ::= {  staTcpiArpTablEntry 5 }

staTcpiArpTablVla OBJECT-TYPE
                  SYNTAX INTEGER (0..65535)
                  MAX-ACCESS read-only
                  STATUS current
                  DESCRIPTION "VLAN-ID"
                  ::= {  staTcpiArpTablEntry 7 }

staTcpiArpTablPee OBJECT-TYPE
                  SYNTAX DisplayString (SIZE(0..255))
                  MAX-ACCESS read-only
                  STATUS current
                  DESCRIPTION "Peer"
                  ::= {  staTcpiArpTablEntry 6 }

staTcpiArpDele OBJECT-TYPE
               SYNTAX DisplayString
               MAX-ACCESS read-write
               STATUS current
               DESCRIPTION "Delete-Values"
               ::= {  staTcpiArp 8 }

staTcpiIp OBJECT IDENTIFIER ::= { staTcpi 2}
staTcpiIpLanrx OBJECT-TYPE
                            SYNTAX Counter32
                            MAX-ACCESS read-only
                            STATUS current
                            DESCRIPTION "LAN-Rx"
                            ::= {  staTcpiIp 1 }

staTcpiIpLantx OBJECT-TYPE
                            SYNTAX Counter32
                            MAX-ACCESS read-only
                            STATUS current
                            DESCRIPTION "LAN-Tx"
                            ::= {  staTcpiIp 2 }

staTcpiIpLanchecksumerrors OBJECT-TYPE
                            SYNTAX Counter32
                            MAX-ACCESS read-only
                            STATUS current
                            DESCRIPTION "LAN-Checksum-Errors"
                            ::= {  staTcpiIp 3 }

staTcpiIpLanserviceerrors OBJECT-TYPE
                            SYNTAX Counter32
                            MAX-ACCESS read-only
                            STATUS current
                            DESCRIPTION "LAN-Service-Errors"
                            ::= {  staTcpiIp 4 }

staTcpiIpLanfragmentationer OBJECT-TYPE
                            SYNTAX Counter32
                            MAX-ACCESS read-only
                            STATUS current
                            DESCRIPTION "LAN-Fragmentation-Errors"
                            ::= {  staTcpiIp 10 }

staTcpiIpLanfragmentations OBJECT-TYPE
                            SYNTAX Counter32
                            MAX-ACCESS read-only
                            STATUS current
                            DESCRIPTION "LAN-Fragmentations"
                            ::= {  staTcpiIp 13 }

staTcpiIpLanfragmentationsf OBJECT-TYPE
                            SYNTAX Counter32
                            MAX-ACCESS read-only
                            STATUS current
                            DESCRIPTION "LAN-Fragmentations-Forced"
                            ::= {  staTcpiIp 14 }

staTcpiIpWanrx OBJECT-TYPE
                            SYNTAX Counter32
                            MAX-ACCESS read-only
                            STATUS current
                            DESCRIPTION "WAN-Rx"
                            ::= {  staTcpiIp 5 }

staTcpiIpWantx OBJECT-TYPE
                            SYNTAX Counter32
                            MAX-ACCESS read-only
                            STATUS current
                            DESCRIPTION "WAN-Tx"
                            ::= {  staTcpiIp 6 }

staTcpiIpWanchecksumerrors OBJECT-TYPE
                            SYNTAX Counter32
                            MAX-ACCESS read-only
                            STATUS current
                            DESCRIPTION "WAN-Checksum-Errors"
                            ::= {  staTcpiIp 7 }

staTcpiIpWanserviceerrors OBJECT-TYPE
                            SYNTAX Counter32
                            MAX-ACCESS read-only
                            STATUS current
                            DESCRIPTION "WAN-Service-Errors"
                            ::= {  staTcpiIp 8 }

staTcpiIpWanfragmentationer OBJECT-TYPE
                            SYNTAX Counter32
                            MAX-ACCESS read-only
                            STATUS current
                            DESCRIPTION "WAN-Fragmentation-Errors"
                            ::= {  staTcpiIp 11 }

staTcpiIpWanfragmentations OBJECT-TYPE
                            SYNTAX Counter32
                            MAX-ACCESS read-only
                            STATUS current
                            DESCRIPTION "WAN-Fragmentations"
                            ::= {  staTcpiIp 15 }

staTcpiIpWanfragmentationsf OBJECT-TYPE
                            SYNTAX Counter32
                            MAX-ACCESS read-only
                            STATUS current
                            DESCRIPTION "WAN-Fragmentations-Forced"
                            ::= {  staTcpiIp 16 }

staTcpiIpWanrxdisconnect OBJECT-TYPE
                            SYNTAX Counter32
                            MAX-ACCESS read-only
                            STATUS current
                            DESCRIPTION "WAN-Rx-Disconnect"
                            ::= {  staTcpiIp 9 }

staTcpiIpLooperror OBJECT-TYPE
                            SYNTAX Counter32
                            MAX-ACCESS read-only
                            STATUS current
                            DESCRIPTION "Loop-Error"
                            ::= {  staTcpiIp 17 }

staTcpiIpDeletevalues OBJECT-TYPE
                            SYNTAX DisplayString
                            MAX-ACCESS read-write
                            STATUS current
                            DESCRIPTION "Delete-Values"
                            ::= {  staTcpiIp 12 }

staTcpiIcmp OBJECT IDENTIFIER ::= { staTcpi 3}
staTcpiIcmpLanr OBJECT-TYPE
                SYNTAX Counter32
                MAX-ACCESS read-only
                STATUS current
                DESCRIPTION "LAN-Rx"
                ::= {  staTcpiIcmp 1 }

staTcpiIcmpLant OBJECT-TYPE
                SYNTAX Counter32
                MAX-ACCESS read-only
                STATUS current
                DESCRIPTION "LAN-Tx"
                ::= {  staTcpiIcmp 2 }

staTcpiIcmpLanc OBJECT-TYPE
                SYNTAX Counter32
                MAX-ACCESS read-only
                STATUS current
                DESCRIPTION "LAN-Checksum-Errors"
                ::= {  staTcpiIcmp 3 }

staTcpiIcmpLans OBJECT-TYPE
                SYNTAX Counter32
                MAX-ACCESS read-only
                STATUS current
                DESCRIPTION "LAN-Service-Errors"
                ::= {  staTcpiIcmp 4 }

staTcpiIcmpWanr OBJECT-TYPE
                SYNTAX Counter32
                MAX-ACCESS read-only
                STATUS current
                DESCRIPTION "WAN-Rx"
                ::= {  staTcpiIcmp 5 }

staTcpiIcmpWant OBJECT-TYPE
                SYNTAX Counter32
                MAX-ACCESS read-only
                STATUS current
                DESCRIPTION "WAN-Tx"
                ::= {  staTcpiIcmp 6 }

staTcpiIcmpWanc OBJECT-TYPE
                SYNTAX Counter32
                MAX-ACCESS read-only
                STATUS current
                DESCRIPTION "WAN-Checksum-Errors"
                ::= {  staTcpiIcmp 7 }

staTcpiIcmpWans OBJECT-TYPE
                SYNTAX Counter32
                MAX-ACCESS read-only
                STATUS current
                DESCRIPTION "WAN-Service-Errors"
                ::= {  staTcpiIcmp 8 }

staTcpiIcmpDele OBJECT-TYPE
                SYNTAX DisplayString
                MAX-ACCESS read-write
                STATUS current
                DESCRIPTION "Delete-Values"
                ::= {  staTcpiIcmp 9 }

staTcpiTftp OBJECT IDENTIFIER ::= { staTcpi 4}
staTcpiTftpLanrx OBJECT-TYPE
                  SYNTAX Counter32
                  MAX-ACCESS read-only
                  STATUS current
                  DESCRIPTION "LAN-Rx"
                  ::= {  staTcpiTftp 1 }

staTcpiTftpLanrxr OBJECT-TYPE
                  SYNTAX Counter32
                  MAX-ACCESS read-only
                  STATUS current
                  DESCRIPTION "LAN-Rx-Read-Request"
                  ::= {  staTcpiTftp 2 }

staTcpiTftpLanrxw OBJECT-TYPE
                  SYNTAX Counter32
                  MAX-ACCESS read-only
                  STATUS current
                  DESCRIPTION "LAN-Rx-Write-Request"
                  ::= {  staTcpiTftp 3 }

staTcpiTftpLanrxd OBJECT-TYPE
                  SYNTAX Counter32
                  MAX-ACCESS read-only
                  STATUS current
                  DESCRIPTION "LAN-Rx-Data"
                  ::= {  staTcpiTftp 4 }

staTcpiTftpLanrxa OBJECT-TYPE
                  SYNTAX Counter32
                  MAX-ACCESS read-only
                  STATUS current
                  DESCRIPTION "LAN-Rx-Ack."
                  ::= {  staTcpiTftp 5 }

staTcpiTftpLanrxo OBJECT-TYPE
                  SYNTAX Counter32
                  MAX-ACCESS read-only
                  STATUS current
                  DESCRIPTION "LAN-Rx-Option-Ack."
                  ::= {  staTcpiTftp 6 }

staTcpiTftpLanrxe OBJECT-TYPE
                  SYNTAX Counter32
                  MAX-ACCESS read-only
                  STATUS current
                  DESCRIPTION "LAN-Rx-Errors"
                  ::= {  staTcpiTftp 7 }

staTcpiTftpLanrxb OBJECT-TYPE
                  SYNTAX Counter32
                  MAX-ACCESS read-only
                  STATUS current
                  DESCRIPTION "LAN-Rx-Bad-Packets"
                  ::= {  staTcpiTftp 8 }

staTcpiTftpLantx OBJECT-TYPE
                  SYNTAX Counter32
                  MAX-ACCESS read-only
                  STATUS current
                  DESCRIPTION "LAN-Tx"
                  ::= {  staTcpiTftp 9 }

staTcpiTftpLantxd OBJECT-TYPE
                  SYNTAX Counter32
                  MAX-ACCESS read-only
                  STATUS current
                  DESCRIPTION "LAN-Tx-Data"
                  ::= {  staTcpiTftp 10 }

staTcpiTftpLantxa OBJECT-TYPE
                  SYNTAX Counter32
                  MAX-ACCESS read-only
                  STATUS current
                  DESCRIPTION "LAN-Tx-Ack."
                  ::= {  staTcpiTftp 11 }

staTcpiTftpLantxo OBJECT-TYPE
                  SYNTAX Counter32
                  MAX-ACCESS read-only
                  STATUS current
                  DESCRIPTION "LAN-Tx-Option-Ack."
                  ::= {  staTcpiTftp 12 }

staTcpiTftpLantxe OBJECT-TYPE
                  SYNTAX Counter32
                  MAX-ACCESS read-only
                  STATUS current
                  DESCRIPTION "LAN-Tx-Errors"
                  ::= {  staTcpiTftp 13 }

staTcpiTftpLantxr OBJECT-TYPE
                  SYNTAX Counter32
                  MAX-ACCESS read-only
                  STATUS current
                  DESCRIPTION "LAN-Tx-Repeats"
                  ::= {  staTcpiTftp 14 }

staTcpiTftpLancon OBJECT-TYPE
                  SYNTAX Counter32
                  MAX-ACCESS read-only
                  STATUS current
                  DESCRIPTION "LAN-Connections"
                  ::= {  staTcpiTftp 15 }

staTcpiTftpWanrx OBJECT-TYPE
                  SYNTAX Counter32
                  MAX-ACCESS read-only
                  STATUS current
                  DESCRIPTION "WAN-Rx"
                  ::= {  staTcpiTftp 16 }

staTcpiTftpWanrxr OBJECT-TYPE
                  SYNTAX Counter32
                  MAX-ACCESS read-only
                  STATUS current
                  DESCRIPTION "WAN-Rx-Read-Request"
                  ::= {  staTcpiTftp 17 }

staTcpiTftpWanrxw OBJECT-TYPE
                  SYNTAX Counter32
                  MAX-ACCESS read-only
                  STATUS current
                  DESCRIPTION "WAN-Rx-Write-Request"
                  ::= {  staTcpiTftp 18 }

staTcpiTftpWanrxd OBJECT-TYPE
                  SYNTAX Counter32
                  MAX-ACCESS read-only
                  STATUS current
                  DESCRIPTION "WAN-Rx-Data"
                  ::= {  staTcpiTftp 19 }

staTcpiTftpWanrxa OBJECT-TYPE
                  SYNTAX Counter32
                  MAX-ACCESS read-only
                  STATUS current
                  DESCRIPTION "WAN-Rx-Ack."
                  ::= {  staTcpiTftp 20 }

staTcpiTftpWanrxo OBJECT-TYPE
                  SYNTAX Counter32
                  MAX-ACCESS read-only
                  STATUS current
                  DESCRIPTION "WAN-Rx-Option-Ack."
                  ::= {  staTcpiTftp 21 }

staTcpiTftpWanrxe OBJECT-TYPE
                  SYNTAX Counter32
                  MAX-ACCESS read-only
                  STATUS current
                  DESCRIPTION "WAN-Rx-Errors"
                  ::= {  staTcpiTftp 22 }

staTcpiTftpWanrxb OBJECT-TYPE
                  SYNTAX Counter32
                  MAX-ACCESS read-only
                  STATUS current
                  DESCRIPTION "WAN-Rx-Bad-Packets"
                  ::= {  staTcpiTftp 23 }

staTcpiTftpWantx OBJECT-TYPE
                  SYNTAX Counter32
                  MAX-ACCESS read-only
                  STATUS current
                  DESCRIPTION "WAN-Tx"
                  ::= {  staTcpiTftp 24 }

staTcpiTftpWantxd OBJECT-TYPE
                  SYNTAX Counter32
                  MAX-ACCESS read-only
                  STATUS current
                  DESCRIPTION "WAN-Tx-Data"
                  ::= {  staTcpiTftp 25 }

staTcpiTftpWantxa OBJECT-TYPE
                  SYNTAX Counter32
                  MAX-ACCESS read-only
                  STATUS current
                  DESCRIPTION "WAN-Tx-Ack."
                  ::= {  staTcpiTftp 26 }

staTcpiTftpWantxo OBJECT-TYPE
                  SYNTAX Counter32
                  MAX-ACCESS read-only
                  STATUS current
                  DESCRIPTION "WAN-Tx-Option-Ack."
                  ::= {  staTcpiTftp 27 }

staTcpiTftpWantxe OBJECT-TYPE
                  SYNTAX Counter32
                  MAX-ACCESS read-only
                  STATUS current
                  DESCRIPTION "WAN-Tx-Errors"
                  ::= {  staTcpiTftp 28 }

staTcpiTftpWantxr OBJECT-TYPE
                  SYNTAX Counter32
                  MAX-ACCESS read-only
                  STATUS current
                  DESCRIPTION "WAN-Tx-Repeats"
                  ::= {  staTcpiTftp 29 }

staTcpiTftpWancon OBJECT-TYPE
                  SYNTAX Counter32
                  MAX-ACCESS read-only
                  STATUS current
                  DESCRIPTION "WAN-Connections"
                  ::= {  staTcpiTftp 30 }

staTcpiTftpDelete OBJECT-TYPE
                  SYNTAX DisplayString
                  MAX-ACCESS read-write
                  STATUS current
                  DESCRIPTION "Delete-Values"
                  ::= {  staTcpiTftp 31 }

staTcpiTcp OBJECT IDENTIFIER ::= { staTcpi 5}
staTcpiTcpLanrx OBJECT-TYPE
                 SYNTAX Counter32
                 MAX-ACCESS read-only
                 STATUS current
                 DESCRIPTION "LAN-Rx"
                 ::= {  staTcpiTcp 1 }

staTcpiTcpLantx OBJECT-TYPE
                 SYNTAX Counter32
                 MAX-ACCESS read-only
                 STATUS current
                 DESCRIPTION "LAN-Tx"
                 ::= {  staTcpiTcp 2 }

staTcpiTcpLantxr OBJECT-TYPE
                 SYNTAX Counter32
                 MAX-ACCESS read-only
                 STATUS current
                 DESCRIPTION "LAN-Tx-Repeats"
                 ::= {  staTcpiTcp 3 }

staTcpiTcpLanche OBJECT-TYPE
                 SYNTAX Counter32
                 MAX-ACCESS read-only
                 STATUS current
                 DESCRIPTION "LAN-Checksum-Errors"
                 ::= {  staTcpiTcp 4 }

staTcpiTcpLanser OBJECT-TYPE
                 SYNTAX Counter32
                 MAX-ACCESS read-only
                 STATUS current
                 DESCRIPTION "LAN-Service-Errors"
                 ::= {  staTcpiTcp 5 }

staTcpiTcpLancon OBJECT-TYPE
                 SYNTAX Counter32
                 MAX-ACCESS read-only
                 STATUS current
                 DESCRIPTION "LAN-Connections"
                 ::= {  staTcpiTcp 6 }

staTcpiTcpWanrx OBJECT-TYPE
                 SYNTAX Counter32
                 MAX-ACCESS read-only
                 STATUS current
                 DESCRIPTION "WAN-Rx"
                 ::= {  staTcpiTcp 7 }

staTcpiTcpWantx OBJECT-TYPE
                 SYNTAX Counter32
                 MAX-ACCESS read-only
                 STATUS current
                 DESCRIPTION "WAN-Tx"
                 ::= {  staTcpiTcp 8 }

staTcpiTcpWantxr OBJECT-TYPE
                 SYNTAX Counter32
                 MAX-ACCESS read-only
                 STATUS current
                 DESCRIPTION "WAN-Tx-Repeats"
                 ::= {  staTcpiTcp 9 }

staTcpiTcpWanche OBJECT-TYPE
                 SYNTAX Counter32
                 MAX-ACCESS read-only
                 STATUS current
                 DESCRIPTION "WAN-Checksum-Errors"
                 ::= {  staTcpiTcp 10 }

staTcpiTcpWanser OBJECT-TYPE
                 SYNTAX Counter32
                 MAX-ACCESS read-only
                 STATUS current
                 DESCRIPTION "WAN-Service-Errors"
                 ::= {  staTcpiTcp 11 }

staTcpiTcpWancon OBJECT-TYPE
                 SYNTAX Counter32
                 MAX-ACCESS read-only
                 STATUS current
                 DESCRIPTION "WAN-Connections"
                 ::= {  staTcpiTcp 12 }

staTcpiTcpDelete OBJECT-TYPE
                 SYNTAX DisplayString
                 MAX-ACCESS read-write
                 STATUS current
                 DESCRIPTION "Delete-Values"
                 ::= {  staTcpiTcp 13 }

staTcpiDhcp OBJECT IDENTIFIER ::= { staTcpi 6}
staTcpiDhcpLanrx OBJECT-TYPE
                 SYNTAX Counter32
                 MAX-ACCESS read-only
                 STATUS current
                 DESCRIPTION "LAN-Rx"
                 ::= {  staTcpiDhcp 1 }

staTcpiDhcpLantx OBJECT-TYPE
                 SYNTAX Counter32
                 MAX-ACCESS read-only
                 STATUS current
                 DESCRIPTION "LAN-Tx"
                 ::= {  staTcpiDhcp 2 }

staTcpiDhcpWanrx OBJECT-TYPE
                 SYNTAX Counter32
                 MAX-ACCESS read-only
                 STATUS current
                 DESCRIPTION "WAN-Rx"
                 ::= {  staTcpiDhcp 3 }

staTcpiDhcpWantx OBJECT-TYPE
                 SYNTAX Counter32
                 MAX-ACCESS read-only
                 STATUS current
                 DESCRIPTION "WAN-Tx"
                 ::= {  staTcpiDhcp 19 }

staTcpiDhcpDisca OBJECT-TYPE
                 SYNTAX Counter32
                 MAX-ACCESS read-only
                 STATUS current
                 DESCRIPTION "Discard"
                 ::= {  staTcpiDhcp 4 }

staTcpiDhcpRxdis OBJECT-TYPE
                 SYNTAX Counter32
                 MAX-ACCESS read-only
                 STATUS current
                 DESCRIPTION "Rx-Discover"
                 ::= {  staTcpiDhcp 5 }

staTcpiDhcpRxreq OBJECT-TYPE
                 SYNTAX Counter32
                 MAX-ACCESS read-only
                 STATUS current
                 DESCRIPTION "Rx-Request"
                 ::= {  staTcpiDhcp 6 }

staTcpiDhcpRxdec OBJECT-TYPE
                 SYNTAX Counter32
                 MAX-ACCESS read-only
                 STATUS current
                 DESCRIPTION "Rx-Decline"
                 ::= {  staTcpiDhcp 7 }

staTcpiDhcpRxinf OBJECT-TYPE
                 SYNTAX Counter32
                 MAX-ACCESS read-only
                 STATUS current
                 DESCRIPTION "Rx-Inform"
                 ::= {  staTcpiDhcp 8 }

staTcpiDhcpRxrel OBJECT-TYPE
                 SYNTAX Counter32
                 MAX-ACCESS read-only
                 STATUS current
                 DESCRIPTION "Rx-Release"
                 ::= {  staTcpiDhcp 9 }

staTcpiDhcpTxoff OBJECT-TYPE
                 SYNTAX Counter32
                 MAX-ACCESS read-only
                 STATUS current
                 DESCRIPTION "Tx-Offer"
                 ::= {  staTcpiDhcp 10 }

staTcpiDhcpTxack OBJECT-TYPE
                 SYNTAX Counter32
                 MAX-ACCESS read-only
                 STATUS current
                 DESCRIPTION "Tx-Ack."
                 ::= {  staTcpiDhcp 11 }

staTcpiDhcpTxnak OBJECT-TYPE
                 SYNTAX Counter32
                 MAX-ACCESS read-only
                 STATUS current
                 DESCRIPTION "Tx-Nak."
                 ::= {  staTcpiDhcp 12 }

staTcpiDhcpServe OBJECT-TYPE
                 SYNTAX Counter32
                 MAX-ACCESS read-only
                 STATUS current
                 DESCRIPTION "Server-Error"
                 ::= {  staTcpiDhcp 13 }

staTcpiDhcpAssig OBJECT-TYPE
                 SYNTAX INTEGER
                 MAX-ACCESS read-only
                 STATUS current
                 DESCRIPTION "Assigned"
                 ::= {  staTcpiDhcp 14 }

staTcpiDhcpMacco OBJECT-TYPE
                 SYNTAX Counter32
                 MAX-ACCESS read-only
                 STATUS current
                 DESCRIPTION "MAC-Conflicts"
                 ::= {  staTcpiDhcp 15 }

staTcpiDhcpNetwoTable OBJECT-TYPE
                      SYNTAX SEQUENCE OF StaTcpiDhcpNetwoEntry
                      MAX-ACCESS not-accessible
                      STATUS current
                      DESCRIPTION "Network-list"
                      ::= {  staTcpiDhcp 20 }

staTcpiDhcpNetwoEntry OBJECT-TYPE
                      SYNTAX StaTcpiDhcpNetwoEntry
                      MAX-ACCESS not-accessible
                      STATUS current
                      DESCRIPTION "entry in table"
                      INDEX { staTcpiDhcpNetwoNetworknam }
                      ::= {  staTcpiDhcpNetwoTable 1 }

StaTcpiDhcpNetwoEntry ::= SEQUENCE {
                      staTcpiDhcpNetwoNetworknam DisplayString,
                      staTcpiDhcpNetwoStartaddre IpAddress,
                      staTcpiDhcpNetwoEndaddress IpAddress,
                      staTcpiDhcpNetwoNetmask IpAddress,
                      staTcpiDhcpNetwoBroadcasta IpAddress,
                      staTcpiDhcpNetwoGatewayadd IpAddress,
                      staTcpiDhcpNetwoDnsdefault IpAddress,
                      staTcpiDhcpNetwoDnsbackup IpAddress,
                      staTcpiDhcpNetwoNbnsdefaul IpAddress,
                      staTcpiDhcpNetwoNbnsbackup IpAddress,
                      staTcpiDhcpNetwoServerflag DisplayString,
                      staTcpiDhcpNetwoBroadcastb INTEGER,
                      staTcpiDhcpNetwoServerid IpAddress,
                      staTcpiDhcpNetwoLanifc INTEGER,
                      staTcpiDhcpNetwoVlanid INTEGER,
                      staTcpiDhcpNetwoMasterserv IpAddress,
                      staTcpiDhcpNetwoCache INTEGER,
                      staTcpiDhcpNetwoAdaption INTEGER
                     }

staTcpiDhcpNetwoNetworknam OBJECT-TYPE
                           SYNTAX DisplayString (SIZE(0..16))
                           MAX-ACCESS read-only
                           STATUS current
                           DESCRIPTION "Network-name"
                           ::= {  staTcpiDhcpNetwoEntry 1 }

staTcpiDhcpNetwoStartaddre OBJECT-TYPE
                           SYNTAX IpAddress
                           MAX-ACCESS read-only
                           STATUS current
                           DESCRIPTION "Start-Address-Pool"
                           ::= {  staTcpiDhcpNetwoEntry 2 }

staTcpiDhcpNetwoEndaddress OBJECT-TYPE
                           SYNTAX IpAddress
                           MAX-ACCESS read-only
                           STATUS current
                           DESCRIPTION "End-Address-Pool"
                           ::= {  staTcpiDhcpNetwoEntry 3 }

staTcpiDhcpNetwoNetmask OBJECT-TYPE
                           SYNTAX IpAddress
                           MAX-ACCESS read-only
                           STATUS current
                           DESCRIPTION "Netmask"
                           ::= {  staTcpiDhcpNetwoEntry 4 }

staTcpiDhcpNetwoBroadcasta OBJECT-TYPE
                           SYNTAX IpAddress
                           MAX-ACCESS read-only
                           STATUS current
                           DESCRIPTION "Broadcast-Address"
                           ::= {  staTcpiDhcpNetwoEntry 5 }

staTcpiDhcpNetwoGatewayadd OBJECT-TYPE
                           SYNTAX IpAddress
                           MAX-ACCESS read-only
                           STATUS current
                           DESCRIPTION "Gateway-Address"
                           ::= {  staTcpiDhcpNetwoEntry 6 }

staTcpiDhcpNetwoDnsdefault OBJECT-TYPE
                           SYNTAX IpAddress
                           MAX-ACCESS read-only
                           STATUS current
                           DESCRIPTION "DNS-Default"
                           ::= {  staTcpiDhcpNetwoEntry 7 }

staTcpiDhcpNetwoDnsbackup OBJECT-TYPE
                           SYNTAX IpAddress
                           MAX-ACCESS read-only
                           STATUS current
                           DESCRIPTION "DNS-Backup"
                           ::= {  staTcpiDhcpNetwoEntry 8 }

staTcpiDhcpNetwoNbnsdefaul OBJECT-TYPE
                           SYNTAX IpAddress
                           MAX-ACCESS read-only
                           STATUS current
                           DESCRIPTION "NBNS-Default"
                           ::= {  staTcpiDhcpNetwoEntry 9 }

staTcpiDhcpNetwoNbnsbackup OBJECT-TYPE
                           SYNTAX IpAddress
                           MAX-ACCESS read-only
                           STATUS current
                           DESCRIPTION "NBNS-Backup"
                           ::= {  staTcpiDhcpNetwoEntry 10 }

staTcpiDhcpNetwoServerflag OBJECT-TYPE
                           SYNTAX DisplayString (SIZE(0..255))
                           MAX-ACCESS read-only
                           STATUS current
                           DESCRIPTION "Server-Flags"
                           ::= {  staTcpiDhcpNetwoEntry 11 }

staTcpiDhcpNetwoBroadcastb OBJECT-TYPE
                           SYNTAX INTEGER
                           {
                             no(0),
                             yes(1)
                           }
                           MAX-ACCESS read-only
                           STATUS current
                           DESCRIPTION "Broadcast-Bit"
                           ::= {  staTcpiDhcpNetwoEntry 13 }

staTcpiDhcpNetwoServerid OBJECT-TYPE
                           SYNTAX IpAddress
                           MAX-ACCESS read-only
                           STATUS current
                           DESCRIPTION "Server-ID"
                           ::= {  staTcpiDhcpNetwoEntry 14 }

staTcpiDhcpNetwoLanifc OBJECT-TYPE
                           SYNTAX INTEGER
                           {
                             lan-1(0),
                             lan-2(1),
                             lan-3(2),
                             lan-4(3),
                             any(255)
                           }
                           MAX-ACCESS read-only
                           STATUS current
                           DESCRIPTION "LAN-Ifc"
                           ::= {  staTcpiDhcpNetwoEntry 15 }

staTcpiDhcpNetwoVlanid OBJECT-TYPE
                           SYNTAX INTEGER (0..65535)
                           MAX-ACCESS read-only
                           STATUS current
                           DESCRIPTION "VLAN-ID"
                           ::= {  staTcpiDhcpNetwoEntry 16 }

staTcpiDhcpNetwoMasterserv OBJECT-TYPE
                           SYNTAX IpAddress
                           MAX-ACCESS read-only
                           STATUS current
                           DESCRIPTION "Master-Server"
                           ::= {  staTcpiDhcpNetwoEntry 17 }

staTcpiDhcpNetwoCache OBJECT-TYPE
                           SYNTAX INTEGER
                           {
                             no(0),
                             yes(1)
                           }
                           MAX-ACCESS read-only
                           STATUS current
                           DESCRIPTION "Cache"
                           ::= {  staTcpiDhcpNetwoEntry 18 }

staTcpiDhcpNetwoAdaption OBJECT-TYPE
                           SYNTAX INTEGER
                           {
                             no(0),
                             yes(1)
                           }
                           MAX-ACCESS read-only
                           STATUS current
                           DESCRIPTION "Adaption"
                           ::= {  staTcpiDhcpNetwoEntry 19 }

staTcpiDhcpDhcptTable OBJECT-TYPE
                      SYNTAX SEQUENCE OF StaTcpiDhcpDhcptEntry
                      MAX-ACCESS not-accessible
                      STATUS current
                      DESCRIPTION "DHCP-Table"
                      ::= {  staTcpiDhcp 16 }

staTcpiDhcpDhcptEntry OBJECT-TYPE
                      SYNTAX StaTcpiDhcpDhcptEntry
                      MAX-ACCESS not-accessible
                      STATUS current
                      DESCRIPTION "entry in table"
                      INDEX { staTcpiDhcpDhcptIpa, staTcpiDhcpDhcptNet }
                      ::= {  staTcpiDhcpDhcptTable 1 }

StaTcpiDhcpDhcptEntry ::= SEQUENCE {
                      staTcpiDhcpDhcptIpa IpAddress,
                      staTcpiDhcpDhcptMac DisplayString,
                      staTcpiDhcpDhcptTim INTEGER,
                      staTcpiDhcpDhcptHos DisplayString,
                      staTcpiDhcpDhcptTyp BITS,
                      staTcpiDhcpDhcptLan INTEGER,
                      staTcpiDhcpDhcptEth INTEGER,
                      staTcpiDhcpDhcptVla INTEGER,
                      staTcpiDhcpDhcptNet DisplayString
                     }

staTcpiDhcpDhcptIpa OBJECT-TYPE
                    SYNTAX IpAddress
                    MAX-ACCESS read-only
                    STATUS current
                    DESCRIPTION "IP-Address"
                    ::= {  staTcpiDhcpDhcptEntry 1 }

staTcpiDhcpDhcptMac OBJECT-TYPE
                    SYNTAX DisplayString (SIZE(0..12))
                    MAX-ACCESS read-only
                    STATUS current
                    DESCRIPTION "MAC-Address"
                    ::= {  staTcpiDhcpDhcptEntry 2 }

staTcpiDhcpDhcptTim OBJECT-TYPE
                    SYNTAX INTEGER (0..2147483647)
                    MAX-ACCESS read-only
                    STATUS current
                    DESCRIPTION "Timeout"
                    ::= {  staTcpiDhcpDhcptEntry 3 }

staTcpiDhcpDhcptHos OBJECT-TYPE
                    SYNTAX DisplayString (SIZE(0..64))
                    MAX-ACCESS read-only
                    STATUS current
                    DESCRIPTION "Hostname"
                    ::= {  staTcpiDhcpDhcptEntry 4 }

staTcpiDhcpDhcptTyp OBJECT-TYPE
                    SYNTAX BITS
                    {
                      new(15),
                      new(14),
                      dyn(11),
                      unkn(13),
                      stat(12),
                      bootp(10),
                      relay(4)
                    }
                    MAX-ACCESS read-only
                    STATUS current
                    DESCRIPTION "Type"
                    ::= {  staTcpiDhcpDhcptEntry 5 }

staTcpiDhcpDhcptLan OBJECT-TYPE
                    SYNTAX INTEGER
                    {
                      lan-1(0),
                      lan-2(1),
                      lan-3(2),
                      lan-4(3),
                      any(255)
                    }
                    MAX-ACCESS read-only
                    STATUS current
                    DESCRIPTION "LAN-Ifc"
                    ::= {  staTcpiDhcpDhcptEntry 6 }

staTcpiDhcpDhcptEth OBJECT-TYPE
                    SYNTAX INTEGER
                    {
                      wan(1),
                      eth-1(2),
                      eth-2(3),
                      eth-3(4),
                      eth-4(5),
                      unknown(0)
                    }
                    MAX-ACCESS read-only
                    STATUS current
                    DESCRIPTION "Ethernet-Port"
                    ::= {  staTcpiDhcpDhcptEntry 7 }

staTcpiDhcpDhcptVla OBJECT-TYPE
                    SYNTAX INTEGER (0..65535)
                    MAX-ACCESS read-only
                    STATUS current
                    DESCRIPTION "VLAN-ID"
                    ::= {  staTcpiDhcpDhcptEntry 8 }

staTcpiDhcpDhcptNet OBJECT-TYPE
                    SYNTAX DisplayString (SIZE(0..17))
                    MAX-ACCESS read-only
                    STATUS current
                    DESCRIPTION "Network-name"
                    ::= {  staTcpiDhcpDhcptEntry 9 }

staTcpiDhcpDelet OBJECT-TYPE
                 SYNTAX DisplayString
                 MAX-ACCESS read-write
                 STATUS current
                 DESCRIPTION "Delete-Values"
                 ::= {  staTcpiDhcp 18 }

staTcpiDele OBJECT-TYPE
            SYNTAX DisplayString
            MAX-ACCESS read-write
            STATUS current
            DESCRIPTION "Delete-Values"
            ::= {  staTcpi 7 }

staTcpiNetb OBJECT IDENTIFIER ::= { staTcpi 8}
staTcpiNetbLanrx OBJECT-TYPE
                  SYNTAX Counter32
                  MAX-ACCESS read-only
                  STATUS current
                  DESCRIPTION "LAN-Rx"
                  ::= {  staTcpiNetb 1 }

staTcpiNetbLantx OBJECT-TYPE
                  SYNTAX Counter32
                  MAX-ACCESS read-only
                  STATUS current
                  DESCRIPTION "LAN-Tx"
                  ::= {  staTcpiNetb 2 }

staTcpiNetbWanrx OBJECT-TYPE
                  SYNTAX Counter32
                  MAX-ACCESS read-only
                  STATUS current
                  DESCRIPTION "WAN-Rx"
                  ::= {  staTcpiNetb 3 }

staTcpiNetbWantx OBJECT-TYPE
                  SYNTAX Counter32
                  MAX-ACCESS read-only
                  STATUS current
                  DESCRIPTION "WAN-Tx"
                  ::= {  staTcpiNetb 4 }

staTcpiNetbRegist OBJECT-TYPE
                  SYNTAX Counter32
                  MAX-ACCESS read-only
                  STATUS current
                  DESCRIPTION "Registers"
                  ::= {  staTcpiNetb 5 }

staTcpiNetbConfli OBJECT-TYPE
                  SYNTAX Counter32
                  MAX-ACCESS read-only
                  STATUS current
                  DESCRIPTION "Conflicts"
                  ::= {  staTcpiNetb 6 }

staTcpiNetbReleas OBJECT-TYPE
                  SYNTAX Counter32
                  MAX-ACCESS read-only
                  STATUS current
                  DESCRIPTION "Releases"
                  ::= {  staTcpiNetb 7 }

staTcpiNetbRefres OBJECT-TYPE
                  SYNTAX Counter32
                  MAX-ACCESS read-only
                  STATUS current
                  DESCRIPTION "Refreshs"
                  ::= {  staTcpiNetb 8 }

staTcpiNetbTimeou OBJECT-TYPE
                  SYNTAX Counter32
                  MAX-ACCESS read-only
                  STATUS current
                  DESCRIPTION "Timeouts"
                  ::= {  staTcpiNetb 9 }

staTcpiNetbHosts OBJECT-TYPE
                  SYNTAX INTEGER
                  MAX-ACCESS read-only
                  STATUS current
                  DESCRIPTION "Hosts"
                  ::= {  staTcpiNetb 10 }

staTcpiNetbGroups OBJECT-TYPE
                  SYNTAX INTEGER
                  MAX-ACCESS read-only
                  STATUS current
                  DESCRIPTION "Groups"
                  ::= {  staTcpiNetb 11 }

staTcpiNetbBnodes OBJECT-TYPE
                  SYNTAX INTEGER
                  MAX-ACCESS read-only
                  STATUS current
                  DESCRIPTION "B-Nodes"
                  ::= {  staTcpiNetb 12 }

staTcpiNetbPnodes OBJECT-TYPE
                  SYNTAX INTEGER
                  MAX-ACCESS read-only
                  STATUS current
                  DESCRIPTION "P-Nodes"
                  ::= {  staTcpiNetb 13 }

staTcpiNetbMnodes OBJECT-TYPE
                  SYNTAX INTEGER
                  MAX-ACCESS read-only
                  STATUS current
                  DESCRIPTION "M-Nodes"
                  ::= {  staTcpiNetb 14 }

staTcpiNetbWnodes OBJECT-TYPE
                  SYNTAX INTEGER
                  MAX-ACCESS read-only
                  STATUS current
                  DESCRIPTION "W-Nodes"
                  ::= {  staTcpiNetb 15 }

staTcpiNetbPeersTable OBJECT-TYPE
                       SYNTAX SEQUENCE OF StaTcpiNetbPeersEntry
                       MAX-ACCESS not-accessible
                       STATUS current
                       DESCRIPTION "Peers"
                       ::= {  staTcpiNetb 16 }

staTcpiNetbPeersEntry OBJECT-TYPE
                       SYNTAX StaTcpiNetbPeersEntry
                       MAX-ACCESS not-accessible
                       STATUS current
                       DESCRIPTION "entry in table"
                       INDEX { staTcpiNetbPeersNam }
                       ::= {  staTcpiNetbPeersTable 1 }

StaTcpiNetbPeersEntry ::= SEQUENCE {
                       staTcpiNetbPeersNam DisplayString,
                       staTcpiNetbPeersTyp INTEGER,
                       staTcpiNetbPeersBac INTEGER,
                       staTcpiNetbPeersTim INTEGER
                      }

staTcpiNetbPeersNam OBJECT-TYPE
                    SYNTAX DisplayString (SIZE(0..16))
                    MAX-ACCESS read-only
                    STATUS current
                    DESCRIPTION "Name"
                    ::= {  staTcpiNetbPeersEntry 1 }

staTcpiNetbPeersTyp OBJECT-TYPE
                    SYNTAX INTEGER
                    {
                      workstation(1),
                      router(0)
                    }
                    MAX-ACCESS read-only
                    STATUS current
                    DESCRIPTION "Type"
                    ::= {  staTcpiNetbPeersEntry 2 }

staTcpiNetbPeersBac OBJECT-TYPE
                    SYNTAX INTEGER (0..255)
                    MAX-ACCESS read-only
                    STATUS current
                    DESCRIPTION "Backoff"
                    ::= {  staTcpiNetbPeersEntry 3 }

staTcpiNetbPeersTim OBJECT-TYPE
                    SYNTAX INTEGER (0..65535)
                    MAX-ACCESS read-only
                    STATUS current
                    DESCRIPTION "Time"
                    ::= {  staTcpiNetbPeersEntry 4 }

staTcpiNetbNetworTable OBJECT-TYPE
                       SYNTAX SEQUENCE OF StaTcpiNetbNetworEntry
                       MAX-ACCESS not-accessible
                       STATUS current
                       DESCRIPTION "Networks"
                       ::= {  staTcpiNetb 18 }

staTcpiNetbNetworEntry OBJECT-TYPE
                       SYNTAX StaTcpiNetbNetworEntry
                       MAX-ACCESS not-accessible
                       STATUS current
                       DESCRIPTION "entry in table"
                       INDEX { staTcpiNetbNetworNet }
                       ::= {  staTcpiNetbNetworTable 1 }

StaTcpiNetbNetworEntry ::= SEQUENCE {
                       staTcpiNetbNetworNet DisplayString,
                       staTcpiNetbNetworNtd DisplayString,
                       staTcpiNetbNetworRtg INTEGER,
                       staTcpiNetbNetworInt INTEGER,
                       staTcpiNetbNetworVla INTEGER
                      }

staTcpiNetbNetworNet OBJECT-TYPE
                     SYNTAX DisplayString (SIZE(0..16))
                     MAX-ACCESS read-only
                     STATUS current
                     DESCRIPTION "Network-name"
                     ::= {  staTcpiNetbNetworEntry 1 }

staTcpiNetbNetworNtd OBJECT-TYPE
                     SYNTAX DisplayString (SIZE(0..15))
                     MAX-ACCESS read-only
                     STATUS current
                     DESCRIPTION "NT-Domain"
                     ::= {  staTcpiNetbNetworEntry 2 }

staTcpiNetbNetworRtg OBJECT-TYPE
                     SYNTAX INTEGER (0..65535)
                     MAX-ACCESS read-only
                     STATUS current
                     DESCRIPTION "Rtg-tag"
                     ::= {  staTcpiNetbNetworEntry 3 }

staTcpiNetbNetworInt OBJECT-TYPE
                     SYNTAX INTEGER
                     {
                       lan-1(0),
                       lan-2(1),
                       lan-3(2),
                       lan-4(3),
                       any(255)
                     }
                     MAX-ACCESS read-only
                     STATUS current
                     DESCRIPTION "Interface"
                     ::= {  staTcpiNetbNetworEntry 4 }

staTcpiNetbNetworVla OBJECT-TYPE
                     SYNTAX INTEGER (0..65535)
                     MAX-ACCESS read-only
                     STATUS current
                     DESCRIPTION "VLAN-ID"
                     ::= {  staTcpiNetbNetworEntry 5 }

staTcpiNetbGrouplTable OBJECT-TYPE
                       SYNTAX SEQUENCE OF StaTcpiNetbGrouplEntry
                       MAX-ACCESS not-accessible
                       STATUS current
                       DESCRIPTION "Group-List"
                       ::= {  staTcpiNetb 19 }

staTcpiNetbGrouplEntry OBJECT-TYPE
                       SYNTAX StaTcpiNetbGrouplEntry
                       MAX-ACCESS not-accessible
                       STATUS current
                       DESCRIPTION "entry in table"
                       INDEX { staTcpiNetbGrouplGro, staTcpiNetbGrouplTyp, staTcpiNetbGrouplIpa, staTcpiNetbGrouplRtg }
                       ::= {  staTcpiNetbGrouplTable 1 }

StaTcpiNetbGrouplEntry ::= SEQUENCE {
                       staTcpiNetbGrouplGro DisplayString,
                       staTcpiNetbGrouplTyp DisplayString,
                       staTcpiNetbGrouplIpa IpAddress,
                       staTcpiNetbGrouplRtg INTEGER,
                       staTcpiNetbGrouplPee DisplayString,
                       staTcpiNetbGrouplNet DisplayString,
                       staTcpiNetbGrouplTim INTEGER,
                       staTcpiNetbGrouplFla DisplayString
                      }

staTcpiNetbGrouplGro OBJECT-TYPE
                     SYNTAX DisplayString (SIZE(0..15))
                     MAX-ACCESS read-only
                     STATUS current
                     DESCRIPTION "Group/Domain"
                     ::= {  staTcpiNetbGrouplEntry 1 }

staTcpiNetbGrouplTyp OBJECT-TYPE
                     SYNTAX DisplayString (SIZE(0..1))
                     MAX-ACCESS read-only
                     STATUS current
                     DESCRIPTION "Type"
                     ::= {  staTcpiNetbGrouplEntry 2 }

staTcpiNetbGrouplIpa OBJECT-TYPE
                     SYNTAX IpAddress
                     MAX-ACCESS read-only
                     STATUS current
                     DESCRIPTION "IP-Address"
                     ::= {  staTcpiNetbGrouplEntry 3 }

staTcpiNetbGrouplRtg OBJECT-TYPE
                     SYNTAX INTEGER (0..65535)
                     MAX-ACCESS read-only
                     STATUS current
                     DESCRIPTION "Rtg-tag"
                     ::= {  staTcpiNetbGrouplEntry 8 }

staTcpiNetbGrouplPee OBJECT-TYPE
                     SYNTAX DisplayString (SIZE(0..16))
                     MAX-ACCESS read-only
                     STATUS current
                     DESCRIPTION "Peer"
                     ::= {  staTcpiNetbGrouplEntry 4 }

staTcpiNetbGrouplNet OBJECT-TYPE
                     SYNTAX DisplayString (SIZE(0..16))
                     MAX-ACCESS read-only
                     STATUS current
                     DESCRIPTION "Network-name"
                     ::= {  staTcpiNetbGrouplEntry 7 }

staTcpiNetbGrouplTim OBJECT-TYPE
                     SYNTAX INTEGER (0..2147483647)
                     MAX-ACCESS read-only
                     STATUS current
                     DESCRIPTION "Timeout"
                     ::= {  staTcpiNetbGrouplEntry 5 }

staTcpiNetbGrouplFla OBJECT-TYPE
                     SYNTAX DisplayString (SIZE(0..2))
                     MAX-ACCESS read-only
                     STATUS current
                     DESCRIPTION "Flags"
                     ::= {  staTcpiNetbGrouplEntry 6 }

staTcpiNetbHostliTable OBJECT-TYPE
                       SYNTAX SEQUENCE OF StaTcpiNetbHostliEntry
                       MAX-ACCESS not-accessible
                       STATUS current
                       DESCRIPTION "Host-List"
                       ::= {  staTcpiNetb 20 }

staTcpiNetbHostliEntry OBJECT-TYPE
                       SYNTAX StaTcpiNetbHostliEntry
                       MAX-ACCESS not-accessible
                       STATUS current
                       DESCRIPTION "entry in table"
                       INDEX { staTcpiNetbHostliNam, staTcpiNetbHostliTyp, staTcpiNetbHostliIpa, staTcpiNetbHostliRtg }
                       ::= {  staTcpiNetbHostliTable 1 }

StaTcpiNetbHostliEntry ::= SEQUENCE {
                       staTcpiNetbHostliNam DisplayString,
                       staTcpiNetbHostliTyp DisplayString,
                       staTcpiNetbHostliIpa IpAddress,
                       staTcpiNetbHostliRtg INTEGER,
                       staTcpiNetbHostliPee DisplayString,
                       staTcpiNetbHostliNet DisplayString,
                       staTcpiNetbHostliTim INTEGER,
                       staTcpiNetbHostliFla DisplayString
                      }

staTcpiNetbHostliNam OBJECT-TYPE
                     SYNTAX DisplayString (SIZE(0..15))
                     MAX-ACCESS read-only
                     STATUS current
                     DESCRIPTION "Name"
                     ::= {  staTcpiNetbHostliEntry 1 }

staTcpiNetbHostliTyp OBJECT-TYPE
                     SYNTAX DisplayString (SIZE(0..1))
                     MAX-ACCESS read-only
                     STATUS current
                     DESCRIPTION "Type"
                     ::= {  staTcpiNetbHostliEntry 2 }

staTcpiNetbHostliIpa OBJECT-TYPE
                     SYNTAX IpAddress
                     MAX-ACCESS read-only
                     STATUS current
                     DESCRIPTION "IP-Address"
                     ::= {  staTcpiNetbHostliEntry 3 }

staTcpiNetbHostliRtg OBJECT-TYPE
                     SYNTAX INTEGER (0..65535)
                     MAX-ACCESS read-only
                     STATUS current
                     DESCRIPTION "Rtg-tag"
                     ::= {  staTcpiNetbHostliEntry 8 }

staTcpiNetbHostliPee OBJECT-TYPE
                     SYNTAX DisplayString (SIZE(0..16))
                     MAX-ACCESS read-only
                     STATUS current
                     DESCRIPTION "Peer"
                     ::= {  staTcpiNetbHostliEntry 4 }

staTcpiNetbHostliNet OBJECT-TYPE
                     SYNTAX DisplayString (SIZE(0..16))
                     MAX-ACCESS read-only
                     STATUS current
                     DESCRIPTION "Network-name"
                     ::= {  staTcpiNetbHostliEntry 7 }

staTcpiNetbHostliTim OBJECT-TYPE
                     SYNTAX INTEGER (0..2147483647)
                     MAX-ACCESS read-only
                     STATUS current
                     DESCRIPTION "Timeout"
                     ::= {  staTcpiNetbHostliEntry 5 }

staTcpiNetbHostliFla OBJECT-TYPE
                     SYNTAX DisplayString (SIZE(0..2))
                     MAX-ACCESS read-only
                     STATUS current
                     DESCRIPTION "Flags"
                     ::= {  staTcpiNetbHostliEntry 6 }

staTcpiNetbServerTable OBJECT-TYPE
                       SYNTAX SEQUENCE OF StaTcpiNetbServerEntry
                       MAX-ACCESS not-accessible
                       STATUS current
                       DESCRIPTION "Server-List"
                       ::= {  staTcpiNetb 21 }

staTcpiNetbServerEntry OBJECT-TYPE
                       SYNTAX StaTcpiNetbServerEntry
                       MAX-ACCESS not-accessible
                       STATUS current
                       DESCRIPTION "entry in table"
                       INDEX { staTcpiNetbServerHos, staTcpiNetbServerGro, staTcpiNetbServerIpa, staTcpiNetbServerRtg }
                       ::= {  staTcpiNetbServerTable 1 }

StaTcpiNetbServerEntry ::= SEQUENCE {
                       staTcpiNetbServerHos DisplayString,
                       staTcpiNetbServerGro DisplayString,
                       staTcpiNetbServerIpa DisplayString,
                       staTcpiNetbServerRtg INTEGER,
                       staTcpiNetbServerOsv DisplayString,
                       staTcpiNetbServerSmb DisplayString,
                       staTcpiNetbServerSer DisplayString,
                       staTcpiNetbServerPee DisplayString,
                       staTcpiNetbServerNet DisplayString,
                       staTcpiNetbServerTim INTEGER,
                       staTcpiNetbServerFla DisplayString
                      }

staTcpiNetbServerHos OBJECT-TYPE
                     SYNTAX DisplayString (SIZE(0..15))
                     MAX-ACCESS read-only
                     STATUS current
                     DESCRIPTION "Host"
                     ::= {  staTcpiNetbServerEntry 1 }

staTcpiNetbServerGro OBJECT-TYPE
                     SYNTAX DisplayString (SIZE(0..16))
                     MAX-ACCESS read-only
                     STATUS current
                     DESCRIPTION "Group/Domain"
                     ::= {  staTcpiNetbServerEntry 2 }

staTcpiNetbServerIpa OBJECT-TYPE
                     SYNTAX DisplayString (SIZE(0..15))
                     MAX-ACCESS read-only
                     STATUS current
                     DESCRIPTION "IP-Address"
                     ::= {  staTcpiNetbServerEntry 4 }

staTcpiNetbServerRtg OBJECT-TYPE
                     SYNTAX INTEGER (0..65535)
                     MAX-ACCESS read-only
                     STATUS current
                     DESCRIPTION "Rtg-tag"
                     ::= {  staTcpiNetbServerEntry 12 }

staTcpiNetbServerOsv OBJECT-TYPE
                     SYNTAX DisplayString (SIZE(0..2))
                     MAX-ACCESS read-only
                     STATUS current
                     DESCRIPTION "OS-Ver."
                     ::= {  staTcpiNetbServerEntry 5 }

staTcpiNetbServerSmb OBJECT-TYPE
                     SYNTAX DisplayString (SIZE(0..2))
                     MAX-ACCESS read-only
                     STATUS current
                     DESCRIPTION "SMB-Ver."
                     ::= {  staTcpiNetbServerEntry 6 }

staTcpiNetbServerSer OBJECT-TYPE
                     SYNTAX DisplayString (SIZE(0..4))
                     MAX-ACCESS read-only
                     STATUS current
                     DESCRIPTION "Server-Typ"
                     ::= {  staTcpiNetbServerEntry 7 }

staTcpiNetbServerPee OBJECT-TYPE
                     SYNTAX DisplayString (SIZE(0..16))
                     MAX-ACCESS read-only
                     STATUS current
                     DESCRIPTION "Peer"
                     ::= {  staTcpiNetbServerEntry 8 }

staTcpiNetbServerNet OBJECT-TYPE
                     SYNTAX DisplayString (SIZE(0..16))
                     MAX-ACCESS read-only
                     STATUS current
                     DESCRIPTION "Network-name"
                     ::= {  staTcpiNetbServerEntry 11 }

staTcpiNetbServerTim OBJECT-TYPE
                     SYNTAX INTEGER (0..2147483647)
                     MAX-ACCESS read-only
                     STATUS current
                     DESCRIPTION "Timeout"
                     ::= {  staTcpiNetbServerEntry 9 }

staTcpiNetbServerFla OBJECT-TYPE
                     SYNTAX DisplayString (SIZE(0..2))
                     MAX-ACCESS read-only
                     STATUS current
                     DESCRIPTION "Flags"
                     ::= {  staTcpiNetbServerEntry 10 }

staTcpiNetbBrowseTable OBJECT-TYPE
                       SYNTAX SEQUENCE OF StaTcpiNetbBrowseEntry
                       MAX-ACCESS not-accessible
                       STATUS current
                       DESCRIPTION "Browser-List"
                       ::= {  staTcpiNetb 22 }

staTcpiNetbBrowseEntry OBJECT-TYPE
                       SYNTAX StaTcpiNetbBrowseEntry
                       MAX-ACCESS not-accessible
                       STATUS current
                       DESCRIPTION "entry in table"
                       INDEX { staTcpiNetbBrowseBro, staTcpiNetbBrowseGro, staTcpiNetbBrowseIpa, staTcpiNetbBrowseRtg }
                       ::= {  staTcpiNetbBrowseTable 1 }

StaTcpiNetbBrowseEntry ::= SEQUENCE {
                       staTcpiNetbBrowseBro DisplayString,
                       staTcpiNetbBrowseGro DisplayString,
                       staTcpiNetbBrowseIpa DisplayString,
                       staTcpiNetbBrowseRtg INTEGER,
                       staTcpiNetbBrowseOsv DisplayString,
                       staTcpiNetbBrowseSer DisplayString,
                       staTcpiNetbBrowsePee DisplayString,
                       staTcpiNetbBrowseNet DisplayString,
                       staTcpiNetbBrowseTim INTEGER,
                       staTcpiNetbBrowseFla DisplayString
                      }

staTcpiNetbBrowseBro OBJECT-TYPE
                     SYNTAX DisplayString (SIZE(0..15))
                     MAX-ACCESS read-only
                     STATUS current
                     DESCRIPTION "Browser"
                     ::= {  staTcpiNetbBrowseEntry 1 }

staTcpiNetbBrowseGro OBJECT-TYPE
                     SYNTAX DisplayString (SIZE(0..16))
                     MAX-ACCESS read-only
                     STATUS current
                     DESCRIPTION "Group/Domain"
                     ::= {  staTcpiNetbBrowseEntry 2 }

staTcpiNetbBrowseIpa OBJECT-TYPE
                     SYNTAX DisplayString (SIZE(0..15))
                     MAX-ACCESS read-only
                     STATUS current
                     DESCRIPTION "IP-Address"
                     ::= {  staTcpiNetbBrowseEntry 4 }

staTcpiNetbBrowseRtg OBJECT-TYPE
                     SYNTAX INTEGER (0..65535)
                     MAX-ACCESS read-only
                     STATUS current
                     DESCRIPTION "Rtg-tag"
                     ::= {  staTcpiNetbBrowseEntry 12 }

staTcpiNetbBrowseOsv OBJECT-TYPE
                     SYNTAX DisplayString (SIZE(0..2))
                     MAX-ACCESS read-only
                     STATUS current
                     DESCRIPTION "OS-Ver."
                     ::= {  staTcpiNetbBrowseEntry 5 }

staTcpiNetbBrowseSer OBJECT-TYPE
                     SYNTAX DisplayString (SIZE(0..4))
                     MAX-ACCESS read-only
                     STATUS current
                     DESCRIPTION "Server-Typ"
                     ::= {  staTcpiNetbBrowseEntry 7 }

staTcpiNetbBrowsePee OBJECT-TYPE
                     SYNTAX DisplayString (SIZE(0..16))
                     MAX-ACCESS read-only
                     STATUS current
                     DESCRIPTION "Peer"
                     ::= {  staTcpiNetbBrowseEntry 8 }

staTcpiNetbBrowseNet OBJECT-TYPE
                     SYNTAX DisplayString (SIZE(0..16))
                     MAX-ACCESS read-only
                     STATUS current
                     DESCRIPTION "Network-name"
                     ::= {  staTcpiNetbBrowseEntry 11 }

staTcpiNetbBrowseTim OBJECT-TYPE
                     SYNTAX INTEGER (0..2147483647)
                     MAX-ACCESS read-only
                     STATUS current
                     DESCRIPTION "Timeout"
                     ::= {  staTcpiNetbBrowseEntry 9 }

staTcpiNetbBrowseFla OBJECT-TYPE
                     SYNTAX DisplayString (SIZE(0..2))
                     MAX-ACCESS read-only
                     STATUS current
                     DESCRIPTION "Flags"
                     ::= {  staTcpiNetbBrowseEntry 10 }

staTcpiNetbDelete OBJECT-TYPE
                  SYNTAX DisplayString
                  MAX-ACCESS read-write
                  STATUS current
                  DESCRIPTION "Delete-Values"
                  ::= {  staTcpiNetb 17 }

staTcpiDns OBJECT IDENTIFIER ::= { staTcpi 9}
staTcpiDnsLanr OBJECT-TYPE
               SYNTAX Counter32
               MAX-ACCESS read-only
               STATUS current
               DESCRIPTION "LAN-Rx"
               ::= {  staTcpiDns 1 }

staTcpiDnsLant OBJECT-TYPE
               SYNTAX Counter32
               MAX-ACCESS read-only
               STATUS current
               DESCRIPTION "LAN-Tx"
               ::= {  staTcpiDns 2 }

staTcpiDnsWanr OBJECT-TYPE
               SYNTAX Counter32
               MAX-ACCESS read-only
               STATUS current
               DESCRIPTION "WAN-Rx"
               ::= {  staTcpiDns 3 }

staTcpiDnsWant OBJECT-TYPE
               SYNTAX Counter32
               MAX-ACCESS read-only
               STATUS current
               DESCRIPTION "WAN-Tx"
               ::= {  staTcpiDns 4 }

staTcpiDnsForw OBJECT-TYPE
               SYNTAX Counter32
               MAX-ACCESS read-only
               STATUS current
               DESCRIPTION "Forwarded"
               ::= {  staTcpiDns 5 }

staTcpiDnsErro OBJECT-TYPE
               SYNTAX Counter32
               MAX-ACCESS read-only
               STATUS current
               DESCRIPTION "Errors"
               ::= {  staTcpiDns 6 }

staTcpiDnsDnsa OBJECT-TYPE
               SYNTAX Counter32
               MAX-ACCESS read-only
               STATUS current
               DESCRIPTION "DNS-Access"
               ::= {  staTcpiDns 7 }

staTcpiDnsDhcp OBJECT-TYPE
               SYNTAX Counter32
               MAX-ACCESS read-only
               STATUS current
               DESCRIPTION "DHCP-Access"
               ::= {  staTcpiDns 8 }

staTcpiDnsNetb OBJECT-TYPE
               SYNTAX Counter32
               MAX-ACCESS read-only
               STATUS current
               DESCRIPTION "NetBIOS-Access"
               ::= {  staTcpiDns 9 }

staTcpiDnsFilt OBJECT-TYPE
               SYNTAX Counter32
               MAX-ACCESS read-only
               STATUS current
               DESCRIPTION "Filter"
               ::= {  staTcpiDns 10 }

staTcpiDnsHitlTable OBJECT-TYPE
                    SYNTAX SEQUENCE OF StaTcpiDnsHitlEntry
                    MAX-ACCESS not-accessible
                    STATUS current
                    DESCRIPTION "Hit-List"
                    ::= {  staTcpiDns 11 }

staTcpiDnsHitlEntry OBJECT-TYPE
                    SYNTAX StaTcpiDnsHitlEntry
                    MAX-ACCESS not-accessible
                    STATUS current
                    DESCRIPTION "entry in table"
                    INDEX { staTcpiDnsHitlDom }
                    ::= {  staTcpiDnsHitlTable 1 }

StaTcpiDnsHitlEntry ::= SEQUENCE {
                    staTcpiDnsHitlDom DisplayString,
                    staTcpiDnsHitlReq INTEGER,
                    staTcpiDnsHitlTim DisplayString,
                    staTcpiDnsHitlIpa IpAddress
                   }

staTcpiDnsHitlDom OBJECT-TYPE
                  SYNTAX DisplayString (SIZE(0..64))
                  MAX-ACCESS read-only
                  STATUS current
                  DESCRIPTION "Domain"
                  ::= {  staTcpiDnsHitlEntry 1 }

staTcpiDnsHitlReq OBJECT-TYPE
                  SYNTAX INTEGER (0..2147483647)
                  MAX-ACCESS read-only
                  STATUS current
                  DESCRIPTION "Requests"
                  ::= {  staTcpiDnsHitlEntry 2 }

staTcpiDnsHitlTim OBJECT-TYPE
                  SYNTAX DisplayString (SIZE(0..20))
                  MAX-ACCESS read-only
                  STATUS current
                  DESCRIPTION "Time"
                  ::= {  staTcpiDnsHitlEntry 3 }

staTcpiDnsHitlIpa OBJECT-TYPE
                  SYNTAX IpAddress
                  MAX-ACCESS read-only
                  STATUS current
                  DESCRIPTION "IP-Address"
                  ::= {  staTcpiDnsHitlEntry 4 }

staTcpiDnsDele OBJECT-TYPE
               SYNTAX DisplayString
               MAX-ACCESS read-write
               STATUS current
               DESCRIPTION "Delete-Values"
               ::= {  staTcpiDns 12 }

staTcpiHttp OBJECT IDENTIFIER ::= { staTcpi 10}
staTcpiHttpHttpac OBJECT-TYPE
                  SYNTAX Counter32
                  MAX-ACCESS read-only
                  STATUS current
                  DESCRIPTION "HTTP-Accesses"
                  ::= {  staTcpiHttp 1 }

staTcpiHttpHttpsa OBJECT-TYPE
                  SYNTAX Counter32
                  MAX-ACCESS read-only
                  STATUS current
                  DESCRIPTION "HTTPS-Accesses"
                  ::= {  staTcpiHttp 6 }

staTcpiHttpHttpno OBJECT-TYPE
                  SYNTAX Counter32
                  MAX-ACCESS read-only
                  STATUS current
                  DESCRIPTION "HTTP-Notfound-Errors"
                  ::= {  staTcpiHttp 2 }

staTcpiHttpHttpau OBJECT-TYPE
                  SYNTAX Counter32
                  MAX-ACCESS read-only
                  STATUS current
                  DESCRIPTION "HTTP-Authentication-Errors"
                  ::= {  staTcpiHttp 3 }

staTcpiHttpHttppr OBJECT-TYPE
                  SYNTAX Counter32
                  MAX-ACCESS read-only
                  STATUS current
                  DESCRIPTION "HTTP-Protocol-Errors"
                  ::= {  staTcpiHttp 4 }

staTcpiHttpAgentlTable OBJECT-TYPE
                       SYNTAX SEQUENCE OF StaTcpiHttpAgentlEntry
                       MAX-ACCESS not-accessible
                       STATUS current
                       DESCRIPTION "Agent-List"
                       ::= {  staTcpiHttp 7 }

staTcpiHttpAgentlEntry OBJECT-TYPE
                       SYNTAX StaTcpiHttpAgentlEntry
                       MAX-ACCESS not-accessible
                       STATUS current
                       DESCRIPTION "entry in table"
                       INDEX { staTcpiHttpAgentlAge }
                       ::= {  staTcpiHttpAgentlTable 1 }

StaTcpiHttpAgentlEntry ::= SEQUENCE {
                       staTcpiHttpAgentlAge DisplayString,
                       staTcpiHttpAgentlAcc INTEGER
                      }

staTcpiHttpAgentlAge OBJECT-TYPE
                     SYNTAX DisplayString (SIZE(0..67))
                     MAX-ACCESS read-only
                     STATUS current
                     DESCRIPTION "Agent-Name"
                     ::= {  staTcpiHttpAgentlEntry 1 }

staTcpiHttpAgentlAcc OBJECT-TYPE
                     SYNTAX INTEGER (0..2147483647)
                     MAX-ACCESS read-only
                     STATUS current
                     DESCRIPTION "Accesses"
                     ::= {  staTcpiHttpAgentlEntry 2 }

staTcpiHttpDelete OBJECT-TYPE
                  SYNTAX DisplayString
                  MAX-ACCESS read-write
                  STATUS current
                  DESCRIPTION "Delete-Values"
                  ::= {  staTcpiHttp 5 }

staTcpiHttpActiveTable OBJECT-TYPE
                       SYNTAX SEQUENCE OF StaTcpiHttpActiveEntry
                       MAX-ACCESS not-accessible
                       STATUS current
                       DESCRIPTION "Active-Tunnels"
                       ::= {  staTcpiHttp 8 }

staTcpiHttpActiveEntry OBJECT-TYPE
                       SYNTAX StaTcpiHttpActiveEntry
                       MAX-ACCESS not-accessible
                       STATUS current
                       DESCRIPTION "entry in table"
                       INDEX { staTcpiHttpActiveIndex }
                       ::= {  staTcpiHttpActiveTable 1 }

StaTcpiHttpActiveEntry ::= SEQUENCE {
                       staTcpiHttpActiveIndex INTEGER,
                       staTcpiHttpActiveRemotea IpAddress,
                       staTcpiHttpActiveRemotep INTEGER,
                       staTcpiHttpActiveLocalho DisplayString,
                       staTcpiHttpActiveLocalpo INTEGER,
                       staTcpiHttpActiveLocalrt INTEGER,
                       staTcpiHttpActiveIdletim INTEGER,
                       staTcpiHttpActiveNumconn INTEGER
                      }

staTcpiHttpActiveIndex OBJECT-TYPE
                         SYNTAX INTEGER (0..2147483647)
                         MAX-ACCESS read-only
                         STATUS current
                         DESCRIPTION "Index"
                         ::= {  staTcpiHttpActiveEntry 1 }

staTcpiHttpActiveRemotea OBJECT-TYPE
                         SYNTAX IpAddress
                         MAX-ACCESS read-only
                         STATUS current
                         DESCRIPTION "Remote-Address"
                         ::= {  staTcpiHttpActiveEntry 2 }

staTcpiHttpActiveRemotep OBJECT-TYPE
                         SYNTAX INTEGER (0..65535)
                         MAX-ACCESS read-only
                         STATUS current
                         DESCRIPTION "Remote-Port"
                         ::= {  staTcpiHttpActiveEntry 3 }

staTcpiHttpActiveLocalho OBJECT-TYPE
                         SYNTAX DisplayString (SIZE(0..48))
                         MAX-ACCESS read-only
                         STATUS current
                         DESCRIPTION "Local-Host"
                         ::= {  staTcpiHttpActiveEntry 4 }

staTcpiHttpActiveLocalpo OBJECT-TYPE
                         SYNTAX INTEGER (0..65535)
                         MAX-ACCESS read-only
                         STATUS current
                         DESCRIPTION "Local-Port"
                         ::= {  staTcpiHttpActiveEntry 5 }

staTcpiHttpActiveLocalrt OBJECT-TYPE
                         SYNTAX INTEGER (0..65535)
                         MAX-ACCESS read-only
                         STATUS current
                         DESCRIPTION "Local-Rtg-Tag"
                         ::= {  staTcpiHttpActiveEntry 7 }

staTcpiHttpActiveIdletim OBJECT-TYPE
                         SYNTAX INTEGER (0..2147483647)
                         MAX-ACCESS read-only
                         STATUS current
                         DESCRIPTION "Idle-Time"
                         ::= {  staTcpiHttpActiveEntry 6 }

staTcpiHttpActiveNumconn OBJECT-TYPE
                         SYNTAX INTEGER (0..2147483647)
                         MAX-ACCESS read-only
                         STATUS current
                         DESCRIPTION "Num-Connections"
                         ::= {  staTcpiHttpActiveEntry 8 }

staTcpiNetwTable OBJECT-TYPE
                 SYNTAX SEQUENCE OF StaTcpiNetwEntry
                 MAX-ACCESS not-accessible
                 STATUS current
                 DESCRIPTION "Network-list"
                 ::= {  staTcpi 20 }

staTcpiNetwEntry OBJECT-TYPE
                 SYNTAX StaTcpiNetwEntry
                 MAX-ACCESS not-accessible
                 STATUS current
                 DESCRIPTION "entry in table"
                 INDEX { staTcpiNetwNet }
                 ::= {  staTcpiNetwTable 1 }

StaTcpiNetwEntry ::= SEQUENCE {
                 staTcpiNetwNet DisplayString,
                 staTcpiNetwIpa IpAddress,
                 staTcpiNetwIpn IpAddress,
                 staTcpiNetwVla INTEGER,
                 staTcpiNetwInt INTEGER,
                 staTcpiNetwSrc INTEGER,
                 staTcpiNetwTyp INTEGER,
                 staTcpiNetwRtg INTEGER
                }

staTcpiNetwNet OBJECT-TYPE
               SYNTAX DisplayString (SIZE(0..17))
               MAX-ACCESS read-only
               STATUS current
               DESCRIPTION "Network-name"
               ::= {  staTcpiNetwEntry 1 }

staTcpiNetwIpa OBJECT-TYPE
               SYNTAX IpAddress
               MAX-ACCESS read-only
               STATUS current
               DESCRIPTION "IP-Address"
               ::= {  staTcpiNetwEntry 2 }

staTcpiNetwIpn OBJECT-TYPE
               SYNTAX IpAddress
               MAX-ACCESS read-only
               STATUS current
               DESCRIPTION "IP-Netmask"
               ::= {  staTcpiNetwEntry 3 }

staTcpiNetwVla OBJECT-TYPE
               SYNTAX INTEGER (0..65535)
               MAX-ACCESS read-only
               STATUS current
               DESCRIPTION "VLAN-ID"
               ::= {  staTcpiNetwEntry 4 }

staTcpiNetwInt OBJECT-TYPE
               SYNTAX INTEGER
               {
                 lan-1(256),
                 lan-2(257),
                 lan-3(258),
                 lan-4(259),
                 any(65535)
               }
               MAX-ACCESS read-only
               STATUS current
               DESCRIPTION "Interface"
               ::= {  staTcpiNetwEntry 5 }

staTcpiNetwSrc OBJECT-TYPE
               SYNTAX INTEGER
               {
                 strict(1),
                 loose(0)
               }
               MAX-ACCESS read-only
               STATUS current
               DESCRIPTION "Src-check"
               ::= {  staTcpiNetwEntry 6 }

staTcpiNetwTyp OBJECT-TYPE
               SYNTAX INTEGER
               {
                 disabled(0),
                 intranet(1),
                 dmz(2)
               }
               MAX-ACCESS read-only
               STATUS current
               DESCRIPTION "Type"
               ::= {  staTcpiNetwEntry 7 }

staTcpiNetwRtg OBJECT-TYPE
               SYNTAX INTEGER (0..65535)
               MAX-ACCESS read-only
               STATUS current
               DESCRIPTION "Rtg-tag"
               ::= {  staTcpiNetwEntry 8 }

staTcpiSysl OBJECT IDENTIFIER ::= { staTcpi 11}
staTcpiSyslLasTable OBJECT-TYPE
                    SYNTAX SEQUENCE OF StaTcpiSyslLasEntry
                    MAX-ACCESS not-accessible
                    STATUS current
                    DESCRIPTION "Last-Messages"
                    ::= {  staTcpiSysl 11 }

staTcpiSyslLasEntry OBJECT-TYPE
                    SYNTAX StaTcpiSyslLasEntry
                    MAX-ACCESS not-accessible
                    STATUS current
                    DESCRIPTION "entry in table"
                    INDEX { staTcpiSyslLasIdx }
                    ::= {  staTcpiSyslLasTable 1 }

StaTcpiSyslLasEntry ::= SEQUENCE {
                    staTcpiSyslLasIdx INTEGER,
                    staTcpiSyslLasTim DisplayString,
                    staTcpiSyslLasSou INTEGER,
                    staTcpiSyslLasLev INTEGER,
                    staTcpiSyslLasMes DisplayString
                   }

staTcpiSyslLasIdx OBJECT-TYPE
                  SYNTAX INTEGER (0..2147483647)
                  MAX-ACCESS read-only
                  STATUS current
                  DESCRIPTION "Idx."
                  ::= {  staTcpiSyslLasEntry 1 }

staTcpiSyslLasTim OBJECT-TYPE
                  SYNTAX DisplayString (SIZE(0..21))
                  MAX-ACCESS read-only
                  STATUS current
                  DESCRIPTION "Time"
                  ::= {  staTcpiSyslLasEntry 2 }

staTcpiSyslLasSou OBJECT-TYPE
                  SYNTAX INTEGER
                  {
                    kern(0),
                    user(1),
                    mail(2),
                    daemon(3),
                    auth(4),
                    syslog(5),
                    lpr(6),
                    news(7),
                    uucp(8),
                    cron(9),
                    authpriv(10),
                    local0(16),
                    local1(17),
                    local2(18),
                    local3(19),
                    local4(20),
                    local5(21),
                    local6(22),
                    local7(23)
                  }
                  MAX-ACCESS read-only
                  STATUS current
                  DESCRIPTION "Source"
                  ::= {  staTcpiSyslLasEntry 3 }

staTcpiSyslLasLev OBJECT-TYPE
                  SYNTAX INTEGER
                  {
                    emergency(0),
                    alarm(1),
                    critical(2),
                    error(3),
                    warning(4),
                    notice(5),
                    info(6),
                    debug(7)
                  }
                  MAX-ACCESS read-only
                  STATUS current
                  DESCRIPTION "Level"
                  ::= {  staTcpiSyslLasEntry 4 }

staTcpiSyslLasMes OBJECT-TYPE
                  SYNTAX DisplayString (SIZE(0..127))
                  MAX-ACCESS read-only
                  STATUS current
                  DESCRIPTION "Message"
                  ::= {  staTcpiSyslLasEntry 5 }

staTcpiSyslDel OBJECT-TYPE
               SYNTAX DisplayString
               MAX-ACCESS read-write
               STATUS current
               DESCRIPTION "Delete-Values"
               ::= {  staTcpiSysl 99 }

staTcpiRadi OBJECT IDENTIFIER ::= { staTcpi 13}
staTcpiRadiInvalidau OBJECT-TYPE
                     SYNTAX Counter32
                     MAX-ACCESS read-only
                     STATUS current
                     DESCRIPTION "Invalid-Auth.-Address-Responses"
                     ::= {  staTcpiRadi 1 }

staTcpiRadiAuthenticTable OBJECT-TYPE
                          SYNTAX SEQUENCE OF StaTcpiRadiAuthenticEntry
                          MAX-ACCESS not-accessible
                          STATUS current
                          DESCRIPTION "Authentication-Servers"
                          ::= {  staTcpiRadi 2 }

staTcpiRadiAuthenticEntry OBJECT-TYPE
                          SYNTAX StaTcpiRadiAuthenticEntry
                          MAX-ACCESS not-accessible
                          STATUS current
                          DESCRIPTION "entry in table"
                          INDEX { staTcpiRadiAuthenticIpaddress, staTcpiRadiAuthenticPort }
                          ::= {  staTcpiRadiAuthenticTable 1 }

StaTcpiRadiAuthenticEntry ::= SEQUENCE {
                          staTcpiRadiAuthenticIpaddress IpAddress,
                          staTcpiRadiAuthenticPort INTEGER,
                          staTcpiRadiAuthenticLastreque INTEGER,
                          staTcpiRadiAuthenticRoundtrip Counter32,
                          staTcpiRadiAuthenticAccessreq Counter32,
                          staTcpiRadiAuthenticAccessret Counter32,
                          staTcpiRadiAuthenticAccessacc Counter32,
                          staTcpiRadiAuthenticAccessrej Counter32,
                          staTcpiRadiAuthenticAccesscha Counter32,
                          staTcpiRadiAuthenticMalformed Counter32,
                          staTcpiRadiAuthenticBadauthen Counter32,
                          staTcpiRadiAuthenticPendingre Counter32,
                          staTcpiRadiAuthenticTimeouts Counter32,
                          staTcpiRadiAuthenticUnknownty Counter32,
                          staTcpiRadiAuthenticDropped Counter32
                         }

staTcpiRadiAuthenticIpaddress OBJECT-TYPE
                              SYNTAX IpAddress
                              MAX-ACCESS read-only
                              STATUS current
                              DESCRIPTION "IP-Address"
                              ::= {  staTcpiRadiAuthenticEntry 1 }

staTcpiRadiAuthenticPort OBJECT-TYPE
                              SYNTAX INTEGER (0..65535)
                              MAX-ACCESS read-only
                              STATUS current
                              DESCRIPTION "Port"
                              ::= {  staTcpiRadiAuthenticEntry 2 }

staTcpiRadiAuthenticLastreque OBJECT-TYPE
                              SYNTAX INTEGER (0..2147483647)
                              MAX-ACCESS read-only
                              STATUS current
                              DESCRIPTION "Last-Request"
                              ::= {  staTcpiRadiAuthenticEntry 3 }

staTcpiRadiAuthenticRoundtrip OBJECT-TYPE
                              SYNTAX Counter32
                              MAX-ACCESS read-only
                              STATUS current
                              DESCRIPTION "Round-Trip-Time"
                              ::= {  staTcpiRadiAuthenticEntry 4 }

staTcpiRadiAuthenticAccessreq OBJECT-TYPE
                              SYNTAX Counter32
                              MAX-ACCESS read-only
                              STATUS current
                              DESCRIPTION "Access-Requests"
                              ::= {  staTcpiRadiAuthenticEntry 5 }

staTcpiRadiAuthenticAccessret OBJECT-TYPE
                              SYNTAX Counter32
                              MAX-ACCESS read-only
                              STATUS current
                              DESCRIPTION "Access-Retransmits"
                              ::= {  staTcpiRadiAuthenticEntry 6 }

staTcpiRadiAuthenticAccessacc OBJECT-TYPE
                              SYNTAX Counter32
                              MAX-ACCESS read-only
                              STATUS current
                              DESCRIPTION "Access-Accepts"
                              ::= {  staTcpiRadiAuthenticEntry 7 }

staTcpiRadiAuthenticAccessrej OBJECT-TYPE
                              SYNTAX Counter32
                              MAX-ACCESS read-only
                              STATUS current
                              DESCRIPTION "Access-Rejects"
                              ::= {  staTcpiRadiAuthenticEntry 8 }

staTcpiRadiAuthenticAccesscha OBJECT-TYPE
                              SYNTAX Counter32
                              MAX-ACCESS read-only
                              STATUS current
                              DESCRIPTION "Access-Challenges"
                              ::= {  staTcpiRadiAuthenticEntry 9 }

staTcpiRadiAuthenticMalformed OBJECT-TYPE
                              SYNTAX Counter32
                              MAX-ACCESS read-only
                              STATUS current
                              DESCRIPTION "Malformed-Access-Responses"
                              ::= {  staTcpiRadiAuthenticEntry 10 }

staTcpiRadiAuthenticBadauthen OBJECT-TYPE
                              SYNTAX Counter32
                              MAX-ACCESS read-only
                              STATUS current
                              DESCRIPTION "Bad-Authenticators"
                              ::= {  staTcpiRadiAuthenticEntry 11 }

staTcpiRadiAuthenticPendingre OBJECT-TYPE
                              SYNTAX Counter32
                              MAX-ACCESS read-only
                              STATUS current
                              DESCRIPTION "Pending-Requests"
                              ::= {  staTcpiRadiAuthenticEntry 12 }

staTcpiRadiAuthenticTimeouts OBJECT-TYPE
                              SYNTAX Counter32
                              MAX-ACCESS read-only
                              STATUS current
                              DESCRIPTION "Timeouts"
                              ::= {  staTcpiRadiAuthenticEntry 13 }

staTcpiRadiAuthenticUnknownty OBJECT-TYPE
                              SYNTAX Counter32
                              MAX-ACCESS read-only
                              STATUS current
                              DESCRIPTION "Unknown-Types"
                              ::= {  staTcpiRadiAuthenticEntry 14 }

staTcpiRadiAuthenticDropped OBJECT-TYPE
                              SYNTAX Counter32
                              MAX-ACCESS read-only
                              STATUS current
                              DESCRIPTION "Dropped"
                              ::= {  staTcpiRadiAuthenticEntry 15 }

staTcpiRadiInvalidac OBJECT-TYPE
                     SYNTAX Counter32
                     MAX-ACCESS read-only
                     STATUS current
                     DESCRIPTION "Invalid-Accnt.-Address-Responses"
                     ::= {  staTcpiRadi 11 }

staTcpiRadiAccountinTable OBJECT-TYPE
                          SYNTAX SEQUENCE OF StaTcpiRadiAccountinEntry
                          MAX-ACCESS not-accessible
                          STATUS current
                          DESCRIPTION "Accounting-Servers"
                          ::= {  staTcpiRadi 12 }

staTcpiRadiAccountinEntry OBJECT-TYPE
                          SYNTAX StaTcpiRadiAccountinEntry
                          MAX-ACCESS not-accessible
                          STATUS current
                          DESCRIPTION "entry in table"
                          INDEX { staTcpiRadiAccountinIpaddress, staTcpiRadiAccountinPort }
                          ::= {  staTcpiRadiAccountinTable 1 }

StaTcpiRadiAccountinEntry ::= SEQUENCE {
                          staTcpiRadiAccountinIpaddress IpAddress,
                          staTcpiRadiAccountinPort INTEGER,
                          staTcpiRadiAccountinLastrequest INTEGER,
                          staTcpiRadiAccountinRoundtriptime Counter32,
                          staTcpiRadiAccountinAccountingreq Counter32,
                          staTcpiRadiAccountinAccountingret Counter32,
                          staTcpiRadiAccountinAccountingres Counter32,
                          staTcpiRadiAccountinMalformedacco Counter32,
                          staTcpiRadiAccountinBadauthentica Counter32,
                          staTcpiRadiAccountinPendingreques Counter32,
                          staTcpiRadiAccountinTimeouts Counter32,
                          staTcpiRadiAccountinUnknowntypes Counter32,
                          staTcpiRadiAccountinDropped Counter32
                         }

staTcpiRadiAccountinIpaddress OBJECT-TYPE
                                  SYNTAX IpAddress
                                  MAX-ACCESS read-only
                                  STATUS current
                                  DESCRIPTION "IP-Address"
                                  ::= {  staTcpiRadiAccountinEntry 1 }

staTcpiRadiAccountinPort OBJECT-TYPE
                                  SYNTAX INTEGER (0..65535)
                                  MAX-ACCESS read-only
                                  STATUS current
                                  DESCRIPTION "Port"
                                  ::= {  staTcpiRadiAccountinEntry 2 }

staTcpiRadiAccountinLastrequest OBJECT-TYPE
                                  SYNTAX INTEGER (0..2147483647)
                                  MAX-ACCESS read-only
                                  STATUS current
                                  DESCRIPTION "Last-Request"
                                  ::= {  staTcpiRadiAccountinEntry 3 }

staTcpiRadiAccountinRoundtriptime OBJECT-TYPE
                                  SYNTAX Counter32
                                  MAX-ACCESS read-only
                                  STATUS current
                                  DESCRIPTION "Round-Trip-Time"
                                  ::= {  staTcpiRadiAccountinEntry 4 }

staTcpiRadiAccountinAccountingreq OBJECT-TYPE
                                  SYNTAX Counter32
                                  MAX-ACCESS read-only
                                  STATUS current
                                  DESCRIPTION "Accounting-Requests"
                                  ::= {  staTcpiRadiAccountinEntry 5 }

staTcpiRadiAccountinAccountingret OBJECT-TYPE
                                  SYNTAX Counter32
                                  MAX-ACCESS read-only
                                  STATUS current
                                  DESCRIPTION "Accounting-Retransmits"
                                  ::= {  staTcpiRadiAccountinEntry 6 }

staTcpiRadiAccountinAccountingres OBJECT-TYPE
                                  SYNTAX Counter32
                                  MAX-ACCESS read-only
                                  STATUS current
                                  DESCRIPTION "Accounting-Responses"
                                  ::= {  staTcpiRadiAccountinEntry 7 }

staTcpiRadiAccountinMalformedacco OBJECT-TYPE
                                  SYNTAX Counter32
                                  MAX-ACCESS read-only
                                  STATUS current
                                  DESCRIPTION "Malformed-Accounting-Responses"
                                  ::= {  staTcpiRadiAccountinEntry 8 }

staTcpiRadiAccountinBadauthentica OBJECT-TYPE
                                  SYNTAX Counter32
                                  MAX-ACCESS read-only
                                  STATUS current
                                  DESCRIPTION "Bad-Authenticators"
                                  ::= {  staTcpiRadiAccountinEntry 9 }

staTcpiRadiAccountinPendingreques OBJECT-TYPE
                                  SYNTAX Counter32
                                  MAX-ACCESS read-only
                                  STATUS current
                                  DESCRIPTION "Pending-Requests"
                                  ::= {  staTcpiRadiAccountinEntry 10 }

staTcpiRadiAccountinTimeouts OBJECT-TYPE
                                  SYNTAX Counter32
                                  MAX-ACCESS read-only
                                  STATUS current
                                  DESCRIPTION "Timeouts"
                                  ::= {  staTcpiRadiAccountinEntry 11 }

staTcpiRadiAccountinUnknowntypes OBJECT-TYPE
                                  SYNTAX Counter32
                                  MAX-ACCESS read-only
                                  STATUS current
                                  DESCRIPTION "Unknown-Types"
                                  ::= {  staTcpiRadiAccountinEntry 12 }

staTcpiRadiAccountinDropped OBJECT-TYPE
                                  SYNTAX Counter32
                                  MAX-ACCESS read-only
                                  STATUS current
                                  DESCRIPTION "Dropped"
                                  ::= {  staTcpiRadiAccountinEntry 13 }

staIpro OBJECT IDENTIFIER ::= { sta 10}
staIproLanrx OBJECT-TYPE
               SYNTAX Counter32
               MAX-ACCESS read-only
               STATUS current
               DESCRIPTION "LAN-Rx"
               ::= {  staIpro 1 }

staIproLantx OBJECT-TYPE
               SYNTAX Counter32
               MAX-ACCESS read-only
               STATUS current
               DESCRIPTION "LAN-Tx"
               ::= {  staIpro 2 }

staIproLanloca OBJECT-TYPE
               SYNTAX Counter32
               MAX-ACCESS read-only
               STATUS current
               DESCRIPTION "LAN-Local-Routings"
               ::= {  staIpro 3 }

staIproLannetw OBJECT-TYPE
               SYNTAX Counter32
               MAX-ACCESS read-only
               STATUS current
               DESCRIPTION "LAN-Network-Errors"
               ::= {  staIpro 4 }

staIproLanrout OBJECT-TYPE
               SYNTAX Counter32
               MAX-ACCESS read-only
               STATUS current
               DESCRIPTION "LAN-Routing-Errors"
               ::= {  staIpro 5 }

staIproLanttle OBJECT-TYPE
               SYNTAX Counter32
               MAX-ACCESS read-only
               STATUS current
               DESCRIPTION "LAN-TTL-Errors"
               ::= {  staIpro 6 }

staIproLanfilt OBJECT-TYPE
               SYNTAX Counter32
               MAX-ACCESS read-only
               STATUS current
               DESCRIPTION "LAN-Filters"
               ::= {  staIpro 7 }

staIproLandisc OBJECT-TYPE
               SYNTAX Counter32
               MAX-ACCESS read-only
               STATUS current
               DESCRIPTION "LAN-Discards"
               ::= {  staIpro 8 }

staIproWanrx OBJECT-TYPE
               SYNTAX Counter32
               MAX-ACCESS read-only
               STATUS current
               DESCRIPTION "WAN-Rx"
               ::= {  staIpro 9 }

staIproWantx OBJECT-TYPE
               SYNTAX Counter32
               MAX-ACCESS read-only
               STATUS current
               DESCRIPTION "WAN-Tx"
               ::= {  staIpro 10 }

staIproWannetw OBJECT-TYPE
               SYNTAX Counter32
               MAX-ACCESS read-only
               STATUS current
               DESCRIPTION "WAN-Network-Errors"
               ::= {  staIpro 11 }

staIproWanttle OBJECT-TYPE
               SYNTAX Counter32
               MAX-ACCESS read-only
               STATUS current
               DESCRIPTION "WAN-TTL-Errors"
               ::= {  staIpro 12 }

staIproWanfilt OBJECT-TYPE
               SYNTAX Counter32
               MAX-ACCESS read-only
               STATUS current
               DESCRIPTION "WAN-Filters"
               ::= {  staIpro 13 }

staIproWandisc OBJECT-TYPE
               SYNTAX Counter32
               MAX-ACCESS read-only
               STATUS current
               DESCRIPTION "WAN-Discards"
               ::= {  staIpro 14 }

staIproWantype OBJECT-TYPE
               SYNTAX Counter32
               MAX-ACCESS read-only
               STATUS current
               DESCRIPTION "WAN-Type-Errors"
               ::= {  staIpro 15 }

staIproArperro OBJECT-TYPE
               SYNTAX Counter32
               MAX-ACCESS read-only
               STATUS current
               DESCRIPTION "ARP-Errors"
               ::= {  staIpro 16 }

staIproEstabliTable OBJECT-TYPE
                    SYNTAX SEQUENCE OF StaIproEstabliEntry
                    MAX-ACCESS not-accessible
                    STATUS current
                    DESCRIPTION "Establish-Table"
                    ::= {  staIpro 17 }

staIproEstabliEntry OBJECT-TYPE
                    SYNTAX StaIproEstabliEntry
                    MAX-ACCESS not-accessible
                    STATUS current
                    DESCRIPTION "entry in table"
                    INDEX { staIproEstabliTim, staIproEstabliCou }
                    ::= {  staIproEstabliTable 1 }

StaIproEstabliEntry ::= SEQUENCE {
                    staIproEstabliTim DisplayString,
                    staIproEstabliDes IpAddress,
                    staIproEstabliSrc IpAddress,
                    staIproEstabliPro INTEGER,
                    staIproEstabliDpo INTEGER,
                    staIproEstabliSou INTEGER,
                    staIproEstabliCou INTEGER
                   }

staIproEstabliTim OBJECT-TYPE
                  SYNTAX DisplayString (SIZE(0..19))
                  MAX-ACCESS read-only
                  STATUS current
                  DESCRIPTION "Time"
                  ::= {  staIproEstabliEntry 1 }

staIproEstabliDes OBJECT-TYPE
                  SYNTAX IpAddress
                  MAX-ACCESS read-only
                  STATUS current
                  DESCRIPTION "Dest.-Address"
                  ::= {  staIproEstabliEntry 2 }

staIproEstabliSrc OBJECT-TYPE
                  SYNTAX IpAddress
                  MAX-ACCESS read-only
                  STATUS current
                  DESCRIPTION "Src.-Address"
                  ::= {  staIproEstabliEntry 3 }

staIproEstabliPro OBJECT-TYPE
                  SYNTAX INTEGER
                  {
                    icmp(1),
                    igmp(2),
                    ggt(3),
                    ipip(4),
                    tcp(6),
                    egp(8),
                    udp(17),
                    gre(47),
                    esp(50),
                    ah(51),
                    cftp(62),
                    ipcomp(108),
                    vrrp(112),
                    srp(119)
                  }
                  MAX-ACCESS read-only
                  STATUS current
                  DESCRIPTION "Prot."
                  ::= {  staIproEstabliEntry 4 }

staIproEstabliDpo OBJECT-TYPE
                  SYNTAX INTEGER (0..65535)
                  MAX-ACCESS read-only
                  STATUS current
                  DESCRIPTION "D-port-from"
                  ::= {  staIproEstabliEntry 5 }

staIproEstabliSou OBJECT-TYPE
                  SYNTAX INTEGER (0..65535)
                  MAX-ACCESS read-only
                  STATUS current
                  DESCRIPTION "Source-Port"
                  ::= {  staIproEstabliEntry 6 }

staIproEstabliCou OBJECT-TYPE
                  SYNTAX INTEGER (0..2147483647)
                  MAX-ACCESS read-only
                  STATUS current
                  DESCRIPTION "Counter"
                  ::= {  staIproEstabliEntry 7 }

staIproProtocoTable OBJECT-TYPE
                    SYNTAX SEQUENCE OF StaIproProtocoEntry
                    MAX-ACCESS not-accessible
                    STATUS current
                    DESCRIPTION "Protocol-Table"
                    ::= {  staIpro 18 }

staIproProtocoEntry OBJECT-TYPE
                    SYNTAX StaIproProtocoEntry
                    MAX-ACCESS not-accessible
                    STATUS current
                    DESCRIPTION "entry in table"
                    INDEX { staIproProtocoPro }
                    ::= {  staIproProtocoTable 1 }

StaIproProtocoEntry ::= SEQUENCE {
                    staIproProtocoPro INTEGER,
                    staIproProtocoLan Counter32,
                    staIproProtocoWan Counter32
                   }

staIproProtocoPro OBJECT-TYPE
                  SYNTAX INTEGER
                  {
                    icmp(1),
                    igmp(2),
                    ggt(3),
                    ipip(4),
                    tcp(6),
                    egp(8),
                    udp(17),
                    gre(47),
                    esp(50),
                    ah(51),
                    cftp(62),
                    ipcomp(108),
                    vrrp(112),
                    srp(119)
                  }
                  MAX-ACCESS read-only
                  STATUS current
                  DESCRIPTION "Prot."
                  ::= {  staIproProtocoEntry 1 }

staIproProtocoLan OBJECT-TYPE
                  SYNTAX Counter32
                  MAX-ACCESS read-only
                  STATUS current
                  DESCRIPTION "LAN-Tx"
                  ::= {  staIproProtocoEntry 2 }

staIproProtocoWan OBJECT-TYPE
                  SYNTAX Counter32
                  MAX-ACCESS read-only
                  STATUS current
                  DESCRIPTION "WAN-Tx"
                  ::= {  staIproProtocoEntry 3 }

staIproRip OBJECT IDENTIFIER ::= { staIpro 19}
staIproRipRx OBJECT-TYPE
               SYNTAX Counter32
               MAX-ACCESS read-only
               STATUS current
               DESCRIPTION "Rx"
               ::= {  staIproRip 1 }

staIproRipRequ OBJECT-TYPE
               SYNTAX Counter32
               MAX-ACCESS read-only
               STATUS current
               DESCRIPTION "Requests"
               ::= {  staIproRip 2 }

staIproRipResp OBJECT-TYPE
               SYNTAX Counter32
               MAX-ACCESS read-only
               STATUS current
               DESCRIPTION "Response"
               ::= {  staIproRip 3 }

staIproRipDisc OBJECT-TYPE
               SYNTAX Counter32
               MAX-ACCESS read-only
               STATUS current
               DESCRIPTION "Discards"
               ::= {  staIproRip 4 }

staIproRipErro OBJECT-TYPE
               SYNTAX Counter32
               MAX-ACCESS read-only
               STATUS current
               DESCRIPTION "Errors"
               ::= {  staIproRip 5 }

staIproRipEntr OBJECT-TYPE
               SYNTAX Counter32
               MAX-ACCESS read-only
               STATUS current
               DESCRIPTION "Entry-Errors"
               ::= {  staIproRip 6 }

staIproRipTx OBJECT-TYPE
               SYNTAX Counter32
               MAX-ACCESS read-only
               STATUS current
               DESCRIPTION "Tx"
               ::= {  staIproRip 7 }

staIproRipIpriTable OBJECT-TYPE
                    SYNTAX SEQUENCE OF StaIproRipIpriEntry
                    MAX-ACCESS not-accessible
                    STATUS current
                    DESCRIPTION "IP-RIP-Table"
                    ::= {  staIproRip 8 }

staIproRipIpriEntry OBJECT-TYPE
                    SYNTAX StaIproRipIpriEntry
                    MAX-ACCESS not-accessible
                    STATUS current
                    DESCRIPTION "entry in table"
                    INDEX { staIproRipIpriIpa, staIproRipIpriIpn, staIproRipIpriRtg }
                    ::= {  staIproRipIpriTable 1 }

StaIproRipIpriEntry ::= SEQUENCE {
                    staIproRipIpriIpa IpAddress,
                    staIproRipIpriIpn IpAddress,
                    staIproRipIpriRtg INTEGER,
                    staIproRipIpriTim INTEGER,
                    staIproRipIpriDis INTEGER,
                    staIproRipIpriGat IpAddress,
                    staIproRipIpriPee DisplayString,
                    staIproRipIpriPor INTEGER,
                    staIproRipIpriVla INTEGER,
                    staIproRipIpriNet DisplayString
                   }

staIproRipIpriIpa OBJECT-TYPE
                  SYNTAX IpAddress
                  MAX-ACCESS read-only
                  STATUS current
                  DESCRIPTION "IP-Address"
                  ::= {  staIproRipIpriEntry 1 }

staIproRipIpriIpn OBJECT-TYPE
                  SYNTAX IpAddress
                  MAX-ACCESS read-only
                  STATUS current
                  DESCRIPTION "IP-Netmask"
                  ::= {  staIproRipIpriEntry 2 }

staIproRipIpriRtg OBJECT-TYPE
                  SYNTAX INTEGER (0..65535)
                  MAX-ACCESS read-only
                  STATUS current
                  DESCRIPTION "Rtg-tag"
                  ::= {  staIproRipIpriEntry 6 }

staIproRipIpriTim OBJECT-TYPE
                  SYNTAX INTEGER (0..65535)
                  MAX-ACCESS read-only
                  STATUS current
                  DESCRIPTION "Time"
                  ::= {  staIproRipIpriEntry 3 }

staIproRipIpriDis OBJECT-TYPE
                  SYNTAX INTEGER (0..65535)
                  MAX-ACCESS read-only
                  STATUS current
                  DESCRIPTION "Distance"
                  ::= {  staIproRipIpriEntry 4 }

staIproRipIpriGat OBJECT-TYPE
                  SYNTAX IpAddress
                  MAX-ACCESS read-only
                  STATUS current
                  DESCRIPTION "Gateway"
                  ::= {  staIproRipIpriEntry 5 }

staIproRipIpriPee OBJECT-TYPE
                  SYNTAX DisplayString (SIZE(0..16))
                  MAX-ACCESS read-only
                  STATUS current
                  DESCRIPTION "Peer"
                  ::= {  staIproRipIpriEntry 8 }

staIproRipIpriPor OBJECT-TYPE
                  SYNTAX INTEGER
                  {
                    lan-1(0),
                    lan-2(1),
                    lan-3(2),
                    lan-4(3),
                    any(255)
                  }
                  MAX-ACCESS read-only
                  STATUS current
                  DESCRIPTION "Port"
                  ::= {  staIproRipIpriEntry 9 }

staIproRipIpriVla OBJECT-TYPE
                  SYNTAX INTEGER (0..65535)
                  MAX-ACCESS read-only
                  STATUS current
                  DESCRIPTION "VLAN-ID"
                  ::= {  staIproRipIpriEntry 10 }

staIproRipIpriNet OBJECT-TYPE
                  SYNTAX DisplayString (SIZE(0..16))
                  MAX-ACCESS read-only
                  STATUS current
                  DESCRIPTION "Network-name"
                  ::= {  staIproRipIpriEntry 11 }

staIproRipDele OBJECT-TYPE
               SYNTAX DisplayString
               MAX-ACCESS read-write
               STATUS current
               DESCRIPTION "Delete-Values"
               ::= {  staIproRip 9 }

staIproRipLansTable OBJECT-TYPE
                    SYNTAX SEQUENCE OF StaIproRipLansEntry
                    MAX-ACCESS not-accessible
                    STATUS current
                    DESCRIPTION "LAN-Sites"
                    ::= {  staIproRip 10 }

staIproRipLansEntry OBJECT-TYPE
                    SYNTAX StaIproRipLansEntry
                    MAX-ACCESS not-accessible
                    STATUS current
                    DESCRIPTION "entry in table"
                    INDEX { staIproRipLansNetw }
                    ::= {  staIproRipLansTable 1 }

StaIproRipLansEntry ::= SEQUENCE {
                    staIproRipLansNetw DisplayString,
                    staIproRipLansRipt INTEGER,
                    staIproRipLansRips INTEGER,
                    staIproRipLansRipa INTEGER,
                    staIproRipLansProp INTEGER,
                    staIproRipLansPois INTEGER,
                    staIproRipLansDftr INTEGER,
                    staIproRipLansRtgt DisplayString,
                    staIproRipLansRxfi DisplayString,
                    staIproRipLansTxfi DisplayString,
                    staIproRipLansPort INTEGER,
                    staIproRipLansVlan INTEGER
                   }

staIproRipLansNetw OBJECT-TYPE
                   SYNTAX DisplayString (SIZE(0..16))
                   MAX-ACCESS read-only
                   STATUS current
                   DESCRIPTION "Network-name"
                   ::= {  staIproRipLansEntry 1 }

staIproRipLansRipt OBJECT-TYPE
                   SYNTAX INTEGER
                   {
                     off(0),
                     rip-1(1),
                     r1-comp(2),
                     rip-2(3)
                   }
                   MAX-ACCESS read-only
                   STATUS current
                   DESCRIPTION "RIP-Type"
                   ::= {  staIproRipLansEntry 2 }

staIproRipLansRips OBJECT-TYPE
                   SYNTAX INTEGER
                   {
                     no(0),
                     yes(1)
                   }
                   MAX-ACCESS read-only
                   STATUS current
                   DESCRIPTION "RIP-Send"
                   ::= {  staIproRipLansEntry 12 }

staIproRipLansRipa OBJECT-TYPE
                   SYNTAX INTEGER
                   {
                     no(0),
                     yes(1)
                   }
                   MAX-ACCESS read-only
                   STATUS current
                   DESCRIPTION "RIP-Accept"
                   ::= {  staIproRipLansEntry 3 }

staIproRipLansProp OBJECT-TYPE
                   SYNTAX INTEGER
                   {
                     no(0),
                     yes(1)
                   }
                   MAX-ACCESS read-only
                   STATUS current
                   DESCRIPTION "Propagate"
                   ::= {  staIproRipLansEntry 4 }

staIproRipLansPois OBJECT-TYPE
                   SYNTAX INTEGER
                   {
                     no(0),
                     yes(1)
                   }
                   MAX-ACCESS read-only
                   STATUS current
                   DESCRIPTION "Poisoned-Reverse"
                   ::= {  staIproRipLansEntry 9 }

staIproRipLansDftr OBJECT-TYPE
                   SYNTAX INTEGER (0..65535)
                   MAX-ACCESS read-only
                   STATUS current
                   DESCRIPTION "Dft-Rtg-Tag"
                   ::= {  staIproRipLansEntry 5 }

staIproRipLansRtgt OBJECT-TYPE
                   SYNTAX DisplayString (SIZE(0..33))
                   MAX-ACCESS read-only
                   STATUS current
                   DESCRIPTION "Rtg-Tag-List"
                   ::= {  staIproRipLansEntry 6 }

staIproRipLansRxfi OBJECT-TYPE
                   SYNTAX DisplayString (SIZE(0..16))
                   MAX-ACCESS read-only
                   STATUS current
                   DESCRIPTION "Rx-Filter"
                   ::= {  staIproRipLansEntry 10 }

staIproRipLansTxfi OBJECT-TYPE
                   SYNTAX DisplayString (SIZE(0..16))
                   MAX-ACCESS read-only
                   STATUS current
                   DESCRIPTION "Tx-Filter"
                   ::= {  staIproRipLansEntry 11 }

staIproRipLansPort OBJECT-TYPE
                   SYNTAX INTEGER
                   {
                     lan-1(0),
                     lan-2(1),
                     lan-3(2),
                     lan-4(3),
                     any(255)
                   }
                   MAX-ACCESS read-only
                   STATUS current
                   DESCRIPTION "Port"
                   ::= {  staIproRipLansEntry 7 }

staIproRipLansVlan OBJECT-TYPE
                   SYNTAX INTEGER (0..65535)
                   MAX-ACCESS read-only
                   STATUS current
                   DESCRIPTION "VLAN-ID"
                   ::= {  staIproRipLansEntry 8 }

staIproRipVrrpTable OBJECT-TYPE
                    SYNTAX SEQUENCE OF StaIproRipVrrpEntry
                    MAX-ACCESS not-accessible
                    STATUS current
                    DESCRIPTION "VRRP-Sites"
                    ::= {  staIproRip 12 }

staIproRipVrrpEntry OBJECT-TYPE
                    SYNTAX StaIproRipVrrpEntry
                    MAX-ACCESS not-accessible
                    STATUS current
                    DESCRIPTION "entry in table"
                    INDEX { staIproRipVrrpNet, staIproRipVrrpRou }
                    ::= {  staIproRipVrrpTable 1 }

StaIproRipVrrpEntry ::= SEQUENCE {
                    staIproRipVrrpNet DisplayString,
                    staIproRipVrrpRip INTEGER,
                    staIproRipVrrpRou INTEGER
                   }

staIproRipVrrpNet OBJECT-TYPE
                  SYNTAX DisplayString (SIZE(0..16))
                  MAX-ACCESS read-only
                  STATUS current
                  DESCRIPTION "Network-name"
                  ::= {  staIproRipVrrpEntry 1 }

staIproRipVrrpRip OBJECT-TYPE
                  SYNTAX INTEGER
                  {
                    off(0),
                    rip-1(1),
                    r1-comp(2),
                    rip-2(3)
                  }
                  MAX-ACCESS read-only
                  STATUS current
                  DESCRIPTION "RIP-Type"
                  ::= {  staIproRipVrrpEntry 2 }

staIproRipVrrpRou OBJECT-TYPE
                  SYNTAX INTEGER (0..255)
                  MAX-ACCESS read-only
                  STATUS current
                  DESCRIPTION "Router-ID"
                  ::= {  staIproRipVrrpEntry 3 }

staIproRipWansTable OBJECT-TYPE
                    SYNTAX SEQUENCE OF StaIproRipWansEntry
                    MAX-ACCESS not-accessible
                    STATUS current
                    DESCRIPTION "WAN-Sites"
                    ::= {  staIproRip 11 }

staIproRipWansEntry OBJECT-TYPE
                    SYNTAX StaIproRipWansEntry
                    MAX-ACCESS not-accessible
                    STATUS current
                    DESCRIPTION "entry in table"
                    INDEX { staIproRipWansPeer }
                    ::= {  staIproRipWansTable 1 }

StaIproRipWansEntry ::= SEQUENCE {
                    staIproRipWansPeer DisplayString,
                    staIproRipWansRipt INTEGER,
                    staIproRipWansRips INTEGER,
                    staIproRipWansRipa INTEGER,
                    staIproRipWansMasq INTEGER,
                    staIproRipWansPois INTEGER,
                    staIproRipWansRfc2 INTEGER,
                    staIproRipWansGate IpAddress,
                    staIproRipWansDftr INTEGER,
                    staIproRipWansRtgt DisplayString,
                    staIproRipWansRxfi DisplayString,
                    staIproRipWansTxfi DisplayString
                   }

staIproRipWansPeer OBJECT-TYPE
                   SYNTAX DisplayString (SIZE(0..16))
                   MAX-ACCESS read-only
                   STATUS current
                   DESCRIPTION "Peer"
                   ::= {  staIproRipWansEntry 1 }

staIproRipWansRipt OBJECT-TYPE
                   SYNTAX INTEGER
                   {
                     off(0),
                     rip-1(1),
                     r1-comp(2),
                     rip-2(3)
                   }
                   MAX-ACCESS read-only
                   STATUS current
                   DESCRIPTION "RIP-Type"
                   ::= {  staIproRipWansEntry 2 }

staIproRipWansRips OBJECT-TYPE
                   SYNTAX INTEGER
                   {
                     no(0),
                     yes(1)
                   }
                   MAX-ACCESS read-only
                   STATUS current
                   DESCRIPTION "RIP-Send"
                   ::= {  staIproRipWansEntry 12 }

staIproRipWansRipa OBJECT-TYPE
                   SYNTAX INTEGER
                   {
                     no(0),
                     yes(1)
                   }
                   MAX-ACCESS read-only
                   STATUS current
                   DESCRIPTION "RIP-Accept"
                   ::= {  staIproRipWansEntry 3 }

staIproRipWansMasq OBJECT-TYPE
                   SYNTAX INTEGER
                   {
                     auto(0),
                     on(1),
                     intranet(2)
                   }
                   MAX-ACCESS read-only
                   STATUS current
                   DESCRIPTION "Masquerade"
                   ::= {  staIproRipWansEntry 4 }

staIproRipWansPois OBJECT-TYPE
                   SYNTAX INTEGER
                   {
                     no(0),
                     yes(1)
                   }
                   MAX-ACCESS read-only
                   STATUS current
                   DESCRIPTION "Poisoned-Reverse"
                   ::= {  staIproRipWansEntry 7 }

staIproRipWansRfc2 OBJECT-TYPE
                   SYNTAX INTEGER
                   {
                     no(0),
                     yes(1)
                   }
                   MAX-ACCESS read-only
                   STATUS current
                   DESCRIPTION "RFC2091"
                   ::= {  staIproRipWansEntry 8 }

staIproRipWansGate OBJECT-TYPE
                   SYNTAX IpAddress
                   MAX-ACCESS read-only
                   STATUS current
                   DESCRIPTION "Gateway"
                   ::= {  staIproRipWansEntry 9 }

staIproRipWansDftr OBJECT-TYPE
                   SYNTAX INTEGER (0..65535)
                   MAX-ACCESS read-only
                   STATUS current
                   DESCRIPTION "Dft-Rtg-Tag"
                   ::= {  staIproRipWansEntry 5 }

staIproRipWansRtgt OBJECT-TYPE
                   SYNTAX DisplayString (SIZE(0..33))
                   MAX-ACCESS read-only
                   STATUS current
                   DESCRIPTION "Rtg-Tag-List"
                   ::= {  staIproRipWansEntry 6 }

staIproRipWansRxfi OBJECT-TYPE
                   SYNTAX DisplayString (SIZE(0..16))
                   MAX-ACCESS read-only
                   STATUS current
                   DESCRIPTION "Rx-Filter"
                   ::= {  staIproRipWansEntry 10 }

staIproRipWansTxfi OBJECT-TYPE
                   SYNTAX DisplayString (SIZE(0..16))
                   MAX-ACCESS read-only
                   STATUS current
                   DESCRIPTION "Tx-Filter"
                   ::= {  staIproRipWansEntry 11 }

staIproRipDynlTable OBJECT-TYPE
                    SYNTAX SEQUENCE OF StaIproRipDynlEntry
                    MAX-ACCESS not-accessible
                    STATUS current
                    DESCRIPTION "Dyn.-LAN-Sites"
                    ::= {  staIproRip 13 }

staIproRipDynlEntry OBJECT-TYPE
                    SYNTAX StaIproRipDynlEntry
                    MAX-ACCESS not-accessible
                    STATUS current
                    DESCRIPTION "entry in table"
                    INDEX { staIproRipDynlGate }
                    ::= {  staIproRipDynlTable 1 }

StaIproRipDynlEntry ::= SEQUENCE {
                    staIproRipDynlGate DisplayString,
                    staIproRipDynlRipt INTEGER,
                    staIproRipDynlRips INTEGER,
                    staIproRipDynlRipa INTEGER,
                    staIproRipDynlPois INTEGER,
                    staIproRipDynlDftr INTEGER,
                    staIproRipDynlRtgt DisplayString,
                    staIproRipDynlRxfi DisplayString,
                    staIproRipDynlTxfi DisplayString,
                    staIproRipDynlPort INTEGER,
                    staIproRipDynlVlan INTEGER
                   }

staIproRipDynlGate OBJECT-TYPE
                   SYNTAX DisplayString (SIZE(0..16))
                   MAX-ACCESS read-only
                   STATUS current
                   DESCRIPTION "Gateway"
                   ::= {  staIproRipDynlEntry 1 }

staIproRipDynlRipt OBJECT-TYPE
                   SYNTAX INTEGER
                   {
                     off(0),
                     rip-1(1),
                     r1-comp(2),
                     rip-2(3)
                   }
                   MAX-ACCESS read-only
                   STATUS current
                   DESCRIPTION "RIP-Type"
                   ::= {  staIproRipDynlEntry 2 }

staIproRipDynlRips OBJECT-TYPE
                   SYNTAX INTEGER
                   {
                     no(0),
                     yes(1)
                   }
                   MAX-ACCESS read-only
                   STATUS current
                   DESCRIPTION "RIP-Send"
                   ::= {  staIproRipDynlEntry 12 }

staIproRipDynlRipa OBJECT-TYPE
                   SYNTAX INTEGER
                   {
                     no(0),
                     yes(1)
                   }
                   MAX-ACCESS read-only
                   STATUS current
                   DESCRIPTION "RIP-Accept"
                   ::= {  staIproRipDynlEntry 3 }

staIproRipDynlPois OBJECT-TYPE
                   SYNTAX INTEGER
                   {
                     no(0),
                     yes(1)
                   }
                   MAX-ACCESS read-only
                   STATUS current
                   DESCRIPTION "Poisoned-Reverse"
                   ::= {  staIproRipDynlEntry 4 }

staIproRipDynlDftr OBJECT-TYPE
                   SYNTAX INTEGER (0..65535)
                   MAX-ACCESS read-only
                   STATUS current
                   DESCRIPTION "Dft-Rtg-Tag"
                   ::= {  staIproRipDynlEntry 5 }

staIproRipDynlRtgt OBJECT-TYPE
                   SYNTAX DisplayString (SIZE(0..33))
                   MAX-ACCESS read-only
                   STATUS current
                   DESCRIPTION "Rtg-Tag-List"
                   ::= {  staIproRipDynlEntry 6 }

staIproRipDynlRxfi OBJECT-TYPE
                   SYNTAX DisplayString (SIZE(0..16))
                   MAX-ACCESS read-only
                   STATUS current
                   DESCRIPTION "Rx-Filter"
                   ::= {  staIproRipDynlEntry 10 }

staIproRipDynlTxfi OBJECT-TYPE
                   SYNTAX DisplayString (SIZE(0..16))
                   MAX-ACCESS read-only
                   STATUS current
                   DESCRIPTION "Tx-Filter"
                   ::= {  staIproRipDynlEntry 11 }

staIproRipDynlPort OBJECT-TYPE
                   SYNTAX INTEGER
                   {
                     lan-1(0),
                     lan-2(1),
                     lan-3(2),
                     lan-4(3),
                     any(255)
                   }
                   MAX-ACCESS read-only
                   STATUS current
                   DESCRIPTION "Port"
                   ::= {  staIproRipDynlEntry 7 }

staIproRipDynlVlan OBJECT-TYPE
                   SYNTAX INTEGER (0..65535)
                   MAX-ACCESS read-only
                   STATUS current
                   DESCRIPTION "VLAN-ID"
                   ::= {  staIproRipDynlEntry 8 }

staIproRipDynwTable OBJECT-TYPE
                    SYNTAX SEQUENCE OF StaIproRipDynwEntry
                    MAX-ACCESS not-accessible
                    STATUS current
                    DESCRIPTION "Dyn.-WAN-Sites"
                    ::= {  staIproRip 14 }

staIproRipDynwEntry OBJECT-TYPE
                    SYNTAX StaIproRipDynwEntry
                    MAX-ACCESS not-accessible
                    STATUS current
                    DESCRIPTION "entry in table"
                    INDEX { staIproRipDynwPeer }
                    ::= {  staIproRipDynwTable 1 }

StaIproRipDynwEntry ::= SEQUENCE {
                    staIproRipDynwPeer DisplayString,
                    staIproRipDynwRipt INTEGER,
                    staIproRipDynwRips INTEGER,
                    staIproRipDynwRipa INTEGER,
                    staIproRipDynwMasq INTEGER,
                    staIproRipDynwPois INTEGER,
                    staIproRipDynwRfc2 INTEGER,
                    staIproRipDynwGate IpAddress,
                    staIproRipDynwDftr INTEGER,
                    staIproRipDynwRtgt DisplayString,
                    staIproRipDynwRxfi DisplayString,
                    staIproRipDynwTxfi DisplayString
                   }

staIproRipDynwPeer OBJECT-TYPE
                   SYNTAX DisplayString (SIZE(0..16))
                   MAX-ACCESS read-only
                   STATUS current
                   DESCRIPTION "Peer"
                   ::= {  staIproRipDynwEntry 1 }

staIproRipDynwRipt OBJECT-TYPE
                   SYNTAX INTEGER
                   {
                     off(0),
                     rip-1(1),
                     r1-comp(2),
                     rip-2(3)
                   }
                   MAX-ACCESS read-only
                   STATUS current
                   DESCRIPTION "RIP-Type"
                   ::= {  staIproRipDynwEntry 2 }

staIproRipDynwRips OBJECT-TYPE
                   SYNTAX INTEGER
                   {
                     no(0),
                     yes(1)
                   }
                   MAX-ACCESS read-only
                   STATUS current
                   DESCRIPTION "RIP-Send"
                   ::= {  staIproRipDynwEntry 12 }

staIproRipDynwRipa OBJECT-TYPE
                   SYNTAX INTEGER
                   {
                     no(0),
                     yes(1)
                   }
                   MAX-ACCESS read-only
                   STATUS current
                   DESCRIPTION "RIP-Accept"
                   ::= {  staIproRipDynwEntry 3 }

staIproRipDynwMasq OBJECT-TYPE
                   SYNTAX INTEGER
                   {
                     auto(0),
                     on(1),
                     intranet(2)
                   }
                   MAX-ACCESS read-only
                   STATUS current
                   DESCRIPTION "Masquerade"
                   ::= {  staIproRipDynwEntry 4 }

staIproRipDynwPois OBJECT-TYPE
                   SYNTAX INTEGER
                   {
                     no(0),
                     yes(1)
                   }
                   MAX-ACCESS read-only
                   STATUS current
                   DESCRIPTION "Poisoned-Reverse"
                   ::= {  staIproRipDynwEntry 7 }

staIproRipDynwRfc2 OBJECT-TYPE
                   SYNTAX INTEGER
                   {
                     no(0),
                     yes(1)
                   }
                   MAX-ACCESS read-only
                   STATUS current
                   DESCRIPTION "RFC2091"
                   ::= {  staIproRipDynwEntry 8 }

staIproRipDynwGate OBJECT-TYPE
                   SYNTAX IpAddress
                   MAX-ACCESS read-only
                   STATUS current
                   DESCRIPTION "Gateway"
                   ::= {  staIproRipDynwEntry 9 }

staIproRipDynwDftr OBJECT-TYPE
                   SYNTAX INTEGER (0..65535)
                   MAX-ACCESS read-only
                   STATUS current
                   DESCRIPTION "Dft-Rtg-Tag"
                   ::= {  staIproRipDynwEntry 5 }

staIproRipDynwRtgt OBJECT-TYPE
                   SYNTAX DisplayString (SIZE(0..33))
                   MAX-ACCESS read-only
                   STATUS current
                   DESCRIPTION "Rtg-Tag-List"
                   ::= {  staIproRipDynwEntry 6 }

staIproRipDynwRxfi OBJECT-TYPE
                   SYNTAX DisplayString (SIZE(0..16))
                   MAX-ACCESS read-only
                   STATUS current
                   DESCRIPTION "Rx-Filter"
                   ::= {  staIproRipDynwEntry 10 }

staIproRipDynwTxfi OBJECT-TYPE
                   SYNTAX DisplayString (SIZE(0..16))
                   MAX-ACCESS read-only
                   STATUS current
                   DESCRIPTION "Tx-Filter"
                   ::= {  staIproRipDynwEntry 11 }

staIproRipWildTable OBJECT-TYPE
                    SYNTAX SEQUENCE OF StaIproRipWildEntry
                    MAX-ACCESS not-accessible
                    STATUS current
                    DESCRIPTION "Wildcard-Sites"
                    ::= {  staIproRip 16 }

staIproRipWildEntry OBJECT-TYPE
                    SYNTAX StaIproRipWildEntry
                    MAX-ACCESS not-accessible
                    STATUS current
                    DESCRIPTION "entry in table"
                    INDEX { staIproRipWildPeer }
                    ::= {  staIproRipWildTable 1 }

StaIproRipWildEntry ::= SEQUENCE {
                    staIproRipWildPeer DisplayString,
                    staIproRipWildRipt INTEGER,
                    staIproRipWildRips INTEGER,
                    staIproRipWildRipa INTEGER,
                    staIproRipWildMasq INTEGER,
                    staIproRipWildPois INTEGER,
                    staIproRipWildRfc2 INTEGER,
                    staIproRipWildGate IpAddress,
                    staIproRipWildDftr INTEGER,
                    staIproRipWildRtgt DisplayString,
                    staIproRipWildRxfi DisplayString,
                    staIproRipWildTxfi DisplayString
                   }

staIproRipWildPeer OBJECT-TYPE
                   SYNTAX DisplayString (SIZE(0..16))
                   MAX-ACCESS read-only
                   STATUS current
                   DESCRIPTION "Peer"
                   ::= {  staIproRipWildEntry 1 }

staIproRipWildRipt OBJECT-TYPE
                   SYNTAX INTEGER
                   {
                     off(0),
                     rip-1(1),
                     r1-comp(2),
                     rip-2(3)
                   }
                   MAX-ACCESS read-only
                   STATUS current
                   DESCRIPTION "RIP-Type"
                   ::= {  staIproRipWildEntry 2 }

staIproRipWildRips OBJECT-TYPE
                   SYNTAX INTEGER
                   {
                     no(0),
                     yes(1)
                   }
                   MAX-ACCESS read-only
                   STATUS current
                   DESCRIPTION "RIP-Send"
                   ::= {  staIproRipWildEntry 12 }

staIproRipWildRipa OBJECT-TYPE
                   SYNTAX INTEGER
                   {
                     no(0),
                     yes(1)
                   }
                   MAX-ACCESS read-only
                   STATUS current
                   DESCRIPTION "RIP-Accept"
                   ::= {  staIproRipWildEntry 3 }

staIproRipWildMasq OBJECT-TYPE
                   SYNTAX INTEGER
                   {
                     auto(0),
                     on(1),
                     intranet(2)
                   }
                   MAX-ACCESS read-only
                   STATUS current
                   DESCRIPTION "Masquerade"
                   ::= {  staIproRipWildEntry 4 }

staIproRipWildPois OBJECT-TYPE
                   SYNTAX INTEGER
                   {
                     no(0),
                     yes(1)
                   }
                   MAX-ACCESS read-only
                   STATUS current
                   DESCRIPTION "Poisoned-Reverse"
                   ::= {  staIproRipWildEntry 7 }

staIproRipWildRfc2 OBJECT-TYPE
                   SYNTAX INTEGER
                   {
                     no(0),
                     yes(1)
                   }
                   MAX-ACCESS read-only
                   STATUS current
                   DESCRIPTION "RFC2091"
                   ::= {  staIproRipWildEntry 8 }

staIproRipWildGate OBJECT-TYPE
                   SYNTAX IpAddress
                   MAX-ACCESS read-only
                   STATUS current
                   DESCRIPTION "Gateway"
                   ::= {  staIproRipWildEntry 9 }

staIproRipWildDftr OBJECT-TYPE
                   SYNTAX INTEGER (0..65535)
                   MAX-ACCESS read-only
                   STATUS current
                   DESCRIPTION "Dft-Rtg-Tag"
                   ::= {  staIproRipWildEntry 5 }

staIproRipWildRtgt OBJECT-TYPE
                   SYNTAX DisplayString (SIZE(0..33))
                   MAX-ACCESS read-only
                   STATUS current
                   DESCRIPTION "Rtg-Tag-List"
                   ::= {  staIproRipWildEntry 6 }

staIproRipWildRxfi OBJECT-TYPE
                   SYNTAX DisplayString (SIZE(0..16))
                   MAX-ACCESS read-only
                   STATUS current
                   DESCRIPTION "Rx-Filter"
                   ::= {  staIproRipWildEntry 10 }

staIproRipWildTxfi OBJECT-TYPE
                   SYNTAX DisplayString (SIZE(0..16))
                   MAX-ACCESS read-only
                   STATUS current
                   DESCRIPTION "Tx-Filter"
                   ::= {  staIproRipWildEntry 11 }

staIproRipFiltTable OBJECT-TYPE
                    SYNTAX SEQUENCE OF StaIproRipFiltEntry
                    MAX-ACCESS not-accessible
                    STATUS current
                    DESCRIPTION "Filter"
                    ::= {  staIproRip 15 }

staIproRipFiltEntry OBJECT-TYPE
                    SYNTAX StaIproRipFiltEntry
                    MAX-ACCESS not-accessible
                    STATUS current
                    DESCRIPTION "entry in table"
                    INDEX { staIproRipFiltIdx }
                    ::= {  staIproRipFiltTable 1 }

StaIproRipFiltEntry ::= SEQUENCE {
                    staIproRipFiltIdx INTEGER,
                    staIproRipFiltNam DisplayString,
                    staIproRipFiltIpa IpAddress,
                    staIproRipFiltIpn IpAddress,
                    staIproRipFiltTyp INTEGER
                   }

staIproRipFiltIdx OBJECT-TYPE
                  SYNTAX INTEGER (0..65535)
                  MAX-ACCESS read-only
                  STATUS current
                  DESCRIPTION "Idx."
                  ::= {  staIproRipFiltEntry 1 }

staIproRipFiltNam OBJECT-TYPE
                  SYNTAX DisplayString (SIZE(0..255))
                  MAX-ACCESS read-only
                  STATUS current
                  DESCRIPTION "Name"
                  ::= {  staIproRipFiltEntry 3 }

staIproRipFiltIpa OBJECT-TYPE
                  SYNTAX IpAddress
                  MAX-ACCESS read-only
                  STATUS current
                  DESCRIPTION "IP-Address"
                  ::= {  staIproRipFiltEntry 4 }

staIproRipFiltIpn OBJECT-TYPE
                  SYNTAX IpAddress
                  MAX-ACCESS read-only
                  STATUS current
                  DESCRIPTION "IP-Netmask"
                  ::= {  staIproRipFiltEntry 5 }

staIproRipFiltTyp OBJECT-TYPE
                  SYNTAX INTEGER
                  {
                    unknown(0),
                    positive(1),
                    negative(2)
                  }
                  MAX-ACCESS read-only
                  STATUS current
                  DESCRIPTION "Type"
                  ::= {  staIproRipFiltEntry 2 }

staIproDeletev OBJECT-TYPE
               SYNTAX DisplayString
               MAX-ACCESS read-write
               STATUS current
               DESCRIPTION "Delete-Values"
               ::= {  staIpro 20 }

staIproServiceTable OBJECT-TYPE
                    SYNTAX SEQUENCE OF StaIproServiceEntry
                    MAX-ACCESS not-accessible
                    STATUS current
                    DESCRIPTION "Service-Table"
                    ::= {  staIpro 21 }

staIproServiceEntry OBJECT-TYPE
                    SYNTAX StaIproServiceEntry
                    MAX-ACCESS not-accessible
                    STATUS current
                    DESCRIPTION "entry in table"
                    INDEX { staIproServiceService }
                    ::= {  staIproServiceTable 1 }

StaIproServiceEntry ::= SEQUENCE {
                    staIproServiceService INTEGER,
                    staIproServicePacketrx Counter32,
                    staIproServicePackettx Counter32,
                    staIproServicePacketre DisplayString,
                    staIproServiceKbytesrx Counter32,
                    staIproServiceKbytestx Counter32,
                    staIproServiceKbytesre DisplayString
                   }

staIproServiceService OBJECT-TYPE
                       SYNTAX INTEGER
                       {
                         icmp(1),
                         ftp(2),
                         http(3),
                         smtp(4),
                         dns(5),
                         telnet(6),
                         tftp(7),
                         dhcp(8),
                         pop3(9),
                         netbios(10),
                         imap2(11),
                         news(12),
                         irc(13),
                         snmp(14),
                         other(15),
                         total(16)
                       }
                       MAX-ACCESS read-only
                       STATUS current
                       DESCRIPTION "Service"
                       ::= {  staIproServiceEntry 1 }

staIproServicePacketrx OBJECT-TYPE
                       SYNTAX Counter32
                       MAX-ACCESS read-only
                       STATUS current
                       DESCRIPTION "Packet-Rx"
                       ::= {  staIproServiceEntry 2 }

staIproServicePackettx OBJECT-TYPE
                       SYNTAX Counter32
                       MAX-ACCESS read-only
                       STATUS current
                       DESCRIPTION "Packet-Tx"
                       ::= {  staIproServiceEntry 3 }

staIproServicePacketre OBJECT-TYPE
                       SYNTAX DisplayString (SIZE(0..255))
                       MAX-ACCESS read-only
                       STATUS current
                       DESCRIPTION "Packet-Rel"
                       ::= {  staIproServiceEntry 4 }

staIproServiceKbytesrx OBJECT-TYPE
                       SYNTAX Counter32
                       MAX-ACCESS read-only
                       STATUS current
                       DESCRIPTION "KBytes-Rx"
                       ::= {  staIproServiceEntry 5 }

staIproServiceKbytestx OBJECT-TYPE
                       SYNTAX Counter32
                       MAX-ACCESS read-only
                       STATUS current
                       DESCRIPTION "KBytes-Tx"
                       ::= {  staIproServiceEntry 6 }

staIproServiceKbytesre OBJECT-TYPE
                       SYNTAX DisplayString (SIZE(0..255))
                       MAX-ACCESS read-only
                       STATUS current
                       DESCRIPTION "KBytes-Rel"
                       ::= {  staIproServiceEntry 7 }

staIproFilterlTable OBJECT-TYPE
                    SYNTAX SEQUENCE OF StaIproFilterlEntry
                    MAX-ACCESS not-accessible
                    STATUS current
                    DESCRIPTION "Filter-List"
                    ::= {  staIpro 22 }

staIproFilterlEntry OBJECT-TYPE
                    SYNTAX StaIproFilterlEntry
                    MAX-ACCESS not-accessible
                    STATUS current
                    DESCRIPTION "entry in table"
                    INDEX { staIproFilterlIdx }
                    ::= {  staIproFilterlTable 1 }

StaIproFilterlEntry ::= SEQUENCE {
                    staIproFilterlIdx INTEGER,
                    staIproFilterlProt INTEGER,
                    staIproFilterlSrcm DisplayString,
                    staIproFilterlSrca IpAddress,
                    staIproFilterlSrcn IpAddress,
                    staIproFilterlSst INTEGER,
                    staIproFilterlSend INTEGER,
                    staIproFilterlDstm DisplayString,
                    staIproFilterlDsta IpAddress,
                    staIproFilterlDstn IpAddress,
                    staIproFilterlDst INTEGER,
                    staIproFilterlDend INTEGER,
                    staIproFilterlActi DisplayString,
                    staIproFilterlLink INTEGER,
                    staIproFilterlPrio INTEGER,
                    staIproFilterlRtgt INTEGER
                   }

staIproFilterlIdx OBJECT-TYPE
                   SYNTAX INTEGER (0..65535)
                   MAX-ACCESS read-only
                   STATUS current
                   DESCRIPTION "Idx."
                   ::= {  staIproFilterlEntry 1 }

staIproFilterlProt OBJECT-TYPE
                   SYNTAX INTEGER (0..255)
                   MAX-ACCESS read-only
                   STATUS current
                   DESCRIPTION "Prot."
                   ::= {  staIproFilterlEntry 2 }

staIproFilterlSrcm OBJECT-TYPE
                   SYNTAX DisplayString (SIZE(0..12))
                   MAX-ACCESS read-only
                   STATUS current
                   DESCRIPTION "Src-MAC"
                   ::= {  staIproFilterlEntry 13 }

staIproFilterlSrca OBJECT-TYPE
                   SYNTAX IpAddress
                   MAX-ACCESS read-only
                   STATUS current
                   DESCRIPTION "Src-Address"
                   ::= {  staIproFilterlEntry 3 }

staIproFilterlSrcn OBJECT-TYPE
                   SYNTAX IpAddress
                   MAX-ACCESS read-only
                   STATUS current
                   DESCRIPTION "Src-Netmask"
                   ::= {  staIproFilterlEntry 4 }

staIproFilterlSst OBJECT-TYPE
                   SYNTAX INTEGER (0..65535)
                   MAX-ACCESS read-only
                   STATUS current
                   DESCRIPTION "S-St."
                   ::= {  staIproFilterlEntry 5 }

staIproFilterlSend OBJECT-TYPE
                   SYNTAX INTEGER (0..65535)
                   MAX-ACCESS read-only
                   STATUS current
                   DESCRIPTION "S-End"
                   ::= {  staIproFilterlEntry 6 }

staIproFilterlDstm OBJECT-TYPE
                   SYNTAX DisplayString (SIZE(0..12))
                   MAX-ACCESS read-only
                   STATUS current
                   DESCRIPTION "Dst-MAC"
                   ::= {  staIproFilterlEntry 14 }

staIproFilterlDsta OBJECT-TYPE
                   SYNTAX IpAddress
                   MAX-ACCESS read-only
                   STATUS current
                   DESCRIPTION "Dst-Address"
                   ::= {  staIproFilterlEntry 7 }

staIproFilterlDstn OBJECT-TYPE
                   SYNTAX IpAddress
                   MAX-ACCESS read-only
                   STATUS current
                   DESCRIPTION "Dst-Netmask"
                   ::= {  staIproFilterlEntry 8 }

staIproFilterlDst OBJECT-TYPE
                   SYNTAX INTEGER (0..65535)
                   MAX-ACCESS read-only
                   STATUS current
                   DESCRIPTION "D-St."
                   ::= {  staIproFilterlEntry 9 }

staIproFilterlDend OBJECT-TYPE
                   SYNTAX INTEGER (0..65535)
                   MAX-ACCESS read-only
                   STATUS current
                   DESCRIPTION "D-End"
                   ::= {  staIproFilterlEntry 10 }

staIproFilterlActi OBJECT-TYPE
                   SYNTAX DisplayString (SIZE(0..255))
                   MAX-ACCESS read-only
                   STATUS current
                   DESCRIPTION "Action"
                   ::= {  staIproFilterlEntry 11 }

staIproFilterlLink OBJECT-TYPE
                   SYNTAX INTEGER
                   {
                     no(0),
                     yes(1)
                   }
                   MAX-ACCESS read-only
                   STATUS current
                   DESCRIPTION "Linked"
                   ::= {  staIproFilterlEntry 15 }

staIproFilterlPrio OBJECT-TYPE
                   SYNTAX INTEGER (0..65535)
                   MAX-ACCESS read-only
                   STATUS current
                   DESCRIPTION "Prio"
                   ::= {  staIproFilterlEntry 16 }

staIproFilterlRtgt OBJECT-TYPE
                   SYNTAX INTEGER (0..65535)
                   MAX-ACCESS read-only
                   STATUS current
                   DESCRIPTION "Rtg-tag"
                   ::= {  staIproFilterlEntry 17 }

staIproConnectTable OBJECT-TYPE
                    SYNTAX SEQUENCE OF StaIproConnectEntry
                    MAX-ACCESS not-accessible
                    STATUS current
                    DESCRIPTION "Connection-List"
                    ::= {  staIpro 23 }

staIproConnectEntry OBJECT-TYPE
                    SYNTAX StaIproConnectEntry
                    MAX-ACCESS not-accessible
                    STATUS current
                    DESCRIPTION "entry in table"
                    INDEX { staIproConnectSrca, staIproConnectDsta, staIproConnectProt, staIproConnectSrcp, staIproConnectDstp }
                    ::= {  staIproConnectTable 1 }

StaIproConnectEntry ::= SEQUENCE {
                    staIproConnectSrca IpAddress,
                    staIproConnectDsta IpAddress,
                    staIproConnectProt INTEGER,
                    staIproConnectSrcp INTEGER,
                    staIproConnectDstp INTEGER,
                    staIproConnectRtgt INTEGER,
                    staIproConnectTime INTEGER,
                    staIproConnectFlag INTEGER,
                    staIproConnectFilt DisplayString,
                    staIproConnectSrcr DisplayString,
                    staIproConnectDest DisplayString
                   }

staIproConnectSrca OBJECT-TYPE
                   SYNTAX IpAddress
                   MAX-ACCESS read-only
                   STATUS current
                   DESCRIPTION "Src-Address"
                   ::= {  staIproConnectEntry 1 }

staIproConnectDsta OBJECT-TYPE
                   SYNTAX IpAddress
                   MAX-ACCESS read-only
                   STATUS current
                   DESCRIPTION "Dst-Address"
                   ::= {  staIproConnectEntry 2 }

staIproConnectProt OBJECT-TYPE
                   SYNTAX INTEGER (0..255)
                   MAX-ACCESS read-only
                   STATUS current
                   DESCRIPTION "Prot."
                   ::= {  staIproConnectEntry 3 }

staIproConnectSrcp OBJECT-TYPE
                   SYNTAX INTEGER (0..65535)
                   MAX-ACCESS read-only
                   STATUS current
                   DESCRIPTION "Src-Port"
                   ::= {  staIproConnectEntry 4 }

staIproConnectDstp OBJECT-TYPE
                   SYNTAX INTEGER (0..65535)
                   MAX-ACCESS read-only
                   STATUS current
                   DESCRIPTION "Dst-Port"
                   ::= {  staIproConnectEntry 5 }

staIproConnectRtgt OBJECT-TYPE
                   SYNTAX INTEGER (0..65535)
                   MAX-ACCESS read-only
                   STATUS current
                   DESCRIPTION "Rtg-tag"
                   ::= {  staIproConnectEntry 11 }

staIproConnectTime OBJECT-TYPE
                   SYNTAX INTEGER (0..65535)
                   MAX-ACCESS read-only
                   STATUS current
                   DESCRIPTION "Timeout"
                   ::= {  staIproConnectEntry 6 }

staIproConnectFlag OBJECT-TYPE
                   SYNTAX INTEGER (0..2147483647)
                   MAX-ACCESS read-only
                   STATUS current
                   DESCRIPTION "Flags"
                   ::= {  staIproConnectEntry 7 }

staIproConnectFilt OBJECT-TYPE
                   SYNTAX DisplayString (SIZE(0..255))
                   MAX-ACCESS read-only
                   STATUS current
                   DESCRIPTION "Filter-Rule"
                   ::= {  staIproConnectEntry 8 }

staIproConnectSrcr OBJECT-TYPE
                   SYNTAX DisplayString (SIZE(0..255))
                   MAX-ACCESS read-only
                   STATUS current
                   DESCRIPTION "Src-Route"
                   ::= {  staIproConnectEntry 9 }

staIproConnectDest OBJECT-TYPE
                   SYNTAX DisplayString (SIZE(0..255))
                   MAX-ACCESS read-only
                   STATUS current
                   DESCRIPTION "Dest-Route"
                   ::= {  staIproConnectEntry 10 }

staIproOpenporTable OBJECT-TYPE
                    SYNTAX SEQUENCE OF StaIproOpenporEntry
                    MAX-ACCESS not-accessible
                    STATUS current
                    DESCRIPTION "Open-Port-List"
                    ::= {  staIpro 29 }

staIproOpenporEntry OBJECT-TYPE
                    SYNTAX StaIproOpenporEntry
                    MAX-ACCESS not-accessible
                    STATUS current
                    DESCRIPTION "entry in table"
                    INDEX { staIproOpenporSrca, staIproOpenporDsta, staIproOpenporProt, staIproOpenporDstp }
                    ::= {  staIproOpenporTable 1 }

StaIproOpenporEntry ::= SEQUENCE {
                    staIproOpenporSrca IpAddress,
                    staIproOpenporDsta IpAddress,
                    staIproOpenporProt INTEGER,
                    staIproOpenporDstp INTEGER,
                    staIproOpenporTime INTEGER,
                    staIproOpenporFilt DisplayString,
                    staIproOpenporSrcr DisplayString
                   }

staIproOpenporSrca OBJECT-TYPE
                   SYNTAX IpAddress
                   MAX-ACCESS read-only
                   STATUS current
                   DESCRIPTION "Src-Address"
                   ::= {  staIproOpenporEntry 1 }

staIproOpenporDsta OBJECT-TYPE
                   SYNTAX IpAddress
                   MAX-ACCESS read-only
                   STATUS current
                   DESCRIPTION "Dst-Address"
                   ::= {  staIproOpenporEntry 2 }

staIproOpenporProt OBJECT-TYPE
                   SYNTAX INTEGER (0..255)
                   MAX-ACCESS read-only
                   STATUS current
                   DESCRIPTION "Prot."
                   ::= {  staIproOpenporEntry 3 }

staIproOpenporDstp OBJECT-TYPE
                   SYNTAX INTEGER (0..65535)
                   MAX-ACCESS read-only
                   STATUS current
                   DESCRIPTION "Dst-Port"
                   ::= {  staIproOpenporEntry 5 }

staIproOpenporTime OBJECT-TYPE
                   SYNTAX INTEGER (0..65535)
                   MAX-ACCESS read-only
                   STATUS current
                   DESCRIPTION "Timeout"
                   ::= {  staIproOpenporEntry 6 }

staIproOpenporFilt OBJECT-TYPE
                   SYNTAX DisplayString (SIZE(0..255))
                   MAX-ACCESS read-only
                   STATUS current
                   DESCRIPTION "Filter-Rule"
                   ::= {  staIproOpenporEntry 8 }

staIproOpenporSrcr OBJECT-TYPE
                   SYNTAX DisplayString (SIZE(0..255))
                   MAX-ACCESS read-only
                   STATUS current
                   DESCRIPTION "Src-Route"
                   ::= {  staIproOpenporEntry 9 }

staIproHostbloTable OBJECT-TYPE
                    SYNTAX SEQUENCE OF StaIproHostbloEntry
                    MAX-ACCESS not-accessible
                    STATUS current
                    DESCRIPTION "Host-Block-List"
                    ::= {  staIpro 24 }

staIproHostbloEntry OBJECT-TYPE
                    SYNTAX StaIproHostbloEntry
                    MAX-ACCESS not-accessible
                    STATUS current
                    DESCRIPTION "entry in table"
                    INDEX { staIproHostbloSrc }
                    ::= {  staIproHostbloTable 1 }

StaIproHostbloEntry ::= SEQUENCE {
                    staIproHostbloSrc IpAddress,
                    staIproHostbloTim INTEGER,
                    staIproHostbloFil DisplayString
                   }

staIproHostbloSrc OBJECT-TYPE
                  SYNTAX IpAddress
                  MAX-ACCESS read-only
                  STATUS current
                  DESCRIPTION "Src-Address"
                  ::= {  staIproHostbloEntry 1 }

staIproHostbloTim OBJECT-TYPE
                  SYNTAX INTEGER (0..2147483647)
                  MAX-ACCESS read-only
                  STATUS current
                  DESCRIPTION "Timeout"
                  ::= {  staIproHostbloEntry 2 }

staIproHostbloFil OBJECT-TYPE
                  SYNTAX DisplayString (SIZE(0..255))
                  MAX-ACCESS read-only
                  STATUS current
                  DESCRIPTION "Filter-Rule"
                  ::= {  staIproHostbloEntry 3 }

staIproPortbloTable OBJECT-TYPE
                    SYNTAX SEQUENCE OF StaIproPortbloEntry
                    MAX-ACCESS not-accessible
                    STATUS current
                    DESCRIPTION "Port-Block-List"
                    ::= {  staIpro 25 }

staIproPortbloEntry OBJECT-TYPE
                    SYNTAX StaIproPortbloEntry
                    MAX-ACCESS not-accessible
                    STATUS current
                    DESCRIPTION "entry in table"
                    INDEX { staIproPortbloDsta }
                    ::= {  staIproPortbloTable 1 }

StaIproPortbloEntry ::= SEQUENCE {
                    staIproPortbloDsta IpAddress,
                    staIproPortbloProt INTEGER,
                    staIproPortbloDstp INTEGER,
                    staIproPortbloTime INTEGER,
                    staIproPortbloFilt DisplayString
                   }

staIproPortbloDsta OBJECT-TYPE
                   SYNTAX IpAddress
                   MAX-ACCESS read-only
                   STATUS current
                   DESCRIPTION "Dst-Address"
                   ::= {  staIproPortbloEntry 1 }

staIproPortbloProt OBJECT-TYPE
                   SYNTAX INTEGER (0..65535)
                   MAX-ACCESS read-only
                   STATUS current
                   DESCRIPTION "Prot."
                   ::= {  staIproPortbloEntry 2 }

staIproPortbloDstp OBJECT-TYPE
                   SYNTAX INTEGER (0..65535)
                   MAX-ACCESS read-only
                   STATUS current
                   DESCRIPTION "Dst-Port"
                   ::= {  staIproPortbloEntry 3 }

staIproPortbloTime OBJECT-TYPE
                   SYNTAX INTEGER (0..2147483647)
                   MAX-ACCESS read-only
                   STATUS current
                   DESCRIPTION "Timeout"
                   ::= {  staIproPortbloEntry 4 }

staIproPortbloFilt OBJECT-TYPE
                   SYNTAX DisplayString (SIZE(0..255))
                   MAX-ACCESS read-only
                   STATUS current
                   DESCRIPTION "Filter-Rule"
                   ::= {  staIproPortbloEntry 5 }

staIproLogtablTable OBJECT-TYPE
                    SYNTAX SEQUENCE OF StaIproLogtablEntry
                    MAX-ACCESS not-accessible
                    STATUS current
                    DESCRIPTION "Log-Table"
                    ::= {  staIpro 26 }

staIproLogtablEntry OBJECT-TYPE
                    SYNTAX StaIproLogtablEntry
                    MAX-ACCESS not-accessible
                    STATUS current
                    DESCRIPTION "entry in table"
                    INDEX { staIproLogtablIdx }
                    ::= {  staIproLogtablTable 1 }

StaIproLogtablEntry ::= SEQUENCE {
                    staIproLogtablIdx INTEGER,
                    staIproLogtablSyst DisplayString,
                    staIproLogtablSrca IpAddress,
                    staIproLogtablDsta IpAddress,
                    staIproLogtablProt INTEGER,
                    staIproLogtablSrcp INTEGER,
                    staIproLogtablDstp INTEGER,
                    staIproLogtablFilt DisplayString,
                    staIproLogtablLimi INTEGER,
                    staIproLogtablThre INTEGER,
                    staIproLogtablActi INTEGER
                   }

staIproLogtablIdx OBJECT-TYPE
                   SYNTAX INTEGER (0..65535)
                   MAX-ACCESS read-only
                   STATUS current
                   DESCRIPTION "Idx."
                   ::= {  staIproLogtablEntry 1 }

staIproLogtablSyst OBJECT-TYPE
                   SYNTAX DisplayString (SIZE(0..19))
                   MAX-ACCESS read-only
                   STATUS current
                   DESCRIPTION "System-time"
                   ::= {  staIproLogtablEntry 2 }

staIproLogtablSrca OBJECT-TYPE
                   SYNTAX IpAddress
                   MAX-ACCESS read-only
                   STATUS current
                   DESCRIPTION "Src-Address"
                   ::= {  staIproLogtablEntry 3 }

staIproLogtablDsta OBJECT-TYPE
                   SYNTAX IpAddress
                   MAX-ACCESS read-only
                   STATUS current
                   DESCRIPTION "Dst-Address"
                   ::= {  staIproLogtablEntry 4 }

staIproLogtablProt OBJECT-TYPE
                   SYNTAX INTEGER (0..255)
                   MAX-ACCESS read-only
                   STATUS current
                   DESCRIPTION "Prot."
                   ::= {  staIproLogtablEntry 5 }

staIproLogtablSrcp OBJECT-TYPE
                   SYNTAX INTEGER (0..65535)
                   MAX-ACCESS read-only
                   STATUS current
                   DESCRIPTION "Src-Port"
                   ::= {  staIproLogtablEntry 6 }

staIproLogtablDstp OBJECT-TYPE
                   SYNTAX INTEGER (0..65535)
                   MAX-ACCESS read-only
                   STATUS current
                   DESCRIPTION "Dst-Port"
                   ::= {  staIproLogtablEntry 7 }

staIproLogtablFilt OBJECT-TYPE
                   SYNTAX DisplayString (SIZE(0..32))
                   MAX-ACCESS read-only
                   STATUS current
                   DESCRIPTION "Filter-Rule"
                   ::= {  staIproLogtablEntry 8 }

staIproLogtablLimi OBJECT-TYPE
                   SYNTAX INTEGER (0..2147483647)
                   MAX-ACCESS read-only
                   STATUS current
                   DESCRIPTION "Limit"
                   ::= {  staIproLogtablEntry 9 }

staIproLogtablThre OBJECT-TYPE
                   SYNTAX INTEGER (0..2147483647)
                   MAX-ACCESS read-only
                   STATUS current
                   DESCRIPTION "Threshold"
                   ::= {  staIproLogtablEntry 10 }

staIproLogtablActi OBJECT-TYPE
                   SYNTAX INTEGER (0..2147483647)
                   MAX-ACCESS read-only
                   STATUS current
                   DESCRIPTION "Action"
                   ::= {  staIproLogtablEntry 11 }

staIproHoconnlTable OBJECT-TYPE
                    SYNTAX SEQUENCE OF StaIproHoconnlEntry
                    MAX-ACCESS not-accessible
                    STATUS current
                    DESCRIPTION "HO-Conn.-List"
                    ::= {  staIpro 27 }

staIproHoconnlEntry OBJECT-TYPE
                    SYNTAX StaIproHoconnlEntry
                    MAX-ACCESS not-accessible
                    STATUS current
                    DESCRIPTION "entry in table"
                    INDEX { staIproHoconnlDst }
                    ::= {  staIproHoconnlTable 1 }

StaIproHoconnlEntry ::= SEQUENCE {
                    staIproHoconnlDst IpAddress,
                    staIproHoconnlNum INTEGER,
                    staIproHoconnlTim INTEGER
                   }

staIproHoconnlDst OBJECT-TYPE
                  SYNTAX IpAddress
                  MAX-ACCESS read-only
                  STATUS current
                  DESCRIPTION "Dst-Address"
                  ::= {  staIproHoconnlEntry 1 }

staIproHoconnlNum OBJECT-TYPE
                  SYNTAX INTEGER (0..2147483647)
                  MAX-ACCESS read-only
                  STATUS current
                  DESCRIPTION "Num-HO-Conn."
                  ::= {  staIproHoconnlEntry 2 }

staIproHoconnlTim OBJECT-TYPE
                  SYNTAX INTEGER (0..65535)
                  MAX-ACCESS read-only
                  STATUS current
                  DESCRIPTION "Timeout"
                  ::= {  staIproHoconnlEntry 3 }

staIproQosTable OBJECT-TYPE
                    SYNTAX SEQUENCE OF StaIproQosEntry
                    MAX-ACCESS not-accessible
                    STATUS current
                    DESCRIPTION "QoS"
                    ::= {  staIpro 28 }

staIproQosEntry OBJECT-TYPE
                    SYNTAX StaIproQosEntry
                    MAX-ACCESS not-accessible
                    STATUS current
                    DESCRIPTION "entry in table"
                    INDEX { staIproQosIfc }
                    ::= {  staIproQosTable 1 }

StaIproQosEntry ::= SEQUENCE {
                    staIproQosIfc INTEGER,
                    staIproQosPeer DisplayString,
                    staIproQosUpstr INTEGER,
                    staIproQosDowns INTEGER,
                    staIproQosRxres INTEGER,
                    staIproQosRxreq INTEGER,
                    staIproQosRxblo INTEGER,
                    staIproQosTxres INTEGER,
                    staIproQosTxreq INTEGER,
                    staIproQosTxfav INTEGER,
                    staIproQosTxblo INTEGER,
                    staIproQosFragm INTEGER,
                    staIproQosPmtus INTEGER
                   }

staIproQosIfc OBJECT-TYPE
                SYNTAX INTEGER
                {
                  dsl-ch-1(1),
                  dsl-ch-2(2),
                  dsl-ch-3(3),
                  dsl-ch-4(4),
                  dsl-ch-5(5),
                  dsl-ch-6(6),
                  dsl-ch-7(7),
                  dsl-ch-8(8),
                  ch01(9),
                  ch02(10),
                  ext(11)
                }
                MAX-ACCESS read-only
                STATUS current
                DESCRIPTION "Ifc"
                ::= {  staIproQosEntry 1 }

staIproQosPeer OBJECT-TYPE
                SYNTAX DisplayString (SIZE(0..16))
                MAX-ACCESS read-only
                STATUS current
                DESCRIPTION "Peer"
                ::= {  staIproQosEntry 2 }

staIproQosUpstr OBJECT-TYPE
                SYNTAX INTEGER (0..2147483647)
                MAX-ACCESS read-only
                STATUS current
                DESCRIPTION "Upstream-Rate"
                ::= {  staIproQosEntry 8 }

staIproQosDowns OBJECT-TYPE
                SYNTAX INTEGER (0..2147483647)
                MAX-ACCESS read-only
                STATUS current
                DESCRIPTION "Downstream-Rate"
                ::= {  staIproQosEntry 3 }

staIproQosRxres OBJECT-TYPE
                SYNTAX INTEGER (0..2147483647)
                MAX-ACCESS read-only
                STATUS current
                DESCRIPTION "Rx-reserved"
                ::= {  staIproQosEntry 4 }

staIproQosRxreq OBJECT-TYPE
                SYNTAX INTEGER (0..2147483647)
                MAX-ACCESS read-only
                STATUS current
                DESCRIPTION "Rx-requested"
                ::= {  staIproQosEntry 11 }

staIproQosRxblo OBJECT-TYPE
                SYNTAX INTEGER (0..65535)
                MAX-ACCESS read-only
                STATUS current
                DESCRIPTION "Rx-blocks-pending"
                ::= {  staIproQosEntry 5 }

staIproQosTxres OBJECT-TYPE
                SYNTAX INTEGER (0..2147483647)
                MAX-ACCESS read-only
                STATUS current
                DESCRIPTION "Tx-reserved"
                ::= {  staIproQosEntry 9 }

staIproQosTxreq OBJECT-TYPE
                SYNTAX INTEGER (0..2147483647)
                MAX-ACCESS read-only
                STATUS current
                DESCRIPTION "Tx-requested"
                ::= {  staIproQosEntry 12 }

staIproQosTxfav OBJECT-TYPE
                SYNTAX INTEGER (0..2147483647)
                MAX-ACCESS read-only
                STATUS current
                DESCRIPTION "Tx-favoured"
                ::= {  staIproQosEntry 13 }

staIproQosTxblo OBJECT-TYPE
                SYNTAX INTEGER (0..65535)
                MAX-ACCESS read-only
                STATUS current
                DESCRIPTION "Tx-blocks-pending"
                ::= {  staIproQosEntry 10 }

staIproQosFragm OBJECT-TYPE
                SYNTAX INTEGER (0..65535)
                MAX-ACCESS read-only
                STATUS current
                DESCRIPTION "Fragment-size"
                ::= {  staIproQosEntry 6 }

staIproQosPmtus OBJECT-TYPE
                SYNTAX INTEGER (0..65535)
                MAX-ACCESS read-only
                STATUS current
                DESCRIPTION "PMTU-size"
                ::= {  staIproQosEntry 7 }

staIproRules OBJECT-TYPE
               SYNTAX INTEGER
               MAX-ACCESS read-only
               STATUS current
               DESCRIPTION "Rules"
               ::= {  staIpro 34 }

staIproFilter OBJECT-TYPE
               SYNTAX INTEGER
               MAX-ACCESS read-only
               STATUS current
               DESCRIPTION "Filter"
               ::= {  staIpro 35 }

staIproL4error OBJECT-TYPE
               SYNTAX Counter32
               MAX-ACCESS read-only
               STATUS current
               DESCRIPTION "L4-Errors"
               ::= {  staIpro 31 }

staIproLoadbal OBJECT IDENTIFIER ::= { staIpro 32}
staIproLoadbalOpe OBJECT-TYPE
                  SYNTAX INTEGER
                  {
                    no(0),
                    yes(1)
                  }
                  MAX-ACCESS read-only
                  STATUS current
                  DESCRIPTION "Operating"
                  ::= {  staIproLoadbal 1 }

staIproLoadbalConTable OBJECT-TYPE
                       SYNTAX SEQUENCE OF StaIproLoadbalConEntry
                       MAX-ACCESS not-accessible
                       STATUS current
                       DESCRIPTION "Connections"
                       ::= {  staIproLoadbal 2 }

staIproLoadbalConEntry OBJECT-TYPE
                       SYNTAX StaIproLoadbalConEntry
                       MAX-ACCESS not-accessible
                       STATUS current
                       DESCRIPTION "entry in table"
                       INDEX { staIproLoadbalConPee, staIproLoadbalConBun }
                       ::= {  staIproLoadbalConTable 1 }

StaIproLoadbalConEntry ::= SEQUENCE {
                       staIproLoadbalConPee DisplayString,
                       staIproLoadbalConBun DisplayString,
                       staIproLoadbalConSta INTEGER,
                       staIproLoadbalConTcp INTEGER,
                       staIproLoadbalConPpt INTEGER,
                       staIproLoadbalConVpn INTEGER
                      }

staIproLoadbalConPee OBJECT-TYPE
                     SYNTAX DisplayString (SIZE(0..16))
                     MAX-ACCESS read-only
                     STATUS current
                     DESCRIPTION "Peer"
                     ::= {  staIproLoadbalConEntry 1 }

staIproLoadbalConBun OBJECT-TYPE
                     SYNTAX DisplayString (SIZE(0..16))
                     MAX-ACCESS read-only
                     STATUS current
                     DESCRIPTION "Bundle-Peer"
                     ::= {  staIproLoadbalConEntry 2 }

staIproLoadbalConSta OBJECT-TYPE
                     SYNTAX INTEGER
                     {
                       ready(2),
                       connection(7),
                       disconnecting(8)
                     }
                     MAX-ACCESS read-only
                     STATUS current
                     DESCRIPTION "State"
                     ::= {  staIproLoadbalConEntry 3 }

staIproLoadbalConTcp OBJECT-TYPE
                     SYNTAX INTEGER (0..2147483647)
                     MAX-ACCESS read-only
                     STATUS current
                     DESCRIPTION "TCP/IP-Sessions"
                     ::= {  staIproLoadbalConEntry 4 }

staIproLoadbalConPpt OBJECT-TYPE
                     SYNTAX INTEGER (0..2147483647)
                     MAX-ACCESS read-only
                     STATUS current
                     DESCRIPTION "PPTP-Sessions"
                     ::= {  staIproLoadbalConEntry 5 }

staIproLoadbalConVpn OBJECT-TYPE
                     SYNTAX INTEGER (0..2147483647)
                     MAX-ACCESS read-only
                     STATUS current
                     DESCRIPTION "VPN-Sessions"
                     ::= {  staIproLoadbalConEntry 6 }

staIproVrrp OBJECT IDENTIFIER ::= { staIpro 33}
staIproVrrpOpe OBJECT-TYPE
               SYNTAX INTEGER
               {
                 no(0),
                 yes(1)
               }
               MAX-ACCESS read-only
               STATUS current
               DESCRIPTION "Operating"
               ::= {  staIproVrrp 5 }

staIproVrrpRx OBJECT-TYPE
               SYNTAX Counter32
               MAX-ACCESS read-only
               STATUS current
               DESCRIPTION "Rx"
               ::= {  staIproVrrp 1 }

staIproVrrpTx OBJECT-TYPE
               SYNTAX Counter32
               MAX-ACCESS read-only
               STATUS current
               DESCRIPTION "Tx"
               ::= {  staIproVrrp 2 }

staIproVrrpErr OBJECT-TYPE
               SYNTAX Counter32
               MAX-ACCESS read-only
               STATUS current
               DESCRIPTION "Error"
               ::= {  staIproVrrp 3 }

staIproVrrpDro OBJECT-TYPE
               SYNTAX Counter32
               MAX-ACCESS read-only
               STATUS current
               DESCRIPTION "Drop"
               ::= {  staIproVrrp 4 }

staIproVrrpInt OBJECT-TYPE
               SYNTAX INTEGER
               {
                 no(0),
                 yes(1)
               }
               MAX-ACCESS read-only
               STATUS current
               DESCRIPTION "Internal-Services"
               ::= {  staIproVrrp 6 }

staIproVrrpVirTable OBJECT-TYPE
                    SYNTAX SEQUENCE OF StaIproVrrpVirEntry
                    MAX-ACCESS not-accessible
                    STATUS current
                    DESCRIPTION "Virtual-Router"
                    ::= {  staIproVrrp 10 }

staIproVrrpVirEntry OBJECT-TYPE
                    SYNTAX StaIproVrrpVirEntry
                    MAX-ACCESS not-accessible
                    STATUS current
                    DESCRIPTION "entry in table"
                    INDEX { staIproVrrpVirRou }
                    ::= {  staIproVrrpVirTable 1 }

StaIproVrrpVirEntry ::= SEQUENCE {
                    staIproVrrpVirRou INTEGER,
                    staIproVrrpVirVir IpAddress,
                    staIproVrrpVirPri INTEGER,
                    staIproVrrpVirBpr INTEGER,
                    staIproVrrpVirPee DisplayString,
                    staIproVrrpVirSta INTEGER,
                    staIproVrrpVirBac INTEGER,
                    staIproVrrpVirMas IpAddress,
                    staIproVrrpVirPor INTEGER,
                    staIproVrrpVirVla INTEGER,
                    staIproVrrpVirNet DisplayString
                   }

staIproVrrpVirRou OBJECT-TYPE
                  SYNTAX INTEGER (0..255)
                  MAX-ACCESS read-only
                  STATUS current
                  DESCRIPTION "Router-ID"
                  ::= {  staIproVrrpVirEntry 1 }

staIproVrrpVirVir OBJECT-TYPE
                  SYNTAX IpAddress
                  MAX-ACCESS read-only
                  STATUS current
                  DESCRIPTION "virt.-Address"
                  ::= {  staIproVrrpVirEntry 2 }

staIproVrrpVirPri OBJECT-TYPE
                  SYNTAX INTEGER (0..255)
                  MAX-ACCESS read-only
                  STATUS current
                  DESCRIPTION "Prio"
                  ::= {  staIproVrrpVirEntry 3 }

staIproVrrpVirBpr OBJECT-TYPE
                  SYNTAX INTEGER (0..255)
                  MAX-ACCESS read-only
                  STATUS current
                  DESCRIPTION "B-Prio"
                  ::= {  staIproVrrpVirEntry 4 }

staIproVrrpVirPee OBJECT-TYPE
                  SYNTAX DisplayString (SIZE(0..16))
                  MAX-ACCESS read-only
                  STATUS current
                  DESCRIPTION "Peer"
                  ::= {  staIproVrrpVirEntry 5 }

staIproVrrpVirSta OBJECT-TYPE
                  SYNTAX INTEGER
                  {
                    init(0),
                    listen(1),
                    standby(2),
                    master(3),
                    down(4),
                    reconnect(5)
                  }
                  MAX-ACCESS read-only
                  STATUS current
                  DESCRIPTION "State"
                  ::= {  staIproVrrpVirEntry 6 }

staIproVrrpVirBac OBJECT-TYPE
                  SYNTAX INTEGER
                  {
                    no(0),
                    yes(1)
                  }
                  MAX-ACCESS read-only
                  STATUS current
                  DESCRIPTION "Backup"
                  ::= {  staIproVrrpVirEntry 7 }

staIproVrrpVirMas OBJECT-TYPE
                  SYNTAX IpAddress
                  MAX-ACCESS read-only
                  STATUS current
                  DESCRIPTION "Master"
                  ::= {  staIproVrrpVirEntry 8 }

staIproVrrpVirPor OBJECT-TYPE
                  SYNTAX INTEGER
                  {
                    lan-1(0),
                    lan-2(1),
                    lan-3(2),
                    lan-4(3),
                    any(255)
                  }
                  MAX-ACCESS read-only
                  STATUS current
                  DESCRIPTION "Port"
                  ::= {  staIproVrrpVirEntry 9 }

staIproVrrpVirVla OBJECT-TYPE
                  SYNTAX INTEGER (0..65535)
                  MAX-ACCESS read-only
                  STATUS current
                  DESCRIPTION "VLAN-ID"
                  ::= {  staIproVrrpVirEntry 10 }

staIproVrrpVirNet OBJECT-TYPE
                  SYNTAX DisplayString (SIZE(0..16))
                  MAX-ACCESS read-only
                  STATUS current
                  DESCRIPTION "Network-name"
                  ::= {  staIproVrrpVirEntry 11 }

staIproVrrpMacTable OBJECT-TYPE
                    SYNTAX SEQUENCE OF StaIproVrrpMacEntry
                    MAX-ACCESS not-accessible
                    STATUS current
                    DESCRIPTION "MAC-List"
                    ::= {  staIproVrrp 11 }

staIproVrrpMacEntry OBJECT-TYPE
                    SYNTAX StaIproVrrpMacEntry
                    MAX-ACCESS not-accessible
                    STATUS current
                    DESCRIPTION "entry in table"
                    INDEX { staIproVrrpMacVir }
                    ::= {  staIproVrrpMacTable 1 }

StaIproVrrpMacEntry ::= SEQUENCE {
                    staIproVrrpMacVir IpAddress,
                    staIproVrrpMacMac MacAddress,
                    staIproVrrpMacRou INTEGER
                   }

staIproVrrpMacVir OBJECT-TYPE
                  SYNTAX IpAddress
                  MAX-ACCESS read-only
                  STATUS current
                  DESCRIPTION "virt.-Address"
                  ::= {  staIproVrrpMacEntry 1 }

staIproVrrpMacMac OBJECT-TYPE
                  SYNTAX MacAddress
                  MAX-ACCESS read-only
                  STATUS current
                  DESCRIPTION "MAC-Address"
                  ::= {  staIproVrrpMacEntry 2 }

staIproVrrpMacRou OBJECT-TYPE
                  SYNTAX INTEGER (0..255)
                  MAX-ACCESS read-only
                  STATUS current
                  DESCRIPTION "Router-ID"
                  ::= {  staIproVrrpMacEntry 3 }

staIproVrrpEveTable OBJECT-TYPE
                    SYNTAX SEQUENCE OF StaIproVrrpEveEntry
                    MAX-ACCESS not-accessible
                    STATUS current
                    DESCRIPTION "Event-Log"
                    ::= {  staIproVrrp 12 }

staIproVrrpEveEntry OBJECT-TYPE
                    SYNTAX StaIproVrrpEveEntry
                    MAX-ACCESS not-accessible
                    STATUS current
                    DESCRIPTION "entry in table"
                    INDEX { staIproVrrpEveIdx }
                    ::= {  staIproVrrpEveTable 1 }

StaIproVrrpEveEntry ::= SEQUENCE {
                    staIproVrrpEveIdx INTEGER,
                    staIproVrrpEveSys DisplayString,
                    staIproVrrpEveSrc IpAddress,
                    staIproVrrpEveVri INTEGER,
                    staIproVrrpEveEve INTEGER,
                    staIproVrrpEveInf DisplayString
                   }

staIproVrrpEveIdx OBJECT-TYPE
                  SYNTAX INTEGER (0..65535)
                  MAX-ACCESS read-only
                  STATUS current
                  DESCRIPTION "Idx."
                  ::= {  staIproVrrpEveEntry 1 }

staIproVrrpEveSys OBJECT-TYPE
                  SYNTAX DisplayString (SIZE(0..19))
                  MAX-ACCESS read-only
                  STATUS current
                  DESCRIPTION "System-time"
                  ::= {  staIproVrrpEveEntry 2 }

staIproVrrpEveSrc OBJECT-TYPE
                  SYNTAX IpAddress
                  MAX-ACCESS read-only
                  STATUS current
                  DESCRIPTION "Src-Address"
                  ::= {  staIproVrrpEveEntry 3 }

staIproVrrpEveVri OBJECT-TYPE
                  SYNTAX INTEGER (0..255)
                  MAX-ACCESS read-only
                  STATUS current
                  DESCRIPTION "VRID"
                  ::= {  staIproVrrpEveEntry 4 }

staIproVrrpEveEve OBJECT-TYPE
                  SYNTAX INTEGER
                  {
                    invalid-ttl(1),
                    invalid-version(2),
                    bad-number-of-virtual-addresses(3),
                    bad-authentication-type(4),
                    bad-advertisement-interval(5),
                    invalid-vrid(6),
                    invalid-router-address(7),
                    invalid-priority(8),
                    virtual-router-stopped(9),
                    virtual-router-started(10),
                    link-up(11),
                    link-down(12),
                    new-master(13),
                    backup-started(14),
                    backup-ended(15)
                  }
                  MAX-ACCESS read-only
                  STATUS current
                  DESCRIPTION "Event"
                  ::= {  staIproVrrpEveEntry 5 }

staIproVrrpEveInf OBJECT-TYPE
                  SYNTAX DisplayString (SIZE(0..255))
                  MAX-ACCESS read-only
                  STATUS current
                  DESCRIPTION "Info"
                  ::= {  staIproVrrpEveEntry 6 }

staIproVrrpDel OBJECT-TYPE
               SYNTAX DisplayString
               MAX-ACCESS read-write
               STATUS current
               DESCRIPTION "Delete-Values"
               ::= {  staIproVrrp 20 }

staIproActiproTable OBJECT-TYPE
                    SYNTAX SEQUENCE OF StaIproActiproEntry
                    MAX-ACCESS not-accessible
                    STATUS current
                    DESCRIPTION "Act.-IP-Routing-Tab."
                    ::= {  staIpro 30 }

staIproActiproEntry OBJECT-TYPE
                    SYNTAX StaIproActiproEntry
                    MAX-ACCESS not-accessible
                    STATUS current
                    DESCRIPTION "entry in table"
                    INDEX { staIproActiproIpa, staIproActiproIpn, staIproActiproRtg }
                    ::= {  staIproActiproTable 1 }

StaIproActiproEntry ::= SEQUENCE {
                    staIproActiproIpa IpAddress,
                    staIproActiproIpn IpAddress,
                    staIproActiproRtg INTEGER,
                    staIproActiproGat IpAddress,
                    staIproActiproPee DisplayString,
                    staIproActiproDis INTEGER,
                    staIproActiproMas INTEGER,
                    staIproActiproTyp INTEGER
                   }

staIproActiproIpa OBJECT-TYPE
                  SYNTAX IpAddress
                  MAX-ACCESS read-only
                  STATUS current
                  DESCRIPTION "IP-Address"
                  ::= {  staIproActiproEntry 1 }

staIproActiproIpn OBJECT-TYPE
                  SYNTAX IpAddress
                  MAX-ACCESS read-only
                  STATUS current
                  DESCRIPTION "IP-Netmask"
                  ::= {  staIproActiproEntry 2 }

staIproActiproRtg OBJECT-TYPE
                  SYNTAX INTEGER (0..65535)
                  MAX-ACCESS read-only
                  STATUS current
                  DESCRIPTION "Rtg-tag"
                  ::= {  staIproActiproEntry 3 }

staIproActiproGat OBJECT-TYPE
                  SYNTAX IpAddress
                  MAX-ACCESS read-only
                  STATUS current
                  DESCRIPTION "Gateway"
                  ::= {  staIproActiproEntry 4 }

staIproActiproPee OBJECT-TYPE
                  SYNTAX DisplayString (SIZE(0..255))
                  MAX-ACCESS read-only
                  STATUS current
                  DESCRIPTION "Peer"
                  ::= {  staIproActiproEntry 5 }

staIproActiproDis OBJECT-TYPE
                  SYNTAX INTEGER (0..255)
                  MAX-ACCESS read-only
                  STATUS current
                  DESCRIPTION "Distance"
                  ::= {  staIproActiproEntry 6 }

staIproActiproMas OBJECT-TYPE
                  SYNTAX INTEGER
                  {
                    no(0),
                    on(1),
                    intranet(2),
                    unknown(255)
                  }
                  MAX-ACCESS read-only
                  STATUS current
                  DESCRIPTION "Masquerade"
                  ::= {  staIproActiproEntry 7 }

staIproActiproTyp OBJECT-TYPE
                  SYNTAX INTEGER
                  {
                    unknown(0),
                    static(1),
                    rip(2),
                    vpn(3),
                    capwap(4)
                  }
                  MAX-ACCESS read-only
                  STATUS current
                  DESCRIPTION "Type"
                  ::= {  staIproActiproEntry 8 }

staConf OBJECT IDENTIFIER ::= { sta 11}
staConfLanactiv OBJECT-TYPE
                SYNTAX INTEGER
                MAX-ACCESS read-only
                STATUS current
                DESCRIPTION "LAN-Active-Connections"
                ::= {  staConf 1 }

staConfLantotal OBJECT-TYPE
                SYNTAX Counter32
                MAX-ACCESS read-only
                STATUS current
                DESCRIPTION "LAN-Total-Connections"
                ::= {  staConf 2 }

staConfWanactiv OBJECT-TYPE
                SYNTAX INTEGER
                MAX-ACCESS read-only
                STATUS current
                DESCRIPTION "WAN-Active-Connections"
                ::= {  staConf 3 }

staConfWantotal OBJECT-TYPE
                SYNTAX Counter32
                MAX-ACCESS read-only
                STATUS current
                DESCRIPTION "WAN-Total-Connections"
                ::= {  staConf 4 }

staConfOutbanda OBJECT-TYPE
                SYNTAX INTEGER
                MAX-ACCESS read-only
                STATUS current
                DESCRIPTION "Outband-Active-Connections"
                ::= {  staConf 5 }

staConfOutbandt OBJECT-TYPE
                SYNTAX Counter32
                MAX-ACCESS read-only
                STATUS current
                DESCRIPTION "Outband-total-Connections"
                ::= {  staConf 6 }

staConfOutbandb OBJECT-TYPE
                SYNTAX INTEGER
                MAX-ACCESS read-only
                STATUS current
                DESCRIPTION "Outband-Bitrate"
                ::= {  staConf 7 }

staConfLoginerr OBJECT-TYPE
                SYNTAX Counter32
                MAX-ACCESS read-only
                STATUS current
                DESCRIPTION "Login-Errors"
                ::= {  staConf 8 }

staConfLoginloc OBJECT-TYPE
                SYNTAX Counter32
                MAX-ACCESS read-only
                STATUS current
                DESCRIPTION "Login-Locks"
                ::= {  staConf 9 }

staConfLoginrej OBJECT-TYPE
                SYNTAX Counter32
                MAX-ACCESS read-only
                STATUS current
                DESCRIPTION "Login-Rejects"
                ::= {  staConf 10 }

staConfStartsca OBJECT-TYPE
                SYNTAX DisplayString
                MAX-ACCESS read-write
                STATUS current
                DESCRIPTION "Start-Scan"
                ::= {  staConf 13 }

staConfScanresuTable OBJECT-TYPE
                     SYNTAX SEQUENCE OF StaConfScanresuEntry
                     MAX-ACCESS not-accessible
                     STATUS current
                     DESCRIPTION "Scan-Results"
                     ::= {  staConf 14 }

staConfScanresuEntry OBJECT-TYPE
                     SYNTAX StaConfScanresuEntry
                     MAX-ACCESS not-accessible
                     STATUS current
                     DESCRIPTION "entry in table"
                     INDEX { staConfScanresuIpadd, staConfScanresuRtgta }
                     ::= {  staConfScanresuTable 1 }

StaConfScanresuEntry ::= SEQUENCE {
                     staConfScanresuIpadd IpAddress,
                     staConfScanresuRtgta INTEGER,
                     staConfScanresuName DisplayString,
                     staConfScanresuDevic DisplayString,
                     staConfScanresuVersi DisplayString,
                     staConfScanresuCapip INTEGER,
                     staConfScanresuHttpp INTEGER,
                     staConfScanresuHttps INTEGER,
                     staConfScanresuState INTEGER
                    }

staConfScanresuIpadd OBJECT-TYPE
                     SYNTAX IpAddress
                     MAX-ACCESS read-only
                     STATUS current
                     DESCRIPTION "IP-Address"
                     ::= {  staConfScanresuEntry 1 }

staConfScanresuRtgta OBJECT-TYPE
                     SYNTAX INTEGER (0..65535)
                     MAX-ACCESS read-only
                     STATUS current
                     DESCRIPTION "Rtg-tag"
                     ::= {  staConfScanresuEntry 9 }

staConfScanresuName OBJECT-TYPE
                     SYNTAX DisplayString (SIZE(0..17))
                     MAX-ACCESS read-only
                     STATUS current
                     DESCRIPTION "Name"
                     ::= {  staConfScanresuEntry 2 }

staConfScanresuDevic OBJECT-TYPE
                     SYNTAX DisplayString (SIZE(0..64))
                     MAX-ACCESS read-only
                     STATUS current
                     DESCRIPTION "Device-Type"
                     ::= {  staConfScanresuEntry 3 }

staConfScanresuVersi OBJECT-TYPE
                     SYNTAX DisplayString (SIZE(0..30))
                     MAX-ACCESS read-only
                     STATUS current
                     DESCRIPTION "Version"
                     ::= {  staConfScanresuEntry 4 }

staConfScanresuCapip OBJECT-TYPE
                     SYNTAX INTEGER (0..65535)
                     MAX-ACCESS read-only
                     STATUS current
                     DESCRIPTION "CAPI-Port"
                     ::= {  staConfScanresuEntry 6 }

staConfScanresuHttpp OBJECT-TYPE
                     SYNTAX INTEGER (0..65535)
                     MAX-ACCESS read-only
                     STATUS current
                     DESCRIPTION "HTTP-Port"
                     ::= {  staConfScanresuEntry 7 }

staConfScanresuHttps OBJECT-TYPE
                     SYNTAX INTEGER (0..65535)
                     MAX-ACCESS read-only
                     STATUS current
                     DESCRIPTION "HTTPS-Port"
                     ::= {  staConfScanresuEntry 8 }

staConfScanresuState OBJECT-TYPE
                     SYNTAX INTEGER
                     {
                       scanning(0),
                       ready(1),
                       error(2)
                     }
                     MAX-ACCESS read-only
                     STATUS current
                     DESCRIPTION "State"
                     ::= {  staConfScanresuEntry 5 }

staConfFeaturesTable OBJECT-TYPE
                     SYNTAX SEQUENCE OF StaConfFeaturesEntry
                     MAX-ACCESS not-accessible
                     STATUS current
                     DESCRIPTION "Features"
                     ::= {  staConf 16 }

staConfFeaturesEntry OBJECT-TYPE
                     SYNTAX StaConfFeaturesEntry
                     MAX-ACCESS not-accessible
                     STATUS current
                     DESCRIPTION "entry in table"
                     INDEX { staConfFeaturesFea }
                     ::= {  staConfFeaturesTable 1 }

StaConfFeaturesEntry ::= SEQUENCE {
                     staConfFeaturesFea INTEGER,
                     staConfFeaturesExp DisplayString
                    }

staConfFeaturesFea OBJECT-TYPE
                   SYNTAX INTEGER
                   {
                     ipx(1),
                     lan-bridge(2),
                     lancapi(3),
                     leased-line(4),
                     switched-line(5),
                     dsl-interface(6),
                     fax(7),
                     modem(8),
                     vpn-5(9),
                     vpn-25(10),
                     vpn-25-old(11),
                     vpn-50-old(12),
                     vpn-100(13),
                     wlc-4025-100(14),
                     wlan-point-to-point(15),
                     public-spot(16),
                     vpn-200(17),
                     vpn-500(18),
                     vpn-1000(19),
                     hermes1-wpa(20),
                     vpn-3(21),
                     umts(22),
                     dynamic-vpn(23),
                     wlan-5ghz(24),
                     wlan-no-encryption(25),
                     voip-advanced-32(26),
                     voip-basic(27),
                     wlan-fcc-restrictions(28),
                     wlc-4025-50(29),
                     wlc-4006-12(30),
                     voip-advanced-8(31),
                     unused(32),
                     unused(33),
                     utm-antivirus-small(34),
                     utm-antispam-small(35),
                     utm-contentfilter-small(36),
                     wlc-public-spot(37),
                     wlan-monitor-mode(38),
                     wlan-no-5ghz(39)
                   }
                   MAX-ACCESS read-only
                   STATUS current
                   DESCRIPTION "Feature"
                   ::= {  staConfFeaturesEntry 1 }

staConfFeaturesExp OBJECT-TYPE
                   SYNTAX DisplayString (SIZE(0..255))
                   MAX-ACCESS read-only
                   STATUS current
                   DESCRIPTION "Expire"
                   ::= {  staConfFeaturesEntry 2 }

staConfAntithef OBJECT IDENTIFIER ::= { staConf 15}
staConfAntithefState OBJECT-TYPE
                     SYNTAX INTEGER
                     {
                       disabled(0),
                       active(1),
                       successfull(2),
                       locked(3)
                     }
                     MAX-ACCESS read-only
                     STATUS current
                     DESCRIPTION "State"
                     ::= {  staConfAntithef 1 }

staConfAntithefSendi OBJECT-TYPE
                     SYNTAX DisplayString (SIZE(0..14))
                     MAX-ACCESS read-only
                     STATUS current
                     DESCRIPTION "sending-call-to"
                     ::= {  staConfAntithef 2 }

staConfAntithefWaiti OBJECT-TYPE
                     SYNTAX DisplayString (SIZE(0..14))
                     MAX-ACCESS read-only
                     STATUS current
                     DESCRIPTION "waiting-for-call-from"
                     ::= {  staConfAntithef 3 }

staConfAntithefLasts OBJECT-TYPE
                     SYNTAX DisplayString (SIZE(0..14))
                     MAX-ACCESS read-only
                     STATUS current
                     DESCRIPTION "last-seen-call-from"
                     ::= {  staConfAntithef 4 }

staConfAntithefCalla OBJECT-TYPE
                     SYNTAX INTEGER
                     {
                       no(0),
                       yes(1)
                     }
                     MAX-ACCESS read-only
                     STATUS current
                     DESCRIPTION "call-accepted"
                     ::= {  staConfAntithef 5 }

staConfAntithefIncom OBJECT-TYPE
                     SYNTAX INTEGER
                     {
                       no(0),
                       yes(1)
                     }
                     MAX-ACCESS read-only
                     STATUS current
                     DESCRIPTION "incoming-call"
                     ::= {  staConfAntithef 7 }

staConfAntithefLaste OBJECT-TYPE
                     SYNTAX INTEGER
                     {
                       unknown(0),
                       unallocated-number(1),
                       no-route-to-destination(3),
                       normal-call-clearing(16),
                       user-busy(17),
                       no-user-responding(18),
                       user-alerting-no-answer(19),
                       call-rejected(21),
                       number-changed(22),
                       non-selected-user-clearing(26),
                       destination-out-of-order(27),
                       normal-unspecified(31),
                       no-channel-available(34),
                       switching-equipment-congestion(42),
                       invalid-call-reference-number(81),
                       incompatible-destination(88),
                       temp-failure(41),
                       facility-not-subscribed(50),
                       facility-not-available(63)
                     }
                     MAX-ACCESS read-only
                     STATUS current
                     DESCRIPTION "last-error"
                     ::= {  staConfAntithef 6 }

staConfAntithefMetho OBJECT-TYPE
                     SYNTAX INTEGER
                     {
                       basic-call(0),
                       facility(1)
                     }
                     MAX-ACCESS read-only
                     STATUS current
                     DESCRIPTION "Method"
                     ::= {  staConfAntithef 8 }

staConfLl2m OBJECT IDENTIFIER ::= { staConf 65}
staConfLl2mRxpa OBJECT-TYPE
                SYNTAX INTEGER
                MAX-ACCESS read-only
                STATUS current
                DESCRIPTION "Rx-Packets"
                ::= {  staConfLl2m 1 }

staConfLl2mRxbr OBJECT-TYPE
                SYNTAX INTEGER
                MAX-ACCESS read-only
                STATUS current
                DESCRIPTION "Rx-Broadcast-Packets"
                ::= {  staConfLl2m 2 }

staConfLl2mRxmu OBJECT-TYPE
                SYNTAX INTEGER
                MAX-ACCESS read-only
                STATUS current
                DESCRIPTION "Rx-Multicast-Packets"
                ::= {  staConfLl2m 3 }

staConfLl2mRxun OBJECT-TYPE
                SYNTAX INTEGER
                MAX-ACCESS read-only
                STATUS current
                DESCRIPTION "Rx-Unicast-Packets"
                ::= {  staConfLl2m 4 }

staConfLl2mRxdi OBJECT-TYPE
                SYNTAX INTEGER
                MAX-ACCESS read-only
                STATUS current
                DESCRIPTION "Rx-Discard"
                ::= {  staConfLl2m 5 }

staConfLl2mRxma OBJECT-TYPE
                SYNTAX INTEGER
                MAX-ACCESS read-only
                STATUS current
                DESCRIPTION "Rx-Malformed"
                ::= {  staConfLl2m 6 }

staConfLl2mServ OBJECT IDENTIFIER ::= { staConfLl2m 20}
staConfLl2mServRxp OBJECT-TYPE
                   SYNTAX INTEGER
                   MAX-ACCESS read-only
                   STATUS current
                   DESCRIPTION "Rx-Packets"
                   ::= {  staConfLl2mServ 1 }

staConfLl2mServRxb OBJECT-TYPE
                   SYNTAX INTEGER
                   MAX-ACCESS read-only
                   STATUS current
                   DESCRIPTION "Rx-Broadcast-Packets"
                   ::= {  staConfLl2mServ 2 }

staConfLl2mServRxm OBJECT-TYPE
                   SYNTAX INTEGER
                   MAX-ACCESS read-only
                   STATUS current
                   DESCRIPTION "Rx-Multicast-Packets"
                   ::= {  staConfLl2mServ 3 }

staConfLl2mServRxu OBJECT-TYPE
                   SYNTAX INTEGER
                   MAX-ACCESS read-only
                   STATUS current
                   DESCRIPTION "Rx-Unicast-Packets"
                   ::= {  staConfLl2mServ 4 }

staConfLl2mServRxd OBJECT-TYPE
                   SYNTAX INTEGER
                   MAX-ACCESS read-only
                   STATUS current
                   DESCRIPTION "Rx-Discard"
                   ::= {  staConfLl2mServ 5 }

staConfLl2mServDel OBJECT-TYPE
                   SYNTAX DisplayString
                   MAX-ACCESS read-write
                   STATUS current
                   DESCRIPTION "Delete-Values"
                   ::= {  staConfLl2mServ 99 }

staConfLl2mClie OBJECT IDENTIFIER ::= { staConfLl2m 30}
staConfLl2mClieRxp OBJECT-TYPE
                   SYNTAX INTEGER
                   MAX-ACCESS read-only
                   STATUS current
                   DESCRIPTION "Rx-Packets"
                   ::= {  staConfLl2mClie 1 }

staConfLl2mClieRxb OBJECT-TYPE
                   SYNTAX INTEGER
                   MAX-ACCESS read-only
                   STATUS current
                   DESCRIPTION "Rx-Broadcast-Packets"
                   ::= {  staConfLl2mClie 2 }

staConfLl2mClieRxm OBJECT-TYPE
                   SYNTAX INTEGER
                   MAX-ACCESS read-only
                   STATUS current
                   DESCRIPTION "Rx-Multicast-Packets"
                   ::= {  staConfLl2mClie 3 }

staConfLl2mClieRxu OBJECT-TYPE
                   SYNTAX INTEGER
                   MAX-ACCESS read-only
                   STATUS current
                   DESCRIPTION "Rx-Unicast-Packets"
                   ::= {  staConfLl2mClie 4 }

staConfLl2mClieRxd OBJECT-TYPE
                   SYNTAX INTEGER
                   MAX-ACCESS read-only
                   STATUS current
                   DESCRIPTION "Rx-Discard"
                   ::= {  staConfLl2mClie 5 }

staConfLl2mClieDel OBJECT-TYPE
                   SYNTAX DisplayString
                   MAX-ACCESS read-write
                   STATUS current
                   DESCRIPTION "Delete-Values"
                   ::= {  staConfLl2mClie 99 }

staConfLl2mDele OBJECT-TYPE
                SYNTAX DisplayString
                MAX-ACCESS read-write
                STATUS current
                DESCRIPTION "Delete-Values"
                ::= {  staConfLl2m 99 }

staConfDeleteva OBJECT-TYPE
                SYNTAX DisplayString
                MAX-ACCESS read-write
                STATUS current
                DESCRIPTION "Delete-Values"
                ::= {  staConf 11 }

staConfEventlogTable OBJECT-TYPE
                     SYNTAX SEQUENCE OF StaConfEventlogEntry
                     MAX-ACCESS not-accessible
                     STATUS current
                     DESCRIPTION "Event-Log"
                     ::= {  staConf 12 }

staConfEventlogEntry OBJECT-TYPE
                     SYNTAX StaConfEventlogEntry
                     MAX-ACCESS not-accessible
                     STATUS current
                     DESCRIPTION "entry in table"
                     INDEX { staConfEventlogIdx }
                     ::= {  staConfEventlogTable 1 }

StaConfEventlogEntry ::= SEQUENCE {
                     staConfEventlogIdx INTEGER,
                     staConfEventlogSyste DisplayString,
                     staConfEventlogEvent INTEGER,
                     staConfEventlogAcces INTEGER,
                     staConfEventlogIpadd IpAddress,
                     staConfEventlogInfo1 DisplayString,
                     staConfEventlogInfo2 DisplayString
                    }

staConfEventlogIdx OBJECT-TYPE
                     SYNTAX INTEGER (0..255)
                     MAX-ACCESS read-only
                     STATUS current
                     DESCRIPTION "Idx."
                     ::= {  staConfEventlogEntry 1 }

staConfEventlogSyste OBJECT-TYPE
                     SYNTAX DisplayString (SIZE(0..19))
                     MAX-ACCESS read-only
                     STATUS current
                     DESCRIPTION "System-time"
                     ::= {  staConfEventlogEntry 7 }

staConfEventlogEvent OBJECT-TYPE
                     SYNTAX INTEGER
                     {
                       fwuplstart(4),
                       uplsucc(5),
                       uplfailto(6),
                       uplfailincl(7),
                       uplfailbaddev(8),
                       login(9),
                       logout(10),
                       cnfuplstart(11),
                       cnfdnlstart(12),
                       cnfdnlsucc(13),
                       errlogin(29)
                     }
                     MAX-ACCESS read-only
                     STATUS current
                     DESCRIPTION "Event"
                     ::= {  staConfEventlogEntry 2 }

staConfEventlogAcces OBJECT-TYPE
                     SYNTAX INTEGER
                     {
                       outband(0),
                       telnet(1),
                       tftp(2),
                       http(3),
                       snmp(4),
                       https(5),
                       telnet-ssl(6),
                       ssh(7),
                       ll2m(8),
                       ppp(254),
                       unknown(255)
                     }
                     MAX-ACCESS read-only
                     STATUS current
                     DESCRIPTION "Access"
                     ::= {  staConfEventlogEntry 3 }

staConfEventlogIpadd OBJECT-TYPE
                     SYNTAX IpAddress
                     MAX-ACCESS read-only
                     STATUS current
                     DESCRIPTION "IP-Address"
                     ::= {  staConfEventlogEntry 4 }

staConfEventlogInfo1 OBJECT-TYPE
                     SYNTAX DisplayString (SIZE(0..32))
                     MAX-ACCESS read-only
                     STATUS current
                     DESCRIPTION "Info1"
                     ::= {  staConfEventlogEntry 5 }

staConfEventlogInfo2 OBJECT-TYPE
                     SYNTAX DisplayString (SIZE(0..64))
                     MAX-ACCESS read-only
                     STATUS current
                     DESCRIPTION "Info2"
                     ::= {  staConfEventlogEntry 6 }

staQueu OBJECT IDENTIFIER ::= { sta 12}
staQueuLanheap OBJECT-TYPE
               SYNTAX INTEGER
               MAX-ACCESS read-only
               STATUS current
               DESCRIPTION "LAN-Heap-Packets"
               ::= {  staQueu 1 }

staQueuQueuepa OBJECT-TYPE
               SYNTAX INTEGER
               MAX-ACCESS read-only
               STATUS current
               DESCRIPTION "Queue-Packets"
               ::= {  staQueu 2 }

staQueuWanheap OBJECT-TYPE
               SYNTAX INTEGER
               MAX-ACCESS read-only
               STATUS current
               DESCRIPTION "WAN-Heap-Packets"
               ::= {  staQueu 3 }

staQueuWanqueu OBJECT-TYPE
               SYNTAX INTEGER
               MAX-ACCESS read-only
               STATUS current
               DESCRIPTION "WAN-Queue-Packets"
               ::= {  staQueu 4 }

staQueuArpquer OBJECT-TYPE
               SYNTAX INTEGER
               MAX-ACCESS read-only
               STATUS current
               DESCRIPTION "ARP-query-Queue-Packets"
               ::= {  staQueu 7 }

staQueuArpqueu OBJECT-TYPE
               SYNTAX INTEGER
               MAX-ACCESS read-only
               STATUS current
               DESCRIPTION "ARP-Queue-Packets"
               ::= {  staQueu 8 }

staQueuIpqueue OBJECT-TYPE
               SYNTAX INTEGER
               MAX-ACCESS read-only
               STATUS current
               DESCRIPTION "IP-Queue-Packets"
               ::= {  staQueu 9 }

staQueuIpurgen OBJECT-TYPE
               SYNTAX INTEGER
               MAX-ACCESS read-only
               STATUS current
               DESCRIPTION "IP-urgent-Queue-Packets"
               ::= {  staQueu 10 }

staQueuIcmpque OBJECT-TYPE
               SYNTAX INTEGER
               MAX-ACCESS read-only
               STATUS current
               DESCRIPTION "ICMP-Queue-Packets"
               ::= {  staQueu 11 }

staQueuTcpqueu OBJECT-TYPE
               SYNTAX INTEGER
               MAX-ACCESS read-only
               STATUS current
               DESCRIPTION "TCP-Queue-Packets"
               ::= {  staQueu 12 }

staQueuTftpser OBJECT-TYPE
               SYNTAX INTEGER
               MAX-ACCESS read-only
               STATUS current
               DESCRIPTION "TFTP-server-Queue-Packets"
               ::= {  staQueu 13 }

staQueuSnmpque OBJECT-TYPE
               SYNTAX INTEGER
               MAX-ACCESS read-only
               STATUS current
               DESCRIPTION "SNMP-Queue-Packets"
               ::= {  staQueu 14 }

staQueuProthea OBJECT-TYPE
               SYNTAX INTEGER
               MAX-ACCESS read-only
               STATUS current
               DESCRIPTION "PROT-Heap-Packets"
               ::= {  staQueu 22 }

staQueuDhcpser OBJECT-TYPE
               SYNTAX INTEGER
               MAX-ACCESS read-only
               STATUS current
               DESCRIPTION "DHCP-server-Queue-Packets"
               ::= {  staQueu 27 }

staQueuDhcpcli OBJECT-TYPE
               SYNTAX INTEGER
               MAX-ACCESS read-only
               STATUS current
               DESCRIPTION "DHCP-client-Queue-Packets"
               ::= {  staQueu 28 }

staQueuIprripq OBJECT-TYPE
               SYNTAX INTEGER
               MAX-ACCESS read-only
               STATUS current
               DESCRIPTION "IPR-RIP-Queue-Packets"
               ::= {  staQueu 29 }

staQueuDnstxqu OBJECT-TYPE
               SYNTAX INTEGER
               MAX-ACCESS read-only
               STATUS current
               DESCRIPTION "DNS-TX-Queue-Packets"
               ::= {  staQueu 30 }

staQueuDnsrxqu OBJECT-TYPE
               SYNTAX INTEGER
               MAX-ACCESS read-only
               STATUS current
               DESCRIPTION "DNS-RX-Queue-Packets"
               ::= {  staQueu 31 }

staConnTable OBJECT-TYPE
             SYNTAX SEQUENCE OF StaConnEntry
             MAX-ACCESS not-accessible
             STATUS current
             DESCRIPTION "Connection"
             ::= {  sta 13 }

staConnEntry OBJECT-TYPE
             SYNTAX StaConnEntry
             MAX-ACCESS not-accessible
             STATUS current
             DESCRIPTION "entry in table"
             INDEX { staConnIfc }
             ::= {  staConnTable 1 }

StaConnEntry ::= SEQUENCE {
             staConnIfc INTEGER,
             staConnConn INTEGER,
             staConnActi INTEGER,
             staConnPass INTEGER,
             staConnErro INTEGER,
             staConnCont DisplayString,
             staConnChar INTEGER
            }

staConnIfc OBJECT-TYPE
            SYNTAX INTEGER
            {
              dsl-ch-1(1),
              dsl-ch-2(2),
              dsl-ch-3(3),
              dsl-ch-4(4),
              dsl-ch-5(5),
              dsl-ch-6(6),
              dsl-ch-7(7),
              dsl-ch-8(8),
              ch01(9),
              ch02(10),
              ext(11)
            }
            MAX-ACCESS read-only
            STATUS current
            DESCRIPTION "Ifc"
            ::= {  staConnEntry 1 }

staConnConn OBJECT-TYPE
            SYNTAX INTEGER (0..2147483647)
            MAX-ACCESS read-only
            STATUS current
            DESCRIPTION "Connections"
            ::= {  staConnEntry 2 }

staConnActi OBJECT-TYPE
            SYNTAX INTEGER (0..2147483647)
            MAX-ACCESS read-only
            STATUS current
            DESCRIPTION "active"
            ::= {  staConnEntry 3 }

staConnPass OBJECT-TYPE
            SYNTAX INTEGER (0..2147483647)
            MAX-ACCESS read-only
            STATUS current
            DESCRIPTION "passive"
            ::= {  staConnEntry 4 }

staConnErro OBJECT-TYPE
            SYNTAX INTEGER (0..2147483647)
            MAX-ACCESS read-only
            STATUS current
            DESCRIPTION "Errors"
            ::= {  staConnEntry 5 }

staConnCont OBJECT-TYPE
            SYNTAX DisplayString (SIZE(0..255))
            MAX-ACCESS read-only
            STATUS current
            DESCRIPTION "Con.-Time"
            ::= {  staConnEntry 6 }

staConnChar OBJECT-TYPE
            SYNTAX INTEGER (0..2147483647)
            MAX-ACCESS read-only
            STATUS current
            DESCRIPTION "Charge"
            ::= {  staConnEntry 7 }

staInfoTable OBJECT-TYPE
             SYNTAX SEQUENCE OF StaInfoEntry
             MAX-ACCESS not-accessible
             STATUS current
             DESCRIPTION "Info-Connection"
             ::= {  sta 14 }

staInfoEntry OBJECT-TYPE
             SYNTAX StaInfoEntry
             MAX-ACCESS not-accessible
             STATUS current
             DESCRIPTION "entry in table"
             INDEX { staInfoIfc }
             ::= {  staInfoTable 1 }

StaInfoEntry ::= SEQUENCE {
             staInfoIfc INTEGER,
             staInfoSta DisplayString,
             staInfoMod INTEGER,
             staInfoDia DisplayString,
             staInfoPee DisplayString,
             staInfoB1d INTEGER,
             staInfoB2d INTEGER
            }

staInfoIfc OBJECT-TYPE
           SYNTAX INTEGER
           {
             dsl-ch-1(1),
             dsl-ch-2(2),
             dsl-ch-3(3),
             dsl-ch-4(4),
             dsl-ch-5(5),
             dsl-ch-6(6),
             dsl-ch-7(7),
             dsl-ch-8(8),
             ch01(9),
             ch02(10),
             ext(11)
           }
           MAX-ACCESS read-only
           STATUS current
           DESCRIPTION "Ifc"
           ::= {  staInfoEntry 1 }

staInfoSta OBJECT-TYPE
           SYNTAX DisplayString (SIZE(0..16))
           MAX-ACCESS read-only
           STATUS current
           DESCRIPTION "Status"
           ::= {  staInfoEntry 2 }

staInfoMod OBJECT-TYPE
           SYNTAX INTEGER
           {
             unknown(0),
             active(4),
             passive(5),
             callback(9)
           }
           MAX-ACCESS read-only
           STATUS current
           DESCRIPTION "Mode"
           ::= {  staInfoEntry 3 }

staInfoDia OBJECT-TYPE
           SYNTAX DisplayString (SIZE(0..20))
           MAX-ACCESS read-only
           STATUS current
           DESCRIPTION "Dialup-remote"
           ::= {  staInfoEntry 4 }

staInfoPee OBJECT-TYPE
           SYNTAX DisplayString (SIZE(0..16))
           MAX-ACCESS read-only
           STATUS current
           DESCRIPTION "Peer"
           ::= {  staInfoEntry 5 }

staInfoB1d OBJECT-TYPE
           SYNTAX INTEGER (0..65535)
           MAX-ACCESS read-only
           STATUS current
           DESCRIPTION "B1-DT"
           ::= {  staInfoEntry 6 }

staInfoB2d OBJECT-TYPE
           SYNTAX INTEGER (0..65535)
           MAX-ACCESS read-only
           STATUS current
           DESCRIPTION "B2-DT"
           ::= {  staInfoEntry 7 }

staLayeTable OBJECT-TYPE
             SYNTAX SEQUENCE OF StaLayeEntry
             MAX-ACCESS not-accessible
             STATUS current
             DESCRIPTION "Layer-Connection"
             ::= {  sta 15 }

staLayeEntry OBJECT-TYPE
             SYNTAX StaLayeEntry
             MAX-ACCESS not-accessible
             STATUS current
             DESCRIPTION "entry in table"
             INDEX { staLayeIfc }
             ::= {  staLayeTable 1 }

StaLayeEntry ::= SEQUENCE {
             staLayeIfc INTEGER,
             staLayeWanl DisplayString,
             staLayeEnca INTEGER,
             staLayeLay3 INTEGER,
             staLayeLay2 INTEGER,
             staLayeL2op INTEGER,
             staLayeLay1 INTEGER,
             staLayeL1pa INTEGER
            }

staLayeIfc OBJECT-TYPE
            SYNTAX INTEGER
            {
              dsl-ch-1(1),
              dsl-ch-2(2),
              dsl-ch-3(3),
              dsl-ch-4(4),
              dsl-ch-5(5),
              dsl-ch-6(6),
              dsl-ch-7(7),
              dsl-ch-8(8),
              ch01(9),
              ch02(10),
              ext(11)
            }
            MAX-ACCESS read-only
            STATUS current
            DESCRIPTION "Ifc"
            ::= {  staLayeEntry 1 }

staLayeWanl OBJECT-TYPE
            SYNTAX DisplayString (SIZE(0..9))
            MAX-ACCESS read-only
            STATUS current
            DESCRIPTION "WAN-layer"
            ::= {  staLayeEntry 2 }

staLayeEnca OBJECT-TYPE
            SYNTAX INTEGER
            {
              ether(0),
              trans(255)
            }
            MAX-ACCESS read-only
            STATUS current
            DESCRIPTION "Encaps."
            ::= {  staLayeEntry 3 }

staLayeLay3 OBJECT-TYPE
            SYNTAX INTEGER
            {
              trans(0),
              ppp(4),
              appp(5),
              scppp(6),
              scappp(7),
              sctrans(8),
              dhcp(9),
              trans(255)
            }
            MAX-ACCESS read-only
            STATUS current
            DESCRIPTION "Lay-3"
            ::= {  staLayeEntry 4 }

staLayeLay2 OBJECT-TYPE
            SYNTAX INTEGER
            {
              sscop(6),
              pppoe(5),
              x-75lapb(0),
              trans(1)
            }
            MAX-ACCESS read-only
            STATUS current
            DESCRIPTION "Lay-2"
            ::= {  staLayeEntry 5 }

staLayeL2op OBJECT-TYPE
            SYNTAX INTEGER
            {
              none(255),
              compr(0),
              bundle(1),
              bnd-plus-cmpr(2)
            }
            MAX-ACCESS read-only
            STATUS current
            DESCRIPTION "L2-Opt."
            ::= {  staLayeEntry 6 }

staLayeLay1 OBJECT-TYPE
            SYNTAX INTEGER
            {
              aal-5(2),
              eth(4),
              hdlc64k(0),
              hdlc56k(1),
              v110-9k6(3),
              v110-19k2(67),
              v110-38k4(131),
              modem(5)
            }
            MAX-ACCESS read-only
            STATUS current
            DESCRIPTION "Lay-1"
            ::= {  staLayeEntry 7 }

staLayeL1pa OBJECT-TYPE
            SYNTAX INTEGER
            {
              none(0),
              v-21-300(1),
              v-23-600(2),
              v-23-1200(3),
              v-22-1200(4),
              v-22bis-2400(5),
              v-32qam-4800(6),
              v-32qam-9600(7),
              v-32bis-7200(8),
              v-32tcm-9600(9),
              v-32bis-12000(10),
              v-32bis-14400(11),
              v-34-2400(12),
              v-34-4800(13),
              v-34-7200(14),
              v-34-9600(15),
              v-34-12000(16),
              v-34-14400(17),
              v-34-16800(18),
              v-34-19200(19),
              v-34-21600(20),
              v-34-24000(21),
              v-34-26400(22),
              v-34-28800(23),
              v-34-31200(24),
              v-34-33600(25),
              v-90-28000(26),
              v-90-29333(27),
              v-90-30667(28),
              v-90-32000(29),
              v-90-33333(30),
              v-90-34667(31),
              v-90-36000(32),
              v-90-37333(33),
              v-90-38667(34),
              v-90-40000(35),
              v-90-41333(36),
              v-90-42667(37),
              v-90-44000(38),
              v-90-45333(39),
              v-90-46667(40),
              v-90-48000(41),
              v-90-49333(42),
              v-90-50667(43),
              v-90-52000(44),
              v-90-53333(45),
              v-90-54667(46),
              v-90-56000(47)
            }
            MAX-ACCESS read-only
            STATUS current
            DESCRIPTION "L1-Parameter"
            ::= {  staLayeEntry 8 }

staCallTable OBJECT-TYPE
             SYNTAX SEQUENCE OF StaCallEntry
             MAX-ACCESS not-accessible
             STATUS current
             DESCRIPTION "Call-Information"
             ::= {  sta 16 }

staCallEntry OBJECT-TYPE
             SYNTAX StaCallEntry
             MAX-ACCESS not-accessible
             STATUS current
             DESCRIPTION "entry in table"
             INDEX { staCallSys, staCallCou }
             ::= {  staCallTable 1 }

StaCallEntry ::= SEQUENCE {
             staCallSys INTEGER,
             staCallIfc INTEGER,
             staCallCli DisplayString,
             staCallDia DisplayString,
             staCallCap INTEGER,
             staCallBch INTEGER,
             staCallCou INTEGER
            }

staCallSys OBJECT-TYPE
           SYNTAX INTEGER (0..2147483647)
           MAX-ACCESS read-only
           STATUS current
           DESCRIPTION "System-time"
           ::= {  staCallEntry 1 }

staCallIfc OBJECT-TYPE
           SYNTAX INTEGER
           {
             dsl-1(1),
             dsl-2(2),
             dsl-3(3),
             dsl-4(4),
             s0-1(5),
             ext(6)
           }
           MAX-ACCESS read-only
           STATUS current
           DESCRIPTION "Ifc"
           ::= {  staCallEntry 2 }

staCallCli OBJECT-TYPE
           SYNTAX DisplayString (SIZE(0..20))
           MAX-ACCESS read-only
           STATUS current
           DESCRIPTION "CLIP-Caller"
           ::= {  staCallEntry 3 }

staCallDia OBJECT-TYPE
           SYNTAX DisplayString (SIZE(0..20))
           MAX-ACCESS read-only
           STATUS current
           DESCRIPTION "Dial-Caller"
           ::= {  staCallEntry 4 }

staCallCap OBJECT-TYPE
           SYNTAX INTEGER
           {
             unknown(255),
             hdlc64k(0),
             hdlc56k(1),
             v110-9k6(3),
             v110-19k2(67),
             v110-38k4(131),
             modem(5),
             a-3-1khz(13),
             speech(14),
             fax-g2-3(15)
           }
           MAX-ACCESS read-only
           STATUS current
           DESCRIPTION "Capab."
           ::= {  staCallEntry 5 }

staCallBch OBJECT-TYPE
           SYNTAX INTEGER (0..65535)
           MAX-ACCESS read-only
           STATUS current
           DESCRIPTION "B-chan."
           ::= {  staCallEntry 6 }

staCallCou OBJECT-TYPE
           SYNTAX INTEGER (0..2147483647)
           MAX-ACCESS read-only
           STATUS current
           DESCRIPTION "Counter"
           ::= {  staCallEntry 7 }

staRemoTable OBJECT-TYPE
             SYNTAX SEQUENCE OF StaRemoEntry
             MAX-ACCESS not-accessible
             STATUS current
             DESCRIPTION "Remote-Connections"
             ::= {  sta 17 }

staRemoEntry OBJECT-TYPE
             SYNTAX StaRemoEntry
             MAX-ACCESS not-accessible
             STATUS current
             DESCRIPTION "entry in table"
             INDEX { staRemoConns, staRemoCount }
             ::= {  staRemoTable 1 }

StaRemoEntry ::= SEQUENCE {
             staRemoConns DisplayString,
             staRemoRemot DisplayString,
             staRemoMode INTEGER,
             staRemoIfc INTEGER,
             staRemoConnt DisplayString,
             staRemoCharg INTEGER,
             staRemoCount INTEGER
            }

staRemoConns OBJECT-TYPE
             SYNTAX DisplayString (SIZE(0..19))
             MAX-ACCESS read-only
             STATUS current
             DESCRIPTION "Conn.-start"
             ::= {  staRemoEntry 1 }

staRemoRemot OBJECT-TYPE
             SYNTAX DisplayString (SIZE(0..16))
             MAX-ACCESS read-only
             STATUS current
             DESCRIPTION "Remote-ID"
             ::= {  staRemoEntry 2 }

staRemoMode OBJECT-TYPE
             SYNTAX INTEGER
             {
               unknown(0),
               active(4),
               passive(5),
               callback(9)
             }
             MAX-ACCESS read-only
             STATUS current
             DESCRIPTION "Mode"
             ::= {  staRemoEntry 3 }

staRemoIfc OBJECT-TYPE
             SYNTAX INTEGER
             {
               dsl-ch-1(1),
               dsl-ch-2(2),
               dsl-ch-3(3),
               dsl-ch-4(4),
               dsl-ch-5(5),
               dsl-ch-6(6),
               dsl-ch-7(7),
               dsl-ch-8(8),
               ch01(9),
               ch02(10),
               ext(11)
             }
             MAX-ACCESS read-only
             STATUS current
             DESCRIPTION "Ifc"
             ::= {  staRemoEntry 4 }

staRemoConnt OBJECT-TYPE
             SYNTAX DisplayString (SIZE(0..255))
             MAX-ACCESS read-only
             STATUS current
             DESCRIPTION "Conn.-time"
             ::= {  staRemoEntry 5 }

staRemoCharg OBJECT-TYPE
             SYNTAX INTEGER (0..2147483647)
             MAX-ACCESS read-only
             STATUS current
             DESCRIPTION "Charge"
             ::= {  staRemoEntry 6 }

staRemoCount OBJECT-TYPE
             SYNTAX INTEGER (0..2147483647)
             MAX-ACCESS read-only
             STATUS current
             DESCRIPTION "Counter"
             ::= {  staRemoEntry 8 }

staCurr OBJECT-TYPE
        SYNTAX DisplayString
        MAX-ACCESS read-only
        STATUS current
        DESCRIPTION "Current-Time"
        ::= {  sta 18 }

staTime OBJECT IDENTIFIER ::= { sta 21}
staTimeCur OBJECT-TYPE
           SYNTAX DisplayString
           MAX-ACCESS read-only
           STATUS current
           DESCRIPTION "Current-Time"
           ::= {  staTime 1 }

staTimeSou OBJECT-TYPE
           SYNTAX INTEGER
           {
             manual(1),
             isdn(2),
             lan(3),
             ram(4),
             ntp(9),
             lanconfig(8),
             no(0)
           }
           MAX-ACCESS read-only
           STATUS current
           DESCRIPTION "Source"
           ::= {  staTime 2 }

staTimeSet OBJECT-TYPE
           SYNTAX Counter32
           MAX-ACCESS read-only
           STATUS current
           DESCRIPTION "Set-Count"
           ::= {  staTime 3 }

staTimeIsd OBJECT IDENTIFIER ::= { staTime 4}
staTimeIsdConne OBJECT-TYPE
                SYNTAX INTEGER
                MAX-ACCESS read-only
                STATUS current
                DESCRIPTION "Connection"
                ::= {  staTimeIsd 1 }

staTimeIsdInfor OBJECT-TYPE
                SYNTAX INTEGER
                MAX-ACCESS read-only
                STATUS current
                DESCRIPTION "Information"
                ::= {  staTimeIsd 2 }

staTimeIsdInfoe OBJECT-TYPE
                SYNTAX INTEGER
                MAX-ACCESS read-only
                STATUS current
                DESCRIPTION "Info-Error"
                ::= {  staTimeIsd 3 }

staTimeIsdUnits OBJECT-TYPE
                SYNTAX INTEGER
                MAX-ACCESS read-only
                STATUS current
                DESCRIPTION "Units"
                ::= {  staTimeIsd 4 }

staTimeIsdDelet OBJECT-TYPE
                SYNTAX DisplayString
                MAX-ACCESS read-write
                STATUS current
                DESCRIPTION "Delete-Values"
                ::= {  staTimeIsd 5 }

staTimeUtc OBJECT-TYPE
           SYNTAX Counter32
           MAX-ACCESS read-only
           STATUS current
           DESCRIPTION "UTC-in-Seconds"
           ::= {  staTime 7 }

staTimeTim OBJECT-TYPE
           SYNTAX INTEGER
           {
             e0(0),
             plus-1(1),
             plus-2(2),
             plus-3(3),
             plus-4(4),
             plus-5(5),
             plus-6(6),
             plus-7(7),
             plus-8(8),
             plus-9(9),
             plus-10(10),
             plus-11(11),
             plus-12(12),
             plus-13(13),
             plus-14(14),
             minus-1(255),
             minus-2(254),
             minus-3(253),
             minus-4(252),
             minus-5(251),
             minus-6(250),
             minus-7(249),
             minus-8(248),
             minus-9(247),
             minus-10(246),
             minus-11(245),
             minus-12(244)
           }
           MAX-ACCESS read-only
           STATUS current
           DESCRIPTION "Timezone"
           ::= {  staTime 10 }

staTimeDay OBJECT-TYPE
           SYNTAX INTEGER
           {
             no(0),
             yes(1),
             europe-eu(2),
             russia(3),
             usa(4),
             user-defined(255)
           }
           MAX-ACCESS read-only
           STATUS current
           DESCRIPTION "Daylight-saving-time"
           ::= {  staTime 11 }

staTimeDstTable OBJECT-TYPE
                SYNTAX SEQUENCE OF StaTimeDstEntry
                MAX-ACCESS not-accessible
                STATUS current
                DESCRIPTION "DST-clock-changes"
                ::= {  staTime 12 }

staTimeDstEntry OBJECT-TYPE
                SYNTAX StaTimeDstEntry
                MAX-ACCESS not-accessible
                STATUS current
                DESCRIPTION "entry in table"
                INDEX { staTimeDstEve }
                ::= {  staTimeDstTable 1 }

StaTimeDstEntry ::= SEQUENCE {
                staTimeDstEve INTEGER,
                staTimeDstInd INTEGER,
                staTimeDstDay INTEGER,
                staTimeDstMon INTEGER,
                staTimeDstHou INTEGER,
                staTimeDstMin INTEGER,
                staTimeDstTim INTEGER
               }

staTimeDstEve OBJECT-TYPE
              SYNTAX INTEGER
              {
                start(1),
                end(2)
              }
              MAX-ACCESS read-only
              STATUS current
              DESCRIPTION "Event"
              ::= {  staTimeDstEntry 1 }

staTimeDstInd OBJECT-TYPE
              SYNTAX INTEGER
              {
                e4-last(252),
                e3-last(253),
                e2-last(254),
                last(255),
                first(1),
                second(2),
                third(3),
                fourth(4)
              }
              MAX-ACCESS read-write
              STATUS current
              DESCRIPTION "Index"
              ::= {  staTimeDstEntry 2 }

staTimeDstDay OBJECT-TYPE
              SYNTAX INTEGER
              {
                monday(1),
                tuesday(2),
                wednesday(3),
                thursday(4),
                friday(5),
                saturday(6),
                sunday(0)
              }
              MAX-ACCESS read-write
              STATUS current
              DESCRIPTION "Day"
              ::= {  staTimeDstEntry 3 }

staTimeDstMon OBJECT-TYPE
              SYNTAX INTEGER
              {
                january(1),
                february(2),
                march(3),
                april(4),
                may(5),
                june(6),
                july(7),
                august(8),
                september(9),
                october(10),
                november(11),
                december(12)
              }
              MAX-ACCESS read-write
              STATUS current
              DESCRIPTION "Month"
              ::= {  staTimeDstEntry 4 }

staTimeDstHou OBJECT-TYPE
              SYNTAX INTEGER (0..255)
              MAX-ACCESS read-write
              STATUS current
              DESCRIPTION "Hour"
              ::= {  staTimeDstEntry 5 }

staTimeDstMin OBJECT-TYPE
              SYNTAX INTEGER (0..255)
              MAX-ACCESS read-write
              STATUS current
              DESCRIPTION "Minute"
              ::= {  staTimeDstEntry 6 }

staTimeDstTim OBJECT-TYPE
              SYNTAX INTEGER
              {
                utc(1),
                lst(0)
              }
              MAX-ACCESS read-write
              STATUS current
              DESCRIPTION "Time-type"
              ::= {  staTimeDstEntry 7 }

staLcr OBJECT IDENTIFIER ::= { sta 22}
staLcrTot OBJECT-TYPE
          SYNTAX Counter32
          MAX-ACCESS read-only
          STATUS current
          DESCRIPTION "Total-Calls"
          ::= {  staLcr 1 }

staLcrFou OBJECT-TYPE
          SYNTAX Counter32
          MAX-ACCESS read-only
          STATUS current
          DESCRIPTION "Found-Events"
          ::= {  staLcr 2 }

staLcrNot OBJECT-TYPE
          SYNTAX Counter32
          MAX-ACCESS read-only
          STATUS current
          DESCRIPTION "Notfound-Errors"
          ::= {  staLcr 3 }

staLcrMis OBJECT-TYPE
          SYNTAX Counter32
          MAX-ACCESS read-only
          STATUS current
          DESCRIPTION "Missingtime-Errors"
          ::= {  staLcr 4 }

staLcrProTable OBJECT-TYPE
               SYNTAX SEQUENCE OF StaLcrProEntry
               MAX-ACCESS not-accessible
               STATUS current
               DESCRIPTION "Provider"
               ::= {  staLcr 6 }

staLcrProEntry OBJECT-TYPE
               SYNTAX StaLcrProEntry
               MAX-ACCESS not-accessible
               STATUS current
               DESCRIPTION "entry in table"
               INDEX { staLcrProPro }
               ::= {  staLcrProTable 1 }

StaLcrProEntry ::= SEQUENCE {
               staLcrProPro DisplayString,
               staLcrProFai INTEGER,
               staLcrProSuc INTEGER
              }

staLcrProPro OBJECT-TYPE
             SYNTAX DisplayString (SIZE(0..10))
             MAX-ACCESS read-only
             STATUS current
             DESCRIPTION "Provider"
             ::= {  staLcrProEntry 1 }

staLcrProFai OBJECT-TYPE
             SYNTAX INTEGER (0..2147483647)
             MAX-ACCESS read-only
             STATUS current
             DESCRIPTION "Failures"
             ::= {  staLcrProEntry 2 }

staLcrProSuc OBJECT-TYPE
             SYNTAX INTEGER (0..2147483647)
             MAX-ACCESS read-only
             STATUS current
             DESCRIPTION "Successes"
             ::= {  staLcrProEntry 3 }

staLcrDel OBJECT-TYPE
          SYNTAX DisplayString
          MAX-ACCESS read-write
          STATUS current
          DESCRIPTION "Delete-Values"
          ::= {  staLcr 7 }

staChar OBJECT IDENTIFIER ::= { sta 24}
staCharSpareda OBJECT-TYPE
               SYNTAX INTEGER
               MAX-ACCESS read-only
               STATUS current
               DESCRIPTION "Spare-Days-per-Period"
               ::= {  staChar 6 }

staCharSpareun OBJECT-TYPE
               SYNTAX INTEGER
               MAX-ACCESS read-only
               STATUS current
               DESCRIPTION "Spare-Units"
               ::= {  staChar 4 }

staCharRouteru OBJECT-TYPE
               SYNTAX INTEGER
               MAX-ACCESS read-only
               STATUS current
               DESCRIPTION "Router-Units"
               ::= {  staChar 7 }

staCharTotalun OBJECT-TYPE
               SYNTAX INTEGER
               MAX-ACCESS read-only
               STATUS current
               DESCRIPTION "Total-Units"
               ::= {  staChar 8 }

staCharTablebuTable OBJECT-TYPE
                    SYNTAX SEQUENCE OF StaCharTablebuEntry
                    MAX-ACCESS not-accessible
                    STATUS current
                    DESCRIPTION "Table-Budget"
                    ::= {  staChar 5 }

staCharTablebuEntry OBJECT-TYPE
                    SYNTAX StaCharTablebuEntry
                    MAX-ACCESS not-accessible
                    STATUS current
                    DESCRIPTION "entry in table"
                    INDEX { staCharTablebuIfc }
                    ::= {  staCharTablebuTable 1 }

StaCharTablebuEntry ::= SEQUENCE {
                    staCharTablebuIfc INTEGER,
                    staCharTablebuBud INTEGER,
                    staCharTablebuSpa INTEGER,
                    staCharTablebuTot INTEGER
                   }

staCharTablebuIfc OBJECT-TYPE
                  SYNTAX INTEGER
                  {
                    router-isdn-serial(1),
                    lancapi(2),
                    ab-1(3),
                    ab-2(4),
                    ab-3(5),
                    ab-4(6),
                    time-modul(255)
                  }
                  MAX-ACCESS read-only
                  STATUS current
                  DESCRIPTION "Ifc"
                  ::= {  staCharTablebuEntry 1 }

staCharTablebuBud OBJECT-TYPE
                  SYNTAX INTEGER (0..65535)
                  MAX-ACCESS read-only
                  STATUS current
                  DESCRIPTION "Budget-units"
                  ::= {  staCharTablebuEntry 2 }

staCharTablebuSpa OBJECT-TYPE
                  SYNTAX INTEGER (0..65535)
                  MAX-ACCESS read-only
                  STATUS current
                  DESCRIPTION "Spare-Budget"
                  ::= {  staCharTablebuEntry 3 }

staCharTablebuTot OBJECT-TYPE
                  SYNTAX INTEGER (0..2147483647)
                  MAX-ACCESS read-only
                  STATUS current
                  DESCRIPTION "Total-units"
                  ::= {  staCharTablebuEntry 4 }

staCharSparedi OBJECT-TYPE
               SYNTAX INTEGER
               MAX-ACCESS read-only
               STATUS current
               DESCRIPTION "Spare-Dialup-Minutes"
               ::= {  staChar 10 }

staCharRouteri OBJECT-TYPE
               SYNTAX INTEGER
               MAX-ACCESS read-only
               STATUS current
               DESCRIPTION "Router-ISDN-Serial-Minutes-Active"
               ::= {  staChar 11 }

staCharSpareds OBJECT-TYPE
               SYNTAX INTEGER
               MAX-ACCESS read-only
               STATUS current
               DESCRIPTION "Spare-DSL-Broadband-Minutes"
               ::= {  staChar 1 }

staCharRouterd OBJECT-TYPE
               SYNTAX INTEGER
               MAX-ACCESS read-only
               STATUS current
               DESCRIPTION "Router-DSL-Broadband-Minutes-Active"
               ::= {  staChar 9 }

staCharTimetabTable OBJECT-TYPE
                    SYNTAX SEQUENCE OF StaCharTimetabEntry
                    MAX-ACCESS not-accessible
                    STATUS current
                    DESCRIPTION "Time-Table"
                    ::= {  staChar 2 }

staCharTimetabEntry OBJECT-TYPE
                    SYNTAX StaCharTimetabEntry
                    MAX-ACCESS not-accessible
                    STATUS current
                    DESCRIPTION "entry in table"
                    INDEX { staCharTimetabIfc }
                    ::= {  staCharTimetabTable 1 }

StaCharTimetabEntry ::= SEQUENCE {
                    staCharTimetabIfc INTEGER,
                    staCharTimetabBudgetmi INTEGER,
                    staCharTimetabSparemin INTEGER,
                    staCharTimetabMinutesa INTEGER,
                    staCharTimetabMinutesp INTEGER
                   }

staCharTimetabIfc OBJECT-TYPE
                       SYNTAX INTEGER
                       {
                         router-dsl-broadband(1),
                         router-isdn-serial(2),
                         lancapi(3),
                         ab-1(4),
                         ab-2(5),
                         ab-3(6),
                         ab-4(7),
                         time-modul(255)
                       }
                       MAX-ACCESS read-only
                       STATUS current
                       DESCRIPTION "Ifc"
                       ::= {  staCharTimetabEntry 1 }

staCharTimetabBudgetmi OBJECT-TYPE
                       SYNTAX INTEGER (0..2147483647)
                       MAX-ACCESS read-only
                       STATUS current
                       DESCRIPTION "Budget-minutes"
                       ::= {  staCharTimetabEntry 2 }

staCharTimetabSparemin OBJECT-TYPE
                       SYNTAX INTEGER (0..2147483647)
                       MAX-ACCESS read-only
                       STATUS current
                       DESCRIPTION "Spare-minutes"
                       ::= {  staCharTimetabEntry 3 }

staCharTimetabMinutesa OBJECT-TYPE
                       SYNTAX INTEGER (0..2147483647)
                       MAX-ACCESS read-only
                       STATUS current
                       DESCRIPTION "Minutes-active"
                       ::= {  staCharTimetabEntry 4 }

staCharTimetabMinutesp OBJECT-TYPE
                       SYNTAX INTEGER (0..2147483647)
                       MAX-ACCESS read-only
                       STATUS current
                       DESCRIPTION "Minutes-passive"
                       ::= {  staCharTimetabEntry 5 }

staCharDeletev OBJECT-TYPE
               SYNTAX DisplayString
               MAX-ACCESS read-write
               STATUS current
               DESCRIPTION "Delete-Values"
               ::= {  staChar 3 }

staDsl OBJECT IDENTIFIER ::= { sta 25}
staDslIntTable OBJECT-TYPE
               SYNTAX SEQUENCE OF StaDslIntEntry
               MAX-ACCESS not-accessible
               STATUS current
               DESCRIPTION "Interfaces"
               ::= {  staDsl 1 }

staDslIntEntry OBJECT-TYPE
               SYNTAX StaDslIntEntry
               MAX-ACCESS not-accessible
               STATUS current
               DESCRIPTION "entry in table"
               INDEX { staDslIntIfc }
               ::= {  staDslIntTable 1 }

StaDslIntEntry ::= SEQUENCE {
               staDslIntIfc DisplayString,
               staDslIntLin INTEGER
              }

staDslIntIfc OBJECT-TYPE
             SYNTAX DisplayString (SIZE(0..255))
             MAX-ACCESS read-only
             STATUS current
             DESCRIPTION "Ifc"
             ::= {  staDslIntEntry 1 }

staDslIntLin OBJECT-TYPE
             SYNTAX INTEGER
             {
               no(0),
               yes(1)
             }
             MAX-ACCESS read-only
             STATUS current
             DESCRIPTION "Link-Active"
             ::= {  staDslIntEntry 3 }

staDslBytTable OBJECT-TYPE
               SYNTAX SEQUENCE OF StaDslBytEntry
               MAX-ACCESS not-accessible
               STATUS current
               DESCRIPTION "Byte-Transport"
               ::= {  staDsl 2 }

staDslBytEntry OBJECT-TYPE
               SYNTAX StaDslBytEntry
               MAX-ACCESS not-accessible
               STATUS current
               DESCRIPTION "entry in table"
               INDEX { staDslBytIfc }
               ::= {  staDslBytTable 1 }

StaDslBytEntry ::= SEQUENCE {
               staDslBytIfc DisplayString,
               staDslBytTxb Counter64,
               staDslBytRxb Counter64
              }

staDslBytIfc OBJECT-TYPE
             SYNTAX DisplayString (SIZE(0..255))
             MAX-ACCESS read-only
             STATUS current
             DESCRIPTION "Ifc"
             ::= {  staDslBytEntry 1 }

staDslBytTxb OBJECT-TYPE
             SYNTAX Counter64
             MAX-ACCESS read-only
             STATUS current
             DESCRIPTION "Tx-Bytes"
             ::= {  staDslBytEntry 2 }

staDslBytRxb OBJECT-TYPE
             SYNTAX Counter64
             MAX-ACCESS read-only
             STATUS current
             DESCRIPTION "Rx-Bytes"
             ::= {  staDslBytEntry 3 }

staDslPacTable OBJECT-TYPE
               SYNTAX SEQUENCE OF StaDslPacEntry
               MAX-ACCESS not-accessible
               STATUS current
               DESCRIPTION "Packet-Transport"
               ::= {  staDsl 3 }

staDslPacEntry OBJECT-TYPE
               SYNTAX StaDslPacEntry
               MAX-ACCESS not-accessible
               STATUS current
               DESCRIPTION "entry in table"
               INDEX { staDslPacIfc }
               ::= {  staDslPacTable 1 }

StaDslPacEntry ::= SEQUENCE {
               staDslPacIfc DisplayString,
               staDslPacRxp Counter32,
               staDslPacTxp Counter32,
               staDslPacRxb Counter32,
               staDslPacRxm Counter32,
               staDslPacRxu Counter32,
               staDslPacTxb Counter32,
               staDslPacTxm Counter32,
               staDslPacTxu Counter32
              }

staDslPacIfc OBJECT-TYPE
             SYNTAX DisplayString (SIZE(0..255))
             MAX-ACCESS read-only
             STATUS current
             DESCRIPTION "Ifc"
             ::= {  staDslPacEntry 1 }

staDslPacRxp OBJECT-TYPE
             SYNTAX Counter32
             MAX-ACCESS read-only
             STATUS current
             DESCRIPTION "Rx-Packets"
             ::= {  staDslPacEntry 2 }

staDslPacTxp OBJECT-TYPE
             SYNTAX Counter32
             MAX-ACCESS read-only
             STATUS current
             DESCRIPTION "Tx-Packets"
             ::= {  staDslPacEntry 3 }

staDslPacRxb OBJECT-TYPE
             SYNTAX Counter32
             MAX-ACCESS read-only
             STATUS current
             DESCRIPTION "Rx-Broadcasts"
             ::= {  staDslPacEntry 4 }

staDslPacRxm OBJECT-TYPE
             SYNTAX Counter32
             MAX-ACCESS read-only
             STATUS current
             DESCRIPTION "Rx-Multicasts"
             ::= {  staDslPacEntry 5 }

staDslPacRxu OBJECT-TYPE
             SYNTAX Counter32
             MAX-ACCESS read-only
             STATUS current
             DESCRIPTION "Rx-Unicasts"
             ::= {  staDslPacEntry 6 }

staDslPacTxb OBJECT-TYPE
             SYNTAX Counter32
             MAX-ACCESS read-only
             STATUS current
             DESCRIPTION "Tx-Broadcasts"
             ::= {  staDslPacEntry 7 }

staDslPacTxm OBJECT-TYPE
             SYNTAX Counter32
             MAX-ACCESS read-only
             STATUS current
             DESCRIPTION "Tx-Multicasts"
             ::= {  staDslPacEntry 8 }

staDslPacTxu OBJECT-TYPE
             SYNTAX Counter32
             MAX-ACCESS read-only
             STATUS current
             DESCRIPTION "Tx-Unicasts"
             ::= {  staDslPacEntry 9 }

staDslErrTable OBJECT-TYPE
               SYNTAX SEQUENCE OF StaDslErrEntry
               MAX-ACCESS not-accessible
               STATUS current
               DESCRIPTION "Errors"
               ::= {  staDsl 4 }

staDslErrEntry OBJECT-TYPE
               SYNTAX StaDslErrEntry
               MAX-ACCESS not-accessible
               STATUS current
               DESCRIPTION "entry in table"
               INDEX { staDslErrIfc }
               ::= {  staDslErrTable 1 }

StaDslErrEntry ::= SEQUENCE {
               staDslErrIfc DisplayString,
               staDslErrRxerro Counter32,
               staDslErrTxerro Counter32,
               staDslErrStacke Counter32,
               staDslErrNicerr Counter32,
               staDslErrQueuee Counter32,
               staDslErrRxcrce Counter32,
               staDslErrCollis Counter32,
               staDslErrSingle Counter32,
               staDslErrMultip Counter32,
               staDslErrLateco Counter32,
               staDslErrExcess Counter32,
               staDslErrRxalig Counter32,
               staDslErrRxtoos Counter32,
               staDslErrRxtool Counter32,
               staDslErrTxcarr Counter32,
               staDslErrTxdefe Counter32
              }

staDslErrIfc OBJECT-TYPE
                SYNTAX DisplayString (SIZE(0..255))
                MAX-ACCESS read-only
                STATUS current
                DESCRIPTION "Ifc"
                ::= {  staDslErrEntry 1 }

staDslErrRxerro OBJECT-TYPE
                SYNTAX Counter32
                MAX-ACCESS read-only
                STATUS current
                DESCRIPTION "Rx-Errors"
                ::= {  staDslErrEntry 2 }

staDslErrTxerro OBJECT-TYPE
                SYNTAX Counter32
                MAX-ACCESS read-only
                STATUS current
                DESCRIPTION "Tx-Errors"
                ::= {  staDslErrEntry 3 }

staDslErrStacke OBJECT-TYPE
                SYNTAX Counter32
                MAX-ACCESS read-only
                STATUS current
                DESCRIPTION "Stack-Errors"
                ::= {  staDslErrEntry 4 }

staDslErrNicerr OBJECT-TYPE
                SYNTAX Counter32
                MAX-ACCESS read-only
                STATUS current
                DESCRIPTION "NIC-Errors"
                ::= {  staDslErrEntry 5 }

staDslErrQueuee OBJECT-TYPE
                SYNTAX Counter32
                MAX-ACCESS read-only
                STATUS current
                DESCRIPTION "Queue-Errors"
                ::= {  staDslErrEntry 6 }

staDslErrRxcrce OBJECT-TYPE
                SYNTAX Counter32
                MAX-ACCESS read-only
                STATUS current
                DESCRIPTION "Rx-CRC-Errors"
                ::= {  staDslErrEntry 7 }

staDslErrCollis OBJECT-TYPE
                SYNTAX Counter32
                MAX-ACCESS read-only
                STATUS current
                DESCRIPTION "Collisions"
                ::= {  staDslErrEntry 8 }

staDslErrSingle OBJECT-TYPE
                SYNTAX Counter32
                MAX-ACCESS read-only
                STATUS current
                DESCRIPTION "Single-Collisions"
                ::= {  staDslErrEntry 9 }

staDslErrMultip OBJECT-TYPE
                SYNTAX Counter32
                MAX-ACCESS read-only
                STATUS current
                DESCRIPTION "Multiple-Collisions"
                ::= {  staDslErrEntry 10 }

staDslErrLateco OBJECT-TYPE
                SYNTAX Counter32
                MAX-ACCESS read-only
                STATUS current
                DESCRIPTION "Late-Collisions"
                ::= {  staDslErrEntry 11 }

staDslErrExcess OBJECT-TYPE
                SYNTAX Counter32
                MAX-ACCESS read-only
                STATUS current
                DESCRIPTION "Excessive-Collisions"
                ::= {  staDslErrEntry 12 }

staDslErrRxalig OBJECT-TYPE
                SYNTAX Counter32
                MAX-ACCESS read-only
                STATUS current
                DESCRIPTION "Rx-Align-Errors"
                ::= {  staDslErrEntry 13 }

staDslErrRxtoos OBJECT-TYPE
                SYNTAX Counter32
                MAX-ACCESS read-only
                STATUS current
                DESCRIPTION "Rx-Too-Short"
                ::= {  staDslErrEntry 14 }

staDslErrRxtool OBJECT-TYPE
                SYNTAX Counter32
                MAX-ACCESS read-only
                STATUS current
                DESCRIPTION "Rx-Too-Long"
                ::= {  staDslErrEntry 15 }

staDslErrTxcarr OBJECT-TYPE
                SYNTAX Counter32
                MAX-ACCESS read-only
                STATUS current
                DESCRIPTION "Tx-Carrier"
                ::= {  staDslErrEntry 16 }

staDslErrTxdefe OBJECT-TYPE
                SYNTAX Counter32
                MAX-ACCESS read-only
                STATUS current
                DESCRIPTION "Tx-Deferred"
                ::= {  staDslErrEntry 17 }

staDslPpp OBJECT IDENTIFIER ::= { staDsl 23}
staDslPppTxpadi OBJECT-TYPE
                SYNTAX INTEGER
                MAX-ACCESS read-only
                STATUS current
                DESCRIPTION "Tx-PADI"
                ::= {  staDslPpp 1 }

staDslPppRxpado OBJECT-TYPE
                SYNTAX INTEGER
                MAX-ACCESS read-only
                STATUS current
                DESCRIPTION "Rx-PADO"
                ::= {  staDslPpp 2 }

staDslPppTxpadr OBJECT-TYPE
                SYNTAX INTEGER
                MAX-ACCESS read-only
                STATUS current
                DESCRIPTION "Tx-PADR"
                ::= {  staDslPpp 3 }

staDslPppRxpads OBJECT-TYPE
                SYNTAX INTEGER
                MAX-ACCESS read-only
                STATUS current
                DESCRIPTION "Rx-PADS"
                ::= {  staDslPpp 4 }

staDslPppTxpadt OBJECT-TYPE
                SYNTAX INTEGER
                MAX-ACCESS read-only
                STATUS current
                DESCRIPTION "Tx-PADT"
                ::= {  staDslPpp 5 }

staDslPppRxpadt OBJECT-TYPE
                SYNTAX INTEGER
                MAX-ACCESS read-only
                STATUS current
                DESCRIPTION "Rx-PADT"
                ::= {  staDslPpp 6 }

staDslPppTxprot OBJECT-TYPE
                SYNTAX INTEGER
                MAX-ACCESS read-only
                STATUS current
                DESCRIPTION "Tx-Protocol"
                ::= {  staDslPpp 7 }

staDslPppRxprot OBJECT-TYPE
                SYNTAX INTEGER
                MAX-ACCESS read-only
                STATUS current
                DESCRIPTION "Rx-Protocol"
                ::= {  staDslPpp 8 }

staDslPppTxdata OBJECT-TYPE
                SYNTAX INTEGER
                MAX-ACCESS read-only
                STATUS current
                DESCRIPTION "Tx-Data"
                ::= {  staDslPpp 9 }

staDslPppRxdata OBJECT-TYPE
                SYNTAX INTEGER
                MAX-ACCESS read-only
                STATUS current
                DESCRIPTION "Rx-Data"
                ::= {  staDslPpp 10 }

staDslPppRxbad OBJECT-TYPE
                SYNTAX INTEGER
                MAX-ACCESS read-only
                STATUS current
                DESCRIPTION "Rx-Bad"
                ::= {  staDslPpp 11 }

staDslPppAcname OBJECT-TYPE
                SYNTAX DisplayString (SIZE(0..63))
                MAX-ACCESS read-only
                STATUS current
                DESCRIPTION "AC-Name"
                ::= {  staDslPpp 12 }

staDslPppServic OBJECT-TYPE
                SYNTAX DisplayString (SIZE(0..63))
                MAX-ACCESS read-only
                STATUS current
                DESCRIPTION "Service"
                ::= {  staDslPpp 13 }

staDslPppDelete OBJECT-TYPE
                SYNTAX DisplayString
                MAX-ACCESS read-write
                STATUS current
                DESCRIPTION "Delete-Values"
                ::= {  staDslPpp 30 }

staDslDel OBJECT-TYPE
          SYNTAX DisplayString
          MAX-ACCESS read-write
          STATUS current
          DESCRIPTION "Delete-Values"
          ::= {  staDsl 30 }

staVpn OBJECT IDENTIFIER ::= { sta 26}
staVpnPeers OBJECT-TYPE
              SYNTAX INTEGER
              MAX-ACCESS read-only
              STATUS current
              DESCRIPTION "Peers"
              ::= {  staVpn 1 }

staVpnRules OBJECT-TYPE
              SYNTAX INTEGER
              MAX-ACCESS read-only
              STATUS current
              DESCRIPTION "Rules"
              ::= {  staVpn 2 }

staVpnTunnel OBJECT-TYPE
              SYNTAX INTEGER
              MAX-ACCESS read-only
              STATUS current
              DESCRIPTION "Tunnel"
              ::= {  staVpn 4 }

staVpnIkesas OBJECT-TYPE
              SYNTAX INTEGER
              MAX-ACCESS read-only
              STATUS current
              DESCRIPTION "IKE-SAs"
              ::= {  staVpn 5 }

staVpnEspsas OBJECT-TYPE
              SYNTAX INTEGER
              MAX-ACCESS read-only
              STATUS current
              DESCRIPTION "ESP-SAs"
              ::= {  staVpn 6 }

staVpnAhsas OBJECT-TYPE
              SYNTAX INTEGER
              MAX-ACCESS read-only
              STATUS current
              DESCRIPTION "AH-SAs"
              ::= {  staVpn 7 }

staVpnIpcomps OBJECT-TYPE
              SYNTAX INTEGER
              MAX-ACCESS read-only
              STATUS current
              DESCRIPTION "IPCOMP-SAs"
              ::= {  staVpn 13 }

staVpnIkeTable OBJECT-TYPE
                   SYNTAX SEQUENCE OF StaVpnIkeEntry
                   MAX-ACCESS not-accessible
                   STATUS current
                   DESCRIPTION "IKE"
                   ::= {  staVpn 8 }

staVpnIkeEntry OBJECT-TYPE
                   SYNTAX StaVpnIkeEntry
                   MAX-ACCESS not-accessible
                   STATUS current
                   DESCRIPTION "entry in table"
                   INDEX { staVpnIkeIdx }
                   ::= {  staVpnIkeTable 1 }

StaVpnIkeEntry ::= SEQUENCE {
                   staVpnIkeIdx DisplayString,
                   staVpnIkePeer DisplayString,
                   staVpnIkeDesta IpAddress,
                   staVpnIkeDstpo INTEGER,
                   staVpnIkeSrcad IpAddress,
                   staVpnIkeSrcpo INTEGER,
                   staVpnIkeCrypt DisplayString,
                   staVpnIkeHasha DisplayString,
                   staVpnIkeIkeau INTEGER,
                   staVpnIkeIniti DisplayString,
                   staVpnIkeAge INTEGER,
                   staVpnIkeSofts INTEGER,
                   staVpnIkeMaxse INTEGER,
                   staVpnIkeKbyte INTEGER,
                   staVpnIkeSoftk INTEGER,
                   staVpnIkeMaxkb INTEGER
                  }

staVpnIkeIdx OBJECT-TYPE
               SYNTAX DisplayString (SIZE(0..3))
               MAX-ACCESS read-only
               STATUS current
               DESCRIPTION "Idx."
               ::= {  staVpnIkeEntry 1 }

staVpnIkePeer OBJECT-TYPE
               SYNTAX DisplayString (SIZE(0..15))
               MAX-ACCESS read-only
               STATUS current
               DESCRIPTION "Peer"
               ::= {  staVpnIkeEntry 2 }

staVpnIkeDesta OBJECT-TYPE
               SYNTAX IpAddress
               MAX-ACCESS read-only
               STATUS current
               DESCRIPTION "Dest.-Address"
               ::= {  staVpnIkeEntry 3 }

staVpnIkeDstpo OBJECT-TYPE
               SYNTAX INTEGER (0..65535)
               MAX-ACCESS read-only
               STATUS current
               DESCRIPTION "Dst-Port"
               ::= {  staVpnIkeEntry 16 }

staVpnIkeSrcad OBJECT-TYPE
               SYNTAX IpAddress
               MAX-ACCESS read-only
               STATUS current
               DESCRIPTION "Src.-Address"
               ::= {  staVpnIkeEntry 4 }

staVpnIkeSrcpo OBJECT-TYPE
               SYNTAX INTEGER (0..65535)
               MAX-ACCESS read-only
               STATUS current
               DESCRIPTION "Src-Port"
               ::= {  staVpnIkeEntry 17 }

staVpnIkeCrypt OBJECT-TYPE
               SYNTAX DisplayString (SIZE(0..12))
               MAX-ACCESS read-only
               STATUS current
               DESCRIPTION "Crypt-Alg"
               ::= {  staVpnIkeEntry 5 }

staVpnIkeHasha OBJECT-TYPE
               SYNTAX DisplayString (SIZE(0..12))
               MAX-ACCESS read-only
               STATUS current
               DESCRIPTION "Hash-Alg"
               ::= {  staVpnIkeEntry 6 }

staVpnIkeIkeau OBJECT-TYPE
               SYNTAX INTEGER
               {
                 no(0),
                 pre-shared(1),
                 dss(2),
                 rsa-sig(3),
                 rsa-enc(4),
                 rsa-enc-rev(5),
                 el-gamal-enc(6),
                 el-gamal-enc-rev(7),
                 ecdsa-sig(8),
                 pre-shared-init-xauth(65001),
                 pre-shared-resp-xauth(65002),
                 dss-init-xauth(65003),
                 dss-resp-xauth(65004),
                 rsa-init-xauth(65005),
                 rsa-resp-xauth(65006)
               }
               MAX-ACCESS read-only
               STATUS current
               DESCRIPTION "IKE-Auth-Mode"
               ::= {  staVpnIkeEntry 15 }

staVpnIkeIniti OBJECT-TYPE
               SYNTAX DisplayString (SIZE(0..3))
               MAX-ACCESS read-only
               STATUS current
               DESCRIPTION "Initiator"
               ::= {  staVpnIkeEntry 9 }

staVpnIkeAge OBJECT-TYPE
               SYNTAX INTEGER (0..2147483647)
               MAX-ACCESS read-only
               STATUS current
               DESCRIPTION "Age"
               ::= {  staVpnIkeEntry 8 }

staVpnIkeSofts OBJECT-TYPE
               SYNTAX INTEGER (0..2147483647)
               MAX-ACCESS read-only
               STATUS current
               DESCRIPTION "Soft-Sec"
               ::= {  staVpnIkeEntry 10 }

staVpnIkeMaxse OBJECT-TYPE
               SYNTAX INTEGER (0..2147483647)
               MAX-ACCESS read-only
               STATUS current
               DESCRIPTION "Max-Sec"
               ::= {  staVpnIkeEntry 11 }

staVpnIkeKbyte OBJECT-TYPE
               SYNTAX INTEGER (0..2147483647)
               MAX-ACCESS read-only
               STATUS current
               DESCRIPTION "KByte"
               ::= {  staVpnIkeEntry 12 }

staVpnIkeSoftk OBJECT-TYPE
               SYNTAX INTEGER (0..2147483647)
               MAX-ACCESS read-only
               STATUS current
               DESCRIPTION "Soft-KByte"
               ::= {  staVpnIkeEntry 13 }

staVpnIkeMaxkb OBJECT-TYPE
               SYNTAX INTEGER (0..2147483647)
               MAX-ACCESS read-only
               STATUS current
               DESCRIPTION "Max-KByte"
               ::= {  staVpnIkeEntry 14 }

staVpnEspTable OBJECT-TYPE
                   SYNTAX SEQUENCE OF StaVpnEspEntry
                   MAX-ACCESS not-accessible
                   STATUS current
                   DESCRIPTION "ESP"
                   ::= {  staVpn 9 }

staVpnEspEntry OBJECT-TYPE
                   SYNTAX StaVpnEspEntry
                   MAX-ACCESS not-accessible
                   STATUS current
                   DESCRIPTION "entry in table"
                   INDEX { staVpnEspIdx }
                   ::= {  staVpnEspTable 1 }

StaVpnEspEntry ::= SEQUENCE {
                   staVpnEspIdx DisplayString,
                   staVpnEspPeer DisplayString,
                   staVpnEspDesta IpAddress,
                   staVpnEspSrcad IpAddress,
                   staVpnEspMode DisplayString,
                   staVpnEspCrypt DisplayString,
                   staVpnEspHasha DisplayString,
                   staVpnEspSpi DisplayString,
                   staVpnEspAge INTEGER,
                   staVpnEspSofts INTEGER,
                   staVpnEspMaxse INTEGER,
                   staVpnEspKbyte INTEGER,
                   staVpnEspSoftk INTEGER,
                   staVpnEspMaxkb INTEGER
                  }

staVpnEspIdx OBJECT-TYPE
               SYNTAX DisplayString (SIZE(0..3))
               MAX-ACCESS read-only
               STATUS current
               DESCRIPTION "Idx."
               ::= {  staVpnEspEntry 1 }

staVpnEspPeer OBJECT-TYPE
               SYNTAX DisplayString (SIZE(0..15))
               MAX-ACCESS read-only
               STATUS current
               DESCRIPTION "Peer"
               ::= {  staVpnEspEntry 2 }

staVpnEspDesta OBJECT-TYPE
               SYNTAX IpAddress
               MAX-ACCESS read-only
               STATUS current
               DESCRIPTION "Dest.-Address"
               ::= {  staVpnEspEntry 3 }

staVpnEspSrcad OBJECT-TYPE
               SYNTAX IpAddress
               MAX-ACCESS read-only
               STATUS current
               DESCRIPTION "Src.-Address"
               ::= {  staVpnEspEntry 4 }

staVpnEspMode OBJECT-TYPE
               SYNTAX DisplayString (SIZE(0..2))
               MAX-ACCESS read-only
               STATUS current
               DESCRIPTION "Mode"
               ::= {  staVpnEspEntry 5 }

staVpnEspCrypt OBJECT-TYPE
               SYNTAX DisplayString (SIZE(0..12))
               MAX-ACCESS read-only
               STATUS current
               DESCRIPTION "Crypt-Alg"
               ::= {  staVpnEspEntry 6 }

staVpnEspHasha OBJECT-TYPE
               SYNTAX DisplayString (SIZE(0..12))
               MAX-ACCESS read-only
               STATUS current
               DESCRIPTION "Hash-Alg"
               ::= {  staVpnEspEntry 7 }

staVpnEspSpi OBJECT-TYPE
               SYNTAX DisplayString (SIZE(0..15))
               MAX-ACCESS read-only
               STATUS current
               DESCRIPTION "SPI"
               ::= {  staVpnEspEntry 9 }

staVpnEspAge OBJECT-TYPE
               SYNTAX INTEGER (0..2147483647)
               MAX-ACCESS read-only
               STATUS current
               DESCRIPTION "Age"
               ::= {  staVpnEspEntry 10 }

staVpnEspSofts OBJECT-TYPE
               SYNTAX INTEGER (0..2147483647)
               MAX-ACCESS read-only
               STATUS current
               DESCRIPTION "Soft-Sec"
               ::= {  staVpnEspEntry 11 }

staVpnEspMaxse OBJECT-TYPE
               SYNTAX INTEGER (0..2147483647)
               MAX-ACCESS read-only
               STATUS current
               DESCRIPTION "Max-Sec"
               ::= {  staVpnEspEntry 12 }

staVpnEspKbyte OBJECT-TYPE
               SYNTAX INTEGER (0..2147483647)
               MAX-ACCESS read-only
               STATUS current
               DESCRIPTION "KByte"
               ::= {  staVpnEspEntry 13 }

staVpnEspSoftk OBJECT-TYPE
               SYNTAX INTEGER (0..2147483647)
               MAX-ACCESS read-only
               STATUS current
               DESCRIPTION "Soft-KByte"
               ::= {  staVpnEspEntry 14 }

staVpnEspMaxkb OBJECT-TYPE
               SYNTAX INTEGER (0..2147483647)
               MAX-ACCESS read-only
               STATUS current
               DESCRIPTION "Max-KByte"
               ::= {  staVpnEspEntry 15 }

staVpnAhTable OBJECT-TYPE
                   SYNTAX SEQUENCE OF StaVpnAhEntry
                   MAX-ACCESS not-accessible
                   STATUS current
                   DESCRIPTION "AH"
                   ::= {  staVpn 10 }

staVpnAhEntry OBJECT-TYPE
                   SYNTAX StaVpnAhEntry
                   MAX-ACCESS not-accessible
                   STATUS current
                   DESCRIPTION "entry in table"
                   INDEX { staVpnAhIdx }
                   ::= {  staVpnAhTable 1 }

StaVpnAhEntry ::= SEQUENCE {
                   staVpnAhIdx DisplayString,
                   staVpnAhPeer DisplayString,
                   staVpnAhDesta IpAddress,
                   staVpnAhSrcad IpAddress,
                   staVpnAhMode DisplayString,
                   staVpnAhCrypt DisplayString,
                   staVpnAhHasha DisplayString,
                   staVpnAhSpi DisplayString,
                   staVpnAhAge INTEGER,
                   staVpnAhSofts INTEGER,
                   staVpnAhMaxse INTEGER,
                   staVpnAhKbyte INTEGER,
                   staVpnAhSoftk INTEGER,
                   staVpnAhMaxkb INTEGER
                  }

staVpnAhIdx OBJECT-TYPE
              SYNTAX DisplayString (SIZE(0..3))
              MAX-ACCESS read-only
              STATUS current
              DESCRIPTION "Idx."
              ::= {  staVpnAhEntry 1 }

staVpnAhPeer OBJECT-TYPE
              SYNTAX DisplayString (SIZE(0..15))
              MAX-ACCESS read-only
              STATUS current
              DESCRIPTION "Peer"
              ::= {  staVpnAhEntry 2 }

staVpnAhDesta OBJECT-TYPE
              SYNTAX IpAddress
              MAX-ACCESS read-only
              STATUS current
              DESCRIPTION "Dest.-Address"
              ::= {  staVpnAhEntry 3 }

staVpnAhSrcad OBJECT-TYPE
              SYNTAX IpAddress
              MAX-ACCESS read-only
              STATUS current
              DESCRIPTION "Src.-Address"
              ::= {  staVpnAhEntry 4 }

staVpnAhMode OBJECT-TYPE
              SYNTAX DisplayString (SIZE(0..2))
              MAX-ACCESS read-only
              STATUS current
              DESCRIPTION "Mode"
              ::= {  staVpnAhEntry 5 }

staVpnAhCrypt OBJECT-TYPE
              SYNTAX DisplayString (SIZE(0..12))
              MAX-ACCESS read-only
              STATUS current
              DESCRIPTION "Crypt-Alg"
              ::= {  staVpnAhEntry 6 }

staVpnAhHasha OBJECT-TYPE
              SYNTAX DisplayString (SIZE(0..12))
              MAX-ACCESS read-only
              STATUS current
              DESCRIPTION "Hash-Alg"
              ::= {  staVpnAhEntry 7 }

staVpnAhSpi OBJECT-TYPE
              SYNTAX DisplayString (SIZE(0..15))
              MAX-ACCESS read-only
              STATUS current
              DESCRIPTION "SPI"
              ::= {  staVpnAhEntry 9 }

staVpnAhAge OBJECT-TYPE
              SYNTAX INTEGER (0..2147483647)
              MAX-ACCESS read-only
              STATUS current
              DESCRIPTION "Age"
              ::= {  staVpnAhEntry 10 }

staVpnAhSofts OBJECT-TYPE
              SYNTAX INTEGER (0..2147483647)
              MAX-ACCESS read-only
              STATUS current
              DESCRIPTION "Soft-Sec"
              ::= {  staVpnAhEntry 11 }

staVpnAhMaxse OBJECT-TYPE
              SYNTAX INTEGER (0..2147483647)
              MAX-ACCESS read-only
              STATUS current
              DESCRIPTION "Max-Sec"
              ::= {  staVpnAhEntry 12 }

staVpnAhKbyte OBJECT-TYPE
              SYNTAX INTEGER (0..2147483647)
              MAX-ACCESS read-only
              STATUS current
              DESCRIPTION "KByte"
              ::= {  staVpnAhEntry 13 }

staVpnAhSoftk OBJECT-TYPE
              SYNTAX INTEGER (0..2147483647)
              MAX-ACCESS read-only
              STATUS current
              DESCRIPTION "Soft-KByte"
              ::= {  staVpnAhEntry 14 }

staVpnAhMaxkb OBJECT-TYPE
              SYNTAX INTEGER (0..2147483647)
              MAX-ACCESS read-only
              STATUS current
              DESCRIPTION "Max-KByte"
              ::= {  staVpnAhEntry 15 }

staVpnIpcompTable OBJECT-TYPE
                   SYNTAX SEQUENCE OF StaVpnIpcompEntry
                   MAX-ACCESS not-accessible
                   STATUS current
                   DESCRIPTION "IPCOMP"
                   ::= {  staVpn 14 }

staVpnIpcompEntry OBJECT-TYPE
                   SYNTAX StaVpnIpcompEntry
                   MAX-ACCESS not-accessible
                   STATUS current
                   DESCRIPTION "entry in table"
                   INDEX { staVpnIpcompIdx }
                   ::= {  staVpnIpcompTable 1 }

StaVpnIpcompEntry ::= SEQUENCE {
                   staVpnIpcompIdx DisplayString,
                   staVpnIpcompPeer DisplayString,
                   staVpnIpcompDesta IpAddress,
                   staVpnIpcompSrcad IpAddress,
                   staVpnIpcompMode DisplayString,
                   staVpnIpcompCrypt DisplayString,
                   staVpnIpcompHasha DisplayString,
                   staVpnIpcompSpi DisplayString,
                   staVpnIpcompAge INTEGER,
                   staVpnIpcompSofts INTEGER,
                   staVpnIpcompMaxse INTEGER,
                   staVpnIpcompKbyte INTEGER,
                   staVpnIpcompSoftk INTEGER,
                   staVpnIpcompMaxkb INTEGER
                  }

staVpnIpcompIdx OBJECT-TYPE
                  SYNTAX DisplayString (SIZE(0..3))
                  MAX-ACCESS read-only
                  STATUS current
                  DESCRIPTION "Idx."
                  ::= {  staVpnIpcompEntry 1 }

staVpnIpcompPeer OBJECT-TYPE
                  SYNTAX DisplayString (SIZE(0..15))
                  MAX-ACCESS read-only
                  STATUS current
                  DESCRIPTION "Peer"
                  ::= {  staVpnIpcompEntry 2 }

staVpnIpcompDesta OBJECT-TYPE
                  SYNTAX IpAddress
                  MAX-ACCESS read-only
                  STATUS current
                  DESCRIPTION "Dest.-Address"
                  ::= {  staVpnIpcompEntry 3 }

staVpnIpcompSrcad OBJECT-TYPE
                  SYNTAX IpAddress
                  MAX-ACCESS read-only
                  STATUS current
                  DESCRIPTION "Src.-Address"
                  ::= {  staVpnIpcompEntry 4 }

staVpnIpcompMode OBJECT-TYPE
                  SYNTAX DisplayString (SIZE(0..2))
                  MAX-ACCESS read-only
                  STATUS current
                  DESCRIPTION "Mode"
                  ::= {  staVpnIpcompEntry 5 }

staVpnIpcompCrypt OBJECT-TYPE
                  SYNTAX DisplayString (SIZE(0..12))
                  MAX-ACCESS read-only
                  STATUS current
                  DESCRIPTION "Crypt-Alg"
                  ::= {  staVpnIpcompEntry 6 }

staVpnIpcompHasha OBJECT-TYPE
                  SYNTAX DisplayString (SIZE(0..12))
                  MAX-ACCESS read-only
                  STATUS current
                  DESCRIPTION "Hash-Alg"
                  ::= {  staVpnIpcompEntry 7 }

staVpnIpcompSpi OBJECT-TYPE
                  SYNTAX DisplayString (SIZE(0..15))
                  MAX-ACCESS read-only
                  STATUS current
                  DESCRIPTION "SPI"
                  ::= {  staVpnIpcompEntry 9 }

staVpnIpcompAge OBJECT-TYPE
                  SYNTAX INTEGER (0..2147483647)
                  MAX-ACCESS read-only
                  STATUS current
                  DESCRIPTION "Age"
                  ::= {  staVpnIpcompEntry 10 }

staVpnIpcompSofts OBJECT-TYPE
                  SYNTAX INTEGER (0..2147483647)
                  MAX-ACCESS read-only
                  STATUS current
                  DESCRIPTION "Soft-Sec"
                  ::= {  staVpnIpcompEntry 11 }

staVpnIpcompMaxse OBJECT-TYPE
                  SYNTAX INTEGER (0..2147483647)
                  MAX-ACCESS read-only
                  STATUS current
                  DESCRIPTION "Max-Sec"
                  ::= {  staVpnIpcompEntry 12 }

staVpnIpcompKbyte OBJECT-TYPE
                  SYNTAX INTEGER (0..2147483647)
                  MAX-ACCESS read-only
                  STATUS current
                  DESCRIPTION "KByte"
                  ::= {  staVpnIpcompEntry 13 }

staVpnIpcompSoftk OBJECT-TYPE
                  SYNTAX INTEGER (0..2147483647)
                  MAX-ACCESS read-only
                  STATUS current
                  DESCRIPTION "Soft-KByte"
                  ::= {  staVpnIpcompEntry 14 }

staVpnIpcompMaxkb OBJECT-TYPE
                  SYNTAX INTEGER (0..2147483647)
                  MAX-ACCESS read-only
                  STATUS current
                  DESCRIPTION "Max-KByte"
                  ::= {  staVpnIpcompEntry 15 }

staVpnConnectTable OBJECT-TYPE
                   SYNTAX SEQUENCE OF StaVpnConnectEntry
                   MAX-ACCESS not-accessible
                   STATUS current
                   DESCRIPTION "Connections"
                   ::= {  staVpn 17 }

staVpnConnectEntry OBJECT-TYPE
                   SYNTAX StaVpnConnectEntry
                   MAX-ACCESS not-accessible
                   STATUS current
                   DESCRIPTION "entry in table"
                   INDEX { staVpnConnectPeer }
                   ::= {  staVpnConnectTable 1 }

StaVpnConnectEntry ::= SEQUENCE {
                   staVpnConnectPeer DisplayString,
                   staVpnConnectState INTEGER,
                   staVpnConnectLaster INTEGER,
                   staVpnConnectMode INTEGER,
                   staVpnConnectShtime INTEGER,
                   staVpnConnectPhysco DisplayString,
                   staVpnConnectB1dt INTEGER,
                   staVpnConnectRemote IpAddress,
                   staVpnConnectNatdet INTEGER,
                   staVpnConnectCrypta DisplayString,
                   staVpnConnectCryptl INTEGER,
                   staVpnConnectHashal DisplayString,
                   staVpnConnectHashle INTEGER,
                   staVpnConnectHmacal DisplayString,
                   staVpnConnectHmacle INTEGER,
                   staVpnConnectCompra DisplayString,
                   staVpnConnectClient INTEGER,
                   staVpnConnectConnti INTEGER
                  }

staVpnConnectPeer OBJECT-TYPE
                    SYNTAX DisplayString (SIZE(0..16))
                    MAX-ACCESS read-only
                    STATUS current
                    DESCRIPTION "Peer"
                    ::= {  staVpnConnectEntry 1 }

staVpnConnectState OBJECT-TYPE
                    SYNTAX INTEGER
                    {
                      init(0),
                      setup-wan(1),
                      ready(2),
                      wait-for-cb(3),
                      dial(4),
                      incoming-call(5),
                      protocol(6),
                      connection(7),
                      disconnecting(8),
                      call-back(9),
                      bundle-connect(10),
                      protocol-2(11),
                      reserved(12),
                      bundle(13)
                    }
                    MAX-ACCESS read-only
                    STATUS current
                    DESCRIPTION "State"
                    ::= {  staVpnConnectEntry 11 }

staVpnConnectLaster OBJECT-TYPE
                    SYNTAX INTEGER
                    {
                      none(0),
                      icmp-conn-error(275),
                      ifc-i-license-exceeded(4353),
                      ifc-r-license-exceeded(4609),
                      ifc-i-no-channel-available(4354),
                      ifc-r-no-channel-available(4610),
                      ifc-i-no-route-to-remote-gateway(4355),
                      ifc-r-no-route-to-remote-gateway(4611),
                      ifc-i-no-ppp-table-entry-matched(4356),
                      ifc-r-no-ppp-table-entry-matched(4612),
                      ifc-i-connection-timeout-dynamic(4357),
                      ifc-r-connection-timeout-dynamic(4613),
                      ifc-i-connection-timeout-ike-ipsec(4358),
                      ifc-r-connection-timeout-ike-ipsec(4614),
                      ifc-x-line-polling-failed(4871),
                      ifc-i-no-poll-table-entry-matched(4360),
                      ifc-i-name-resolution-failed(4361),
                      ifc-i-negotiator-charge-locked(4369),
                      ifc-i-negotiator-time-locked(4370),
                      ifc-i-negotiator-no-dial-number(4371),
                      ifc-i-negotiator-no-remote(4372),
                      ifc-i-negotiator-remote-blocked(4373),
                      ifc-i-negotiator-no-multiconnect(4374),
                      ifc-i-negotiator-line-error(4375),
                      ifc-i-physical-charge-locked(4385),
                      ifc-i-physical-time-locked(4386),
                      ifc-i-physical-no-dial-number(4387),
                      ifc-i-physical-no-remote(4388),
                      ifc-i-physical-no-server-address(4389),
                      ifc-i-physical-remote-locked(4390),
                      ifc-i-physical-no-multiconnect(4391),
                      ifc-x-physical-line-error(4904),
                      ike-r-license-exceeded(8705),
                      ike-r-exchange-type-mismatch(8706),
                      ike-i-no-proposal-matched(8451),
                      ike-r-no-proposal-matched(8707),
                      ike-r-ike-group-mismatch(8708),
                      ike-r-life-type-unsupported(8709),
                      ike-r-life-duration-mismatch(8710),
                      ike-r-id-type-unsupported(8711),
                      ike-r-id-type-mismatch(8712),
                      ike-r-no-rule-matched-id(8713),
                      ike-i-ike-key-mismatch(8458),
                      ike-r-ike-key-mismatch(8714),
                      ike-r-license-demosn-exceeded(8715),
                      ike-r-license-sn-exceeded(8716),
                      ike-i-dpd-timeout(8461),
                      ike-r-dpd-timeout(8717),
                      ike-i-unable-to-get-issuer-cert(8462),
                      ike-r-unable-to-get-issuer-cert(8718),
                      ike-i-unable-to-get-crl(8463),
                      ike-r-unable-to-get-crl(8719),
                      ike-i-unable-to-decrypt-cert-signature(8464),
                      ike-r-unable-to-decrypt-cert-signature(8720),
                      ike-i-unable-to-decrypt-crl-signature(8465),
                      ike-r-unable-to-decrypt-crl-signature(8721),
                      ike-i-unable-to-decode-issuer-public-key(8466),
                      ike-r-unable-to-decode-issuer-public-key(8722),
                      ike-i-cert-signature-failure(8467),
                      ike-r-cert-signature-failure(8723),
                      ike-i-crl-signature-failure(8468),
                      ike-r-crl-signature-failure(8724),
                      ike-i-cert-not-yet-valid(8469),
                      ike-r-cert-not-yet-valid(8725),
                      ike-i-cert-has-expired(8470),
                      ike-r-cert-has-expired(8726),
                      ike-i-crl-not-yet-valid(8471),
                      ike-r-crl-not-yet-valid(8727),
                      ike-i-crl-has-expired(8472),
                      ike-r-crl-has-expired(8728),
                      ike-i-error-in-cert-not-before-field(8473),
                      ike-r-error-in-cert-not-before-field(8729),
                      ike-i-error-in-cert-not-after-field(8474),
                      ike-r-error-in-cert-not-after-field(8730),
                      ike-i-error-in-crl-last-update-field(8475),
                      ike-r-error-in-crl-last-update-field(8731),
                      ike-i-error-in-crl-next-update-field(8476),
                      ike-r-error-in-crl-next-update-field(8732),
                      ike-i-out-of-mem(8477),
                      ike-r-out-of-mem(8733),
                      ike-i-depth-zero-self-signed-cert(8478),
                      ike-r-depth-zero-self-signed-cert(8734),
                      ike-i-self-signed-cert-in-chain(8479),
                      ike-r-self-signed-cert-in-chain(8735),
                      ike-i-unable-to-get-issuer-cert-locally(8480),
                      ike-r-unable-to-get-issuer-cert-locally(8736),
                      ike-i-unable-to-verify-leaf-signature(8481),
                      ike-r-unable-to-verify-leaf-signature(8737),
                      ike-i-cert-chain-too-long(8482),
                      ike-r-cert-chain-too-long(8738),
                      ike-i-cert-revoked(8483),
                      ike-r-cert-revoked(8739),
                      ike-i-invalid-ca(8484),
                      ike-r-invalid-ca(8740),
                      ike-i-path-length-exceeded(8485),
                      ike-r-path-length-exceeded(8741),
                      ike-i-invalid-purpose(8486),
                      ike-r-invalid-purpose(8742),
                      ike-i-cert-untrusted(8487),
                      ike-r-cert-untrusted(8743),
                      ike-i-cert-rejected(8488),
                      ike-r-cert-rejected(8744),
                      ike-i-subject-issuer-mismatch(8489),
                      ike-r-subject-issuer-mismatch(8745),
                      ike-i-akid-skid-mismatch(8490),
                      ike-r-akid-skid-mismatch(8746),
                      ike-i-akid-issuer-serial-mismatch(8491),
                      ike-r-akid-issuer-serial-mismatch(8747),
                      ike-i-keyusage-no-certsign(8492),
                      ike-r-keyusage-no-certsign(8748),
                      ike-i-unable-to-get-crl-issuer(8493),
                      ike-r-unable-to-get-crl-issuer(8749),
                      ike-i-unhandled-critical-extension(8494),
                      ike-r-unhandled-critical-extension(8750),
                      ike-i-keyusage-no-crl-sign(8495),
                      ike-r-keyusage-no-crl-sign(8751),
                      ike-i-unhandled-critical-crl-extension(8496),
                      ike-r-unhandled-critical-crl-extension(8752),
                      ike-i-crl-has-exceeded-exceedance(8497),
                      ike-r-crl-has-exceeded-exceedance(8753),
                      ike-i-application-verification(8498),
                      ike-r-application-verification(8754),
                      ike-i-cert-revoked-unspecified(8499),
                      ike-r-cert-revoked-unspecified(8755),
                      ike-i-cert-revoked-key-compromise(8500),
                      ike-r-cert-revoked-key-compromise(8756),
                      ike-i-cert-revoked-ca-compromise(8501),
                      ike-r-cert-revoked-ca-compromise(8757),
                      ike-i-cert-revoked-affiliation-changed(8502),
                      ike-r-cert-revoked-affiliation-changed(8758),
                      ike-i-cert-revoked-superseded(8503),
                      ike-r-cert-revoked-superseded(8759),
                      ike-i-cert-revoked-cessation-of-operation(8504),
                      ike-r-cert-revoked-cessation-of-operation(8760),
                      ike-i-cert-revoked-certificate-hold(8505),
                      ike-r-cert-revoked-certificate-hold(8761),
                      ike-i-cert-revoked-remove-from-crl(8506),
                      ike-r-cert-revoked-remove-from-crl(8762),
                      ike-i-cert-revoked-privilege-withdrawn(8507),
                      ike-r-cert-revoked-privilege-withdrawn(8763),
                      ike-i-cert-revoked-a-a-compromise(8508),
                      ike-r-cert-revoked-a-a-compromise(8764),
                      ike-i-cert-revoked-unknown-reason(8509),
                      ike-r-cert-revoked-unknown-reason(8765),
                      ike-i-general-failure(8703),
                      ike-r-general-failure(8959),
                      ike-i-out-of-memory(8702),
                      ike-r-out-of-memory(8958),
                      ipsec-r-no-rule-matched-ids(12801),
                      ipsec-i-no-proposal-matched(12546),
                      ipsec-r-no-proposal-matched(12802),
                      ipsec-r-pfs-group-mismatch(12803),
                      remote-disconnected(17153),
                      manual-disconnect(17154),
                      shorthold-expired(17155),
                      physical-disconnected(17156),
                      invalid-physical-channel(17157),
                      dynamic-vpn-reconnect(17158),
                      configuration-changed(17159),
                      removed-from-config(17160)
                    }
                    MAX-ACCESS read-write
                    STATUS current
                    DESCRIPTION "Last-Error"
                    ::= {  staVpnConnectEntry 16 }

staVpnConnectMode OBJECT-TYPE
                    SYNTAX INTEGER
                    {
                      active(128),
                      passive(0)
                    }
                    MAX-ACCESS read-only
                    STATUS current
                    DESCRIPTION "Mode"
                    ::= {  staVpnConnectEntry 12 }

staVpnConnectShtime OBJECT-TYPE
                    SYNTAX INTEGER (0..65535)
                    MAX-ACCESS read-only
                    STATUS current
                    DESCRIPTION "SH-Time"
                    ::= {  staVpnConnectEntry 13 }

staVpnConnectPhysco OBJECT-TYPE
                    SYNTAX DisplayString (SIZE(0..16))
                    MAX-ACCESS read-only
                    STATUS current
                    DESCRIPTION "phys.-Conn."
                    ::= {  staVpnConnectEntry 2 }

staVpnConnectB1dt OBJECT-TYPE
                    SYNTAX INTEGER (0..65535)
                    MAX-ACCESS read-only
                    STATUS current
                    DESCRIPTION "B1-DT"
                    ::= {  staVpnConnectEntry 14 }

staVpnConnectRemote OBJECT-TYPE
                    SYNTAX IpAddress
                    MAX-ACCESS read-only
                    STATUS current
                    DESCRIPTION "Remote-Gw"
                    ::= {  staVpnConnectEntry 3 }

staVpnConnectNatdet OBJECT-TYPE
                    SYNTAX INTEGER
                    {
                      no-nat(0),
                      nat-local(1),
                      nat-remote(2),
                      nat-both(3)
                    }
                    MAX-ACCESS read-only
                    STATUS current
                    DESCRIPTION "Nat-Detection"
                    ::= {  staVpnConnectEntry 18 }

staVpnConnectCrypta OBJECT-TYPE
                    SYNTAX DisplayString (SIZE(0..14))
                    MAX-ACCESS read-only
                    STATUS current
                    DESCRIPTION "Crypt-Alg"
                    ::= {  staVpnConnectEntry 4 }

staVpnConnectCryptl OBJECT-TYPE
                    SYNTAX INTEGER (0..65535)
                    MAX-ACCESS read-only
                    STATUS current
                    DESCRIPTION "Crypt-Length"
                    ::= {  staVpnConnectEntry 5 }

staVpnConnectHashal OBJECT-TYPE
                    SYNTAX DisplayString (SIZE(0..14))
                    MAX-ACCESS read-only
                    STATUS current
                    DESCRIPTION "Hash-Alg"
                    ::= {  staVpnConnectEntry 6 }

staVpnConnectHashle OBJECT-TYPE
                    SYNTAX INTEGER (0..65535)
                    MAX-ACCESS read-only
                    STATUS current
                    DESCRIPTION "Hash-Length"
                    ::= {  staVpnConnectEntry 7 }

staVpnConnectHmacal OBJECT-TYPE
                    SYNTAX DisplayString (SIZE(0..14))
                    MAX-ACCESS read-only
                    STATUS current
                    DESCRIPTION "Hmac-Alg"
                    ::= {  staVpnConnectEntry 8 }

staVpnConnectHmacle OBJECT-TYPE
                    SYNTAX INTEGER (0..65535)
                    MAX-ACCESS read-only
                    STATUS current
                    DESCRIPTION "Hmac-Length"
                    ::= {  staVpnConnectEntry 9 }

staVpnConnectCompra OBJECT-TYPE
                    SYNTAX DisplayString (SIZE(0..14))
                    MAX-ACCESS read-only
                    STATUS current
                    DESCRIPTION "Compr-Alg"
                    ::= {  staVpnConnectEntry 10 }

staVpnConnectClient OBJECT-TYPE
                    SYNTAX INTEGER
                    {
                      not-available(-1),
                      demo-version(0)
                    }
                    MAX-ACCESS read-only
                    STATUS current
                    DESCRIPTION "Client-SN"
                    ::= {  staVpnConnectEntry 17 }

staVpnConnectConnti OBJECT-TYPE
                    SYNTAX INTEGER (0..2147483647)
                    MAX-ACCESS read-only
                    STATUS current
                    DESCRIPTION "Conn.-time"
                    ::= {  staVpnConnectEntry 19 }

staVpnDeletev OBJECT-TYPE
              SYNTAX DisplayString
              MAX-ACCESS read-write
              STATUS current
              DESCRIPTION "Delete-Values"
              ::= {  staVpn 12 }

staPptp OBJECT IDENTIFIER ::= { sta 27}
staPptpRxp OBJECT-TYPE
           SYNTAX Counter32
           MAX-ACCESS read-only
           STATUS current
           DESCRIPTION "Rx-Packets"
           ::= {  staPptp 1 }

staPptpTxp OBJECT-TYPE
           SYNTAX Counter32
           MAX-ACCESS read-only
           STATUS current
           DESCRIPTION "Tx-Packets"
           ::= {  staPptp 2 }

staPptpEch OBJECT-TYPE
           SYNTAX Counter32
           MAX-ACCESS read-only
           STATUS current
           DESCRIPTION "Echo-Retries"
           ::= {  staPptp 3 }

staPptpAck OBJECT-TYPE
           SYNTAX Counter32
           MAX-ACCESS read-only
           STATUS current
           DESCRIPTION "Ack-Timeouts"
           ::= {  staPptp 4 }

staPptpDro OBJECT-TYPE
           SYNTAX Counter32
           MAX-ACCESS read-only
           STATUS current
           DESCRIPTION "Dropped-Packets"
           ::= {  staPptp 5 }

staPptpRxe OBJECT-TYPE
           SYNTAX Counter32
           MAX-ACCESS read-only
           STATUS current
           DESCRIPTION "Rx-Errors"
           ::= {  staPptp 6 }

staPptpTcp OBJECT-TYPE
           SYNTAX Counter32
           MAX-ACCESS read-only
           STATUS current
           DESCRIPTION "Tcp-Errors"
           ::= {  staPptp 7 }

staPptpCal OBJECT-TYPE
           SYNTAX Counter32
           MAX-ACCESS read-only
           STATUS current
           DESCRIPTION "Call-Errors"
           ::= {  staPptp 8 }

staPptpConTable OBJECT-TYPE
                SYNTAX SEQUENCE OF StaPptpConEntry
                MAX-ACCESS not-accessible
                STATUS current
                DESCRIPTION "Connections"
                ::= {  staPptp 9 }

staPptpConEntry OBJECT-TYPE
                SYNTAX StaPptpConEntry
                MAX-ACCESS not-accessible
                STATUS current
                DESCRIPTION "entry in table"
                INDEX { staPptpConChann }
                ::= {  staPptpConTable 1 }

StaPptpConEntry ::= SEQUENCE {
                staPptpConChann DisplayString,
                staPptpConState INTEGER,
                staPptpConLaste INTEGER,
                staPptpConMode INTEGER,
                staPptpConShtim INTEGER,
                staPptpConPhysc DisplayString,
                staPptpConPeera IpAddress,
                staPptpConIpadd IpAddress,
                staPptpConDnsde IpAddress,
                staPptpConDnsba IpAddress,
                staPptpConNbnsd IpAddress,
                staPptpConNbnsb IpAddress,
                staPptpConConnt INTEGER,
                staPptpConGatew IpAddress
               }

staPptpConChann OBJECT-TYPE
                SYNTAX DisplayString (SIZE(0..16))
                MAX-ACCESS read-only
                STATUS current
                DESCRIPTION "Channel"
                ::= {  staPptpConEntry 1 }

staPptpConState OBJECT-TYPE
                SYNTAX INTEGER
                {
                  init(0),
                  setup-wan(1),
                  ready(2),
                  wait-for-cb(3),
                  dial(4),
                  incoming-call(5),
                  protocol(6),
                  connection(7),
                  disconnecting(8),
                  call-back(9),
                  bundle-connect(10),
                  protocol-2(11),
                  reserved(12),
                  bundle(13)
                }
                MAX-ACCESS read-only
                STATUS current
                DESCRIPTION "State"
                ::= {  staPptpConEntry 3 }

staPptpConLaste OBJECT-TYPE
                SYNTAX INTEGER
                {
                  none(0),
                  remote-disconnected(17153),
                  manual-disconnect(17154),
                  shorthold-expired(17155),
                  physical-disconnected(17156),
                  invalid-physical-channel(17157),
                  dynamic-vpn-reconnect(17158),
                  configuration-changed(17159),
                  removed-from-config(17160),
                  remote-doubled(267),
                  icmp-conn-error(275),
                  dhcp-timeout(277),
                  pptp-no-response(278),
                  vpn-no-response(279),
                  arp-no-response(280),
                  pptp-no-channel(513),
                  pptp-bad-format(514),
                  pptp-bad-value(515),
                  pptp-no-ressource(516),
                  pptp-bad-call-id(517),
                  pptp-gen-error(518),
                  lcp-rejected(32768),
                  auth-error(32769),
                  auth-rejected(32770),
                  lcp-conn-error(32771),
                  pap-rejected(32784),
                  pap-rx-timeout(32785),
                  pap-tx-timeout(32786),
                  wrong-pap-req(32787),
                  pap-nak-received(32788),
                  unkn-pap-peer(32789),
                  chap-rejected(32800),
                  chap-rx-timeout(32801),
                  chap-tx-timeout(32802),
                  wrong-chap-resp(32803),
                  chap-fail-recvd(32804),
                  unkn-chap-peer(32805),
                  ipxcp-rejected(32816),
                  wrong-ipxcp-net(32817),
                  ipxcp-net-reject(32818),
                  ipxcp-route-unkn(32819),
                  ipcp-rejected(32832),
                  ccp-rejected(32848),
                  no-ncp-available(33008)
                }
                MAX-ACCESS read-write
                STATUS current
                DESCRIPTION "Last-Error"
                ::= {  staPptpConEntry 11 }

staPptpConMode OBJECT-TYPE
                SYNTAX INTEGER
                {
                  active(128),
                  passive(0)
                }
                MAX-ACCESS read-only
                STATUS current
                DESCRIPTION "Mode"
                ::= {  staPptpConEntry 4 }

staPptpConShtim OBJECT-TYPE
                SYNTAX INTEGER (0..65535)
                MAX-ACCESS read-only
                STATUS current
                DESCRIPTION "SH-Time"
                ::= {  staPptpConEntry 5 }

staPptpConPhysc OBJECT-TYPE
                SYNTAX DisplayString (SIZE(0..16))
                MAX-ACCESS read-only
                STATUS current
                DESCRIPTION "Phys.-connection"
                ::= {  staPptpConEntry 6 }

staPptpConPeera OBJECT-TYPE
                SYNTAX IpAddress
                MAX-ACCESS read-only
                STATUS current
                DESCRIPTION "Peer-Address"
                ::= {  staPptpConEntry 7 }

staPptpConIpadd OBJECT-TYPE
                SYNTAX IpAddress
                MAX-ACCESS read-only
                STATUS current
                DESCRIPTION "IP-Address"
                ::= {  staPptpConEntry 8 }

staPptpConDnsde OBJECT-TYPE
                SYNTAX IpAddress
                MAX-ACCESS read-only
                STATUS current
                DESCRIPTION "DNS-Default"
                ::= {  staPptpConEntry 9 }

staPptpConDnsba OBJECT-TYPE
                SYNTAX IpAddress
                MAX-ACCESS read-only
                STATUS current
                DESCRIPTION "DNS-Backup"
                ::= {  staPptpConEntry 12 }

staPptpConNbnsd OBJECT-TYPE
                SYNTAX IpAddress
                MAX-ACCESS read-only
                STATUS current
                DESCRIPTION "NBNS-Default"
                ::= {  staPptpConEntry 10 }

staPptpConNbnsb OBJECT-TYPE
                SYNTAX IpAddress
                MAX-ACCESS read-only
                STATUS current
                DESCRIPTION "NBNS-Backup"
                ::= {  staPptpConEntry 13 }

staPptpConConnt OBJECT-TYPE
                SYNTAX INTEGER (0..2147483647)
                MAX-ACCESS read-only
                STATUS current
                DESCRIPTION "Conn.-time"
                ::= {  staPptpConEntry 14 }

staPptpConGatew OBJECT-TYPE
                SYNTAX IpAddress
                MAX-ACCESS read-only
                STATUS current
                DESCRIPTION "Gateway"
                ::= {  staPptpConEntry 15 }

staPptpTun OBJECT-TYPE
           SYNTAX INTEGER
           MAX-ACCESS read-only
           STATUS current
           DESCRIPTION "Tunnel"
           ::= {  staPptp 10 }

staPptpDel OBJECT-TYPE
           SYNTAX DisplayString
           MAX-ACCESS read-write
           STATUS current
           DESCRIPTION "Delete-Values"
           ::= {  staPptp 11 }

staPptpFlo OBJECT-TYPE
           SYNTAX INTEGER
           MAX-ACCESS read-only
           STATUS current
           DESCRIPTION "Flow-Control-Queue"
           ::= {  staPptp 12 }

staDhcp OBJECT IDENTIFIER ::= { sta 32}
staDhcpWanTable OBJECT-TYPE
                SYNTAX SEQUENCE OF StaDhcpWanEntry
                MAX-ACCESS not-accessible
                STATUS current
                DESCRIPTION "WAN-IP-List"
                ::= {  staDhcp 20 }

staDhcpWanEntry OBJECT-TYPE
                SYNTAX StaDhcpWanEntry
                MAX-ACCESS not-accessible
                STATUS current
                DESCRIPTION "entry in table"
                INDEX { staDhcpWanIfc }
                ::= {  staDhcpWanTable 1 }

StaDhcpWanEntry ::= SEQUENCE {
                staDhcpWanIfc INTEGER,
                staDhcpWanIpadd IpAddress,
                staDhcpWanIpnet IpAddress,
                staDhcpWanGatew IpAddress,
                staDhcpWanDnsde IpAddress,
                staDhcpWanDnsba IpAddress,
                staDhcpWanNbnsd IpAddress,
                staDhcpWanNbnsb IpAddress,
                staDhcpWanDomai DisplayString,
                staDhcpWanDhcps IpAddress
               }

staDhcpWanIfc OBJECT-TYPE
                SYNTAX INTEGER
                {
                  dsl-ch-1(1),
                  dsl-ch-2(2),
                  dsl-ch-3(3),
                  dsl-ch-4(4),
                  dsl-ch-5(5),
                  dsl-ch-6(6),
                  dsl-ch-7(7),
                  dsl-ch-8(8),
                  ch01(9),
                  ch02(10),
                  ext(11)
                }
                MAX-ACCESS read-only
                STATUS current
                DESCRIPTION "Ifc"
                ::= {  staDhcpWanEntry 1 }

staDhcpWanIpadd OBJECT-TYPE
                SYNTAX IpAddress
                MAX-ACCESS read-only
                STATUS current
                DESCRIPTION "IP-Address"
                ::= {  staDhcpWanEntry 2 }

staDhcpWanIpnet OBJECT-TYPE
                SYNTAX IpAddress
                MAX-ACCESS read-only
                STATUS current
                DESCRIPTION "IP-Netmask"
                ::= {  staDhcpWanEntry 3 }

staDhcpWanGatew OBJECT-TYPE
                SYNTAX IpAddress
                MAX-ACCESS read-only
                STATUS current
                DESCRIPTION "Gateway"
                ::= {  staDhcpWanEntry 4 }

staDhcpWanDnsde OBJECT-TYPE
                SYNTAX IpAddress
                MAX-ACCESS read-only
                STATUS current
                DESCRIPTION "DNS-Default"
                ::= {  staDhcpWanEntry 5 }

staDhcpWanDnsba OBJECT-TYPE
                SYNTAX IpAddress
                MAX-ACCESS read-only
                STATUS current
                DESCRIPTION "DNS-Backup"
                ::= {  staDhcpWanEntry 6 }

staDhcpWanNbnsd OBJECT-TYPE
                SYNTAX IpAddress
                MAX-ACCESS read-only
                STATUS current
                DESCRIPTION "NBNS-Default"
                ::= {  staDhcpWanEntry 7 }

staDhcpWanNbnsb OBJECT-TYPE
                SYNTAX IpAddress
                MAX-ACCESS read-only
                STATUS current
                DESCRIPTION "NBNS-Backup"
                ::= {  staDhcpWanEntry 8 }

staDhcpWanDomai OBJECT-TYPE
                SYNTAX DisplayString (SIZE(0..255))
                MAX-ACCESS read-only
                STATUS current
                DESCRIPTION "Domain"
                ::= {  staDhcpWanEntry 10 }

staDhcpWanDhcps OBJECT-TYPE
                SYNTAX IpAddress
                MAX-ACCESS read-only
                STATUS current
                DESCRIPTION "DHCP-server"
                ::= {  staDhcpWanEntry 9 }

staDhcpLanTable OBJECT-TYPE
                SYNTAX SEQUENCE OF StaDhcpLanEntry
                MAX-ACCESS not-accessible
                STATUS current
                DESCRIPTION "LAN-IP-List"
                ::= {  staDhcp 21 }

staDhcpLanEntry OBJECT-TYPE
                SYNTAX StaDhcpLanEntry
                MAX-ACCESS not-accessible
                STATUS current
                DESCRIPTION "entry in table"
                INDEX { staDhcpLanIfc }
                ::= {  staDhcpLanTable 1 }

StaDhcpLanEntry ::= SEQUENCE {
                staDhcpLanIfc DisplayString,
                staDhcpLanIpadd IpAddress,
                staDhcpLanIpnet IpAddress,
                staDhcpLanGatew IpAddress,
                staDhcpLanDnsde IpAddress,
                staDhcpLanDnsba IpAddress,
                staDhcpLanNbnsd IpAddress,
                staDhcpLanNbnsb IpAddress,
                staDhcpLanDomai DisplayString,
                staDhcpLanDhcps IpAddress
               }

staDhcpLanIfc OBJECT-TYPE
                SYNTAX DisplayString (SIZE(0..16))
                MAX-ACCESS read-only
                STATUS current
                DESCRIPTION "Ifc"
                ::= {  staDhcpLanEntry 1 }

staDhcpLanIpadd OBJECT-TYPE
                SYNTAX IpAddress
                MAX-ACCESS read-only
                STATUS current
                DESCRIPTION "IP-Address"
                ::= {  staDhcpLanEntry 2 }

staDhcpLanIpnet OBJECT-TYPE
                SYNTAX IpAddress
                MAX-ACCESS read-only
                STATUS current
                DESCRIPTION "IP-Netmask"
                ::= {  staDhcpLanEntry 3 }

staDhcpLanGatew OBJECT-TYPE
                SYNTAX IpAddress
                MAX-ACCESS read-only
                STATUS current
                DESCRIPTION "Gateway"
                ::= {  staDhcpLanEntry 4 }

staDhcpLanDnsde OBJECT-TYPE
                SYNTAX IpAddress
                MAX-ACCESS read-only
                STATUS current
                DESCRIPTION "DNS-Default"
                ::= {  staDhcpLanEntry 5 }

staDhcpLanDnsba OBJECT-TYPE
                SYNTAX IpAddress
                MAX-ACCESS read-only
                STATUS current
                DESCRIPTION "DNS-Backup"
                ::= {  staDhcpLanEntry 6 }

staDhcpLanNbnsd OBJECT-TYPE
                SYNTAX IpAddress
                MAX-ACCESS read-only
                STATUS current
                DESCRIPTION "NBNS-Default"
                ::= {  staDhcpLanEntry 7 }

staDhcpLanNbnsb OBJECT-TYPE
                SYNTAX IpAddress
                MAX-ACCESS read-only
                STATUS current
                DESCRIPTION "NBNS-Backup"
                ::= {  staDhcpLanEntry 8 }

staDhcpLanDomai OBJECT-TYPE
                SYNTAX DisplayString (SIZE(0..255))
                MAX-ACCESS read-only
                STATUS current
                DESCRIPTION "Domain"
                ::= {  staDhcpLanEntry 10 }

staDhcpLanDhcps OBJECT-TYPE
                SYNTAX IpAddress
                MAX-ACCESS read-only
                STATUS current
                DESCRIPTION "DHCP-server"
                ::= {  staDhcpLanEntry 9 }

staIsdn OBJECT IDENTIFIER ::= { sta 33}
staIsdnLin OBJECT IDENTIFIER ::= { staIsdn 1}
staIsdnLinS0Table OBJECT-TYPE
                   SYNTAX SEQUENCE OF StaIsdnLinS0Entry
                   MAX-ACCESS not-accessible
                   STATUS current
                   DESCRIPTION "S0"
                   ::= {  staIsdnLin 1 }

staIsdnLinS0Entry OBJECT-TYPE
                   SYNTAX StaIsdnLinS0Entry
                   MAX-ACCESS not-accessible
                   STATUS current
                   DESCRIPTION "entry in table"
                   INDEX { staIsdnLinS0Ifc }
                   ::= {  staIsdnLinS0Table 1 }

StaIsdnLinS0Entry ::= SEQUENCE {
                   staIsdnLinS0Ifc INTEGER,
                   staIsdnLinS0Ope INTEGER
                  }

staIsdnLinS0Ifc OBJECT-TYPE
                SYNTAX INTEGER
                {
                  dsl-1(1),
                  dsl-2(2),
                  dsl-3(3),
                  dsl-4(4),
                  s0-1(5),
                  ext(6)
                }
                MAX-ACCESS read-only
                STATUS current
                DESCRIPTION "Ifc"
                ::= {  staIsdnLinS0Entry 1 }

staIsdnLinS0Ope OBJECT-TYPE
                SYNTAX INTEGER
                {
                  no(0),
                  yes(1)
                }
                MAX-ACCESS read-only
                STATUS current
                DESCRIPTION "Operating"
                ::= {  staIsdnLinS0Entry 2 }

staIsdnFra OBJECT IDENTIFIER ::= { staIsdn 2}
staIsdnFraS0Table OBJECT-TYPE
                   SYNTAX SEQUENCE OF StaIsdnFraS0Entry
                   MAX-ACCESS not-accessible
                   STATUS current
                   DESCRIPTION "S0"
                   ::= {  staIsdnFra 1 }

staIsdnFraS0Entry OBJECT-TYPE
                   SYNTAX StaIsdnFraS0Entry
                   MAX-ACCESS not-accessible
                   STATUS current
                   DESCRIPTION "entry in table"
                   INDEX { staIsdnFraS0Ifc }
                   ::= {  staIsdnFraS0Table 1 }

StaIsdnFraS0Entry ::= SEQUENCE {
                   staIsdnFraS0Ifc INTEGER,
                   staIsdnFraS0Sta DisplayString,
                   staIsdnFraS0B1f BITS,
                   staIsdnFraS0B2f BITS
                  }

staIsdnFraS0Ifc OBJECT-TYPE
                SYNTAX INTEGER
                {
                  dsl-1(1),
                  dsl-2(2),
                  dsl-3(3),
                  dsl-4(4),
                  s0-1(5),
                  ext(6)
                }
                MAX-ACCESS read-only
                STATUS current
                DESCRIPTION "Ifc"
                ::= {  staIsdnFraS0Entry 1 }

staIsdnFraS0Sta OBJECT-TYPE
                SYNTAX DisplayString (SIZE(0..255))
                MAX-ACCESS read-only
                STATUS current
                DESCRIPTION "State"
                ::= {  staIsdnFraS0Entry 2 }

staIsdnFraS0B1f OBJECT-TYPE
                SYNTAX BITS
                {
                  loop(7),
                  rx-data(6),
                  tx-data(5)
                }
                MAX-ACCESS read-only
                STATUS current
                DESCRIPTION "B1-Frame"
                ::= {  staIsdnFraS0Entry 3 }

staIsdnFraS0B2f OBJECT-TYPE
                SYNTAX BITS
                {
                  loop(7),
                  rx-data(6),
                  tx-data(5)
                }
                MAX-ACCESS read-only
                STATUS current
                DESCRIPTION "B2-Frame"
                ::= {  staIsdnFraS0Entry 4 }

staIsdnSig OBJECT IDENTIFIER ::= { staIsdn 3}
staIsdnSigLay OBJECT IDENTIFIER ::= { staIsdnSig 1}
staIsdnSigLayLapTable OBJECT-TYPE
                      SYNTAX SEQUENCE OF StaIsdnSigLayLapEntry
                      MAX-ACCESS not-accessible
                      STATUS current
                      DESCRIPTION "LAPD"
                      ::= {  staIsdnSigLay 1 }

staIsdnSigLayLapEntry OBJECT-TYPE
                      SYNTAX StaIsdnSigLayLapEntry
                      MAX-ACCESS not-accessible
                      STATUS current
                      DESCRIPTION "entry in table"
                      INDEX { staIsdnSigLayLapCha }
                      ::= {  staIsdnSigLayLapTable 1 }

StaIsdnSigLayLapEntry ::= SEQUENCE {
                      staIsdnSigLayLapCha INTEGER,
                      staIsdnSigLayLapTei INTEGER,
                      staIsdnSigLayLapL2a INTEGER,
                      staIsdnSigLayLapCon INTEGER
                     }

staIsdnSigLayLapCha OBJECT-TYPE
                    SYNTAX INTEGER
                    {
                      e1-1(1),
                      e1-2(2)
                    }
                    MAX-ACCESS read-only
                    STATUS current
                    DESCRIPTION "Channel"
                    ::= {  staIsdnSigLayLapEntry 1 }

staIsdnSigLayLapTei OBJECT-TYPE
                    SYNTAX INTEGER
                    {
                      none(128)
                    }
                    MAX-ACCESS read-only
                    STATUS current
                    DESCRIPTION "TEI"
                    ::= {  staIsdnSigLayLapEntry 2 }

staIsdnSigLayLapL2a OBJECT-TYPE
                    SYNTAX INTEGER
                    {
                      no(0),
                      yes(1)
                    }
                    MAX-ACCESS read-only
                    STATUS current
                    DESCRIPTION "L2-Activation"
                    ::= {  staIsdnSigLayLapEntry 3 }

staIsdnSigLayLapCon OBJECT-TYPE
                    SYNTAX INTEGER (0..255)
                    MAX-ACCESS read-only
                    STATUS current
                    DESCRIPTION "Connections"
                    ::= {  staIsdnSigLayLapEntry 4 }

staIsdnSigMan OBJECT IDENTIFIER ::= { staIsdnSig 3}
staIsdnSigManDinTable OBJECT-TYPE
                      SYNTAX SEQUENCE OF StaIsdnSigManDinEntry
                      MAX-ACCESS not-accessible
                      STATUS current
                      DESCRIPTION "D-Info"
                      ::= {  staIsdnSigMan 1 }

staIsdnSigManDinEntry OBJECT-TYPE
                      SYNTAX StaIsdnSigManDinEntry
                      MAX-ACCESS not-accessible
                      STATUS current
                      DESCRIPTION "entry in table"
                      INDEX { staIsdnSigManDinCha }
                      ::= {  staIsdnSigManDinTable 1 }

StaIsdnSigManDinEntry ::= SEQUENCE {
                      staIsdnSigManDinCha INTEGER,
                      staIsdnSigManDinPro INTEGER,
                      staIsdnSigManDinLay INTEGER,
                      staIsdnSigManDinTei INTEGER,
                      staIsdnSigManDinS0a INTEGER
                     }

staIsdnSigManDinCha OBJECT-TYPE
                    SYNTAX INTEGER
                    {
                      dsl-1(1),
                      dsl-2(2),
                      dsl-3(3),
                      dsl-4(4),
                      s0-1(5),
                      ext(6)
                    }
                    MAX-ACCESS read-only
                    STATUS current
                    DESCRIPTION "Channel"
                    ::= {  staIsdnSigManDinEntry 1 }

staIsdnSigManDinPro OBJECT-TYPE
                    SYNTAX INTEGER
                    {
                      no(0),
                      dss1(1),
                      e1tr6(2),
                      p2p-dss1(4),
                      auto(255)
                    }
                    MAX-ACCESS read-only
                    STATUS current
                    DESCRIPTION "Protocol"
                    ::= {  staIsdnSigManDinEntry 2 }

staIsdnSigManDinLay OBJECT-TYPE
                    SYNTAX INTEGER
                    {
                      no(0),
                      yes(1)
                    }
                    MAX-ACCESS read-only
                    STATUS current
                    DESCRIPTION "Layer-2"
                    ::= {  staIsdnSigManDinEntry 3 }

staIsdnSigManDinTei OBJECT-TYPE
                    SYNTAX INTEGER
                    {
                      no(0),
                      yes(1)
                    }
                    MAX-ACCESS read-only
                    STATUS current
                    DESCRIPTION "TEI"
                    ::= {  staIsdnSigManDinEntry 4 }

staIsdnSigManDinS0a OBJECT-TYPE
                    SYNTAX INTEGER
                    {
                      no(0),
                      yes(1)
                    }
                    MAX-ACCESS read-only
                    STATUS current
                    DESCRIPTION "S0-Activation"
                    ::= {  staIsdnSigManDinEntry 5 }

staIsdnSigManErrTable OBJECT-TYPE
                      SYNTAX SEQUENCE OF StaIsdnSigManErrEntry
                      MAX-ACCESS not-accessible
                      STATUS current
                      DESCRIPTION "Error-Statistic"
                      ::= {  staIsdnSigMan 2 }

staIsdnSigManErrEntry OBJECT-TYPE
                      SYNTAX StaIsdnSigManErrEntry
                      MAX-ACCESS not-accessible
                      STATUS current
                      DESCRIPTION "entry in table"
                      INDEX { staIsdnSigManErrIfc }
                      ::= {  staIsdnSigManErrTable 1 }

StaIsdnSigManErrEntry ::= SEQUENCE {
                      staIsdnSigManErrIfc INTEGER,
                      staIsdnSigManErrA INTEGER,
                      staIsdnSigManErrB INTEGER,
                      staIsdnSigManErrC INTEGER,
                      staIsdnSigManErrD INTEGER,
                      staIsdnSigManErrE INTEGER,
                      staIsdnSigManErrF INTEGER,
                      staIsdnSigManErrG INTEGER,
                      staIsdnSigManErrH INTEGER,
                      staIsdnSigManErrI INTEGER,
                      staIsdnSigManErrJ INTEGER,
                      staIsdnSigManErrK INTEGER,
                      staIsdnSigManErrL INTEGER,
                      staIsdnSigManErrM INTEGER,
                      staIsdnSigManErrN INTEGER,
                      staIsdnSigManErrO INTEGER
                     }

staIsdnSigManErrIfc OBJECT-TYPE
                    SYNTAX INTEGER
                    {
                      dsl-1(1),
                      dsl-2(2),
                      dsl-3(3),
                      dsl-4(4),
                      s0-1(5),
                      ext(6)
                    }
                    MAX-ACCESS read-only
                    STATUS current
                    DESCRIPTION "Ifc"
                    ::= {  staIsdnSigManErrEntry 1 }

staIsdnSigManErrA OBJECT-TYPE
                    SYNTAX INTEGER (0..65535)
                    MAX-ACCESS read-only
                    STATUS current
                    DESCRIPTION "A"
                    ::= {  staIsdnSigManErrEntry 2 }

staIsdnSigManErrB OBJECT-TYPE
                    SYNTAX INTEGER (0..65535)
                    MAX-ACCESS read-only
                    STATUS current
                    DESCRIPTION "B"
                    ::= {  staIsdnSigManErrEntry 3 }

staIsdnSigManErrC OBJECT-TYPE
                    SYNTAX INTEGER (0..65535)
                    MAX-ACCESS read-only
                    STATUS current
                    DESCRIPTION "C"
                    ::= {  staIsdnSigManErrEntry 4 }

staIsdnSigManErrD OBJECT-TYPE
                    SYNTAX INTEGER (0..65535)
                    MAX-ACCESS read-only
                    STATUS current
                    DESCRIPTION "D"
                    ::= {  staIsdnSigManErrEntry 5 }

staIsdnSigManErrE OBJECT-TYPE
                    SYNTAX INTEGER (0..65535)
                    MAX-ACCESS read-only
                    STATUS current
                    DESCRIPTION "E"
                    ::= {  staIsdnSigManErrEntry 6 }

staIsdnSigManErrF OBJECT-TYPE
                    SYNTAX INTEGER (0..65535)
                    MAX-ACCESS read-only
                    STATUS current
                    DESCRIPTION "F"
                    ::= {  staIsdnSigManErrEntry 7 }

staIsdnSigManErrG OBJECT-TYPE
                    SYNTAX INTEGER (0..65535)
                    MAX-ACCESS read-only
                    STATUS current
                    DESCRIPTION "G"
                    ::= {  staIsdnSigManErrEntry 8 }

staIsdnSigManErrH OBJECT-TYPE
                    SYNTAX INTEGER (0..65535)
                    MAX-ACCESS read-only
                    STATUS current
                    DESCRIPTION "H"
                    ::= {  staIsdnSigManErrEntry 9 }

staIsdnSigManErrI OBJECT-TYPE
                    SYNTAX INTEGER (0..65535)
                    MAX-ACCESS read-only
                    STATUS current
                    DESCRIPTION "I"
                    ::= {  staIsdnSigManErrEntry 10 }

staIsdnSigManErrJ OBJECT-TYPE
                    SYNTAX INTEGER (0..65535)
                    MAX-ACCESS read-only
                    STATUS current
                    DESCRIPTION "J"
                    ::= {  staIsdnSigManErrEntry 11 }

staIsdnSigManErrK OBJECT-TYPE
                    SYNTAX INTEGER (0..65535)
                    MAX-ACCESS read-only
                    STATUS current
                    DESCRIPTION "K"
                    ::= {  staIsdnSigManErrEntry 12 }

staIsdnSigManErrL OBJECT-TYPE
                    SYNTAX INTEGER (0..65535)
                    MAX-ACCESS read-only
                    STATUS current
                    DESCRIPTION "L"
                    ::= {  staIsdnSigManErrEntry 13 }

staIsdnSigManErrM OBJECT-TYPE
                    SYNTAX INTEGER (0..65535)
                    MAX-ACCESS read-only
                    STATUS current
                    DESCRIPTION "M"
                    ::= {  staIsdnSigManErrEntry 14 }

staIsdnSigManErrN OBJECT-TYPE
                    SYNTAX INTEGER (0..65535)
                    MAX-ACCESS read-only
                    STATUS current
                    DESCRIPTION "N"
                    ::= {  staIsdnSigManErrEntry 15 }

staIsdnSigManErrO OBJECT-TYPE
                    SYNTAX INTEGER (0..65535)
                    MAX-ACCESS read-only
                    STATUS current
                    DESCRIPTION "O"
                    ::= {  staIsdnSigManErrEntry 16 }

staIsdnDel OBJECT-TYPE
           SYNTAX DisplayString
           MAX-ACCESS read-write
           STATUS current
           DESCRIPTION "Delete-Values"
           ::= {  staIsdn 99 }

staSnmp OBJECT IDENTIFIER ::= { sta 35}
staSnmpEveTable OBJECT-TYPE
                SYNTAX SEQUENCE OF StaSnmpEveEntry
                MAX-ACCESS not-accessible
                STATUS current
                DESCRIPTION "Event"
                ::= {  staSnmp 1 }

staSnmpEveEntry OBJECT-TYPE
                SYNTAX StaSnmpEveEntry
                MAX-ACCESS not-accessible
                STATUS current
                DESCRIPTION "entry in table"
                INDEX { staSnmpEveTra, staSnmpEveVen }
                ::= {  staSnmpEveTable 1 }

StaSnmpEveEntry ::= SEQUENCE {
                staSnmpEveTra INTEGER,
                staSnmpEveVen INTEGER,
                staSnmpEveCou INTEGER
               }

staSnmpEveTra OBJECT-TYPE
              SYNTAX INTEGER
              {
                coldstart(255),
                warmstart(1),
                linkdown(2),
                linkup(3),
                authfail(4),
                epgnloss(5),
                enterprise(6)
              }
              MAX-ACCESS read-only
              STATUS current
              DESCRIPTION "Trap-Name"
              ::= {  staSnmpEveEntry 1 }

staSnmpEveVen OBJECT-TYPE
              SYNTAX INTEGER
              {
                fwuplstart(4),
                uplsucc(5),
                uplfailto(6),
                uplfailincl(7),
                uplfailbaddev(8),
                login(9),
                logout(10),
                cnfuplstart(11),
                cnfdnlstart(12),
                cnfdnlsucc(13),
                errlogin(29),
                pptpconn(28),
                pppoesconn(39),
                vpnconn(27),
                http-tunnel-open(2000),
                http-tunnel-close(2001),
                ipfwflt(26),
                ldblconn(38),
                vrrp(41),
                lan-overtemp-throttle(5002),
                lan-overtemp-throttle-end(5003),
                lan-overtemp-throttle-recommend(5004),
                statchan(1)
              }
              MAX-ACCESS read-only
              STATUS current
              DESCRIPTION "Vendor-Name"
              ::= {  staSnmpEveEntry 2 }

staSnmpEveCou OBJECT-TYPE
              SYNTAX INTEGER (0..2147483647)
              MAX-ACCESS read-only
              STATUS current
              DESCRIPTION "Count"
              ::= {  staSnmpEveEntry 3 }

staMail OBJECT IDENTIFIER ::= { sta 43}
staMailBuf OBJECT-TYPE
           SYNTAX INTEGER
           MAX-ACCESS read-only
           STATUS current
           DESCRIPTION "Buffered-Mails"
           ::= {  staMail 1 }

staMailSen OBJECT-TYPE
           SYNTAX Counter32
           MAX-ACCESS read-only
           STATUS current
           DESCRIPTION "Sent-Mails"
           ::= {  staMail 2 }

staMailDis OBJECT-TYPE
           SYNTAX Counter32
           MAX-ACCESS read-only
           STATUS current
           DESCRIPTION "Discarded-Mails"
           ::= {  staMail 3 }

staMailCle OBJECT-TYPE
           SYNTAX DisplayString
           MAX-ACCESS read-write
           STATUS current
           DESCRIPTION "Clear-Buffer"
           ::= {  staMail 4 }

staMailDel OBJECT-TYPE
           SYNTAX DisplayString
           MAX-ACCESS read-write
           STATUS current
           DESCRIPTION "Delete-Statistics"
           ::= {  staMail 5 }

staHard OBJECT IDENTIFIER ::= { sta 47}
staHardMode OBJECT-TYPE
            SYNTAX DisplayString (SIZE(0..64))
            MAX-ACCESS read-only
            STATUS current
            DESCRIPTION "Model-Number"
            ::= {  staHard 6 }

staHardSeri OBJECT-TYPE
            SYNTAX DisplayString (SIZE(0..12))
            MAX-ACCESS read-only
            STATUS current
            DESCRIPTION "Serial-Number"
            ::= {  staHard 7 }

staHardBoar OBJECT-TYPE
            SYNTAX DisplayString (SIZE(0..1))
            MAX-ACCESS read-only
            STATUS current
            DESCRIPTION "Board-Revision"
            ::= {  staHard 8 }

staHardCput OBJECT-TYPE
            SYNTAX DisplayString (SIZE(0..39))
            MAX-ACCESS read-only
            STATUS current
            DESCRIPTION "CPU-Type"
            ::= {  staHard 1 }

staHardCpuc OBJECT-TYPE
            SYNTAX INTEGER
            MAX-ACCESS read-only
            STATUS current
            DESCRIPTION "CPU-Clock-MHz"
            ::= {  staHard 2 }

staHardCpul OBJECT-TYPE
            SYNTAX INTEGER
            MAX-ACCESS read-only
            STATUS current
            DESCRIPTION "CPU-Load-Percent"
            ::= {  staHard 3 }

staHardTota OBJECT-TYPE
            SYNTAX INTEGER
            MAX-ACCESS read-only
            STATUS current
            DESCRIPTION "Total-Memory-KBytes"
            ::= {  staHard 4 }

staHardFree OBJECT-TYPE
            SYNTAX INTEGER
            MAX-ACCESS read-only
            STATUS current
            DESCRIPTION "Free-Memory-KBytes"
            ::= {  staHard 5 }

staHardVpnh OBJECT-TYPE
            SYNTAX INTEGER
            {
              no(0),
              yes(1)
            }
            MAX-ACCESS read-only
            STATUS current
            DESCRIPTION "VPN-HW-Accelerator"
            ::= {  staHard 11 }

staHardSwve OBJECT-TYPE
            SYNTAX DisplayString (SIZE(0..39))
            MAX-ACCESS read-only
            STATUS current
            DESCRIPTION "SW-Version"
            ::= {  staHard 9 }

staHardEthe OBJECT-TYPE
            SYNTAX DisplayString (SIZE(0..40))
            MAX-ACCESS read-only
            STATUS current
            DESCRIPTION "Ethernet-Switch-Type"
            ::= {  staHard 10 }

staChanTable OBJECT-TYPE
             SYNTAX SEQUENCE OF StaChanEntry
             MAX-ACCESS not-accessible
             STATUS current
             DESCRIPTION "Channel"
             ::= {  sta 48 }

staChanEntry OBJECT-TYPE
             SYNTAX StaChanEntry
             MAX-ACCESS not-accessible
             STATUS current
             DESCRIPTION "entry in table"
             INDEX { staChanChan }
             ::= {  staChanTable 1 }

StaChanEntry ::= SEQUENCE {
             staChanChan INTEGER,
             staChanPhcha INTEGER,
             staChanPlci INTEGER,
             staChanBus INTEGER,
             staChanState INTEGER,
             staChanApp INTEGER,
             staChanMode INTEGER,
             staChanCause INTEGER,
             staChanNumbe DisplayString,
             staChanSubad INTEGER,
             staChanCharg INTEGER,
             staChanConns INTEGER,
             staChanConnt INTEGER,
             staChanExtra DisplayString,
             staChanIsdnd DisplayString,
             staChanPptpc INTEGER,
             staChanVpnco INTEGER
            }

staChanChan OBJECT-TYPE
             SYNTAX INTEGER
             {
               dsl-err(1),
               dsl-ch-1(2),
               dsl-ch-2(3),
               dsl-ch-3(4),
               dsl-ch-4(5),
               dsl-ch-5(6),
               dsl-ch-6(7),
               dsl-ch-7(8),
               dsl-ch-8(9),
               s0-1-err(10),
               s0-1-b1(11),
               s0-1-b2(12),
               ext-err(13),
               ext(14)
             }
             MAX-ACCESS read-only
             STATUS current
             DESCRIPTION "Chan."
             ::= {  staChanEntry 1 }

staChanPhcha OBJECT-TYPE
             SYNTAX INTEGER (0..2147483647)
             MAX-ACCESS read-only
             STATUS current
             DESCRIPTION "Ph.-Chan."
             ::= {  staChanEntry 15 }

staChanPlci OBJECT-TYPE
             SYNTAX INTEGER (0..2147483647)
             MAX-ACCESS read-only
             STATUS current
             DESCRIPTION "PLCI"
             ::= {  staChanEntry 2 }

staChanBus OBJECT-TYPE
             SYNTAX INTEGER (0..2147483647)
             MAX-ACCESS read-only
             STATUS current
             DESCRIPTION "Bus"
             ::= {  staChanEntry 3 }

staChanState OBJECT-TYPE
             SYNTAX INTEGER (0..2147483647)
             MAX-ACCESS read-only
             STATUS current
             DESCRIPTION "State"
             ::= {  staChanEntry 4 }

staChanApp OBJECT-TYPE
             SYNTAX INTEGER
             {
               none(0),
               router(1),
               capi(2),
               a-b(3),
               time-module(255)
             }
             MAX-ACCESS read-only
             STATUS current
             DESCRIPTION "App"
             ::= {  staChanEntry 5 }

staChanMode OBJECT-TYPE
             SYNTAX INTEGER
             {
               unk(0),
               act(1),
               pas(2),
               perm(3)
             }
             MAX-ACCESS read-only
             STATUS current
             DESCRIPTION "Mode"
             ::= {  staChanEntry 6 }

staChanCause OBJECT-TYPE
             SYNTAX INTEGER (0..65535)
             MAX-ACCESS read-write
             STATUS current
             DESCRIPTION "Cause"
             ::= {  staChanEntry 7 }

staChanNumbe OBJECT-TYPE
             SYNTAX DisplayString (SIZE(0..40))
             MAX-ACCESS read-only
             STATUS current
             DESCRIPTION "Number"
             ::= {  staChanEntry 8 }

staChanSubad OBJECT-TYPE
             SYNTAX INTEGER (0..2147483647)
             MAX-ACCESS read-only
             STATUS current
             DESCRIPTION "Subaddress"
             ::= {  staChanEntry 9 }

staChanCharg OBJECT-TYPE
             SYNTAX INTEGER (0..2147483647)
             MAX-ACCESS read-only
             STATUS current
             DESCRIPTION "Charge"
             ::= {  staChanEntry 10 }

staChanConns OBJECT-TYPE
             SYNTAX INTEGER (0..2147483647)
             MAX-ACCESS read-only
             STATUS current
             DESCRIPTION "Conn.-start"
             ::= {  staChanEntry 13 }

staChanConnt OBJECT-TYPE
             SYNTAX INTEGER (0..2147483647)
             MAX-ACCESS read-only
             STATUS current
             DESCRIPTION "Conn.-time"
             ::= {  staChanEntry 12 }

staChanExtra OBJECT-TYPE
             SYNTAX DisplayString (SIZE(0..16))
             MAX-ACCESS read-only
             STATUS current
             DESCRIPTION "Extra"
             ::= {  staChanEntry 11 }

staChanIsdnd OBJECT-TYPE
             SYNTAX DisplayString (SIZE(0..34))
             MAX-ACCESS read-only
             STATUS current
             DESCRIPTION "ISDN-display"
             ::= {  staChanEntry 14 }

staChanPptpc OBJECT-TYPE
             SYNTAX INTEGER (0..2147483647)
             MAX-ACCESS read-only
             STATUS current
             DESCRIPTION "PPTP-Conns."
             ::= {  staChanEntry 16 }

staChanVpnco OBJECT-TYPE
             SYNTAX INTEGER (0..2147483647)
             MAX-ACCESS read-only
             STATUS current
             DESCRIPTION "VPN-Conns."
             ::= {  staChanEntry 17 }

staMode OBJECT IDENTIFIER ::= { sta 49}
staModeOperating OBJECT-TYPE
                      SYNTAX INTEGER
                      {
                        no(0),
                        modem(1),
                        umts-gprs(2)
                      }
                      MAX-ACCESS read-only
                      STATUS current
                      DESCRIPTION "Operating"
                      ::= {  staMode 4 }

staModeModeminfo OBJECT-TYPE
                      SYNTAX DisplayString (SIZE(0..255))
                      MAX-ACCESS read-only
                      STATUS current
                      DESCRIPTION "Modem-Info"
                      ::= {  staMode 1 }

staModeConnectinfo OBJECT-TYPE
                      SYNTAX DisplayString (SIZE(0..63))
                      MAX-ACCESS read-only
                      STATUS current
                      DESCRIPTION "Connect-Info"
                      ::= {  staMode 2 }

staModeState OBJECT-TYPE
                      SYNTAX INTEGER
                      {
                        wait-for-device(15),
                        deactivated(0),
                        device-detection(1),
                        reset(2),
                        initializing(3),
                        modem-id(4),
                        ready(5),
                        connecting(6),
                        pass-connecting(7),
                        data-mode(8),
                        network-scan(9),
                        set-pin(10),
                        pin-invalid(11),
                        unexpected-response(12),
                        puk-required(13),
                        network(14)
                      }
                      MAX-ACCESS read-only
                      STATUS current
                      DESCRIPTION "State"
                      ::= {  staMode 3 }

staModeDatarate OBJECT-TYPE
                      SYNTAX INTEGER
                      MAX-ACCESS read-only
                      STATUS current
                      DESCRIPTION "Data-Rate"
                      ::= {  staMode 5 }

staModeSignaldbm OBJECT-TYPE
                      SYNTAX INTEGER
                      MAX-ACCESS read-only
                      STATUS current
                      DESCRIPTION "Signal[dBm]"
                      ::= {  staMode 6 }

staModeRegistration OBJECT-TYPE
                      SYNTAX INTEGER
                      {
                        no-network(0),
                        home-network(1),
                        searching(2),
                        denied(3),
                        unknown(4),
                        roaming(5)
                      }
                      MAX-ACCESS read-only
                      STATUS current
                      DESCRIPTION "Registration"
                      ::= {  staMode 7 }

staModeNetwork OBJECT-TYPE
                      SYNTAX DisplayString (SIZE(0..16))
                      MAX-ACCESS read-only
                      STATUS current
                      DESCRIPTION "Network"
                      ::= {  staMode 8 }

staModeMode OBJECT-TYPE
                      SYNTAX INTEGER
                      {
                        unknown(0),
                        umts(1),
                        gprs(2),
                        gsm(3),
                        edge(4),
                        hsdpa(5),
                        hsupa(6)
                      }
                      MAX-ACCESS read-only
                      STATUS current
                      DESCRIPTION "Mode"
                      ::= {  staMode 12 }

staModePort OBJECT-TYPE
                      SYNTAX INTEGER
                      {
                        none(0),
                        outband(1),
                        usb(2)
                      }
                      MAX-ACCESS read-only
                      STATUS current
                      DESCRIPTION "Port"
                      ::= {  staMode 13 }

staModePinstatus OBJECT-TYPE
                      SYNTAX DisplayString (SIZE(0..47))
                      MAX-ACCESS read-only
                      STATUS current
                      DESCRIPTION "PIN-Status"
                      ::= {  staMode 21 }

staModeHardwareresets OBJECT-TYPE
                      SYNTAX INTEGER
                      MAX-ACCESS read-only
                      STATUS current
                      DESCRIPTION "Hardware-Resets"
                      ::= {  staMode 15 }

staModeTemperaturesta OBJECT-TYPE
                      SYNTAX INTEGER
                      {
                        unknown(0),
                        normal(1),
                        low(2),
                        high(3),
                        low-critical(5),
                        high-critical(6)
                      }
                      MAX-ACCESS read-only
                      STATUS current
                      DESCRIPTION "Temperature_status"
                      ::= {  staMode 17 }

staModeTemperaturedeg OBJECT-TYPE
                      SYNTAX INTEGER
                      MAX-ACCESS read-only
                      STATUS current
                      DESCRIPTION "Temperature[degC]"
                      ::= {  staMode 18 }

staModeSupplyvoltages OBJECT-TYPE
                      SYNTAX INTEGER
                      {
                        unknown(0),
                        normal(1),
                        low(2),
                        high(3),
                        low-critical(5),
                        high-critical(6)
                      }
                      MAX-ACCESS read-only
                      STATUS current
                      DESCRIPTION "Supply_voltage_status"
                      ::= {  staMode 19 }

staModeSupplyvoltagem OBJECT-TYPE
                      SYNTAX INTEGER
                      MAX-ACCESS read-only
                      STATUS current
                      DESCRIPTION "Supply_voltage[mV]"
                      ::= {  staMode 20 }

staModeSimidiccid OBJECT-TYPE
                      SYNTAX DisplayString (SIZE(0..22))
                      MAX-ACCESS read-only
                      STATUS current
                      DESCRIPTION "SIM-ID(ICCID)"
                      ::= {  staMode 23 }

staModeNetworklistTable OBJECT-TYPE
                           SYNTAX SEQUENCE OF StaModeNetworklistEntry
                           MAX-ACCESS not-accessible
                           STATUS current
                           DESCRIPTION "Network-List"
                           ::= {  staMode 9 }

staModeNetworklistEntry OBJECT-TYPE
                           SYNTAX StaModeNetworklistEntry
                           MAX-ACCESS not-accessible
                           STATUS current
                           DESCRIPTION "entry in table"
                           INDEX { staModeNetworklistNet }
                           ::= {  staModeNetworklistTable 1 }

StaModeNetworklistEntry ::= SEQUENCE {
                           staModeNetworklistNet DisplayString,
                           staModeNetworklistNum INTEGER,
                           staModeNetworklistSta INTEGER,
                           staModeNetworklistMod BITS
                          }

staModeNetworklistNet OBJECT-TYPE
                      SYNTAX DisplayString (SIZE(0..16))
                      MAX-ACCESS read-only
                      STATUS current
                      DESCRIPTION "Network"
                      ::= {  staModeNetworklistEntry 1 }

staModeNetworklistNum OBJECT-TYPE
                      SYNTAX INTEGER (0..2147483647)
                      MAX-ACCESS read-only
                      STATUS current
                      DESCRIPTION "Numeric"
                      ::= {  staModeNetworklistEntry 4 }

staModeNetworklistSta OBJECT-TYPE
                      SYNTAX INTEGER
                      {
                        unknown(1),
                        available(2),
                        current(3),
                        forbidden(4)
                      }
                      MAX-ACCESS read-only
                      STATUS current
                      DESCRIPTION "State"
                      ::= {  staModeNetworklistEntry 2 }

staModeNetworklistMod OBJECT-TYPE
                      SYNTAX BITS
                      {
                        gprs(31),
                        umts(30)
                      }
                      MAX-ACCESS read-only
                      STATUS current
                      DESCRIPTION "Mode"
                      ::= {  staModeNetworklistEntry 3 }

staModeHistoryTable OBJECT-TYPE
                           SYNTAX SEQUENCE OF StaModeHistoryEntry
                           MAX-ACCESS not-accessible
                           STATUS current
                           DESCRIPTION "History"
                           ::= {  staMode 16 }

staModeHistoryEntry OBJECT-TYPE
                           SYNTAX StaModeHistoryEntry
                           MAX-ACCESS not-accessible
                           STATUS current
                           DESCRIPTION "entry in table"
                           INDEX { staModeHistoryInd }
                           ::= {  staModeHistoryTable 1 }

StaModeHistoryEntry ::= SEQUENCE {
                           staModeHistoryInd INTEGER,
                           staModeHistoryTim INTEGER,
                           staModeHistorySig INTEGER,
                           staModeHistoryNet DisplayString,
                           staModeHistoryMod INTEGER,
                           staModeHistoryReg INTEGER
                          }

staModeHistoryInd OBJECT-TYPE
                  SYNTAX INTEGER (0..2147483647)
                  MAX-ACCESS read-only
                  STATUS current
                  DESCRIPTION "Index"
                  ::= {  staModeHistoryEntry 1 }

staModeHistoryTim OBJECT-TYPE
                  SYNTAX INTEGER (0..2147483647)
                  MAX-ACCESS read-only
                  STATUS current
                  DESCRIPTION "Timestamp"
                  ::= {  staModeHistoryEntry 2 }

staModeHistorySig OBJECT-TYPE
                  SYNTAX INTEGER (-2147483648..2147483647)
                  MAX-ACCESS read-only
                  STATUS current
                  DESCRIPTION "Signal[dBm]"
                  ::= {  staModeHistoryEntry 3 }

staModeHistoryNet OBJECT-TYPE
                  SYNTAX DisplayString (SIZE(0..1))
                  MAX-ACCESS read-only
                  STATUS current
                  DESCRIPTION "Network"
                  ::= {  staModeHistoryEntry 4 }

staModeHistoryMod OBJECT-TYPE
                  SYNTAX INTEGER
                  {
                    unknown(0),
                    umts(1),
                    gprs(2),
                    gsm(3),
                    edge(4),
                    hsdpa(5),
                    hsupa(6)
                  }
                  MAX-ACCESS read-only
                  STATUS current
                  DESCRIPTION "Mode"
                  ::= {  staModeHistoryEntry 5 }

staModeHistoryReg OBJECT-TYPE
                  SYNTAX INTEGER
                  {
                    no-network(0),
                    home-network(1),
                    searching(2),
                    denied(3),
                    unknown(4),
                    roaming(5)
                  }
                  MAX-ACCESS read-only
                  STATUS current
                  DESCRIPTION "Registration"
                  ::= {  staModeHistoryEntry 6 }

staModeScannetworks OBJECT-TYPE
                      SYNTAX DisplayString
                      MAX-ACCESS read-write
                      STATUS current
                      DESCRIPTION "Scan-Networks"
                      ::= {  staMode 10 }

staModeInputpuk OBJECT-TYPE
                      SYNTAX DisplayString
                      MAX-ACCESS read-write
                      STATUS current
                      DESCRIPTION "Input-PUK"
                      ::= {  staMode 11 }

staModeDroppedtxpacke OBJECT-TYPE
                      SYNTAX INTEGER
                      MAX-ACCESS read-only
                      STATUS current
                      DESCRIPTION "Dropped-Tx-packets"
                      ::= {  staMode 14 }

staModeRxtimeouts OBJECT-TYPE
                      SYNTAX INTEGER
                      MAX-ACCESS read-only
                      STATUS current
                      DESCRIPTION "Rx-Timeouts"
                      ::= {  staMode 22 }

staFile OBJECT IDENTIFIER ::= { sta 50}
staFileConTable OBJECT-TYPE
                SYNTAX SEQUENCE OF StaFileConEntry
                MAX-ACCESS not-accessible
                STATUS current
                DESCRIPTION "Contents"
                ::= {  staFile 1 }

staFileConEntry OBJECT-TYPE
                SYNTAX StaFileConEntry
                MAX-ACCESS not-accessible
                STATUS current
                DESCRIPTION "entry in table"
                INDEX { staFileConNam }
                ::= {  staFileConTable 1 }

StaFileConEntry ::= SEQUENCE {
                staFileConNam DisplayString,
                staFileConSiz INTEGER
               }

staFileConNam OBJECT-TYPE
              SYNTAX DisplayString (SIZE(0..255))
              MAX-ACCESS read-only
              STATUS current
              DESCRIPTION "Name"
              ::= {  staFileConEntry 1 }

staFileConSiz OBJECT-TYPE
              SYNTAX INTEGER (0..2147483647)
              MAX-ACCESS read-only
              STATUS current
              DESCRIPTION "Size"
              ::= {  staFileConEntry 2 }

staEthe OBJECT IDENTIFIER ::= { sta 51}
staEthePortsTable OBJECT-TYPE
                       SYNTAX SEQUENCE OF StaEthePortsEntry
                       MAX-ACCESS not-accessible
                       STATUS current
                       DESCRIPTION "Ports"
                       ::= {  staEthe 1 }

staEthePortsEntry OBJECT-TYPE
                       SYNTAX StaEthePortsEntry
                       MAX-ACCESS not-accessible
                       STATUS current
                       DESCRIPTION "entry in table"
                       INDEX { staEthePortsPor }
                       ::= {  staEthePortsTable 1 }

StaEthePortsEntry ::= SEQUENCE {
                       staEthePortsPor INTEGER,
                       staEthePortsAss INTEGER,
                       staEthePortsPri INTEGER,
                       staEthePortsLin INTEGER,
                       staEthePortsCon INTEGER,
                       staEthePortsAut INTEGER,
                       staEthePortsFlo INTEGER,
                       staEthePortsMdi INTEGER
                      }

staEthePortsPor OBJECT-TYPE
                SYNTAX INTEGER
                {
                  wan(1),
                  eth-1(2),
                  eth-2(3),
                  eth-3(4),
                  eth-4(5),
                  unknown(0)
                }
                MAX-ACCESS read-only
                STATUS current
                DESCRIPTION "Port"
                ::= {  staEthePortsEntry 1 }

staEthePortsAss OBJECT-TYPE
                SYNTAX INTEGER
                {
                  dsl-1(512),
                  dsl-2(513),
                  dsl-3(514),
                  dsl-4(515),
                  lan-1(0),
                  lan-2(1),
                  lan-3(2),
                  lan-4(3),
                  idle(65533),
                  monitor(65534),
                  power-down(65535)
                }
                MAX-ACCESS read-only
                STATUS current
                DESCRIPTION "Assignment"
                ::= {  staEthePortsEntry 7 }

staEthePortsPri OBJECT-TYPE
                SYNTAX INTEGER
                {
                  no(0),
                  yes(1)
                }
                MAX-ACCESS read-only
                STATUS current
                DESCRIPTION "Private-Mode"
                ::= {  staEthePortsEntry 9 }

staEthePortsLin OBJECT-TYPE
                SYNTAX INTEGER
                {
                  no(0),
                  yes(1)
                }
                MAX-ACCESS read-only
                STATUS current
                DESCRIPTION "Link-Active"
                ::= {  staEthePortsEntry 3 }

staEthePortsCon OBJECT-TYPE
                SYNTAX INTEGER
                {
                  none(0),
                  e10b-t(1),
                  fd10b-tx(2),
                  e100b-tx(3),
                  fd100b-tx(4)
                }
                MAX-ACCESS read-only
                STATUS current
                DESCRIPTION "Connector"
                ::= {  staEthePortsEntry 4 }

staEthePortsAut OBJECT-TYPE
                SYNTAX INTEGER
                {
                  pending(0),
                  completed(1),
                  disabled(2),
                  not-available(3)
                }
                MAX-ACCESS read-only
                STATUS current
                DESCRIPTION "Auto-Negotiation"
                ::= {  staEthePortsEntry 10 }

staEthePortsFlo OBJECT-TYPE
                SYNTAX INTEGER
                {
                  no(0),
                  yes(1)
                }
                MAX-ACCESS read-only
                STATUS current
                DESCRIPTION "Flow-Control"
                ::= {  staEthePortsEntry 8 }

staEthePortsMdi OBJECT-TYPE
                SYNTAX INTEGER
                {
                  mdi(0),
                  mdix(1)
                }
                MAX-ACCESS read-only
                STATUS current
                DESCRIPTION "MDI-Mode"
                ::= {  staEthePortsEntry 6 }

staEtheCabletest OBJECT-TYPE
                  SYNTAX DisplayString
                  MAX-ACCESS read-write
                  STATUS current
                  DESCRIPTION "Cable-Test"
                  ::= {  staEthe 2 }

staEtheCabletestrTable OBJECT-TYPE
                       SYNTAX SEQUENCE OF StaEtheCabletestrEntry
                       MAX-ACCESS not-accessible
                       STATUS current
                       DESCRIPTION "Cable-Test-Results"
                       ::= {  staEthe 3 }

staEtheCabletestrEntry OBJECT-TYPE
                       SYNTAX StaEtheCabletestrEntry
                       MAX-ACCESS not-accessible
                       STATUS current
                       DESCRIPTION "entry in table"
                       INDEX { staEtheCabletestrIfc }
                       ::= {  staEtheCabletestrTable 1 }

StaEtheCabletestrEntry ::= SEQUENCE {
                       staEtheCabletestrIfc INTEGER,
                       staEtheCabletestrTxs INTEGER,
                       staEtheCabletestrTxd DisplayString,
                       staEtheCabletestrRxs INTEGER,
                       staEtheCabletestrRxd DisplayString
                      }

staEtheCabletestrIfc OBJECT-TYPE
                     SYNTAX INTEGER
                     {
                       wan(1),
                       eth-1(2),
                       eth-2(3),
                       eth-3(4),
                       eth-4(5),
                       unknown(0)
                     }
                     MAX-ACCESS read-only
                     STATUS current
                     DESCRIPTION "Ifc"
                     ::= {  staEtheCabletestrEntry 1 }

staEtheCabletestrTxs OBJECT-TYPE
                     SYNTAX INTEGER
                     {
                       unknown(0),
                       ok(1),
                       open(2),
                       short(3),
                       impedance-fault(4),
                       fail(5),
                       busy(6)
                     }
                     MAX-ACCESS read-only
                     STATUS current
                     DESCRIPTION "Tx-Status"
                     ::= {  staEtheCabletestrEntry 4 }

staEtheCabletestrTxd OBJECT-TYPE
                     SYNTAX DisplayString (SIZE(0..10))
                     MAX-ACCESS read-only
                     STATUS current
                     DESCRIPTION "Tx-Distance"
                     ::= {  staEtheCabletestrEntry 5 }

staEtheCabletestrRxs OBJECT-TYPE
                     SYNTAX INTEGER
                     {
                       unknown(0),
                       ok(1),
                       open(2),
                       short(3),
                       impedance-fault(4),
                       fail(5),
                       busy(6)
                     }
                     MAX-ACCESS read-only
                     STATUS current
                     DESCRIPTION "Rx-Status"
                     ::= {  staEtheCabletestrEntry 2 }

staEtheCabletestrRxd OBJECT-TYPE
                     SYNTAX DisplayString (SIZE(0..10))
                     MAX-ACCESS read-only
                     STATUS current
                     DESCRIPTION "Rx-Distance"
                     ::= {  staEtheCabletestrEntry 3 }

staPppo OBJECT IDENTIFIER ::= { sta 52}
staPppoRxp OBJECT-TYPE
           SYNTAX Counter32
           MAX-ACCESS read-only
           STATUS current
           DESCRIPTION "Rx-Packets"
           ::= {  staPppo 1 }

staPppoTxp OBJECT-TYPE
           SYNTAX Counter32
           MAX-ACCESS read-only
           STATUS current
           DESCRIPTION "Tx-Packets"
           ::= {  staPppo 2 }

staPppoDro OBJECT-TYPE
           SYNTAX Counter32
           MAX-ACCESS read-only
           STATUS current
           DESCRIPTION "Dropped-Packets"
           ::= {  staPppo 5 }

staPppoRxe OBJECT-TYPE
           SYNTAX Counter32
           MAX-ACCESS read-only
           STATUS current
           DESCRIPTION "Rx-Errors"
           ::= {  staPppo 6 }

staPppoSes OBJECT-TYPE
           SYNTAX Counter32
           MAX-ACCESS read-only
           STATUS current
           DESCRIPTION "Session-Errors"
           ::= {  staPppo 8 }

staPppoConTable OBJECT-TYPE
                SYNTAX SEQUENCE OF StaPppoConEntry
                MAX-ACCESS not-accessible
                STATUS current
                DESCRIPTION "Connections"
                ::= {  staPppo 9 }

staPppoConEntry OBJECT-TYPE
                SYNTAX StaPppoConEntry
                MAX-ACCESS not-accessible
                STATUS current
                DESCRIPTION "entry in table"
                INDEX { staPppoConCha, staPppoConMac }
                ::= {  staPppoConTable 1 }

StaPppoConEntry ::= SEQUENCE {
                staPppoConCha DisplayString,
                staPppoConMac DisplayString,
                staPppoConSta INTEGER,
                staPppoConLas INTEGER,
                staPppoConSht INTEGER,
                staPppoConPee IpAddress,
                staPppoConCon INTEGER
               }

staPppoConCha OBJECT-TYPE
              SYNTAX DisplayString (SIZE(0..16))
              MAX-ACCESS read-only
              STATUS current
              DESCRIPTION "Channel"
              ::= {  staPppoConEntry 1 }

staPppoConMac OBJECT-TYPE
              SYNTAX DisplayString (SIZE(0..12))
              MAX-ACCESS read-only
              STATUS current
              DESCRIPTION "MAC-Address"
              ::= {  staPppoConEntry 2 }

staPppoConSta OBJECT-TYPE
              SYNTAX INTEGER
              {
                init(0),
                setup-wan(1),
                ready(2),
                wait-for-cb(3),
                dial(4),
                incoming-call(5),
                protocol(6),
                connection(7),
                disconnecting(8),
                call-back(9),
                bundle-connect(10),
                protocol-2(11),
                reserved(12),
                bundle(13)
              }
              MAX-ACCESS read-only
              STATUS current
              DESCRIPTION "State"
              ::= {  staPppoConEntry 3 }

staPppoConLas OBJECT-TYPE
              SYNTAX INTEGER
              {
                none(0),
                remote-disconnected(17153),
                manual-disconnect(17154),
                shorthold-expired(17155),
                physical-disconnected(17156),
                invalid-physical-channel(17157),
                dynamic-vpn-reconnect(17158),
                configuration-changed(17159),
                removed-from-config(17160),
                remote-doubled(267),
                icmp-conn-error(275),
                dhcp-timeout(277),
                pptp-no-response(278),
                vpn-no-response(279),
                arp-no-response(280),
                pptp-no-channel(513),
                pptp-bad-format(514),
                pptp-bad-value(515),
                pptp-no-ressource(516),
                pptp-bad-call-id(517),
                pptp-gen-error(518),
                lcp-rejected(32768),
                auth-error(32769),
                auth-rejected(32770),
                lcp-conn-error(32771),
                pap-rejected(32784),
                pap-rx-timeout(32785),
                pap-tx-timeout(32786),
                wrong-pap-req(32787),
                pap-nak-received(32788),
                unkn-pap-peer(32789),
                chap-rejected(32800),
                chap-rx-timeout(32801),
                chap-tx-timeout(32802),
                wrong-chap-resp(32803),
                chap-fail-recvd(32804),
                unkn-chap-peer(32805),
                ipxcp-rejected(32816),
                wrong-ipxcp-net(32817),
                ipxcp-net-reject(32818),
                ipxcp-route-unkn(32819),
                ipcp-rejected(32832),
                ccp-rejected(32848),
                no-ncp-available(33008)
              }
              MAX-ACCESS read-write
              STATUS current
              DESCRIPTION "Last-Error"
              ::= {  staPppoConEntry 4 }

staPppoConSht OBJECT-TYPE
              SYNTAX INTEGER (0..65535)
              MAX-ACCESS read-only
              STATUS current
              DESCRIPTION "SH-Time"
              ::= {  staPppoConEntry 5 }

staPppoConPee OBJECT-TYPE
              SYNTAX IpAddress
              MAX-ACCESS read-only
              STATUS current
              DESCRIPTION "Peer-Address"
              ::= {  staPppoConEntry 6 }

staPppoConCon OBJECT-TYPE
              SYNTAX INTEGER (0..2147483647)
              MAX-ACCESS read-only
              STATUS current
              DESCRIPTION "Conn.-time"
              ::= {  staPppoConEntry 7 }

staPppoNum OBJECT-TYPE
           SYNTAX INTEGER
           MAX-ACCESS read-only
           STATUS current
           DESCRIPTION "Num.-Connections"
           ::= {  staPppo 10 }

staPppoDel OBJECT-TYPE
           SYNTAX DisplayString
           MAX-ACCESS read-write
           STATUS current
           DESCRIPTION "Delete-Values"
           ::= {  staPppo 11 }

staUsb OBJECT IDENTIFIER ::= { sta 54}
staUsbDevTable OBJECT-TYPE
               SYNTAX SEQUENCE OF StaUsbDevEntry
               MAX-ACCESS not-accessible
               STATUS current
               DESCRIPTION "Devices"
               ::= {  staUsb 1 }

staUsbDevEntry OBJECT-TYPE
               SYNTAX StaUsbDevEntry
               MAX-ACCESS not-accessible
               STATUS current
               DESCRIPTION "entry in table"
               INDEX { staUsbDevBus, staUsbDevAddress }
               ::= {  staUsbDevTable 1 }

StaUsbDevEntry ::= SEQUENCE {
               staUsbDevBus DisplayString,
               staUsbDevAddress INTEGER,
               staUsbDevVendor DisplayString,
               staUsbDevVendorid INTEGER,
               staUsbDevProduct DisplayString,
               staUsbDevProducti INTEGER,
               staUsbDevDepth INTEGER,
               staUsbDevSpeed INTEGER,
               staUsbDevInterfac INTEGER,
               staUsbDevPower INTEGER,
               staUsbDevDriver DisplayString,
               staUsbDevParent DisplayString
              }

staUsbDevBus OBJECT-TYPE
                  SYNTAX DisplayString (SIZE(0..255))
                  MAX-ACCESS read-only
                  STATUS current
                  DESCRIPTION "Bus"
                  ::= {  staUsbDevEntry 1 }

staUsbDevAddress OBJECT-TYPE
                  SYNTAX INTEGER (0..255)
                  MAX-ACCESS read-only
                  STATUS current
                  DESCRIPTION "Address"
                  ::= {  staUsbDevEntry 2 }

staUsbDevVendor OBJECT-TYPE
                  SYNTAX DisplayString (SIZE(0..255))
                  MAX-ACCESS read-only
                  STATUS current
                  DESCRIPTION "Vendor"
                  ::= {  staUsbDevEntry 3 }

staUsbDevVendorid OBJECT-TYPE
                  SYNTAX INTEGER (0..65535)
                  MAX-ACCESS read-only
                  STATUS current
                  DESCRIPTION "Vendor-ID"
                  ::= {  staUsbDevEntry 4 }

staUsbDevProduct OBJECT-TYPE
                  SYNTAX DisplayString (SIZE(0..255))
                  MAX-ACCESS read-only
                  STATUS current
                  DESCRIPTION "Product"
                  ::= {  staUsbDevEntry 5 }

staUsbDevProducti OBJECT-TYPE
                  SYNTAX INTEGER (0..65535)
                  MAX-ACCESS read-only
                  STATUS current
                  DESCRIPTION "Product-ID"
                  ::= {  staUsbDevEntry 6 }

staUsbDevDepth OBJECT-TYPE
                  SYNTAX INTEGER (0..255)
                  MAX-ACCESS read-only
                  STATUS current
                  DESCRIPTION "Depth"
                  ::= {  staUsbDevEntry 8 }

staUsbDevSpeed OBJECT-TYPE
                  SYNTAX INTEGER (0..255)
                  MAX-ACCESS read-only
                  STATUS current
                  DESCRIPTION "Speed"
                  ::= {  staUsbDevEntry 9 }

staUsbDevInterfac OBJECT-TYPE
                  SYNTAX INTEGER (0..255)
                  MAX-ACCESS read-only
                  STATUS current
                  DESCRIPTION "Interfaces"
                  ::= {  staUsbDevEntry 10 }

staUsbDevPower OBJECT-TYPE
                  SYNTAX INTEGER (0..2147483647)
                  MAX-ACCESS read-only
                  STATUS current
                  DESCRIPTION "Power"
                  ::= {  staUsbDevEntry 11 }

staUsbDevDriver OBJECT-TYPE
                  SYNTAX DisplayString (SIZE(0..255))
                  MAX-ACCESS read-only
                  STATUS current
                  DESCRIPTION "Driver"
                  ::= {  staUsbDevEntry 12 }

staUsbDevParent OBJECT-TYPE
                  SYNTAX DisplayString (SIZE(0..255))
                  MAX-ACCESS read-only
                  STATUS current
                  DESCRIPTION "Parent"
                  ::= {  staUsbDevEntry 13 }

staUsbRei OBJECT-TYPE
          SYNTAX DisplayString
          MAX-ACCESS read-write
          STATUS current
          DESCRIPTION "Reinit"
          ::= {  staUsb 2 }

staAcco OBJECT IDENTIFIER ::= { sta 56}
staAccoCurTable OBJECT-TYPE
                SYNTAX SEQUENCE OF StaAccoCurEntry
                MAX-ACCESS not-accessible
                STATUS current
                DESCRIPTION "Current-User"
                ::= {  staAcco 1 }

staAccoCurEntry OBJECT-TYPE
                SYNTAX StaAccoCurEntry
                MAX-ACCESS not-accessible
                STATUS current
                DESCRIPTION "entry in table"
                INDEX { staAccoCurUsern, staAccoCurMacad, staAccoCurPeer, staAccoCurConnt }
                ::= {  staAccoCurTable 1 }

StaAccoCurEntry ::= SEQUENCE {
                staAccoCurUsern DisplayString,
                staAccoCurMacad DisplayString,
                staAccoCurPeer DisplayString,
                staAccoCurConnt INTEGER,
                staAccoCurRxkby INTEGER,
                staAccoCurTxkby INTEGER,
                staAccoCurTotal INTEGER,
                staAccoCurConne INTEGER
               }

staAccoCurUsern OBJECT-TYPE
                SYNTAX DisplayString (SIZE(0..28))
                MAX-ACCESS read-only
                STATUS current
                DESCRIPTION "Username"
                ::= {  staAccoCurEntry 1 }

staAccoCurMacad OBJECT-TYPE
                SYNTAX DisplayString (SIZE(0..255))
                MAX-ACCESS read-only
                STATUS current
                DESCRIPTION "MAC-Address"
                ::= {  staAccoCurEntry 2 }

staAccoCurPeer OBJECT-TYPE
                SYNTAX DisplayString (SIZE(0..31))
                MAX-ACCESS read-only
                STATUS current
                DESCRIPTION "Peer"
                ::= {  staAccoCurEntry 3 }

staAccoCurConnt OBJECT-TYPE
                SYNTAX INTEGER
                {
                  unknown(0),
                  dial-up(1),
                  leased-line(2),
                  dsl-line(4),
                  vpn-conn(7),
                  pptp-conn(8)
                }
                MAX-ACCESS read-only
                STATUS current
                DESCRIPTION "Conn.-Type"
                ::= {  staAccoCurEntry 4 }

staAccoCurRxkby OBJECT-TYPE
                SYNTAX INTEGER (0..2147483647)
                MAX-ACCESS read-only
                STATUS current
                DESCRIPTION "Rx-KBytes"
                ::= {  staAccoCurEntry 5 }

staAccoCurTxkby OBJECT-TYPE
                SYNTAX INTEGER (0..2147483647)
                MAX-ACCESS read-only
                STATUS current
                DESCRIPTION "Tx-KBytes"
                ::= {  staAccoCurEntry 6 }

staAccoCurTotal OBJECT-TYPE
                SYNTAX INTEGER (0..2147483647)
                MAX-ACCESS read-only
                STATUS current
                DESCRIPTION "Total-Time"
                ::= {  staAccoCurEntry 8 }

staAccoCurConne OBJECT-TYPE
                SYNTAX INTEGER (0..2147483647)
                MAX-ACCESS read-only
                STATUS current
                DESCRIPTION "Connections"
                ::= {  staAccoCurEntry 9 }

staAccoAccTable OBJECT-TYPE
                SYNTAX SEQUENCE OF StaAccoAccEntry
                MAX-ACCESS not-accessible
                STATUS current
                DESCRIPTION "Accounting-List"
                ::= {  staAcco 2 }

staAccoAccEntry OBJECT-TYPE
                SYNTAX StaAccoAccEntry
                MAX-ACCESS not-accessible
                STATUS current
                DESCRIPTION "entry in table"
                INDEX { staAccoAccUsern, staAccoAccMacad, staAccoAccPeer, staAccoAccConnt }
                ::= {  staAccoAccTable 1 }

StaAccoAccEntry ::= SEQUENCE {
                staAccoAccUsern DisplayString,
                staAccoAccMacad DisplayString,
                staAccoAccPeer DisplayString,
                staAccoAccConnt INTEGER,
                staAccoAccRxkby INTEGER,
                staAccoAccTxkby INTEGER,
                staAccoAccTotal INTEGER,
                staAccoAccConne INTEGER
               }

staAccoAccUsern OBJECT-TYPE
                SYNTAX DisplayString (SIZE(0..28))
                MAX-ACCESS read-only
                STATUS current
                DESCRIPTION "Username"
                ::= {  staAccoAccEntry 1 }

staAccoAccMacad OBJECT-TYPE
                SYNTAX DisplayString (SIZE(0..255))
                MAX-ACCESS read-only
                STATUS current
                DESCRIPTION "MAC-Address"
                ::= {  staAccoAccEntry 2 }

staAccoAccPeer OBJECT-TYPE
                SYNTAX DisplayString (SIZE(0..31))
                MAX-ACCESS read-only
                STATUS current
                DESCRIPTION "Peer"
                ::= {  staAccoAccEntry 3 }

staAccoAccConnt OBJECT-TYPE
                SYNTAX INTEGER
                {
                  unknown(0),
                  dial-up(1),
                  leased-line(2),
                  dsl-line(4),
                  vpn-conn(7),
                  pptp-conn(8)
                }
                MAX-ACCESS read-only
                STATUS current
                DESCRIPTION "Conn.-Type"
                ::= {  staAccoAccEntry 4 }

staAccoAccRxkby OBJECT-TYPE
                SYNTAX INTEGER (0..2147483647)
                MAX-ACCESS read-only
                STATUS current
                DESCRIPTION "Rx-KBytes"
                ::= {  staAccoAccEntry 5 }

staAccoAccTxkby OBJECT-TYPE
                SYNTAX INTEGER (0..2147483647)
                MAX-ACCESS read-only
                STATUS current
                DESCRIPTION "Tx-KBytes"
                ::= {  staAccoAccEntry 6 }

staAccoAccTotal OBJECT-TYPE
                SYNTAX INTEGER (0..2147483647)
                MAX-ACCESS read-only
                STATUS current
                DESCRIPTION "Total-Time"
                ::= {  staAccoAccEntry 8 }

staAccoAccConne OBJECT-TYPE
                SYNTAX INTEGER (0..2147483647)
                MAX-ACCESS read-only
                STATUS current
                DESCRIPTION "Connections"
                ::= {  staAccoAccEntry 9 }

staAccoLasTable OBJECT-TYPE
                SYNTAX SEQUENCE OF StaAccoLasEntry
                MAX-ACCESS not-accessible
                STATUS current
                DESCRIPTION "Last-Snapshot"
                ::= {  staAcco 3 }

staAccoLasEntry OBJECT-TYPE
                SYNTAX StaAccoLasEntry
                MAX-ACCESS not-accessible
                STATUS current
                DESCRIPTION "entry in table"
                INDEX { staAccoLasUsern, staAccoLasMacad, staAccoLasPeer, staAccoLasConnt }
                ::= {  staAccoLasTable 1 }

StaAccoLasEntry ::= SEQUENCE {
                staAccoLasUsern DisplayString,
                staAccoLasMacad DisplayString,
                staAccoLasPeer DisplayString,
                staAccoLasConnt INTEGER,
                staAccoLasRxkby INTEGER,
                staAccoLasTxkby INTEGER,
                staAccoLasTotal INTEGER,
                staAccoLasConne INTEGER
               }

staAccoLasUsern OBJECT-TYPE
                SYNTAX DisplayString (SIZE(0..28))
                MAX-ACCESS read-only
                STATUS current
                DESCRIPTION "Username"
                ::= {  staAccoLasEntry 1 }

staAccoLasMacad OBJECT-TYPE
                SYNTAX DisplayString (SIZE(0..255))
                MAX-ACCESS read-only
                STATUS current
                DESCRIPTION "MAC-Address"
                ::= {  staAccoLasEntry 2 }

staAccoLasPeer OBJECT-TYPE
                SYNTAX DisplayString (SIZE(0..31))
                MAX-ACCESS read-only
                STATUS current
                DESCRIPTION "Peer"
                ::= {  staAccoLasEntry 3 }

staAccoLasConnt OBJECT-TYPE
                SYNTAX INTEGER
                {
                  unknown(0),
                  dial-up(1),
                  leased-line(2),
                  dsl-line(4),
                  vpn-conn(7),
                  pptp-conn(8)
                }
                MAX-ACCESS read-only
                STATUS current
                DESCRIPTION "Conn.-Type"
                ::= {  staAccoLasEntry 4 }

staAccoLasRxkby OBJECT-TYPE
                SYNTAX INTEGER (0..2147483647)
                MAX-ACCESS read-only
                STATUS current
                DESCRIPTION "Rx-KBytes"
                ::= {  staAccoLasEntry 5 }

staAccoLasTxkby OBJECT-TYPE
                SYNTAX INTEGER (0..2147483647)
                MAX-ACCESS read-only
                STATUS current
                DESCRIPTION "Tx-KBytes"
                ::= {  staAccoLasEntry 6 }

staAccoLasTotal OBJECT-TYPE
                SYNTAX INTEGER (0..2147483647)
                MAX-ACCESS read-only
                STATUS current
                DESCRIPTION "Total-Time"
                ::= {  staAccoLasEntry 8 }

staAccoLasConne OBJECT-TYPE
                SYNTAX INTEGER (0..2147483647)
                MAX-ACCESS read-only
                STATUS current
                DESCRIPTION "Connections"
                ::= {  staAccoLasEntry 9 }

staAccoTimTable OBJECT-TYPE
                SYNTAX SEQUENCE OF StaAccoTimEntry
                MAX-ACCESS not-accessible
                STATUS current
                DESCRIPTION "Time-Last-Snapshot"
                ::= {  staAcco 5 }

staAccoTimEntry OBJECT-TYPE
                SYNTAX StaAccoTimEntry
                MAX-ACCESS not-accessible
                STATUS current
                DESCRIPTION "entry in table"
                INDEX { staAccoTimSys }
                ::= {  staAccoTimTable 1 }

StaAccoTimEntry ::= SEQUENCE {
                staAccoTimSys Counter32
               }

staAccoTimSys OBJECT-TYPE
              SYNTAX Counter32
              MAX-ACCESS read-only
              STATUS current
              DESCRIPTION "System-time"
              ::= {  staAccoTimEntry 1 }

staAccoDel OBJECT-TYPE
           SYNTAX DisplayString
           MAX-ACCESS read-write
           STATUS current
           DESCRIPTION "Delete-Values"
           ::= {  staAcco 4 }

staCert OBJECT IDENTIFIER ::= { sta 61}
staCertSce OBJECT IDENTIFIER ::= { staCert 1}
staCertSceNumca OBJECT-TYPE
                SYNTAX INTEGER
                MAX-ACCESS read-only
                STATUS current
                DESCRIPTION "NumCAs"
                ::= {  staCertSce 1 }

staCertSceNumra OBJECT-TYPE
                SYNTAX INTEGER
                MAX-ACCESS read-only
                STATUS current
                DESCRIPTION "NumRAs"
                ::= {  staCertSce 2 }

staCertSceNumce OBJECT-TYPE
                SYNTAX INTEGER
                MAX-ACCESS read-only
                STATUS current
                DESCRIPTION "NumCerts"
                ::= {  staCertSce 3 }

staCertSceCasTable OBJECT-TYPE
                     SYNTAX SEQUENCE OF StaCertSceCasEntry
                     MAX-ACCESS not-accessible
                     STATUS current
                     DESCRIPTION "CAs"
                     ::= {  staCertSce 4 }

staCertSceCasEntry OBJECT-TYPE
                     SYNTAX StaCertSceCasEntry
                     MAX-ACCESS not-accessible
                     STATUS current
                     DESCRIPTION "entry in table"
                     INDEX { staCertSceCasIdx }
                     ::= {  staCertSceCasTable 1 }

StaCertSceCasEntry ::= SEQUENCE {
                     staCertSceCasIdx INTEGER,
                     staCertSceCasName DisplayString,
                     staCertSceCasExpire DisplayString,
                     staCertSceCasIssued DisplayString,
                     staCertSceCasKeyusa DisplayString,
                     staCertSceCasIssuer DisplayString,
                     staCertSceCasSubjec DisplayString,
                     staCertSceCasStatus INTEGER,
                     staCertSceCasIkecer INTEGER,
                     staCertSceCasMd5fin DisplayString,
                     staCertSceCasSha1fi DisplayString,
                     staCertSceCasExpsnm INTEGER,
                     staCertSceCasIsssnm INTEGER
                    }

staCertSceCasIdx OBJECT-TYPE
                    SYNTAX INTEGER (0..2147483647)
                    MAX-ACCESS read-only
                    STATUS current
                    DESCRIPTION "Idx."
                    ::= {  staCertSceCasEntry 1 }

staCertSceCasName OBJECT-TYPE
                    SYNTAX DisplayString (SIZE(0..15))
                    MAX-ACCESS read-only
                    STATUS current
                    DESCRIPTION "Name"
                    ::= {  staCertSceCasEntry 2 }

staCertSceCasExpire OBJECT-TYPE
                    SYNTAX DisplayString (SIZE(0..19))
                    MAX-ACCESS read-only
                    STATUS current
                    DESCRIPTION "Expires"
                    ::= {  staCertSceCasEntry 3 }

staCertSceCasIssued OBJECT-TYPE
                    SYNTAX DisplayString (SIZE(0..19))
                    MAX-ACCESS read-only
                    STATUS current
                    DESCRIPTION "Issued"
                    ::= {  staCertSceCasEntry 4 }

staCertSceCasKeyusa OBJECT-TYPE
                    SYNTAX DisplayString (SIZE(0..251))
                    MAX-ACCESS read-only
                    STATUS current
                    DESCRIPTION "Key-Usage"
                    ::= {  staCertSceCasEntry 5 }

staCertSceCasIssuer OBJECT-TYPE
                    SYNTAX DisplayString (SIZE(0..251))
                    MAX-ACCESS read-only
                    STATUS current
                    DESCRIPTION "Issuer"
                    ::= {  staCertSceCasEntry 6 }

staCertSceCasSubjec OBJECT-TYPE
                    SYNTAX DisplayString (SIZE(0..251))
                    MAX-ACCESS read-only
                    STATUS current
                    DESCRIPTION "Subject"
                    ::= {  staCertSceCasEntry 7 }

staCertSceCasStatus OBJECT-TYPE
                    SYNTAX INTEGER
                    {
                      status-unknown(0),
                      enroll-requested(1),
                      enroll-received(2),
                      enroll-ok(3),
                      enroll-bad(4),
                      enroll-bad-config(5),
                      enroll-pending(6),
                      enroll-rejected(7),
                      enroll-rejected-badalg(8),
                      enroll-rejected-badmsgchk(9),
                      enroll-rejected-badreq(10),
                      enroll-rejected-badtime(11),
                      enroll-rejected-badcertid(12),
                      enroll-ca-missing(13),
                      enroll-exp-unknown(14),
                      enroll-key-missing(15),
                      enroll-req-missing(16),
                      enroll-bad-reply(17),
                      ca-ra-requested(18),
                      ca-ra-received(19),
                      ca-ra-ok(20),
                      ca-ra-need-update(21),
                      ca-ra-bad(22),
                      ca-ra-bad-config(23),
                      not-a-ca-cert(24),
                      fingerprint-check-failed(25),
                      job-busy(26),
                      job-timeout(27),
                      job-scep-not-free(28),
                      job-no-url(29),
                      job-no-scep-msg(30),
                      utc-err(31),
                      mem-err(32),
                      msg-len-err(33),
                      selfsigned-err(34),
                      pkcs7-wrap-err(35),
                      pkcs7-unwrap-err(36),
                      gen-err(37),
                      job-httpc-err(38),
                      job-httpc-con-err(39),
                      job-httpc-dns-err(40),
                      job-httpc-prot-err(41),
                      job-httpc-mem-err(42),
                      job-wdog-err(43),
                      ok(44),
                      dn-normalization-failed(45),
                      io-err(46),
                      disabled(47)
                    }
                    MAX-ACCESS read-only
                    STATUS current
                    DESCRIPTION "Status"
                    ::= {  staCertSceCasEntry 8 }

staCertSceCasIkecer OBJECT-TYPE
                    SYNTAX INTEGER
                    {
                      yes(1),
                      no(0)
                    }
                    MAX-ACCESS read-only
                    STATUS current
                    DESCRIPTION "IKE-Certificate"
                    ::= {  staCertSceCasEntry 9 }

staCertSceCasMd5fin OBJECT-TYPE
                    SYNTAX DisplayString (SIZE(0..46))
                    MAX-ACCESS read-only
                    STATUS current
                    DESCRIPTION "md5-Fingerprint"
                    ::= {  staCertSceCasEntry 10 }

staCertSceCasSha1fi OBJECT-TYPE
                    SYNTAX DisplayString (SIZE(0..58))
                    MAX-ACCESS read-only
                    STATUS current
                    DESCRIPTION "sha1-Fingerprint"
                    ::= {  staCertSceCasEntry 11 }

staCertSceCasExpsnm OBJECT-TYPE
                    SYNTAX INTEGER (0..2147483647)
                    MAX-ACCESS read-only
                    STATUS current
                    DESCRIPTION "Exp-SNMP"
                    ::= {  staCertSceCasEntry 12 }

staCertSceCasIsssnm OBJECT-TYPE
                    SYNTAX INTEGER (0..2147483647)
                    MAX-ACCESS read-only
                    STATUS current
                    DESCRIPTION "Iss-SNMP"
                    ::= {  staCertSceCasEntry 13 }

staCertSceRasTable OBJECT-TYPE
                     SYNTAX SEQUENCE OF StaCertSceRasEntry
                     MAX-ACCESS not-accessible
                     STATUS current
                     DESCRIPTION "RAs"
                     ::= {  staCertSce 5 }

staCertSceRasEntry OBJECT-TYPE
                     SYNTAX StaCertSceRasEntry
                     MAX-ACCESS not-accessible
                     STATUS current
                     DESCRIPTION "entry in table"
                     INDEX { staCertSceRasIdx }
                     ::= {  staCertSceRasTable 1 }

StaCertSceRasEntry ::= SEQUENCE {
                     staCertSceRasIdx INTEGER,
                     staCertSceRasName DisplayString,
                     staCertSceRasExpire DisplayString,
                     staCertSceRasIssued DisplayString,
                     staCertSceRasKeyusa DisplayString,
                     staCertSceRasIssuer DisplayString,
                     staCertSceRasSubjec DisplayString,
                     staCertSceRasStatus INTEGER,
                     staCertSceRasExpsnm INTEGER,
                     staCertSceRasIsssnm INTEGER
                    }

staCertSceRasIdx OBJECT-TYPE
                    SYNTAX INTEGER (0..2147483647)
                    MAX-ACCESS read-only
                    STATUS current
                    DESCRIPTION "Idx."
                    ::= {  staCertSceRasEntry 1 }

staCertSceRasName OBJECT-TYPE
                    SYNTAX DisplayString (SIZE(0..15))
                    MAX-ACCESS read-only
                    STATUS current
                    DESCRIPTION "Name"
                    ::= {  staCertSceRasEntry 2 }

staCertSceRasExpire OBJECT-TYPE
                    SYNTAX DisplayString (SIZE(0..19))
                    MAX-ACCESS read-only
                    STATUS current
                    DESCRIPTION "Expires"
                    ::= {  staCertSceRasEntry 3 }

staCertSceRasIssued OBJECT-TYPE
                    SYNTAX DisplayString (SIZE(0..19))
                    MAX-ACCESS read-only
                    STATUS current
                    DESCRIPTION "Issued"
                    ::= {  staCertSceRasEntry 4 }

staCertSceRasKeyusa OBJECT-TYPE
                    SYNTAX DisplayString (SIZE(0..251))
                    MAX-ACCESS read-only
                    STATUS current
                    DESCRIPTION "Key-Usage"
                    ::= {  staCertSceRasEntry 5 }

staCertSceRasIssuer OBJECT-TYPE
                    SYNTAX DisplayString (SIZE(0..251))
                    MAX-ACCESS read-only
                    STATUS current
                    DESCRIPTION "Issuer"
                    ::= {  staCertSceRasEntry 6 }

staCertSceRasSubjec OBJECT-TYPE
                    SYNTAX DisplayString (SIZE(0..251))
                    MAX-ACCESS read-only
                    STATUS current
                    DESCRIPTION "Subject"
                    ::= {  staCertSceRasEntry 7 }

staCertSceRasStatus OBJECT-TYPE
                    SYNTAX INTEGER
                    {
                      status-unknown(0),
                      enroll-requested(1),
                      enroll-received(2),
                      enroll-ok(3),
                      enroll-bad(4),
                      enroll-bad-config(5),
                      enroll-pending(6),
                      enroll-rejected(7),
                      enroll-rejected-badalg(8),
                      enroll-rejected-badmsgchk(9),
                      enroll-rejected-badreq(10),
                      enroll-rejected-badtime(11),
                      enroll-rejected-badcertid(12),
                      enroll-ca-missing(13),
                      enroll-exp-unknown(14),
                      enroll-key-missing(15),
                      enroll-req-missing(16),
                      enroll-bad-reply(17),
                      ca-ra-requested(18),
                      ca-ra-received(19),
                      ca-ra-ok(20),
                      ca-ra-need-update(21),
                      ca-ra-bad(22),
                      ca-ra-bad-config(23),
                      not-a-ca-cert(24),
                      fingerprint-check-failed(25),
                      job-busy(26),
                      job-timeout(27),
                      job-scep-not-free(28),
                      job-no-url(29),
                      job-no-scep-msg(30),
                      utc-err(31),
                      mem-err(32),
                      msg-len-err(33),
                      selfsigned-err(34),
                      pkcs7-wrap-err(35),
                      pkcs7-unwrap-err(36),
                      gen-err(37),
                      job-httpc-err(38),
                      job-httpc-con-err(39),
                      job-httpc-dns-err(40),
                      job-httpc-prot-err(41),
                      job-httpc-mem-err(42),
                      job-wdog-err(43),
                      ok(44),
                      dn-normalization-failed(45),
                      io-err(46),
                      disabled(47)
                    }
                    MAX-ACCESS read-only
                    STATUS current
                    DESCRIPTION "Status"
                    ::= {  staCertSceRasEntry 8 }

staCertSceRasExpsnm OBJECT-TYPE
                    SYNTAX INTEGER (0..2147483647)
                    MAX-ACCESS read-only
                    STATUS current
                    DESCRIPTION "Exp-SNMP"
                    ::= {  staCertSceRasEntry 9 }

staCertSceRasIsssnm OBJECT-TYPE
                    SYNTAX INTEGER (0..2147483647)
                    MAX-ACCESS read-only
                    STATUS current
                    DESCRIPTION "Iss-SNMP"
                    ::= {  staCertSceRasEntry 10 }

staCertSceCertsTable OBJECT-TYPE
                     SYNTAX SEQUENCE OF StaCertSceCertsEntry
                     MAX-ACCESS not-accessible
                     STATUS current
                     DESCRIPTION "Certs"
                     ::= {  staCertSce 6 }

staCertSceCertsEntry OBJECT-TYPE
                     SYNTAX StaCertSceCertsEntry
                     MAX-ACCESS not-accessible
                     STATUS current
                     DESCRIPTION "entry in table"
                     INDEX { staCertSceCertsIdx }
                     ::= {  staCertSceCertsTable 1 }

StaCertSceCertsEntry ::= SEQUENCE {
                     staCertSceCertsIdx INTEGER,
                     staCertSceCertsName DisplayString,
                     staCertSceCertsExpires DisplayString,
                     staCertSceCertsIssued DisplayString,
                     staCertSceCertsKeyusage DisplayString,
                     staCertSceCertsExtended DisplayString,
                     staCertSceCertsSubjecta DisplayString,
                     staCertSceCertsIssuer DisplayString,
                     staCertSceCertsSubject DisplayString,
                     staCertSceCertsStatus INTEGER,
                     staCertSceCertsExpsnmp INTEGER,
                     staCertSceCertsIsssnmp INTEGER
                    }

staCertSceCertsIdx OBJECT-TYPE
                        SYNTAX INTEGER (0..2147483647)
                        MAX-ACCESS read-only
                        STATUS current
                        DESCRIPTION "Idx."
                        ::= {  staCertSceCertsEntry 1 }

staCertSceCertsName OBJECT-TYPE
                        SYNTAX DisplayString (SIZE(0..15))
                        MAX-ACCESS read-only
                        STATUS current
                        DESCRIPTION "Name"
                        ::= {  staCertSceCertsEntry 2 }

staCertSceCertsExpires OBJECT-TYPE
                        SYNTAX DisplayString (SIZE(0..19))
                        MAX-ACCESS read-only
                        STATUS current
                        DESCRIPTION "Expires"
                        ::= {  staCertSceCertsEntry 3 }

staCertSceCertsIssued OBJECT-TYPE
                        SYNTAX DisplayString (SIZE(0..19))
                        MAX-ACCESS read-only
                        STATUS current
                        DESCRIPTION "Issued"
                        ::= {  staCertSceCertsEntry 4 }

staCertSceCertsKeyusage OBJECT-TYPE
                        SYNTAX DisplayString (SIZE(0..251))
                        MAX-ACCESS read-only
                        STATUS current
                        DESCRIPTION "Key-Usage"
                        ::= {  staCertSceCertsEntry 5 }

staCertSceCertsExtended OBJECT-TYPE
                        SYNTAX DisplayString (SIZE(0..251))
                        MAX-ACCESS read-only
                        STATUS current
                        DESCRIPTION "Extended-KeyUsage"
                        ::= {  staCertSceCertsEntry 12 }

staCertSceCertsSubjecta OBJECT-TYPE
                        SYNTAX DisplayString (SIZE(0..251))
                        MAX-ACCESS read-only
                        STATUS current
                        DESCRIPTION "SubjectAltName"
                        ::= {  staCertSceCertsEntry 6 }

staCertSceCertsIssuer OBJECT-TYPE
                        SYNTAX DisplayString (SIZE(0..251))
                        MAX-ACCESS read-only
                        STATUS current
                        DESCRIPTION "Issuer"
                        ::= {  staCertSceCertsEntry 7 }

staCertSceCertsSubject OBJECT-TYPE
                        SYNTAX DisplayString (SIZE(0..251))
                        MAX-ACCESS read-only
                        STATUS current
                        DESCRIPTION "Subject"
                        ::= {  staCertSceCertsEntry 8 }

staCertSceCertsStatus OBJECT-TYPE
                        SYNTAX INTEGER
                        {
                          status-unknown(0),
                          enroll-requested(1),
                          enroll-received(2),
                          enroll-ok(3),
                          enroll-bad(4),
                          enroll-bad-config(5),
                          enroll-pending(6),
                          enroll-rejected(7),
                          enroll-rejected-badalg(8),
                          enroll-rejected-badmsgchk(9),
                          enroll-rejected-badreq(10),
                          enroll-rejected-badtime(11),
                          enroll-rejected-badcertid(12),
                          enroll-ca-missing(13),
                          enroll-exp-unknown(14),
                          enroll-key-missing(15),
                          enroll-req-missing(16),
                          enroll-bad-reply(17),
                          ca-ra-requested(18),
                          ca-ra-received(19),
                          ca-ra-ok(20),
                          ca-ra-need-update(21),
                          ca-ra-bad(22),
                          ca-ra-bad-config(23),
                          not-a-ca-cert(24),
                          fingerprint-check-failed(25),
                          job-busy(26),
                          job-timeout(27),
                          job-scep-not-free(28),
                          job-no-url(29),
                          job-no-scep-msg(30),
                          utc-err(31),
                          mem-err(32),
                          msg-len-err(33),
                          selfsigned-err(34),
                          pkcs7-wrap-err(35),
                          pkcs7-unwrap-err(36),
                          gen-err(37),
                          job-httpc-err(38),
                          job-httpc-con-err(39),
                          job-httpc-dns-err(40),
                          job-httpc-prot-err(41),
                          job-httpc-mem-err(42),
                          job-wdog-err(43),
                          ok(44),
                          dn-normalization-failed(45),
                          io-err(46),
                          disabled(47)
                        }
                        MAX-ACCESS read-only
                        STATUS current
                        DESCRIPTION "Status"
                        ::= {  staCertSceCertsEntry 9 }

staCertSceCertsExpsnmp OBJECT-TYPE
                        SYNTAX INTEGER (0..2147483647)
                        MAX-ACCESS read-only
                        STATUS current
                        DESCRIPTION "Exp-SNMP"
                        ::= {  staCertSceCertsEntry 10 }

staCertSceCertsIsssnmp OBJECT-TYPE
                        SYNTAX INTEGER (0..2147483647)
                        MAX-ACCESS read-only
                        STATUS current
                        DESCRIPTION "Iss-SNMP"
                        ::= {  staCertSceCertsEntry 11 }

staCertSceDelet OBJECT-TYPE
                SYNTAX DisplayString
                MAX-ACCESS read-write
                STATUS current
                DESCRIPTION "Delete-Values"
                ::= {  staCertSce 7 }

staCertCrl OBJECT IDENTIFIER ::= { staCert 3}
staCertCrlNum OBJECT-TYPE
              SYNTAX INTEGER
              MAX-ACCESS read-only
              STATUS current
              DESCRIPTION "NumCRLs"
              ::= {  staCertCrl 1 }

staCertCrlCrlTable OBJECT-TYPE
                   SYNTAX SEQUENCE OF StaCertCrlCrlEntry
                   MAX-ACCESS not-accessible
                   STATUS current
                   DESCRIPTION "CRLs"
                   ::= {  staCertCrl 2 }

staCertCrlCrlEntry OBJECT-TYPE
                   SYNTAX StaCertCrlCrlEntry
                   MAX-ACCESS not-accessible
                   STATUS current
                   DESCRIPTION "entry in table"
                   INDEX { staCertCrlCrlIdx }
                   ::= {  staCertCrlCrlTable 1 }

StaCertCrlCrlEntry ::= SEQUENCE {
                   staCertCrlCrlIdx INTEGER,
                   staCertCrlCrlExpire DisplayString,
                   staCertCrlCrlIssued DisplayString,
                   staCertCrlCrlIssuer DisplayString,
                   staCertCrlCrlDistri DisplayString,
                   staCertCrlCrlStatus INTEGER,
                   staCertCrlCrlExpsnm INTEGER,
                   staCertCrlCrlIsssnm INTEGER
                  }

staCertCrlCrlIdx OBJECT-TYPE
                    SYNTAX INTEGER (0..2147483647)
                    MAX-ACCESS read-only
                    STATUS current
                    DESCRIPTION "Idx."
                    ::= {  staCertCrlCrlEntry 1 }

staCertCrlCrlExpire OBJECT-TYPE
                    SYNTAX DisplayString (SIZE(0..19))
                    MAX-ACCESS read-only
                    STATUS current
                    DESCRIPTION "Expires"
                    ::= {  staCertCrlCrlEntry 2 }

staCertCrlCrlIssued OBJECT-TYPE
                    SYNTAX DisplayString (SIZE(0..19))
                    MAX-ACCESS read-only
                    STATUS current
                    DESCRIPTION "Issued"
                    ::= {  staCertCrlCrlEntry 3 }

staCertCrlCrlIssuer OBJECT-TYPE
                    SYNTAX DisplayString (SIZE(0..251))
                    MAX-ACCESS read-only
                    STATUS current
                    DESCRIPTION "Issuer"
                    ::= {  staCertCrlCrlEntry 4 }

staCertCrlCrlDistri OBJECT-TYPE
                    SYNTAX DisplayString (SIZE(0..251))
                    MAX-ACCESS read-only
                    STATUS current
                    DESCRIPTION "Distribution-Point"
                    ::= {  staCertCrlCrlEntry 5 }

staCertCrlCrlStatus OBJECT-TYPE
                    SYNTAX INTEGER
                    {
                      status-unknown(0),
                      update-requested(1),
                      update-received(2),
                      update-ok(3),
                      update-bad(4),
                      crl-job-busy(5),
                      crl-job-timeout(6),
                      crl-not-free-err(7),
                      no-url-passed-err(8),
                      no-crl-received-err(9),
                      no-utc-err(10),
                      crl-job-mem-err(11),
                      crl-len-err(12),
                      crl-gen-err(13),
                      httpc-err(14),
                      httpc-con-err(15),
                      httpc-dns-err(16),
                      httpc-prot-err(17),
                      httpc-mem-err(18),
                      crl-job-wdog-err(19),
                      prefetching(20),
                      retrieving(21),
                      crl-ok(22),
                      not-a-crl(23),
                      no-root-issuer(24),
                      issuer-mismatch(25),
                      no-lu-in-crl(26),
                      crl-not-gmt(27),
                      invalid-field(28),
                      update-expired(29),
                      crls-disabled(30)
                    }
                    MAX-ACCESS read-only
                    STATUS current
                    DESCRIPTION "Status"
                    ::= {  staCertCrlCrlEntry 6 }

staCertCrlCrlExpsnm OBJECT-TYPE
                    SYNTAX INTEGER (0..2147483647)
                    MAX-ACCESS read-only
                    STATUS current
                    DESCRIPTION "Exp-SNMP"
                    ::= {  staCertCrlCrlEntry 7 }

staCertCrlCrlIsssnm OBJECT-TYPE
                    SYNTAX INTEGER (0..2147483647)
                    MAX-ACCESS read-only
                    STATUS current
                    DESCRIPTION "Iss-SNMP"
                    ::= {  staCertCrlCrlEntry 8 }

staVlan OBJECT IDENTIFIER ::= { sta 62}
staVlanOpe OBJECT-TYPE
           SYNTAX INTEGER
           {
             no(0),
             yes(1)
           }
           MAX-ACCESS read-only
           STATUS current
           DESCRIPTION "Operating"
           ::= {  staVlan 4 }

staVlanNetTable OBJECT-TYPE
                SYNTAX SEQUENCE OF StaVlanNetEntry
                MAX-ACCESS not-accessible
                STATUS current
                DESCRIPTION "Networks"
                ::= {  staVlan 1 }

staVlanNetEntry OBJECT-TYPE
                SYNTAX StaVlanNetEntry
                MAX-ACCESS not-accessible
                STATUS current
                DESCRIPTION "entry in table"
                INDEX { staVlanNetVla }
                ::= {  staVlanNetTable 1 }

StaVlanNetEntry ::= SEQUENCE {
                staVlanNetVla INTEGER,
                staVlanNetPor DisplayString
               }

staVlanNetVla OBJECT-TYPE
              SYNTAX INTEGER (0..65535)
              MAX-ACCESS read-only
              STATUS current
              DESCRIPTION "VLAN-ID"
              ::= {  staVlanNetEntry 1 }

staVlanNetPor OBJECT-TYPE
              SYNTAX DisplayString (SIZE(0..255))
              MAX-ACCESS read-only
              STATUS current
              DESCRIPTION "Ports"
              ::= {  staVlanNetEntry 4 }

staVlanPorTable OBJECT-TYPE
                SYNTAX SEQUENCE OF StaVlanPorEntry
                MAX-ACCESS not-accessible
                STATUS current
                DESCRIPTION "Port-Table"
                ::= {  staVlan 2 }

staVlanPorEntry OBJECT-TYPE
                SYNTAX StaVlanPorEntry
                MAX-ACCESS not-accessible
                STATUS current
                DESCRIPTION "entry in table"
                INDEX { staVlanPorPor }
                ::= {  staVlanPorTable 1 }

StaVlanPorEntry ::= SEQUENCE {
                staVlanPorPor DisplayString,
                staVlanPorTag INTEGER
               }

staVlanPorPor OBJECT-TYPE
              SYNTAX DisplayString (SIZE(0..8))
              MAX-ACCESS read-only
              STATUS current
              DESCRIPTION "Port"
              ::= {  staVlanPorEntry 1 }

staVlanPorTag OBJECT-TYPE
              SYNTAX INTEGER
              {
                ingress-mixed(0),
                never(1),
                mixed(2),
                always(3)
              }
              MAX-ACCESS read-only
              STATUS current
              DESCRIPTION "Tagging-Mode"
              ::= {  staVlanPorEntry 6 }

staComp OBJECT IDENTIFIER ::= { sta 67}
staCompDevTable OBJECT-TYPE
                SYNTAX SEQUENCE OF StaCompDevEntry
                MAX-ACCESS not-accessible
                STATUS current
                DESCRIPTION "Devices"
                ::= {  staComp 1 }

staCompDevEntry OBJECT-TYPE
                SYNTAX StaCompDevEntry
                MAX-ACCESS not-accessible
                STATUS current
                DESCRIPTION "entry in table"
                INDEX { staCompDevIndex }
                ::= {  staCompDevTable 1 }

StaCompDevEntry ::= SEQUENCE {
                staCompDevIndex INTEGER,
                staCompDevDevicet INTEGER,
                staCompDevBus INTEGER,
                staCompDevDevice INTEGER,
                staCompDevVendor INTEGER,
                staCompDevUsbdriv INTEGER,
                staCompDevState INTEGER,
                staCompDevFirmwar DisplayString,
                staCompDevService INTEGER,
                staCompDevFullnam DisplayString
               }

staCompDevIndex OBJECT-TYPE
                  SYNTAX INTEGER (0..2147483647)
                  MAX-ACCESS read-only
                  STATUS current
                  DESCRIPTION "Index"
                  ::= {  staCompDevEntry 1 }

staCompDevDevicet OBJECT-TYPE
                  SYNTAX INTEGER
                  {
                    outband-modem(2),
                    outband(1),
                    option-icon(17),
                    novatel-merlin-mc950d(26),
                    sierra-compass-885(39),
                    sierra-aircard-875u(30),
                    huawei-e172-e220-e870(31),
                    e4g-systems-uxs1(23),
                    belkin-f5u103(33),
                    prolific-2303(34),
                    ftdi-8u232am(35)
                  }
                  MAX-ACCESS read-only
                  STATUS current
                  DESCRIPTION "Device-Type"
                  ::= {  staCompDevEntry 2 }

staCompDevBus OBJECT-TYPE
                  SYNTAX INTEGER
                  {
                    unknown(0),
                    outband(1),
                    cardbus(2),
                    usb(3),
                    virtual(4)
                  }
                  MAX-ACCESS read-only
                  STATUS current
                  DESCRIPTION "Bus"
                  ::= {  staCompDevEntry 3 }

staCompDevDevice OBJECT-TYPE
                  SYNTAX INTEGER (0..65535)
                  MAX-ACCESS read-only
                  STATUS current
                  DESCRIPTION "Device"
                  ::= {  staCompDevEntry 4 }

staCompDevVendor OBJECT-TYPE
                  SYNTAX INTEGER (0..65535)
                  MAX-ACCESS read-only
                  STATUS current
                  DESCRIPTION "Vendor"
                  ::= {  staCompDevEntry 5 }

staCompDevUsbdriv OBJECT-TYPE
                  SYNTAX INTEGER
                  {
                    unknown(0),
                    ubsa(1),
                    uchcom(2),
                    uftdi(3),
                    ugensa(4),
                    uhmodem(5),
                    ukyopon(6),
                    uplcom(7),
                    uslsa(8)
                  }
                  MAX-ACCESS read-only
                  STATUS current
                  DESCRIPTION "USB-Driver"
                  ::= {  staCompDevEntry 11 }

staCompDevState OBJECT-TYPE
                  SYNTAX INTEGER
                  {
                    unknown(0),
                    initialize(1),
                    wait-for-firmware(2),
                    ready(3),
                    in-use(4),
                    exclusive(5),
                    initialize(6)
                  }
                  MAX-ACCESS read-only
                  STATUS current
                  DESCRIPTION "State"
                  ::= {  staCompDevEntry 13 }

staCompDevFirmwar OBJECT-TYPE
                  SYNTAX DisplayString (SIZE(0..31))
                  MAX-ACCESS read-only
                  STATUS current
                  DESCRIPTION "Firmware-Version"
                  ::= {  staCompDevEntry 14 }

staCompDevService OBJECT-TYPE
                  SYNTAX INTEGER
                  {
                    wan(1),
                    com-port-server(2)
                  }
                  MAX-ACCESS read-only
                  STATUS current
                  DESCRIPTION "Service"
                  ::= {  staCompDevEntry 15 }

staCompDevFullnam OBJECT-TYPE
                  SYNTAX DisplayString (SIZE(0..31))
                  MAX-ACCESS read-only
                  STATUS current
                  DESCRIPTION "Full-Name"
                  ::= {  staCompDevEntry 99 }

staCompCom OBJECT IDENTIFIER ::= { staComp 2}
staCompComNetworksTable OBJECT-TYPE
                        SYNTAX SEQUENCE OF StaCompComNetworksEntry
                        MAX-ACCESS not-accessible
                        STATUS current
                        DESCRIPTION "Network-Status"
                        ::= {  staCompCom 1 }

staCompComNetworksEntry OBJECT-TYPE
                        SYNTAX StaCompComNetworksEntry
                        MAX-ACCESS not-accessible
                        STATUS current
                        DESCRIPTION "entry in table"
                        INDEX { staCompComNetworksDevicet, staCompComNetworksPortnum }
                        ::= {  staCompComNetworksTable 1 }

StaCompComNetworksEntry ::= SEQUENCE {
                        staCompComNetworksDevicet INTEGER,
                        staCompComNetworksPortnum INTEGER,
                        staCompComNetworksFullnam DisplayString,
                        staCompComNetworksConnect INTEGER,
                        staCompComNetworksLasterr INTEGER,
                        staCompComNetworksRemotea IpAddress,
                        staCompComNetworksLocalpo INTEGER,
                        staCompComNetworksRemotep INTEGER
                       }

staCompComNetworksDevicet OBJECT-TYPE
                          SYNTAX INTEGER
                          {
                            outband(1),
                            belkin-f5u103(33),
                            prolific-2303(34),
                            ftdi-8u232am(35)
                          }
                          MAX-ACCESS read-only
                          STATUS current
                          DESCRIPTION "Device-Type"
                          ::= {  staCompComNetworksEntry 1 }

staCompComNetworksPortnum OBJECT-TYPE
                          SYNTAX INTEGER (0..255)
                          MAX-ACCESS read-only
                          STATUS current
                          DESCRIPTION "Port-Number"
                          ::= {  staCompComNetworksEntry 2 }

staCompComNetworksFullnam OBJECT-TYPE
                          SYNTAX DisplayString (SIZE(0..255))
                          MAX-ACCESS read-only
                          STATUS current
                          DESCRIPTION "Full-Name"
                          ::= {  staCompComNetworksEntry 99 }

staCompComNetworksConnect OBJECT-TYPE
                          SYNTAX INTEGER
                          {
                            idle(0),
                            listening(1),
                            connecting(2),
                            connected(3),
                            not-listening(4)
                          }
                          MAX-ACCESS read-only
                          STATUS current
                          DESCRIPTION "Connection-Status"
                          ::= {  staCompComNetworksEntry 4 }

staCompComNetworksLasterr OBJECT-TYPE
                          SYNTAX INTEGER
                          {
                            none(0),
                            dns-error(1),
                            tcp-connect-error(2),
                            remote-disconnect(3)
                          }
                          MAX-ACCESS read-only
                          STATUS current
                          DESCRIPTION "Last-Error"
                          ::= {  staCompComNetworksEntry 5 }

staCompComNetworksRemotea OBJECT-TYPE
                          SYNTAX IpAddress
                          MAX-ACCESS read-only
                          STATUS current
                          DESCRIPTION "Remote-Address"
                          ::= {  staCompComNetworksEntry 6 }

staCompComNetworksLocalpo OBJECT-TYPE
                          SYNTAX INTEGER (0..65535)
                          MAX-ACCESS read-only
                          STATUS current
                          DESCRIPTION "Local-Port"
                          ::= {  staCompComNetworksEntry 7 }

staCompComNetworksRemotep OBJECT-TYPE
                          SYNTAX INTEGER (0..65535)
                          MAX-ACCESS read-only
                          STATUS current
                          DESCRIPTION "Remote-Port"
                          ::= {  staCompComNetworksEntry 8 }

staCompComComportsTable OBJECT-TYPE
                        SYNTAX SEQUENCE OF StaCompComComportsEntry
                        MAX-ACCESS not-accessible
                        STATUS current
                        DESCRIPTION "COM-Port-Status"
                        ::= {  staCompCom 2 }

staCompComComportsEntry OBJECT-TYPE
                        SYNTAX StaCompComComportsEntry
                        MAX-ACCESS not-accessible
                        STATUS current
                        DESCRIPTION "entry in table"
                        INDEX { staCompComComportsDev, staCompComComportsPor }
                        ::= {  staCompComComportsTable 1 }

StaCompComComportsEntry ::= SEQUENCE {
                        staCompComComportsDev INTEGER,
                        staCompComComportsPor INTEGER,
                        staCompComComportsFul DisplayString,
                        staCompComComportsInt INTEGER,
                        staCompComComportsBit INTEGER,
                        staCompComComportsDat INTEGER,
                        staCompComComportsPar INTEGER,
                        staCompComComportsSto INTEGER,
                        staCompComComportsHan INTEGER
                       }

staCompComComportsDev OBJECT-TYPE
                      SYNTAX INTEGER
                      {
                        outband(1),
                        belkin-f5u103(33),
                        prolific-2303(34),
                        ftdi-8u232am(35)
                      }
                      MAX-ACCESS read-only
                      STATUS current
                      DESCRIPTION "Device-Type"
                      ::= {  staCompComComportsEntry 1 }

staCompComComportsPor OBJECT-TYPE
                      SYNTAX INTEGER (0..255)
                      MAX-ACCESS read-only
                      STATUS current
                      DESCRIPTION "Port-Number"
                      ::= {  staCompComComportsEntry 2 }

staCompComComportsFul OBJECT-TYPE
                      SYNTAX DisplayString (SIZE(0..255))
                      MAX-ACCESS read-only
                      STATUS current
                      DESCRIPTION "Full-Name"
                      ::= {  staCompComComportsEntry 99 }

staCompComComportsInt OBJECT-TYPE
                      SYNTAX INTEGER
                      {
                        not-present(0),
                        not-ready(1),
                        ready(2)
                      }
                      MAX-ACCESS read-only
                      STATUS current
                      DESCRIPTION "Interface-Status"
                      ::= {  staCompComComportsEntry 4 }

staCompComComportsBit OBJECT-TYPE
                      SYNTAX INTEGER
                      {
                        e110(110),
                        e300(300),
                        e600(600),
                        e1200(1200),
                        e2400(2400),
                        e4800(4800),
                        e9600(9600),
                        e19200(19200),
                        e38400(38400),
                        e57600(57600),
                        e115200(115200),
                        e125000(125000),
                        e230400(230400)
                      }
                      MAX-ACCESS read-only
                      STATUS current
                      DESCRIPTION "Bit-Rate"
                      ::= {  staCompComComportsEntry 5 }

staCompComComportsDat OBJECT-TYPE
                      SYNTAX INTEGER
                      {
                        e7(7),
                        e8(8)
                      }
                      MAX-ACCESS read-only
                      STATUS current
                      DESCRIPTION "Data-Bits"
                      ::= {  staCompComComportsEntry 6 }

staCompComComportsPar OBJECT-TYPE
                      SYNTAX INTEGER
                      {
                        none(1),
                        odd(2),
                        even(3)
                      }
                      MAX-ACCESS read-only
                      STATUS current
                      DESCRIPTION "Parity"
                      ::= {  staCompComComportsEntry 7 }

staCompComComportsSto OBJECT-TYPE
                      SYNTAX INTEGER
                      {
                        e1(1),
                        e2(2)
                      }
                      MAX-ACCESS read-only
                      STATUS current
                      DESCRIPTION "Stop-Bits"
                      ::= {  staCompComComportsEntry 8 }

staCompComComportsHan OBJECT-TYPE
                      SYNTAX INTEGER
                      {
                        none(0),
                        rts-cts(1)
                      }
                      MAX-ACCESS read-only
                      STATUS current
                      DESCRIPTION "Handshake"
                      ::= {  staCompComComportsEntry 9 }

staCompComBytecounTable OBJECT-TYPE
                        SYNTAX SEQUENCE OF StaCompComBytecounEntry
                        MAX-ACCESS not-accessible
                        STATUS current
                        DESCRIPTION "Byte-Counters"
                        ::= {  staCompCom 3 }

staCompComBytecounEntry OBJECT-TYPE
                        SYNTAX StaCompComBytecounEntry
                        MAX-ACCESS not-accessible
                        STATUS current
                        DESCRIPTION "entry in table"
                        INDEX { staCompComBytecounDevicety, staCompComBytecounPortnumb }
                        ::= {  staCompComBytecounTable 1 }

StaCompComBytecounEntry ::= SEQUENCE {
                        staCompComBytecounDevicety INTEGER,
                        staCompComBytecounPortnumb INTEGER,
                        staCompComBytecounFullname DisplayString,
                        staCompComBytecounSerialtx INTEGER,
                        staCompComBytecounSerialrx INTEGER,
                        staCompComBytecounNetworkt INTEGER,
                        staCompComBytecounNetworkr INTEGER
                       }

staCompComBytecounDevicety OBJECT-TYPE
                           SYNTAX INTEGER
                           {
                             outband(1),
                             belkin-f5u103(33),
                             prolific-2303(34),
                             ftdi-8u232am(35)
                           }
                           MAX-ACCESS read-only
                           STATUS current
                           DESCRIPTION "Device-Type"
                           ::= {  staCompComBytecounEntry 1 }

staCompComBytecounPortnumb OBJECT-TYPE
                           SYNTAX INTEGER (0..255)
                           MAX-ACCESS read-only
                           STATUS current
                           DESCRIPTION "Port-Number"
                           ::= {  staCompComBytecounEntry 2 }

staCompComBytecounFullname OBJECT-TYPE
                           SYNTAX DisplayString (SIZE(0..255))
                           MAX-ACCESS read-only
                           STATUS current
                           DESCRIPTION "Full-Name"
                           ::= {  staCompComBytecounEntry 99 }

staCompComBytecounSerialtx OBJECT-TYPE
                           SYNTAX INTEGER (0..2147483647)
                           MAX-ACCESS read-only
                           STATUS current
                           DESCRIPTION "Serial-Tx"
                           ::= {  staCompComBytecounEntry 4 }

staCompComBytecounSerialrx OBJECT-TYPE
                           SYNTAX INTEGER (0..2147483647)
                           MAX-ACCESS read-only
                           STATUS current
                           DESCRIPTION "Serial-Rx"
                           ::= {  staCompComBytecounEntry 5 }

staCompComBytecounNetworkt OBJECT-TYPE
                           SYNTAX INTEGER (0..2147483647)
                           MAX-ACCESS read-only
                           STATUS current
                           DESCRIPTION "Network-Tx"
                           ::= {  staCompComBytecounEntry 6 }

staCompComBytecounNetworkr OBJECT-TYPE
                           SYNTAX INTEGER (0..2147483647)
                           MAX-ACCESS read-only
                           STATUS current
                           DESCRIPTION "Network-Rx"
                           ::= {  staCompComBytecounEntry 7 }

staCompComComporteTable OBJECT-TYPE
                        SYNTAX SEQUENCE OF StaCompComComporteEntry
                        MAX-ACCESS not-accessible
                        STATUS current
                        DESCRIPTION "COM-Port-Errors"
                        ::= {  staCompCom 4 }

staCompComComporteEntry OBJECT-TYPE
                        SYNTAX StaCompComComporteEntry
                        MAX-ACCESS not-accessible
                        STATUS current
                        DESCRIPTION "entry in table"
                        INDEX { staCompComComporteDev, staCompComComportePor }
                        ::= {  staCompComComporteTable 1 }

StaCompComComporteEntry ::= SEQUENCE {
                        staCompComComporteDev INTEGER,
                        staCompComComportePor INTEGER,
                        staCompComComporteFul DisplayString,
                        staCompComComportePar INTEGER,
                        staCompComComporteFra INTEGER
                       }

staCompComComporteDev OBJECT-TYPE
                      SYNTAX INTEGER
                      {
                        outband(1),
                        belkin-f5u103(33),
                        prolific-2303(34),
                        ftdi-8u232am(35)
                      }
                      MAX-ACCESS read-only
                      STATUS current
                      DESCRIPTION "Device-Type"
                      ::= {  staCompComComporteEntry 1 }

staCompComComportePor OBJECT-TYPE
                      SYNTAX INTEGER (0..255)
                      MAX-ACCESS read-only
                      STATUS current
                      DESCRIPTION "Port-Number"
                      ::= {  staCompComComporteEntry 2 }

staCompComComporteFul OBJECT-TYPE
                      SYNTAX DisplayString (SIZE(0..255))
                      MAX-ACCESS read-only
                      STATUS current
                      DESCRIPTION "Full-Name"
                      ::= {  staCompComComporteEntry 99 }

staCompComComportePar OBJECT-TYPE
                      SYNTAX INTEGER (0..2147483647)
                      MAX-ACCESS read-only
                      STATUS current
                      DESCRIPTION "Parity-Errors"
                      ::= {  staCompComComporteEntry 4 }

staCompComComporteFra OBJECT-TYPE
                      SYNTAX INTEGER (0..2147483647)
                      MAX-ACCESS read-only
                      STATUS current
                      DESCRIPTION "Framing-Errors"
                      ::= {  staCompComComporteEntry 5 }

staCompComConnectiTable OBJECT-TYPE
                        SYNTAX SEQUENCE OF StaCompComConnectiEntry
                        MAX-ACCESS not-accessible
                        STATUS current
                        DESCRIPTION "Connections"
                        ::= {  staCompCom 5 }

staCompComConnectiEntry OBJECT-TYPE
                        SYNTAX StaCompComConnectiEntry
                        MAX-ACCESS not-accessible
                        STATUS current
                        DESCRIPTION "entry in table"
                        INDEX { staCompComConnectiDevicet, staCompComConnectiPortnum }
                        ::= {  staCompComConnectiTable 1 }

StaCompComConnectiEntry ::= SEQUENCE {
                        staCompComConnectiDevicet INTEGER,
                        staCompComConnectiPortnum INTEGER,
                        staCompComConnectiFullnam DisplayString,
                        staCompComConnectiServerg INTEGER,
                        staCompComConnectiServerr INTEGER,
                        staCompComConnectiClients INTEGER,
                        staCompComConnectiClientd INTEGER,
                        staCompComConnectiClientt INTEGER,
                        staCompComConnectiClientr INTEGER
                       }

staCompComConnectiDevicet OBJECT-TYPE
                          SYNTAX INTEGER
                          {
                            outband(1),
                            belkin-f5u103(33),
                            prolific-2303(34),
                            ftdi-8u232am(35)
                          }
                          MAX-ACCESS read-only
                          STATUS current
                          DESCRIPTION "Device-Type"
                          ::= {  staCompComConnectiEntry 1 }

staCompComConnectiPortnum OBJECT-TYPE
                          SYNTAX INTEGER (0..255)
                          MAX-ACCESS read-only
                          STATUS current
                          DESCRIPTION "Port-Number"
                          ::= {  staCompComConnectiEntry 2 }

staCompComConnectiFullnam OBJECT-TYPE
                          SYNTAX DisplayString (SIZE(0..255))
                          MAX-ACCESS read-only
                          STATUS current
                          DESCRIPTION "Full-Name"
                          ::= {  staCompComConnectiEntry 99 }

staCompComConnectiServerg OBJECT-TYPE
                          SYNTAX INTEGER (0..2147483647)
                          MAX-ACCESS read-only
                          STATUS current
                          DESCRIPTION "Server-Granted"
                          ::= {  staCompComConnectiEntry 4 }

staCompComConnectiServerr OBJECT-TYPE
                          SYNTAX INTEGER (0..2147483647)
                          MAX-ACCESS read-only
                          STATUS current
                          DESCRIPTION "Server-Rejected"
                          ::= {  staCompComConnectiEntry 5 }

staCompComConnectiClients OBJECT-TYPE
                          SYNTAX INTEGER (0..2147483647)
                          MAX-ACCESS read-only
                          STATUS current
                          DESCRIPTION "Client-Succeeded"
                          ::= {  staCompComConnectiEntry 6 }

staCompComConnectiClientd OBJECT-TYPE
                          SYNTAX INTEGER (0..2147483647)
                          MAX-ACCESS read-only
                          STATUS current
                          DESCRIPTION "Client-DNS-Error"
                          ::= {  staCompComConnectiEntry 7 }

staCompComConnectiClientt OBJECT-TYPE
                          SYNTAX INTEGER (0..2147483647)
                          MAX-ACCESS read-only
                          STATUS current
                          DESCRIPTION "Client-TCP-Error"
                          ::= {  staCompComConnectiEntry 8 }

staCompComConnectiClientr OBJECT-TYPE
                          SYNTAX INTEGER (0..2147483647)
                          MAX-ACCESS read-only
                          STATUS current
                          DESCRIPTION "Client-Remote-Disconnects"
                          ::= {  staCompComConnectiEntry 9 }

staCompComDeleteva OBJECT-TYPE
                   SYNTAX DisplayString
                   MAX-ACCESS read-write
                   STATUS current
                   DESCRIPTION "Delete-Values"
                   ::= {  staCompCom 99 }

staTaca OBJECT IDENTIFIER ::= { sta 69}
staTacaAuthe OBJECT-TYPE
             SYNTAX Counter32
             MAX-ACCESS read-only
             STATUS current
             DESCRIPTION "Authentication-Errors"
             ::= {  staTaca 1 }

staTacaAutho OBJECT-TYPE
             SYNTAX Counter32
             MAX-ACCESS read-only
             STATUS current
             DESCRIPTION "Authorisation-Errors"
             ::= {  staTaca 2 }

staTacaDelet OBJECT-TYPE
             SYNTAX DisplayString
             MAX-ACCESS read-write
             STATUS current
             DESCRIPTION "Delete-Values"
             ::= {  staTaca 3 }

staDele OBJECT-TYPE
        SYNTAX DisplayString
        MAX-ACCESS read-write
        STATUS current
        DESCRIPTION "Delete-Values"
        ::= {  sta 100 }

setName OBJECT-TYPE
        SYNTAX DisplayString (SIZE(0..16))
        MAX-ACCESS read-write
        STATUS current
        DESCRIPTION "Name"
        ::= {  set 1 }

setWan OBJECT IDENTIFIER ::= { set 2}
setWanDialuppTable OBJECT-TYPE
                   SYNTAX SEQUENCE OF SetWanDialuppEntry
                   MAX-ACCESS not-accessible
                   STATUS current
                   DESCRIPTION "Dialup-Peers"
                   ::= {  setWan 2 }

setWanDialuppEntry OBJECT-TYPE
                   SYNTAX SetWanDialuppEntry
                   MAX-ACCESS not-accessible
                   STATUS current
                   DESCRIPTION "entry in table"
                   INDEX { setWanDialuppPee }
                   ::= {  setWanDialuppTable 1 }

SetWanDialuppEntry ::= SEQUENCE {
                   setWanDialuppPee DisplayString,
                   setWanDialuppDia DisplayString,
                   setWanDialuppB1d INTEGER,
                   setWanDialuppB2d INTEGER,
                   setWanDialuppWan DisplayString,
                   setWanDialuppCal INTEGER
                  }

setWanDialuppPee OBJECT-TYPE
                 SYNTAX DisplayString (SIZE(0..16))
                 MAX-ACCESS read-write
                 STATUS current
                 DESCRIPTION "Peer"
                 ::= {  setWanDialuppEntry 1 }

setWanDialuppDia OBJECT-TYPE
                 SYNTAX DisplayString (SIZE(0..31))
                 MAX-ACCESS read-write
                 STATUS current
                 DESCRIPTION "Dialup-remote"
                 ::= {  setWanDialuppEntry 2 }

setWanDialuppB1d OBJECT-TYPE
                 SYNTAX INTEGER (0..65535)
                 MAX-ACCESS read-write
                 STATUS current
                 DESCRIPTION "B1-DT"
                 ::= {  setWanDialuppEntry 3 }

setWanDialuppB2d OBJECT-TYPE
                 SYNTAX INTEGER (0..65535)
                 MAX-ACCESS read-write
                 STATUS current
                 DESCRIPTION "B2-DT"
                 ::= {  setWanDialuppEntry 4 }

setWanDialuppWan OBJECT-TYPE
                 SYNTAX DisplayString (SIZE(0..9))
                 MAX-ACCESS read-write
                 STATUS current
                 DESCRIPTION "WAN-layer"
                 ::= {  setWanDialuppEntry 5 }

setWanDialuppCal OBJECT-TYPE
                 SYNTAX INTEGER
                 {
                   no(0),
                   auto(1),
                   name(5),
                   fast(9),
                   looser(2)
                 }
                 MAX-ACCESS read-write
                 STATUS current
                 DESCRIPTION "Callback"
                 ::= {  setWanDialuppEntry 6 }

setWanRoundroTable OBJECT-TYPE
                   SYNTAX SEQUENCE OF SetWanRoundroEntry
                   MAX-ACCESS not-accessible
                   STATUS current
                   DESCRIPTION "RoundRobin"
                   ::= {  setWan 3 }

setWanRoundroEntry OBJECT-TYPE
                   SYNTAX SetWanRoundroEntry
                   MAX-ACCESS not-accessible
                   STATUS current
                   DESCRIPTION "entry in table"
                   INDEX { setWanRoundroPee }
                   ::= {  setWanRoundroTable 1 }

SetWanRoundroEntry ::= SEQUENCE {
                   setWanRoundroPee DisplayString,
                   setWanRoundroRou DisplayString,
                   setWanRoundroHea INTEGER
                  }

setWanRoundroPee OBJECT-TYPE
                 SYNTAX DisplayString (SIZE(0..18))
                 MAX-ACCESS read-write
                 STATUS current
                 DESCRIPTION "Peer"
                 ::= {  setWanRoundroEntry 1 }

setWanRoundroRou OBJECT-TYPE
                 SYNTAX DisplayString (SIZE(0..53))
                 MAX-ACCESS read-write
                 STATUS current
                 DESCRIPTION "Round-Robin"
                 ::= {  setWanRoundroEntry 2 }

setWanRoundroHea OBJECT-TYPE
                 SYNTAX INTEGER
                 {
                   last(0),
                   first(1)
                 }
                 MAX-ACCESS read-write
                 STATUS current
                 DESCRIPTION "Head"
                 ::= {  setWanRoundroEntry 3 }

setWanLayerTable OBJECT-TYPE
                   SYNTAX SEQUENCE OF SetWanLayerEntry
                   MAX-ACCESS not-accessible
                   STATUS current
                   DESCRIPTION "Layer"
                   ::= {  setWan 4 }

setWanLayerEntry OBJECT-TYPE
                   SYNTAX SetWanLayerEntry
                   MAX-ACCESS not-accessible
                   STATUS current
                   DESCRIPTION "entry in table"
                   INDEX { setWanLayerWanl }
                   ::= {  setWanLayerTable 1 }

SetWanLayerEntry ::= SEQUENCE {
                   setWanLayerWanl DisplayString,
                   setWanLayerEnca INTEGER,
                   setWanLayerLay3 INTEGER,
                   setWanLayerLay2 INTEGER,
                   setWanLayerL2op INTEGER,
                   setWanLayerLay1 INTEGER
                  }

setWanLayerWanl OBJECT-TYPE
                SYNTAX DisplayString (SIZE(0..9))
                MAX-ACCESS read-write
                STATUS current
                DESCRIPTION "WAN-layer"
                ::= {  setWanLayerEntry 1 }

setWanLayerEnca OBJECT-TYPE
                SYNTAX INTEGER
                {
                  ether(0),
                  trans(255)
                }
                MAX-ACCESS read-write
                STATUS current
                DESCRIPTION "Encaps."
                ::= {  setWanLayerEntry 2 }

setWanLayerLay3 OBJECT-TYPE
                SYNTAX INTEGER
                {
                  ppp(4),
                  appp(5),
                  scppp(6),
                  scappp(7),
                  sctrans(8),
                  dhcp(9),
                  trans(255)
                }
                MAX-ACCESS read-write
                STATUS current
                DESCRIPTION "Lay-3"
                ::= {  setWanLayerEntry 3 }

setWanLayerLay2 OBJECT-TYPE
                SYNTAX INTEGER
                {
                  pppoe(5),
                  x-75lapb(0),
                  trans(1)
                }
                MAX-ACCESS read-write
                STATUS current
                DESCRIPTION "Lay-2"
                ::= {  setWanLayerEntry 4 }

setWanLayerL2op OBJECT-TYPE
                SYNTAX INTEGER
                {
                  none(255),
                  compr(0),
                  bundle(1),
                  bnd-plus-cmpr(2)
                }
                MAX-ACCESS read-write
                STATUS current
                DESCRIPTION "L2-Opt."
                ::= {  setWanLayerEntry 5 }

setWanLayerLay1 OBJECT-TYPE
                SYNTAX INTEGER
                {
                  eth(4),
                  hdlc64k(0),
                  hdlc56k(1),
                  v110-9k6(3),
                  v110-19k2(67),
                  v110-38k4(131),
                  serial(6)
                }
                MAX-ACCESS read-write
                STATUS current
                DESCRIPTION "Lay-1"
                ::= {  setWanLayerEntry 6 }

setWanPppTable OBJECT-TYPE
                   SYNTAX SEQUENCE OF SetWanPppEntry
                   MAX-ACCESS not-accessible
                   STATUS current
                   DESCRIPTION "PPP"
                   ::= {  setWan 5 }

setWanPppEntry OBJECT-TYPE
                   SYNTAX SetWanPppEntry
                   MAX-ACCESS not-accessible
                   STATUS current
                   DESCRIPTION "entry in table"
                   INDEX { setWanPppPeer }
                   ::= {  setWanPppTable 1 }

SetWanPppEntry ::= SEQUENCE {
                   setWanPppPeer DisplayString,
                   setWanPppAuthentreq BITS,
                   setWanPppAuthentres BITS,
                   setWanPppKey DisplayString,
                   setWanPppTime INTEGER,
                   setWanPppTry INTEGER,
                   setWanPppConf INTEGER,
                   setWanPppFail INTEGER,
                   setWanPppTerm INTEGER,
                   setWanPppUsername DisplayString,
                   setWanPppRights INTEGER
                  }

setWanPppPeer OBJECT-TYPE
                    SYNTAX DisplayString (SIZE(0..16))
                    MAX-ACCESS read-write
                    STATUS current
                    DESCRIPTION "Peer"
                    ::= {  setWanPppEntry 1 }

setWanPppAuthentreq OBJECT-TYPE
                    SYNTAX BITS
                    {
                      ms-chapv2(2),
                      ms-chap(3),
                      chap(4),
                      pap(5)
                    }
                    MAX-ACCESS read-write
                    STATUS current
                    DESCRIPTION "Authent.request"
                    ::= {  setWanPppEntry 2 }

setWanPppAuthentres OBJECT-TYPE
                    SYNTAX BITS
                    {
                      ms-chapv2(2),
                      ms-chap(3),
                      chap(4),
                      pap(5)
                    }
                    MAX-ACCESS read-write
                    STATUS current
                    DESCRIPTION "Authent-response"
                    ::= {  setWanPppEntry 11 }

setWanPppKey OBJECT-TYPE
                    SYNTAX DisplayString (SIZE(0..32))
                    MAX-ACCESS read-write
                    STATUS current
                    DESCRIPTION "Key"
                    ::= {  setWanPppEntry 3 }

setWanPppTime OBJECT-TYPE
                    SYNTAX INTEGER (0..255)
                    MAX-ACCESS read-write
                    STATUS current
                    DESCRIPTION "Time"
                    ::= {  setWanPppEntry 4 }

setWanPppTry OBJECT-TYPE
                    SYNTAX INTEGER (0..255)
                    MAX-ACCESS read-write
                    STATUS current
                    DESCRIPTION "Try"
                    ::= {  setWanPppEntry 5 }

setWanPppConf OBJECT-TYPE
                    SYNTAX INTEGER (0..255)
                    MAX-ACCESS read-write
                    STATUS current
                    DESCRIPTION "Conf"
                    ::= {  setWanPppEntry 7 }

setWanPppFail OBJECT-TYPE
                    SYNTAX INTEGER (0..255)
                    MAX-ACCESS read-write
                    STATUS current
                    DESCRIPTION "Fail"
                    ::= {  setWanPppEntry 8 }

setWanPppTerm OBJECT-TYPE
                    SYNTAX INTEGER (0..255)
                    MAX-ACCESS read-write
                    STATUS current
                    DESCRIPTION "Term"
                    ::= {  setWanPppEntry 9 }

setWanPppUsername OBJECT-TYPE
                    SYNTAX DisplayString (SIZE(0..64))
                    MAX-ACCESS read-write
                    STATUS current
                    DESCRIPTION "Username"
                    ::= {  setWanPppEntry 6 }

setWanPppRights OBJECT-TYPE
                    SYNTAX INTEGER
                    {
                      none(0),
                      ip(1),
                      ip-plus-nbt(3)
                    }
                    MAX-ACCESS read-write
                    STATUS current
                    DESCRIPTION "Rights"
                    ::= {  setWanPppEntry 10 }

setWanDslbroaTable OBJECT-TYPE
                   SYNTAX SEQUENCE OF SetWanDslbroaEntry
                   MAX-ACCESS not-accessible
                   STATUS current
                   DESCRIPTION "DSL-Broadband-Peers"
                   ::= {  setWan 19 }

setWanDslbroaEntry OBJECT-TYPE
                   SYNTAX SetWanDslbroaEntry
                   MAX-ACCESS not-accessible
                   STATUS current
                   DESCRIPTION "entry in table"
                   INDEX { setWanDslbroaPee }
                   ::= {  setWanDslbroaTable 1 }

SetWanDslbroaEntry ::= SEQUENCE {
                   setWanDslbroaPee DisplayString,
                   setWanDslbroaSht INTEGER,
                   setWanDslbroaAcn DisplayString,
                   setWanDslbroaSer DisplayString,
                   setWanDslbroaWan DisplayString,
                   setWanDslbroaMac INTEGER,
                   setWanDslbroaUse MacAddress,
                   setWanDslbroaDsl DisplayString,
                   setWanDslbroaVla INTEGER
                  }

setWanDslbroaPee OBJECT-TYPE
                 SYNTAX DisplayString (SIZE(0..16))
                 MAX-ACCESS read-write
                 STATUS current
                 DESCRIPTION "Peer"
                 ::= {  setWanDslbroaEntry 1 }

setWanDslbroaSht OBJECT-TYPE
                 SYNTAX INTEGER (0..65535)
                 MAX-ACCESS read-write
                 STATUS current
                 DESCRIPTION "SH-Time"
                 ::= {  setWanDslbroaEntry 2 }

setWanDslbroaAcn OBJECT-TYPE
                 SYNTAX DisplayString (SIZE(0..64))
                 MAX-ACCESS read-write
                 STATUS current
                 DESCRIPTION "AC-name"
                 ::= {  setWanDslbroaEntry 3 }

setWanDslbroaSer OBJECT-TYPE
                 SYNTAX DisplayString (SIZE(0..32))
                 MAX-ACCESS read-write
                 STATUS current
                 DESCRIPTION "Servicename"
                 ::= {  setWanDslbroaEntry 4 }

setWanDslbroaWan OBJECT-TYPE
                 SYNTAX DisplayString (SIZE(0..9))
                 MAX-ACCESS read-write
                 STATUS current
                 DESCRIPTION "WAN-layer"
                 ::= {  setWanDslbroaEntry 5 }

setWanDslbroaMac OBJECT-TYPE
                 SYNTAX INTEGER
                 {
                   global(1),
                   local(0),
                   user-def(2)
                 }
                 MAX-ACCESS read-write
                 STATUS current
                 DESCRIPTION "MAC-Type"
                 ::= {  setWanDslbroaEntry 15 }

setWanDslbroaUse OBJECT-TYPE
                 SYNTAX MacAddress
                 MAX-ACCESS read-write
                 STATUS current
                 DESCRIPTION "user-def.-MAC"
                 ::= {  setWanDslbroaEntry 13 }

setWanDslbroaDsl OBJECT-TYPE
                 SYNTAX DisplayString (SIZE(0..8))
                 MAX-ACCESS read-write
                 STATUS current
                 DESCRIPTION "DSL-ifc(s)"
                 ::= {  setWanDslbroaEntry 14 }

setWanDslbroaVla OBJECT-TYPE
                 SYNTAX INTEGER (0..65535)
                 MAX-ACCESS read-write
                 STATUS current
                 DESCRIPTION "VLAN-ID"
                 ::= {  setWanDslbroaEntry 16 }

setWanMtulistTable OBJECT-TYPE
                   SYNTAX SEQUENCE OF SetWanMtulistEntry
                   MAX-ACCESS not-accessible
                   STATUS current
                   DESCRIPTION "MTU-List"
                   ::= {  setWan 26 }

setWanMtulistEntry OBJECT-TYPE
                   SYNTAX SetWanMtulistEntry
                   MAX-ACCESS not-accessible
                   STATUS current
                   DESCRIPTION "entry in table"
                   INDEX { setWanMtulistPee }
                   ::= {  setWanMtulistTable 1 }

SetWanMtulistEntry ::= SEQUENCE {
                   setWanMtulistPee DisplayString,
                   setWanMtulistMtu INTEGER
                  }

setWanMtulistPee OBJECT-TYPE
                 SYNTAX DisplayString (SIZE(0..16))
                 MAX-ACCESS read-write
                 STATUS current
                 DESCRIPTION "Peer"
                 ::= {  setWanMtulistEntry 1 }

setWanMtulistMtu OBJECT-TYPE
                 SYNTAX INTEGER (0..65535)
                 MAX-ACCESS read-write
                 STATUS current
                 DESCRIPTION "MTU"
                 ::= {  setWanMtulistEntry 2 }

setWanIplistTable OBJECT-TYPE
                   SYNTAX SEQUENCE OF SetWanIplistEntry
                   MAX-ACCESS not-accessible
                   STATUS current
                   DESCRIPTION "IP-List"
                   ::= {  setWan 20 }

setWanIplistEntry OBJECT-TYPE
                   SYNTAX SetWanIplistEntry
                   MAX-ACCESS not-accessible
                   STATUS current
                   DESCRIPTION "entry in table"
                   INDEX { setWanIplistPeer }
                   ::= {  setWanIplistTable 1 }

SetWanIplistEntry ::= SEQUENCE {
                   setWanIplistPeer DisplayString,
                   setWanIplistIpadd IpAddress,
                   setWanIplistIpnet IpAddress,
                   setWanIplistMasqi IpAddress,
                   setWanIplistGatew IpAddress,
                   setWanIplistDnsde IpAddress,
                   setWanIplistDnsba IpAddress,
                   setWanIplistNbnsd IpAddress,
                   setWanIplistNbnsb IpAddress
                  }

setWanIplistPeer OBJECT-TYPE
                  SYNTAX DisplayString (SIZE(0..17))
                  MAX-ACCESS read-write
                  STATUS current
                  DESCRIPTION "Peer"
                  ::= {  setWanIplistEntry 1 }

setWanIplistIpadd OBJECT-TYPE
                  SYNTAX IpAddress
                  MAX-ACCESS read-write
                  STATUS current
                  DESCRIPTION "IP-Address"
                  ::= {  setWanIplistEntry 2 }

setWanIplistIpnet OBJECT-TYPE
                  SYNTAX IpAddress
                  MAX-ACCESS read-write
                  STATUS current
                  DESCRIPTION "IP-Netmask"
                  ::= {  setWanIplistEntry 3 }

setWanIplistMasqi OBJECT-TYPE
                  SYNTAX IpAddress
                  MAX-ACCESS read-write
                  STATUS current
                  DESCRIPTION "Masq.-IP-Addr."
                  ::= {  setWanIplistEntry 9 }

setWanIplistGatew OBJECT-TYPE
                  SYNTAX IpAddress
                  MAX-ACCESS read-write
                  STATUS current
                  DESCRIPTION "Gateway"
                  ::= {  setWanIplistEntry 4 }

setWanIplistDnsde OBJECT-TYPE
                  SYNTAX IpAddress
                  MAX-ACCESS read-write
                  STATUS current
                  DESCRIPTION "DNS-Default"
                  ::= {  setWanIplistEntry 5 }

setWanIplistDnsba OBJECT-TYPE
                  SYNTAX IpAddress
                  MAX-ACCESS read-write
                  STATUS current
                  DESCRIPTION "DNS-Backup"
                  ::= {  setWanIplistEntry 6 }

setWanIplistNbnsd OBJECT-TYPE
                  SYNTAX IpAddress
                  MAX-ACCESS read-write
                  STATUS current
                  DESCRIPTION "NBNS-Default"
                  ::= {  setWanIplistEntry 7 }

setWanIplistNbnsb OBJECT-TYPE
                  SYNTAX IpAddress
                  MAX-ACCESS read-write
                  STATUS current
                  DESCRIPTION "NBNS-Backup"
                  ::= {  setWanIplistEntry 8 }

setWanPptppeeTable OBJECT-TYPE
                   SYNTAX SEQUENCE OF SetWanPptppeeEntry
                   MAX-ACCESS not-accessible
                   STATUS current
                   DESCRIPTION "PPTP-Peers"
                   ::= {  setWan 21 }

setWanPptppeeEntry OBJECT-TYPE
                   SYNTAX SetWanPptppeeEntry
                   MAX-ACCESS not-accessible
                   STATUS current
                   DESCRIPTION "entry in table"
                   INDEX { setWanPptppeePee }
                   ::= {  setWanPptppeeTable 1 }

SetWanPptppeeEntry ::= SEQUENCE {
                   setWanPptppeePee DisplayString,
                   setWanPptppeeIpa IpAddress,
                   setWanPptppeeRtg INTEGER,
                   setWanPptppeePor INTEGER,
                   setWanPptppeeSht INTEGER
                  }

setWanPptppeePee OBJECT-TYPE
                 SYNTAX DisplayString (SIZE(0..16))
                 MAX-ACCESS read-write
                 STATUS current
                 DESCRIPTION "Peer"
                 ::= {  setWanPptppeeEntry 1 }

setWanPptppeeIpa OBJECT-TYPE
                 SYNTAX IpAddress
                 MAX-ACCESS read-write
                 STATUS current
                 DESCRIPTION "IP-Address"
                 ::= {  setWanPptppeeEntry 2 }

setWanPptppeeRtg OBJECT-TYPE
                 SYNTAX INTEGER (0..65535)
                 MAX-ACCESS read-write
                 STATUS current
                 DESCRIPTION "Rtg-tag"
                 ::= {  setWanPptppeeEntry 5 }

setWanPptppeePor OBJECT-TYPE
                 SYNTAX INTEGER (0..65535)
                 MAX-ACCESS read-write
                 STATUS current
                 DESCRIPTION "Port"
                 ::= {  setWanPptppeeEntry 3 }

setWanPptppeeSht OBJECT-TYPE
                 SYNTAX INTEGER (0..65535)
                 MAX-ACCESS read-write
                 STATUS current
                 DESCRIPTION "SH-Time"
                 ::= {  setWanPptppeeEntry 4 }

setWanRadius OBJECT IDENTIFIER ::= { setWan 22}
setWanRadiusOperat OBJECT-TYPE
                   SYNTAX INTEGER
                   {
                     no(0),
                     yes(1),
                     exclusive(2)
                   }
                   MAX-ACCESS read-write
                   STATUS current
                   DESCRIPTION "Operating"
                   ::= {  setWanRadius 1 }

setWanRadiusServer OBJECT-TYPE
                   SYNTAX IpAddress
                   MAX-ACCESS read-write
                   STATUS current
                   DESCRIPTION "Server-Address"
                   ::= {  setWanRadius 2 }

setWanRadiusAuthpo OBJECT-TYPE
                   SYNTAX INTEGER
                   MAX-ACCESS read-write
                   STATUS current
                   DESCRIPTION "Auth.-Port"
                   ::= {  setWanRadius 3 }

setWanRadiusLoopba OBJECT-TYPE
                   SYNTAX DisplayString (SIZE(0..16))
                   MAX-ACCESS read-write
                   STATUS current
                   DESCRIPTION "Loopback-Addr."
                   ::= {  setWanRadius 8 }

setWanRadiusProtoc OBJECT-TYPE
                   SYNTAX INTEGER
                   {
                     radius(0),
                     radsec(1)
                   }
                   MAX-ACCESS read-write
                   STATUS current
                   DESCRIPTION "Protocol"
                   ::= {  setWanRadius 9 }

setWanRadiusSecret OBJECT-TYPE
                   SYNTAX DisplayString (SIZE(0..31))
                   MAX-ACCESS read-write
                   STATUS current
                   DESCRIPTION "Secret"
                   ::= {  setWanRadius 4 }

setWanRadiusPppope OBJECT-TYPE
                   SYNTAX INTEGER
                   {
                     no(0),
                     yes(1),
                     exclusive(2)
                   }
                   MAX-ACCESS read-write
                   STATUS current
                   DESCRIPTION "PPP-Operation"
                   ::= {  setWanRadius 5 }

setWanRadiusAuthpr OBJECT-TYPE
                   SYNTAX BITS
                   {
                     ms-chapv2(2),
                     ms-chap(3),
                     chap(4),
                     pap(5)
                   }
                   MAX-ACCESS read-write
                   STATUS current
                   DESCRIPTION "Auth.-Protocols"
                   ::= {  setWanRadius 10 }

setWanRadiusClipop OBJECT-TYPE
                   SYNTAX INTEGER
                   {
                     no(0),
                     yes(1),
                     exclusive(2)
                   }
                   MAX-ACCESS read-write
                   STATUS current
                   DESCRIPTION "CLIP-Operation"
                   ::= {  setWanRadius 6 }

setWanRadiusClippa OBJECT-TYPE
                   SYNTAX DisplayString (SIZE(0..31))
                   MAX-ACCESS read-write
                   STATUS current
                   DESCRIPTION "CLIP-Password"
                   ::= {  setWanRadius 7 }

setWanPollingTable OBJECT-TYPE
                   SYNTAX SEQUENCE OF SetWanPollingEntry
                   MAX-ACCESS not-accessible
                   STATUS current
                   DESCRIPTION "Polling-Table"
                   ::= {  setWan 23 }

setWanPollingEntry OBJECT-TYPE
                   SYNTAX SetWanPollingEntry
                   MAX-ACCESS not-accessible
                   STATUS current
                   DESCRIPTION "entry in table"
                   INDEX { setWanPollingPeer }
                   ::= {  setWanPollingTable 1 }

SetWanPollingEntry ::= SEQUENCE {
                   setWanPollingPeer DisplayString,
                   setWanPollingIpaddress1 IpAddress,
                   setWanPollingIpaddress2 IpAddress,
                   setWanPollingIpaddress3 IpAddress,
                   setWanPollingIpaddress4 IpAddress,
                   setWanPollingTime INTEGER,
                   setWanPollingTry INTEGER,
                   setWanPollingLoopbackad DisplayString
                  }

setWanPollingPeer OBJECT-TYPE
                        SYNTAX DisplayString (SIZE(0..16))
                        MAX-ACCESS read-write
                        STATUS current
                        DESCRIPTION "Peer"
                        ::= {  setWanPollingEntry 1 }

setWanPollingIpaddress1 OBJECT-TYPE
                        SYNTAX IpAddress
                        MAX-ACCESS read-write
                        STATUS current
                        DESCRIPTION "IP-Address-1"
                        ::= {  setWanPollingEntry 2 }

setWanPollingIpaddress2 OBJECT-TYPE
                        SYNTAX IpAddress
                        MAX-ACCESS read-write
                        STATUS current
                        DESCRIPTION "IP-Address-2"
                        ::= {  setWanPollingEntry 5 }

setWanPollingIpaddress3 OBJECT-TYPE
                        SYNTAX IpAddress
                        MAX-ACCESS read-write
                        STATUS current
                        DESCRIPTION "IP-Address-3"
                        ::= {  setWanPollingEntry 6 }

setWanPollingIpaddress4 OBJECT-TYPE
                        SYNTAX IpAddress
                        MAX-ACCESS read-write
                        STATUS current
                        DESCRIPTION "IP-Address-4"
                        ::= {  setWanPollingEntry 7 }

setWanPollingTime OBJECT-TYPE
                        SYNTAX INTEGER (0..65535)
                        MAX-ACCESS read-write
                        STATUS current
                        DESCRIPTION "Time"
                        ::= {  setWanPollingEntry 3 }

setWanPollingTry OBJECT-TYPE
                        SYNTAX INTEGER (0..255)
                        MAX-ACCESS read-write
                        STATUS current
                        DESCRIPTION "Try"
                        ::= {  setWanPollingEntry 4 }

setWanPollingLoopbackad OBJECT-TYPE
                        SYNTAX DisplayString (SIZE(0..16))
                        MAX-ACCESS read-write
                        STATUS current
                        DESCRIPTION "Loopback-Addr."
                        ::= {  setWanPollingEntry 8 }

setWanBackuppTable OBJECT-TYPE
                   SYNTAX SEQUENCE OF SetWanBackuppEntry
                   MAX-ACCESS not-accessible
                   STATUS current
                   DESCRIPTION "Backup-Peers"
                   ::= {  setWan 24 }

setWanBackuppEntry OBJECT-TYPE
                   SYNTAX SetWanBackuppEntry
                   MAX-ACCESS not-accessible
                   STATUS current
                   DESCRIPTION "entry in table"
                   INDEX { setWanBackuppPee }
                   ::= {  setWanBackuppTable 1 }

SetWanBackuppEntry ::= SEQUENCE {
                   setWanBackuppPee DisplayString,
                   setWanBackuppAlt DisplayString,
                   setWanBackuppHea INTEGER
                  }

setWanBackuppPee OBJECT-TYPE
                 SYNTAX DisplayString (SIZE(0..18))
                 MAX-ACCESS read-write
                 STATUS current
                 DESCRIPTION "Peer"
                 ::= {  setWanBackuppEntry 1 }

setWanBackuppAlt OBJECT-TYPE
                 SYNTAX DisplayString (SIZE(0..53))
                 MAX-ACCESS read-write
                 STATUS current
                 DESCRIPTION "Alternative-Peers"
                 ::= {  setWanBackuppEntry 2 }

setWanBackuppHea OBJECT-TYPE
                 SYNTAX INTEGER
                 {
                   last(0),
                   first(1)
                 }
                 MAX-ACCESS read-write
                 STATUS current
                 DESCRIPTION "Head"
                 ::= {  setWanBackuppEntry 3 }

setWanActiontTable OBJECT-TYPE
                   SYNTAX SEQUENCE OF SetWanActiontEntry
                   MAX-ACCESS not-accessible
                   STATUS current
                   DESCRIPTION "Action-Table"
                   ::= {  setWan 25 }

setWanActiontEntry OBJECT-TYPE
                   SYNTAX SetWanActiontEntry
                   MAX-ACCESS not-accessible
                   STATUS current
                   DESCRIPTION "entry in table"
                   INDEX { setWanActiontIndex }
                   ::= {  setWanActiontTable 1 }

SetWanActiontEntry ::= SEQUENCE {
                   setWanActiontIndex INTEGER,
                   setWanActiontActiv INTEGER,
                   setWanActiontHostn DisplayString,
                   setWanActiontPeer DisplayString,
                   setWanActiontLockt INTEGER,
                   setWanActiontCondi INTEGER,
                   setWanActiontActio DisplayString,
                   setWanActiontCheck DisplayString,
                   setWanActiontOwner DisplayString
                  }

setWanActiontIndex OBJECT-TYPE
                   SYNTAX INTEGER (0..65535)
                   MAX-ACCESS read-write
                   STATUS current
                   DESCRIPTION "Index"
                   ::= {  setWanActiontEntry 1 }

setWanActiontActiv OBJECT-TYPE
                   SYNTAX INTEGER
                   {
                     yes(0),
                     no(1)
                   }
                   MAX-ACCESS read-write
                   STATUS current
                   DESCRIPTION "Active"
                   ::= {  setWanActiontEntry 8 }

setWanActiontHostn OBJECT-TYPE
                   SYNTAX DisplayString (SIZE(0..64))
                   MAX-ACCESS read-write
                   STATUS current
                   DESCRIPTION "Host-Name"
                   ::= {  setWanActiontEntry 2 }

setWanActiontPeer OBJECT-TYPE
                   SYNTAX DisplayString (SIZE(0..16))
                   MAX-ACCESS read-write
                   STATUS current
                   DESCRIPTION "Peer"
                   ::= {  setWanActiontEntry 3 }

setWanActiontLockt OBJECT-TYPE
                   SYNTAX INTEGER (0..2147483647)
                   MAX-ACCESS read-write
                   STATUS current
                   DESCRIPTION "Lock-Time"
                   ::= {  setWanActiontEntry 4 }

setWanActiontCondi OBJECT-TYPE
                   SYNTAX INTEGER
                   {
                     establish(0),
                     disconnect(1),
                     end(2),
                     failure(3),
                     establish-failure(4)
                   }
                   MAX-ACCESS read-write
                   STATUS current
                   DESCRIPTION "Condition"
                   ::= {  setWanActiontEntry 5 }

setWanActiontActio OBJECT-TYPE
                   SYNTAX DisplayString (SIZE(0..250))
                   MAX-ACCESS read-write
                   STATUS current
                   DESCRIPTION "Action"
                   ::= {  setWanActiontEntry 6 }

setWanActiontCheck OBJECT-TYPE
                   SYNTAX DisplayString (SIZE(0..50))
                   MAX-ACCESS read-write
                   STATUS current
                   DESCRIPTION "Check-For"
                   ::= {  setWanActiontEntry 7 }

setWanActiontOwner OBJECT-TYPE
                   SYNTAX DisplayString (SIZE(0..16))
                   MAX-ACCESS read-write
                   STATUS current
                   DESCRIPTION "Owner"
                   ::= {  setWanActiontEntry 9 }

setWanBackupd OBJECT-TYPE
              SYNTAX INTEGER
              MAX-ACCESS read-write
              STATUS current
              DESCRIPTION "Backup-Delay-Seconds"
              ::= {  setWan 18 }

setWanIncominTable OBJECT-TYPE
                   SYNTAX SEQUENCE OF SetWanIncominEntry
                   MAX-ACCESS not-accessible
                   STATUS current
                   DESCRIPTION "Incoming-Calling-Numbers"
                   ::= {  setWan 6 }

setWanIncominEntry OBJECT-TYPE
                   SYNTAX SetWanIncominEntry
                   MAX-ACCESS not-accessible
                   STATUS current
                   DESCRIPTION "entry in table"
                   INDEX { setWanIncominDia }
                   ::= {  setWanIncominTable 1 }

SetWanIncominEntry ::= SEQUENCE {
                   setWanIncominDia DisplayString,
                   setWanIncominPee DisplayString
                  }

setWanIncominDia OBJECT-TYPE
                 SYNTAX DisplayString (SIZE(0..31))
                 MAX-ACCESS read-write
                 STATUS current
                 DESCRIPTION "Dialup-remote"
                 ::= {  setWanIncominEntry 1 }

setWanIncominPee OBJECT-TYPE
                 SYNTAX DisplayString (SIZE(0..16))
                 MAX-ACCESS read-write
                 STATUS current
                 DESCRIPTION "Peer"
                 ::= {  setWanIncominEntry 2 }

setWanScriptsTable OBJECT-TYPE
                   SYNTAX SEQUENCE OF SetWanScriptsEntry
                   MAX-ACCESS not-accessible
                   STATUS current
                   DESCRIPTION "Scripts"
                   ::= {  setWan 8 }

setWanScriptsEntry OBJECT-TYPE
                   SYNTAX SetWanScriptsEntry
                   MAX-ACCESS not-accessible
                   STATUS current
                   DESCRIPTION "entry in table"
                   INDEX { setWanScriptsPee }
                   ::= {  setWanScriptsTable 1 }

SetWanScriptsEntry ::= SEQUENCE {
                   setWanScriptsPee DisplayString,
                   setWanScriptsScr DisplayString
                  }

setWanScriptsPee OBJECT-TYPE
                 SYNTAX DisplayString (SIZE(0..18))
                 MAX-ACCESS read-write
                 STATUS current
                 DESCRIPTION "Peer"
                 ::= {  setWanScriptsEntry 1 }

setWanScriptsScr OBJECT-TYPE
                 SYNTAX DisplayString (SIZE(0..58))
                 MAX-ACCESS read-write
                 STATUS current
                 DESCRIPTION "Script"
                 ::= {  setWanScriptsEntry 2 }

setWanProtect OBJECT-TYPE
              SYNTAX INTEGER
              {
                none(0),
                number(2),
                screened(4)
              }
              MAX-ACCESS read-write
              STATUS current
              DESCRIPTION "Protect"
              ::= {  setWan 9 }

setWanCallbac OBJECT-TYPE
              SYNTAX INTEGER
              MAX-ACCESS read-write
              STATUS current
              DESCRIPTION "Callback-Attempts"
              ::= {  setWan 10 }

setWanManuald OBJECT IDENTIFIER ::= { setWan 13}
setWanManualdCon OBJECT-TYPE
                 SYNTAX DisplayString
                 MAX-ACCESS read-write
                 STATUS current
                 DESCRIPTION "Connect"
                 ::= {  setWanManuald 1 }

setWanManualdDis OBJECT-TYPE
                 SYNTAX DisplayString
                 MAX-ACCESS read-write
                 STATUS current
                 DESCRIPTION "Disconnect"
                 ::= {  setWanManuald 2 }

setWanRouteriTable OBJECT-TYPE
                   SYNTAX SEQUENCE OF SetWanRouteriEntry
                   MAX-ACCESS not-accessible
                   STATUS current
                   DESCRIPTION "Router-Interface"
                   ::= {  setWan 11 }

setWanRouteriEntry OBJECT-TYPE
                   SYNTAX SetWanRouteriEntry
                   MAX-ACCESS not-accessible
                   STATUS current
                   DESCRIPTION "entry in table"
                   INDEX { setWanRouteriIfc }
                   ::= {  setWanRouteriTable 1 }

SetWanRouteriEntry ::= SEQUENCE {
                   setWanRouteriIfc INTEGER,
                   setWanRouteriMsn DisplayString,
                   setWanRouteriYc INTEGER,
                   setWanRouteriCli INTEGER,
                   setWanRouteriAcc INTEGER,
                   setWanRouteriTyp INTEGER
                  }

setWanRouteriIfc OBJECT-TYPE
                 SYNTAX INTEGER
                 {
                   dsl-1(1),
                   dsl-2(2),
                   dsl-3(3),
                   dsl-4(4),
                   s0-1(5),
                   ext(6)
                 }
                 MAX-ACCESS read-only
                 STATUS current
                 DESCRIPTION "Ifc"
                 ::= {  setWanRouteriEntry 1 }

setWanRouteriMsn OBJECT-TYPE
                 SYNTAX DisplayString (SIZE(0..30))
                 MAX-ACCESS read-write
                 STATUS current
                 DESCRIPTION "MSN/EAZ"
                 ::= {  setWanRouteriEntry 2 }

setWanRouteriYc OBJECT-TYPE
                 SYNTAX INTEGER
                 {
                   yes(0),
                   no(1)
                 }
                 MAX-ACCESS read-write
                 STATUS current
                 DESCRIPTION "YC."
                 ::= {  setWanRouteriEntry 8 }

setWanRouteriCli OBJECT-TYPE
                 SYNTAX INTEGER
                 {
                   yes(0),
                   no(1)
                 }
                 MAX-ACCESS read-write
                 STATUS current
                 DESCRIPTION "CLIP"
                 ::= {  setWanRouteriEntry 3 }

setWanRouteriAcc OBJECT-TYPE
                 SYNTAX INTEGER
                 {
                   all(0),
                   analog(2),
                   digital(1),
                   none(128)
                 }
                 MAX-ACCESS read-write
                 STATUS current
                 DESCRIPTION "Accept-calls"
                 ::= {  setWanRouteriEntry 9 }

setWanRouteriTyp OBJECT-TYPE
                 SYNTAX INTEGER (0..2147483647)
                 MAX-ACCESS read-only
                 STATUS current
                 DESCRIPTION "Type-of-interface"
                 ::= {  setWanRouteriEntry 10 }

setWanDialpre OBJECT-TYPE
              SYNTAX DisplayString (SIZE(0..8))
              MAX-ACCESS not-accessible
              STATUS current
              DESCRIPTION "Dial-Prefix"
              ::= {  setWan 7 }

setAcco OBJECT IDENTIFIER ::= { set 18}
setAccoOpe OBJECT-TYPE
           SYNTAX INTEGER
           {
             no(0),
             yes(1)
           }
           MAX-ACCESS read-write
           STATUS current
           DESCRIPTION "Operating"
           ::= {  setAcco 1 }

setAccoSav OBJECT-TYPE
           SYNTAX INTEGER
           {
             no(0),
             yes(1)
           }
           MAX-ACCESS read-write
           STATUS current
           DESCRIPTION "Save-to-Flashrom"
           ::= {  setAcco 2 }

setAccoDis OBJECT-TYPE
           SYNTAX INTEGER
           {
             mac-address(0),
             ip-address(1)
           }
           MAX-ACCESS read-write
           STATUS current
           DESCRIPTION "Discriminator"
           ::= {  setAcco 10 }

setAccoSor OBJECT-TYPE
           SYNTAX INTEGER
           {
             time(0),
             data(1)
           }
           MAX-ACCESS read-write
           STATUS current
           DESCRIPTION "Sort-by"
           ::= {  setAcco 3 }

setAccoCurTable OBJECT-TYPE
                SYNTAX SEQUENCE OF SetAccoCurEntry
                MAX-ACCESS not-accessible
                STATUS current
                DESCRIPTION "Current-User"
                ::= {  setAcco 4 }

setAccoCurEntry OBJECT-TYPE
                SYNTAX SetAccoCurEntry
                MAX-ACCESS not-accessible
                STATUS current
                DESCRIPTION "entry in table"
                INDEX { setAccoCurUsern, setAccoCurMacad, setAccoCurPeer, setAccoCurConnt }
                ::= {  setAccoCurTable 1 }

SetAccoCurEntry ::= SEQUENCE {
                setAccoCurUsern DisplayString,
                setAccoCurMacad DisplayString,
                setAccoCurPeer DisplayString,
                setAccoCurConnt INTEGER,
                setAccoCurRxkby INTEGER,
                setAccoCurTxkby INTEGER,
                setAccoCurTotal INTEGER,
                setAccoCurConne INTEGER
               }

setAccoCurUsern OBJECT-TYPE
                SYNTAX DisplayString (SIZE(0..28))
                MAX-ACCESS read-only
                STATUS current
                DESCRIPTION "Username"
                ::= {  setAccoCurEntry 1 }

setAccoCurMacad OBJECT-TYPE
                SYNTAX DisplayString (SIZE(0..255))
                MAX-ACCESS read-only
                STATUS current
                DESCRIPTION "MAC-Address"
                ::= {  setAccoCurEntry 2 }

setAccoCurPeer OBJECT-TYPE
                SYNTAX DisplayString (SIZE(0..31))
                MAX-ACCESS read-only
                STATUS current
                DESCRIPTION "Peer"
                ::= {  setAccoCurEntry 3 }

setAccoCurConnt OBJECT-TYPE
                SYNTAX INTEGER
                {
                  unknown(0),
                  dial-up(1),
                  leased-line(2),
                  dsl-line(4),
                  vpn-conn(7),
                  pptp-conn(8)
                }
                MAX-ACCESS read-only
                STATUS current
                DESCRIPTION "Conn.-Type"
                ::= {  setAccoCurEntry 4 }

setAccoCurRxkby OBJECT-TYPE
                SYNTAX INTEGER (0..2147483647)
                MAX-ACCESS read-only
                STATUS current
                DESCRIPTION "Rx-KBytes"
                ::= {  setAccoCurEntry 5 }

setAccoCurTxkby OBJECT-TYPE
                SYNTAX INTEGER (0..2147483647)
                MAX-ACCESS read-only
                STATUS current
                DESCRIPTION "Tx-KBytes"
                ::= {  setAccoCurEntry 6 }

setAccoCurTotal OBJECT-TYPE
                SYNTAX INTEGER (0..2147483647)
                MAX-ACCESS read-only
                STATUS current
                DESCRIPTION "Total-Time"
                ::= {  setAccoCurEntry 8 }

setAccoCurConne OBJECT-TYPE
                SYNTAX INTEGER (0..2147483647)
                MAX-ACCESS read-only
                STATUS current
                DESCRIPTION "Connections"
                ::= {  setAccoCurEntry 9 }

setAccoAccTable OBJECT-TYPE
                SYNTAX SEQUENCE OF SetAccoAccEntry
                MAX-ACCESS not-accessible
                STATUS current
                DESCRIPTION "Accounting-List"
                ::= {  setAcco 5 }

setAccoAccEntry OBJECT-TYPE
                SYNTAX SetAccoAccEntry
                MAX-ACCESS not-accessible
                STATUS current
                DESCRIPTION "entry in table"
                INDEX { setAccoAccUsern, setAccoAccMacad, setAccoAccPeer, setAccoAccConnt }
                ::= {  setAccoAccTable 1 }

SetAccoAccEntry ::= SEQUENCE {
                setAccoAccUsern DisplayString,
                setAccoAccMacad DisplayString,
                setAccoAccPeer DisplayString,
                setAccoAccConnt INTEGER,
                setAccoAccRxkby INTEGER,
                setAccoAccTxkby INTEGER,
                setAccoAccTotal INTEGER,
                setAccoAccConne INTEGER
               }

setAccoAccUsern OBJECT-TYPE
                SYNTAX DisplayString (SIZE(0..28))
                MAX-ACCESS read-only
                STATUS current
                DESCRIPTION "Username"
                ::= {  setAccoAccEntry 1 }

setAccoAccMacad OBJECT-TYPE
                SYNTAX DisplayString (SIZE(0..255))
                MAX-ACCESS read-only
                STATUS current
                DESCRIPTION "MAC-Address"
                ::= {  setAccoAccEntry 2 }

setAccoAccPeer OBJECT-TYPE
                SYNTAX DisplayString (SIZE(0..31))
                MAX-ACCESS read-only
                STATUS current
                DESCRIPTION "Peer"
                ::= {  setAccoAccEntry 3 }

setAccoAccConnt OBJECT-TYPE
                SYNTAX INTEGER
                {
                  unknown(0),
                  dial-up(1),
                  leased-line(2),
                  dsl-line(4),
                  vpn-conn(7),
                  pptp-conn(8)
                }
                MAX-ACCESS read-only
                STATUS current
                DESCRIPTION "Conn.-Type"
                ::= {  setAccoAccEntry 4 }

setAccoAccRxkby OBJECT-TYPE
                SYNTAX INTEGER (0..2147483647)
                MAX-ACCESS read-only
                STATUS current
                DESCRIPTION "Rx-KBytes"
                ::= {  setAccoAccEntry 5 }

setAccoAccTxkby OBJECT-TYPE
                SYNTAX INTEGER (0..2147483647)
                MAX-ACCESS read-only
                STATUS current
                DESCRIPTION "Tx-KBytes"
                ::= {  setAccoAccEntry 6 }

setAccoAccTotal OBJECT-TYPE
                SYNTAX INTEGER (0..2147483647)
                MAX-ACCESS read-only
                STATUS current
                DESCRIPTION "Total-Time"
                ::= {  setAccoAccEntry 8 }

setAccoAccConne OBJECT-TYPE
                SYNTAX INTEGER (0..2147483647)
                MAX-ACCESS read-only
                STATUS current
                DESCRIPTION "Connections"
                ::= {  setAccoAccEntry 9 }

setAccoDel OBJECT-TYPE
           SYNTAX DisplayString
           MAX-ACCESS read-write
           STATUS current
           DESCRIPTION "Delete-Accounting-List"
           ::= {  setAcco 6 }

setAccoTimTable OBJECT-TYPE
                SYNTAX SEQUENCE OF SetAccoTimEntry
                MAX-ACCESS not-accessible
                STATUS current
                DESCRIPTION "Time-Snapshot"
                ::= {  setAcco 8 }

setAccoTimEntry OBJECT-TYPE
                SYNTAX SetAccoTimEntry
                MAX-ACCESS not-accessible
                STATUS current
                DESCRIPTION "entry in table"
                INDEX { setAccoTimInde }
                ::= {  setAccoTimTable 1 }

SetAccoTimEntry ::= SEQUENCE {
                setAccoTimInde INTEGER,
                setAccoTimActi INTEGER,
                setAccoTimType INTEGER,
                setAccoTimDay INTEGER,
                setAccoTimDayo INTEGER,
                setAccoTimHour INTEGER,
                setAccoTimMinu INTEGER
               }

setAccoTimInde OBJECT-TYPE
               SYNTAX INTEGER (0..255)
               MAX-ACCESS read-only
               STATUS current
               DESCRIPTION "Index"
               ::= {  setAccoTimEntry 1 }

setAccoTimActi OBJECT-TYPE
               SYNTAX INTEGER
               {
                 yes(1),
                 no(0)
               }
               MAX-ACCESS read-write
               STATUS current
               DESCRIPTION "Active"
               ::= {  setAccoTimEntry 2 }

setAccoTimType OBJECT-TYPE
               SYNTAX INTEGER
               {
                 monthly(0),
                 weekly(1),
                 daily(2)
               }
               MAX-ACCESS read-write
               STATUS current
               DESCRIPTION "Type"
               ::= {  setAccoTimEntry 3 }

setAccoTimDay OBJECT-TYPE
               SYNTAX INTEGER (0..255)
               MAX-ACCESS read-write
               STATUS current
               DESCRIPTION "Day"
               ::= {  setAccoTimEntry 4 }

setAccoTimDayo OBJECT-TYPE
               SYNTAX INTEGER
               {
                 unknown(0),
                 sunday(1),
                 monday(2),
                 tuesday(3),
                 wednesday(4),
                 thursday(5),
                 friday(6),
                 saturday(7)
               }
               MAX-ACCESS read-write
               STATUS current
               DESCRIPTION "DayOfWeek"
               ::= {  setAccoTimEntry 5 }

setAccoTimHour OBJECT-TYPE
               SYNTAX INTEGER (0..255)
               MAX-ACCESS read-write
               STATUS current
               DESCRIPTION "Hour"
               ::= {  setAccoTimEntry 6 }

setAccoTimMinu OBJECT-TYPE
               SYNTAX INTEGER (0..255)
               MAX-ACCESS read-write
               STATUS current
               DESCRIPTION "Minute"
               ::= {  setAccoTimEntry 7 }

setAccoLasTable OBJECT-TYPE
                SYNTAX SEQUENCE OF SetAccoLasEntry
                MAX-ACCESS not-accessible
                STATUS current
                DESCRIPTION "Last-Snapshot"
                ::= {  setAcco 9 }

setAccoLasEntry OBJECT-TYPE
                SYNTAX SetAccoLasEntry
                MAX-ACCESS not-accessible
                STATUS current
                DESCRIPTION "entry in table"
                INDEX { setAccoLasUsern, setAccoLasMacad, setAccoLasPeer, setAccoLasConnt }
                ::= {  setAccoLasTable 1 }

SetAccoLasEntry ::= SEQUENCE {
                setAccoLasUsern DisplayString,
                setAccoLasMacad DisplayString,
                setAccoLasPeer DisplayString,
                setAccoLasConnt INTEGER,
                setAccoLasRxkby INTEGER,
                setAccoLasTxkby INTEGER,
                setAccoLasTotal INTEGER,
                setAccoLasConne INTEGER
               }

setAccoLasUsern OBJECT-TYPE
                SYNTAX DisplayString (SIZE(0..28))
                MAX-ACCESS read-only
                STATUS current
                DESCRIPTION "Username"
                ::= {  setAccoLasEntry 1 }

setAccoLasMacad OBJECT-TYPE
                SYNTAX DisplayString (SIZE(0..255))
                MAX-ACCESS read-only
                STATUS current
                DESCRIPTION "MAC-Address"
                ::= {  setAccoLasEntry 2 }

setAccoLasPeer OBJECT-TYPE
                SYNTAX DisplayString (SIZE(0..31))
                MAX-ACCESS read-only
                STATUS current
                DESCRIPTION "Peer"
                ::= {  setAccoLasEntry 3 }

setAccoLasConnt OBJECT-TYPE
                SYNTAX INTEGER
                {
                  unknown(0),
                  dial-up(1),
                  leased-line(2),
                  dsl-line(4),
                  vpn-conn(7),
                  pptp-conn(8)
                }
                MAX-ACCESS read-only
                STATUS current
                DESCRIPTION "Conn.-Type"
                ::= {  setAccoLasEntry 4 }

setAccoLasRxkby OBJECT-TYPE
                SYNTAX INTEGER (0..2147483647)
                MAX-ACCESS read-only
                STATUS current
                DESCRIPTION "Rx-KBytes"
                ::= {  setAccoLasEntry 5 }

setAccoLasTxkby OBJECT-TYPE
                SYNTAX INTEGER (0..2147483647)
                MAX-ACCESS read-only
                STATUS current
                DESCRIPTION "Tx-KBytes"
                ::= {  setAccoLasEntry 6 }

setAccoLasTotal OBJECT-TYPE
                SYNTAX INTEGER (0..2147483647)
                MAX-ACCESS read-only
                STATUS current
                DESCRIPTION "Total-Time"
                ::= {  setAccoLasEntry 8 }

setAccoLasConne OBJECT-TYPE
                SYNTAX INTEGER (0..2147483647)
                MAX-ACCESS read-only
                STATUS current
                DESCRIPTION "Connections"
                ::= {  setAccoLasEntry 9 }

setChar OBJECT IDENTIFIER ::= { set 3}
setCharDaysper OBJECT-TYPE
               SYNTAX INTEGER
               MAX-ACCESS read-write
               STATUS current
               DESCRIPTION "Days-per-Period"
               ::= {  setChar 2 }

setCharBudgetu OBJECT-TYPE
               SYNTAX INTEGER
               MAX-ACCESS read-write
               STATUS current
               DESCRIPTION "Budget-Units"
               ::= {  setChar 1 }

setCharSpareun OBJECT-TYPE
               SYNTAX INTEGER
               MAX-ACCESS read-only
               STATUS current
               DESCRIPTION "Spare-Units"
               ::= {  setChar 3 }

setCharRouteru OBJECT-TYPE
               SYNTAX INTEGER
               MAX-ACCESS read-only
               STATUS current
               DESCRIPTION "Router-Units"
               ::= {  setChar 4 }

setCharTotalun OBJECT-TYPE
               SYNTAX INTEGER
               MAX-ACCESS read-only
               STATUS current
               DESCRIPTION "Total-Units"
               ::= {  setChar 6 }

setCharTablebuTable OBJECT-TYPE
                    SYNTAX SEQUENCE OF SetCharTablebuEntry
                    MAX-ACCESS not-accessible
                    STATUS current
                    DESCRIPTION "Table-Budget"
                    ::= {  setChar 5 }

setCharTablebuEntry OBJECT-TYPE
                    SYNTAX SetCharTablebuEntry
                    MAX-ACCESS not-accessible
                    STATUS current
                    DESCRIPTION "entry in table"
                    INDEX { setCharTablebuIfc }
                    ::= {  setCharTablebuTable 1 }

SetCharTablebuEntry ::= SEQUENCE {
                    setCharTablebuIfc INTEGER,
                    setCharTablebuBud INTEGER,
                    setCharTablebuSpa INTEGER,
                    setCharTablebuTot INTEGER
                   }

setCharTablebuIfc OBJECT-TYPE
                  SYNTAX INTEGER
                  {
                    router-isdn-serial(1),
                    lancapi(2),
                    ab-1(3),
                    ab-2(4),
                    ab-3(5),
                    ab-4(6),
                    time-modul(255)
                  }
                  MAX-ACCESS read-only
                  STATUS current
                  DESCRIPTION "Ifc"
                  ::= {  setCharTablebuEntry 1 }

setCharTablebuBud OBJECT-TYPE
                  SYNTAX INTEGER (0..65535)
                  MAX-ACCESS read-only
                  STATUS current
                  DESCRIPTION "Budget-units"
                  ::= {  setCharTablebuEntry 2 }

setCharTablebuSpa OBJECT-TYPE
                  SYNTAX INTEGER (0..65535)
                  MAX-ACCESS read-only
                  STATUS current
                  DESCRIPTION "Spare-Budget"
                  ::= {  setCharTablebuEntry 3 }

setCharTablebuTot OBJECT-TYPE
                  SYNTAX INTEGER (0..2147483647)
                  MAX-ACCESS read-only
                  STATUS current
                  DESCRIPTION "Total-units"
                  ::= {  setCharTablebuEntry 4 }

setCharDialupm OBJECT-TYPE
               SYNTAX INTEGER
               MAX-ACCESS read-write
               STATUS current
               DESCRIPTION "Dialup-Minutes-Budget"
               ::= {  setChar 13 }

setCharSparedi OBJECT-TYPE
               SYNTAX INTEGER
               MAX-ACCESS read-only
               STATUS current
               DESCRIPTION "Spare-Dialup-Minutes"
               ::= {  setChar 14 }

setCharRouteri OBJECT-TYPE
               SYNTAX INTEGER
               MAX-ACCESS read-only
               STATUS current
               DESCRIPTION "Router-ISDN-Serial-Minutes-Active"
               ::= {  setChar 15 }

setCharTimetabTable OBJECT-TYPE
                    SYNTAX SEQUENCE OF SetCharTimetabEntry
                    MAX-ACCESS not-accessible
                    STATUS current
                    DESCRIPTION "Time-Table"
                    ::= {  setChar 7 }

setCharTimetabEntry OBJECT-TYPE
                    SYNTAX SetCharTimetabEntry
                    MAX-ACCESS not-accessible
                    STATUS current
                    DESCRIPTION "entry in table"
                    INDEX { setCharTimetabIfc }
                    ::= {  setCharTimetabTable 1 }

SetCharTimetabEntry ::= SEQUENCE {
                    setCharTimetabIfc INTEGER,
                    setCharTimetabBudgetmi INTEGER,
                    setCharTimetabSparemin INTEGER,
                    setCharTimetabMinutesa INTEGER,
                    setCharTimetabMinutesp INTEGER
                   }

setCharTimetabIfc OBJECT-TYPE
                       SYNTAX INTEGER
                       {
                         router-dsl-broadband(1),
                         router-isdn-serial(2),
                         lancapi(3),
                         ab-1(4),
                         ab-2(5),
                         ab-3(6),
                         ab-4(7),
                         time-modul(255)
                       }
                       MAX-ACCESS read-only
                       STATUS current
                       DESCRIPTION "Ifc"
                       ::= {  setCharTimetabEntry 1 }

setCharTimetabBudgetmi OBJECT-TYPE
                       SYNTAX INTEGER (0..2147483647)
                       MAX-ACCESS read-only
                       STATUS current
                       DESCRIPTION "Budget-minutes"
                       ::= {  setCharTimetabEntry 2 }

setCharTimetabSparemin OBJECT-TYPE
                       SYNTAX INTEGER (0..2147483647)
                       MAX-ACCESS read-only
                       STATUS current
                       DESCRIPTION "Spare-minutes"
                       ::= {  setCharTimetabEntry 3 }

setCharTimetabMinutesa OBJECT-TYPE
                       SYNTAX INTEGER (0..2147483647)
                       MAX-ACCESS read-only
                       STATUS current
                       DESCRIPTION "Minutes-active"
                       ::= {  setCharTimetabEntry 4 }

setCharTimetabMinutesp OBJECT-TYPE
                       SYNTAX INTEGER (0..2147483647)
                       MAX-ACCESS read-only
                       STATUS current
                       DESCRIPTION "Minutes-passive"
                       ::= {  setCharTimetabEntry 5 }

setCharDslbroa OBJECT-TYPE
               SYNTAX INTEGER
               MAX-ACCESS read-write
               STATUS current
               DESCRIPTION "DSL-Broadband-Minutes-Budget"
               ::= {  setChar 8 }

setCharAdditio OBJECT-TYPE
               SYNTAX INTEGER
               MAX-ACCESS read-write
               STATUS current
               DESCRIPTION "Additional-DSL-Broadband-Budget"
               ::= {  setChar 11 }

setCharSpareds OBJECT-TYPE
               SYNTAX INTEGER
               MAX-ACCESS read-only
               STATUS current
               DESCRIPTION "Spare-DSL-Broadband-Minutes"
               ::= {  setChar 9 }

setCharRouterd OBJECT-TYPE
               SYNTAX INTEGER
               MAX-ACCESS read-only
               STATUS current
               DESCRIPTION "Router-DSL-Broadband-Minutes-Active"
               ::= {  setChar 10 }

setCharActivat OBJECT-TYPE
               SYNTAX DisplayString
               MAX-ACCESS read-write
               STATUS current
               DESCRIPTION "Activate-Additional-Budget"
               ::= {  setChar 12 }

setCharResetbu OBJECT-TYPE
               SYNTAX DisplayString
               MAX-ACCESS read-write
               STATUS current
               DESCRIPTION "Reset-Budgets"
               ::= {  setChar 16 }

setLan OBJECT IDENTIFIER ::= { set 4}
setLanMacadd OBJECT-TYPE
             SYNTAX MacAddress
             MAX-ACCESS read-only
             STATUS current
             DESCRIPTION "MAC-Address"
             ::= {  setLan 2 }

setLanSpareh OBJECT-TYPE
             SYNTAX INTEGER
             MAX-ACCESS read-write
             STATUS current
             DESCRIPTION "Spare-Heap"
             ::= {  setLan 3 }

setLanTracem OBJECT-TYPE
             SYNTAX MacAddress
             MAX-ACCESS read-write
             STATUS current
             DESCRIPTION "Trace-MAC"
             ::= {  setLan 8 }

setLanTracel OBJECT-TYPE
             SYNTAX INTEGER
             MAX-ACCESS read-write
             STATUS current
             DESCRIPTION "Trace-Level"
             ::= {  setLan 9 }

setTcpi OBJECT IDENTIFIER ::= { set 7}
setTcpiOpera OBJECT-TYPE
             SYNTAX INTEGER
             {
               no(0),
               yes(1)
             }
             MAX-ACCESS read-write
             STATUS current
             DESCRIPTION "Operating"
             ::= {  setTcpi 1 }

setTcpiNetwoTable OBJECT-TYPE
                  SYNTAX SEQUENCE OF SetTcpiNetwoEntry
                  MAX-ACCESS not-accessible
                  STATUS current
                  DESCRIPTION "Network-list"
                  ::= {  setTcpi 30 }

setTcpiNetwoEntry OBJECT-TYPE
                  SYNTAX SetTcpiNetwoEntry
                  MAX-ACCESS not-accessible
                  STATUS current
                  DESCRIPTION "entry in table"
                  INDEX { setTcpiNetwoNet }
                  ::= {  setTcpiNetwoTable 1 }

SetTcpiNetwoEntry ::= SEQUENCE {
                  setTcpiNetwoNet DisplayString,
                  setTcpiNetwoIpa IpAddress,
                  setTcpiNetwoIpn IpAddress,
                  setTcpiNetwoVla INTEGER,
                  setTcpiNetwoInt INTEGER,
                  setTcpiNetwoSrc INTEGER,
                  setTcpiNetwoTyp INTEGER,
                  setTcpiNetwoRtg INTEGER,
                  setTcpiNetwoCom DisplayString
                 }

setTcpiNetwoNet OBJECT-TYPE
                SYNTAX DisplayString (SIZE(0..17))
                MAX-ACCESS read-write
                STATUS current
                DESCRIPTION "Network-name"
                ::= {  setTcpiNetwoEntry 1 }

setTcpiNetwoIpa OBJECT-TYPE
                SYNTAX IpAddress
                MAX-ACCESS read-write
                STATUS current
                DESCRIPTION "IP-Address"
                ::= {  setTcpiNetwoEntry 2 }

setTcpiNetwoIpn OBJECT-TYPE
                SYNTAX IpAddress
                MAX-ACCESS read-write
                STATUS current
                DESCRIPTION "IP-Netmask"
                ::= {  setTcpiNetwoEntry 3 }

setTcpiNetwoVla OBJECT-TYPE
                SYNTAX INTEGER (0..65535)
                MAX-ACCESS read-write
                STATUS current
                DESCRIPTION "VLAN-ID"
                ::= {  setTcpiNetwoEntry 4 }

setTcpiNetwoInt OBJECT-TYPE
                SYNTAX INTEGER
                {
                  lan-1(256),
                  lan-2(257),
                  lan-3(258),
                  lan-4(259),
                  any(65535)
                }
                MAX-ACCESS read-write
                STATUS current
                DESCRIPTION "Interface"
                ::= {  setTcpiNetwoEntry 5 }

setTcpiNetwoSrc OBJECT-TYPE
                SYNTAX INTEGER
                {
                  strict(1),
                  loose(0)
                }
                MAX-ACCESS read-write
                STATUS current
                DESCRIPTION "Src-check"
                ::= {  setTcpiNetwoEntry 6 }

setTcpiNetwoTyp OBJECT-TYPE
                SYNTAX INTEGER
                {
                  disabled(0),
                  intranet(1),
                  dmz(2)
                }
                MAX-ACCESS read-write
                STATUS current
                DESCRIPTION "Type"
                ::= {  setTcpiNetwoEntry 7 }

setTcpiNetwoRtg OBJECT-TYPE
                SYNTAX INTEGER (0..65535)
                MAX-ACCESS read-write
                STATUS current
                DESCRIPTION "Rtg-tag"
                ::= {  setTcpiNetwoEntry 8 }

setTcpiNetwoCom OBJECT-TYPE
                SYNTAX DisplayString (SIZE(0..64))
                MAX-ACCESS read-write
                STATUS current
                DESCRIPTION "Comment"
                ::= {  setTcpiNetwoEntry 9 }

setTcpiLoopbTable OBJECT-TYPE
                  SYNTAX SEQUENCE OF SetTcpiLoopbEntry
                  MAX-ACCESS not-accessible
                  STATUS current
                  DESCRIPTION "Loopback-List"
                  ::= {  setTcpi 17 }

setTcpiLoopbEntry OBJECT-TYPE
                  SYNTAX SetTcpiLoopbEntry
                  MAX-ACCESS not-accessible
                  STATUS current
                  DESCRIPTION "entry in table"
                  INDEX { setTcpiLoopbNam }
                  ::= {  setTcpiLoopbTable 1 }

SetTcpiLoopbEntry ::= SEQUENCE {
                  setTcpiLoopbNam DisplayString,
                  setTcpiLoopbLoo IpAddress,
                  setTcpiLoopbRtg INTEGER
                 }

setTcpiLoopbNam OBJECT-TYPE
                SYNTAX DisplayString (SIZE(0..16))
                MAX-ACCESS read-write
                STATUS current
                DESCRIPTION "Name"
                ::= {  setTcpiLoopbEntry 2 }

setTcpiLoopbLoo OBJECT-TYPE
                SYNTAX IpAddress
                MAX-ACCESS read-write
                STATUS current
                DESCRIPTION "Loopback-Addr."
                ::= {  setTcpiLoopbEntry 1 }

setTcpiLoopbRtg OBJECT-TYPE
                SYNTAX INTEGER (0..65535)
                MAX-ACCESS read-write
                STATUS current
                DESCRIPTION "Rtg-tag"
                ::= {  setTcpiLoopbEntry 3 }

setTcpiAccesTable OBJECT-TYPE
                  SYNTAX SEQUENCE OF SetTcpiAccesEntry
                  MAX-ACCESS not-accessible
                  STATUS current
                  DESCRIPTION "Access-List"
                  ::= {  setTcpi 6 }

setTcpiAccesEntry OBJECT-TYPE
                  SYNTAX SetTcpiAccesEntry
                  MAX-ACCESS not-accessible
                  STATUS current
                  DESCRIPTION "entry in table"
                  INDEX { setTcpiAccesIpa, setTcpiAccesIpn, setTcpiAccesRtg }
                  ::= {  setTcpiAccesTable 1 }

SetTcpiAccesEntry ::= SEQUENCE {
                  setTcpiAccesIpa IpAddress,
                  setTcpiAccesIpn IpAddress,
                  setTcpiAccesRtg INTEGER
                 }

setTcpiAccesIpa OBJECT-TYPE
                SYNTAX IpAddress
                MAX-ACCESS read-write
                STATUS current
                DESCRIPTION "IP-Address"
                ::= {  setTcpiAccesEntry 1 }

setTcpiAccesIpn OBJECT-TYPE
                SYNTAX IpAddress
                MAX-ACCESS read-write
                STATUS current
                DESCRIPTION "IP-Netmask"
                ::= {  setTcpiAccesEntry 2 }

setTcpiAccesRtg OBJECT-TYPE
                SYNTAX INTEGER (0..65535)
                MAX-ACCESS read-write
                STATUS current
                DESCRIPTION "Rtg-tag"
                ::= {  setTcpiAccesEntry 3 }

setTcpiDnsde OBJECT-TYPE
             SYNTAX IpAddress
             MAX-ACCESS read-write
             STATUS current
             DESCRIPTION "DNS-Default"
             ::= {  setTcpi 7 }

setTcpiDnsba OBJECT-TYPE
             SYNTAX IpAddress
             MAX-ACCESS read-write
             STATUS current
             DESCRIPTION "DNS-Backup"
             ::= {  setTcpi 8 }

setTcpiNbnsd OBJECT-TYPE
             SYNTAX IpAddress
             MAX-ACCESS read-write
             STATUS current
             DESCRIPTION "NBNS-Default"
             ::= {  setTcpi 9 }

setTcpiNbnsb OBJECT-TYPE
             SYNTAX IpAddress
             MAX-ACCESS read-write
             STATUS current
             DESCRIPTION "NBNS-Backup"
             ::= {  setTcpi 10 }

setTcpiArptaTable OBJECT-TYPE
                  SYNTAX SEQUENCE OF SetTcpiArptaEntry
                  MAX-ACCESS not-accessible
                  STATUS current
                  DESCRIPTION "ARP-Table"
                  ::= {  setTcpi 16 }

setTcpiArptaEntry OBJECT-TYPE
                  SYNTAX SetTcpiArptaEntry
                  MAX-ACCESS not-accessible
                  STATUS current
                  DESCRIPTION "entry in table"
                  INDEX { setTcpiArptaIpa }
                  ::= {  setTcpiArptaTable 1 }

SetTcpiArptaEntry ::= SEQUENCE {
                  setTcpiArptaIpa IpAddress,
                  setTcpiArptaMac MacAddress,
                  setTcpiArptaLas INTEGER,
                  setTcpiArptaCon INTEGER,
                  setTcpiArptaEth INTEGER,
                  setTcpiArptaVla INTEGER,
                  setTcpiArptaPee DisplayString
                 }

setTcpiArptaIpa OBJECT-TYPE
                SYNTAX IpAddress
                MAX-ACCESS read-only
                STATUS current
                DESCRIPTION "IP-Address"
                ::= {  setTcpiArptaEntry 1 }

setTcpiArptaMac OBJECT-TYPE
                SYNTAX MacAddress
                MAX-ACCESS read-only
                STATUS current
                DESCRIPTION "MAC-Address"
                ::= {  setTcpiArptaEntry 2 }

setTcpiArptaLas OBJECT-TYPE
                SYNTAX INTEGER (0..2147483647)
                MAX-ACCESS read-only
                STATUS current
                DESCRIPTION "Last-access"
                ::= {  setTcpiArptaEntry 3 }

setTcpiArptaCon OBJECT-TYPE
                SYNTAX INTEGER
                {
                  lan-1(0),
                  lan-2(1),
                  lan-3(2),
                  lan-4(3),
                  wan(4)
                }
                MAX-ACCESS read-only
                STATUS current
                DESCRIPTION "Connect"
                ::= {  setTcpiArptaEntry 4 }

setTcpiArptaEth OBJECT-TYPE
                SYNTAX INTEGER
                {
                  wan(1),
                  eth-1(2),
                  eth-2(3),
                  eth-3(4),
                  eth-4(5),
                  unknown(0)
                }
                MAX-ACCESS read-only
                STATUS current
                DESCRIPTION "Ethernet-Port"
                ::= {  setTcpiArptaEntry 5 }

setTcpiArptaVla OBJECT-TYPE
                SYNTAX INTEGER (0..65535)
                MAX-ACCESS read-only
                STATUS current
                DESCRIPTION "VLAN-ID"
                ::= {  setTcpiArptaEntry 7 }

setTcpiArptaPee OBJECT-TYPE
                SYNTAX DisplayString (SIZE(0..255))
                MAX-ACCESS read-only
                STATUS current
                DESCRIPTION "Peer"
                ::= {  setTcpiArptaEntry 6 }

setTcpiNonlo OBJECT-TYPE
             SYNTAX INTEGER
             {
               no(0),
               yes(1)
             }
             MAX-ACCESS read-write
             STATUS current
             DESCRIPTION "Non-Loc.-ARP-Replies"
             ::= {  setTcpi 20 }

setTcpiIcmpo OBJECT-TYPE
             SYNTAX INTEGER
             {
               no(0),
               yes(1)
             }
             MAX-ACCESS read-write
             STATUS current
             DESCRIPTION "ICMP-On-ARP-Timeout"
             ::= {  setTcpi 22 }

setTcpiArpag OBJECT-TYPE
             SYNTAX INTEGER
             MAX-ACCESS read-write
             STATUS current
             DESCRIPTION "ARP-Aging-Minutes"
             ::= {  setTcpi 11 }

setTcpiAlive OBJECT IDENTIFIER ::= { setTcpi 21}
setTcpiAliveTarget OBJECT-TYPE
                   SYNTAX IpAddress
                   MAX-ACCESS read-write
                   STATUS current
                   DESCRIPTION "Target-Address"
                   ::= {  setTcpiAlive 1 }

setTcpiAliveTestin OBJECT-TYPE
                   SYNTAX INTEGER
                   MAX-ACCESS read-write
                   STATUS current
                   DESCRIPTION "Test-Interval"
                   ::= {  setTcpiAlive 2 }

setTcpiAliveRetryc OBJECT-TYPE
                   SYNTAX INTEGER
                   MAX-ACCESS read-write
                   STATUS current
                   DESCRIPTION "Retry-Count"
                   ::= {  setTcpiAlive 3 }

setTcpiAliveRetryi OBJECT-TYPE
                   SYNTAX INTEGER
                   MAX-ACCESS read-write
                   STATUS current
                   DESCRIPTION "Retry-Interval"
                   ::= {  setTcpiAlive 4 }

setTcpiAliveFailli OBJECT-TYPE
                   SYNTAX INTEGER
                   MAX-ACCESS read-write
                   STATUS current
                   DESCRIPTION "Fail-Limit"
                   ::= {  setTcpiAlive 5 }

setTcpiAliveBootty OBJECT-TYPE
                   SYNTAX INTEGER
                   {
                     warm-boot(0),
                     cold-boot(1)
                   }
                   MAX-ACCESS read-write
                   STATUS current
                   DESCRIPTION "Boot-Type"
                   ::= {  setTcpiAlive 6 }

setIpro OBJECT IDENTIFIER ::= { set 8}
setIproOpe OBJECT-TYPE
           SYNTAX INTEGER
           {
             no(0),
             yes(1)
           }
           MAX-ACCESS read-write
           STATUS current
           DESCRIPTION "Operating"
           ::= {  setIpro 1 }

setIproIprTable OBJECT-TYPE
                SYNTAX SEQUENCE OF SetIproIprEntry
                MAX-ACCESS not-accessible
                STATUS current
                DESCRIPTION "IP-Routing-Table"
                ::= {  setIpro 2 }

setIproIprEntry OBJECT-TYPE
                SYNTAX SetIproIprEntry
                MAX-ACCESS not-accessible
                STATUS current
                DESCRIPTION "entry in table"
                INDEX { setIproIprIpa, setIproIprIpn, setIproIprRtg }
                ::= {  setIproIprTable 1 }

SetIproIprEntry ::= SEQUENCE {
                setIproIprIpa IpAddress,
                setIproIprIpn IpAddress,
                setIproIprRtg INTEGER,
                setIproIprPee DisplayString,
                setIproIprDis INTEGER,
                setIproIprMas INTEGER,
                setIproIprAct INTEGER,
                setIproIprCom DisplayString
               }

setIproIprIpa OBJECT-TYPE
              SYNTAX IpAddress
              MAX-ACCESS read-write
              STATUS current
              DESCRIPTION "IP-Address"
              ::= {  setIproIprEntry 1 }

setIproIprIpn OBJECT-TYPE
              SYNTAX IpAddress
              MAX-ACCESS read-write
              STATUS current
              DESCRIPTION "IP-Netmask"
              ::= {  setIproIprEntry 2 }

setIproIprRtg OBJECT-TYPE
              SYNTAX INTEGER (0..65535)
              MAX-ACCESS read-write
              STATUS current
              DESCRIPTION "Rtg-tag"
              ::= {  setIproIprEntry 8 }

setIproIprPee OBJECT-TYPE
              SYNTAX DisplayString (SIZE(0..16))
              MAX-ACCESS read-write
              STATUS current
              DESCRIPTION "Peer-or-IP"
              ::= {  setIproIprEntry 3 }

setIproIprDis OBJECT-TYPE
              SYNTAX INTEGER (0..255)
              MAX-ACCESS read-write
              STATUS current
              DESCRIPTION "Distance"
              ::= {  setIproIprEntry 4 }

setIproIprMas OBJECT-TYPE
              SYNTAX INTEGER
              {
                no(0),
                on(1),
                intranet(2)
              }
              MAX-ACCESS read-write
              STATUS current
              DESCRIPTION "Masquerade"
              ::= {  setIproIprEntry 5 }

setIproIprAct OBJECT-TYPE
              SYNTAX INTEGER
              {
                no(1),
                yes(0),
                semi(2)
              }
              MAX-ACCESS read-write
              STATUS current
              DESCRIPTION "Active"
              ::= {  setIproIprEntry 6 }

setIproIprCom OBJECT-TYPE
              SYNTAX DisplayString (SIZE(0..64))
              MAX-ACCESS read-write
              STATUS current
              DESCRIPTION "Comment"
              ::= {  setIproIprEntry 7 }

setIproDefTable OBJECT-TYPE
                SYNTAX SEQUENCE OF SetIproDefEntry
                MAX-ACCESS not-accessible
                STATUS current
                DESCRIPTION "Default-Time-List"
                ::= {  setIpro 13 }

setIproDefEntry OBJECT-TYPE
                SYNTAX SetIproDefEntry
                MAX-ACCESS not-accessible
                STATUS current
                DESCRIPTION "entry in table"
                INDEX { setIproDefInd }
                ::= {  setIproDefTable 1 }

SetIproDefEntry ::= SEQUENCE {
                setIproDefInd INTEGER,
                setIproDefDay BITS,
                setIproDefSta DisplayString,
                setIproDefSto DisplayString,
                setIproDefPee DisplayString
               }

setIproDefInd OBJECT-TYPE
              SYNTAX INTEGER (0..65535)
              MAX-ACCESS read-write
              STATUS current
              DESCRIPTION "Index"
              ::= {  setIproDefEntry 1 }

setIproDefDay OBJECT-TYPE
              SYNTAX BITS
              {
                monday(7),
                tuesday(6),
                wednesday(5),
                thursday(4),
                friday(3),
                saturday(2),
                sunday(1),
                holiday(0)
              }
              MAX-ACCESS read-write
              STATUS current
              DESCRIPTION "Days"
              ::= {  setIproDefEntry 2 }

setIproDefSta OBJECT-TYPE
              SYNTAX DisplayString (SIZE(0..5))
              MAX-ACCESS read-write
              STATUS current
              DESCRIPTION "Start"
              ::= {  setIproDefEntry 3 }

setIproDefSto OBJECT-TYPE
              SYNTAX DisplayString (SIZE(0..5))
              MAX-ACCESS read-write
              STATUS current
              DESCRIPTION "Stop"
              ::= {  setIproDefEntry 4 }

setIproDefPee OBJECT-TYPE
              SYNTAX DisplayString (SIZE(0..16))
              MAX-ACCESS read-write
              STATUS current
              DESCRIPTION "Peer"
              ::= {  setIproDefEntry 5 }

setIproUsa OBJECT-TYPE
           SYNTAX INTEGER
           {
             no(0),
             yes(1)
           }
           MAX-ACCESS read-write
           STATUS current
           DESCRIPTION "Usage-Default-Timetable"
           ::= {  setIpro 14 }

setIproPro OBJECT-TYPE
           SYNTAX INTEGER
           {
             no(0),
             yes(1)
           }
           MAX-ACCESS read-write
           STATUS current
           DESCRIPTION "Proxy-ARP"
           ::= {  setIpro 5 }

setIproSen OBJECT-TYPE
           SYNTAX INTEGER
           {
             no(1),
             yes(0)
           }
           MAX-ACCESS read-write
           STATUS current
           DESCRIPTION "Send-ICMP-Redirect"
           ::= {  setIpro 6 }

setIproSta OBJECT-TYPE
           SYNTAX IpAddress
           MAX-ACCESS read-write
           STATUS current
           DESCRIPTION "Start-WAN-Pool"
           ::= {  setIpro 11 }

setIproEnd OBJECT-TYPE
           SYNTAX IpAddress
           MAX-ACCESS read-write
           STATUS current
           DESCRIPTION "End-WAN-Pool"
           ::= {  setIpro 12 }

setIproLoa OBJECT IDENTIFIER ::= { setIpro 20}
setIproLoaOpe OBJECT-TYPE
              SYNTAX INTEGER
              {
                no(0),
                yes(1)
              }
              MAX-ACCESS read-write
              STATUS current
              DESCRIPTION "Operating"
              ::= {  setIproLoa 1 }

setIproLoaBunTable OBJECT-TYPE
                   SYNTAX SEQUENCE OF SetIproLoaBunEntry
                   MAX-ACCESS not-accessible
                   STATUS current
                   DESCRIPTION "Bundle-Peers"
                   ::= {  setIproLoa 2 }

setIproLoaBunEntry OBJECT-TYPE
                   SYNTAX SetIproLoaBunEntry
                   MAX-ACCESS not-accessible
                   STATUS current
                   DESCRIPTION "entry in table"
                   INDEX { setIproLoaBunPeer }
                   ::= {  setIproLoaBunTable 1 }

SetIproLoaBunEntry ::= SEQUENCE {
                   setIproLoaBunPeer DisplayString,
                   setIproLoaBunBundlepeer1 DisplayString,
                   setIproLoaBunBundlepeer2 DisplayString,
                   setIproLoaBunBundlepeer3 DisplayString,
                   setIproLoaBunBundlepeer4 DisplayString
                  }

setIproLoaBunPeer OBJECT-TYPE
                         SYNTAX DisplayString (SIZE(0..16))
                         MAX-ACCESS read-write
                         STATUS current
                         DESCRIPTION "Peer"
                         ::= {  setIproLoaBunEntry 1 }

setIproLoaBunBundlepeer1 OBJECT-TYPE
                         SYNTAX DisplayString (SIZE(0..16))
                         MAX-ACCESS read-write
                         STATUS current
                         DESCRIPTION "Bundle-Peer-1"
                         ::= {  setIproLoaBunEntry 2 }

setIproLoaBunBundlepeer2 OBJECT-TYPE
                         SYNTAX DisplayString (SIZE(0..16))
                         MAX-ACCESS read-write
                         STATUS current
                         DESCRIPTION "Bundle-Peer-2"
                         ::= {  setIproLoaBunEntry 3 }

setIproLoaBunBundlepeer3 OBJECT-TYPE
                         SYNTAX DisplayString (SIZE(0..16))
                         MAX-ACCESS read-write
                         STATUS current
                         DESCRIPTION "Bundle-Peer-3"
                         ::= {  setIproLoaBunEntry 4 }

setIproLoaBunBundlepeer4 OBJECT-TYPE
                         SYNTAX DisplayString (SIZE(0..16))
                         MAX-ACCESS read-write
                         STATUS current
                         DESCRIPTION "Bundle-Peer-4"
                         ::= {  setIproLoaBunEntry 5 }

setIproVrr OBJECT IDENTIFIER ::= { setIpro 21}
setIproVrrOpe OBJECT-TYPE
              SYNTAX INTEGER
              {
                no(0),
                yes(1)
              }
              MAX-ACCESS read-write
              STATUS current
              DESCRIPTION "Operating"
              ::= {  setIproVrr 1 }

setIproVrrVrrTable OBJECT-TYPE
                   SYNTAX SEQUENCE OF SetIproVrrVrrEntry
                   MAX-ACCESS not-accessible
                   STATUS current
                   DESCRIPTION "VRRP-List"
                   ::= {  setIproVrr 2 }

setIproVrrVrrEntry OBJECT-TYPE
                   SYNTAX SetIproVrrVrrEntry
                   MAX-ACCESS not-accessible
                   STATUS current
                   DESCRIPTION "entry in table"
                   INDEX { setIproVrrVrrRou }
                   ::= {  setIproVrrVrrTable 1 }

SetIproVrrVrrEntry ::= SEQUENCE {
                   setIproVrrVrrRou INTEGER,
                   setIproVrrVrrVir IpAddress,
                   setIproVrrVrrPri INTEGER,
                   setIproVrrVrrBpr INTEGER,
                   setIproVrrVrrPee DisplayString,
                   setIproVrrVrrCom DisplayString
                  }

setIproVrrVrrRou OBJECT-TYPE
                 SYNTAX INTEGER (0..255)
                 MAX-ACCESS read-write
                 STATUS current
                 DESCRIPTION "Router-ID"
                 ::= {  setIproVrrVrrEntry 1 }

setIproVrrVrrVir OBJECT-TYPE
                 SYNTAX IpAddress
                 MAX-ACCESS read-write
                 STATUS current
                 DESCRIPTION "virt.-Address"
                 ::= {  setIproVrrVrrEntry 2 }

setIproVrrVrrPri OBJECT-TYPE
                 SYNTAX INTEGER (0..255)
                 MAX-ACCESS read-write
                 STATUS current
                 DESCRIPTION "Prio"
                 ::= {  setIproVrrVrrEntry 3 }

setIproVrrVrrBpr OBJECT-TYPE
                 SYNTAX INTEGER (0..255)
                 MAX-ACCESS read-write
                 STATUS current
                 DESCRIPTION "B-Prio"
                 ::= {  setIproVrrVrrEntry 4 }

setIproVrrVrrPee OBJECT-TYPE
                 SYNTAX DisplayString (SIZE(0..16))
                 MAX-ACCESS read-write
                 STATUS current
                 DESCRIPTION "Peer"
                 ::= {  setIproVrrVrrEntry 5 }

setIproVrrVrrCom OBJECT-TYPE
                 SYNTAX DisplayString (SIZE(0..64))
                 MAX-ACCESS read-write
                 STATUS current
                 DESCRIPTION "Comment"
                 ::= {  setIproVrrVrrEntry 6 }

setIproVrrRec OBJECT-TYPE
              SYNTAX INTEGER
              MAX-ACCESS read-write
              STATUS current
              DESCRIPTION "Reconnect-Delay"
              ::= {  setIproVrr 3 }

setIproVrrAdv OBJECT-TYPE
              SYNTAX INTEGER
              MAX-ACCESS read-write
              STATUS current
              DESCRIPTION "Advert.-Intervall"
              ::= {  setIproVrr 4 }

setIproVrrInt OBJECT-TYPE
              SYNTAX INTEGER
              {
                no(0),
                yes(1)
              }
              MAX-ACCESS read-write
              STATUS current
              DESCRIPTION "Internal-Services"
              ::= {  setIproVrr 5 }

setIproRou OBJECT IDENTIFIER ::= { setIpro 7}
setIproRouRou OBJECT-TYPE
              SYNTAX INTEGER
              {
                normal(0),
                type-of-service(1),
                diffserv(2)
              }
              MAX-ACCESS read-write
              STATUS current
              DESCRIPTION "Routing-Method"
              ::= {  setIproRou 1 }

setIproRouIcm OBJECT-TYPE
              SYNTAX INTEGER
              {
                normal(0),
                reliable(1)
              }
              MAX-ACCESS read-write
              STATUS current
              DESCRIPTION "ICMP-Routing-Method"
              ::= {  setIproRou 2 }

setIproRouSyn OBJECT-TYPE
              SYNTAX INTEGER
              {
                no(0),
                yes(1)
              }
              MAX-ACCESS read-write
              STATUS current
              DESCRIPTION "SYN/ACK-Speedup"
              ::= {  setIproRou 3 }

setIproRouL2l OBJECT-TYPE
              SYNTAX INTEGER
              {
                no(0),
                yes(1),
                auto(2)
              }
              MAX-ACCESS read-write
              STATUS current
              DESCRIPTION "L2-L3-Tagging"
              ::= {  setIproRou 4 }

setIproRouL3l OBJECT-TYPE
              SYNTAX INTEGER
              {
                no(0),
                yes(1)
              }
              MAX-ACCESS read-write
              STATUS current
              DESCRIPTION "L3-L2-Tagging"
              ::= {  setIproRou 5 }

setIproRip OBJECT IDENTIFIER ::= { setIpro 8}
setIproRipLanTable OBJECT-TYPE
                   SYNTAX SEQUENCE OF SetIproRipLanEntry
                   MAX-ACCESS not-accessible
                   STATUS current
                   DESCRIPTION "LAN-Sites"
                   ::= {  setIproRip 5 }

setIproRipLanEntry OBJECT-TYPE
                   SYNTAX SetIproRipLanEntry
                   MAX-ACCESS not-accessible
                   STATUS current
                   DESCRIPTION "entry in table"
                   INDEX { setIproRipLanNetw }
                   ::= {  setIproRipLanTable 1 }

SetIproRipLanEntry ::= SEQUENCE {
                   setIproRipLanNetw DisplayString,
                   setIproRipLanRipt INTEGER,
                   setIproRipLanRips INTEGER,
                   setIproRipLanRipa INTEGER,
                   setIproRipLanProp INTEGER,
                   setIproRipLanPois INTEGER,
                   setIproRipLanDftr INTEGER,
                   setIproRipLanRtgt DisplayString,
                   setIproRipLanRxfi DisplayString,
                   setIproRipLanTxfi DisplayString
                  }

setIproRipLanNetw OBJECT-TYPE
                  SYNTAX DisplayString (SIZE(0..16))
                  MAX-ACCESS read-write
                  STATUS current
                  DESCRIPTION "Network-name"
                  ::= {  setIproRipLanEntry 1 }

setIproRipLanRipt OBJECT-TYPE
                  SYNTAX INTEGER
                  {
                    off(0),
                    rip-1(1),
                    r1-comp(2),
                    rip-2(3)
                  }
                  MAX-ACCESS read-write
                  STATUS current
                  DESCRIPTION "RIP-Type"
                  ::= {  setIproRipLanEntry 2 }

setIproRipLanRips OBJECT-TYPE
                  SYNTAX INTEGER
                  {
                    no(0),
                    yes(1)
                  }
                  MAX-ACCESS read-write
                  STATUS current
                  DESCRIPTION "RIP-Send"
                  ::= {  setIproRipLanEntry 12 }

setIproRipLanRipa OBJECT-TYPE
                  SYNTAX INTEGER
                  {
                    no(0),
                    yes(1)
                  }
                  MAX-ACCESS read-write
                  STATUS current
                  DESCRIPTION "RIP-Accept"
                  ::= {  setIproRipLanEntry 3 }

setIproRipLanProp OBJECT-TYPE
                  SYNTAX INTEGER
                  {
                    no(0),
                    yes(1)
                  }
                  MAX-ACCESS read-write
                  STATUS current
                  DESCRIPTION "Propagate"
                  ::= {  setIproRipLanEntry 4 }

setIproRipLanPois OBJECT-TYPE
                  SYNTAX INTEGER
                  {
                    no(0),
                    yes(1)
                  }
                  MAX-ACCESS read-write
                  STATUS current
                  DESCRIPTION "Poisoned-Reverse"
                  ::= {  setIproRipLanEntry 7 }

setIproRipLanDftr OBJECT-TYPE
                  SYNTAX INTEGER (0..65535)
                  MAX-ACCESS read-write
                  STATUS current
                  DESCRIPTION "Dft-Rtg-Tag"
                  ::= {  setIproRipLanEntry 5 }

setIproRipLanRtgt OBJECT-TYPE
                  SYNTAX DisplayString (SIZE(0..33))
                  MAX-ACCESS read-write
                  STATUS current
                  DESCRIPTION "Rtg-Tag-List"
                  ::= {  setIproRipLanEntry 6 }

setIproRipLanRxfi OBJECT-TYPE
                  SYNTAX DisplayString (SIZE(0..16))
                  MAX-ACCESS read-write
                  STATUS current
                  DESCRIPTION "Rx-Filter"
                  ::= {  setIproRipLanEntry 10 }

setIproRipLanTxfi OBJECT-TYPE
                  SYNTAX DisplayString (SIZE(0..16))
                  MAX-ACCESS read-write
                  STATUS current
                  DESCRIPTION "Tx-Filter"
                  ::= {  setIproRipLanEntry 11 }

setIproRipR1m OBJECT-TYPE
              SYNTAX INTEGER
              {
                class(0),
                address(1),
                cl-plus-addr(2)
              }
              MAX-ACCESS read-write
              STATUS current
              DESCRIPTION "R1-Mask"
              ::= {  setIproRip 2 }

setIproRipIprTable OBJECT-TYPE
                   SYNTAX SEQUENCE OF SetIproRipIprEntry
                   MAX-ACCESS not-accessible
                   STATUS current
                   DESCRIPTION "IP-RIP-Table"
                   ::= {  setIproRip 3 }

setIproRipIprEntry OBJECT-TYPE
                   SYNTAX SetIproRipIprEntry
                   MAX-ACCESS not-accessible
                   STATUS current
                   DESCRIPTION "entry in table"
                   INDEX { setIproRipIprIpa, setIproRipIprIpn, setIproRipIprRtg }
                   ::= {  setIproRipIprTable 1 }

SetIproRipIprEntry ::= SEQUENCE {
                   setIproRipIprIpa IpAddress,
                   setIproRipIprIpn IpAddress,
                   setIproRipIprRtg INTEGER,
                   setIproRipIprTim INTEGER,
                   setIproRipIprDis INTEGER,
                   setIproRipIprGat IpAddress,
                   setIproRipIprPee DisplayString,
                   setIproRipIprPor INTEGER,
                   setIproRipIprVla INTEGER,
                   setIproRipIprNet DisplayString
                  }

setIproRipIprIpa OBJECT-TYPE
                 SYNTAX IpAddress
                 MAX-ACCESS read-only
                 STATUS current
                 DESCRIPTION "IP-Address"
                 ::= {  setIproRipIprEntry 1 }

setIproRipIprIpn OBJECT-TYPE
                 SYNTAX IpAddress
                 MAX-ACCESS read-only
                 STATUS current
                 DESCRIPTION "IP-Netmask"
                 ::= {  setIproRipIprEntry 2 }

setIproRipIprRtg OBJECT-TYPE
                 SYNTAX INTEGER (0..65535)
                 MAX-ACCESS read-only
                 STATUS current
                 DESCRIPTION "Rtg-tag"
                 ::= {  setIproRipIprEntry 6 }

setIproRipIprTim OBJECT-TYPE
                 SYNTAX INTEGER (0..65535)
                 MAX-ACCESS read-only
                 STATUS current
                 DESCRIPTION "Time"
                 ::= {  setIproRipIprEntry 3 }

setIproRipIprDis OBJECT-TYPE
                 SYNTAX INTEGER (0..65535)
                 MAX-ACCESS read-only
                 STATUS current
                 DESCRIPTION "Distance"
                 ::= {  setIproRipIprEntry 4 }

setIproRipIprGat OBJECT-TYPE
                 SYNTAX IpAddress
                 MAX-ACCESS read-only
                 STATUS current
                 DESCRIPTION "Gateway"
                 ::= {  setIproRipIprEntry 5 }

setIproRipIprPee OBJECT-TYPE
                 SYNTAX DisplayString (SIZE(0..16))
                 MAX-ACCESS read-only
                 STATUS current
                 DESCRIPTION "Peer"
                 ::= {  setIproRipIprEntry 8 }

setIproRipIprPor OBJECT-TYPE
                 SYNTAX INTEGER
                 {
                   lan-1(0),
                   lan-2(1),
                   lan-3(2),
                   lan-4(3),
                   any(255)
                 }
                 MAX-ACCESS read-only
                 STATUS current
                 DESCRIPTION "Port"
                 ::= {  setIproRipIprEntry 9 }

setIproRipIprVla OBJECT-TYPE
                 SYNTAX INTEGER (0..65535)
                 MAX-ACCESS read-only
                 STATUS current
                 DESCRIPTION "VLAN-ID"
                 ::= {  setIproRipIprEntry 10 }

setIproRipIprNet OBJECT-TYPE
                 SYNTAX DisplayString (SIZE(0..16))
                 MAX-ACCESS read-only
                 STATUS current
                 DESCRIPTION "Network-name"
                 ::= {  setIproRipIprEntry 11 }

setIproRipWanTable OBJECT-TYPE
                   SYNTAX SEQUENCE OF SetIproRipWanEntry
                   MAX-ACCESS not-accessible
                   STATUS current
                   DESCRIPTION "WAN-Sites"
                   ::= {  setIproRip 4 }

setIproRipWanEntry OBJECT-TYPE
                   SYNTAX SetIproRipWanEntry
                   MAX-ACCESS not-accessible
                   STATUS current
                   DESCRIPTION "entry in table"
                   INDEX { setIproRipWanPeer }
                   ::= {  setIproRipWanTable 1 }

SetIproRipWanEntry ::= SEQUENCE {
                   setIproRipWanPeer DisplayString,
                   setIproRipWanRipt INTEGER,
                   setIproRipWanRips INTEGER,
                   setIproRipWanRipa INTEGER,
                   setIproRipWanMasq INTEGER,
                   setIproRipWanPois INTEGER,
                   setIproRipWanRfc2 INTEGER,
                   setIproRipWanGate IpAddress,
                   setIproRipWanDftr INTEGER,
                   setIproRipWanRtgt DisplayString,
                   setIproRipWanRxfi DisplayString,
                   setIproRipWanTxfi DisplayString
                  }

setIproRipWanPeer OBJECT-TYPE
                  SYNTAX DisplayString (SIZE(0..16))
                  MAX-ACCESS read-write
                  STATUS current
                  DESCRIPTION "Peer"
                  ::= {  setIproRipWanEntry 1 }

setIproRipWanRipt OBJECT-TYPE
                  SYNTAX INTEGER
                  {
                    off(0),
                    rip-1(1),
                    r1-comp(2),
                    rip-2(3)
                  }
                  MAX-ACCESS read-write
                  STATUS current
                  DESCRIPTION "RIP-Type"
                  ::= {  setIproRipWanEntry 2 }

setIproRipWanRips OBJECT-TYPE
                  SYNTAX INTEGER
                  {
                    no(0),
                    yes(1)
                  }
                  MAX-ACCESS read-write
                  STATUS current
                  DESCRIPTION "RIP-Send"
                  ::= {  setIproRipWanEntry 12 }

setIproRipWanRipa OBJECT-TYPE
                  SYNTAX INTEGER
                  {
                    no(0),
                    yes(1)
                  }
                  MAX-ACCESS read-write
                  STATUS current
                  DESCRIPTION "RIP-Accept"
                  ::= {  setIproRipWanEntry 3 }

setIproRipWanMasq OBJECT-TYPE
                  SYNTAX INTEGER
                  {
                    auto(0),
                    on(1),
                    intranet(2)
                  }
                  MAX-ACCESS read-write
                  STATUS current
                  DESCRIPTION "Masquerade"
                  ::= {  setIproRipWanEntry 4 }

setIproRipWanPois OBJECT-TYPE
                  SYNTAX INTEGER
                  {
                    no(0),
                    yes(1)
                  }
                  MAX-ACCESS read-write
                  STATUS current
                  DESCRIPTION "Poisoned-Reverse"
                  ::= {  setIproRipWanEntry 7 }

setIproRipWanRfc2 OBJECT-TYPE
                  SYNTAX INTEGER
                  {
                    no(0),
                    yes(1)
                  }
                  MAX-ACCESS read-write
                  STATUS current
                  DESCRIPTION "RFC2091"
                  ::= {  setIproRipWanEntry 8 }

setIproRipWanGate OBJECT-TYPE
                  SYNTAX IpAddress
                  MAX-ACCESS read-write
                  STATUS current
                  DESCRIPTION "Gateway"
                  ::= {  setIproRipWanEntry 9 }

setIproRipWanDftr OBJECT-TYPE
                  SYNTAX INTEGER (0..65535)
                  MAX-ACCESS read-write
                  STATUS current
                  DESCRIPTION "Dft-Rtg-Tag"
                  ::= {  setIproRipWanEntry 5 }

setIproRipWanRtgt OBJECT-TYPE
                  SYNTAX DisplayString (SIZE(0..33))
                  MAX-ACCESS read-write
                  STATUS current
                  DESCRIPTION "Rtg-Tag-List"
                  ::= {  setIproRipWanEntry 6 }

setIproRipWanRxfi OBJECT-TYPE
                  SYNTAX DisplayString (SIZE(0..16))
                  MAX-ACCESS read-write
                  STATUS current
                  DESCRIPTION "Rx-Filter"
                  ::= {  setIproRipWanEntry 10 }

setIproRipWanTxfi OBJECT-TYPE
                  SYNTAX DisplayString (SIZE(0..16))
                  MAX-ACCESS read-write
                  STATUS current
                  DESCRIPTION "Tx-Filter"
                  ::= {  setIproRipWanEntry 11 }

setIproRipFilTable OBJECT-TYPE
                   SYNTAX SEQUENCE OF SetIproRipFilEntry
                   MAX-ACCESS not-accessible
                   STATUS current
                   DESCRIPTION "Filter"
                   ::= {  setIproRip 7 }

setIproRipFilEntry OBJECT-TYPE
                   SYNTAX SetIproRipFilEntry
                   MAX-ACCESS not-accessible
                   STATUS current
                   DESCRIPTION "entry in table"
                   INDEX { setIproRipFilNam }
                   ::= {  setIproRipFilTable 1 }

SetIproRipFilEntry ::= SEQUENCE {
                   setIproRipFilNam DisplayString,
                   setIproRipFilFil DisplayString
                  }

setIproRipFilNam OBJECT-TYPE
                 SYNTAX DisplayString (SIZE(0..18))
                 MAX-ACCESS read-write
                 STATUS current
                 DESCRIPTION "Name"
                 ::= {  setIproRipFilEntry 1 }

setIproRipFilFil OBJECT-TYPE
                 SYNTAX DisplayString (SIZE(0..64))
                 MAX-ACCESS read-write
                 STATUS current
                 DESCRIPTION "Filter"
                 ::= {  setIproRipFilEntry 2 }

setIproRipPar OBJECT IDENTIFIER ::= { setIproRip 6}
setIproRipParUpda OBJECT-TYPE
                  SYNTAX INTEGER
                  MAX-ACCESS read-write
                  STATUS current
                  DESCRIPTION "Update"
                  ::= {  setIproRipPar 1 }

setIproRipParHold OBJECT-TYPE
                  SYNTAX INTEGER
                  MAX-ACCESS read-write
                  STATUS current
                  DESCRIPTION "Holddown"
                  ::= {  setIproRipPar 2 }

setIproRipParInva OBJECT-TYPE
                  SYNTAX INTEGER
                  MAX-ACCESS read-write
                  STATUS current
                  DESCRIPTION "Invalidate"
                  ::= {  setIproRipPar 3 }

setIproRipParFlus OBJECT-TYPE
                  SYNTAX INTEGER
                  MAX-ACCESS read-write
                  STATUS current
                  DESCRIPTION "Flush"
                  ::= {  setIproRipPar 4 }

setIproRipParUpdd OBJECT-TYPE
                  SYNTAX INTEGER
                  MAX-ACCESS read-write
                  STATUS current
                  DESCRIPTION "Upd-Delay"
                  ::= {  setIproRipPar 5 }

setIproRipParMaxh OBJECT-TYPE
                  SYNTAX INTEGER
                  MAX-ACCESS read-write
                  STATUS current
                  DESCRIPTION "Max-Hopcount"
                  ::= {  setIproRipPar 6 }

setIproRipParRout OBJECT-TYPE
                  SYNTAX INTEGER
                  MAX-ACCESS read-write
                  STATUS current
                  DESCRIPTION "Routes-per-Frame"
                  ::= {  setIproRipPar 7 }

setIpro1nn OBJECT IDENTIFIER ::= { setIpro 9}
setIpro1nnTcpagings OBJECT-TYPE
                    SYNTAX INTEGER
                    MAX-ACCESS read-write
                    STATUS current
                    DESCRIPTION "TCP-Aging-Seconds"
                    ::= {  setIpro1nn 1 }

setIpro1nnUdpagings OBJECT-TYPE
                    SYNTAX INTEGER
                    MAX-ACCESS read-write
                    STATUS current
                    DESCRIPTION "UDP-Aging-Seconds"
                    ::= {  setIpro1nn 2 }

setIpro1nnIcmpaging OBJECT-TYPE
                    SYNTAX INTEGER
                    MAX-ACCESS read-write
                    STATUS current
                    DESCRIPTION "ICMP-Aging-Seconds"
                    ::= {  setIpro1nn 3 }

setIpro1nnServicetaTable OBJECT-TYPE
                         SYNTAX SEQUENCE OF SetIpro1nnServicetaEntry
                         MAX-ACCESS not-accessible
                         STATUS current
                         DESCRIPTION "Service-Table"
                         ::= {  setIpro1nn 4 }

setIpro1nnServicetaEntry OBJECT-TYPE
                         SYNTAX SetIpro1nnServicetaEntry
                         MAX-ACCESS not-accessible
                         STATUS current
                         DESCRIPTION "entry in table"
                         INDEX { setIpro1nnServicetaDportf, setIpro1nnServicetaDportt, setIpro1nnServicetaProtoc, setIpro1nnServicetaPeer, setIpro1nnServicetaWanadd }
                         ::= {  setIpro1nnServicetaTable 1 }

SetIpro1nnServicetaEntry ::= SEQUENCE {
                         setIpro1nnServicetaDportf INTEGER,
                         setIpro1nnServicetaDportt INTEGER,
                         setIpro1nnServicetaProtoc INTEGER,
                         setIpro1nnServicetaPeer DisplayString,
                         setIpro1nnServicetaWanadd IpAddress,
                         setIpro1nnServicetaIntran IpAddress,
                         setIpro1nnServicetaMappor INTEGER,
                         setIpro1nnServicetaActive INTEGER,
                         setIpro1nnServicetaCommen DisplayString
                        }

setIpro1nnServicetaDportf OBJECT-TYPE
                          SYNTAX INTEGER (0..65535)
                          MAX-ACCESS read-write
                          STATUS current
                          DESCRIPTION "D-port-from"
                          ::= {  setIpro1nnServicetaEntry 1 }

setIpro1nnServicetaDportt OBJECT-TYPE
                          SYNTAX INTEGER (0..65535)
                          MAX-ACCESS read-write
                          STATUS current
                          DESCRIPTION "D-port-to"
                          ::= {  setIpro1nnServicetaEntry 3 }

setIpro1nnServicetaProtoc OBJECT-TYPE
                          SYNTAX INTEGER
                          {
                            tcp(1),
                            udp(2),
                            tcp-plus-udp(0)
                          }
                          MAX-ACCESS read-write
                          STATUS current
                          DESCRIPTION "Protocol"
                          ::= {  setIpro1nnServicetaEntry 8 }

setIpro1nnServicetaPeer OBJECT-TYPE
                          SYNTAX DisplayString (SIZE(0..16))
                          MAX-ACCESS read-write
                          STATUS current
                          DESCRIPTION "Peer"
                          ::= {  setIpro1nnServicetaEntry 7 }

setIpro1nnServicetaWanadd OBJECT-TYPE
                          SYNTAX IpAddress
                          MAX-ACCESS read-write
                          STATUS current
                          DESCRIPTION "WAN-Address"
                          ::= {  setIpro1nnServicetaEntry 9 }

setIpro1nnServicetaIntran OBJECT-TYPE
                          SYNTAX IpAddress
                          MAX-ACCESS read-write
                          STATUS current
                          DESCRIPTION "Intranet-Address"
                          ::= {  setIpro1nnServicetaEntry 2 }

setIpro1nnServicetaMappor OBJECT-TYPE
                          SYNTAX INTEGER (0..65535)
                          MAX-ACCESS read-write
                          STATUS current
                          DESCRIPTION "Map-Port"
                          ::= {  setIpro1nnServicetaEntry 4 }

setIpro1nnServicetaActive OBJECT-TYPE
                          SYNTAX INTEGER
                          {
                            no(1),
                            yes(0)
                          }
                          MAX-ACCESS read-write
                          STATUS current
                          DESCRIPTION "Active"
                          ::= {  setIpro1nnServicetaEntry 5 }

setIpro1nnServicetaCommen OBJECT-TYPE
                          SYNTAX DisplayString (SIZE(0..64))
                          MAX-ACCESS read-write
                          STATUS current
                          DESCRIPTION "Comment"
                          ::= {  setIpro1nnServicetaEntry 6 }

setIpro1nnTable1nnaTable OBJECT-TYPE
                         SYNTAX SEQUENCE OF SetIpro1nnTable1nnaEntry
                         MAX-ACCESS not-accessible
                         STATUS current
                         DESCRIPTION "Table-1-N-NAT"
                         ::= {  setIpro1nn 5 }

setIpro1nnTable1nnaEntry OBJECT-TYPE
                         SYNTAX SetIpro1nnTable1nnaEntry
                         MAX-ACCESS not-accessible
                         STATUS current
                         DESCRIPTION "entry in table"
                         INDEX { setIpro1nnTable1nnaInt }
                         ::= {  setIpro1nnTable1nnaTable 1 }

SetIpro1nnTable1nnaEntry ::= SEQUENCE {
                         setIpro1nnTable1nnaInt IpAddress,
                         setIpro1nnTable1nnaSou INTEGER,
                         setIpro1nnTable1nnaPro INTEGER,
                         setIpro1nnTable1nnaTim INTEGER,
                         setIpro1nnTable1nnaHan DisplayString,
                         setIpro1nnTable1nnaRem IpAddress
                        }

setIpro1nnTable1nnaInt OBJECT-TYPE
                       SYNTAX IpAddress
                       MAX-ACCESS read-only
                       STATUS current
                       DESCRIPTION "Intranet-Address"
                       ::= {  setIpro1nnTable1nnaEntry 1 }

setIpro1nnTable1nnaSou OBJECT-TYPE
                       SYNTAX INTEGER (0..65535)
                       MAX-ACCESS read-only
                       STATUS current
                       DESCRIPTION "Source-Port"
                       ::= {  setIpro1nnTable1nnaEntry 2 }

setIpro1nnTable1nnaPro OBJECT-TYPE
                       SYNTAX INTEGER
                       {
                         tcp(6),
                         udp(17),
                         icmp(1)
                       }
                       MAX-ACCESS read-only
                       STATUS current
                       DESCRIPTION "Protocol"
                       ::= {  setIpro1nnTable1nnaEntry 3 }

setIpro1nnTable1nnaTim OBJECT-TYPE
                       SYNTAX INTEGER (0..65535)
                       MAX-ACCESS read-only
                       STATUS current
                       DESCRIPTION "Timeout"
                       ::= {  setIpro1nnTable1nnaEntry 4 }

setIpro1nnTable1nnaHan OBJECT-TYPE
                       SYNTAX DisplayString (SIZE(0..255))
                       MAX-ACCESS read-only
                       STATUS current
                       DESCRIPTION "Handler"
                       ::= {  setIpro1nnTable1nnaEntry 5 }

setIpro1nnTable1nnaRem OBJECT-TYPE
                       SYNTAX IpAddress
                       MAX-ACCESS read-only
                       STATUS current
                       DESCRIPTION "remote-Address"
                       ::= {  setIpro1nnTable1nnaEntry 6 }

setIpro1nnFragments OBJECT-TYPE
                    SYNTAX INTEGER
                    {
                      filter(0),
                      route(1),
                      reassemble(2)
                    }
                    MAX-ACCESS read-write
                    STATUS current
                    DESCRIPTION "Fragments"
                    ::= {  setIpro1nn 6 }

setIpro1nnFragmenta OBJECT-TYPE
                    SYNTAX INTEGER
                    MAX-ACCESS read-write
                    STATUS current
                    DESCRIPTION "Fragment-Aging-Seconds"
                    ::= {  setIpro1nn 7 }

setIpro1nnIpsecagin OBJECT-TYPE
                    SYNTAX INTEGER
                    MAX-ACCESS read-write
                    STATUS current
                    DESCRIPTION "IPSec-Aging-Seconds"
                    ::= {  setIpro1nn 8 }

setIpro1nnIpsectablTable OBJECT-TYPE
                         SYNTAX SEQUENCE OF SetIpro1nnIpsectablEntry
                         MAX-ACCESS not-accessible
                         STATUS current
                         DESCRIPTION "IPSec-Table"
                         ::= {  setIpro1nn 9 }

setIpro1nnIpsectablEntry OBJECT-TYPE
                         SYNTAX SetIpro1nnIpsectablEntry
                         MAX-ACCESS not-accessible
                         STATUS current
                         DESCRIPTION "entry in table"
                         INDEX { setIpro1nnIpsectablRemotea }
                         ::= {  setIpro1nnIpsectablTable 1 }

SetIpro1nnIpsectablEntry ::= SEQUENCE {
                         setIpro1nnIpsectablRemotea IpAddress,
                         setIpro1nnIpsectablLocalad IpAddress,
                         setIpro1nnIpsectablRchi DisplayString,
                         setIpro1nnIpsectablRclo DisplayString,
                         setIpro1nnIpsectablLchi DisplayString,
                         setIpro1nnIpsectablLclo DisplayString,
                         setIpro1nnIpsectablRemotes DisplayString,
                         setIpro1nnIpsectablLocalsp DisplayString,
                         setIpro1nnIpsectablTimeout INTEGER,
                         setIpro1nnIpsectablCo INTEGER,
                         setIpro1nnIpsectablNl INTEGER,
                         setIpro1nnIpsectablNr INTEGER,
                         setIpro1nnIpsectablDp INTEGER,
                         setIpro1nnIpsectablFlags DisplayString
                        }

setIpro1nnIpsectablRemotea OBJECT-TYPE
                           SYNTAX IpAddress
                           MAX-ACCESS read-only
                           STATUS current
                           DESCRIPTION "remote-Address"
                           ::= {  setIpro1nnIpsectablEntry 1 }

setIpro1nnIpsectablLocalad OBJECT-TYPE
                           SYNTAX IpAddress
                           MAX-ACCESS read-only
                           STATUS current
                           DESCRIPTION "local-Address"
                           ::= {  setIpro1nnIpsectablEntry 2 }

setIpro1nnIpsectablRchi OBJECT-TYPE
                           SYNTAX DisplayString (SIZE(0..8))
                           MAX-ACCESS read-only
                           STATUS current
                           DESCRIPTION "rc-hi"
                           ::= {  setIpro1nnIpsectablEntry 3 }

setIpro1nnIpsectablRclo OBJECT-TYPE
                           SYNTAX DisplayString (SIZE(0..8))
                           MAX-ACCESS read-only
                           STATUS current
                           DESCRIPTION "rc-lo"
                           ::= {  setIpro1nnIpsectablEntry 4 }

setIpro1nnIpsectablLchi OBJECT-TYPE
                           SYNTAX DisplayString (SIZE(0..8))
                           MAX-ACCESS read-only
                           STATUS current
                           DESCRIPTION "lc-hi"
                           ::= {  setIpro1nnIpsectablEntry 5 }

setIpro1nnIpsectablLclo OBJECT-TYPE
                           SYNTAX DisplayString (SIZE(0..8))
                           MAX-ACCESS read-only
                           STATUS current
                           DESCRIPTION "lc-lo"
                           ::= {  setIpro1nnIpsectablEntry 6 }

setIpro1nnIpsectablRemotes OBJECT-TYPE
                           SYNTAX DisplayString (SIZE(0..8))
                           MAX-ACCESS read-only
                           STATUS current
                           DESCRIPTION "remote-SPI"
                           ::= {  setIpro1nnIpsectablEntry 7 }

setIpro1nnIpsectablLocalsp OBJECT-TYPE
                           SYNTAX DisplayString (SIZE(0..8))
                           MAX-ACCESS read-only
                           STATUS current
                           DESCRIPTION "local-SPI"
                           ::= {  setIpro1nnIpsectablEntry 8 }

setIpro1nnIpsectablTimeout OBJECT-TYPE
                           SYNTAX INTEGER (0..2147483647)
                           MAX-ACCESS read-only
                           STATUS current
                           DESCRIPTION "Timeout"
                           ::= {  setIpro1nnIpsectablEntry 9 }

setIpro1nnIpsectablCo OBJECT-TYPE
                           SYNTAX INTEGER (0..255)
                           MAX-ACCESS read-only
                           STATUS current
                           DESCRIPTION "CO"
                           ::= {  setIpro1nnIpsectablEntry 11 }

setIpro1nnIpsectablNl OBJECT-TYPE
                           SYNTAX INTEGER (0..255)
                           MAX-ACCESS read-only
                           STATUS current
                           DESCRIPTION "NL"
                           ::= {  setIpro1nnIpsectablEntry 12 }

setIpro1nnIpsectablNr OBJECT-TYPE
                           SYNTAX INTEGER (0..255)
                           MAX-ACCESS read-only
                           STATUS current
                           DESCRIPTION "NR"
                           ::= {  setIpro1nnIpsectablEntry 13 }

setIpro1nnIpsectablDp OBJECT-TYPE
                           SYNTAX INTEGER (0..255)
                           MAX-ACCESS read-only
                           STATUS current
                           DESCRIPTION "DP"
                           ::= {  setIpro1nnIpsectablEntry 14 }

setIpro1nnIpsectablFlags OBJECT-TYPE
                           SYNTAX DisplayString (SIZE(0..4))
                           MAX-ACCESS read-only
                           STATUS current
                           DESCRIPTION "Flags"
                           ::= {  setIpro1nnIpsectablEntry 10 }

setIpro1nnIdspoofin OBJECT-TYPE
                    SYNTAX INTEGER
                    {
                      no(0),
                      yes(1)
                    }
                    MAX-ACCESS read-write
                    STATUS current
                    DESCRIPTION "ID-Spoofing"
                    ::= {  setIpro1nn 10 }

setIproFir OBJECT IDENTIFIER ::= { setIpro 10}
setIproFirOpera OBJECT-TYPE
                SYNTAX INTEGER
                {
                  no(0),
                  yes(1)
                }
                MAX-ACCESS read-write
                STATUS current
                DESCRIPTION "Operating"
                ::= {  setIproFir 11 }

setIproFirActioTable OBJECT-TYPE
                     SYNTAX SEQUENCE OF SetIproFirActioEntry
                     MAX-ACCESS not-accessible
                     STATUS current
                     DESCRIPTION "Actions"
                     ::= {  setIproFir 4 }

setIproFirActioEntry OBJECT-TYPE
                     SYNTAX SetIproFirActioEntry
                     MAX-ACCESS not-accessible
                     STATUS current
                     DESCRIPTION "entry in table"
                     INDEX { setIproFirActioNam }
                     ::= {  setIproFirActioTable 1 }

SetIproFirActioEntry ::= SEQUENCE {
                     setIproFirActioNam DisplayString,
                     setIproFirActioDes DisplayString
                    }

setIproFirActioNam OBJECT-TYPE
                   SYNTAX DisplayString (SIZE(0..32))
                   MAX-ACCESS read-write
                   STATUS current
                   DESCRIPTION "Name"
                   ::= {  setIproFirActioEntry 1 }

setIproFirActioDes OBJECT-TYPE
                   SYNTAX DisplayString (SIZE(0..64))
                   MAX-ACCESS read-write
                   STATUS current
                   DESCRIPTION "Description"
                   ::= {  setIproFirActioEntry 2 }

setIproFirObjecTable OBJECT-TYPE
                     SYNTAX SEQUENCE OF SetIproFirObjecEntry
                     MAX-ACCESS not-accessible
                     STATUS current
                     DESCRIPTION "Objects"
                     ::= {  setIproFir 1 }

setIproFirObjecEntry OBJECT-TYPE
                     SYNTAX SetIproFirObjecEntry
                     MAX-ACCESS not-accessible
                     STATUS current
                     DESCRIPTION "entry in table"
                     INDEX { setIproFirObjecNam }
                     ::= {  setIproFirObjecTable 1 }

SetIproFirObjecEntry ::= SEQUENCE {
                     setIproFirObjecNam DisplayString,
                     setIproFirObjecDes DisplayString
                    }

setIproFirObjecNam OBJECT-TYPE
                   SYNTAX DisplayString (SIZE(0..32))
                   MAX-ACCESS read-write
                   STATUS current
                   DESCRIPTION "Name"
                   ::= {  setIproFirObjecEntry 1 }

setIproFirObjecDes OBJECT-TYPE
                   SYNTAX DisplayString (SIZE(0..64))
                   MAX-ACCESS read-write
                   STATUS current
                   DESCRIPTION "Description"
                   ::= {  setIproFirObjecEntry 2 }

setIproFirRulesTable OBJECT-TYPE
                     SYNTAX SEQUENCE OF SetIproFirRulesEntry
                     MAX-ACCESS not-accessible
                     STATUS current
                     DESCRIPTION "Rules"
                     ::= {  setIproFir 2 }

setIproFirRulesEntry OBJECT-TYPE
                     SYNTAX SetIproFirRulesEntry
                     MAX-ACCESS not-accessible
                     STATUS current
                     DESCRIPTION "entry in table"
                     INDEX { setIproFirRulesNam }
                     ::= {  setIproFirRulesTable 1 }

SetIproFirRulesEntry ::= SEQUENCE {
                     setIproFirRulesNam DisplayString,
                     setIproFirRulesPro DisplayString,
                     setIproFirRulesSou DisplayString,
                     setIproFirRulesDes DisplayString,
                     setIproFirRulesAct DisplayString,
                     setIproFirRulesLin INTEGER,
                     setIproFirRulesPri INTEGER,
                     setIproFirRulesFir INTEGER,
                     setIproFirRulesVpn INTEGER,
                     setIproFirRulesSta INTEGER,
                     setIproFirRulesRtg INTEGER,
                     setIproFirRulesCom DisplayString
                    }

setIproFirRulesNam OBJECT-TYPE
                   SYNTAX DisplayString (SIZE(0..32))
                   MAX-ACCESS read-write
                   STATUS current
                   DESCRIPTION "Name"
                   ::= {  setIproFirRulesEntry 1 }

setIproFirRulesPro OBJECT-TYPE
                   SYNTAX DisplayString (SIZE(0..10))
                   MAX-ACCESS read-write
                   STATUS current
                   DESCRIPTION "Prot."
                   ::= {  setIproFirRulesEntry 2 }

setIproFirRulesSou OBJECT-TYPE
                   SYNTAX DisplayString (SIZE(0..40))
                   MAX-ACCESS read-write
                   STATUS current
                   DESCRIPTION "Source"
                   ::= {  setIproFirRulesEntry 3 }

setIproFirRulesDes OBJECT-TYPE
                   SYNTAX DisplayString (SIZE(0..40))
                   MAX-ACCESS read-write
                   STATUS current
                   DESCRIPTION "Destination"
                   ::= {  setIproFirRulesEntry 4 }

setIproFirRulesAct OBJECT-TYPE
                   SYNTAX DisplayString (SIZE(0..40))
                   MAX-ACCESS read-write
                   STATUS current
                   DESCRIPTION "Action"
                   ::= {  setIproFirRulesEntry 7 }

setIproFirRulesLin OBJECT-TYPE
                   SYNTAX INTEGER
                   {
                     no(0),
                     yes(1)
                   }
                   MAX-ACCESS read-write
                   STATUS current
                   DESCRIPTION "Linked"
                   ::= {  setIproFirRulesEntry 8 }

setIproFirRulesPri OBJECT-TYPE
                   SYNTAX INTEGER (0..65535)
                   MAX-ACCESS read-write
                   STATUS current
                   DESCRIPTION "Prio"
                   ::= {  setIproFirRulesEntry 9 }

setIproFirRulesFir OBJECT-TYPE
                   SYNTAX INTEGER
                   {
                     no(1),
                     yes(0)
                   }
                   MAX-ACCESS read-write
                   STATUS current
                   DESCRIPTION "Firewall-Rule"
                   ::= {  setIproFirRulesEntry 10 }

setIproFirRulesVpn OBJECT-TYPE
                   SYNTAX INTEGER
                   {
                     no(0),
                     yes(1)
                   }
                   MAX-ACCESS read-write
                   STATUS current
                   DESCRIPTION "VPN-Rule"
                   ::= {  setIproFirRulesEntry 11 }

setIproFirRulesSta OBJECT-TYPE
                   SYNTAX INTEGER
                   {
                     no(1),
                     yes(0)
                   }
                   MAX-ACCESS read-write
                   STATUS current
                   DESCRIPTION "Stateful"
                   ::= {  setIproFirRulesEntry 12 }

setIproFirRulesRtg OBJECT-TYPE
                   SYNTAX INTEGER (0..65535)
                   MAX-ACCESS read-write
                   STATUS current
                   DESCRIPTION "Rtg-tag"
                   ::= {  setIproFirRulesEntry 14 }

setIproFirRulesCom OBJECT-TYPE
                   SYNTAX DisplayString (SIZE(0..64))
                   MAX-ACCESS read-write
                   STATUS current
                   DESCRIPTION "Comment"
                   ::= {  setIproFirRulesEntry 13 }

setIproFirFilteTable OBJECT-TYPE
                     SYNTAX SEQUENCE OF SetIproFirFilteEntry
                     MAX-ACCESS not-accessible
                     STATUS current
                     DESCRIPTION "Filter-List"
                     ::= {  setIproFir 3 }

setIproFirFilteEntry OBJECT-TYPE
                     SYNTAX SetIproFirFilteEntry
                     MAX-ACCESS not-accessible
                     STATUS current
                     DESCRIPTION "entry in table"
                     INDEX { setIproFirFilteIdx }
                     ::= {  setIproFirFilteTable 1 }

SetIproFirFilteEntry ::= SEQUENCE {
                     setIproFirFilteIdx INTEGER,
                     setIproFirFilteProt INTEGER,
                     setIproFirFilteSrcm DisplayString,
                     setIproFirFilteSrca IpAddress,
                     setIproFirFilteSrcn IpAddress,
                     setIproFirFilteSst INTEGER,
                     setIproFirFilteSend INTEGER,
                     setIproFirFilteDstm DisplayString,
                     setIproFirFilteDsta IpAddress,
                     setIproFirFilteDstn IpAddress,
                     setIproFirFilteDst INTEGER,
                     setIproFirFilteDend INTEGER,
                     setIproFirFilteActi DisplayString,
                     setIproFirFilteLink INTEGER,
                     setIproFirFiltePrio INTEGER,
                     setIproFirFilteRtgt INTEGER
                    }

setIproFirFilteIdx OBJECT-TYPE
                    SYNTAX INTEGER (0..65535)
                    MAX-ACCESS read-only
                    STATUS current
                    DESCRIPTION "Idx."
                    ::= {  setIproFirFilteEntry 1 }

setIproFirFilteProt OBJECT-TYPE
                    SYNTAX INTEGER (0..255)
                    MAX-ACCESS read-only
                    STATUS current
                    DESCRIPTION "Prot."
                    ::= {  setIproFirFilteEntry 2 }

setIproFirFilteSrcm OBJECT-TYPE
                    SYNTAX DisplayString (SIZE(0..12))
                    MAX-ACCESS read-only
                    STATUS current
                    DESCRIPTION "Src-MAC"
                    ::= {  setIproFirFilteEntry 13 }

setIproFirFilteSrca OBJECT-TYPE
                    SYNTAX IpAddress
                    MAX-ACCESS read-only
                    STATUS current
                    DESCRIPTION "Src-Address"
                    ::= {  setIproFirFilteEntry 3 }

setIproFirFilteSrcn OBJECT-TYPE
                    SYNTAX IpAddress
                    MAX-ACCESS read-only
                    STATUS current
                    DESCRIPTION "Src-Netmask"
                    ::= {  setIproFirFilteEntry 4 }

setIproFirFilteSst OBJECT-TYPE
                    SYNTAX INTEGER (0..65535)
                    MAX-ACCESS read-only
                    STATUS current
                    DESCRIPTION "S-St."
                    ::= {  setIproFirFilteEntry 5 }

setIproFirFilteSend OBJECT-TYPE
                    SYNTAX INTEGER (0..65535)
                    MAX-ACCESS read-only
                    STATUS current
                    DESCRIPTION "S-End"
                    ::= {  setIproFirFilteEntry 6 }

setIproFirFilteDstm OBJECT-TYPE
                    SYNTAX DisplayString (SIZE(0..12))
                    MAX-ACCESS read-only
                    STATUS current
                    DESCRIPTION "Dst-MAC"
                    ::= {  setIproFirFilteEntry 14 }

setIproFirFilteDsta OBJECT-TYPE
                    SYNTAX IpAddress
                    MAX-ACCESS read-only
                    STATUS current
                    DESCRIPTION "Dst-Address"
                    ::= {  setIproFirFilteEntry 7 }

setIproFirFilteDstn OBJECT-TYPE
                    SYNTAX IpAddress
                    MAX-ACCESS read-only
                    STATUS current
                    DESCRIPTION "Dst-Netmask"
                    ::= {  setIproFirFilteEntry 8 }

setIproFirFilteDst OBJECT-TYPE
                    SYNTAX INTEGER (0..65535)
                    MAX-ACCESS read-only
                    STATUS current
                    DESCRIPTION "D-St."
                    ::= {  setIproFirFilteEntry 9 }

setIproFirFilteDend OBJECT-TYPE
                    SYNTAX INTEGER (0..65535)
                    MAX-ACCESS read-only
                    STATUS current
                    DESCRIPTION "D-End"
                    ::= {  setIproFirFilteEntry 10 }

setIproFirFilteActi OBJECT-TYPE
                    SYNTAX DisplayString (SIZE(0..255))
                    MAX-ACCESS read-only
                    STATUS current
                    DESCRIPTION "Action"
                    ::= {  setIproFirFilteEntry 11 }

setIproFirFilteLink OBJECT-TYPE
                    SYNTAX INTEGER
                    {
                      no(0),
                      yes(1)
                    }
                    MAX-ACCESS read-only
                    STATUS current
                    DESCRIPTION "Linked"
                    ::= {  setIproFirFilteEntry 15 }

setIproFirFiltePrio OBJECT-TYPE
                    SYNTAX INTEGER (0..65535)
                    MAX-ACCESS read-only
                    STATUS current
                    DESCRIPTION "Prio"
                    ::= {  setIproFirFilteEntry 16 }

setIproFirFilteRtgt OBJECT-TYPE
                    SYNTAX INTEGER (0..65535)
                    MAX-ACCESS read-only
                    STATUS current
                    DESCRIPTION "Rtg-tag"
                    ::= {  setIproFirFilteEntry 17 }

setIproFirConneTable OBJECT-TYPE
                     SYNTAX SEQUENCE OF SetIproFirConneEntry
                     MAX-ACCESS not-accessible
                     STATUS current
                     DESCRIPTION "Connection-List"
                     ::= {  setIproFir 5 }

setIproFirConneEntry OBJECT-TYPE
                     SYNTAX SetIproFirConneEntry
                     MAX-ACCESS not-accessible
                     STATUS current
                     DESCRIPTION "entry in table"
                     INDEX { setIproFirConneSrca, setIproFirConneDsta, setIproFirConneProt, setIproFirConneSrcp, setIproFirConneDstp }
                     ::= {  setIproFirConneTable 1 }

SetIproFirConneEntry ::= SEQUENCE {
                     setIproFirConneSrca IpAddress,
                     setIproFirConneDsta IpAddress,
                     setIproFirConneProt INTEGER,
                     setIproFirConneSrcp INTEGER,
                     setIproFirConneDstp INTEGER,
                     setIproFirConneRtgt INTEGER,
                     setIproFirConneTime INTEGER,
                     setIproFirConneFlag INTEGER,
                     setIproFirConneFilt DisplayString,
                     setIproFirConneSrcr DisplayString,
                     setIproFirConneDest DisplayString
                    }

setIproFirConneSrca OBJECT-TYPE
                    SYNTAX IpAddress
                    MAX-ACCESS read-only
                    STATUS current
                    DESCRIPTION "Src-Address"
                    ::= {  setIproFirConneEntry 1 }

setIproFirConneDsta OBJECT-TYPE
                    SYNTAX IpAddress
                    MAX-ACCESS read-only
                    STATUS current
                    DESCRIPTION "Dst-Address"
                    ::= {  setIproFirConneEntry 2 }

setIproFirConneProt OBJECT-TYPE
                    SYNTAX INTEGER (0..255)
                    MAX-ACCESS read-only
                    STATUS current
                    DESCRIPTION "Prot."
                    ::= {  setIproFirConneEntry 3 }

setIproFirConneSrcp OBJECT-TYPE
                    SYNTAX INTEGER (0..65535)
                    MAX-ACCESS read-only
                    STATUS current
                    DESCRIPTION "Src-Port"
                    ::= {  setIproFirConneEntry 4 }

setIproFirConneDstp OBJECT-TYPE
                    SYNTAX INTEGER (0..65535)
                    MAX-ACCESS read-only
                    STATUS current
                    DESCRIPTION "Dst-Port"
                    ::= {  setIproFirConneEntry 5 }

setIproFirConneRtgt OBJECT-TYPE
                    SYNTAX INTEGER (0..65535)
                    MAX-ACCESS read-only
                    STATUS current
                    DESCRIPTION "Rtg-tag"
                    ::= {  setIproFirConneEntry 11 }

setIproFirConneTime OBJECT-TYPE
                    SYNTAX INTEGER (0..65535)
                    MAX-ACCESS read-only
                    STATUS current
                    DESCRIPTION "Timeout"
                    ::= {  setIproFirConneEntry 6 }

setIproFirConneFlag OBJECT-TYPE
                    SYNTAX INTEGER (0..2147483647)
                    MAX-ACCESS read-only
                    STATUS current
                    DESCRIPTION "Flags"
                    ::= {  setIproFirConneEntry 7 }

setIproFirConneFilt OBJECT-TYPE
                    SYNTAX DisplayString (SIZE(0..255))
                    MAX-ACCESS read-only
                    STATUS current
                    DESCRIPTION "Filter-Rule"
                    ::= {  setIproFirConneEntry 8 }

setIproFirConneSrcr OBJECT-TYPE
                    SYNTAX DisplayString (SIZE(0..255))
                    MAX-ACCESS read-only
                    STATUS current
                    DESCRIPTION "Src-Route"
                    ::= {  setIproFirConneEntry 9 }

setIproFirConneDest OBJECT-TYPE
                    SYNTAX DisplayString (SIZE(0..255))
                    MAX-ACCESS read-only
                    STATUS current
                    DESCRIPTION "Dest-Route"
                    ::= {  setIproFirConneEntry 10 }

setIproFirOpenpTable OBJECT-TYPE
                     SYNTAX SEQUENCE OF SetIproFirOpenpEntry
                     MAX-ACCESS not-accessible
                     STATUS current
                     DESCRIPTION "Open-Port-List"
                     ::= {  setIproFir 19 }

setIproFirOpenpEntry OBJECT-TYPE
                     SYNTAX SetIproFirOpenpEntry
                     MAX-ACCESS not-accessible
                     STATUS current
                     DESCRIPTION "entry in table"
                     INDEX { setIproFirOpenpSrca, setIproFirOpenpDsta, setIproFirOpenpProt, setIproFirOpenpDstp }
                     ::= {  setIproFirOpenpTable 1 }

SetIproFirOpenpEntry ::= SEQUENCE {
                     setIproFirOpenpSrca IpAddress,
                     setIproFirOpenpDsta IpAddress,
                     setIproFirOpenpProt INTEGER,
                     setIproFirOpenpDstp INTEGER,
                     setIproFirOpenpTime INTEGER,
                     setIproFirOpenpFilt DisplayString,
                     setIproFirOpenpSrcr DisplayString
                    }

setIproFirOpenpSrca OBJECT-TYPE
                    SYNTAX IpAddress
                    MAX-ACCESS read-only
                    STATUS current
                    DESCRIPTION "Src-Address"
                    ::= {  setIproFirOpenpEntry 1 }

setIproFirOpenpDsta OBJECT-TYPE
                    SYNTAX IpAddress
                    MAX-ACCESS read-only
                    STATUS current
                    DESCRIPTION "Dst-Address"
                    ::= {  setIproFirOpenpEntry 2 }

setIproFirOpenpProt OBJECT-TYPE
                    SYNTAX INTEGER (0..255)
                    MAX-ACCESS read-only
                    STATUS current
                    DESCRIPTION "Prot."
                    ::= {  setIproFirOpenpEntry 3 }

setIproFirOpenpDstp OBJECT-TYPE
                    SYNTAX INTEGER (0..65535)
                    MAX-ACCESS read-only
                    STATUS current
                    DESCRIPTION "Dst-Port"
                    ::= {  setIproFirOpenpEntry 5 }

setIproFirOpenpTime OBJECT-TYPE
                    SYNTAX INTEGER (0..65535)
                    MAX-ACCESS read-only
                    STATUS current
                    DESCRIPTION "Timeout"
                    ::= {  setIproFirOpenpEntry 6 }

setIproFirOpenpFilt OBJECT-TYPE
                    SYNTAX DisplayString (SIZE(0..255))
                    MAX-ACCESS read-only
                    STATUS current
                    DESCRIPTION "Filter-Rule"
                    ::= {  setIproFirOpenpEntry 8 }

setIproFirOpenpSrcr OBJECT-TYPE
                    SYNTAX DisplayString (SIZE(0..255))
                    MAX-ACCESS read-only
                    STATUS current
                    DESCRIPTION "Src-Route"
                    ::= {  setIproFirOpenpEntry 9 }

setIproFirHostbTable OBJECT-TYPE
                     SYNTAX SEQUENCE OF SetIproFirHostbEntry
                     MAX-ACCESS not-accessible
                     STATUS current
                     DESCRIPTION "Host-Block-List"
                     ::= {  setIproFir 6 }

setIproFirHostbEntry OBJECT-TYPE
                     SYNTAX SetIproFirHostbEntry
                     MAX-ACCESS not-accessible
                     STATUS current
                     DESCRIPTION "entry in table"
                     INDEX { setIproFirHostbSrc }
                     ::= {  setIproFirHostbTable 1 }

SetIproFirHostbEntry ::= SEQUENCE {
                     setIproFirHostbSrc IpAddress,
                     setIproFirHostbTim INTEGER,
                     setIproFirHostbFil DisplayString
                    }

setIproFirHostbSrc OBJECT-TYPE
                   SYNTAX IpAddress
                   MAX-ACCESS read-only
                   STATUS current
                   DESCRIPTION "Src-Address"
                   ::= {  setIproFirHostbEntry 1 }

setIproFirHostbTim OBJECT-TYPE
                   SYNTAX INTEGER (0..2147483647)
                   MAX-ACCESS read-only
                   STATUS current
                   DESCRIPTION "Timeout"
                   ::= {  setIproFirHostbEntry 2 }

setIproFirHostbFil OBJECT-TYPE
                   SYNTAX DisplayString (SIZE(0..255))
                   MAX-ACCESS read-only
                   STATUS current
                   DESCRIPTION "Filter-Rule"
                   ::= {  setIproFirHostbEntry 3 }

setIproFirPortbTable OBJECT-TYPE
                     SYNTAX SEQUENCE OF SetIproFirPortbEntry
                     MAX-ACCESS not-accessible
                     STATUS current
                     DESCRIPTION "Port-Block-List"
                     ::= {  setIproFir 7 }

setIproFirPortbEntry OBJECT-TYPE
                     SYNTAX SetIproFirPortbEntry
                     MAX-ACCESS not-accessible
                     STATUS current
                     DESCRIPTION "entry in table"
                     INDEX { setIproFirPortbDsta }
                     ::= {  setIproFirPortbTable 1 }

SetIproFirPortbEntry ::= SEQUENCE {
                     setIproFirPortbDsta IpAddress,
                     setIproFirPortbProt INTEGER,
                     setIproFirPortbDstp INTEGER,
                     setIproFirPortbTime INTEGER,
                     setIproFirPortbFilt DisplayString
                    }

setIproFirPortbDsta OBJECT-TYPE
                    SYNTAX IpAddress
                    MAX-ACCESS read-only
                    STATUS current
                    DESCRIPTION "Dst-Address"
                    ::= {  setIproFirPortbEntry 1 }

setIproFirPortbProt OBJECT-TYPE
                    SYNTAX INTEGER (0..65535)
                    MAX-ACCESS read-only
                    STATUS current
                    DESCRIPTION "Prot."
                    ::= {  setIproFirPortbEntry 2 }

setIproFirPortbDstp OBJECT-TYPE
                    SYNTAX INTEGER (0..65535)
                    MAX-ACCESS read-only
                    STATUS current
                    DESCRIPTION "Dst-Port"
                    ::= {  setIproFirPortbEntry 3 }

setIproFirPortbTime OBJECT-TYPE
                    SYNTAX INTEGER (0..2147483647)
                    MAX-ACCESS read-only
                    STATUS current
                    DESCRIPTION "Timeout"
                    ::= {  setIproFirPortbEntry 4 }

setIproFirPortbFilt OBJECT-TYPE
                    SYNTAX DisplayString (SIZE(0..255))
                    MAX-ACCESS read-only
                    STATUS current
                    DESCRIPTION "Filter-Rule"
                    ::= {  setIproFirPortbEntry 5 }

setIproFirMaxha OBJECT-TYPE
                SYNTAX INTEGER
                MAX-ACCESS read-write
                STATUS current
                DESCRIPTION "Max.-Half-Open-Conns."
                ::= {  setIproFir 8 }

setIproFirDosac OBJECT-TYPE
                SYNTAX DisplayString (SIZE(0..29))
                MAX-ACCESS read-write
                STATUS current
                DESCRIPTION "DoS-Action"
                ::= {  setIproFir 9 }

setIproFirPorts OBJECT-TYPE
                SYNTAX INTEGER
                MAX-ACCESS read-write
                STATUS current
                DESCRIPTION "Port-Scan-Threshold"
                ::= {  setIproFir 12 }

setIproFirIdsac OBJECT-TYPE
                SYNTAX DisplayString (SIZE(0..29))
                MAX-ACCESS read-write
                STATUS current
                DESCRIPTION "IDS-Action"
                ::= {  setIproFir 13 }

setIproFirAdmin OBJECT-TYPE
                SYNTAX DisplayString (SIZE(0..255))
                MAX-ACCESS read-write
                STATUS current
                DESCRIPTION "Admin.-Email"
                ::= {  setIproFir 10 }

setIproFirPingb OBJECT-TYPE
                SYNTAX INTEGER
                {
                  off(0),
                  allways(1),
                  wan(2),
                  default-route(3)
                }
                MAX-ACCESS read-write
                STATUS current
                DESCRIPTION "Ping-Block"
                ::= {  setIproFir 14 }

setIproFirSteal OBJECT-TYPE
                SYNTAX INTEGER
                {
                  off(0),
                  allways(1),
                  wan(2),
                  default-route(3)
                }
                MAX-ACCESS read-write
                STATUS current
                DESCRIPTION "Stealth-Mode"
                ::= {  setIproFir 15 }

setIproFirAuthp OBJECT-TYPE
                SYNTAX INTEGER
                {
                  closed(0),
                  stealth(1)
                }
                MAX-ACCESS read-write
                STATUS current
                DESCRIPTION "Auth-Port"
                ::= {  setIproFir 16 }

setIproFirDenys OBJECT-TYPE
                SYNTAX INTEGER
                {
                  off(0),
                  allways(1),
                  wan(2),
                  default-route(3)
                }
                MAX-ACCESS read-write
                STATUS current
                DESCRIPTION "Deny-Session-Recover"
                ::= {  setIproFir 17 }

setIproFirAppli OBJECT IDENTIFIER ::= { setIproFir 20}
setIproFirAppliFtp OBJECT IDENTIFIER ::= { setIproFirAppli 1}
setIproFirAppliFtpFtp OBJECT-TYPE
                      SYNTAX INTEGER
                      {
                        off(0),
                        allways(1),
                        wan(2),
                        default-route(3)
                      }
                      MAX-ACCESS read-write
                      STATUS current
                      DESCRIPTION "FTP-Block"
                      ::= {  setIproFirAppliFtp 1 }

setIproFirAppliFtpAct OBJECT-TYPE
                      SYNTAX INTEGER
                      {
                        off(0),
                        allways(1),
                        wan(2),
                        default-route(3)
                      }
                      MAX-ACCESS read-write
                      STATUS current
                      DESCRIPTION "Active-FTP-Block"
                      ::= {  setIproFirAppliFtp 2 }

setIproFirAppliFtpMin OBJECT-TYPE
                      SYNTAX INTEGER
                      MAX-ACCESS read-write
                      STATUS current
                      DESCRIPTION "Min-Port"
                      ::= {  setIproFirAppliFtp 3 }

setIproFirAppliFtpChe OBJECT-TYPE
                      SYNTAX INTEGER
                      {
                        off(0),
                        allways(1),
                        wan(2),
                        default-route(3)
                      }
                      MAX-ACCESS read-write
                      STATUS current
                      DESCRIPTION "Check-Host-IP"
                      ::= {  setIproFirAppliFtp 4 }

setIproFirAppliFtpFxp OBJECT-TYPE
                      SYNTAX INTEGER
                      {
                        off(0),
                        allways(1),
                        wan(2),
                        default-route(3)
                      }
                      MAX-ACCESS read-write
                      STATUS current
                      DESCRIPTION "FXP-Block"
                      ::= {  setIproFirAppliFtp 5 }

setIproFirAppliIrc OBJECT IDENTIFIER ::= { setIproFirAppli 2}
setIproFirAppliIrcIrc OBJECT-TYPE
                      SYNTAX INTEGER
                      {
                        off(0),
                        allways(1),
                        wan(2),
                        default-route(3)
                      }
                      MAX-ACCESS read-write
                      STATUS current
                      DESCRIPTION "IRC-Block"
                      ::= {  setIproFirAppliIrc 1 }

setIproFirAppliIrcDdc OBJECT-TYPE
                      SYNTAX INTEGER
                      {
                        off(0),
                        allways(1),
                        wan(2),
                        default-route(3)
                      }
                      MAX-ACCESS read-write
                      STATUS current
                      DESCRIPTION "DDC-Block"
                      ::= {  setIproFirAppliIrc 2 }

setIproFirAppliIrcMin OBJECT-TYPE
                      SYNTAX INTEGER
                      MAX-ACCESS read-write
                      STATUS current
                      DESCRIPTION "Min-Port"
                      ::= {  setIproFirAppliIrc 3 }

setIproFirAppliIrcChe OBJECT-TYPE
                      SYNTAX INTEGER
                      {
                        off(0),
                        allways(1),
                        wan(2),
                        default-route(3)
                      }
                      MAX-ACCESS read-write
                      STATUS current
                      DESCRIPTION "Check-Host-IP"
                      ::= {  setIproFirAppliIrc 4 }

setIproFirAppliApp OBJECT-TYPE
                   SYNTAX DisplayString (SIZE(0..29))
                   MAX-ACCESS read-write
                   STATUS current
                   DESCRIPTION "Appl.-Action"
                   ::= {  setIproFirAppli 10 }

setIproNnnTable OBJECT-TYPE
                SYNTAX SEQUENCE OF SetIproNnnEntry
                MAX-ACCESS not-accessible
                STATUS current
                DESCRIPTION "N-N-NAT"
                ::= {  setIpro 19 }

setIproNnnEntry OBJECT-TYPE
                SYNTAX SetIproNnnEntry
                MAX-ACCESS not-accessible
                STATUS current
                DESCRIPTION "entry in table"
                INDEX { setIproNnnIdx }
                ::= {  setIproNnnTable 1 }

SetIproNnnEntry ::= SEQUENCE {
                setIproNnnIdx DisplayString,
                setIproNnnSrca IpAddress,
                setIproNnnSrcm IpAddress,
                setIproNnnDsts DisplayString,
                setIproNnnMapp IpAddress
               }

setIproNnnIdx OBJECT-TYPE
               SYNTAX DisplayString (SIZE(0..4))
               MAX-ACCESS read-write
               STATUS current
               DESCRIPTION "Idx."
               ::= {  setIproNnnEntry 1 }

setIproNnnSrca OBJECT-TYPE
               SYNTAX IpAddress
               MAX-ACCESS read-write
               STATUS current
               DESCRIPTION "Src-Address"
               ::= {  setIproNnnEntry 2 }

setIproNnnSrcm OBJECT-TYPE
               SYNTAX IpAddress
               MAX-ACCESS read-write
               STATUS current
               DESCRIPTION "Src-Mask"
               ::= {  setIproNnnEntry 3 }

setIproNnnDsts OBJECT-TYPE
               SYNTAX DisplayString (SIZE(0..16))
               MAX-ACCESS read-write
               STATUS current
               DESCRIPTION "Dst-Station"
               ::= {  setIproNnnEntry 4 }

setIproNnnMapp OBJECT-TYPE
               SYNTAX IpAddress
               MAX-ACCESS read-write
               STATUS current
               DESCRIPTION "Mapped-Network"
               ::= {  setIproNnnEntry 5 }

setIproWan OBJECT-TYPE
           SYNTAX INTEGER
           {
             manual(0),
             auto(1)
           }
           MAX-ACCESS read-write
           STATUS current
           DESCRIPTION "WAN-Tag-Creation"
           ::= {  setIpro 22 }

setIproTagTable OBJECT-TYPE
                SYNTAX SEQUENCE OF SetIproTagEntry
                MAX-ACCESS not-accessible
                STATUS current
                DESCRIPTION "Tag-Table"
                ::= {  setIpro 23 }

setIproTagEntry OBJECT-TYPE
                SYNTAX SetIproTagEntry
                MAX-ACCESS not-accessible
                STATUS current
                DESCRIPTION "entry in table"
                INDEX { setIproTagPee }
                ::= {  setIproTagTable 1 }

SetIproTagEntry ::= SEQUENCE {
                setIproTagPee DisplayString,
                setIproTagRtg INTEGER,
                setIproTagSta IpAddress,
                setIproTagEnd IpAddress
               }

setIproTagPee OBJECT-TYPE
              SYNTAX DisplayString (SIZE(0..16))
              MAX-ACCESS read-write
              STATUS current
              DESCRIPTION "Peer"
              ::= {  setIproTagEntry 1 }

setIproTagRtg OBJECT-TYPE
              SYNTAX INTEGER (0..65535)
              MAX-ACCESS read-write
              STATUS current
              DESCRIPTION "Rtg-tag"
              ::= {  setIproTagEntry 2 }

setIproTagSta OBJECT-TYPE
              SYNTAX IpAddress
              MAX-ACCESS read-write
              STATUS current
              DESCRIPTION "Start-WAN-Pool"
              ::= {  setIproTagEntry 3 }

setIproTagEnd OBJECT-TYPE
              SYNTAX IpAddress
              MAX-ACCESS read-write
              STATUS current
              DESCRIPTION "End-WAN-Pool"
              ::= {  setIproTagEntry 4 }

setSnmp OBJECT IDENTIFIER ::= { set 9}
setSnmpSendtrap OBJECT-TYPE
                SYNTAX INTEGER
                {
                  no(0),
                  yes(1)
                }
                MAX-ACCESS read-write
                STATUS current
                DESCRIPTION "Send-Traps"
                ::= {  setSnmp 1 }

setSnmpIptrapsTable OBJECT-TYPE
                     SYNTAX SEQUENCE OF SetSnmpIptrapsEntry
                     MAX-ACCESS not-accessible
                     STATUS current
                     DESCRIPTION "IP-Traps"
                     ::= {  setSnmp 2 }

setSnmpIptrapsEntry OBJECT-TYPE
                     SYNTAX SetSnmpIptrapsEntry
                     MAX-ACCESS not-accessible
                     STATUS current
                     DESCRIPTION "entry in table"
                     INDEX { setSnmpIptrapsTra }
                     ::= {  setSnmpIptrapsTable 1 }

SetSnmpIptrapsEntry ::= SEQUENCE {
                     setSnmpIptrapsTra IpAddress,
                     setSnmpIptrapsLoo DisplayString,
                     setSnmpIptrapsVer INTEGER
                    }

setSnmpIptrapsTra OBJECT-TYPE
                  SYNTAX IpAddress
                  MAX-ACCESS read-write
                  STATUS current
                  DESCRIPTION "Trap-IP"
                  ::= {  setSnmpIptrapsEntry 1 }

setSnmpIptrapsLoo OBJECT-TYPE
                  SYNTAX DisplayString (SIZE(0..16))
                  MAX-ACCESS read-write
                  STATUS current
                  DESCRIPTION "Loopback-Addr."
                  ::= {  setSnmpIptrapsEntry 3 }

setSnmpIptrapsVer OBJECT-TYPE
                  SYNTAX INTEGER
                  {
                    snmpv1(1),
                    snmpv2(0)
                  }
                  MAX-ACCESS read-write
                  STATUS current
                  DESCRIPTION "Version"
                  ::= {  setSnmpIptrapsEntry 4 }

setSnmpAdminist OBJECT-TYPE
                SYNTAX DisplayString (SIZE(0..255))
                MAX-ACCESS read-write
                STATUS current
                DESCRIPTION "Administrator"
                ::= {  setSnmp 3 }

setSnmpLocation OBJECT-TYPE
                SYNTAX DisplayString (SIZE(0..255))
                MAX-ACCESS read-write
                STATUS current
                DESCRIPTION "Location"
                ::= {  setSnmp 4 }

setSnmpRegister OBJECT-TYPE
                SYNTAX DisplayString
                MAX-ACCESS read-write
                STATUS current
                DESCRIPTION "Register-Monitor"
                ::= {  setSnmp 5 }

setSnmpDeletemo OBJECT-TYPE
                SYNTAX DisplayString
                MAX-ACCESS read-write
                STATUS current
                DESCRIPTION "Delete-Monitor"
                ::= {  setSnmp 6 }

setSnmpMonitortTable OBJECT-TYPE
                     SYNTAX SEQUENCE OF SetSnmpMonitortEntry
                     MAX-ACCESS not-accessible
                     STATUS current
                     DESCRIPTION "Monitor-Table"
                     ::= {  setSnmp 7 }

setSnmpMonitortEntry OBJECT-TYPE
                     SYNTAX SetSnmpMonitortEntry
                     MAX-ACCESS not-accessible
                     STATUS current
                     DESCRIPTION "entry in table"
                     INDEX { setSnmpMonitortIpa, setSnmpMonitortPor }
                     ::= {  setSnmpMonitortTable 1 }

SetSnmpMonitortEntry ::= SEQUENCE {
                     setSnmpMonitortIpa IpAddress,
                     setSnmpMonitortPor INTEGER,
                     setSnmpMonitortMac DisplayString,
                     setSnmpMonitortVla INTEGER,
                     setSnmpMonitortTim INTEGER,
                     setSnmpMonitortPee DisplayString,
                     setSnmpMonitortLoo IpAddress,
                     setSnmpMonitortLan DisplayString,
                     setSnmpMonitortEth INTEGER
                    }

setSnmpMonitortIpa OBJECT-TYPE
                   SYNTAX IpAddress
                   MAX-ACCESS read-only
                   STATUS current
                   DESCRIPTION "IP-Address"
                   ::= {  setSnmpMonitortEntry 1 }

setSnmpMonitortPor OBJECT-TYPE
                   SYNTAX INTEGER (0..65535)
                   MAX-ACCESS read-only
                   STATUS current
                   DESCRIPTION "Port"
                   ::= {  setSnmpMonitortEntry 2 }

setSnmpMonitortMac OBJECT-TYPE
                   SYNTAX DisplayString (SIZE(0..12))
                   MAX-ACCESS read-only
                   STATUS current
                   DESCRIPTION "MAC-Address"
                   ::= {  setSnmpMonitortEntry 4 }

setSnmpMonitortVla OBJECT-TYPE
                   SYNTAX INTEGER (0..65535)
                   MAX-ACCESS read-only
                   STATUS current
                   DESCRIPTION "VLAN-ID"
                   ::= {  setSnmpMonitortEntry 7 }

setSnmpMonitortTim OBJECT-TYPE
                   SYNTAX INTEGER (0..65535)
                   MAX-ACCESS read-only
                   STATUS current
                   DESCRIPTION "Timeout"
                   ::= {  setSnmpMonitortEntry 3 }

setSnmpMonitortPee OBJECT-TYPE
                   SYNTAX DisplayString (SIZE(0..16))
                   MAX-ACCESS read-only
                   STATUS current
                   DESCRIPTION "Peer"
                   ::= {  setSnmpMonitortEntry 5 }

setSnmpMonitortLoo OBJECT-TYPE
                   SYNTAX IpAddress
                   MAX-ACCESS read-only
                   STATUS current
                   DESCRIPTION "Loopback-Addr."
                   ::= {  setSnmpMonitortEntry 6 }

setSnmpMonitortLan OBJECT-TYPE
                   SYNTAX DisplayString (SIZE(0..255))
                   MAX-ACCESS read-only
                   STATUS current
                   DESCRIPTION "LAN-Ifc"
                   ::= {  setSnmpMonitortEntry 8 }

setSnmpMonitortEth OBJECT-TYPE
                   SYNTAX INTEGER (0..255)
                   MAX-ACCESS read-only
                   STATUS current
                   DESCRIPTION "Ethernet-Port"
                   ::= {  setSnmpMonitortEntry 9 }

setSnmpPassword OBJECT-TYPE
                SYNTAX INTEGER
                {
                  no(0),
                  yes(1)
                }
                MAX-ACCESS read-write
                STATUS current
                DESCRIPTION "Password-Required-for-SNMP-Read-Access"
                ::= {  setSnmp 10 }

setSnmpReadonly OBJECT-TYPE
                SYNTAX DisplayString (SIZE(0..31))
                MAX-ACCESS read-write
                STATUS current
                DESCRIPTION "Read-Only-Community"
                ::= {  setSnmp 15 }

setSnmpComment1 OBJECT-TYPE
                SYNTAX DisplayString (SIZE(0..255))
                MAX-ACCESS read-write
                STATUS current
                DESCRIPTION "Comment-1"
                ::= {  setSnmp 11 }

setSnmpComment2 OBJECT-TYPE
                SYNTAX DisplayString (SIZE(0..255))
                MAX-ACCESS read-write
                STATUS current
                DESCRIPTION "Comment-2"
                ::= {  setSnmp 12 }

setSnmpComment3 OBJECT-TYPE
                SYNTAX DisplayString (SIZE(0..255))
                MAX-ACCESS read-write
                STATUS current
                DESCRIPTION "Comment-3"
                ::= {  setSnmp 13 }

setSnmpComment4 OBJECT-TYPE
                SYNTAX DisplayString (SIZE(0..255))
                MAX-ACCESS read-write
                STATUS current
                DESCRIPTION "Comment-4"
                ::= {  setSnmp 14 }

setDhcp OBJECT IDENTIFIER ::= { set 10}
setDhcpNetTable OBJECT-TYPE
                SYNTAX SEQUENCE OF SetDhcpNetEntry
                MAX-ACCESS not-accessible
                STATUS current
                DESCRIPTION "Network-list"
                ::= {  setDhcp 20 }

setDhcpNetEntry OBJECT-TYPE
                SYNTAX SetDhcpNetEntry
                MAX-ACCESS not-accessible
                STATUS current
                DESCRIPTION "entry in table"
                INDEX { setDhcpNetNetworknam }
                ::= {  setDhcpNetTable 1 }

SetDhcpNetEntry ::= SEQUENCE {
                setDhcpNetNetworknam DisplayString,
                setDhcpNetStartaddre IpAddress,
                setDhcpNetEndaddress IpAddress,
                setDhcpNetNetmask IpAddress,
                setDhcpNetBroadcasta IpAddress,
                setDhcpNetGatewayadd IpAddress,
                setDhcpNetDnsdefault IpAddress,
                setDhcpNetDnsbackup IpAddress,
                setDhcpNetNbnsdefaul IpAddress,
                setDhcpNetNbnsbackup IpAddress,
                setDhcpNetOperating INTEGER,
                setDhcpNetBroadcastb INTEGER,
                setDhcpNetMasterserv IpAddress,
                setDhcpNetCache INTEGER,
                setDhcpNetAdaption INTEGER
               }

setDhcpNetNetworknam OBJECT-TYPE
                     SYNTAX DisplayString (SIZE(0..16))
                     MAX-ACCESS read-write
                     STATUS current
                     DESCRIPTION "Network-name"
                     ::= {  setDhcpNetEntry 1 }

setDhcpNetStartaddre OBJECT-TYPE
                     SYNTAX IpAddress
                     MAX-ACCESS read-write
                     STATUS current
                     DESCRIPTION "Start-Address-Pool"
                     ::= {  setDhcpNetEntry 2 }

setDhcpNetEndaddress OBJECT-TYPE
                     SYNTAX IpAddress
                     MAX-ACCESS read-write
                     STATUS current
                     DESCRIPTION "End-Address-Pool"
                     ::= {  setDhcpNetEntry 3 }

setDhcpNetNetmask OBJECT-TYPE
                     SYNTAX IpAddress
                     MAX-ACCESS read-write
                     STATUS current
                     DESCRIPTION "Netmask"
                     ::= {  setDhcpNetEntry 4 }

setDhcpNetBroadcasta OBJECT-TYPE
                     SYNTAX IpAddress
                     MAX-ACCESS read-write
                     STATUS current
                     DESCRIPTION "Broadcast-Address"
                     ::= {  setDhcpNetEntry 5 }

setDhcpNetGatewayadd OBJECT-TYPE
                     SYNTAX IpAddress
                     MAX-ACCESS read-write
                     STATUS current
                     DESCRIPTION "Gateway-Address"
                     ::= {  setDhcpNetEntry 6 }

setDhcpNetDnsdefault OBJECT-TYPE
                     SYNTAX IpAddress
                     MAX-ACCESS read-write
                     STATUS current
                     DESCRIPTION "DNS-Default"
                     ::= {  setDhcpNetEntry 7 }

setDhcpNetDnsbackup OBJECT-TYPE
                     SYNTAX IpAddress
                     MAX-ACCESS read-write
                     STATUS current
                     DESCRIPTION "DNS-Backup"
                     ::= {  setDhcpNetEntry 8 }

setDhcpNetNbnsdefaul OBJECT-TYPE
                     SYNTAX IpAddress
                     MAX-ACCESS read-write
                     STATUS current
                     DESCRIPTION "NBNS-Default"
                     ::= {  setDhcpNetEntry 9 }

setDhcpNetNbnsbackup OBJECT-TYPE
                     SYNTAX IpAddress
                     MAX-ACCESS read-write
                     STATUS current
                     DESCRIPTION "NBNS-Backup"
                     ::= {  setDhcpNetEntry 10 }

setDhcpNetOperating OBJECT-TYPE
                     SYNTAX INTEGER
                     {
                       no(0),
                       yes(1),
                       auto(2),
                       relay(16),
                       client(4)
                     }
                     MAX-ACCESS read-write
                     STATUS current
                     DESCRIPTION "Operating"
                     ::= {  setDhcpNetEntry 11 }

setDhcpNetBroadcastb OBJECT-TYPE
                     SYNTAX INTEGER
                     {
                       no(0),
                       yes(1)
                     }
                     MAX-ACCESS read-write
                     STATUS current
                     DESCRIPTION "Broadcast-Bit"
                     ::= {  setDhcpNetEntry 12 }

setDhcpNetMasterserv OBJECT-TYPE
                     SYNTAX IpAddress
                     MAX-ACCESS read-write
                     STATUS current
                     DESCRIPTION "Master-Server"
                     ::= {  setDhcpNetEntry 13 }

setDhcpNetCache OBJECT-TYPE
                     SYNTAX INTEGER
                     {
                       no(0),
                       yes(1)
                     }
                     MAX-ACCESS read-write
                     STATUS current
                     DESCRIPTION "Cache"
                     ::= {  setDhcpNetEntry 14 }

setDhcpNetAdaption OBJECT-TYPE
                     SYNTAX INTEGER
                     {
                       no(0),
                       yes(1)
                     }
                     MAX-ACCESS read-write
                     STATUS current
                     DESCRIPTION "Adaption"
                     ::= {  setDhcpNetEntry 15 }

setDhcpPorTable OBJECT-TYPE
                SYNTAX SEQUENCE OF SetDhcpPorEntry
                MAX-ACCESS not-accessible
                STATUS current
                DESCRIPTION "Ports"
                ::= {  setDhcp 18 }

setDhcpPorEntry OBJECT-TYPE
                SYNTAX SetDhcpPorEntry
                MAX-ACCESS not-accessible
                STATUS current
                DESCRIPTION "entry in table"
                INDEX { setDhcpPorPor }
                ::= {  setDhcpPorTable 1 }

SetDhcpPorEntry ::= SEQUENCE {
                setDhcpPorPor DisplayString,
                setDhcpPorEna INTEGER
               }

setDhcpPorPor OBJECT-TYPE
              SYNTAX DisplayString (SIZE(0..9))
              MAX-ACCESS read-only
              STATUS current
              DESCRIPTION "Port"
              ::= {  setDhcpPorEntry 2 }

setDhcpPorEna OBJECT-TYPE
              SYNTAX INTEGER
              {
                no(0),
                yes(1)
              }
              MAX-ACCESS read-write
              STATUS current
              DESCRIPTION "Enable-DHCP"
              ::= {  setDhcpPorEntry 3 }

setDhcpMax OBJECT-TYPE
           SYNTAX INTEGER
           MAX-ACCESS read-write
           STATUS current
           DESCRIPTION "Max.-Lease-Time-Minutes"
           ::= {  setDhcp 6 }

setDhcpDef OBJECT-TYPE
           SYNTAX INTEGER
           MAX-ACCESS read-write
           STATUS current
           DESCRIPTION "Default-Lease-Time-Minutes"
           ::= {  setDhcp 7 }

setDhcpDhcTable OBJECT-TYPE
                SYNTAX SEQUENCE OF SetDhcpDhcEntry
                MAX-ACCESS not-accessible
                STATUS current
                DESCRIPTION "DHCP-Table"
                ::= {  setDhcp 8 }

setDhcpDhcEntry OBJECT-TYPE
                SYNTAX SetDhcpDhcEntry
                MAX-ACCESS not-accessible
                STATUS current
                DESCRIPTION "entry in table"
                INDEX { setDhcpDhcIpa, setDhcpDhcNet }
                ::= {  setDhcpDhcTable 1 }

SetDhcpDhcEntry ::= SEQUENCE {
                setDhcpDhcIpa IpAddress,
                setDhcpDhcMac DisplayString,
                setDhcpDhcTim INTEGER,
                setDhcpDhcHos DisplayString,
                setDhcpDhcTyp BITS,
                setDhcpDhcLan INTEGER,
                setDhcpDhcEth INTEGER,
                setDhcpDhcVla INTEGER,
                setDhcpDhcNet DisplayString
               }

setDhcpDhcIpa OBJECT-TYPE
              SYNTAX IpAddress
              MAX-ACCESS read-only
              STATUS current
              DESCRIPTION "IP-Address"
              ::= {  setDhcpDhcEntry 1 }

setDhcpDhcMac OBJECT-TYPE
              SYNTAX DisplayString (SIZE(0..12))
              MAX-ACCESS read-only
              STATUS current
              DESCRIPTION "MAC-Address"
              ::= {  setDhcpDhcEntry 2 }

setDhcpDhcTim OBJECT-TYPE
              SYNTAX INTEGER (0..2147483647)
              MAX-ACCESS read-only
              STATUS current
              DESCRIPTION "Timeout"
              ::= {  setDhcpDhcEntry 3 }

setDhcpDhcHos OBJECT-TYPE
              SYNTAX DisplayString (SIZE(0..64))
              MAX-ACCESS read-only
              STATUS current
              DESCRIPTION "Hostname"
              ::= {  setDhcpDhcEntry 4 }

setDhcpDhcTyp OBJECT-TYPE
              SYNTAX BITS
              {
                new(15),
                new(14),
                dyn(11),
                unkn(13),
                stat(12),
                bootp(10),
                relay(4)
              }
              MAX-ACCESS read-only
              STATUS current
              DESCRIPTION "Type"
              ::= {  setDhcpDhcEntry 5 }

setDhcpDhcLan OBJECT-TYPE
              SYNTAX INTEGER
              {
                lan-1(0),
                lan-2(1),
                lan-3(2),
                lan-4(3),
                any(255)
              }
              MAX-ACCESS read-only
              STATUS current
              DESCRIPTION "LAN-Ifc"
              ::= {  setDhcpDhcEntry 6 }

setDhcpDhcEth OBJECT-TYPE
              SYNTAX INTEGER
              {
                wan(1),
                eth-1(2),
                eth-2(3),
                eth-3(4),
                eth-4(5),
                unknown(0)
              }
              MAX-ACCESS read-only
              STATUS current
              DESCRIPTION "Ethernet-Port"
              ::= {  setDhcpDhcEntry 7 }

setDhcpDhcVla OBJECT-TYPE
              SYNTAX INTEGER (0..65535)
              MAX-ACCESS read-only
              STATUS current
              DESCRIPTION "VLAN-ID"
              ::= {  setDhcpDhcEntry 8 }

setDhcpDhcNet OBJECT-TYPE
              SYNTAX DisplayString (SIZE(0..17))
              MAX-ACCESS read-only
              STATUS current
              DESCRIPTION "Network-name"
              ::= {  setDhcpDhcEntry 9 }

setDhcpHosTable OBJECT-TYPE
                SYNTAX SEQUENCE OF SetDhcpHosEntry
                MAX-ACCESS not-accessible
                STATUS current
                DESCRIPTION "Hosts"
                ::= {  setDhcp 9 }

setDhcpHosEntry OBJECT-TYPE
                SYNTAX SetDhcpHosEntry
                MAX-ACCESS not-accessible
                STATUS current
                DESCRIPTION "entry in table"
                INDEX { setDhcpHosMac, setDhcpHosNet }
                ::= {  setDhcpHosTable 1 }

SetDhcpHosEntry ::= SEQUENCE {
                setDhcpHosMac DisplayString,
                setDhcpHosNet DisplayString,
                setDhcpHosIpa IpAddress,
                setDhcpHosHos DisplayString,
                setDhcpHosIma DisplayString
               }

setDhcpHosMac OBJECT-TYPE
              SYNTAX DisplayString (SIZE(0..12))
              MAX-ACCESS read-write
              STATUS current
              DESCRIPTION "MAC-Address"
              ::= {  setDhcpHosEntry 1 }

setDhcpHosNet OBJECT-TYPE
              SYNTAX DisplayString (SIZE(0..16))
              MAX-ACCESS read-write
              STATUS current
              DESCRIPTION "Network-name"
              ::= {  setDhcpHosEntry 5 }

setDhcpHosIpa OBJECT-TYPE
              SYNTAX IpAddress
              MAX-ACCESS read-write
              STATUS current
              DESCRIPTION "IP-Address"
              ::= {  setDhcpHosEntry 2 }

setDhcpHosHos OBJECT-TYPE
              SYNTAX DisplayString (SIZE(0..30))
              MAX-ACCESS read-write
              STATUS current
              DESCRIPTION "Hostname"
              ::= {  setDhcpHosEntry 3 }

setDhcpHosIma OBJECT-TYPE
              SYNTAX DisplayString (SIZE(0..16))
              MAX-ACCESS read-write
              STATUS current
              DESCRIPTION "Image-alias"
              ::= {  setDhcpHosEntry 4 }

setDhcpAliTable OBJECT-TYPE
                SYNTAX SEQUENCE OF SetDhcpAliEntry
                MAX-ACCESS not-accessible
                STATUS current
                DESCRIPTION "Alias-List"
                ::= {  setDhcp 10 }

setDhcpAliEntry OBJECT-TYPE
                SYNTAX SetDhcpAliEntry
                MAX-ACCESS not-accessible
                STATUS current
                DESCRIPTION "entry in table"
                INDEX { setDhcpAliImagea }
                ::= {  setDhcpAliTable 1 }

SetDhcpAliEntry ::= SEQUENCE {
                setDhcpAliImagea DisplayString,
                setDhcpAliImages IpAddress,
                setDhcpAliImagef DisplayString
               }

setDhcpAliImagea OBJECT-TYPE
                 SYNTAX DisplayString (SIZE(0..16))
                 MAX-ACCESS read-write
                 STATUS current
                 DESCRIPTION "Image-alias"
                 ::= {  setDhcpAliEntry 1 }

setDhcpAliImages OBJECT-TYPE
                 SYNTAX IpAddress
                 MAX-ACCESS read-write
                 STATUS current
                 DESCRIPTION "Image-Server"
                 ::= {  setDhcpAliEntry 3 }

setDhcpAliImagef OBJECT-TYPE
                 SYNTAX DisplayString (SIZE(0..60))
                 MAX-ACCESS read-write
                 STATUS current
                 DESCRIPTION "Image-file"
                 ::= {  setDhcpAliEntry 2 }

setDhcpAddTable OBJECT-TYPE
                SYNTAX SEQUENCE OF SetDhcpAddEntry
                MAX-ACCESS not-accessible
                STATUS current
                DESCRIPTION "Additional-Options"
                ::= {  setDhcp 21 }

setDhcpAddEntry OBJECT-TYPE
                SYNTAX SetDhcpAddEntry
                MAX-ACCESS not-accessible
                STATUS current
                DESCRIPTION "entry in table"
                INDEX { setDhcpAddOptionn, setDhcpAddNetwork }
                ::= {  setDhcpAddTable 1 }

SetDhcpAddEntry ::= SEQUENCE {
                setDhcpAddOptionn INTEGER,
                setDhcpAddNetwork DisplayString,
                setDhcpAddOptiont INTEGER,
                setDhcpAddOptionv DisplayString
               }

setDhcpAddOptionn OBJECT-TYPE
                  SYNTAX INTEGER (0..255)
                  MAX-ACCESS read-write
                  STATUS current
                  DESCRIPTION "Option-Number"
                  ::= {  setDhcpAddEntry 1 }

setDhcpAddNetwork OBJECT-TYPE
                  SYNTAX DisplayString (SIZE(0..16))
                  MAX-ACCESS read-write
                  STATUS current
                  DESCRIPTION "Network-name"
                  ::= {  setDhcpAddEntry 2 }

setDhcpAddOptiont OBJECT-TYPE
                  SYNTAX INTEGER
                  {
                    string(0),
                    integer32(1),
                    integer16(3),
                    integer8(4),
                    ip-address(2)
                  }
                  MAX-ACCESS read-write
                  STATUS current
                  DESCRIPTION "Option-Type"
                  ::= {  setDhcpAddEntry 4 }

setDhcpAddOptionv OBJECT-TYPE
                  SYNTAX DisplayString (SIZE(0..128))
                  MAX-ACCESS read-write
                  STATUS current
                  DESCRIPTION "Option-Value"
                  ::= {  setDhcpAddEntry 3 }

setDhcpUse OBJECT-TYPE
           SYNTAX DisplayString (SIZE(0..63))
           MAX-ACCESS read-write
           STATUS current
           DESCRIPTION "User-Class-Identifer"
           ::= {  setDhcp 19 }

setDns OBJECT IDENTIFIER ::= { set 17}
setDnsOper OBJECT-TYPE
           SYNTAX INTEGER
           {
             no(0),
             yes(1)
           }
           MAX-ACCESS read-write
           STATUS current
           DESCRIPTION "Operating"
           ::= {  setDns 1 }

setDnsDoma OBJECT-TYPE
           SYNTAX DisplayString (SIZE(0..64))
           MAX-ACCESS read-write
           STATUS current
           DESCRIPTION "Domain"
           ::= {  setDns 2 }

setDnsSubdTable OBJECT-TYPE
                SYNTAX SEQUENCE OF SetDnsSubdEntry
                MAX-ACCESS not-accessible
                STATUS current
                DESCRIPTION "Sub-Domains"
                ::= {  setDns 13 }

setDnsSubdEntry OBJECT-TYPE
                SYNTAX SetDnsSubdEntry
                MAX-ACCESS not-accessible
                STATUS current
                DESCRIPTION "entry in table"
                INDEX { setDnsSubdNet }
                ::= {  setDnsSubdTable 1 }

SetDnsSubdEntry ::= SEQUENCE {
                setDnsSubdNet DisplayString,
                setDnsSubdSub DisplayString
               }

setDnsSubdNet OBJECT-TYPE
              SYNTAX DisplayString (SIZE(0..16))
              MAX-ACCESS read-write
              STATUS current
              DESCRIPTION "Network-name"
              ::= {  setDnsSubdEntry 1 }

setDnsSubdSub OBJECT-TYPE
              SYNTAX DisplayString (SIZE(0..64))
              MAX-ACCESS read-write
              STATUS current
              DESCRIPTION "Sub-Domain"
              ::= {  setDnsSubdEntry 2 }

setDnsReso OBJECT-TYPE
           SYNTAX INTEGER
           {
             no(0),
             yes(1)
           }
           MAX-ACCESS read-write
           STATUS current
           DESCRIPTION "Resolve-Domain"
           ::= {  setDns 12 }

setDnsDhcp OBJECT-TYPE
           SYNTAX INTEGER
           {
             no(0),
             yes(1)
           }
           MAX-ACCESS read-write
           STATUS current
           DESCRIPTION "DHCP-Usage"
           ::= {  setDns 3 }

setDnsNetb OBJECT-TYPE
           SYNTAX INTEGER
           {
             no(0),
             yes(1)
           }
           MAX-ACCESS read-write
           STATUS current
           DESCRIPTION "NetBIOS-Usage"
           ::= {  setDns 4 }

setDnsDnslTable OBJECT-TYPE
                SYNTAX SEQUENCE OF SetDnsDnslEntry
                MAX-ACCESS not-accessible
                STATUS current
                DESCRIPTION "DNS-List"
                ::= {  setDns 5 }

setDnsDnslEntry OBJECT-TYPE
                SYNTAX SetDnsDnslEntry
                MAX-ACCESS not-accessible
                STATUS current
                DESCRIPTION "entry in table"
                INDEX { setDnsDnslHos }
                ::= {  setDnsDnslTable 1 }

SetDnsDnslEntry ::= SEQUENCE {
                setDnsDnslHos DisplayString,
                setDnsDnslIpa IpAddress
               }

setDnsDnslHos OBJECT-TYPE
              SYNTAX DisplayString (SIZE(0..64))
              MAX-ACCESS read-write
              STATUS current
              DESCRIPTION "Host-name"
              ::= {  setDnsDnslEntry 1 }

setDnsDnslIpa OBJECT-TYPE
              SYNTAX IpAddress
              MAX-ACCESS read-write
              STATUS current
              DESCRIPTION "IP-Address"
              ::= {  setDnsDnslEntry 2 }

setDnsFiltTable OBJECT-TYPE
                SYNTAX SEQUENCE OF SetDnsFiltEntry
                MAX-ACCESS not-accessible
                STATUS current
                DESCRIPTION "Filter-List"
                ::= {  setDns 6 }

setDnsFiltEntry OBJECT-TYPE
                SYNTAX SetDnsFiltEntry
                MAX-ACCESS not-accessible
                STATUS current
                DESCRIPTION "entry in table"
                INDEX { setDnsFiltIdx }
                ::= {  setDnsFiltTable 1 }

SetDnsFiltEntry ::= SEQUENCE {
                setDnsFiltIdx DisplayString,
                setDnsFiltDom DisplayString,
                setDnsFiltIpa IpAddress,
                setDnsFiltNet IpAddress
               }

setDnsFiltIdx OBJECT-TYPE
              SYNTAX DisplayString (SIZE(0..4))
              MAX-ACCESS read-write
              STATUS current
              DESCRIPTION "Idx."
              ::= {  setDnsFiltEntry 1 }

setDnsFiltDom OBJECT-TYPE
              SYNTAX DisplayString (SIZE(0..64))
              MAX-ACCESS read-write
              STATUS current
              DESCRIPTION "Domain"
              ::= {  setDnsFiltEntry 2 }

setDnsFiltIpa OBJECT-TYPE
              SYNTAX IpAddress
              MAX-ACCESS read-write
              STATUS current
              DESCRIPTION "IP-Address"
              ::= {  setDnsFiltEntry 3 }

setDnsFiltNet OBJECT-TYPE
              SYNTAX IpAddress
              MAX-ACCESS read-write
              STATUS current
              DESCRIPTION "Netmask"
              ::= {  setDnsFiltEntry 4 }

setDnsDyndTable OBJECT-TYPE
                SYNTAX SEQUENCE OF SetDnsDyndEntry
                MAX-ACCESS not-accessible
                STATUS current
                DESCRIPTION "Dyn.-DNS-List"
                ::= {  setDns 8 }

setDnsDyndEntry OBJECT-TYPE
                SYNTAX SetDnsDyndEntry
                MAX-ACCESS not-accessible
                STATUS current
                DESCRIPTION "entry in table"
                INDEX { setDnsDyndHos }
                ::= {  setDnsDyndTable 1 }

SetDnsDyndEntry ::= SEQUENCE {
                setDnsDyndHos DisplayString,
                setDnsDyndIpa IpAddress,
                setDnsDyndTim INTEGER
               }

setDnsDyndHos OBJECT-TYPE
              SYNTAX DisplayString (SIZE(0..64))
              MAX-ACCESS read-only
              STATUS current
              DESCRIPTION "Host-name"
              ::= {  setDnsDyndEntry 1 }

setDnsDyndIpa OBJECT-TYPE
              SYNTAX IpAddress
              MAX-ACCESS read-only
              STATUS current
              DESCRIPTION "IP-Address"
              ::= {  setDnsDyndEntry 2 }

setDnsDyndTim OBJECT-TYPE
              SYNTAX INTEGER (0..2147483647)
              MAX-ACCESS read-only
              STATUS current
              DESCRIPTION "Timeout"
              ::= {  setDnsDyndEntry 3 }

setDnsDnsdTable OBJECT-TYPE
                SYNTAX SEQUENCE OF SetDnsDnsdEntry
                MAX-ACCESS not-accessible
                STATUS current
                DESCRIPTION "DNS-Destinations"
                ::= {  setDns 9 }

setDnsDnsdEntry OBJECT-TYPE
                SYNTAX SetDnsDnsdEntry
                MAX-ACCESS not-accessible
                STATUS current
                DESCRIPTION "entry in table"
                INDEX { setDnsDnsdDom }
                ::= {  setDnsDnsdTable 1 }

SetDnsDnsdEntry ::= SEQUENCE {
                setDnsDnsdDom DisplayString,
                setDnsDnsdDes DisplayString
               }

setDnsDnsdDom OBJECT-TYPE
              SYNTAX DisplayString (SIZE(0..64))
              MAX-ACCESS read-write
              STATUS current
              DESCRIPTION "Domain-name"
              ::= {  setDnsDnsdEntry 1 }

setDnsDnsdDes OBJECT-TYPE
              SYNTAX DisplayString (SIZE(0..31))
              MAX-ACCESS read-write
              STATUS current
              DESCRIPTION "Destination"
              ::= {  setDnsDnsdEntry 2 }

setDnsLeas OBJECT-TYPE
           SYNTAX INTEGER
           MAX-ACCESS read-write
           STATUS current
           DESCRIPTION "Leasetime"
           ::= {  setDns 7 }

setDnsServTable OBJECT-TYPE
                SYNTAX SEQUENCE OF SetDnsServEntry
                MAX-ACCESS not-accessible
                STATUS current
                DESCRIPTION "Service-Location-List"
                ::= {  setDns 10 }

setDnsServEntry OBJECT-TYPE
                SYNTAX SetDnsServEntry
                MAX-ACCESS not-accessible
                STATUS current
                DESCRIPTION "entry in table"
                INDEX { setDnsServSer }
                ::= {  setDnsServTable 1 }

SetDnsServEntry ::= SEQUENCE {
                setDnsServSer DisplayString,
                setDnsServHos DisplayString,
                setDnsServPor INTEGER
               }

setDnsServSer OBJECT-TYPE
              SYNTAX DisplayString (SIZE(0..64))
              MAX-ACCESS read-write
              STATUS current
              DESCRIPTION "Service-Name"
              ::= {  setDnsServEntry 1 }

setDnsServHos OBJECT-TYPE
              SYNTAX DisplayString (SIZE(0..64))
              MAX-ACCESS read-write
              STATUS current
              DESCRIPTION "Host-name"
              ::= {  setDnsServEntry 2 }

setDnsServPor OBJECT-TYPE
              SYNTAX INTEGER (0..65535)
              MAX-ACCESS read-write
              STATUS current
              DESCRIPTION "Port"
              ::= {  setDnsServEntry 3 }

setDnsDynaTable OBJECT-TYPE
                SYNTAX SEQUENCE OF SetDnsDynaEntry
                MAX-ACCESS not-accessible
                STATUS current
                DESCRIPTION "Dynamic-SRV-List"
                ::= {  setDns 11 }

setDnsDynaEntry OBJECT-TYPE
                SYNTAX SetDnsDynaEntry
                MAX-ACCESS not-accessible
                STATUS current
                DESCRIPTION "entry in table"
                INDEX { setDnsDynaSer }
                ::= {  setDnsDynaTable 1 }

SetDnsDynaEntry ::= SEQUENCE {
                setDnsDynaSer DisplayString,
                setDnsDynaHos DisplayString,
                setDnsDynaPor INTEGER
               }

setDnsDynaSer OBJECT-TYPE
              SYNTAX DisplayString (SIZE(0..64))
              MAX-ACCESS read-only
              STATUS current
              DESCRIPTION "Service-Name"
              ::= {  setDnsDynaEntry 1 }

setDnsDynaHos OBJECT-TYPE
              SYNTAX DisplayString (SIZE(0..64))
              MAX-ACCESS read-only
              STATUS current
              DESCRIPTION "Host-name"
              ::= {  setDnsDynaEntry 2 }

setDnsDynaPor OBJECT-TYPE
              SYNTAX INTEGER (0..65535)
              MAX-ACCESS read-only
              STATUS current
              DESCRIPTION "Port"
              ::= {  setDnsDynaEntry 3 }

setNetb OBJECT IDENTIFIER ::= { set 16}
setNetbOpe OBJECT-TYPE
           SYNTAX INTEGER
           {
             no(0),
             yes(1)
           }
           MAX-ACCESS read-write
           STATUS current
           DESCRIPTION "Operating"
           ::= {  setNetb 1 }

setNetbNetTable OBJECT-TYPE
                SYNTAX SEQUENCE OF SetNetbNetEntry
                MAX-ACCESS not-accessible
                STATUS current
                DESCRIPTION "Networks"
                ::= {  setNetb 12 }

setNetbNetEntry OBJECT-TYPE
                SYNTAX SetNetbNetEntry
                MAX-ACCESS not-accessible
                STATUS current
                DESCRIPTION "entry in table"
                INDEX { setNetbNetNet }
                ::= {  setNetbNetTable 1 }

SetNetbNetEntry ::= SEQUENCE {
                setNetbNetNet DisplayString,
                setNetbNetOpe INTEGER,
                setNetbNetNtd DisplayString
               }

setNetbNetNet OBJECT-TYPE
              SYNTAX DisplayString (SIZE(0..16))
              MAX-ACCESS read-write
              STATUS current
              DESCRIPTION "Network-name"
              ::= {  setNetbNetEntry 1 }

setNetbNetOpe OBJECT-TYPE
              SYNTAX INTEGER
              {
                no(0),
                yes(1)
              }
              MAX-ACCESS read-write
              STATUS current
              DESCRIPTION "Operating"
              ::= {  setNetbNetEntry 2 }

setNetbNetNtd OBJECT-TYPE
              SYNTAX DisplayString (SIZE(0..15))
              MAX-ACCESS read-write
              STATUS current
              DESCRIPTION "NT-Domain"
              ::= {  setNetbNetEntry 3 }

setNetbSco OBJECT-TYPE
           SYNTAX DisplayString (SIZE(0..64))
           MAX-ACCESS read-write
           STATUS current
           DESCRIPTION "Scope-ID"
           ::= {  setNetb 2 }

setNetbPeeTable OBJECT-TYPE
                SYNTAX SEQUENCE OF SetNetbPeeEntry
                MAX-ACCESS not-accessible
                STATUS current
                DESCRIPTION "Peers"
                ::= {  setNetb 4 }

setNetbPeeEntry OBJECT-TYPE
                SYNTAX SetNetbPeeEntry
                MAX-ACCESS not-accessible
                STATUS current
                DESCRIPTION "entry in table"
                INDEX { setNetbPeeNam }
                ::= {  setNetbPeeTable 1 }

SetNetbPeeEntry ::= SEQUENCE {
                setNetbPeeNam DisplayString,
                setNetbPeeTyp INTEGER
               }

setNetbPeeNam OBJECT-TYPE
              SYNTAX DisplayString (SIZE(0..16))
              MAX-ACCESS read-write
              STATUS current
              DESCRIPTION "Name"
              ::= {  setNetbPeeEntry 1 }

setNetbPeeTyp OBJECT-TYPE
              SYNTAX INTEGER
              {
                workstation(1),
                router(0)
              }
              MAX-ACCESS read-write
              STATUS current
              DESCRIPTION "Type"
              ::= {  setNetbPeeEntry 3 }

setNetbGroTable OBJECT-TYPE
                SYNTAX SEQUENCE OF SetNetbGroEntry
                MAX-ACCESS not-accessible
                STATUS current
                DESCRIPTION "Group-List"
                ::= {  setNetb 5 }

setNetbGroEntry OBJECT-TYPE
                SYNTAX SetNetbGroEntry
                MAX-ACCESS not-accessible
                STATUS current
                DESCRIPTION "entry in table"
                INDEX { setNetbGroGro, setNetbGroTyp, setNetbGroIpa, setNetbGroRtg }
                ::= {  setNetbGroTable 1 }

SetNetbGroEntry ::= SEQUENCE {
                setNetbGroGro DisplayString,
                setNetbGroTyp DisplayString,
                setNetbGroIpa IpAddress,
                setNetbGroRtg INTEGER,
                setNetbGroPee DisplayString,
                setNetbGroNet DisplayString,
                setNetbGroTim INTEGER,
                setNetbGroFla DisplayString
               }

setNetbGroGro OBJECT-TYPE
              SYNTAX DisplayString (SIZE(0..15))
              MAX-ACCESS read-only
              STATUS current
              DESCRIPTION "Group/Domain"
              ::= {  setNetbGroEntry 1 }

setNetbGroTyp OBJECT-TYPE
              SYNTAX DisplayString (SIZE(0..1))
              MAX-ACCESS read-only
              STATUS current
              DESCRIPTION "Type"
              ::= {  setNetbGroEntry 2 }

setNetbGroIpa OBJECT-TYPE
              SYNTAX IpAddress
              MAX-ACCESS read-only
              STATUS current
              DESCRIPTION "IP-Address"
              ::= {  setNetbGroEntry 3 }

setNetbGroRtg OBJECT-TYPE
              SYNTAX INTEGER (0..65535)
              MAX-ACCESS read-only
              STATUS current
              DESCRIPTION "Rtg-tag"
              ::= {  setNetbGroEntry 8 }

setNetbGroPee OBJECT-TYPE
              SYNTAX DisplayString (SIZE(0..16))
              MAX-ACCESS read-only
              STATUS current
              DESCRIPTION "Peer"
              ::= {  setNetbGroEntry 4 }

setNetbGroNet OBJECT-TYPE
              SYNTAX DisplayString (SIZE(0..16))
              MAX-ACCESS read-only
              STATUS current
              DESCRIPTION "Network-name"
              ::= {  setNetbGroEntry 7 }

setNetbGroTim OBJECT-TYPE
              SYNTAX INTEGER (0..2147483647)
              MAX-ACCESS read-only
              STATUS current
              DESCRIPTION "Timeout"
              ::= {  setNetbGroEntry 5 }

setNetbGroFla OBJECT-TYPE
              SYNTAX DisplayString (SIZE(0..2))
              MAX-ACCESS read-only
              STATUS current
              DESCRIPTION "Flags"
              ::= {  setNetbGroEntry 6 }

setNetbHosTable OBJECT-TYPE
                SYNTAX SEQUENCE OF SetNetbHosEntry
                MAX-ACCESS not-accessible
                STATUS current
                DESCRIPTION "Host-List"
                ::= {  setNetb 6 }

setNetbHosEntry OBJECT-TYPE
                SYNTAX SetNetbHosEntry
                MAX-ACCESS not-accessible
                STATUS current
                DESCRIPTION "entry in table"
                INDEX { setNetbHosNam, setNetbHosTyp, setNetbHosIpa, setNetbHosRtg }
                ::= {  setNetbHosTable 1 }

SetNetbHosEntry ::= SEQUENCE {
                setNetbHosNam DisplayString,
                setNetbHosTyp DisplayString,
                setNetbHosIpa IpAddress,
                setNetbHosRtg INTEGER,
                setNetbHosPee DisplayString,
                setNetbHosNet DisplayString,
                setNetbHosTim INTEGER,
                setNetbHosFla DisplayString
               }

setNetbHosNam OBJECT-TYPE
              SYNTAX DisplayString (SIZE(0..15))
              MAX-ACCESS read-only
              STATUS current
              DESCRIPTION "Name"
              ::= {  setNetbHosEntry 1 }

setNetbHosTyp OBJECT-TYPE
              SYNTAX DisplayString (SIZE(0..1))
              MAX-ACCESS read-only
              STATUS current
              DESCRIPTION "Type"
              ::= {  setNetbHosEntry 2 }

setNetbHosIpa OBJECT-TYPE
              SYNTAX IpAddress
              MAX-ACCESS read-only
              STATUS current
              DESCRIPTION "IP-Address"
              ::= {  setNetbHosEntry 3 }

setNetbHosRtg OBJECT-TYPE
              SYNTAX INTEGER (0..65535)
              MAX-ACCESS read-only
              STATUS current
              DESCRIPTION "Rtg-tag"
              ::= {  setNetbHosEntry 8 }

setNetbHosPee OBJECT-TYPE
              SYNTAX DisplayString (SIZE(0..16))
              MAX-ACCESS read-only
              STATUS current
              DESCRIPTION "Peer"
              ::= {  setNetbHosEntry 4 }

setNetbHosNet OBJECT-TYPE
              SYNTAX DisplayString (SIZE(0..16))
              MAX-ACCESS read-only
              STATUS current
              DESCRIPTION "Network-name"
              ::= {  setNetbHosEntry 7 }

setNetbHosTim OBJECT-TYPE
              SYNTAX INTEGER (0..2147483647)
              MAX-ACCESS read-only
              STATUS current
              DESCRIPTION "Timeout"
              ::= {  setNetbHosEntry 5 }

setNetbHosFla OBJECT-TYPE
              SYNTAX DisplayString (SIZE(0..2))
              MAX-ACCESS read-only
              STATUS current
              DESCRIPTION "Flags"
              ::= {  setNetbHosEntry 6 }

setNetbSerTable OBJECT-TYPE
                SYNTAX SEQUENCE OF SetNetbSerEntry
                MAX-ACCESS not-accessible
                STATUS current
                DESCRIPTION "Server-List"
                ::= {  setNetb 7 }

setNetbSerEntry OBJECT-TYPE
                SYNTAX SetNetbSerEntry
                MAX-ACCESS not-accessible
                STATUS current
                DESCRIPTION "entry in table"
                INDEX { setNetbSerHos, setNetbSerGro, setNetbSerIpa, setNetbSerRtg }
                ::= {  setNetbSerTable 1 }

SetNetbSerEntry ::= SEQUENCE {
                setNetbSerHos DisplayString,
                setNetbSerGro DisplayString,
                setNetbSerIpa DisplayString,
                setNetbSerRtg INTEGER,
                setNetbSerOsv DisplayString,
                setNetbSerSmb DisplayString,
                setNetbSerSer DisplayString,
                setNetbSerPee DisplayString,
                setNetbSerNet DisplayString,
                setNetbSerTim INTEGER,
                setNetbSerFla DisplayString
               }

setNetbSerHos OBJECT-TYPE
              SYNTAX DisplayString (SIZE(0..15))
              MAX-ACCESS read-only
              STATUS current
              DESCRIPTION "Host"
              ::= {  setNetbSerEntry 1 }

setNetbSerGro OBJECT-TYPE
              SYNTAX DisplayString (SIZE(0..16))
              MAX-ACCESS read-only
              STATUS current
              DESCRIPTION "Group/Domain"
              ::= {  setNetbSerEntry 2 }

setNetbSerIpa OBJECT-TYPE
              SYNTAX DisplayString (SIZE(0..15))
              MAX-ACCESS read-only
              STATUS current
              DESCRIPTION "IP-Address"
              ::= {  setNetbSerEntry 4 }

setNetbSerRtg OBJECT-TYPE
              SYNTAX INTEGER (0..65535)
              MAX-ACCESS read-only
              STATUS current
              DESCRIPTION "Rtg-tag"
              ::= {  setNetbSerEntry 12 }

setNetbSerOsv OBJECT-TYPE
              SYNTAX DisplayString (SIZE(0..2))
              MAX-ACCESS read-only
              STATUS current
              DESCRIPTION "OS-Ver."
              ::= {  setNetbSerEntry 5 }

setNetbSerSmb OBJECT-TYPE
              SYNTAX DisplayString (SIZE(0..2))
              MAX-ACCESS read-only
              STATUS current
              DESCRIPTION "SMB-Ver."
              ::= {  setNetbSerEntry 6 }

setNetbSerSer OBJECT-TYPE
              SYNTAX DisplayString (SIZE(0..4))
              MAX-ACCESS read-only
              STATUS current
              DESCRIPTION "Server-Typ"
              ::= {  setNetbSerEntry 7 }

setNetbSerPee OBJECT-TYPE
              SYNTAX DisplayString (SIZE(0..16))
              MAX-ACCESS read-only
              STATUS current
              DESCRIPTION "Peer"
              ::= {  setNetbSerEntry 8 }

setNetbSerNet OBJECT-TYPE
              SYNTAX DisplayString (SIZE(0..16))
              MAX-ACCESS read-only
              STATUS current
              DESCRIPTION "Network-name"
              ::= {  setNetbSerEntry 11 }

setNetbSerTim OBJECT-TYPE
              SYNTAX INTEGER (0..2147483647)
              MAX-ACCESS read-only
              STATUS current
              DESCRIPTION "Timeout"
              ::= {  setNetbSerEntry 9 }

setNetbSerFla OBJECT-TYPE
              SYNTAX DisplayString (SIZE(0..2))
              MAX-ACCESS read-only
              STATUS current
              DESCRIPTION "Flags"
              ::= {  setNetbSerEntry 10 }

setNetbBroTable OBJECT-TYPE
                SYNTAX SEQUENCE OF SetNetbBroEntry
                MAX-ACCESS not-accessible
                STATUS current
                DESCRIPTION "Browser-List"
                ::= {  setNetb 13 }

setNetbBroEntry OBJECT-TYPE
                SYNTAX SetNetbBroEntry
                MAX-ACCESS not-accessible
                STATUS current
                DESCRIPTION "entry in table"
                INDEX { setNetbBroBro, setNetbBroGro, setNetbBroIpa, setNetbBroRtg }
                ::= {  setNetbBroTable 1 }

SetNetbBroEntry ::= SEQUENCE {
                setNetbBroBro DisplayString,
                setNetbBroGro DisplayString,
                setNetbBroIpa DisplayString,
                setNetbBroRtg INTEGER,
                setNetbBroOsv DisplayString,
                setNetbBroSer DisplayString,
                setNetbBroPee DisplayString,
                setNetbBroNet DisplayString,
                setNetbBroTim INTEGER,
                setNetbBroFla DisplayString
               }

setNetbBroBro OBJECT-TYPE
              SYNTAX DisplayString (SIZE(0..15))
              MAX-ACCESS read-only
              STATUS current
              DESCRIPTION "Browser"
              ::= {  setNetbBroEntry 1 }

setNetbBroGro OBJECT-TYPE
              SYNTAX DisplayString (SIZE(0..16))
              MAX-ACCESS read-only
              STATUS current
              DESCRIPTION "Group/Domain"
              ::= {  setNetbBroEntry 2 }

setNetbBroIpa OBJECT-TYPE
              SYNTAX DisplayString (SIZE(0..15))
              MAX-ACCESS read-only
              STATUS current
              DESCRIPTION "IP-Address"
              ::= {  setNetbBroEntry 4 }

setNetbBroRtg OBJECT-TYPE
              SYNTAX INTEGER (0..65535)
              MAX-ACCESS read-only
              STATUS current
              DESCRIPTION "Rtg-tag"
              ::= {  setNetbBroEntry 12 }

setNetbBroOsv OBJECT-TYPE
              SYNTAX DisplayString (SIZE(0..2))
              MAX-ACCESS read-only
              STATUS current
              DESCRIPTION "OS-Ver."
              ::= {  setNetbBroEntry 5 }

setNetbBroSer OBJECT-TYPE
              SYNTAX DisplayString (SIZE(0..4))
              MAX-ACCESS read-only
              STATUS current
              DESCRIPTION "Server-Typ"
              ::= {  setNetbBroEntry 7 }

setNetbBroPee OBJECT-TYPE
              SYNTAX DisplayString (SIZE(0..16))
              MAX-ACCESS read-only
              STATUS current
              DESCRIPTION "Peer"
              ::= {  setNetbBroEntry 8 }

setNetbBroNet OBJECT-TYPE
              SYNTAX DisplayString (SIZE(0..16))
              MAX-ACCESS read-only
              STATUS current
              DESCRIPTION "Network-name"
              ::= {  setNetbBroEntry 11 }

setNetbBroTim OBJECT-TYPE
              SYNTAX INTEGER (0..2147483647)
              MAX-ACCESS read-only
              STATUS current
              DESCRIPTION "Timeout"
              ::= {  setNetbBroEntry 9 }

setNetbBroFla OBJECT-TYPE
              SYNTAX DisplayString (SIZE(0..2))
              MAX-ACCESS read-only
              STATUS current
              DESCRIPTION "Flags"
              ::= {  setNetbBroEntry 10 }

setNetbSup OBJECT-TYPE
           SYNTAX INTEGER
           {
             no(0),
             yes(1)
           }
           MAX-ACCESS read-write
           STATUS current
           DESCRIPTION "Support-Browsing"
           ::= {  setNetb 14 }

setNetbWat OBJECT-TYPE
           SYNTAX INTEGER
           {
             spoof(1),
             route(0)
           }
           MAX-ACCESS read-write
           STATUS current
           DESCRIPTION "Watchdogs"
           ::= {  setNetb 8 }

setNetbUpd OBJECT-TYPE
           SYNTAX INTEGER
           {
             pback(0),
             trig(1),
             time(2)
           }
           MAX-ACCESS read-write
           STATUS current
           DESCRIPTION "Update"
           ::= {  setNetb 9 }

setNetbWan OBJECT-TYPE
           SYNTAX INTEGER
           MAX-ACCESS read-write
           STATUS current
           DESCRIPTION "WAN-Update-Minutes"
           ::= {  setNetb 10 }

setNetbLea OBJECT-TYPE
           SYNTAX INTEGER
           MAX-ACCESS read-write
           STATUS current
           DESCRIPTION "Leasetime"
           ::= {  setNetb 11 }

setConf OBJECT IDENTIFIER ::= { set 11}
setConfPasswor OBJECT-TYPE
               SYNTAX INTEGER
               {
                 no(0),
                 yes(1)
               }
               MAX-ACCESS read-write
               STATUS current
               DESCRIPTION "Password-Required-for-SNMP-Read-Access"
               ::= {  setConf 3 }

setConfAdminea OBJECT-TYPE
               SYNTAX DisplayString (SIZE(0..31))
               MAX-ACCESS read-write
               STATUS current
               DESCRIPTION "Admin.-EAZ-MSN"
               ::= {  setConf 9 }

setConfMaximum OBJECT-TYPE
               SYNTAX INTEGER
               MAX-ACCESS read-write
               STATUS current
               DESCRIPTION "Maximum-Connections"
               ::= {  setConf 4 }

setConfConfiga OBJECT-TYPE
               SYNTAX INTEGER
               MAX-ACCESS read-write
               STATUS current
               DESCRIPTION "Config-Aging-Minutes"
               ::= {  setConf 5 }

setConfOutband OBJECT-TYPE
               SYNTAX INTEGER
               MAX-ACCESS read-write
               STATUS current
               DESCRIPTION "Outband-Aging-Minutes"
               ::= {  setConf 33 }

setConfLoginer OBJECT-TYPE
               SYNTAX INTEGER
               MAX-ACCESS read-write
               STATUS current
               DESCRIPTION "Login-Errors"
               ::= {  setConf 7 }

setConfLockmin OBJECT-TYPE
               SYNTAX INTEGER
               MAX-ACCESS read-write
               STATUS current
               DESCRIPTION "Lock-Minutes"
               ::= {  setConf 8 }

setConfLanguag OBJECT-TYPE
               SYNTAX INTEGER
               {
                 english(1),
                 deutsch(2)
               }
               MAX-ACCESS read-write
               STATUS current
               DESCRIPTION "Language"
               ::= {  setConf 6 }

setConfTftpcli OBJECT IDENTIFIER ::= { setConf 13}
setConfTftpcliConfigadd OBJECT-TYPE
                        SYNTAX DisplayString (SIZE(0..31))
                        MAX-ACCESS read-write
                        STATUS current
                        DESCRIPTION "Config-Address"
                        ::= {  setConfTftpcli 1 }

setConfTftpcliConfigfil OBJECT-TYPE
                        SYNTAX DisplayString (SIZE(0..63))
                        MAX-ACCESS read-write
                        STATUS current
                        DESCRIPTION "Config-Filename"
                        ::= {  setConfTftpcli 2 }

setConfTftpcliFirmwarea OBJECT-TYPE
                        SYNTAX DisplayString (SIZE(0..31))
                        MAX-ACCESS read-write
                        STATUS current
                        DESCRIPTION "Firmware-Address"
                        ::= {  setConfTftpcli 3 }

setConfTftpcliFirmwaref OBJECT-TYPE
                        SYNTAX DisplayString (SIZE(0..63))
                        MAX-ACCESS read-write
                        STATUS current
                        DESCRIPTION "Firmware-Filename"
                        ::= {  setConfTftpcli 4 }

setConfTftpcliScriptadd OBJECT-TYPE
                        SYNTAX DisplayString (SIZE(0..31))
                        MAX-ACCESS read-write
                        STATUS current
                        DESCRIPTION "Script-Address"
                        ::= {  setConfTftpcli 6 }

setConfTftpcliScriptfil OBJECT-TYPE
                        SYNTAX DisplayString (SIZE(0..63))
                        MAX-ACCESS read-write
                        STATUS current
                        DESCRIPTION "Script-Filename"
                        ::= {  setConfTftpcli 7 }

setConfTftpcliBytesperh OBJECT-TYPE
                        SYNTAX INTEGER
                        MAX-ACCESS read-write
                        STATUS current
                        DESCRIPTION "Bytes-per-Hashmark"
                        ::= {  setConfTftpcli 5 }

setConfAccesstTable OBJECT-TYPE
                    SYNTAX SEQUENCE OF SetConfAccesstEntry
                    MAX-ACCESS not-accessible
                    STATUS current
                    DESCRIPTION "Access-Table"
                    ::= {  setConf 15 }

setConfAccesstEntry OBJECT-TYPE
                    SYNTAX SetConfAccesstEntry
                    MAX-ACCESS not-accessible
                    STATUS current
                    DESCRIPTION "entry in table"
                    INDEX { setConfAccesstIfc }
                    ::= {  setConfAccesstTable 1 }

SetConfAccesstEntry ::= SEQUENCE {
                    setConfAccesstIfc INTEGER,
                    setConfAccesstTelnet INTEGER,
                    setConfAccesstTftp INTEGER,
                    setConfAccesstHttp INTEGER,
                    setConfAccesstSnmp INTEGER,
                    setConfAccesstHttps INTEGER,
                    setConfAccesstTelnets INTEGER,
                    setConfAccesstSsh INTEGER
                   }

setConfAccesstIfc OBJECT-TYPE
                      SYNTAX INTEGER
                      {
                        lan(1),
                        wan(2)
                      }
                      MAX-ACCESS read-only
                      STATUS current
                      DESCRIPTION "Ifc."
                      ::= {  setConfAccesstEntry 1 }

setConfAccesstTelnet OBJECT-TYPE
                      SYNTAX INTEGER
                      {
                        vpn(16),
                        yes(1),
                        read(4),
                        no(0)
                      }
                      MAX-ACCESS read-write
                      STATUS current
                      DESCRIPTION "Telnet"
                      ::= {  setConfAccesstEntry 2 }

setConfAccesstTftp OBJECT-TYPE
                      SYNTAX INTEGER
                      {
                        vpn(16),
                        yes(1),
                        read(4),
                        no(0)
                      }
                      MAX-ACCESS read-write
                      STATUS current
                      DESCRIPTION "TFTP"
                      ::= {  setConfAccesstEntry 3 }

setConfAccesstHttp OBJECT-TYPE
                      SYNTAX INTEGER
                      {
                        vpn(16),
                        yes(1),
                        read(4),
                        no(0)
                      }
                      MAX-ACCESS read-write
                      STATUS current
                      DESCRIPTION "HTTP"
                      ::= {  setConfAccesstEntry 4 }

setConfAccesstSnmp OBJECT-TYPE
                      SYNTAX INTEGER
                      {
                        vpn(16),
                        yes(1),
                        read(4),
                        no(0)
                      }
                      MAX-ACCESS read-write
                      STATUS current
                      DESCRIPTION "SNMP"
                      ::= {  setConfAccesstEntry 5 }

setConfAccesstHttps OBJECT-TYPE
                      SYNTAX INTEGER
                      {
                        vpn(16),
                        yes(1),
                        read(4),
                        no(0)
                      }
                      MAX-ACCESS read-write
                      STATUS current
                      DESCRIPTION "HTTPS"
                      ::= {  setConfAccesstEntry 6 }

setConfAccesstTelnets OBJECT-TYPE
                      SYNTAX INTEGER
                      {
                        vpn(16),
                        yes(1),
                        read(4),
                        no(0)
                      }
                      MAX-ACCESS read-write
                      STATUS current
                      DESCRIPTION "Telnet-SSL"
                      ::= {  setConfAccesstEntry 7 }

setConfAccesstSsh OBJECT-TYPE
                      SYNTAX INTEGER
                      {
                        vpn(16),
                        yes(1),
                        read(4),
                        no(0)
                      }
                      MAX-ACCESS read-write
                      STATUS current
                      DESCRIPTION "SSH"
                      ::= {  setConfAccesstEntry 8 }

setConfScreenh OBJECT-TYPE
               SYNTAX INTEGER
               MAX-ACCESS read-write
               STATUS current
               DESCRIPTION "Screen-Height"
               ::= {  setConf 16 }

setConfFunctioTable OBJECT-TYPE
                    SYNTAX SEQUENCE OF SetConfFunctioEntry
                    MAX-ACCESS not-accessible
                    STATUS current
                    DESCRIPTION "Function-Keys"
                    ::= {  setConf 43 }

setConfFunctioEntry OBJECT-TYPE
                    SYNTAX SetConfFunctioEntry
                    MAX-ACCESS not-accessible
                    STATUS current
                    DESCRIPTION "entry in table"
                    INDEX { setConfFunctioKey }
                    ::= {  setConfFunctioTable 1 }

SetConfFunctioEntry ::= SEQUENCE {
                    setConfFunctioKey INTEGER,
                    setConfFunctioMap DisplayString
                   }

setConfFunctioKey OBJECT-TYPE
                  SYNTAX INTEGER
                  {
                    f1(1),
                    f2(2),
                    f3(3),
                    f4(4),
                    f5(5),
                    f6(6),
                    f7(7),
                    f8(8),
                    f9(9),
                    f10(10),
                    f11(11),
                    f12(12)
                  }
                  MAX-ACCESS read-write
                  STATUS current
                  DESCRIPTION "Key"
                  ::= {  setConfFunctioEntry 1 }

setConfFunctioMap OBJECT-TYPE
                  SYNTAX DisplayString (SIZE(0..99))
                  MAX-ACCESS read-write
                  STATUS current
                  DESCRIPTION "Mapping"
                  ::= {  setConfFunctioEntry 2 }

setConfLl2m OBJECT IDENTIFIER ::= { setConf 50}
setConfLl2mOpe OBJECT-TYPE
               SYNTAX INTEGER
               {
                 no(0),
                 yes(1)
               }
               MAX-ACCESS read-write
               STATUS current
               DESCRIPTION "Operating"
               ::= {  setConfLl2m 1 }

setConfLl2mTim OBJECT-TYPE
               SYNTAX INTEGER
               MAX-ACCESS read-write
               STATUS current
               DESCRIPTION "Time-Limit"
               ::= {  setConfLl2m 2 }

setConfCrashme OBJECT-TYPE
               SYNTAX DisplayString (SIZE(0..32))
               MAX-ACCESS read-write
               STATUS current
               DESCRIPTION "Crash-Message"
               ::= {  setConf 40 }

setConfAdminge OBJECT-TYPE
               SYNTAX INTEGER
               {
                 unknown(0),
                 male(1),
                 female(2),
                 geek(3)
               }
               MAX-ACCESS read-write
               STATUS current
               DESCRIPTION "Admin-Gender"
               ::= {  setConf 41 }

setConfAsserta OBJECT-TYPE
               SYNTAX INTEGER
               {
                 log-only(0),
                 reboot(1)
               }
               MAX-ACCESS read-write
               STATUS current
               DESCRIPTION "Assert-Action"
               ::= {  setConf 42 }

setConfPrompt OBJECT-TYPE
               SYNTAX DisplayString (SIZE(0..31))
               MAX-ACCESS read-write
               STATUS current
               DESCRIPTION "Prompt"
               ::= {  setConf 17 }

setConfLedtest OBJECT-TYPE
               SYNTAX INTEGER
               {
                 off(0),
                 green(2),
                 red(1),
                 no-test(255)
               }
               MAX-ACCESS read-write
               STATUS current
               DESCRIPTION "LED-Test"
               ::= {  setConf 18 }

setConfCrontabTable OBJECT-TYPE
                    SYNTAX SEQUENCE OF SetConfCrontabEntry
                    MAX-ACCESS not-accessible
                    STATUS current
                    DESCRIPTION "Cron-Table"
                    ::= {  setConf 20 }

setConfCrontabEntry OBJECT-TYPE
                    SYNTAX SetConfCrontabEntry
                    MAX-ACCESS not-accessible
                    STATUS current
                    DESCRIPTION "entry in table"
                    INDEX { setConfCrontabInde }
                    ::= {  setConfCrontabTable 1 }

SetConfCrontabEntry ::= SEQUENCE {
                    setConfCrontabInde INTEGER,
                    setConfCrontabActi INTEGER,
                    setConfCrontabBase INTEGER,
                    setConfCrontabVari INTEGER,
                    setConfCrontabMinu DisplayString,
                    setConfCrontabHour DisplayString,
                    setConfCrontabDayo DisplayString,
                    setConfCrontabDay DisplayString,
                    setConfCrontabMont DisplayString,
                    setConfCrontabComm DisplayString,
                    setConfCrontabOwne DisplayString
                   }

setConfCrontabInde OBJECT-TYPE
                   SYNTAX INTEGER (0..65535)
                   MAX-ACCESS read-write
                   STATUS current
                   DESCRIPTION "Index"
                   ::= {  setConfCrontabEntry 1 }

setConfCrontabActi OBJECT-TYPE
                   SYNTAX INTEGER
                   {
                     yes(0),
                     no(1)
                   }
                   MAX-ACCESS read-write
                   STATUS current
                   DESCRIPTION "Active"
                   ::= {  setConfCrontabEntry 9 }

setConfCrontabBase OBJECT-TYPE
                   SYNTAX INTEGER
                   {
                     real-time(0),
                     operation-time(1)
                   }
                   MAX-ACCESS read-write
                   STATUS current
                   DESCRIPTION "Base"
                   ::= {  setConfCrontabEntry 8 }

setConfCrontabVari OBJECT-TYPE
                   SYNTAX INTEGER (0..65535)
                   MAX-ACCESS read-write
                   STATUS current
                   DESCRIPTION "Variation"
                   ::= {  setConfCrontabEntry 11 }

setConfCrontabMinu OBJECT-TYPE
                   SYNTAX DisplayString (SIZE(0..50))
                   MAX-ACCESS read-write
                   STATUS current
                   DESCRIPTION "Minute"
                   ::= {  setConfCrontabEntry 2 }

setConfCrontabHour OBJECT-TYPE
                   SYNTAX DisplayString (SIZE(0..50))
                   MAX-ACCESS read-write
                   STATUS current
                   DESCRIPTION "Hour"
                   ::= {  setConfCrontabEntry 3 }

setConfCrontabDayo OBJECT-TYPE
                   SYNTAX DisplayString (SIZE(0..50))
                   MAX-ACCESS read-write
                   STATUS current
                   DESCRIPTION "DayOfWeek"
                   ::= {  setConfCrontabEntry 4 }

setConfCrontabDay OBJECT-TYPE
                   SYNTAX DisplayString (SIZE(0..50))
                   MAX-ACCESS read-write
                   STATUS current
                   DESCRIPTION "Day"
                   ::= {  setConfCrontabEntry 5 }

setConfCrontabMont OBJECT-TYPE
                   SYNTAX DisplayString (SIZE(0..50))
                   MAX-ACCESS read-write
                   STATUS current
                   DESCRIPTION "Month"
                   ::= {  setConfCrontabEntry 6 }

setConfCrontabComm OBJECT-TYPE
                   SYNTAX DisplayString (SIZE(0..100))
                   MAX-ACCESS read-write
                   STATUS current
                   DESCRIPTION "Command"
                   ::= {  setConfCrontabEntry 7 }

setConfCrontabOwne OBJECT-TYPE
                   SYNTAX DisplayString (SIZE(0..16))
                   MAX-ACCESS read-write
                   STATUS current
                   DESCRIPTION "Owner"
                   ::= {  setConfCrontabEntry 10 }

setConfAdminsTable OBJECT-TYPE
                    SYNTAX SEQUENCE OF SetConfAdminsEntry
                    MAX-ACCESS not-accessible
                    STATUS current
                    DESCRIPTION "Admins"
                    ::= {  setConf 21 }

setConfAdminsEntry OBJECT-TYPE
                    SYNTAX SetConfAdminsEntry
                    MAX-ACCESS not-accessible
                    STATUS current
                    DESCRIPTION "entry in table"
                    INDEX { setConfAdminsAdm }
                    ::= {  setConfAdminsTable 1 }

SetConfAdminsEntry ::= SEQUENCE {
                    setConfAdminsAdm DisplayString,
                    setConfAdminsPas DisplayString,
                    setConfAdminsAct INTEGER,
                    setConfAdminsAcc INTEGER,
                    setConfAdminsFun BITS
                   }

setConfAdminsAdm OBJECT-TYPE
                 SYNTAX DisplayString (SIZE(0..16))
                 MAX-ACCESS read-write
                 STATUS current
                 DESCRIPTION "Administrator"
                 ::= {  setConfAdminsEntry 1 }

setConfAdminsPas OBJECT-TYPE
                 SYNTAX DisplayString (SIZE(0..16))
                 MAX-ACCESS read-write
                 STATUS current
                 DESCRIPTION "Password"
                 ::= {  setConfAdminsEntry 2 }

setConfAdminsAct OBJECT-TYPE
                 SYNTAX INTEGER
                 {
                   no(1),
                   yes(0)
                 }
                 MAX-ACCESS read-write
                 STATUS current
                 DESCRIPTION "Active"
                 ::= {  setConfAdminsEntry 4 }

setConfAdminsAcc OBJECT-TYPE
                 SYNTAX INTEGER
                 {
                   none(0),
                   admin-ro-limit(8388608),
                   admin-rw-limit(8388864),
                   admin-ro(16777216),
                   admin-rw(16777472),
                   supervisor(-1)
                 }
                 MAX-ACCESS read-write
                 STATUS current
                 DESCRIPTION "Access-Rights"
                 ::= {  setConfAdminsEntry 5 }

setConfAdminsFun OBJECT-TYPE
                 SYNTAX BITS
                 {
                   basic-wizard(31),
                   security-wizard(30),
                   internet-wizard(29),
                   ras-wizard(27),
                   provider-selection(28),
                   lanlan-wizard(26),
                   time-setting(25),
                   device-search(24),
                   rollout-wizard(18),
                   dynamic-dns-wizard(17)
                 }
                 MAX-ACCESS read-write
                 STATUS current
                 DESCRIPTION "Function-Rights"
                 ::= {  setConfAdminsEntry 3 }

setConfPredefaTable OBJECT-TYPE
                    SYNTAX SEQUENCE OF SetConfPredefaEntry
                    MAX-ACCESS not-accessible
                    STATUS current
                    DESCRIPTION "Predef.-Admins"
                    ::= {  setConf 27 }

setConfPredefaEntry OBJECT-TYPE
                    SYNTAX SetConfPredefaEntry
                    MAX-ACCESS not-accessible
                    STATUS current
                    DESCRIPTION "entry in table"
                    INDEX { setConfPredefaNam }
                    ::= {  setConfPredefaTable 1 }

SetConfPredefaEntry ::= SEQUENCE {
                    setConfPredefaNam DisplayString
                   }

setConfPredefaNam OBJECT-TYPE
                  SYNTAX DisplayString (SIZE(0..15))
                  MAX-ACCESS read-only
                  STATUS current
                  DESCRIPTION "Name"
                  ::= {  setConfPredefaEntry 1 }

setConfLan OBJECT-TYPE
               SYNTAX INTEGER
               MAX-ACCESS not-accessible
               STATUS current
               DESCRIPTION "LAN"
               ::= {  setConf 1 }

setConfWan OBJECT-TYPE
               SYNTAX INTEGER
               MAX-ACCESS not-accessible
               STATUS current
               DESCRIPTION "WAN"
               ::= {  setConf 2 }

setConfTelnetp OBJECT-TYPE
               SYNTAX INTEGER
               MAX-ACCESS read-write
               STATUS current
               DESCRIPTION "Telnet-Port"
               ::= {  setConf 23 }

setConfTelnets OBJECT-TYPE
               SYNTAX INTEGER
               MAX-ACCESS read-write
               STATUS current
               DESCRIPTION "Telnet-SSL-Port"
               ::= {  setConf 24 }

setConfResetbu OBJECT-TYPE
               SYNTAX INTEGER
               {
                 ignore(0),
                 boot-only(1),
                 reset-or-boot(2)
               }
               MAX-ACCESS read-write
               STATUS current
               DESCRIPTION "Reset-button"
               ::= {  setConf 32 }

setConfMonitor OBJECT IDENTIFIER ::= { setConf 35}
setConfMonitorTracemask1 OBJECT-TYPE
                         SYNTAX INTEGER
                         MAX-ACCESS read-only
                         STATUS current
                         DESCRIPTION "Tracemask1"
                         ::= {  setConfMonitor 1 }

setConfMonitorTracemask2 OBJECT-TYPE
                         SYNTAX INTEGER
                         MAX-ACCESS read-only
                         STATUS current
                         DESCRIPTION "Tracemask2"
                         ::= {  setConfMonitor 2 }

setConfUpdatec OBJECT IDENTIFIER ::= { setConf 30}
setConfUpdatecOperati OBJECT-TYPE
                      SYNTAX INTEGER
                      {
                        no(0),
                        yes(1)
                      }
                      MAX-ACCESS read-write
                      STATUS current
                      DESCRIPTION "Operating"
                      ::= {  setConfUpdatec 1 }

setConfUpdatecServern OBJECT-TYPE
                      SYNTAX DisplayString (SIZE(0..64))
                      MAX-ACCESS read-write
                      STATUS current
                      DESCRIPTION "Server-Name"
                      ::= {  setConfUpdatec 2 }

setConfUpdatecServerp OBJECT-TYPE
                      SYNTAX INTEGER
                      MAX-ACCESS read-write
                      STATUS current
                      DESCRIPTION "Server-Port"
                      ::= {  setConfUpdatec 3 }

setConfUpdatecRespons OBJECT-TYPE
                      SYNTAX INTEGER
                      MAX-ACCESS read-write
                      STATUS current
                      DESCRIPTION "Response-Timeout"
                      ::= {  setConfUpdatec 4 }

setConfUpdatecRetryfa OBJECT-TYPE
                      SYNTAX INTEGER
                      MAX-ACCESS read-write
                      STATUS current
                      DESCRIPTION "Retry-Failure"
                      ::= {  setConfUpdatec 5 }

setConfUpdatecRetryok OBJECT-TYPE
                      SYNTAX INTEGER
                      MAX-ACCESS read-write
                      STATUS current
                      DESCRIPTION "Retry-Ok"
                      ::= {  setConfUpdatec 6 }

setConfUpdatecLastfir OBJECT-TYPE
                      SYNTAX DisplayString (SIZE(0..21))
                      MAX-ACCESS read-only
                      STATUS current
                      DESCRIPTION "Last-Firmware-Update"
                      ::= {  setConfUpdatec 7 }

setConfUpdatecLastcon OBJECT-TYPE
                      SYNTAX DisplayString (SIZE(0..21))
                      MAX-ACCESS read-only
                      STATUS current
                      DESCRIPTION "Last-Config-Update"
                      ::= {  setConfUpdatec 8 }

setConfAntithe OBJECT IDENTIFIER ::= { setConf 31}
setConfAntitheEna OBJECT-TYPE
                  SYNTAX INTEGER
                  {
                    no(0),
                    yes(1)
                  }
                  MAX-ACCESS read-write
                  STATUS current
                  DESCRIPTION "Enabled"
                  ::= {  setConfAntithe 1 }

setConfAntitheMet OBJECT-TYPE
                  SYNTAX INTEGER
                  {
                    basic-call(0),
                    facility(1)
                  }
                  MAX-ACCESS read-write
                  STATUS current
                  DESCRIPTION "Method"
                  ::= {  setConfAntithe 6 }

setConfAntitheIsd OBJECT-TYPE
                  SYNTAX INTEGER
                  {
                    s0-1(1)
                  }
                  MAX-ACCESS read-write
                  STATUS current
                  DESCRIPTION "ISDN-Ifc"
                  ::= {  setConfAntithe 7 }

setConfAntitheCal OBJECT-TYPE
                  SYNTAX DisplayString (SIZE(0..14))
                  MAX-ACCESS read-write
                  STATUS current
                  DESCRIPTION "Called-Number"
                  ::= {  setConfAntithe 2 }

setConfAntitheOut OBJECT-TYPE
                  SYNTAX DisplayString (SIZE(0..14))
                  MAX-ACCESS read-write
                  STATUS current
                  DESCRIPTION "Outgoing-Calling-Number"
                  ::= {  setConfAntithe 3 }

setConfAntitheChe OBJECT-TYPE
                  SYNTAX DisplayString (SIZE(0..14))
                  MAX-ACCESS read-write
                  STATUS current
                  DESCRIPTION "Checked-Calling-Number"
                  ::= {  setConfAntithe 4 }

setConfSshport OBJECT-TYPE
               SYNTAX INTEGER
               MAX-ACCESS read-write
               STATUS current
               DESCRIPTION "SSH-Port"
               ::= {  setConf 25 }

setConfSshauthTable OBJECT-TYPE
                    SYNTAX SEQUENCE OF SetConfSshauthEntry
                    MAX-ACCESS not-accessible
                    STATUS current
                    DESCRIPTION "SSH-Authentication-Methods"
                    ::= {  setConf 26 }

setConfSshauthEntry OBJECT-TYPE
                    SYNTAX SetConfSshauthEntry
                    MAX-ACCESS not-accessible
                    STATUS current
                    DESCRIPTION "entry in table"
                    INDEX { setConfSshauthIfc }
                    ::= {  setConfSshauthTable 1 }

SetConfSshauthEntry ::= SEQUENCE {
                    setConfSshauthIfc INTEGER,
                    setConfSshauthMet INTEGER
                   }

setConfSshauthIfc OBJECT-TYPE
                  SYNTAX INTEGER
                  {
                    lan(1),
                    wan(2)
                  }
                  MAX-ACCESS read-only
                  STATUS current
                  DESCRIPTION "Ifc."
                  ::= {  setConfSshauthEntry 1 }

setConfSshauthMet OBJECT-TYPE
                  SYNTAX INTEGER
                  {
                    public-key(1),
                    password(2),
                    all(255)
                  }
                  MAX-ACCESS read-write
                  STATUS current
                  DESCRIPTION "Methods"
                  ::= {  setConfSshauthEntry 2 }

setLanc OBJECT IDENTIFIER ::= { set 13}
setLancAccTable OBJECT-TYPE
                SYNTAX SEQUENCE OF SetLancAccEntry
                MAX-ACCESS not-accessible
                STATUS current
                DESCRIPTION "Access-List"
                ::= {  setLanc 1 }

setLancAccEntry OBJECT-TYPE
                SYNTAX SetLancAccEntry
                MAX-ACCESS not-accessible
                STATUS current
                DESCRIPTION "entry in table"
                INDEX { setLancAccIpa, setLancAccIpn, setLancAccRtg }
                ::= {  setLancAccTable 1 }

SetLancAccEntry ::= SEQUENCE {
                setLancAccIpa IpAddress,
                setLancAccIpn IpAddress,
                setLancAccRtg INTEGER
               }

setLancAccIpa OBJECT-TYPE
              SYNTAX IpAddress
              MAX-ACCESS read-write
              STATUS current
              DESCRIPTION "IP-Address"
              ::= {  setLancAccEntry 1 }

setLancAccIpn OBJECT-TYPE
              SYNTAX IpAddress
              MAX-ACCESS read-write
              STATUS current
              DESCRIPTION "IP-Netmask"
              ::= {  setLancAccEntry 2 }

setLancAccRtg OBJECT-TYPE
              SYNTAX INTEGER (0..65535)
              MAX-ACCESS read-write
              STATUS current
              DESCRIPTION "Rtg-tag"
              ::= {  setLancAccEntry 3 }

setLancUdp OBJECT-TYPE
           SYNTAX INTEGER
           MAX-ACCESS read-write
           STATUS current
           DESCRIPTION "UDP-Port"
           ::= {  setLanc 3 }

setLancIntTable OBJECT-TYPE
                SYNTAX SEQUENCE OF SetLancIntEntry
                MAX-ACCESS not-accessible
                STATUS current
                DESCRIPTION "Interface-List"
                ::= {  setLanc 6 }

setLancIntEntry OBJECT-TYPE
                SYNTAX SetLancIntEntry
                MAX-ACCESS not-accessible
                STATUS current
                DESCRIPTION "entry in table"
                INDEX { setLancIntIfc }
                ::= {  setLancIntTable 1 }

SetLancIntEntry ::= SEQUENCE {
                setLancIntIfc INTEGER,
                setLancIntOpe INTEGER,
                setLancIntMax INTEGER,
                setLancIntEaz DisplayString,
                setLancIntFor INTEGER
               }

setLancIntIfc OBJECT-TYPE
              SYNTAX INTEGER
              {
                s0-1(1)
              }
              MAX-ACCESS read-only
              STATUS current
              DESCRIPTION "Ifc"
              ::= {  setLancIntEntry 1 }

setLancIntOpe OBJECT-TYPE
              SYNTAX INTEGER
              {
                no(0),
                yes(1),
                dial-only(2),
                dial-in-only(3)
              }
              MAX-ACCESS read-write
              STATUS current
              DESCRIPTION "Operating"
              ::= {  setLancIntEntry 2 }

setLancIntMax OBJECT-TYPE
              SYNTAX INTEGER (0..255)
              MAX-ACCESS read-write
              STATUS current
              DESCRIPTION "Max-Connections"
              ::= {  setLancIntEntry 6 }

setLancIntEaz OBJECT-TYPE
              SYNTAX DisplayString (SIZE(0..30))
              MAX-ACCESS read-write
              STATUS current
              DESCRIPTION "EAZ-MSN(s)"
              ::= {  setLancIntEntry 3 }

setLancIntFor OBJECT-TYPE
              SYNTAX INTEGER
              {
                no(0),
                yes(1)
              }
              MAX-ACCESS read-write
              STATUS current
              DESCRIPTION "Force-Out-MSN"
              ::= {  setLancIntEntry 5 }

setLancPriTable OBJECT-TYPE
                SYNTAX SEQUENCE OF SetLancPriEntry
                MAX-ACCESS not-accessible
                STATUS current
                DESCRIPTION "Priority-List"
                ::= {  setLanc 7 }

setLancPriEntry OBJECT-TYPE
                SYNTAX SetLancPriEntry
                MAX-ACCESS not-accessible
                STATUS current
                DESCRIPTION "entry in table"
                INDEX { setLancPriIfc }
                ::= {  setLancPriTable 1 }

SetLancPriEntry ::= SEQUENCE {
                setLancPriIfc INTEGER,
                setLancPriPri INTEGER
               }

setLancPriIfc OBJECT-TYPE
              SYNTAX INTEGER
              {
                s0-1(1)
              }
              MAX-ACCESS read-only
              STATUS current
              DESCRIPTION "Ifc"
              ::= {  setLancPriEntry 1 }

setLancPriPri OBJECT-TYPE
              SYNTAX INTEGER
              {
                p1(0),
                p2(1),
                p3(2)
              }
              MAX-ACCESS read-write
              STATUS current
              DESCRIPTION "Prio-out"
              ::= {  setLancPriEntry 2 }

setLcr OBJECT IDENTIFIER ::= { set 15}
setLcrRou OBJECT-TYPE
          SYNTAX INTEGER
          {
            no(0),
            yes(1)
          }
          MAX-ACCESS read-write
          STATUS current
          DESCRIPTION "Router-Usage"
          ::= {  setLcr 1 }

setLcrLan OBJECT-TYPE
          SYNTAX INTEGER
          {
            no(0),
            yes(1)
          }
          MAX-ACCESS read-write
          STATUS current
          DESCRIPTION "Lancapi-Usage"
          ::= {  setLcr 2 }

setLcrTimTable OBJECT-TYPE
               SYNTAX SEQUENCE OF SetLcrTimEntry
               MAX-ACCESS not-accessible
               STATUS current
               DESCRIPTION "Time-List"
               ::= {  setLcr 4 }

setLcrTimEntry OBJECT-TYPE
               SYNTAX SetLcrTimEntry
               MAX-ACCESS not-accessible
               STATUS current
               DESCRIPTION "entry in table"
               INDEX { setLcrTimInd }
               ::= {  setLcrTimTable 1 }

SetLcrTimEntry ::= SEQUENCE {
               setLcrTimInd INTEGER,
               setLcrTimPre DisplayString,
               setLcrTimDay BITS,
               setLcrTimSta DisplayString,
               setLcrTimSto DisplayString,
               setLcrTimNum DisplayString,
               setLcrTimFal INTEGER
              }

setLcrTimInd OBJECT-TYPE
             SYNTAX INTEGER (0..65535)
             MAX-ACCESS read-write
             STATUS current
             DESCRIPTION "Index"
             ::= {  setLcrTimEntry 1 }

setLcrTimPre OBJECT-TYPE
             SYNTAX DisplayString (SIZE(0..10))
             MAX-ACCESS read-write
             STATUS current
             DESCRIPTION "Prefix"
             ::= {  setLcrTimEntry 2 }

setLcrTimDay OBJECT-TYPE
             SYNTAX BITS
             {
               monday(7),
               tuesday(6),
               wednesday(5),
               thursday(4),
               friday(3),
               saturday(2),
               sunday(1),
               holiday(0)
             }
             MAX-ACCESS read-write
             STATUS current
             DESCRIPTION "Days"
             ::= {  setLcrTimEntry 3 }

setLcrTimSta OBJECT-TYPE
             SYNTAX DisplayString (SIZE(0..5))
             MAX-ACCESS read-write
             STATUS current
             DESCRIPTION "Start"
             ::= {  setLcrTimEntry 4 }

setLcrTimSto OBJECT-TYPE
             SYNTAX DisplayString (SIZE(0..5))
             MAX-ACCESS read-write
             STATUS current
             DESCRIPTION "Stop"
             ::= {  setLcrTimEntry 5 }

setLcrTimNum OBJECT-TYPE
             SYNTAX DisplayString (SIZE(0..29))
             MAX-ACCESS read-write
             STATUS current
             DESCRIPTION "Number-List"
             ::= {  setLcrTimEntry 6 }

setLcrTimFal OBJECT-TYPE
             SYNTAX INTEGER
             {
               no(0),
               yes(1)
             }
             MAX-ACCESS read-write
             STATUS current
             DESCRIPTION "Fallback"
             ::= {  setLcrTimEntry 7 }

setLcrHolTable OBJECT-TYPE
               SYNTAX SEQUENCE OF SetLcrHolEntry
               MAX-ACCESS not-accessible
               STATUS current
               DESCRIPTION "Holidays"
               ::= {  setLcr 5 }

setLcrHolEntry OBJECT-TYPE
               SYNTAX SetLcrHolEntry
               MAX-ACCESS not-accessible
               STATUS current
               DESCRIPTION "entry in table"
               INDEX { setLcrHolInd }
               ::= {  setLcrHolTable 1 }

SetLcrHolEntry ::= SEQUENCE {
               setLcrHolInd INTEGER,
               setLcrHolDat DisplayString
              }

setLcrHolInd OBJECT-TYPE
             SYNTAX INTEGER (0..65535)
             MAX-ACCESS read-write
             STATUS current
             DESCRIPTION "Index"
             ::= {  setLcrHolEntry 1 }

setLcrHolDat OBJECT-TYPE
             SYNTAX DisplayString (SIZE(0..13))
             MAX-ACCESS read-write
             STATUS current
             DESCRIPTION "Date"
             ::= {  setLcrHolEntry 2 }

setTime OBJECT IDENTIFIER ::= { set 14}
setTimeFetch OBJECT-TYPE
             SYNTAX INTEGER
             {
               none(0),
               isdn(1),
               ntp(2)
             }
             MAX-ACCESS read-write
             STATUS current
             DESCRIPTION "Fetch-Method"
             ::= {  setTime 1 }

setTimeCurre OBJECT-TYPE
             SYNTAX DisplayString
             MAX-ACCESS read-only
             STATUS current
             DESCRIPTION "Current-Time"
             ::= {  setTime 2 }

setTimeTimec OBJECT-TYPE
             SYNTAX DisplayString (SIZE(0..39))
             MAX-ACCESS read-write
             STATUS current
             DESCRIPTION "Time-Call-Number"
             ::= {  setTime 3 }

setTimeCalla OBJECT-TYPE
             SYNTAX INTEGER
             MAX-ACCESS read-write
             STATUS current
             DESCRIPTION "Call-Attempts"
             ::= {  setTime 5 }

setTimeUtcin OBJECT-TYPE
             SYNTAX Counter32
             MAX-ACCESS read-only
             STATUS current
             DESCRIPTION "UTC-in-Seconds"
             ::= {  setTime 7 }

setTimeTimez OBJECT-TYPE
             SYNTAX INTEGER
             {
               e0(0),
               plus-1(1),
               plus-2(2),
               plus-3(3),
               plus-4(4),
               plus-5(5),
               plus-6(6),
               plus-7(7),
               plus-8(8),
               plus-9(9),
               plus-10(10),
               plus-11(11),
               plus-12(12),
               plus-13(13),
               plus-14(14),
               minus-1(255),
               minus-2(254),
               minus-3(253),
               minus-4(252),
               minus-5(251),
               minus-6(250),
               minus-7(249),
               minus-8(248),
               minus-9(247),
               minus-10(246),
               minus-11(245),
               minus-12(244)
             }
             MAX-ACCESS read-write
             STATUS current
             DESCRIPTION "Timezone"
             ::= {  setTime 10 }

setTimeDayli OBJECT-TYPE
             SYNTAX INTEGER
             {
               no(0),
               yes(1),
               europe-eu(2),
               russia(3),
               usa(4),
               user-defined(255)
             }
             MAX-ACCESS read-write
             STATUS current
             DESCRIPTION "Daylight-saving-time"
             ::= {  setTime 11 }

setTimeDstclTable OBJECT-TYPE
                  SYNTAX SEQUENCE OF SetTimeDstclEntry
                  MAX-ACCESS not-accessible
                  STATUS current
                  DESCRIPTION "DST-clock-changes"
                  ::= {  setTime 12 }

setTimeDstclEntry OBJECT-TYPE
                  SYNTAX SetTimeDstclEntry
                  MAX-ACCESS not-accessible
                  STATUS current
                  DESCRIPTION "entry in table"
                  INDEX { setTimeDstclEve }
                  ::= {  setTimeDstclTable 1 }

SetTimeDstclEntry ::= SEQUENCE {
                  setTimeDstclEve INTEGER,
                  setTimeDstclInd INTEGER,
                  setTimeDstclDay INTEGER,
                  setTimeDstclMon INTEGER,
                  setTimeDstclHou INTEGER,
                  setTimeDstclMin INTEGER,
                  setTimeDstclTim INTEGER
                 }

setTimeDstclEve OBJECT-TYPE
                SYNTAX INTEGER
                {
                  start(1),
                  end(2)
                }
                MAX-ACCESS read-only
                STATUS current
                DESCRIPTION "Event"
                ::= {  setTimeDstclEntry 1 }

setTimeDstclInd OBJECT-TYPE
                SYNTAX INTEGER
                {
                  e4-last(252),
                  e3-last(253),
                  e2-last(254),
                  last(255),
                  first(1),
                  second(2),
                  third(3),
                  fourth(4)
                }
                MAX-ACCESS read-write
                STATUS current
                DESCRIPTION "Index"
                ::= {  setTimeDstclEntry 2 }

setTimeDstclDay OBJECT-TYPE
                SYNTAX INTEGER
                {
                  monday(1),
                  tuesday(2),
                  wednesday(3),
                  thursday(4),
                  friday(5),
                  saturday(6),
                  sunday(0)
                }
                MAX-ACCESS read-write
                STATUS current
                DESCRIPTION "Day"
                ::= {  setTimeDstclEntry 3 }

setTimeDstclMon OBJECT-TYPE
                SYNTAX INTEGER
                {
                  january(1),
                  february(2),
                  march(3),
                  april(4),
                  may(5),
                  june(6),
                  july(7),
                  august(8),
                  september(9),
                  october(10),
                  november(11),
                  december(12)
                }
                MAX-ACCESS read-write
                STATUS current
                DESCRIPTION "Month"
                ::= {  setTimeDstclEntry 4 }

setTimeDstclHou OBJECT-TYPE
                SYNTAX INTEGER (0..255)
                MAX-ACCESS read-write
                STATUS current
                DESCRIPTION "Hour"
                ::= {  setTimeDstclEntry 5 }

setTimeDstclMin OBJECT-TYPE
                SYNTAX INTEGER (0..255)
                MAX-ACCESS read-write
                STATUS current
                DESCRIPTION "Minute"
                ::= {  setTimeDstclEntry 6 }

setTimeDstclTim OBJECT-TYPE
                SYNTAX INTEGER
                {
                  utc(1),
                  lst(0)
                }
                MAX-ACCESS read-write
                STATUS current
                DESCRIPTION "Time-type"
                ::= {  setTimeDstclEntry 7 }

setTimeGetti OBJECT-TYPE
             SYNTAX DisplayString
             MAX-ACCESS read-write
             STATUS current
             DESCRIPTION "Get-Time"
             ::= {  setTime 13 }

setVpn OBJECT IDENTIFIER ::= { set 19}
setVpnOperating OBJECT-TYPE
                  SYNTAX INTEGER
                  {
                    no(0),
                    yes(1),
                    exclusive(3)
                  }
                  MAX-ACCESS read-write
                  STATUS current
                  DESCRIPTION "Operating"
                  ::= {  setVpn 8 }

setVpnNattoperati OBJECT-TYPE
                  SYNTAX INTEGER
                  {
                    no(0),
                    yes(1)
                  }
                  MAX-ACCESS read-write
                  STATUS current
                  DESCRIPTION "NAT-T-Operating"
                  ::= {  setVpn 16 }

setVpnSimplecertr OBJECT-TYPE
                  SYNTAX INTEGER
                  {
                    no(0),
                    yes(1)
                  }
                  MAX-ACCESS read-write
                  STATUS current
                  DESCRIPTION "Simple-Cert-RAS-Operating"
                  ::= {  setVpn 17 }

setVpnAllowremote OBJECT-TYPE
                  SYNTAX INTEGER
                  {
                    no(0),
                    yes(1)
                  }
                  MAX-ACCESS read-write
                  STATUS current
                  DESCRIPTION "Allow-Remote-Network-Selection"
                  ::= {  setVpn 22 }

setVpnEstablishsa OBJECT-TYPE
                  SYNTAX INTEGER
                  {
                    no(0),
                    yes(1),
                    only-with-keepalive(2)
                  }
                  MAX-ACCESS read-write
                  STATUS current
                  DESCRIPTION "Establish-SAs-Collectively"
                  ::= {  setVpn 23 }

setVpnVpnpeersTable OBJECT-TYPE
                       SYNTAX SEQUENCE OF SetVpnVpnpeersEntry
                       MAX-ACCESS not-accessible
                       STATUS current
                       DESCRIPTION "VPN-Peers"
                       ::= {  setVpn 9 }

setVpnVpnpeersEntry OBJECT-TYPE
                       SYNTAX SetVpnVpnpeersEntry
                       MAX-ACCESS not-accessible
                       STATUS current
                       DESCRIPTION "entry in table"
                       INDEX { setVpnVpnpeersPeer }
                       ::= {  setVpnVpnpeersTable 1 }

SetVpnVpnpeersEntry ::= SEQUENCE {
                       setVpnVpnpeersPeer DisplayString,
                       setVpnVpnpeersShti INTEGER,
                       setVpnVpnpeersExtr IpAddress,
                       setVpnVpnpeersRemo DisplayString,
                       setVpnVpnpeersRtgt INTEGER,
                       setVpnVpnpeersLaye DisplayString,
                       setVpnVpnpeersDyna INTEGER,
                       setVpnVpnpeersIkee INTEGER,
                       setVpnVpnpeersRule INTEGER,
                       setVpnVpnpeersDpdi INTEGER,
                       setVpnVpnpeersIkec INTEGER,
                       setVpnVpnpeersXaut INTEGER
                      }

setVpnVpnpeersPeer OBJECT-TYPE
                   SYNTAX DisplayString (SIZE(0..16))
                   MAX-ACCESS read-write
                   STATUS current
                   DESCRIPTION "Peer"
                   ::= {  setVpnVpnpeersEntry 1 }

setVpnVpnpeersShti OBJECT-TYPE
                   SYNTAX INTEGER (0..65535)
                   MAX-ACCESS read-write
                   STATUS current
                   DESCRIPTION "SH-Time"
                   ::= {  setVpnVpnpeersEntry 6 }

setVpnVpnpeersExtr OBJECT-TYPE
                   SYNTAX IpAddress
                   MAX-ACCESS read-write
                   STATUS current
                   DESCRIPTION "Extranet-Address"
                   ::= {  setVpnVpnpeersEntry 2 }

setVpnVpnpeersRemo OBJECT-TYPE
                   SYNTAX DisplayString (SIZE(0..63))
                   MAX-ACCESS read-write
                   STATUS current
                   DESCRIPTION "Remote-Gw"
                   ::= {  setVpnVpnpeersEntry 8 }

setVpnVpnpeersRtgt OBJECT-TYPE
                   SYNTAX INTEGER (0..65535)
                   MAX-ACCESS read-write
                   STATUS current
                   DESCRIPTION "Rtg-tag"
                   ::= {  setVpnVpnpeersEntry 15 }

setVpnVpnpeersLaye OBJECT-TYPE
                   SYNTAX DisplayString (SIZE(0..16))
                   MAX-ACCESS read-write
                   STATUS current
                   DESCRIPTION "Layer"
                   ::= {  setVpnVpnpeersEntry 4 }

setVpnVpnpeersDyna OBJECT-TYPE
                   SYNTAX INTEGER
                   {
                     no(0),
                     icmp(4),
                     udp(8),
                     b-channel(1),
                     d-channel(2)
                   }
                   MAX-ACCESS read-write
                   STATUS current
                   DESCRIPTION "dynamic"
                   ::= {  setVpnVpnpeersEntry 5 }

setVpnVpnpeersIkee OBJECT-TYPE
                   SYNTAX INTEGER
                   {
                     main-mode(0),
                     aggressive-mode(1)
                   }
                   MAX-ACCESS read-write
                   STATUS current
                   DESCRIPTION "IKE-Exchange"
                   ::= {  setVpnVpnpeersEntry 7 }

setVpnVpnpeersRule OBJECT-TYPE
                   SYNTAX INTEGER
                   {
                     auto(0),
                     manually(1),
                     off(2)
                   }
                   MAX-ACCESS read-write
                   STATUS current
                   DESCRIPTION "Rule-creation"
                   ::= {  setVpnVpnpeersEntry 9 }

setVpnVpnpeersDpdi OBJECT-TYPE
                   SYNTAX INTEGER (0..2147483647)
                   MAX-ACCESS read-write
                   STATUS current
                   DESCRIPTION "DPD-Inact-Timeout"
                   ::= {  setVpnVpnpeersEntry 10 }

setVpnVpnpeersIkec OBJECT-TYPE
                   SYNTAX INTEGER
                   {
                     off(0),
                     client(1),
                     server(2)
                   }
                   MAX-ACCESS read-write
                   STATUS current
                   DESCRIPTION "IKE-CFG"
                   ::= {  setVpnVpnpeersEntry 11 }

setVpnVpnpeersXaut OBJECT-TYPE
                   SYNTAX INTEGER
                   {
                     off(0),
                     client(1),
                     server(2)
                   }
                   MAX-ACCESS read-write
                   STATUS current
                   DESCRIPTION "XAUTH"
                   ::= {  setVpnVpnpeersEntry 12 }

setVpnAdditionalgTable OBJECT-TYPE
                       SYNTAX SEQUENCE OF SetVpnAdditionalgEntry
                       MAX-ACCESS not-accessible
                       STATUS current
                       DESCRIPTION "Additional-Gateways"
                       ::= {  setVpn 12 }

setVpnAdditionalgEntry OBJECT-TYPE
                       SYNTAX SetVpnAdditionalgEntry
                       MAX-ACCESS not-accessible
                       STATUS current
                       DESCRIPTION "entry in table"
                       INDEX { setVpnAdditionalgPeer }
                       ::= {  setVpnAdditionalgTable 1 }

SetVpnAdditionalgEntry ::= SEQUENCE {
                       setVpnAdditionalgPeer DisplayString,
                       setVpnAdditionalgRemotegateway1 DisplayString,
                       setVpnAdditionalgRtgtag1 INTEGER,
                       setVpnAdditionalgRemotegateway2 DisplayString,
                       setVpnAdditionalgRtgtag2 INTEGER,
                       setVpnAdditionalgRemotegateway3 DisplayString,
                       setVpnAdditionalgRtgtag3 INTEGER,
                       setVpnAdditionalgRemotegateway4 DisplayString,
                       setVpnAdditionalgRtgtag4 INTEGER,
                       setVpnAdditionalgRemotegateway5 DisplayString,
                       setVpnAdditionalgRtgtag5 INTEGER,
                       setVpnAdditionalgRemotegateway6 DisplayString,
                       setVpnAdditionalgRtgtag6 INTEGER,
                       setVpnAdditionalgRemotegateway7 DisplayString,
                       setVpnAdditionalgRtgtag7 INTEGER,
                       setVpnAdditionalgRemotegateway8 DisplayString,
                       setVpnAdditionalgRtgtag8 INTEGER,
                       setVpnAdditionalgRemotegateway9 DisplayString,
                       setVpnAdditionalgRtgtag9 INTEGER,
                       setVpnAdditionalgRemotegateway10 DisplayString,
                       setVpnAdditionalgRtgtag10 INTEGER,
                       setVpnAdditionalgRemotegateway11 DisplayString,
                       setVpnAdditionalgRtgtag11 INTEGER,
                       setVpnAdditionalgRemotegateway12 DisplayString,
                       setVpnAdditionalgRtgtag12 INTEGER,
                       setVpnAdditionalgRemotegateway13 DisplayString,
                       setVpnAdditionalgRtgtag13 INTEGER,
                       setVpnAdditionalgRemotegateway14 DisplayString,
                       setVpnAdditionalgRtgtag14 INTEGER,
                       setVpnAdditionalgRemotegateway15 DisplayString,
                       setVpnAdditionalgRtgtag15 INTEGER,
                       setVpnAdditionalgRemotegateway16 DisplayString,
                       setVpnAdditionalgRtgtag16 INTEGER,
                       setVpnAdditionalgBeginwith INTEGER
                      }

setVpnAdditionalgPeer OBJECT-TYPE
                                 SYNTAX DisplayString (SIZE(0..16))
                                 MAX-ACCESS read-write
                                 STATUS current
                                 DESCRIPTION "Peer"
                                 ::= {  setVpnAdditionalgEntry 1 }

setVpnAdditionalgRemotegateway1 OBJECT-TYPE
                                 SYNTAX DisplayString (SIZE(0..63))
                                 MAX-ACCESS read-write
                                 STATUS current
                                 DESCRIPTION "Remote-Gateway-1"
                                 ::= {  setVpnAdditionalgEntry 2 }

setVpnAdditionalgRtgtag1 OBJECT-TYPE
                                 SYNTAX INTEGER (0..65535)
                                 MAX-ACCESS read-write
                                 STATUS current
                                 DESCRIPTION "Rtg-Tag-1"
                                 ::= {  setVpnAdditionalgEntry 11 }

setVpnAdditionalgRemotegateway2 OBJECT-TYPE
                                 SYNTAX DisplayString (SIZE(0..63))
                                 MAX-ACCESS read-write
                                 STATUS current
                                 DESCRIPTION "Remote-Gateway-2"
                                 ::= {  setVpnAdditionalgEntry 3 }

setVpnAdditionalgRtgtag2 OBJECT-TYPE
                                 SYNTAX INTEGER (0..65535)
                                 MAX-ACCESS read-write
                                 STATUS current
                                 DESCRIPTION "Rtg-Tag-2"
                                 ::= {  setVpnAdditionalgEntry 12 }

setVpnAdditionalgRemotegateway3 OBJECT-TYPE
                                 SYNTAX DisplayString (SIZE(0..63))
                                 MAX-ACCESS read-write
                                 STATUS current
                                 DESCRIPTION "Remote-Gateway-3"
                                 ::= {  setVpnAdditionalgEntry 4 }

setVpnAdditionalgRtgtag3 OBJECT-TYPE
                                 SYNTAX INTEGER (0..65535)
                                 MAX-ACCESS read-write
                                 STATUS current
                                 DESCRIPTION "Rtg-Tag-3"
                                 ::= {  setVpnAdditionalgEntry 13 }

setVpnAdditionalgRemotegateway4 OBJECT-TYPE
                                 SYNTAX DisplayString (SIZE(0..63))
                                 MAX-ACCESS read-write
                                 STATUS current
                                 DESCRIPTION "Remote-Gateway-4"
                                 ::= {  setVpnAdditionalgEntry 5 }

setVpnAdditionalgRtgtag4 OBJECT-TYPE
                                 SYNTAX INTEGER (0..65535)
                                 MAX-ACCESS read-write
                                 STATUS current
                                 DESCRIPTION "Rtg-Tag-4"
                                 ::= {  setVpnAdditionalgEntry 14 }

setVpnAdditionalgRemotegateway5 OBJECT-TYPE
                                 SYNTAX DisplayString (SIZE(0..63))
                                 MAX-ACCESS read-write
                                 STATUS current
                                 DESCRIPTION "Remote-Gateway-5"
                                 ::= {  setVpnAdditionalgEntry 6 }

setVpnAdditionalgRtgtag5 OBJECT-TYPE
                                 SYNTAX INTEGER (0..65535)
                                 MAX-ACCESS read-write
                                 STATUS current
                                 DESCRIPTION "Rtg-Tag-5"
                                 ::= {  setVpnAdditionalgEntry 15 }

setVpnAdditionalgRemotegateway6 OBJECT-TYPE
                                 SYNTAX DisplayString (SIZE(0..63))
                                 MAX-ACCESS read-write
                                 STATUS current
                                 DESCRIPTION "Remote-Gateway-6"
                                 ::= {  setVpnAdditionalgEntry 7 }

setVpnAdditionalgRtgtag6 OBJECT-TYPE
                                 SYNTAX INTEGER (0..65535)
                                 MAX-ACCESS read-write
                                 STATUS current
                                 DESCRIPTION "Rtg-Tag-6"
                                 ::= {  setVpnAdditionalgEntry 16 }

setVpnAdditionalgRemotegateway7 OBJECT-TYPE
                                 SYNTAX DisplayString (SIZE(0..63))
                                 MAX-ACCESS read-write
                                 STATUS current
                                 DESCRIPTION "Remote-Gateway-7"
                                 ::= {  setVpnAdditionalgEntry 8 }

setVpnAdditionalgRtgtag7 OBJECT-TYPE
                                 SYNTAX INTEGER (0..65535)
                                 MAX-ACCESS read-write
                                 STATUS current
                                 DESCRIPTION "Rtg-Tag-7"
                                 ::= {  setVpnAdditionalgEntry 17 }

setVpnAdditionalgRemotegateway8 OBJECT-TYPE
                                 SYNTAX DisplayString (SIZE(0..63))
                                 MAX-ACCESS read-write
                                 STATUS current
                                 DESCRIPTION "Remote-Gateway-8"
                                 ::= {  setVpnAdditionalgEntry 9 }

setVpnAdditionalgRtgtag8 OBJECT-TYPE
                                 SYNTAX INTEGER (0..65535)
                                 MAX-ACCESS read-write
                                 STATUS current
                                 DESCRIPTION "Rtg-Tag-8"
                                 ::= {  setVpnAdditionalgEntry 18 }

setVpnAdditionalgRemotegateway9 OBJECT-TYPE
                                 SYNTAX DisplayString (SIZE(0..63))
                                 MAX-ACCESS read-write
                                 STATUS current
                                 DESCRIPTION "Remote-Gateway-9"
                                 ::= {  setVpnAdditionalgEntry 19 }

setVpnAdditionalgRtgtag9 OBJECT-TYPE
                                 SYNTAX INTEGER (0..65535)
                                 MAX-ACCESS read-write
                                 STATUS current
                                 DESCRIPTION "Rtg-Tag-9"
                                 ::= {  setVpnAdditionalgEntry 27 }

setVpnAdditionalgRemotegateway10 OBJECT-TYPE
                                 SYNTAX DisplayString (SIZE(0..63))
                                 MAX-ACCESS read-write
                                 STATUS current
                                 DESCRIPTION "Remote-Gateway-10"
                                 ::= {  setVpnAdditionalgEntry 20 }

setVpnAdditionalgRtgtag10 OBJECT-TYPE
                                 SYNTAX INTEGER (0..65535)
                                 MAX-ACCESS read-write
                                 STATUS current
                                 DESCRIPTION "Rtg-Tag-10"
                                 ::= {  setVpnAdditionalgEntry 28 }

setVpnAdditionalgRemotegateway11 OBJECT-TYPE
                                 SYNTAX DisplayString (SIZE(0..63))
                                 MAX-ACCESS read-write
                                 STATUS current
                                 DESCRIPTION "Remote-Gateway-11"
                                 ::= {  setVpnAdditionalgEntry 21 }

setVpnAdditionalgRtgtag11 OBJECT-TYPE
                                 SYNTAX INTEGER (0..65535)
                                 MAX-ACCESS read-write
                                 STATUS current
                                 DESCRIPTION "Rtg-Tag-11"
                                 ::= {  setVpnAdditionalgEntry 29 }

setVpnAdditionalgRemotegateway12 OBJECT-TYPE
                                 SYNTAX DisplayString (SIZE(0..63))
                                 MAX-ACCESS read-write
                                 STATUS current
                                 DESCRIPTION "Remote-Gateway-12"
                                 ::= {  setVpnAdditionalgEntry 22 }

setVpnAdditionalgRtgtag12 OBJECT-TYPE
                                 SYNTAX INTEGER (0..65535)
                                 MAX-ACCESS read-write
                                 STATUS current
                                 DESCRIPTION "Rtg-Tag-12"
                                 ::= {  setVpnAdditionalgEntry 30 }

setVpnAdditionalgRemotegateway13 OBJECT-TYPE
                                 SYNTAX DisplayString (SIZE(0..63))
                                 MAX-ACCESS read-write
                                 STATUS current
                                 DESCRIPTION "Remote-Gateway-13"
                                 ::= {  setVpnAdditionalgEntry 23 }

setVpnAdditionalgRtgtag13 OBJECT-TYPE
                                 SYNTAX INTEGER (0..65535)
                                 MAX-ACCESS read-write
                                 STATUS current
                                 DESCRIPTION "Rtg-Tag-13"
                                 ::= {  setVpnAdditionalgEntry 31 }

setVpnAdditionalgRemotegateway14 OBJECT-TYPE
                                 SYNTAX DisplayString (SIZE(0..63))
                                 MAX-ACCESS read-write
                                 STATUS current
                                 DESCRIPTION "Remote-Gateway-14"
                                 ::= {  setVpnAdditionalgEntry 24 }

setVpnAdditionalgRtgtag14 OBJECT-TYPE
                                 SYNTAX INTEGER (0..65535)
                                 MAX-ACCESS read-write
                                 STATUS current
                                 DESCRIPTION "Rtg-Tag-14"
                                 ::= {  setVpnAdditionalgEntry 32 }

setVpnAdditionalgRemotegateway15 OBJECT-TYPE
                                 SYNTAX DisplayString (SIZE(0..63))
                                 MAX-ACCESS read-write
                                 STATUS current
                                 DESCRIPTION "Remote-Gateway-15"
                                 ::= {  setVpnAdditionalgEntry 25 }

setVpnAdditionalgRtgtag15 OBJECT-TYPE
                                 SYNTAX INTEGER (0..65535)
                                 MAX-ACCESS read-write
                                 STATUS current
                                 DESCRIPTION "Rtg-Tag-15"
                                 ::= {  setVpnAdditionalgEntry 33 }

setVpnAdditionalgRemotegateway16 OBJECT-TYPE
                                 SYNTAX DisplayString (SIZE(0..63))
                                 MAX-ACCESS read-write
                                 STATUS current
                                 DESCRIPTION "Remote-Gateway-16"
                                 ::= {  setVpnAdditionalgEntry 26 }

setVpnAdditionalgRtgtag16 OBJECT-TYPE
                                 SYNTAX INTEGER (0..65535)
                                 MAX-ACCESS read-write
                                 STATUS current
                                 DESCRIPTION "Rtg-Tag-16"
                                 ::= {  setVpnAdditionalgEntry 34 }

setVpnAdditionalgBeginwith OBJECT-TYPE
                                 SYNTAX INTEGER
                                 {
                                   last-used(0),
                                   first(1),
                                   random(2)
                                 }
                                 MAX-ACCESS read-write
                                 STATUS current
                                 DESCRIPTION "Begin-With"
                                 ::= {  setVpnAdditionalgEntry 10 }

setVpnLayerTable OBJECT-TYPE
                       SYNTAX SEQUENCE OF SetVpnLayerEntry
                       MAX-ACCESS not-accessible
                       STATUS current
                       DESCRIPTION "Layer"
                       ::= {  setVpn 7 }

setVpnLayerEntry OBJECT-TYPE
                       SYNTAX SetVpnLayerEntry
                       MAX-ACCESS not-accessible
                       STATUS current
                       DESCRIPTION "entry in table"
                       INDEX { setVpnLayerName }
                       ::= {  setVpnLayerTable 1 }

SetVpnLayerEntry ::= SEQUENCE {
                       setVpnLayerName DisplayString,
                       setVpnLayerPfsg INTEGER,
                       setVpnLayerIkeg INTEGER,
                       setVpnLayerIkep DisplayString,
                       setVpnLayerIpse DisplayString,
                       setVpnLayerIkek DisplayString
                      }

setVpnLayerName OBJECT-TYPE
                SYNTAX DisplayString (SIZE(0..16))
                MAX-ACCESS read-write
                STATUS current
                DESCRIPTION "Name"
                ::= {  setVpnLayerEntry 1 }

setVpnLayerPfsg OBJECT-TYPE
                SYNTAX INTEGER (0..2147483647)
                MAX-ACCESS read-write
                STATUS current
                DESCRIPTION "PFS-Grp"
                ::= {  setVpnLayerEntry 3 }

setVpnLayerIkeg OBJECT-TYPE
                SYNTAX INTEGER (0..2147483647)
                MAX-ACCESS read-write
                STATUS current
                DESCRIPTION "IKE-Grp"
                ::= {  setVpnLayerEntry 4 }

setVpnLayerIkep OBJECT-TYPE
                SYNTAX DisplayString (SIZE(0..17))
                MAX-ACCESS read-write
                STATUS current
                DESCRIPTION "IKE-Prop-List"
                ::= {  setVpnLayerEntry 5 }

setVpnLayerIpse OBJECT-TYPE
                SYNTAX DisplayString (SIZE(0..17))
                MAX-ACCESS read-write
                STATUS current
                DESCRIPTION "IPSEC-Prop-List"
                ::= {  setVpnLayerEntry 6 }

setVpnLayerIkek OBJECT-TYPE
                SYNTAX DisplayString (SIZE(0..16))
                MAX-ACCESS read-write
                STATUS current
                DESCRIPTION "IKE-Key"
                ::= {  setVpnLayerEntry 7 }

setVpnProposals OBJECT IDENTIFIER ::= { setVpn 4}
setVpnProposalsIkeTable OBJECT-TYPE
                           SYNTAX SEQUENCE OF SetVpnProposalsIkeEntry
                           MAX-ACCESS not-accessible
                           STATUS current
                           DESCRIPTION "IKE"
                           ::= {  setVpnProposals 11 }

setVpnProposalsIkeEntry OBJECT-TYPE
                           SYNTAX SetVpnProposalsIkeEntry
                           MAX-ACCESS not-accessible
                           STATUS current
                           DESCRIPTION "entry in table"
                           INDEX { setVpnProposalsIkeName }
                           ::= {  setVpnProposalsIkeTable 1 }

SetVpnProposalsIkeEntry ::= SEQUENCE {
                           setVpnProposalsIkeName DisplayString,
                           setVpnProposalsIkeIkecrypta INTEGER,
                           setVpnProposalsIkeIkecryptk INTEGER,
                           setVpnProposalsIkeIkeauthal INTEGER,
                           setVpnProposalsIkeIkeauthmo INTEGER,
                           setVpnProposalsIkeLifetimes INTEGER,
                           setVpnProposalsIkeLifetimek INTEGER
                          }

setVpnProposalsIkeName OBJECT-TYPE
                            SYNTAX DisplayString (SIZE(0..17))
                            MAX-ACCESS read-write
                            STATUS current
                            DESCRIPTION "Name"
                            ::= {  setVpnProposalsIkeEntry 1 }

setVpnProposalsIkeIkecrypta OBJECT-TYPE
                            SYNTAX INTEGER
                            {
                              aes-cbc(7),
                              blowfish-cbc(3),
                              cast128-cbc(6),
                              e3des-cbc(5),
                              des-cbc(1),
                              null(42)
                            }
                            MAX-ACCESS read-write
                            STATUS current
                            DESCRIPTION "IKE-Crypt-Alg"
                            ::= {  setVpnProposalsIkeEntry 2 }

setVpnProposalsIkeIkecryptk OBJECT-TYPE
                            SYNTAX INTEGER (0..65535)
                            MAX-ACCESS read-write
                            STATUS current
                            DESCRIPTION "IKE-Crypt-Keylen"
                            ::= {  setVpnProposalsIkeEntry 3 }

setVpnProposalsIkeIkeauthal OBJECT-TYPE
                            SYNTAX INTEGER
                            {
                              md5(1),
                              sha1(2)
                            }
                            MAX-ACCESS read-write
                            STATUS current
                            DESCRIPTION "IKE-Auth-Alg"
                            ::= {  setVpnProposalsIkeEntry 4 }

setVpnProposalsIkeIkeauthmo OBJECT-TYPE
                            SYNTAX INTEGER
                            {
                              preshared-key(1),
                              rsa-signature(3)
                            }
                            MAX-ACCESS read-write
                            STATUS current
                            DESCRIPTION "IKE-Auth-Mode"
                            ::= {  setVpnProposalsIkeEntry 5 }

setVpnProposalsIkeLifetimes OBJECT-TYPE
                            SYNTAX INTEGER (0..2147483647)
                            MAX-ACCESS read-write
                            STATUS current
                            DESCRIPTION "Lifetime-Sec"
                            ::= {  setVpnProposalsIkeEntry 6 }

setVpnProposalsIkeLifetimek OBJECT-TYPE
                            SYNTAX INTEGER (0..2147483647)
                            MAX-ACCESS read-write
                            STATUS current
                            DESCRIPTION "Lifetime-KB"
                            ::= {  setVpnProposalsIkeEntry 7 }

setVpnProposalsIpsecTable OBJECT-TYPE
                           SYNTAX SEQUENCE OF SetVpnProposalsIpsecEntry
                           MAX-ACCESS not-accessible
                           STATUS current
                           DESCRIPTION "IPSEC"
                           ::= {  setVpnProposals 12 }

setVpnProposalsIpsecEntry OBJECT-TYPE
                           SYNTAX SetVpnProposalsIpsecEntry
                           MAX-ACCESS not-accessible
                           STATUS current
                           DESCRIPTION "entry in table"
                           INDEX { setVpnProposalsIpsecName }
                           ::= {  setVpnProposalsIpsecTable 1 }

SetVpnProposalsIpsecEntry ::= SEQUENCE {
                           setVpnProposalsIpsecName DisplayString,
                           setVpnProposalsIpsecEncapsmod INTEGER,
                           setVpnProposalsIpsecEspcrypta INTEGER,
                           setVpnProposalsIpsecEspcryptk INTEGER,
                           setVpnProposalsIpsecEspauthal INTEGER,
                           setVpnProposalsIpsecAhauthalg INTEGER,
                           setVpnProposalsIpsecIpcompalg INTEGER,
                           setVpnProposalsIpsecLifetimes INTEGER,
                           setVpnProposalsIpsecLifetimek INTEGER
                          }

setVpnProposalsIpsecName OBJECT-TYPE
                              SYNTAX DisplayString (SIZE(0..17))
                              MAX-ACCESS read-write
                              STATUS current
                              DESCRIPTION "Name"
                              ::= {  setVpnProposalsIpsecEntry 1 }

setVpnProposalsIpsecEncapsmod OBJECT-TYPE
                              SYNTAX INTEGER
                              {
                                tunnel(1),
                                transport(2),
                                mixed-lcos4(65001)
                              }
                              MAX-ACCESS read-write
                              STATUS current
                              DESCRIPTION "Encaps-Mode"
                              ::= {  setVpnProposalsIpsecEntry 2 }

setVpnProposalsIpsecEspcrypta OBJECT-TYPE
                              SYNTAX INTEGER
                              {
                                none(0),
                                aes-cbc(12),
                                blowfish-cbc(7),
                                cast128-cbc(6),
                                e3des-cbc(3),
                                des-cbc(2),
                                null(11)
                              }
                              MAX-ACCESS read-write
                              STATUS current
                              DESCRIPTION "ESP-Crypt-Alg"
                              ::= {  setVpnProposalsIpsecEntry 3 }

setVpnProposalsIpsecEspcryptk OBJECT-TYPE
                              SYNTAX INTEGER (0..65535)
                              MAX-ACCESS read-write
                              STATUS current
                              DESCRIPTION "ESP-Crypt-Keylen"
                              ::= {  setVpnProposalsIpsecEntry 4 }

setVpnProposalsIpsecEspauthal OBJECT-TYPE
                              SYNTAX INTEGER
                              {
                                none(0),
                                hmac-md5(1),
                                hmac-sha1(2)
                              }
                              MAX-ACCESS read-write
                              STATUS current
                              DESCRIPTION "ESP-Auth-Alg"
                              ::= {  setVpnProposalsIpsecEntry 5 }

setVpnProposalsIpsecAhauthalg OBJECT-TYPE
                              SYNTAX INTEGER
                              {
                                none(0),
                                hmac-md5(1),
                                hmac-sha1(2)
                              }
                              MAX-ACCESS read-write
                              STATUS current
                              DESCRIPTION "AH-Auth-Alg"
                              ::= {  setVpnProposalsIpsecEntry 6 }

setVpnProposalsIpsecIpcompalg OBJECT-TYPE
                              SYNTAX INTEGER
                              {
                                none(0),
                                deflate(2),
                                lzs(3)
                              }
                              MAX-ACCESS read-write
                              STATUS current
                              DESCRIPTION "IPCOMP-Alg"
                              ::= {  setVpnProposalsIpsecEntry 7 }

setVpnProposalsIpsecLifetimes OBJECT-TYPE
                              SYNTAX INTEGER (0..2147483647)
                              MAX-ACCESS read-write
                              STATUS current
                              DESCRIPTION "Lifetime-Sec"
                              ::= {  setVpnProposalsIpsecEntry 8 }

setVpnProposalsIpsecLifetimek OBJECT-TYPE
                              SYNTAX INTEGER (0..2147483647)
                              MAX-ACCESS read-write
                              STATUS current
                              DESCRIPTION "Lifetime-KB"
                              ::= {  setVpnProposalsIpsecEntry 9 }

setVpnProposalsIkeproTable OBJECT-TYPE
                           SYNTAX SEQUENCE OF SetVpnProposalsIkeproEntry
                           MAX-ACCESS not-accessible
                           STATUS current
                           DESCRIPTION "IKE-Proposal-Lists"
                           ::= {  setVpnProposals 9 }

setVpnProposalsIkeproEntry OBJECT-TYPE
                           SYNTAX SetVpnProposalsIkeproEntry
                           MAX-ACCESS not-accessible
                           STATUS current
                           DESCRIPTION "entry in table"
                           INDEX { setVpnProposalsIkeproIkeproposall }
                           ::= {  setVpnProposalsIkeproTable 1 }

SetVpnProposalsIkeproEntry ::= SEQUENCE {
                           setVpnProposalsIkeproIkeproposall DisplayString,
                           setVpnProposalsIkeproIkeproposal1 DisplayString,
                           setVpnProposalsIkeproIkeproposal2 DisplayString,
                           setVpnProposalsIkeproIkeproposal3 DisplayString,
                           setVpnProposalsIkeproIkeproposal4 DisplayString,
                           setVpnProposalsIkeproIkeproposal5 DisplayString,
                           setVpnProposalsIkeproIkeproposal6 DisplayString,
                           setVpnProposalsIkeproIkeproposal7 DisplayString,
                           setVpnProposalsIkeproIkeproposal8 DisplayString
                          }

setVpnProposalsIkeproIkeproposall OBJECT-TYPE
                                  SYNTAX DisplayString (SIZE(0..17))
                                  MAX-ACCESS read-write
                                  STATUS current
                                  DESCRIPTION "IKE-Proposal-Lists"
                                  ::= {  setVpnProposalsIkeproEntry 1 }

setVpnProposalsIkeproIkeproposal1 OBJECT-TYPE
                                  SYNTAX DisplayString (SIZE(0..17))
                                  MAX-ACCESS read-write
                                  STATUS current
                                  DESCRIPTION "IKE-Proposal-1"
                                  ::= {  setVpnProposalsIkeproEntry 2 }

setVpnProposalsIkeproIkeproposal2 OBJECT-TYPE
                                  SYNTAX DisplayString (SIZE(0..17))
                                  MAX-ACCESS read-write
                                  STATUS current
                                  DESCRIPTION "IKE-Proposal-2"
                                  ::= {  setVpnProposalsIkeproEntry 3 }

setVpnProposalsIkeproIkeproposal3 OBJECT-TYPE
                                  SYNTAX DisplayString (SIZE(0..17))
                                  MAX-ACCESS read-write
                                  STATUS current
                                  DESCRIPTION "IKE-Proposal-3"
                                  ::= {  setVpnProposalsIkeproEntry 4 }

setVpnProposalsIkeproIkeproposal4 OBJECT-TYPE
                                  SYNTAX DisplayString (SIZE(0..17))
                                  MAX-ACCESS read-write
                                  STATUS current
                                  DESCRIPTION "IKE-Proposal-4"
                                  ::= {  setVpnProposalsIkeproEntry 5 }

setVpnProposalsIkeproIkeproposal5 OBJECT-TYPE
                                  SYNTAX DisplayString (SIZE(0..17))
                                  MAX-ACCESS read-write
                                  STATUS current
                                  DESCRIPTION "IKE-Proposal-5"
                                  ::= {  setVpnProposalsIkeproEntry 6 }

setVpnProposalsIkeproIkeproposal6 OBJECT-TYPE
                                  SYNTAX DisplayString (SIZE(0..17))
                                  MAX-ACCESS read-write
                                  STATUS current
                                  DESCRIPTION "IKE-Proposal-6"
                                  ::= {  setVpnProposalsIkeproEntry 7 }

setVpnProposalsIkeproIkeproposal7 OBJECT-TYPE
                                  SYNTAX DisplayString (SIZE(0..17))
                                  MAX-ACCESS read-write
                                  STATUS current
                                  DESCRIPTION "IKE-Proposal-7"
                                  ::= {  setVpnProposalsIkeproEntry 8 }

setVpnProposalsIkeproIkeproposal8 OBJECT-TYPE
                                  SYNTAX DisplayString (SIZE(0..17))
                                  MAX-ACCESS read-write
                                  STATUS current
                                  DESCRIPTION "IKE-Proposal-8"
                                  ::= {  setVpnProposalsIkeproEntry 9 }

setVpnProposalsIpsecpTable OBJECT-TYPE
                           SYNTAX SEQUENCE OF SetVpnProposalsIpsecpEntry
                           MAX-ACCESS not-accessible
                           STATUS current
                           DESCRIPTION "IPSEC-Proposal-Lists"
                           ::= {  setVpnProposals 10 }

setVpnProposalsIpsecpEntry OBJECT-TYPE
                           SYNTAX SetVpnProposalsIpsecpEntry
                           MAX-ACCESS not-accessible
                           STATUS current
                           DESCRIPTION "entry in table"
                           INDEX { setVpnProposalsIpsecpIpsecproposall }
                           ::= {  setVpnProposalsIpsecpTable 1 }

SetVpnProposalsIpsecpEntry ::= SEQUENCE {
                           setVpnProposalsIpsecpIpsecproposall DisplayString,
                           setVpnProposalsIpsecpIpsecproposal1 DisplayString,
                           setVpnProposalsIpsecpIpsecproposal2 DisplayString,
                           setVpnProposalsIpsecpIpsecproposal3 DisplayString,
                           setVpnProposalsIpsecpIpsecproposal4 DisplayString,
                           setVpnProposalsIpsecpIpsecproposal5 DisplayString,
                           setVpnProposalsIpsecpIpsecproposal6 DisplayString,
                           setVpnProposalsIpsecpIpsecproposal7 DisplayString,
                           setVpnProposalsIpsecpIpsecproposal8 DisplayString
                          }

setVpnProposalsIpsecpIpsecproposall OBJECT-TYPE
                                    SYNTAX DisplayString (SIZE(0..17))
                                    MAX-ACCESS read-write
                                    STATUS current
                                    DESCRIPTION "IPSEC-Proposal-Lists"
                                    ::= {  setVpnProposalsIpsecpEntry 1 }

setVpnProposalsIpsecpIpsecproposal1 OBJECT-TYPE
                                    SYNTAX DisplayString (SIZE(0..17))
                                    MAX-ACCESS read-write
                                    STATUS current
                                    DESCRIPTION "IPSEC-Proposal-1"
                                    ::= {  setVpnProposalsIpsecpEntry 2 }

setVpnProposalsIpsecpIpsecproposal2 OBJECT-TYPE
                                    SYNTAX DisplayString (SIZE(0..17))
                                    MAX-ACCESS read-write
                                    STATUS current
                                    DESCRIPTION "IPSEC-Proposal-2"
                                    ::= {  setVpnProposalsIpsecpEntry 3 }

setVpnProposalsIpsecpIpsecproposal3 OBJECT-TYPE
                                    SYNTAX DisplayString (SIZE(0..17))
                                    MAX-ACCESS read-write
                                    STATUS current
                                    DESCRIPTION "IPSEC-Proposal-3"
                                    ::= {  setVpnProposalsIpsecpEntry 4 }

setVpnProposalsIpsecpIpsecproposal4 OBJECT-TYPE
                                    SYNTAX DisplayString (SIZE(0..17))
                                    MAX-ACCESS read-write
                                    STATUS current
                                    DESCRIPTION "IPSEC-Proposal-4"
                                    ::= {  setVpnProposalsIpsecpEntry 5 }

setVpnProposalsIpsecpIpsecproposal5 OBJECT-TYPE
                                    SYNTAX DisplayString (SIZE(0..17))
                                    MAX-ACCESS read-write
                                    STATUS current
                                    DESCRIPTION "IPSEC-Proposal-5"
                                    ::= {  setVpnProposalsIpsecpEntry 6 }

setVpnProposalsIpsecpIpsecproposal6 OBJECT-TYPE
                                    SYNTAX DisplayString (SIZE(0..17))
                                    MAX-ACCESS read-write
                                    STATUS current
                                    DESCRIPTION "IPSEC-Proposal-6"
                                    ::= {  setVpnProposalsIpsecpEntry 7 }

setVpnProposalsIpsecpIpsecproposal7 OBJECT-TYPE
                                    SYNTAX DisplayString (SIZE(0..17))
                                    MAX-ACCESS read-write
                                    STATUS current
                                    DESCRIPTION "IPSEC-Proposal-7"
                                    ::= {  setVpnProposalsIpsecpEntry 8 }

setVpnProposalsIpsecpIpsecproposal8 OBJECT-TYPE
                                    SYNTAX DisplayString (SIZE(0..17))
                                    MAX-ACCESS read-write
                                    STATUS current
                                    DESCRIPTION "IPSEC-Proposal-8"
                                    ::= {  setVpnProposalsIpsecpEntry 9 }

setVpnCertificate OBJECT IDENTIFIER ::= { setVpn 5}
setVpnCertificateIkeTable OBJECT-TYPE
                          SYNTAX SEQUENCE OF SetVpnCertificateIkeEntry
                          MAX-ACCESS not-accessible
                          STATUS current
                          DESCRIPTION "IKE-Keys"
                          ::= {  setVpnCertificate 3 }

setVpnCertificateIkeEntry OBJECT-TYPE
                          SYNTAX SetVpnCertificateIkeEntry
                          MAX-ACCESS not-accessible
                          STATUS current
                          DESCRIPTION "entry in table"
                          INDEX { setVpnCertificateIkeName }
                          ::= {  setVpnCertificateIkeTable 1 }

SetVpnCertificateIkeEntry ::= SEQUENCE {
                          setVpnCertificateIkeName DisplayString,
                          setVpnCertificateIkeLocalidtyp INTEGER,
                          setVpnCertificateIkeLocalident DisplayString,
                          setVpnCertificateIkeRemoteidty INTEGER,
                          setVpnCertificateIkeRemoteiden DisplayString,
                          setVpnCertificateIkeSharedsec DisplayString,
                          setVpnCertificateIkeSharedsecf DisplayString
                         }

setVpnCertificateIkeName OBJECT-TYPE
                               SYNTAX DisplayString (SIZE(0..16))
                               MAX-ACCESS read-write
                               STATUS current
                               DESCRIPTION "Name"
                               ::= {  setVpnCertificateIkeEntry 1 }

setVpnCertificateIkeLocalidtyp OBJECT-TYPE
                               SYNTAX INTEGER
                               {
                                 no-identity(0),
                                 ip-address(1),
                                 domain-name(2),
                                 email-address(3),
                                 distinguished-name(9),
                                 key-id(11)
                               }
                               MAX-ACCESS read-write
                               STATUS current
                               DESCRIPTION "Local-ID-Type"
                               ::= {  setVpnCertificateIkeEntry 6 }

setVpnCertificateIkeLocalident OBJECT-TYPE
                               SYNTAX DisplayString (SIZE(0..254))
                               MAX-ACCESS read-write
                               STATUS current
                               DESCRIPTION "Local-Identity"
                               ::= {  setVpnCertificateIkeEntry 7 }

setVpnCertificateIkeRemoteidty OBJECT-TYPE
                               SYNTAX INTEGER
                               {
                                 no-identity(0),
                                 ip-address(1),
                                 domain-name(2),
                                 email-address(3),
                                 distinguished-name(9),
                                 key-id(11)
                               }
                               MAX-ACCESS read-write
                               STATUS current
                               DESCRIPTION "Remote-ID-Type"
                               ::= {  setVpnCertificateIkeEntry 5 }

setVpnCertificateIkeRemoteiden OBJECT-TYPE
                               SYNTAX DisplayString (SIZE(0..254))
                               MAX-ACCESS read-write
                               STATUS current
                               DESCRIPTION "Remote-Identity"
                               ::= {  setVpnCertificateIkeEntry 2 }

setVpnCertificateIkeSharedsec OBJECT-TYPE
                               SYNTAX DisplayString (SIZE(0..64))
                               MAX-ACCESS read-write
                               STATUS current
                               DESCRIPTION "Shared-Sec"
                               ::= {  setVpnCertificateIkeEntry 3 }

setVpnCertificateIkeSharedsecf OBJECT-TYPE
                               SYNTAX DisplayString (SIZE(0..20))
                               MAX-ACCESS read-write
                               STATUS current
                               DESCRIPTION "Shared-Sec-File"
                               ::= {  setVpnCertificateIkeEntry 4 }

setVpnIsakmp OBJECT IDENTIFIER ::= { setVpn 3}
setVpnIsakmpTimTable OBJECT-TYPE
                     SYNTAX SEQUENCE OF SetVpnIsakmpTimEntry
                     MAX-ACCESS not-accessible
                     STATUS current
                     DESCRIPTION "Timer"
                     ::= {  setVpnIsakmp 4 }

setVpnIsakmpTimEntry OBJECT-TYPE
                     SYNTAX SetVpnIsakmpTimEntry
                     MAX-ACCESS not-accessible
                     STATUS current
                     DESCRIPTION "entry in table"
                     INDEX { setVpnIsakmpTimIdx }
                     ::= {  setVpnIsakmpTimTable 1 }

SetVpnIsakmpTimEntry ::= SEQUENCE {
                     setVpnIsakmpTimIdx INTEGER,
                     setVpnIsakmpTimRetrlim INTEGER,
                     setVpnIsakmpTimRetrtim INTEGER,
                     setVpnIsakmpTimRetrtimu INTEGER,
                     setVpnIsakmpTimRetrtimm INTEGER,
                     setVpnIsakmpTimExptim INTEGER
                    }

setVpnIsakmpTimIdx OBJECT-TYPE
                        SYNTAX INTEGER (0..255)
                        MAX-ACCESS read-only
                        STATUS current
                        DESCRIPTION "Idx."
                        ::= {  setVpnIsakmpTimEntry 6 }

setVpnIsakmpTimRetrlim OBJECT-TYPE
                        SYNTAX INTEGER (0..65535)
                        MAX-ACCESS read-write
                        STATUS current
                        DESCRIPTION "Retr-Lim"
                        ::= {  setVpnIsakmpTimEntry 1 }

setVpnIsakmpTimRetrtim OBJECT-TYPE
                        SYNTAX INTEGER (0..65535)
                        MAX-ACCESS read-write
                        STATUS current
                        DESCRIPTION "Retr-Tim"
                        ::= {  setVpnIsakmpTimEntry 2 }

setVpnIsakmpTimRetrtimu OBJECT-TYPE
                        SYNTAX INTEGER (0..2147483647)
                        MAX-ACCESS read-write
                        STATUS current
                        DESCRIPTION "Retr-Tim-Usec"
                        ::= {  setVpnIsakmpTimEntry 3 }

setVpnIsakmpTimRetrtimm OBJECT-TYPE
                        SYNTAX INTEGER (0..65535)
                        MAX-ACCESS read-write
                        STATUS current
                        DESCRIPTION "Retr-Tim-Max"
                        ::= {  setVpnIsakmpTimEntry 4 }

setVpnIsakmpTimExptim OBJECT-TYPE
                        SYNTAX INTEGER (0..65535)
                        MAX-ACCESS read-write
                        STATUS current
                        DESCRIPTION "Exp-Tim"
                        ::= {  setVpnIsakmpTimEntry 5 }

setVpnMainmodepro OBJECT-TYPE
                  SYNTAX DisplayString (SIZE(0..17))
                  MAX-ACCESS read-write
                  STATUS current
                  DESCRIPTION "MainMode-Proposal-List-Default"
                  ::= {  setVpn 13 }

setVpnMainmodeike OBJECT-TYPE
                  SYNTAX INTEGER
                  MAX-ACCESS read-write
                  STATUS current
                  DESCRIPTION "MainMode-IKE-Group-Default"
                  ::= {  setVpn 14 }

setVpnAggrmodepro OBJECT-TYPE
                  SYNTAX DisplayString (SIZE(0..17))
                  MAX-ACCESS read-write
                  STATUS current
                  DESCRIPTION "AggrMode-Proposal-List-Default"
                  ::= {  setVpn 10 }

setVpnAggrmodeike OBJECT-TYPE
                  SYNTAX INTEGER
                  MAX-ACCESS read-write
                  STATUS current
                  DESCRIPTION "AggrMode-IKE-Group-Default"
                  ::= {  setVpn 11 }

setVpnQuickmodepr OBJECT-TYPE
                  SYNTAX DisplayString (SIZE(0..17))
                  MAX-ACCESS read-write
                  STATUS current
                  DESCRIPTION "QuickMode-Proposal-List-Default"
                  ::= {  setVpn 19 }

setVpnQuickmodepf OBJECT-TYPE
                  SYNTAX INTEGER
                  MAX-ACCESS read-write
                  STATUS current
                  DESCRIPTION "QuickMode-PFS-Group-Default"
                  ::= {  setVpn 20 }

setVpnQuickmodesh OBJECT-TYPE
                  SYNTAX INTEGER
                  MAX-ACCESS read-write
                  STATUS current
                  DESCRIPTION "QuickMode-Shorthold-Time-Default"
                  ::= {  setVpn 21 }

setVpnLegacydynvp OBJECT-TYPE
                  SYNTAX INTEGER
                  {
                    no(0),
                    yes(1)
                  }
                  MAX-ACCESS read-write
                  STATUS current
                  DESCRIPTION "legacy-dyn-VPN(LCOS5.0x)-support"
                  ::= {  setVpn 15 }

setHttp OBJECT IDENTIFIER ::= { set 21}
setHttpDoc OBJECT-TYPE
           SYNTAX DisplayString (SIZE(0..99))
           MAX-ACCESS read-write
           STATUS current
           DESCRIPTION "Document-Root"
           ::= {  setHttp 1 }

setHttpUse OBJECT-TYPE
           SYNTAX INTEGER
           {
             no(0),
             yes(1)
           }
           MAX-ACCESS read-write
           STATUS current
           DESCRIPTION "Use-CSS"
           ::= {  setHttp 2 }

setHttpFon OBJECT-TYPE
           SYNTAX DisplayString (SIZE(0..39))
           MAX-ACCESS read-write
           STATUS current
           DESCRIPTION "Font-Family"
           ::= {  setHttp 3 }

setHttpErr OBJECT-TYPE
           SYNTAX INTEGER
           {
             standard(0),
             nifty(1)
           }
           MAX-ACCESS read-write
           STATUS current
           DESCRIPTION "Error-Page-Style"
           ::= {  setHttp 6 }

setHttpPor OBJECT-TYPE
           SYNTAX INTEGER
           MAX-ACCESS read-write
           STATUS current
           DESCRIPTION "Port"
           ::= {  setHttp 7 }

setHttpSsl OBJECT-TYPE
           SYNTAX INTEGER
           MAX-ACCESS read-write
           STATUS current
           DESCRIPTION "SSL-Port"
           ::= {  setHttp 8 }

setHttpSes OBJECT-TYPE
           SYNTAX INTEGER
           MAX-ACCESS read-write
           STATUS current
           DESCRIPTION "Session-Timeout"
           ::= {  setHttp 11 }

setHttpSta OBJECT-TYPE
           SYNTAX INTEGER
           {
             normal-design(0),
             design-for-small-resolutions(1),
             design-with-high-contrast(2)
           }
           MAX-ACCESS read-write
           STATUS current
           DESCRIPTION "Standard-Design"
           ::= {  setHttp 13 }

setHttpShoTable OBJECT-TYPE
                SYNTAX SEQUENCE OF SetHttpShoEntry
                MAX-ACCESS not-accessible
                STATUS current
                DESCRIPTION "Show-device-information"
                ::= {  setHttp 14 }

setHttpShoEntry OBJECT-TYPE
                SYNTAX SetHttpShoEntry
                MAX-ACCESS not-accessible
                STATUS current
                DESCRIPTION "entry in table"
                INDEX { setHttpShoDev }
                ::= {  setHttpShoTable 1 }

SetHttpShoEntry ::= SEQUENCE {
                setHttpShoDev INTEGER,
                setHttpShoPos INTEGER
               }

setHttpShoDev OBJECT-TYPE
              SYNTAX INTEGER
              {
                cpu(1),
                memory(2),
                ethernet-ports(5),
                troughput-ethernet(6),
                umts-modem-interface(7),
                router(8),
                firewall(9),
                dhcp(10),
                dns(11),
                vpn(12),
                isdn(14),
                dsl-dslol(15),
                time(18),
                ip-addresses(19),
                operating-time(20)
              }
              MAX-ACCESS read-write
              STATUS current
              DESCRIPTION "Device-Information"
              ::= {  setHttpShoEntry 1 }

setHttpShoPos OBJECT-TYPE
              SYNTAX INTEGER (0..2147483647)
              MAX-ACCESS read-write
              STATUS current
              DESCRIPTION "Position"
              ::= {  setHttpShoEntry 2 }

setHttpHtt OBJECT-TYPE
           SYNTAX INTEGER
           {
             activated(0),
             only-for-wan(1),
             deactivated(2)
           }
           MAX-ACCESS read-write
           STATUS current
           DESCRIPTION "HTTP-Compression"
           ::= {  setHttp 15 }

setHttpMax OBJECT-TYPE
           SYNTAX INTEGER
           MAX-ACCESS read-write
           STATUS current
           DESCRIPTION "Max-Tunnel-Connections"
           ::= {  setHttp 9 }

setHttpTun OBJECT-TYPE
           SYNTAX INTEGER
           MAX-ACCESS read-write
           STATUS current
           DESCRIPTION "Tunnel-Idle-Timeout"
           ::= {  setHttp 10 }

setHttpRol OBJECT IDENTIFIER ::= { setHttp 20}
setHttpRolOperating OBJECT-TYPE
                    SYNTAX INTEGER
                    {
                      no(0),
                      yes(1)
                    }
                    MAX-ACCESS read-write
                    STATUS current
                    DESCRIPTION "Operating"
                    ::= {  setHttpRol 1 }

setHttpRolTitle OBJECT-TYPE
                    SYNTAX DisplayString (SIZE(0..50))
                    MAX-ACCESS read-write
                    STATUS current
                    DESCRIPTION "Title"
                    ::= {  setHttpRol 2 }

setHttpRolVariablesTable OBJECT-TYPE
                         SYNTAX SEQUENCE OF SetHttpRolVariablesEntry
                         MAX-ACCESS not-accessible
                         STATUS current
                         DESCRIPTION "Variables"
                         ::= {  setHttpRol 3 }

setHttpRolVariablesEntry OBJECT-TYPE
                         SYNTAX SetHttpRolVariablesEntry
                         MAX-ACCESS not-accessible
                         STATUS current
                         DESCRIPTION "entry in table"
                         INDEX { setHttpRolVariablesInd }
                         ::= {  setHttpRolVariablesTable 1 }

SetHttpRolVariablesEntry ::= SEQUENCE {
                         setHttpRolVariablesInd INTEGER,
                         setHttpRolVariablesIde DisplayString,
                         setHttpRolVariablesTit DisplayString,
                         setHttpRolVariablesTyp INTEGER,
                         setHttpRolVariablesMin INTEGER,
                         setHttpRolVariablesMax INTEGER,
                         setHttpRolVariablesDef DisplayString
                        }

setHttpRolVariablesInd OBJECT-TYPE
                       SYNTAX INTEGER (0..2147483647)
                       MAX-ACCESS read-write
                       STATUS current
                       DESCRIPTION "Index"
                       ::= {  setHttpRolVariablesEntry 1 }

setHttpRolVariablesIde OBJECT-TYPE
                       SYNTAX DisplayString (SIZE(0..16))
                       MAX-ACCESS read-write
                       STATUS current
                       DESCRIPTION "Ident"
                       ::= {  setHttpRolVariablesEntry 2 }

setHttpRolVariablesTit OBJECT-TYPE
                       SYNTAX DisplayString (SIZE(0..40))
                       MAX-ACCESS read-write
                       STATUS current
                       DESCRIPTION "Title"
                       ::= {  setHttpRolVariablesEntry 3 }

setHttpRolVariablesTyp OBJECT-TYPE
                       SYNTAX INTEGER
                       {
                         label(0),
                         integer(1),
                         string(2),
                         password(3),
                         checkmark(4)
                       }
                       MAX-ACCESS read-write
                       STATUS current
                       DESCRIPTION "Type"
                       ::= {  setHttpRolVariablesEntry 4 }

setHttpRolVariablesMin OBJECT-TYPE
                       SYNTAX INTEGER (0..2147483647)
                       MAX-ACCESS read-write
                       STATUS current
                       DESCRIPTION "Min-Value"
                       ::= {  setHttpRolVariablesEntry 5 }

setHttpRolVariablesMax OBJECT-TYPE
                       SYNTAX INTEGER (0..2147483647)
                       MAX-ACCESS read-write
                       STATUS current
                       DESCRIPTION "Max-Value"
                       ::= {  setHttpRolVariablesEntry 6 }

setHttpRolVariablesDef OBJECT-TYPE
                       SYNTAX DisplayString (SIZE(0..30))
                       MAX-ACCESS read-write
                       STATUS current
                       DESCRIPTION "Default-Value"
                       ::= {  setHttpRolVariablesEntry 7 }

setHttpRolRenumberv OBJECT-TYPE
                    SYNTAX DisplayString
                    MAX-ACCESS read-write
                    STATUS current
                    DESCRIPTION "Renumber-Variables"
                    ::= {  setHttpRol 5 }

setHttpRolActionsTable OBJECT-TYPE
                         SYNTAX SEQUENCE OF SetHttpRolActionsEntry
                         MAX-ACCESS not-accessible
                         STATUS current
                         DESCRIPTION "Actions"
                         ::= {  setHttpRol 4 }

setHttpRolActionsEntry OBJECT-TYPE
                         SYNTAX SetHttpRolActionsEntry
                         MAX-ACCESS not-accessible
                         STATUS current
                         DESCRIPTION "entry in table"
                         INDEX { setHttpRolActionsInd }
                         ::= {  setHttpRolActionsTable 1 }

SetHttpRolActionsEntry ::= SEQUENCE {
                         setHttpRolActionsInd INTEGER,
                         setHttpRolActionsAct DisplayString,
                         setHttpRolActionsDes DisplayString
                        }

setHttpRolActionsInd OBJECT-TYPE
                     SYNTAX INTEGER (0..2147483647)
                     MAX-ACCESS read-write
                     STATUS current
                     DESCRIPTION "Index"
                     ::= {  setHttpRolActionsEntry 1 }

setHttpRolActionsAct OBJECT-TYPE
                     SYNTAX DisplayString (SIZE(0..251))
                     MAX-ACCESS read-write
                     STATUS current
                     DESCRIPTION "Action"
                     ::= {  setHttpRolActionsEntry 2 }

setHttpRolActionsDes OBJECT-TYPE
                     SYNTAX DisplayString (SIZE(0..251))
                     MAX-ACCESS read-write
                     STATUS current
                     DESCRIPTION "Description"
                     ::= {  setHttpRolActionsEntry 3 }

setHttpRolRenumbera OBJECT-TYPE
                    SYNTAX DisplayString
                    MAX-ACCESS read-write
                    STATUS current
                    DESCRIPTION "Renumber-Actions"
                    ::= {  setHttpRol 6 }

setHttpRolDisplayco OBJECT-TYPE
                    SYNTAX BITS
                    {
                      isdn(30),
                      vpn(29),
                      dsl(28)
                    }
                    MAX-ACCESS read-write
                    STATUS current
                    DESCRIPTION "Display-Connection-Status-for"
                    ::= {  setHttpRol 7 }

setSysl OBJECT IDENTIFIER ::= { set 22}
setSyslOpe OBJECT-TYPE
           SYNTAX INTEGER
           {
             no(0),
             yes(1)
           }
           MAX-ACCESS read-write
           STATUS current
           DESCRIPTION "Operating"
           ::= {  setSysl 1 }

setSyslSerTable OBJECT-TYPE
                SYNTAX SEQUENCE OF SetSyslSerEntry
                MAX-ACCESS not-accessible
                STATUS current
                DESCRIPTION "Server"
                ::= {  setSysl 2 }

setSyslSerEntry OBJECT-TYPE
                SYNTAX SetSyslSerEntry
                MAX-ACCESS not-accessible
                STATUS current
                DESCRIPTION "entry in table"
                INDEX { setSyslSerIdx }
                ::= {  setSyslSerTable 1 }

SetSyslSerEntry ::= SEQUENCE {
                setSyslSerIdx DisplayString,
                setSyslSerIpa IpAddress,
                setSyslSerSou INTEGER,
                setSyslSerLev INTEGER,
                setSyslSerLoo DisplayString
               }

setSyslSerIdx OBJECT-TYPE
              SYNTAX DisplayString (SIZE(0..4))
              MAX-ACCESS read-write
              STATUS current
              DESCRIPTION "Idx."
              ::= {  setSyslSerEntry 1 }

setSyslSerIpa OBJECT-TYPE
              SYNTAX IpAddress
              MAX-ACCESS read-write
              STATUS current
              DESCRIPTION "IP-Address"
              ::= {  setSyslSerEntry 2 }

setSyslSerSou OBJECT-TYPE
              SYNTAX INTEGER (0..255)
              MAX-ACCESS read-write
              STATUS current
              DESCRIPTION "Source"
              ::= {  setSyslSerEntry 3 }

setSyslSerLev OBJECT-TYPE
              SYNTAX INTEGER (0..255)
              MAX-ACCESS read-write
              STATUS current
              DESCRIPTION "Level"
              ::= {  setSyslSerEntry 4 }

setSyslSerLoo OBJECT-TYPE
              SYNTAX DisplayString (SIZE(0..16))
              MAX-ACCESS read-write
              STATUS current
              DESCRIPTION "Loopback-Addr."
              ::= {  setSyslSerEntry 6 }

setSyslFacTable OBJECT-TYPE
                SYNTAX SEQUENCE OF SetSyslFacEntry
                MAX-ACCESS not-accessible
                STATUS current
                DESCRIPTION "Facility-Mapper"
                ::= {  setSysl 3 }

setSyslFacEntry OBJECT-TYPE
                SYNTAX SetSyslFacEntry
                MAX-ACCESS not-accessible
                STATUS current
                DESCRIPTION "entry in table"
                INDEX { setSyslFacSou }
                ::= {  setSyslFacTable 1 }

SetSyslFacEntry ::= SEQUENCE {
                setSyslFacSou INTEGER,
                setSyslFacFac INTEGER
               }

setSyslFacSou OBJECT-TYPE
              SYNTAX INTEGER
              {
                system(1),
                login(2),
                systemtime(4),
                console-login(8),
                connections(16),
                accounting(32),
                administration(64),
                router(128)
              }
              MAX-ACCESS read-only
              STATUS current
              DESCRIPTION "Source"
              ::= {  setSyslFacEntry 1 }

setSyslFacFac OBJECT-TYPE
              SYNTAX INTEGER
              {
                kern(0),
                user(1),
                mail(2),
                daemon(3),
                auth(4),
                syslog(5),
                lpr(6),
                news(7),
                uucp(8),
                cron(9),
                authpriv(10),
                local0(16),
                local1(17),
                local2(18),
                local3(19),
                local4(20),
                local5(21),
                local6(22),
                local7(23)
              }
              MAX-ACCESS read-write
              STATUS current
              DESCRIPTION "Facility"
              ::= {  setSyslFacEntry 2 }

setSyslPor OBJECT-TYPE
           SYNTAX INTEGER
           MAX-ACCESS read-write
           STATUS current
           DESCRIPTION "Port"
           ::= {  setSysl 4 }

setSyslMes OBJECT-TYPE
           SYNTAX INTEGER
           {
             oldest-on-top(0),
             newest-on-top(1)
           }
           MAX-ACCESS read-write
           STATUS current
           DESCRIPTION "Messages-Table-Order"
           ::= {  setSysl 5 }

setInte OBJECT IDENTIFIER ::= { set 23}
setInteModem OBJECT IDENTIFIER ::= { setInte 40}
setInteModemRingcou OBJECT-TYPE
                    SYNTAX INTEGER
                    MAX-ACCESS read-write
                    STATUS current
                    DESCRIPTION "Ring-Count"
                    ::= {  setInteModem 1 }

setInteModemEchooff OBJECT-TYPE
                    SYNTAX DisplayString (SIZE(0..9))
                    MAX-ACCESS read-write
                    STATUS current
                    DESCRIPTION "Echo-Off-Command"
                    ::= {  setInteModem 2 }

setInteModemResetco OBJECT-TYPE
                    SYNTAX DisplayString (SIZE(0..9))
                    MAX-ACCESS read-write
                    STATUS current
                    DESCRIPTION "Reset-Command"
                    ::= {  setInteModem 3 }

setInteModemInitcom OBJECT-TYPE
                    SYNTAX DisplayString (SIZE(0..63))
                    MAX-ACCESS read-write
                    STATUS current
                    DESCRIPTION "Init-Command"
                    ::= {  setInteModem 4 }

setInteModemRequest OBJECT-TYPE
                    SYNTAX DisplayString (SIZE(0..9))
                    MAX-ACCESS read-write
                    STATUS current
                    DESCRIPTION "Request-ID"
                    ::= {  setInteModem 6 }

setInteModemInitdia OBJECT-TYPE
                    SYNTAX DisplayString (SIZE(0..63))
                    MAX-ACCESS read-write
                    STATUS current
                    DESCRIPTION "Init.-Dial"
                    ::= {  setInteModem 11 }

setInteModemDialcom OBJECT-TYPE
                    SYNTAX DisplayString (SIZE(0..31))
                    MAX-ACCESS read-write
                    STATUS current
                    DESCRIPTION "Dial-Command"
                    ::= {  setInteModem 5 }

setInteModemInitans OBJECT-TYPE
                    SYNTAX DisplayString (SIZE(0..63))
                    MAX-ACCESS read-write
                    STATUS current
                    DESCRIPTION "Init.-Answer"
                    ::= {  setInteModem 12 }

setInteModemAnswerc OBJECT-TYPE
                    SYNTAX DisplayString (SIZE(0..9))
                    MAX-ACCESS read-write
                    STATUS current
                    DESCRIPTION "Answer-Command"
                    ::= {  setInteModem 7 }

setInteModemDisconn OBJECT-TYPE
                    SYNTAX DisplayString (SIZE(0..9))
                    MAX-ACCESS read-write
                    STATUS current
                    DESCRIPTION "Disconnect-Command"
                    ::= {  setInteModem 8 }

setInteModemEscapes OBJECT-TYPE
                    SYNTAX DisplayString (SIZE(0..9))
                    MAX-ACCESS read-write
                    STATUS current
                    DESCRIPTION "Escape-Sequence"
                    ::= {  setInteModem 9 }

setInteModemEscapep OBJECT-TYPE
                    SYNTAX INTEGER
                    MAX-ACCESS read-write
                    STATUS current
                    DESCRIPTION "Escape-Promt-Delay-(ms)"
                    ::= {  setInteModem 10 }

setInteModemCycleti OBJECT-TYPE
                    SYNTAX INTEGER
                    MAX-ACCESS read-write
                    STATUS current
                    DESCRIPTION "Cycletime-AT-Poll-(s)"
                    ::= {  setInteModem 13 }

setInteModemAtpollc OBJECT-TYPE
                    SYNTAX INTEGER
                    MAX-ACCESS read-write
                    STATUS current
                    DESCRIPTION "AT-Poll-Count"
                    ::= {  setInteModem 14 }

setInteMobile OBJECT IDENTIFIER ::= { setInte 41}
setInteMobileProTable OBJECT-TYPE
                      SYNTAX SEQUENCE OF SetInteMobileProEntry
                      MAX-ACCESS not-accessible
                      STATUS current
                      DESCRIPTION "Profiles"
                      ::= {  setInteMobile 1 }

setInteMobileProEntry OBJECT-TYPE
                      SYNTAX SetInteMobileProEntry
                      MAX-ACCESS not-accessible
                      STATUS current
                      DESCRIPTION "entry in table"
                      INDEX { setInteMobileProProf }
                      ::= {  setInteMobileProTable 1 }

SetInteMobileProEntry ::= SEQUENCE {
                      setInteMobileProProf DisplayString,
                      setInteMobileProPin DisplayString,
                      setInteMobileProApn DisplayString,
                      setInteMobileProNetw DisplayString,
                      setInteMobileProSele INTEGER,
                      setInteMobileProMode INTEGER,
                      setInteMobileProQosd INTEGER,
                      setInteMobileProQosu INTEGER
                     }

setInteMobileProProf OBJECT-TYPE
                     SYNTAX DisplayString (SIZE(0..16))
                     MAX-ACCESS read-write
                     STATUS current
                     DESCRIPTION "Profile"
                     ::= {  setInteMobileProEntry 1 }

setInteMobileProPin OBJECT-TYPE
                     SYNTAX DisplayString (SIZE(0..6))
                     MAX-ACCESS read-write
                     STATUS current
                     DESCRIPTION "PIN"
                     ::= {  setInteMobileProEntry 2 }

setInteMobileProApn OBJECT-TYPE
                     SYNTAX DisplayString (SIZE(0..47))
                     MAX-ACCESS read-write
                     STATUS current
                     DESCRIPTION "APN"
                     ::= {  setInteMobileProEntry 3 }

setInteMobileProNetw OBJECT-TYPE
                     SYNTAX DisplayString (SIZE(0..16))
                     MAX-ACCESS read-write
                     STATUS current
                     DESCRIPTION "Network"
                     ::= {  setInteMobileProEntry 4 }

setInteMobileProSele OBJECT-TYPE
                     SYNTAX INTEGER
                     {
                       auto(0),
                       manual(1)
                     }
                     MAX-ACCESS read-write
                     STATUS current
                     DESCRIPTION "Select"
                     ::= {  setInteMobileProEntry 5 }

setInteMobileProMode OBJECT-TYPE
                     SYNTAX INTEGER
                     {
                       auto(0),
                       umts(1),
                       gprs(2)
                     }
                     MAX-ACCESS read-write
                     STATUS current
                     DESCRIPTION "Mode"
                     ::= {  setInteMobileProEntry 6 }

setInteMobileProQosd OBJECT-TYPE
                     SYNTAX INTEGER (0..2147483647)
                     MAX-ACCESS read-write
                     STATUS current
                     DESCRIPTION "QoS-downstream-data-rate"
                     ::= {  setInteMobileProEntry 7 }

setInteMobileProQosu OBJECT-TYPE
                     SYNTAX INTEGER (0..2147483647)
                     MAX-ACCESS read-write
                     STATUS current
                     DESCRIPTION "QoS-upstream-data-rate"
                     ::= {  setInteMobileProEntry 8 }

setInteMobileCon OBJECT-TYPE
                 SYNTAX INTEGER
                 {
                   none(0),
                   ppp(1),
                   ppp-plus-ip(3)
                 }
                 MAX-ACCESS read-write
                 STATUS current
                 DESCRIPTION "Connect-Monitoring"
                 ::= {  setInteMobile 4 }

setInteMobileTri OBJECT-TYPE
                 SYNTAX INTEGER
                 MAX-ACCESS read-write
                 STATUS current
                 DESCRIPTION "Tries"
                 ::= {  setInteMobile 5 }

setInteMobileHis OBJECT-TYPE
                 SYNTAX INTEGER
                 MAX-ACCESS read-write
                 STATUS current
                 DESCRIPTION "History-Interval[Sec]"
                 ::= {  setInteMobile 6 }

setInteMobileSys OBJECT-TYPE
                 SYNTAX INTEGER
                 {
                   no(0),
                   yes(1)
                 }
                 MAX-ACCESS read-write
                 STATUS current
                 DESCRIPTION "Syslog-enabled"
                 ::= {  setInteMobile 7 }

setInteMobileSca OBJECT-TYPE
                 SYNTAX DisplayString
                 MAX-ACCESS read-write
                 STATUS current
                 DESCRIPTION "Scan-Networks"
                 ::= {  setInteMobile 2 }

setInteMobileInp OBJECT-TYPE
                 SYNTAX DisplayString
                 MAX-ACCESS read-write
                 STATUS current
                 DESCRIPTION "Input-PUK"
                 ::= {  setInteMobile 3 }

setInteEthernTable OBJECT-TYPE
                   SYNTAX SEQUENCE OF SetInteEthernEntry
                   MAX-ACCESS not-accessible
                   STATUS current
                   DESCRIPTION "Ethernet-Ports"
                   ::= {  setInte 30 }

setInteEthernEntry OBJECT-TYPE
                   SYNTAX SetInteEthernEntry
                   MAX-ACCESS not-accessible
                   STATUS current
                   DESCRIPTION "entry in table"
                   INDEX { setInteEthernPor }
                   ::= {  setInteEthernTable 1 }

SetInteEthernEntry ::= SEQUENCE {
                   setInteEthernPor INTEGER,
                   setInteEthernAss INTEGER,
                   setInteEthernCon INTEGER,
                   setInteEthernMdi INTEGER,
                   setInteEthernPri INTEGER
                  }

setInteEthernPor OBJECT-TYPE
                 SYNTAX INTEGER
                 {
                   wan(1),
                   eth-1(2),
                   eth-2(3),
                   eth-3(4),
                   eth-4(5),
                   unknown(0)
                 }
                 MAX-ACCESS read-only
                 STATUS current
                 DESCRIPTION "Port"
                 ::= {  setInteEthernEntry 1 }

setInteEthernAss OBJECT-TYPE
                 SYNTAX INTEGER
                 {
                   dsl-1(512),
                   dsl-2(513),
                   dsl-3(514),
                   dsl-4(515),
                   lan-1(0),
                   lan-2(1),
                   lan-3(2),
                   lan-4(3),
                   idle(65533),
                   monitor(65534),
                   power-down(65535)
                 }
                 MAX-ACCESS read-write
                 STATUS current
                 DESCRIPTION "Assignment"
                 ::= {  setInteEthernEntry 4 }

setInteEthernCon OBJECT-TYPE
                 SYNTAX INTEGER
                 {
                   auto(0),
                   e10b-t(1),
                   fd10b-tx(2),
                   e100b-tx(3),
                   fd100b-tx(4)
                 }
                 MAX-ACCESS read-write
                 STATUS current
                 DESCRIPTION "Connector"
                 ::= {  setInteEthernEntry 2 }

setInteEthernMdi OBJECT-TYPE
                 SYNTAX INTEGER
                 {
                   auto(0),
                   mdi(1),
                   mdix(2)
                 }
                 MAX-ACCESS read-write
                 STATUS current
                 DESCRIPTION "MDI-Mode"
                 ::= {  setInteEthernEntry 5 }

setInteEthernPri OBJECT-TYPE
                 SYNTAX INTEGER
                 {
                   no(0),
                   yes(1)
                 }
                 MAX-ACCESS read-write
                 STATUS current
                 DESCRIPTION "Private-Mode"
                 ::= {  setInteEthernEntry 3 }

setInteDslTable OBJECT-TYPE
                   SYNTAX SEQUENCE OF SetInteDslEntry
                   MAX-ACCESS not-accessible
                   STATUS current
                   DESCRIPTION "DSL"
                   ::= {  setInte 4 }

setInteDslEntry OBJECT-TYPE
                   SYNTAX SetInteDslEntry
                   MAX-ACCESS not-accessible
                   STATUS current
                   DESCRIPTION "entry in table"
                   INDEX { setInteDslIfc }
                   ::= {  setInteDslTable 1 }

SetInteDslEntry ::= SEQUENCE {
                   setInteDslIfc INTEGER,
                   setInteDslOpe INTEGER,
                   setInteDslUps INTEGER,
                   setInteDslExt INTEGER,
                   setInteDslDow INTEGER,
                   setInteDslTyp INTEGER
                  }

setInteDslIfc OBJECT-TYPE
              SYNTAX INTEGER
              {
                dsl-1(1),
                dsl-2(2),
                dsl-3(3),
                dsl-4(4),
                s0-1(5),
                ext(6)
              }
              MAX-ACCESS read-only
              STATUS current
              DESCRIPTION "Ifc"
              ::= {  setInteDslEntry 1 }

setInteDslOpe OBJECT-TYPE
              SYNTAX INTEGER
              {
                no(0),
                yes(16)
              }
              MAX-ACCESS read-write
              STATUS current
              DESCRIPTION "Operating"
              ::= {  setInteDslEntry 2 }

setInteDslUps OBJECT-TYPE
              SYNTAX INTEGER (0..2147483647)
              MAX-ACCESS read-write
              STATUS current
              DESCRIPTION "Upstream-Rate"
              ::= {  setInteDslEntry 16 }

setInteDslExt OBJECT-TYPE
              SYNTAX INTEGER (0..2147483647)
              MAX-ACCESS read-write
              STATUS current
              DESCRIPTION "Ext.-Overhead"
              ::= {  setInteDslEntry 17 }

setInteDslDow OBJECT-TYPE
              SYNTAX INTEGER (0..2147483647)
              MAX-ACCESS read-write
              STATUS current
              DESCRIPTION "Downstream-Rate"
              ::= {  setInteDslEntry 18 }

setInteDslTyp OBJECT-TYPE
              SYNTAX INTEGER (0..2147483647)
              MAX-ACCESS read-only
              STATUS current
              DESCRIPTION "Type-of-interface"
              ::= {  setInteDslEntry 15 }

setInteS0Table OBJECT-TYPE
                   SYNTAX SEQUENCE OF SetInteS0Entry
                   MAX-ACCESS not-accessible
                   STATUS current
                   DESCRIPTION "S0"
                   ::= {  setInte 1 }

setInteS0Entry OBJECT-TYPE
                   SYNTAX SetInteS0Entry
                   MAX-ACCESS not-accessible
                   STATUS current
                   DESCRIPTION "entry in table"
                   INDEX { setInteS0Ifc }
                   ::= {  setInteS0Table 1 }

SetInteS0Entry ::= SEQUENCE {
                   setInteS0Ifc INTEGER,
                   setInteS0Prot INTEGER,
                   setInteS0Llbc INTEGER,
                   setInteS0Dial DisplayString,
                   setInteS0Maxi INTEGER,
                   setInteS0Maxo INTEGER,
                   setInteS0Type INTEGER
                  }

setInteS0Ifc OBJECT-TYPE
              SYNTAX INTEGER
              {
                dsl-1(1),
                dsl-2(2),
                dsl-3(3),
                dsl-4(4),
                s0-1(5),
                ext(6)
              }
              MAX-ACCESS read-only
              STATUS current
              DESCRIPTION "Ifc"
              ::= {  setInteS0Entry 1 }

setInteS0Prot OBJECT-TYPE
              SYNTAX INTEGER
              {
                no(0),
                dss1(1),
                e1tr6(2),
                p2p-dss1(4),
                grp0(16),
                auto(255)
              }
              MAX-ACCESS read-write
              STATUS current
              DESCRIPTION "Protocol"
              ::= {  setInteS0Entry 2 }

setInteS0Llbc OBJECT-TYPE
              SYNTAX INTEGER
              {
                none(0),
                b1(1),
                b2(2)
              }
              MAX-ACCESS read-write
              STATUS current
              DESCRIPTION "LL-B-chan."
              ::= {  setInteS0Entry 7 }

setInteS0Dial OBJECT-TYPE
              SYNTAX DisplayString (SIZE(0..8))
              MAX-ACCESS read-write
              STATUS current
              DESCRIPTION "Dial-prefix"
              ::= {  setInteS0Entry 9 }

setInteS0Maxi OBJECT-TYPE
              SYNTAX INTEGER
              {
                zero(2),
                one(1),
                two(0)
              }
              MAX-ACCESS read-write
              STATUS current
              DESCRIPTION "Max-in-calls"
              ::= {  setInteS0Entry 13 }

setInteS0Maxo OBJECT-TYPE
              SYNTAX INTEGER
              {
                zero(2),
                one(1),
                two(0)
              }
              MAX-ACCESS read-write
              STATUS current
              DESCRIPTION "Max-out-calls"
              ::= {  setInteS0Entry 14 }

setInteS0Type OBJECT-TYPE
              SYNTAX INTEGER (0..2147483647)
              MAX-ACCESS read-only
              STATUS current
              DESCRIPTION "Type-of-interface"
              ::= {  setInteS0Entry 15 }

setInteModemmTable OBJECT-TYPE
                   SYNTAX SEQUENCE OF SetInteModemmEntry
                   MAX-ACCESS not-accessible
                   STATUS current
                   DESCRIPTION "Modem-Mobile"
                   ::= {  setInte 7 }

setInteModemmEntry OBJECT-TYPE
                   SYNTAX SetInteModemmEntry
                   MAX-ACCESS not-accessible
                   STATUS current
                   DESCRIPTION "entry in table"
                   INDEX { setInteModemmIfc }
                   ::= {  setInteModemmTable 1 }

SetInteModemmEntry ::= SEQUENCE {
                   setInteModemmIfc INTEGER,
                   setInteModemmOpe INTEGER,
                   setInteModemmTyp INTEGER,
                   setInteModemmDat INTEGER,
                   setInteModemmPro DisplayString
                  }

setInteModemmIfc OBJECT-TYPE
                 SYNTAX INTEGER
                 {
                   dsl-1(1),
                   dsl-2(2),
                   dsl-3(3),
                   dsl-4(4),
                   s0-1(5),
                   ext(6)
                 }
                 MAX-ACCESS read-only
                 STATUS current
                 DESCRIPTION "Ifc"
                 ::= {  setInteModemmEntry 1 }

setInteModemmOpe OBJECT-TYPE
                 SYNTAX INTEGER
                 {
                   no(0),
                   modem(1),
                   umts-gprs(2)
                 }
                 MAX-ACCESS read-write
                 STATUS current
                 DESCRIPTION "Operating"
                 ::= {  setInteModemmEntry 2 }

setInteModemmTyp OBJECT-TYPE
                 SYNTAX INTEGER (0..2147483647)
                 MAX-ACCESS read-only
                 STATUS current
                 DESCRIPTION "Type-of-interface"
                 ::= {  setInteModemmEntry 15 }

setInteModemmDat OBJECT-TYPE
                 SYNTAX INTEGER
                 {
                   e19200(19200),
                   e38400(38400),
                   e57600(57600),
                   e115200(115200)
                 }
                 MAX-ACCESS read-write
                 STATUS current
                 DESCRIPTION "Data-Rate"
                 ::= {  setInteModemmEntry 21 }

setInteModemmPro OBJECT-TYPE
                 SYNTAX DisplayString (SIZE(0..16))
                 MAX-ACCESS read-write
                 STATUS current
                 DESCRIPTION "Profile"
                 ::= {  setInteModemmEntry 22 }

setRadi OBJECT IDENTIFIER ::= { set 25}
setRadiAutht OBJECT-TYPE
             SYNTAX INTEGER
             MAX-ACCESS read-write
             STATUS current
             DESCRIPTION "Auth.-Timeout"
             ::= {  setRadi 4 }

setRadiAuthr OBJECT-TYPE
             SYNTAX INTEGER
             MAX-ACCESS read-write
             STATUS current
             DESCRIPTION "Auth.-Retry"
             ::= {  setRadi 5 }

setRadiBacku OBJECT-TYPE
             SYNTAX INTEGER
             {
               block(0),
               cyclic(1)
             }
             MAX-ACCESS read-write
             STATUS current
             DESCRIPTION "Backup-Query-Strategy"
             ::= {  setRadi 9 }

setNtp OBJECT IDENTIFIER ::= { set 26}
setNtpSer OBJECT-TYPE
          SYNTAX INTEGER
          {
            no(0),
            yes(1)
          }
          MAX-ACCESS read-write
          STATUS current
          DESCRIPTION "Server-Operating"
          ::= {  setNtp 2 }

setNtpBcm OBJECT-TYPE
          SYNTAX INTEGER
          {
            no(0),
            yes(1)
          }
          MAX-ACCESS read-write
          STATUS current
          DESCRIPTION "BC-Mode"
          ::= {  setNtp 3 }

setNtpBci OBJECT-TYPE
          SYNTAX INTEGER
          MAX-ACCESS read-write
          STATUS current
          DESCRIPTION "BC-Interval"
          ::= {  setNtp 4 }

setNtpRqi OBJECT-TYPE
          SYNTAX INTEGER
          MAX-ACCESS read-write
          STATUS current
          DESCRIPTION "RQ-Interval"
          ::= {  setNtp 7 }

setNtpRqt OBJECT-TYPE
          SYNTAX INTEGER
          MAX-ACCESS read-write
          STATUS current
          DESCRIPTION "RQ-Tries"
          ::= {  setNtp 12 }

setNtpRqaTable OBJECT-TYPE
               SYNTAX SEQUENCE OF SetNtpRqaEntry
               MAX-ACCESS not-accessible
               STATUS current
               DESCRIPTION "RQ-Address"
               ::= {  setNtp 11 }

setNtpRqaEntry OBJECT-TYPE
               SYNTAX SetNtpRqaEntry
               MAX-ACCESS not-accessible
               STATUS current
               DESCRIPTION "entry in table"
               INDEX { setNtpRqaRqa }
               ::= {  setNtpRqaTable 1 }

SetNtpRqaEntry ::= SEQUENCE {
               setNtpRqaRqa DisplayString,
               setNtpRqaLoo DisplayString
              }

setNtpRqaRqa OBJECT-TYPE
             SYNTAX DisplayString (SIZE(0..31))
             MAX-ACCESS read-write
             STATUS current
             DESCRIPTION "RQ-Address"
             ::= {  setNtpRqaEntry 1 }

setNtpRqaLoo OBJECT-TYPE
             SYNTAX DisplayString (SIZE(0..16))
             MAX-ACCESS read-write
             STATUS current
             DESCRIPTION "Loopback-Addr."
             ::= {  setNtpRqaEntry 2 }

setMail OBJECT IDENTIFIER ::= { set 27}
setMailSmtps OBJECT-TYPE
             SYNTAX DisplayString (SIZE(0..31))
             MAX-ACCESS read-write
             STATUS current
             DESCRIPTION "SMTP-Server"
             ::= {  setMail 1 }

setMailSmtpp OBJECT-TYPE
             SYNTAX INTEGER
             MAX-ACCESS read-write
             STATUS current
             DESCRIPTION "SMTP-Port"
             ::= {  setMail 2 }

setMailPop3s OBJECT-TYPE
             SYNTAX DisplayString (SIZE(0..31))
             MAX-ACCESS read-write
             STATUS current
             DESCRIPTION "POP3-Server"
             ::= {  setMail 3 }

setMailPop3p OBJECT-TYPE
             SYNTAX INTEGER
             MAX-ACCESS read-write
             STATUS current
             DESCRIPTION "POP3-Port"
             ::= {  setMail 4 }

setMailLoopb OBJECT-TYPE
             SYNTAX DisplayString (SIZE(0..16))
             MAX-ACCESS read-write
             STATUS current
             DESCRIPTION "Loopback-Addr."
             ::= {  setMail 11 }

setMailUsern OBJECT-TYPE
             SYNTAX DisplayString (SIZE(0..63))
             MAX-ACCESS read-write
             STATUS current
             DESCRIPTION "User-Name"
             ::= {  setMail 5 }

setMailPassw OBJECT-TYPE
             SYNTAX DisplayString (SIZE(0..31))
             MAX-ACCESS read-write
             STATUS current
             DESCRIPTION "Password"
             ::= {  setMail 6 }

setMailEmail OBJECT-TYPE
             SYNTAX DisplayString (SIZE(0..63))
             MAX-ACCESS read-write
             STATUS current
             DESCRIPTION "E-Mail-Sender"
             ::= {  setMail 7 }

setMailSenda OBJECT-TYPE
             SYNTAX INTEGER
             MAX-ACCESS read-write
             STATUS current
             DESCRIPTION "Send-Again-(min.)"
             ::= {  setMail 8 }

setMailHoldt OBJECT-TYPE
             SYNTAX INTEGER
             MAX-ACCESS read-write
             STATUS current
             DESCRIPTION "Hold-Time-(hrs.)"
             ::= {  setMail 9 }

setMailBuffe OBJECT-TYPE
             SYNTAX INTEGER
             MAX-ACCESS read-write
             STATUS current
             DESCRIPTION "Buffers"
             ::= {  setMail 10 }

setPppo OBJECT IDENTIFIER ::= { set 31}
setPppoOpe OBJECT-TYPE
           SYNTAX INTEGER
           {
             no(0),
             yes(1)
           }
           MAX-ACCESS read-write
           STATUS current
           DESCRIPTION "Operating"
           ::= {  setPppo 1 }

setPppoNamTable OBJECT-TYPE
                SYNTAX SEQUENCE OF SetPppoNamEntry
                MAX-ACCESS not-accessible
                STATUS current
                DESCRIPTION "Name-List"
                ::= {  setPppo 2 }

setPppoNamEntry OBJECT-TYPE
                SYNTAX SetPppoNamEntry
                MAX-ACCESS not-accessible
                STATUS current
                DESCRIPTION "entry in table"
                INDEX { setPppoNamPee }
                ::= {  setPppoNamTable 1 }

SetPppoNamEntry ::= SEQUENCE {
                setPppoNamPee DisplayString,
                setPppoNamSht INTEGER,
                setPppoNamMac DisplayString
               }

setPppoNamPee OBJECT-TYPE
              SYNTAX DisplayString (SIZE(0..16))
              MAX-ACCESS read-write
              STATUS current
              DESCRIPTION "Peer"
              ::= {  setPppoNamEntry 1 }

setPppoNamSht OBJECT-TYPE
              SYNTAX INTEGER (0..65535)
              MAX-ACCESS read-write
              STATUS current
              DESCRIPTION "SH-Time"
              ::= {  setPppoNamEntry 2 }

setPppoNamMac OBJECT-TYPE
              SYNTAX DisplayString (SIZE(0..12))
              MAX-ACCESS read-write
              STATUS current
              DESCRIPTION "MAC-Address"
              ::= {  setPppoNamEntry 3 }

setPppoSer OBJECT-TYPE
           SYNTAX DisplayString (SIZE(0..32))
           MAX-ACCESS read-write
           STATUS current
           DESCRIPTION "Service"
           ::= {  setPppo 3 }

setPppoSes OBJECT-TYPE
           SYNTAX INTEGER
           MAX-ACCESS read-write
           STATUS current
           DESCRIPTION "Session-Limit"
           ::= {  setPppo 4 }

setPppoPorTable OBJECT-TYPE
                SYNTAX SEQUENCE OF SetPppoPorEntry
                MAX-ACCESS not-accessible
                STATUS current
                DESCRIPTION "Ports"
                ::= {  setPppo 5 }

setPppoPorEntry OBJECT-TYPE
                SYNTAX SetPppoPorEntry
                MAX-ACCESS not-accessible
                STATUS current
                DESCRIPTION "entry in table"
                INDEX { setPppoPorPor }
                ::= {  setPppoPorTable 1 }

SetPppoPorEntry ::= SEQUENCE {
                setPppoPorPor DisplayString,
                setPppoPorEna INTEGER
               }

setPppoPorPor OBJECT-TYPE
              SYNTAX DisplayString (SIZE(0..10))
              MAX-ACCESS read-only
              STATUS current
              DESCRIPTION "Port"
              ::= {  setPppoPorEntry 2 }

setPppoPorEna OBJECT-TYPE
              SYNTAX INTEGER
              {
                no(0),
                yes(1)
              }
              MAX-ACCESS read-write
              STATUS current
              DESCRIPTION "Enable-PPPoE"
              ::= {  setPppoPorEntry 3 }

setVlan OBJECT IDENTIFIER ::= { set 32}
setVlanOpe OBJECT-TYPE
           SYNTAX INTEGER
           {
             no(0),
             yes(1)
           }
           MAX-ACCESS read-write
           STATUS current
           DESCRIPTION "Operating"
           ::= {  setVlan 4 }

setVlanNetTable OBJECT-TYPE
                SYNTAX SEQUENCE OF SetVlanNetEntry
                MAX-ACCESS not-accessible
                STATUS current
                DESCRIPTION "Networks"
                ::= {  setVlan 1 }

setVlanNetEntry OBJECT-TYPE
                SYNTAX SetVlanNetEntry
                MAX-ACCESS not-accessible
                STATUS current
                DESCRIPTION "entry in table"
                INDEX { setVlanNetNam }
                ::= {  setVlanNetTable 1 }

SetVlanNetEntry ::= SEQUENCE {
                setVlanNetNam DisplayString,
                setVlanNetVla INTEGER,
                setVlanNetPor DisplayString
               }

setVlanNetNam OBJECT-TYPE
              SYNTAX DisplayString (SIZE(0..16))
              MAX-ACCESS read-write
              STATUS current
              DESCRIPTION "Name"
              ::= {  setVlanNetEntry 1 }

setVlanNetVla OBJECT-TYPE
              SYNTAX INTEGER (0..65535)
              MAX-ACCESS read-write
              STATUS current
              DESCRIPTION "VLAN-ID"
              ::= {  setVlanNetEntry 2 }

setVlanNetPor OBJECT-TYPE
              SYNTAX DisplayString (SIZE(0..251))
              MAX-ACCESS read-write
              STATUS current
              DESCRIPTION "Ports"
              ::= {  setVlanNetEntry 4 }

setVlanTag OBJECT-TYPE
           SYNTAX DisplayString (SIZE(0..4))
           MAX-ACCESS read-write
           STATUS current
           DESCRIPTION "Tag-Value"
           ::= {  setVlan 5 }

setVlanPorTable OBJECT-TYPE
                SYNTAX SEQUENCE OF SetVlanPorEntry
                MAX-ACCESS not-accessible
                STATUS current
                DESCRIPTION "Port-Table"
                ::= {  setVlan 2 }

setVlanPorEntry OBJECT-TYPE
                SYNTAX SetVlanPorEntry
                MAX-ACCESS not-accessible
                STATUS current
                DESCRIPTION "entry in table"
                INDEX { setVlanPorPort }
                ::= {  setVlanPorTable 1 }

SetVlanPorEntry ::= SEQUENCE {
                setVlanPorPort DisplayString,
                setVlanPorTaggi INTEGER,
                setVlanPorAllow INTEGER,
                setVlanPorPortv INTEGER
               }

setVlanPorPort OBJECT-TYPE
                SYNTAX DisplayString (SIZE(0..9))
                MAX-ACCESS read-only
                STATUS current
                DESCRIPTION "Port"
                ::= {  setVlanPorEntry 1 }

setVlanPorTaggi OBJECT-TYPE
                SYNTAX INTEGER
                {
                  ingress-mixed(0),
                  never(1),
                  mixed(2),
                  always(3)
                }
                MAX-ACCESS read-write
                STATUS current
                DESCRIPTION "Tagging-Mode"
                ::= {  setVlanPorEntry 6 }

setVlanPorAllow OBJECT-TYPE
                SYNTAX INTEGER
                {
                  no(0),
                  yes(1)
                }
                MAX-ACCESS read-write
                STATUS current
                DESCRIPTION "Allow-All-VLANs"
                ::= {  setVlanPorEntry 4 }

setVlanPorPortv OBJECT-TYPE
                SYNTAX INTEGER (0..65535)
                MAX-ACCESS read-write
                STATUS current
                DESCRIPTION "Port-VLAN-Id"
                ::= {  setVlanPorEntry 5 }

setPrin OBJECT IDENTIFIER ::= { set 34}
setPrinPriTable OBJECT-TYPE
                SYNTAX SEQUENCE OF SetPrinPriEntry
                MAX-ACCESS not-accessible
                STATUS current
                DESCRIPTION "Printer"
                ::= {  setPrin 1 }

setPrinPriEntry OBJECT-TYPE
                SYNTAX SetPrinPriEntry
                MAX-ACCESS not-accessible
                STATUS current
                DESCRIPTION "entry in table"
                INDEX { setPrinPriPri }
                ::= {  setPrinPriTable 1 }

SetPrinPriEntry ::= SEQUENCE {
                setPrinPriPri DisplayString,
                setPrinPriRaw INTEGER,
                setPrinPriLpd INTEGER,
                setPrinPriAct INTEGER,
                setPrinPriBid INTEGER,
                setPrinPriRes INTEGER
               }

setPrinPriPri OBJECT-TYPE
              SYNTAX DisplayString (SIZE(0..15))
              MAX-ACCESS read-write
              STATUS current
              DESCRIPTION "Printer"
              ::= {  setPrinPriEntry 1 }

setPrinPriRaw OBJECT-TYPE
              SYNTAX INTEGER (0..2147483647)
              MAX-ACCESS read-write
              STATUS current
              DESCRIPTION "RawIp-Port"
              ::= {  setPrinPriEntry 2 }

setPrinPriLpd OBJECT-TYPE
              SYNTAX INTEGER (0..2147483647)
              MAX-ACCESS read-write
              STATUS current
              DESCRIPTION "LPD-Port"
              ::= {  setPrinPriEntry 3 }

setPrinPriAct OBJECT-TYPE
              SYNTAX INTEGER
              {
                no(0),
                yes(1)
              }
              MAX-ACCESS read-write
              STATUS current
              DESCRIPTION "Activ"
              ::= {  setPrinPriEntry 4 }

setPrinPriBid OBJECT-TYPE
              SYNTAX INTEGER
              {
                no(0),
                yes(1)
              }
              MAX-ACCESS read-write
              STATUS current
              DESCRIPTION "Bidirectional"
              ::= {  setPrinPriEntry 5 }

setPrinPriRes OBJECT-TYPE
              SYNTAX INTEGER
              {
                no(0),
                yes(1)
              }
              MAX-ACCESS read-write
              STATUS current
              DESCRIPTION "Reset-on-Open"
              ::= {  setPrinPriEntry 6 }

setPrinAccTable OBJECT-TYPE
                SYNTAX SEQUENCE OF SetPrinAccEntry
                MAX-ACCESS not-accessible
                STATUS current
                DESCRIPTION "Access-List"
                ::= {  setPrin 2 }

setPrinAccEntry OBJECT-TYPE
                SYNTAX SetPrinAccEntry
                MAX-ACCESS not-accessible
                STATUS current
                DESCRIPTION "entry in table"
                INDEX { setPrinAccIpa, setPrinAccIpn, setPrinAccRtg }
                ::= {  setPrinAccTable 1 }

SetPrinAccEntry ::= SEQUENCE {
                setPrinAccIpa IpAddress,
                setPrinAccIpn IpAddress,
                setPrinAccRtg INTEGER
               }

setPrinAccIpa OBJECT-TYPE
              SYNTAX IpAddress
              MAX-ACCESS read-write
              STATUS current
              DESCRIPTION "IP-Address"
              ::= {  setPrinAccEntry 1 }

setPrinAccIpn OBJECT-TYPE
              SYNTAX IpAddress
              MAX-ACCESS read-write
              STATUS current
              DESCRIPTION "IP-Netmask"
              ::= {  setPrinAccEntry 2 }

setPrinAccRtg OBJECT-TYPE
              SYNTAX INTEGER (0..65535)
              MAX-ACCESS read-write
              STATUS current
              DESCRIPTION "Rtg-tag"
              ::= {  setPrinAccEntry 3 }

setCert OBJECT IDENTIFIER ::= { set 39}
setCertSce OBJECT IDENTIFIER ::= { setCert 1}
setCertSceSce OBJECT-TYPE
              SYNTAX INTEGER
              {
                no(0),
                yes(1)
              }
              MAX-ACCESS read-write
              STATUS current
              DESCRIPTION "SCEP-Operating"
              ::= {  setCertSce 1 }

setCertSceRet OBJECT-TYPE
              SYNTAX INTEGER
              MAX-ACCESS read-write
              STATUS current
              DESCRIPTION "Retry-After-Error-Interval"
              ::= {  setCertSce 11 }

setCertSceChe OBJECT-TYPE
              SYNTAX INTEGER
              MAX-ACCESS read-write
              STATUS current
              DESCRIPTION "Check-Pending-Requests-Interval"
              ::= {  setCertSce 12 }

setCertSceDev OBJECT-TYPE
              SYNTAX INTEGER
              MAX-ACCESS read-write
              STATUS current
              DESCRIPTION "Device-Certificate-Update-Before"
              ::= {  setCertSce 2 }

setCertSceCac OBJECT-TYPE
              SYNTAX INTEGER
              MAX-ACCESS read-write
              STATUS current
              DESCRIPTION "CA-Certificate-Update-Before"
              ::= {  setCertSce 3 }

setCertSceCasTable OBJECT-TYPE
                   SYNTAX SEQUENCE OF SetCertSceCasEntry
                   MAX-ACCESS not-accessible
                   STATUS current
                   DESCRIPTION "CAs"
                   ::= {  setCertSce 6 }

setCertSceCasEntry OBJECT-TYPE
                   SYNTAX SetCertSceCasEntry
                   MAX-ACCESS not-accessible
                   STATUS current
                   DESCRIPTION "entry in table"
                   INDEX { setCertSceCasName }
                   ::= {  setCertSceCasTable 1 }

SetCertSceCasEntry ::= SEQUENCE {
                   setCertSceCasName DisplayString,
                   setCertSceCasUrl DisplayString,
                   setCertSceCasDn DisplayString,
                   setCertSceCasEncalg INTEGER,
                   setCertSceCasIdentifier DisplayString,
                   setCertSceCasRaautoapprove INTEGER,
                   setCertSceCasCasignaturealg INTEGER,
                   setCertSceCasCafingerprinta INTEGER,
                   setCertSceCasCafingerprint DisplayString,
                   setCertSceCasApplication INTEGER,
                   setCertSceCasLoopbackaddr DisplayString
                  }

setCertSceCasName OBJECT-TYPE
                            SYNTAX DisplayString (SIZE(0..16))
                            MAX-ACCESS read-write
                            STATUS current
                            DESCRIPTION "Name"
                            ::= {  setCertSceCasEntry 1 }

setCertSceCasUrl OBJECT-TYPE
                            SYNTAX DisplayString (SIZE(0..251))
                            MAX-ACCESS read-write
                            STATUS current
                            DESCRIPTION "URL"
                            ::= {  setCertSceCasEntry 2 }

setCertSceCasDn OBJECT-TYPE
                            SYNTAX DisplayString (SIZE(0..251))
                            MAX-ACCESS read-write
                            STATUS current
                            DESCRIPTION "DN"
                            ::= {  setCertSceCasEntry 3 }

setCertSceCasEncalg OBJECT-TYPE
                            SYNTAX INTEGER
                            {
                              des(0),
                              e3des(1),
                              blowfish(2),
                              aes128(3)
                            }
                            MAX-ACCESS read-write
                            STATUS current
                            DESCRIPTION "Enc-Alg"
                            ::= {  setCertSceCasEntry 4 }

setCertSceCasIdentifier OBJECT-TYPE
                            SYNTAX DisplayString (SIZE(0..251))
                            MAX-ACCESS read-write
                            STATUS current
                            DESCRIPTION "Identifier"
                            ::= {  setCertSceCasEntry 5 }

setCertSceCasRaautoapprove OBJECT-TYPE
                            SYNTAX INTEGER
                            {
                              no(0),
                              yes(1)
                            }
                            MAX-ACCESS read-write
                            STATUS current
                            DESCRIPTION "RA-Autoapprove"
                            ::= {  setCertSceCasEntry 7 }

setCertSceCasCasignaturealg OBJECT-TYPE
                            SYNTAX INTEGER
                            {
                              md5(0),
                              sha1(1)
                            }
                            MAX-ACCESS read-write
                            STATUS current
                            DESCRIPTION "CA-Signature-Algorithm"
                            ::= {  setCertSceCasEntry 6 }

setCertSceCasCafingerprinta OBJECT-TYPE
                            SYNTAX INTEGER
                            {
                              off(0),
                              sha1(1),
                              md5(2)
                            }
                            MAX-ACCESS read-write
                            STATUS current
                            DESCRIPTION "CA-Fingerprint-Algorithm"
                            ::= {  setCertSceCasEntry 8 }

setCertSceCasCafingerprint OBJECT-TYPE
                            SYNTAX DisplayString (SIZE(0..59))
                            MAX-ACCESS read-write
                            STATUS current
                            DESCRIPTION "CA-Fingerprint"
                            ::= {  setCertSceCasEntry 9 }

setCertSceCasApplication OBJECT-TYPE
                            SYNTAX INTEGER
                            {
                              general(2),
                              vpn(0)
                            }
                            MAX-ACCESS read-write
                            STATUS current
                            DESCRIPTION "Application"
                            ::= {  setCertSceCasEntry 10 }

setCertSceCasLoopbackaddr OBJECT-TYPE
                            SYNTAX DisplayString (SIZE(0..16))
                            MAX-ACCESS read-write
                            STATUS current
                            DESCRIPTION "Loopback-Addr."
                            ::= {  setCertSceCasEntry 11 }

setCertSceCerTable OBJECT-TYPE
                   SYNTAX SEQUENCE OF SetCertSceCerEntry
                   MAX-ACCESS not-accessible
                   STATUS current
                   DESCRIPTION "Certificates"
                   ::= {  setCertSce 7 }

setCertSceCerEntry OBJECT-TYPE
                   SYNTAX SetCertSceCerEntry
                   MAX-ACCESS not-accessible
                   STATUS current
                   DESCRIPTION "entry in table"
                   INDEX { setCertSceCerName }
                   ::= {  setCertSceCerTable 1 }

SetCertSceCerEntry ::= SEQUENCE {
                   setCertSceCerName DisplayString,
                   setCertSceCerCadn DisplayString,
                   setCertSceCerSubject DisplayString,
                   setCertSceCerChalleng DisplayString,
                   setCertSceCerSubjecta DisplayString,
                   setCertSceCerKeyusage DisplayString,
                   setCertSceCerExtended DisplayString,
                   setCertSceCerDevicece INTEGER,
                   setCertSceCerApplicat INTEGER
                  }

setCertSceCerName OBJECT-TYPE
                      SYNTAX DisplayString (SIZE(0..16))
                      MAX-ACCESS read-write
                      STATUS current
                      DESCRIPTION "Name"
                      ::= {  setCertSceCerEntry 1 }

setCertSceCerCadn OBJECT-TYPE
                      SYNTAX DisplayString (SIZE(0..251))
                      MAX-ACCESS read-write
                      STATUS current
                      DESCRIPTION "CADN"
                      ::= {  setCertSceCerEntry 2 }

setCertSceCerSubject OBJECT-TYPE
                      SYNTAX DisplayString (SIZE(0..251))
                      MAX-ACCESS read-write
                      STATUS current
                      DESCRIPTION "Subject"
                      ::= {  setCertSceCerEntry 3 }

setCertSceCerChalleng OBJECT-TYPE
                      SYNTAX DisplayString (SIZE(0..251))
                      MAX-ACCESS read-write
                      STATUS current
                      DESCRIPTION "ChallengePwd"
                      ::= {  setCertSceCerEntry 4 }

setCertSceCerSubjecta OBJECT-TYPE
                      SYNTAX DisplayString (SIZE(0..251))
                      MAX-ACCESS read-write
                      STATUS current
                      DESCRIPTION "SubjectAltName"
                      ::= {  setCertSceCerEntry 5 }

setCertSceCerKeyusage OBJECT-TYPE
                      SYNTAX DisplayString (SIZE(0..251))
                      MAX-ACCESS read-write
                      STATUS current
                      DESCRIPTION "KeyUsage"
                      ::= {  setCertSceCerEntry 6 }

setCertSceCerExtended OBJECT-TYPE
                      SYNTAX DisplayString (SIZE(0..251))
                      MAX-ACCESS read-write
                      STATUS current
                      DESCRIPTION "Extended-KeyUsage"
                      ::= {  setCertSceCerEntry 9 }

setCertSceCerDevicece OBJECT-TYPE
                      SYNTAX INTEGER (0..2147483647)
                      MAX-ACCESS read-write
                      STATUS current
                      DESCRIPTION "Device-Certificate-Keylength"
                      ::= {  setCertSceCerEntry 7 }

setCertSceCerApplicat OBJECT-TYPE
                      SYNTAX INTEGER
                      {
                        vpn(0)
                      }
                      MAX-ACCESS read-write
                      STATUS current
                      DESCRIPTION "Application"
                      ::= {  setCertSceCerEntry 8 }

setCertSceRei OBJECT-TYPE
              SYNTAX DisplayString
              MAX-ACCESS read-write
              STATUS current
              DESCRIPTION "Reinit"
              ::= {  setCertSce 8 }

setCertSceUpd OBJECT-TYPE
              SYNTAX DisplayString
              MAX-ACCESS read-write
              STATUS current
              DESCRIPTION "Update"
              ::= {  setCertSce 9 }

setCertSceCle OBJECT-TYPE
              SYNTAX DisplayString
              MAX-ACCESS read-write
              STATUS current
              DESCRIPTION "Clear-SCEP-Filesystem"
              ::= {  setCertSce 10 }

setCertCrl OBJECT IDENTIFIER ::= { setCert 3}
setCertCrlCrl OBJECT-TYPE
              SYNTAX INTEGER
              {
                no(0),
                yes(1)
              }
              MAX-ACCESS read-write
              STATUS current
              DESCRIPTION "CRL-Operating"
              ::= {  setCertCrl 1 }

setCertCrlAlt OBJECT-TYPE
              SYNTAX DisplayString (SIZE(0..255))
              MAX-ACCESS read-write
              STATUS current
              DESCRIPTION "Alternative-URL"
              ::= {  setCertCrl 2 }

setCertCrlUse OBJECT-TYPE
              SYNTAX INTEGER
              {
                no(0),
                yes(1),
                fallback(2)
              }
              MAX-ACCESS read-write
              STATUS current
              DESCRIPTION "Use-Alternative-URL"
              ::= {  setCertCrl 3 }

setCertCrlUpd OBJECT-TYPE
              SYNTAX INTEGER
              MAX-ACCESS read-write
              STATUS current
              DESCRIPTION "Update-Before"
              ::= {  setCertCrl 4 }

setCertCrlPre OBJECT-TYPE
              SYNTAX INTEGER
              MAX-ACCESS read-write
              STATUS current
              DESCRIPTION "Prefetch-Period"
              ::= {  setCertCrl 5 }

setCertCrlVal OBJECT-TYPE
              SYNTAX INTEGER
              MAX-ACCESS read-write
              STATUS current
              DESCRIPTION "Validity-Exceedance"
              ::= {  setCertCrl 6 }

setCertCrlRef OBJECT-TYPE
              SYNTAX DisplayString
              MAX-ACCESS read-write
              STATUS current
              DESCRIPTION "Refresh-CRL-Now"
              ::= {  setCertCrl 7 }

setComp OBJECT IDENTIFIER ::= { set 52}
setCompDevTable OBJECT-TYPE
                SYNTAX SEQUENCE OF SetCompDevEntry
                MAX-ACCESS not-accessible
                STATUS current
                DESCRIPTION "Devices"
                ::= {  setComp 1 }

setCompDevEntry OBJECT-TYPE
                SYNTAX SetCompDevEntry
                MAX-ACCESS not-accessible
                STATUS current
                DESCRIPTION "entry in table"
                INDEX { setCompDevDev }
                ::= {  setCompDevTable 1 }

SetCompDevEntry ::= SEQUENCE {
                setCompDevDev INTEGER,
                setCompDevSer INTEGER
               }

setCompDevDev OBJECT-TYPE
              SYNTAX INTEGER
              {
                outband(1),
                option-icon(17),
                novatel-merlin-mc950d(26),
                sierra-compass-885(39),
                sierra-aircard-875u(30),
                huawei-e172-e220-e870(31),
                e4g-systems-uxs1(23),
                belkin-f5u103(33),
                prolific-2303(34),
                ftdi-8u232am(35)
              }
              MAX-ACCESS read-write
              STATUS current
              DESCRIPTION "Device-Type"
              ::= {  setCompDevEntry 1 }

setCompDevSer OBJECT-TYPE
              SYNTAX INTEGER
              {
                wan(1),
                com-port-server(2)
              }
              MAX-ACCESS read-write
              STATUS current
              DESCRIPTION "Service"
              ::= {  setCompDevEntry 4 }

setCompWan OBJECT IDENTIFIER ::= { setComp 3}
setCompWanDevTable OBJECT-TYPE
                   SYNTAX SEQUENCE OF SetCompWanDevEntry
                   MAX-ACCESS not-accessible
                   STATUS current
                   DESCRIPTION "Devices"
                   ::= {  setCompWan 1 }

setCompWanDevEntry OBJECT-TYPE
                   SYNTAX SetCompWanDevEntry
                   MAX-ACCESS not-accessible
                   STATUS current
                   DESCRIPTION "entry in table"
                   INDEX { setCompWanDevDev }
                   ::= {  setCompWanDevTable 1 }

SetCompWanDevEntry ::= SEQUENCE {
                   setCompWanDevDev INTEGER,
                   setCompWanDevOpe INTEGER
                  }

setCompWanDevDev OBJECT-TYPE
                 SYNTAX INTEGER
                 {
                   outband-modem(2),
                   option-icon(17),
                   novatel-merlin-mc950d(26),
                   sierra-compass-885(39),
                   sierra-aircard-875u(30),
                   huawei-e172-e220-e870(31),
                   e4g-systems-uxs1(23),
                   belkin-f5u103(33),
                   prolific-2303(34),
                   ftdi-8u232am(35)
                 }
                 MAX-ACCESS read-write
                 STATUS current
                 DESCRIPTION "Device-Type"
                 ::= {  setCompWanDevEntry 1 }

setCompWanDevOpe OBJECT-TYPE
                 SYNTAX INTEGER
                 {
                   no(0),
                   yes(1)
                 }
                 MAX-ACCESS read-write
                 STATUS current
                 DESCRIPTION "Operating"
                 ::= {  setCompWanDevEntry 3 }

setCompCom OBJECT IDENTIFIER ::= { setComp 2}
setCompComOpeTable OBJECT-TYPE
                   SYNTAX SEQUENCE OF SetCompComOpeEntry
                   MAX-ACCESS not-accessible
                   STATUS current
                   DESCRIPTION "Operational"
                   ::= {  setCompCom 1 }

setCompComOpeEntry OBJECT-TYPE
                   SYNTAX SetCompComOpeEntry
                   MAX-ACCESS not-accessible
                   STATUS current
                   DESCRIPTION "entry in table"
                   INDEX { setCompComOpeDev, setCompComOpePor }
                   ::= {  setCompComOpeTable 1 }

SetCompComOpeEntry ::= SEQUENCE {
                   setCompComOpeDev INTEGER,
                   setCompComOpePor INTEGER,
                   setCompComOpeOpe INTEGER
                  }

setCompComOpeDev OBJECT-TYPE
                 SYNTAX INTEGER
                 {
                   outband(1),
                   belkin-f5u103(33),
                   prolific-2303(34),
                   ftdi-8u232am(35)
                 }
                 MAX-ACCESS read-write
                 STATUS current
                 DESCRIPTION "Device-Type"
                 ::= {  setCompComOpeEntry 1 }

setCompComOpePor OBJECT-TYPE
                 SYNTAX INTEGER (0..255)
                 MAX-ACCESS read-write
                 STATUS current
                 DESCRIPTION "Port-Number"
                 ::= {  setCompComOpeEntry 2 }

setCompComOpeOpe OBJECT-TYPE
                 SYNTAX INTEGER
                 {
                   no(0),
                   yes(1)
                 }
                 MAX-ACCESS read-write
                 STATUS current
                 DESCRIPTION "Operating"
                 ::= {  setCompComOpeEntry 4 }

setCompComComTable OBJECT-TYPE
                   SYNTAX SEQUENCE OF SetCompComComEntry
                   MAX-ACCESS not-accessible
                   STATUS current
                   DESCRIPTION "COM-Port-Settings"
                   ::= {  setCompCom 2 }

setCompComComEntry OBJECT-TYPE
                   SYNTAX SetCompComComEntry
                   MAX-ACCESS not-accessible
                   STATUS current
                   DESCRIPTION "entry in table"
                   INDEX { setCompComComDevice, setCompComComPortnu }
                   ::= {  setCompComComTable 1 }

SetCompComComEntry ::= SEQUENCE {
                   setCompComComDevice INTEGER,
                   setCompComComPortnu INTEGER,
                   setCompComComBitrat INTEGER,
                   setCompComComDatabi INTEGER,
                   setCompComComParity INTEGER,
                   setCompComComStopbi INTEGER,
                   setCompComComHandsh INTEGER,
                   setCompComComReadyc INTEGER,
                   setCompComComReadyd INTEGER
                  }

setCompComComDevice OBJECT-TYPE
                    SYNTAX INTEGER
                    {
                      outband(1),
                      belkin-f5u103(33),
                      prolific-2303(34),
                      ftdi-8u232am(35)
                    }
                    MAX-ACCESS read-write
                    STATUS current
                    DESCRIPTION "Device-Type"
                    ::= {  setCompComComEntry 1 }

setCompComComPortnu OBJECT-TYPE
                    SYNTAX INTEGER (0..255)
                    MAX-ACCESS read-write
                    STATUS current
                    DESCRIPTION "Port-Number"
                    ::= {  setCompComComEntry 2 }

setCompComComBitrat OBJECT-TYPE
                    SYNTAX INTEGER
                    {
                      e110(110),
                      e300(300),
                      e600(600),
                      e1200(1200),
                      e2400(2400),
                      e4800(4800),
                      e9600(9600),
                      e19200(19200),
                      e38400(38400),
                      e57600(57600),
                      e115200(115200),
                      e125000(125000),
                      e230400(230400)
                    }
                    MAX-ACCESS read-write
                    STATUS current
                    DESCRIPTION "Bit-Rate"
                    ::= {  setCompComComEntry 4 }

setCompComComDatabi OBJECT-TYPE
                    SYNTAX INTEGER
                    {
                      e7(7),
                      e8(8)
                    }
                    MAX-ACCESS read-write
                    STATUS current
                    DESCRIPTION "Data-Bits"
                    ::= {  setCompComComEntry 5 }

setCompComComParity OBJECT-TYPE
                    SYNTAX INTEGER
                    {
                      none(1),
                      odd(2),
                      even(3)
                    }
                    MAX-ACCESS read-write
                    STATUS current
                    DESCRIPTION "Parity"
                    ::= {  setCompComComEntry 6 }

setCompComComStopbi OBJECT-TYPE
                    SYNTAX INTEGER
                    {
                      e1(1),
                      e2(2)
                    }
                    MAX-ACCESS read-write
                    STATUS current
                    DESCRIPTION "Stop-Bits"
                    ::= {  setCompComComEntry 7 }

setCompComComHandsh OBJECT-TYPE
                    SYNTAX INTEGER
                    {
                      none(0),
                      rts-cts(1)
                    }
                    MAX-ACCESS read-write
                    STATUS current
                    DESCRIPTION "Handshake"
                    ::= {  setCompComComEntry 8 }

setCompComComReadyc OBJECT-TYPE
                    SYNTAX INTEGER
                    {
                      dtr(0),
                      data(1)
                    }
                    MAX-ACCESS read-write
                    STATUS current
                    DESCRIPTION "Ready-Condition"
                    ::= {  setCompComComEntry 9 }

setCompComComReadyd OBJECT-TYPE
                    SYNTAX INTEGER (0..2147483647)
                    MAX-ACCESS read-write
                    STATUS current
                    DESCRIPTION "Ready-Data-Timeout"
                    ::= {  setCompComComEntry 10 }

setCompComNetTable OBJECT-TYPE
                   SYNTAX SEQUENCE OF SetCompComNetEntry
                   MAX-ACCESS not-accessible
                   STATUS current
                   DESCRIPTION "Network-Settings"
                   ::= {  setCompCom 3 }

setCompComNetEntry OBJECT-TYPE
                   SYNTAX SetCompComNetEntry
                   MAX-ACCESS not-accessible
                   STATUS current
                   DESCRIPTION "entry in table"
                   INDEX { setCompComNetDevicety, setCompComNetPortnumb }
                   ::= {  setCompComNetTable 1 }

SetCompComNetEntry ::= SEQUENCE {
                   setCompComNetDevicety INTEGER,
                   setCompComNetPortnumb INTEGER,
                   setCompComNetTcpmode INTEGER,
                   setCompComNetListenpo INTEGER,
                   setCompComNetConnecth DisplayString,
                   setCompComNetConnectp INTEGER,
                   setCompComNetLoopback DisplayString,
                   setCompComNetRfc2217e INTEGER,
                   setCompComNetNewlinec INTEGER
                  }

setCompComNetDevicety OBJECT-TYPE
                      SYNTAX INTEGER
                      {
                        outband(1),
                        belkin-f5u103(33),
                        prolific-2303(34),
                        ftdi-8u232am(35)
                      }
                      MAX-ACCESS read-write
                      STATUS current
                      DESCRIPTION "Device-Type"
                      ::= {  setCompComNetEntry 1 }

setCompComNetPortnumb OBJECT-TYPE
                      SYNTAX INTEGER (0..255)
                      MAX-ACCESS read-write
                      STATUS current
                      DESCRIPTION "Port-Number"
                      ::= {  setCompComNetEntry 2 }

setCompComNetTcpmode OBJECT-TYPE
                      SYNTAX INTEGER
                      {
                        server(0),
                        client(1)
                      }
                      MAX-ACCESS read-write
                      STATUS current
                      DESCRIPTION "TCP-Mode"
                      ::= {  setCompComNetEntry 4 }

setCompComNetListenpo OBJECT-TYPE
                      SYNTAX INTEGER (0..65535)
                      MAX-ACCESS read-write
                      STATUS current
                      DESCRIPTION "Listen-Port"
                      ::= {  setCompComNetEntry 5 }

setCompComNetConnecth OBJECT-TYPE
                      SYNTAX DisplayString (SIZE(0..48))
                      MAX-ACCESS read-write
                      STATUS current
                      DESCRIPTION "Connect-Hostname"
                      ::= {  setCompComNetEntry 6 }

setCompComNetConnectp OBJECT-TYPE
                      SYNTAX INTEGER (0..65535)
                      MAX-ACCESS read-write
                      STATUS current
                      DESCRIPTION "Connect-Port"
                      ::= {  setCompComNetEntry 7 }

setCompComNetLoopback OBJECT-TYPE
                      SYNTAX DisplayString (SIZE(0..16))
                      MAX-ACCESS read-write
                      STATUS current
                      DESCRIPTION "Loopback-Addr."
                      ::= {  setCompComNetEntry 8 }

setCompComNetRfc2217e OBJECT-TYPE
                      SYNTAX INTEGER
                      {
                        no(0),
                        yes(1)
                      }
                      MAX-ACCESS read-write
                      STATUS current
                      DESCRIPTION "RFC2217-Extensions"
                      ::= {  setCompComNetEntry 9 }

setCompComNetNewlinec OBJECT-TYPE
                      SYNTAX INTEGER
                      {
                        crlf(0),
                        cr(1),
                        lf(2)
                      }
                      MAX-ACCESS read-write
                      STATUS current
                      DESCRIPTION "Newline-Conversion"
                      ::= {  setCompComNetEntry 10 }

setTaca OBJECT IDENTIFIER ::= { set 54}
setTacaAuthentication OBJECT-TYPE
                         SYNTAX INTEGER
                         {
                           deactivated(0),
                           activated(1)
                         }
                         MAX-ACCESS read-write
                         STATUS current
                         DESCRIPTION "Authentication"
                         ::= {  setTaca 1 }

setTacaAuthorisation OBJECT-TYPE
                         SYNTAX INTEGER
                         {
                           deactivated(0),
                           activated(1)
                         }
                         MAX-ACCESS read-write
                         STATUS current
                         DESCRIPTION "Authorisation"
                         ::= {  setTaca 2 }

setTacaAccounting OBJECT-TYPE
                         SYNTAX INTEGER
                         {
                           deactivated(0),
                           activated(1)
                         }
                         MAX-ACCESS read-write
                         STATUS current
                         DESCRIPTION "Accounting"
                         ::= {  setTaca 3 }

setTacaServerTable OBJECT-TYPE
                              SYNTAX SEQUENCE OF SetTacaServerEntry
                              MAX-ACCESS not-accessible
                              STATUS current
                              DESCRIPTION "Server"
                              ::= {  setTaca 9 }

setTacaServerEntry OBJECT-TYPE
                              SYNTAX SetTacaServerEntry
                              MAX-ACCESS not-accessible
                              STATUS current
                              DESCRIPTION "entry in table"
                              INDEX { setTacaServerSer }
                              ::= {  setTacaServerTable 1 }

SetTacaServerEntry ::= SEQUENCE {
                              setTacaServerSer DisplayString,
                              setTacaServerLoo DisplayString,
                              setTacaServerCom INTEGER
                             }

setTacaServerSer OBJECT-TYPE
                 SYNTAX DisplayString (SIZE(0..31))
                 MAX-ACCESS read-write
                 STATUS current
                 DESCRIPTION "Server-Address"
                 ::= {  setTacaServerEntry 1 }

setTacaServerLoo OBJECT-TYPE
                 SYNTAX DisplayString (SIZE(0..16))
                 MAX-ACCESS read-write
                 STATUS current
                 DESCRIPTION "Loopback-Address"
                 ::= {  setTacaServerEntry 2 }

setTacaServerCom OBJECT-TYPE
                 SYNTAX INTEGER
                 {
                   deactivated(0),
                   activated(1)
                 }
                 MAX-ACCESS read-write
                 STATUS current
                 DESCRIPTION "Compatibility Mode"
                 ::= {  setTacaServerEntry 3 }

setTacaSharedsecret OBJECT-TYPE
                         SYNTAX DisplayString (SIZE(0..31))
                         MAX-ACCESS read-write
                         STATUS current
                         DESCRIPTION "Shared-Secret"
                         ::= {  setTaca 6 }

setTacaEncryption OBJECT-TYPE
                         SYNTAX INTEGER
                         {
                           deactivated(0),
                           activated(1)
                         }
                         MAX-ACCESS read-write
                         STATUS current
                         DESCRIPTION "Encryption"
                         ::= {  setTaca 7 }

setTacaFallbacktolocalus OBJECT-TYPE
                         SYNTAX INTEGER
                         {
                           allowed(0),
                           prohibited(1)
                         }
                         MAX-ACCESS read-write
                         STATUS current
                         DESCRIPTION "Fallback-to-local-users"
                         ::= {  setTaca 10 }

setTacaSnmpgetrequestsau OBJECT-TYPE
                         SYNTAX INTEGER
                         {
                           only-for-setup-tree(0),
                           all(1),
                           none(2)
                         }
                         MAX-ACCESS read-write
                         STATUS current
                         DESCRIPTION "SNMP-GET-Requests-Authorisation"
                         ::= {  setTaca 11 }

setTacaSnmpgetrequestsac OBJECT-TYPE
                         SYNTAX INTEGER
                         {
                           only-for-setup-tree(0),
                           all(1),
                           none(2)
                         }
                         MAX-ACCESS read-write
                         STATUS current
                         DESCRIPTION "SNMP-GET-Requests-Accounting"
                         ::= {  setTaca 12 }

setPerf OBJECT IDENTIFIER ::= { set 36}
setPerfRttmonaTable OBJECT-TYPE
                    SYNTAX SEQUENCE OF SetPerfRttmonaEntry
                    MAX-ACCESS not-accessible
                    STATUS current
                    DESCRIPTION "RttMonAdmin"
                    ::= {  setPerf 2 }

setPerfRttmonaEntry OBJECT-TYPE
                    SYNTAX SetPerfRttmonaEntry
                    MAX-ACCESS not-accessible
                    STATUS current
                    DESCRIPTION "entry in table"
                    INDEX { setPerfRttmonaInd }
                    ::= {  setPerfRttmonaTable 1 }

SetPerfRttmonaEntry ::= SEQUENCE {
                    setPerfRttmonaInd INTEGER,
                    setPerfRttmonaTyp INTEGER,
                    setPerfRttmonaFre INTEGER,
                    setPerfRttmonaTim INTEGER,
                    setPerfRttmonaSta INTEGER
                   }

setPerfRttmonaInd OBJECT-TYPE
                  SYNTAX INTEGER (0..2147483647)
                  MAX-ACCESS read-write
                  STATUS current
                  DESCRIPTION "Index"
                  ::= {  setPerfRttmonaEntry 1 }

setPerfRttmonaTyp OBJECT-TYPE
                  SYNTAX INTEGER
                  {
                    jitter(9)
                  }
                  MAX-ACCESS read-write
                  STATUS current
                  DESCRIPTION "Type"
                  ::= {  setPerfRttmonaEntry 4 }

setPerfRttmonaFre OBJECT-TYPE
                  SYNTAX INTEGER (0..2147483647)
                  MAX-ACCESS read-write
                  STATUS current
                  DESCRIPTION "Frequency"
                  ::= {  setPerfRttmonaEntry 6 }

setPerfRttmonaTim OBJECT-TYPE
                  SYNTAX INTEGER (0..2147483647)
                  MAX-ACCESS read-write
                  STATUS current
                  DESCRIPTION "Timeout"
                  ::= {  setPerfRttmonaEntry 7 }

setPerfRttmonaSta OBJECT-TYPE
                  SYNTAX INTEGER
                  {
                    active(1),
                    not-in-service(2),
                    not-ready(3),
                    create(5),
                    destroy(6)
                  }
                  MAX-ACCESS read-write
                  STATUS current
                  DESCRIPTION "Status"
                  ::= {  setPerfRttmonaEntry 9 }

setPerfRttmoneTable OBJECT-TYPE
                    SYNTAX SEQUENCE OF SetPerfRttmoneEntry
                    MAX-ACCESS not-accessible
                    STATUS current
                    DESCRIPTION "RttMonEchoAdmin"
                    ::= {  setPerf 3 }

setPerfRttmoneEntry OBJECT-TYPE
                    SYNTAX SetPerfRttmoneEntry
                    MAX-ACCESS not-accessible
                    STATUS current
                    DESCRIPTION "entry in table"
                    INDEX { setPerfRttmoneIndex }
                    ::= {  setPerfRttmoneTable 1 }

SetPerfRttmoneEntry ::= SEQUENCE {
                    setPerfRttmoneIndex INTEGER,
                    setPerfRttmoneProtocol INTEGER,
                    setPerfRttmoneDestinationa IpAddress,
                    setPerfRttmonePacketsize INTEGER,
                    setPerfRttmoneDestinationp INTEGER,
                    setPerfRttmoneInterval INTEGER,
                    setPerfRttmonePacketcount INTEGER
                   }

setPerfRttmoneIndex OBJECT-TYPE
                           SYNTAX INTEGER (0..2147483647)
                           MAX-ACCESS read-only
                           STATUS current
                           DESCRIPTION "Index"
                           ::= {  setPerfRttmoneEntry 255 }

setPerfRttmoneProtocol OBJECT-TYPE
                           SYNTAX INTEGER
                           {
                             echo(3)
                           }
                           MAX-ACCESS read-write
                           STATUS current
                           DESCRIPTION "Protocol"
                           ::= {  setPerfRttmoneEntry 1 }

setPerfRttmoneDestinationa OBJECT-TYPE
                           SYNTAX IpAddress
                           MAX-ACCESS read-write
                           STATUS current
                           DESCRIPTION "Destination-Address"
                           ::= {  setPerfRttmoneEntry 2 }

setPerfRttmonePacketsize OBJECT-TYPE
                           SYNTAX INTEGER (0..65535)
                           MAX-ACCESS read-write
                           STATUS current
                           DESCRIPTION "Packet-Size"
                           ::= {  setPerfRttmoneEntry 3 }

setPerfRttmoneDestinationp OBJECT-TYPE
                           SYNTAX INTEGER (0..65535)
                           MAX-ACCESS read-write
                           STATUS current
                           DESCRIPTION "Destination-Port"
                           ::= {  setPerfRttmoneEntry 5 }

setPerfRttmoneInterval OBJECT-TYPE
                           SYNTAX INTEGER (0..2147483647)
                           MAX-ACCESS read-write
                           STATUS current
                           DESCRIPTION "Interval"
                           ::= {  setPerfRttmoneEntry 17 }

setPerfRttmonePacketcount OBJECT-TYPE
                           SYNTAX INTEGER (0..2147483647)
                           MAX-ACCESS read-write
                           STATUS current
                           DESCRIPTION "Packet-Count"
                           ::= {  setPerfRttmoneEntry 18 }

setPerfRttmonsTable OBJECT-TYPE
                    SYNTAX SEQUENCE OF SetPerfRttmonsEntry
                    MAX-ACCESS not-accessible
                    STATUS current
                    DESCRIPTION "RttMonStatistics"
                    ::= {  setPerf 4 }

setPerfRttmonsEntry OBJECT-TYPE
                    SYNTAX SetPerfRttmonsEntry
                    MAX-ACCESS not-accessible
                    STATUS current
                    DESCRIPTION "entry in table"
                    INDEX { setPerfRttmonsIndex }
                    ::= {  setPerfRttmonsTable 1 }

SetPerfRttmonsEntry ::= SEQUENCE {
                    setPerfRttmonsIndex INTEGER,
                    setPerfRttmonsCompletions INTEGER,
                    setPerfRttmonsRttcount INTEGER,
                    setPerfRttmonsRttsum INTEGER,
                    setPerfRttmonsRttmin INTEGER,
                    setPerfRttmonsRttmax INTEGER,
                    setPerfRttmonsJitterminpossd INTEGER,
                    setPerfRttmonsJittermaxpossd INTEGER,
                    setPerfRttmonsJittercountposs INTEGER,
                    setPerfRttmonsJittersumpossd INTEGER,
                    setPerfRttmonsJitterminposds INTEGER,
                    setPerfRttmonsJittermaxposds INTEGER,
                    setPerfRttmonsJittercountposd INTEGER,
                    setPerfRttmonsJittersumposds INTEGER,
                    setPerfRttmonsJitterminnegsd INTEGER,
                    setPerfRttmonsJittermaxnegsd INTEGER,
                    setPerfRttmonsJittercountnegs INTEGER,
                    setPerfRttmonsJittersumnegsd INTEGER,
                    setPerfRttmonsJitterminnegds INTEGER,
                    setPerfRttmonsJittermaxnegds INTEGER,
                    setPerfRttmonsJittercountnegd INTEGER,
                    setPerfRttmonsJittersumnegds INTEGER,
                    setPerfRttmonsPacketlosssd INTEGER,
                    setPerfRttmonsPacketlossds INTEGER,
                    setPerfRttmonsAveragejitter INTEGER,
                    setPerfRttmonsAveragejittersd INTEGER,
                    setPerfRttmonsAveragejitterds INTEGER
                   }

setPerfRttmonsIndex OBJECT-TYPE
                              SYNTAX INTEGER (0..2147483647)
                              MAX-ACCESS read-only
                              STATUS current
                              DESCRIPTION "Index"
                              ::= {  setPerfRttmonsEntry 255 }

setPerfRttmonsCompletions OBJECT-TYPE
                              SYNTAX INTEGER (0..2147483647)
                              MAX-ACCESS read-only
                              STATUS current
                              DESCRIPTION "Completions"
                              ::= {  setPerfRttmonsEntry 2 }

setPerfRttmonsRttcount OBJECT-TYPE
                              SYNTAX INTEGER (0..2147483647)
                              MAX-ACCESS read-only
                              STATUS current
                              DESCRIPTION "RTT-Count"
                              ::= {  setPerfRttmonsEntry 4 }

setPerfRttmonsRttsum OBJECT-TYPE
                              SYNTAX INTEGER (0..2147483647)
                              MAX-ACCESS read-only
                              STATUS current
                              DESCRIPTION "RTT-Sum"
                              ::= {  setPerfRttmonsEntry 5 }

setPerfRttmonsRttmin OBJECT-TYPE
                              SYNTAX INTEGER (0..2147483647)
                              MAX-ACCESS read-only
                              STATUS current
                              DESCRIPTION "RTT-Min"
                              ::= {  setPerfRttmonsEntry 8 }

setPerfRttmonsRttmax OBJECT-TYPE
                              SYNTAX INTEGER (0..2147483647)
                              MAX-ACCESS read-only
                              STATUS current
                              DESCRIPTION "RTT-Max"
                              ::= {  setPerfRttmonsEntry 9 }

setPerfRttmonsJitterminpossd OBJECT-TYPE
                              SYNTAX INTEGER (0..2147483647)
                              MAX-ACCESS read-only
                              STATUS current
                              DESCRIPTION "Jitter-Min-Pos-SD"
                              ::= {  setPerfRttmonsEntry 10 }

setPerfRttmonsJittermaxpossd OBJECT-TYPE
                              SYNTAX INTEGER (0..2147483647)
                              MAX-ACCESS read-only
                              STATUS current
                              DESCRIPTION "Jitter-Max-Pos-SD"
                              ::= {  setPerfRttmonsEntry 11 }

setPerfRttmonsJittercountposs OBJECT-TYPE
                              SYNTAX INTEGER (0..2147483647)
                              MAX-ACCESS read-only
                              STATUS current
                              DESCRIPTION "Jitter-Count-Pos-SD"
                              ::= {  setPerfRttmonsEntry 12 }

setPerfRttmonsJittersumpossd OBJECT-TYPE
                              SYNTAX INTEGER (0..2147483647)
                              MAX-ACCESS read-only
                              STATUS current
                              DESCRIPTION "Jitter-Sum-Pos-SD"
                              ::= {  setPerfRttmonsEntry 13 }

setPerfRttmonsJitterminposds OBJECT-TYPE
                              SYNTAX INTEGER (0..2147483647)
                              MAX-ACCESS read-only
                              STATUS current
                              DESCRIPTION "Jitter-Min-Pos-DS"
                              ::= {  setPerfRttmonsEntry 16 }

setPerfRttmonsJittermaxposds OBJECT-TYPE
                              SYNTAX INTEGER (0..2147483647)
                              MAX-ACCESS read-only
                              STATUS current
                              DESCRIPTION "Jitter-Max-Pos-DS"
                              ::= {  setPerfRttmonsEntry 17 }

setPerfRttmonsJittercountposd OBJECT-TYPE
                              SYNTAX INTEGER (0..2147483647)
                              MAX-ACCESS read-only
                              STATUS current
                              DESCRIPTION "Jitter-Count-Pos-DS"
                              ::= {  setPerfRttmonsEntry 18 }

setPerfRttmonsJittersumposds OBJECT-TYPE
                              SYNTAX INTEGER (0..2147483647)
                              MAX-ACCESS read-only
                              STATUS current
                              DESCRIPTION "Jitter-Sum-Pos-DS"
                              ::= {  setPerfRttmonsEntry 19 }

setPerfRttmonsJitterminnegsd OBJECT-TYPE
                              SYNTAX INTEGER (0..2147483647)
                              MAX-ACCESS read-only
                              STATUS current
                              DESCRIPTION "Jitter-Min-Neg-SD"
                              ::= {  setPerfRttmonsEntry 22 }

setPerfRttmonsJittermaxnegsd OBJECT-TYPE
                              SYNTAX INTEGER (0..2147483647)
                              MAX-ACCESS read-only
                              STATUS current
                              DESCRIPTION "Jitter-Max-Neg-SD"
                              ::= {  setPerfRttmonsEntry 23 }

setPerfRttmonsJittercountnegs OBJECT-TYPE
                              SYNTAX INTEGER (0..2147483647)
                              MAX-ACCESS read-only
                              STATUS current
                              DESCRIPTION "Jitter-Count-Neg-SD"
                              ::= {  setPerfRttmonsEntry 24 }

setPerfRttmonsJittersumnegsd OBJECT-TYPE
                              SYNTAX INTEGER (0..2147483647)
                              MAX-ACCESS read-only
                              STATUS current
                              DESCRIPTION "Jitter-Sum-Neg-SD"
                              ::= {  setPerfRttmonsEntry 25 }

setPerfRttmonsJitterminnegds OBJECT-TYPE
                              SYNTAX INTEGER (0..2147483647)
                              MAX-ACCESS read-only
                              STATUS current
                              DESCRIPTION "Jitter-Min-Neg-DS"
                              ::= {  setPerfRttmonsEntry 28 }

setPerfRttmonsJittermaxnegds OBJECT-TYPE
                              SYNTAX INTEGER (0..2147483647)
                              MAX-ACCESS read-only
                              STATUS current
                              DESCRIPTION "Jitter-Max-Neg-DS"
                              ::= {  setPerfRttmonsEntry 29 }

setPerfRttmonsJittercountnegd OBJECT-TYPE
                              SYNTAX INTEGER (0..2147483647)
                              MAX-ACCESS read-only
                              STATUS current
                              DESCRIPTION "Jitter-Count-Neg-DS"
                              ::= {  setPerfRttmonsEntry 30 }

setPerfRttmonsJittersumnegds OBJECT-TYPE
                              SYNTAX INTEGER (0..2147483647)
                              MAX-ACCESS read-only
                              STATUS current
                              DESCRIPTION "Jitter-Sum-Neg-DS"
                              ::= {  setPerfRttmonsEntry 31 }

setPerfRttmonsPacketlosssd OBJECT-TYPE
                              SYNTAX INTEGER (0..2147483647)
                              MAX-ACCESS read-only
                              STATUS current
                              DESCRIPTION "Packet-Loss-SD"
                              ::= {  setPerfRttmonsEntry 34 }

setPerfRttmonsPacketlossds OBJECT-TYPE
                              SYNTAX INTEGER (0..2147483647)
                              MAX-ACCESS read-only
                              STATUS current
                              DESCRIPTION "Packet-Loss-DS"
                              ::= {  setPerfRttmonsEntry 35 }

setPerfRttmonsAveragejitter OBJECT-TYPE
                              SYNTAX INTEGER (0..2147483647)
                              MAX-ACCESS read-only
                              STATUS current
                              DESCRIPTION "Average-Jitter"
                              ::= {  setPerfRttmonsEntry 62 }

setPerfRttmonsAveragejittersd OBJECT-TYPE
                              SYNTAX INTEGER (0..2147483647)
                              MAX-ACCESS read-only
                              STATUS current
                              DESCRIPTION "Average-Jitter-SD"
                              ::= {  setPerfRttmonsEntry 63 }

setPerfRttmonsAveragejitterds OBJECT-TYPE
                              SYNTAX INTEGER (0..2147483647)
                              MAX-ACCESS read-only
                              STATUS current
                              DESCRIPTION "Average-Jitter-DS"
                              ::= {  setPerfRttmonsEntry 64 }

setEcho OBJECT IDENTIFIER ::= { set 35}
setEchoOpe OBJECT-TYPE
           SYNTAX INTEGER
           {
             no(0),
             yes(1)
           }
           MAX-ACCESS read-write
           STATUS current
           DESCRIPTION "Operating"
           ::= {  setEcho 1 }

setEchoAccTable OBJECT-TYPE
                SYNTAX SEQUENCE OF SetEchoAccEntry
                MAX-ACCESS not-accessible
                STATUS current
                DESCRIPTION "Access-Table"
                ::= {  setEcho 2 }

setEchoAccEntry OBJECT-TYPE
                SYNTAX SetEchoAccEntry
                MAX-ACCESS not-accessible
                STATUS current
                DESCRIPTION "entry in table"
                INDEX { setEchoAccIpa, setEchoAccNet }
                ::= {  setEchoAccTable 1 }

SetEchoAccEntry ::= SEQUENCE {
                setEchoAccIpa IpAddress,
                setEchoAccNet IpAddress,
                setEchoAccPro INTEGER,
                setEchoAccAct INTEGER,
                setEchoAccCom DisplayString
               }

setEchoAccIpa OBJECT-TYPE
              SYNTAX IpAddress
              MAX-ACCESS read-write
              STATUS current
              DESCRIPTION "IP-Address"
              ::= {  setEchoAccEntry 1 }

setEchoAccNet OBJECT-TYPE
              SYNTAX IpAddress
              MAX-ACCESS read-write
              STATUS current
              DESCRIPTION "Netmask"
              ::= {  setEchoAccEntry 2 }

setEchoAccPro OBJECT-TYPE
              SYNTAX INTEGER
              {
                none(0),
                tcp(1),
                udp(2),
                tcp-plus-udp(3)
              }
              MAX-ACCESS read-write
              STATUS current
              DESCRIPTION "Protokoll"
              ::= {  setEchoAccEntry 3 }

setEchoAccAct OBJECT-TYPE
              SYNTAX INTEGER
              {
                yes(0),
                no(1)
              }
              MAX-ACCESS read-write
              STATUS current
              DESCRIPTION "Active"
              ::= {  setEchoAccEntry 4 }

setEchoAccCom OBJECT-TYPE
              SYNTAX DisplayString (SIZE(0..31))
              MAX-ACCESS read-write
              STATUS current
              DESCRIPTION "Comment"
              ::= {  setEchoAccEntry 5 }

setEchoTcp OBJECT-TYPE
           SYNTAX INTEGER
           MAX-ACCESS read-write
           STATUS current
           DESCRIPTION "TCP-Timeout"
           ::= {  setEcho 3 }

firVerTable OBJECT-TYPE
            SYNTAX SEQUENCE OF FirVerEntry
            MAX-ACCESS not-accessible
            STATUS current
            DESCRIPTION "Version-Table"
            ::= {  fir 1 }

firVerEntry OBJECT-TYPE
            SYNTAX FirVerEntry
            MAX-ACCESS not-accessible
            STATUS current
            DESCRIPTION "entry in table"
            INDEX { firVerIfc }
            ::= {  firVerTable 1 }

FirVerEntry ::= SEQUENCE {
            firVerIfc INTEGER,
            firVerMod DisplayString,
            firVerVer DisplayString,
            firVerSer DisplayString
           }

firVerIfc OBJECT-TYPE
          SYNTAX INTEGER
          {
            ifc(1)
          }
          MAX-ACCESS read-only
          STATUS current
          DESCRIPTION "Ifc"
          ::= {  firVerEntry 1 }

firVerMod OBJECT-TYPE
          SYNTAX DisplayString (SIZE(0..64))
          MAX-ACCESS read-only
          STATUS current
          DESCRIPTION "Module"
          ::= {  firVerEntry 2 }

firVerVer OBJECT-TYPE
          SYNTAX DisplayString (SIZE(0..30))
          MAX-ACCESS read-only
          STATUS current
          DESCRIPTION "Version"
          ::= {  firVerEntry 3 }

firVerSer OBJECT-TYPE
          SYNTAX DisplayString (SIZE(0..14))
          MAX-ACCESS read-only
          STATUS current
          DESCRIPTION "Serial-number"
          ::= {  firVerEntry 4 }

firTabTable OBJECT-TYPE
            SYNTAX SEQUENCE OF FirTabEntry
            MAX-ACCESS not-accessible
            STATUS current
            DESCRIPTION "Table-Firmsafe"
            ::= {  fir 2 }

firTabEntry OBJECT-TYPE
            SYNTAX FirTabEntry
            MAX-ACCESS not-accessible
            STATUS current
            DESCRIPTION "entry in table"
            INDEX { firTabPos }
            ::= {  firTabTable 1 }

FirTabEntry ::= SEQUENCE {
            firTabPos INTEGER,
            firTabSta INTEGER,
            firTabVer DisplayString,
            firTabDat DisplayString,
            firTabSiz INTEGER,
            firTabInd INTEGER
           }

firTabPos OBJECT-TYPE
          SYNTAX INTEGER (0..255)
          MAX-ACCESS read-only
          STATUS current
          DESCRIPTION "Position"
          ::= {  firTabEntry 1 }

firTabSta OBJECT-TYPE
          SYNTAX INTEGER
          {
            loader(2),
            active(1),
            inactive(0),
            minimal-plus-active(5),
            minimal-plus-inactive(4)
          }
          MAX-ACCESS read-write
          STATUS current
          DESCRIPTION "Status"
          ::= {  firTabEntry 2 }

firTabVer OBJECT-TYPE
          SYNTAX DisplayString (SIZE(0..5))
          MAX-ACCESS read-only
          STATUS current
          DESCRIPTION "Version"
          ::= {  firTabEntry 3 }

firTabDat OBJECT-TYPE
          SYNTAX DisplayString (SIZE(0..9))
          MAX-ACCESS read-only
          STATUS current
          DESCRIPTION "Date"
          ::= {  firTabEntry 4 }

firTabSiz OBJECT-TYPE
          SYNTAX INTEGER (0..2147483647)
          MAX-ACCESS read-only
          STATUS current
          DESCRIPTION "Size"
          ::= {  firTabEntry 5 }

firTabInd OBJECT-TYPE
          SYNTAX INTEGER (0..2147483647)
          MAX-ACCESS read-only
          STATUS current
          DESCRIPTION "Index"
          ::= {  firTabEntry 6 }

firMod OBJECT-TYPE
       SYNTAX INTEGER
       {
         immediate(0),
         login(1),
         manual(2)
       }
       MAX-ACCESS read-write
       STATUS current
       DESCRIPTION "Mode-Firmsafe"
       ::= {  fir 3 }

firTim OBJECT-TYPE
       SYNTAX INTEGER
       MAX-ACCESS read-write
       STATUS current
       DESCRIPTION "Timeout-Firmsafe"
       ::= {  fir 4 }

firFea OBJECT-TYPE
       SYNTAX DisplayString (SIZE(0..34))
       MAX-ACCESS read-only
       STATUS current
       DESCRIPTION "Feature-Word"
       ::= {  fir 7 }

othMan OBJECT IDENTIFIER ::= { oth 1}
othManCon OBJECT-TYPE
          SYNTAX DisplayString
          MAX-ACCESS read-write
          STATUS current
          DESCRIPTION "Connect"
          ::= {  othMan 1 }

othManDis OBJECT-TYPE
          SYNTAX DisplayString
          MAX-ACCESS read-write
          STATUS current
          DESCRIPTION "Disconnect"
          ::= {  othMan 2 }

othBoo OBJECT-TYPE
       SYNTAX DisplayString
       MAX-ACCESS read-write
       STATUS current
       DESCRIPTION "Boot-System"
       ::= {  oth 2 }

othCol OBJECT-TYPE
       SYNTAX DisplayString
       MAX-ACCESS read-write
       STATUS current
       DESCRIPTION "Cold-Boot"
       ::= {  oth 5 }



-- traps

trapgrp OBJECT IDENTIFIER ::= { lancom-1711-plus 0 }
traps   OBJECT IDENTIFIER ::= { trapgrp 0 }

trpStatChan NOTIFICATION-TYPE
            OBJECTS {
             sysDescr,
             sysName,
             staSnmpEveCou,
             staWanConnectio,
             staChanState,
             staChanApp,
             staChanMode,
             staChanCause,
             staChanNumbe,
             staChanSubad,
             staChanCharg,
             staChanExtra,
             staChanConnt,
             staChanConns,
             staChanIsdnd,
             staChanPhcha,
             staChanPptpc,
             staChanVpnco
            }
            STATUS current
            DESCRIPTION "StatChan"
            ::= { traps 1 }

trpFwUplStart NOTIFICATION-TYPE
              OBJECTS {
               sysDescr,
               sysName,
               staSnmpEveCou,
               staConfEventlogSyste,
               staConfEventlogEvent,
               staConfEventlogAcces,
               staConfEventlogIpadd
              }
              STATUS current
              DESCRIPTION "FwUplStart"
              ::= { traps 4 }

trpUplSucc NOTIFICATION-TYPE
           OBJECTS {
            sysDescr,
            sysName,
            staSnmpEveCou,
            staConfEventlogSyste,
            staConfEventlogEvent,
            staConfEventlogAcces,
            staConfEventlogIpadd,
            staConfEventlogInfo1,
            staConfEventlogInfo2
           }
           STATUS current
           DESCRIPTION "UplSucc"
           ::= { traps 5 }

trpUplFailTo NOTIFICATION-TYPE
             OBJECTS {
              sysDescr,
              sysName,
              staSnmpEveCou,
              staConfEventlogSyste,
              staConfEventlogEvent,
              staConfEventlogAcces,
              staConfEventlogIpadd,
              staConfEventlogInfo1,
              staConfEventlogInfo2
             }
             STATUS current
             DESCRIPTION "UplFailTo"
             ::= { traps 6 }

trpUplFailIncl NOTIFICATION-TYPE
               OBJECTS {
                sysDescr,
                sysName,
                staSnmpEveCou,
                staConfEventlogSyste,
                staConfEventlogEvent,
                staConfEventlogAcces,
                staConfEventlogIpadd,
                staConfEventlogInfo1,
                staConfEventlogInfo2
               }
               STATUS current
               DESCRIPTION "UplFailIncl"
               ::= { traps 7 }

trpUplFailBadDev NOTIFICATION-TYPE
                 OBJECTS {
                  sysDescr,
                  sysName,
                  staSnmpEveCou,
                  staConfEventlogSyste,
                  staConfEventlogEvent,
                  staConfEventlogAcces,
                  staConfEventlogIpadd,
                  staConfEventlogInfo1,
                  staConfEventlogInfo2
                 }
                 STATUS current
                 DESCRIPTION "UplFailBadDev"
                 ::= { traps 8 }

trpLogin NOTIFICATION-TYPE
         OBJECTS {
          sysDescr,
          sysName,
          staSnmpEveCou,
          staConfEventlogSyste,
          staConfEventlogEvent,
          staConfEventlogAcces,
          staConfEventlogIpadd
         }
         STATUS current
         DESCRIPTION "Login"
         ::= { traps 9 }

trpLogout NOTIFICATION-TYPE
          OBJECTS {
           sysDescr,
           sysName,
           staSnmpEveCou,
           staConfEventlogSyste,
           staConfEventlogEvent,
           staConfEventlogAcces,
           staConfEventlogIpadd
          }
          STATUS current
          DESCRIPTION "Logout"
          ::= { traps 10 }

trpCnfUplStart NOTIFICATION-TYPE
               OBJECTS {
                sysDescr,
                sysName,
                staSnmpEveCou,
                staConfEventlogSyste,
                staConfEventlogEvent,
                staConfEventlogAcces,
                staConfEventlogIpadd
               }
               STATUS current
               DESCRIPTION "CnfUplStart"
               ::= { traps 11 }

trpCnfDnlStart NOTIFICATION-TYPE
               OBJECTS {
                sysDescr,
                sysName,
                staSnmpEveCou,
                staConfEventlogSyste,
                staConfEventlogEvent,
                staConfEventlogAcces,
                staConfEventlogIpadd
               }
               STATUS current
               DESCRIPTION "CnfDnlStart"
               ::= { traps 12 }

trpCnfDnlSucc NOTIFICATION-TYPE
              OBJECTS {
               sysDescr,
               sysName,
               staSnmpEveCou,
               staConfEventlogSyste,
               staConfEventlogEvent,
               staConfEventlogAcces,
               staConfEventlogIpadd,
               staConfEventlogInfo1,
               staConfEventlogInfo2
              }
              STATUS current
              DESCRIPTION "CnfDnlSucc"
              ::= { traps 13 }

trpIpFwFlt NOTIFICATION-TYPE
           OBJECTS {
            sysDescr,
            sysName,
            staSnmpEveCou,
            staIproLogtablSyst,
            staIproLogtablSrca,
            staIproLogtablDsta,
            staIproLogtablProt,
            staIproLogtablSrcp,
            staIproLogtablDstp,
            staIproLogtablFilt,
            staIproLogtablLimi,
            staIproLogtablThre,
            staIproLogtablActi
           }
           STATUS current
           DESCRIPTION "IpFwFlt"
           ::= { traps 26 }

trpVPNConn NOTIFICATION-TYPE
           OBJECTS {
            sysDescr,
            sysName,
            staSnmpEveCou,
            staVpnTunnel,
            staVpnConnectPeer,
            staVpnConnectState,
            staVpnConnectLaster,
            staVpnConnectMode,
            staVpnConnectShtime,
            staVpnConnectPhysco,
            staVpnConnectB1dt,
            staVpnConnectRemote,
            staVpnConnectNatdet,
            staVpnConnectCrypta,
            staVpnConnectCryptl,
            staVpnConnectHashal,
            staVpnConnectHashle,
            staVpnConnectHmacal,
            staVpnConnectHmacle,
            staVpnConnectCompra,
            staVpnConnectClient
           }
           STATUS current
           DESCRIPTION "VPNConn"
           ::= { traps 27 }

trpPptpConn NOTIFICATION-TYPE
            OBJECTS {
             sysDescr,
             sysName,
             staSnmpEveCou,
             staPptpTun,
             staPptpConChann,
             staPptpConState,
             staPptpConMode,
             staPptpConShtim,
             staPptpConPhysc,
             staPptpConPeera,
             staPptpConIpadd,
             staPptpConDnsde,
             staPptpConNbnsd,
             staPptpConLaste,
             staPptpConDnsba,
             staPptpConNbnsb
            }
            STATUS current
            DESCRIPTION "PptpConn"
            ::= { traps 28 }

trpErrLogin NOTIFICATION-TYPE
            OBJECTS {
             sysDescr,
             sysName,
             staSnmpEveCou,
             staConfEventlogSyste,
             staConfEventlogEvent,
             staConfEventlogAcces,
             staConfEventlogIpadd
            }
            STATUS current
            DESCRIPTION "ErrLogin"
            ::= { traps 29 }

trpLdblConn NOTIFICATION-TYPE
            OBJECTS {
             sysDescr,
             sysName,
             staSnmpEveCou,
             staIproLoadbalConPee,
             staIproLoadbalConBun,
             staIproLoadbalConSta
            }
            STATUS current
            DESCRIPTION "LdblConn"
            ::= { traps 38 }

trpPPPoESConn NOTIFICATION-TYPE
              OBJECTS {
               sysDescr,
               sysName,
               staSnmpEveCou,
               staPppoNum,
               staPppoConCha,
               staPppoConMac,
               staPppoConSta,
               staPppoConLas,
               staPppoConSht,
               staPppoConPee
              }
              STATUS current
              DESCRIPTION "PPPoESConn"
              ::= { traps 39 }

trpVrrp NOTIFICATION-TYPE
        OBJECTS {
         sysDescr,
         sysName,
         staSnmpEveCou,
         staIproVrrpEveSys,
         staIproVrrpEveSrc,
         staIproVrrpEveVri,
         staIproVrrpEveEve,
         staIproVrrpEveInf
        }
        STATUS current
        DESCRIPTION "Vrrp"
        ::= { traps 41 }

trpHTTP-Tunnel-Open NOTIFICATION-TYPE
                    OBJECTS {
                     sysDescr,
                     sysName,
                     staSnmpEveCou,
                     staTcpiHttpActiveIndex,
                     staTcpiHttpActiveRemotea,
                     staTcpiHttpActiveRemotep,
                     staTcpiHttpActiveLocalho,
                     staTcpiHttpActiveLocalpo,
                     staTcpiHttpActiveIdletim,
                     staTcpiHttpActiveLocalrt
                    }
                    STATUS current
                    DESCRIPTION "HTTP-Tunnel-Open"
                    ::= { traps 2000 }

trpHTTP-Tunnel-Close NOTIFICATION-TYPE
                     OBJECTS {
                      sysDescr,
                      sysName,
                      staSnmpEveCou,
                      staTcpiHttpActiveIndex
                     }
                     STATUS current
                     DESCRIPTION "HTTP-Tunnel-Close"
                     ::= { traps 2001 }

trpLAN-Overtemp-Throttle NOTIFICATION-TYPE
                         OBJECTS {
                          sysDescr,
                          sysName,
                          staSnmpEveCou
                         }
                         STATUS current
                         DESCRIPTION "LAN-Overtemp-Throttle"
                         ::= { traps 5002 }

trpLAN-Overtemp-Throttle-End NOTIFICATION-TYPE
                             OBJECTS {
                              sysDescr,
                              sysName,
                              staSnmpEveCou
                             }
                             STATUS current
                             DESCRIPTION "LAN-Overtemp-Throttle-End"
                             ::= { traps 5003 }

trpLAN-Overtemp-Throttle-Recommend NOTIFICATION-TYPE
                                   OBJECTS {
                                    sysDescr,
                                    sysName,
                                    staSnmpEveCou
                                   }
                                   STATUS current
                                   DESCRIPTION "LAN-Overtemp-Throttle-Recommend"
                                   ::= { traps 5004 }

END
