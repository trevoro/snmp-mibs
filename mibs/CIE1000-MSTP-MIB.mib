-- *****************************************************************
-- MSTP-MIB:  Cisco private MIB
-- ****************************************************************

CIE1000-MSTP-MIB DEFINITIONS ::= BEGIN

IMPORTS
    NOTIFICATION-GROUP, MODULE-COMPLIANCE, OBJECT-GROUP FROM SNMPv2-CONF
    NOTIFICATION-TYPE, MODULE-IDENTITY, OBJECT-TYPE FROM SNMPv2-SMI
    TEXTUAL-CONVENTION FROM SNMPv2-TC
    cie1000SwitchMgmt FROM CISCO-IE1000-MIB
    CIE1000DisplayString FROM CIE1000-TC
    CIE1000InterfaceIndex FROM CIE1000-TC
    CIE1000Unsigned16 FROM CIE1000-TC
    CIE1000Unsigned8 FROM CIE1000-TC
    CIE1000VlanListQuarter FROM CIE1000-TC
    Integer32 FROM SNMPv2-SMI
    Unsigned32 FROM SNMPv2-SMI
    TruthValue FROM SNMPv2-TC
    ;

cie1000MstpMib MODULE-IDENTITY
    LAST-UPDATED "201511130000Z"
    ORGANIZATION
        "Cisco Systems, Inc."
    CONTACT-INFO
        "Cisco Systems
	 Customer Service

	 Postal: 170 West Tasman Drive
	 San Jose, CA  95134
	 USA

	 Tel: +1 800 553-NETS

	 E-mail: cs-snmp@cisco.com"
    DESCRIPTION
        "This is a private version of the 802.1Q-2005 MSTP MIB"
    REVISION    "201511130000Z"
    DESCRIPTION
        "Add TCN counters"
    REVISION    "201511040000Z"
    DESCRIPTION
        "Added msti config table with msti value as the iteration key"
    REVISION    "201509290000Z"
    DESCRIPTION
        "Added range information for bridge parameters"
    REVISION    "201407010000Z"
    DESCRIPTION
        "Initial version"
    ::= { cie1000SwitchMgmt 20 }


CIE1000MSTPForceVersion ::= TEXTUAL-CONVENTION
    STATUS      current
    DESCRIPTION
        "This enumeration control the STP protocol variant to run."
    SYNTAX      INTEGER { stp(0), rstp(2), mstp(3) }

CIE1000MstpPoint2Point ::= TEXTUAL-CONVENTION
    STATUS      current
    DESCRIPTION
        "This enumeration describe the values of adminPointToPointMAC and
         operPointToPointMAC parameters. (Full duplex port administrative and
         operational status.) See 6.4.3 of IEEE Std 802.1D."
    SYNTAX      INTEGER { forceTrue(0), forceFalse(1), auto(2) }

CIE1000MstpPortState ::= TEXTUAL-CONVENTION
    STATUS      current
    DESCRIPTION
        "This enumeration describe the forwarding state of an interface."
    SYNTAX      INTEGER { disabled(0), discarding(1), learning(2),
                          forwarding(3) }

cie1000MstpMibObjects OBJECT IDENTIFIER
    ::= { cie1000MstpMib 1 }

cie1000MstpConfig OBJECT IDENTIFIER
    ::= { cie1000MstpMibObjects 2 }

cie1000MstpConfigBridgeParams OBJECT IDENTIFIER
    ::= { cie1000MstpConfig 1 }

cie1000MstpConfigBridgeParamsBridgeMaxAge OBJECT-TYPE
    SYNTAX      Unsigned32
    MAX-ACCESS  read-write
    STATUS      current
    DESCRIPTION
        "Bridge Max Age, IEEE-802.1D-2004 sect 13.23.4"
    ::= { cie1000MstpConfigBridgeParams 1 }

cie1000MstpConfigBridgeParamsBridgeHelloTime OBJECT-TYPE
    SYNTAX      Unsigned32 (1..2)
    MAX-ACCESS  read-write
    STATUS      current
    DESCRIPTION
        "Bridge Hello Time, 13.25.7 of IEEE-802.1Q-2005. Fixed value of two
         seconds by the standard, but this implementation allow a compatibility
         range from 1 to 2 seconds, in stipulated in 802.1Q-2005"
    ::= { cie1000MstpConfigBridgeParams 2 }

cie1000MstpConfigBridgeParamsBridgeForwardDelay OBJECT-TYPE
    SYNTAX      Unsigned32 (4..30)
    MAX-ACCESS  read-write
    STATUS      current
    DESCRIPTION
        "Bridge Forward Delay, IEEE-802.1D-2004 sect 17.20"
    ::= { cie1000MstpConfigBridgeParams 3 }

cie1000MstpConfigBridgeParamsForceVersion OBJECT-TYPE
    SYNTAX      CIE1000MSTPForceVersion
    MAX-ACCESS  read-write
    STATUS      current
    DESCRIPTION
        "value of the Force Protocol Version parameter - 13.6.2 of
         IEEE-802.1Q-2005"
    ::= { cie1000MstpConfigBridgeParams 4 }

cie1000MstpConfigBridgeParamsTxHoldCount OBJECT-TYPE
    SYNTAX      Unsigned32 (1..10)
    MAX-ACCESS  read-write
    STATUS      current
    DESCRIPTION
        "TxHoldCount - 17.13.12 of IEEE Std 802.1D"
    ::= { cie1000MstpConfigBridgeParams 5 }

cie1000MstpConfigBridgeParamsMaxHops OBJECT-TYPE
    SYNTAX      CIE1000Unsigned8 (6..40)
    MAX-ACCESS  read-write
    STATUS      current
    DESCRIPTION
        "MaxHops - 13.22.1 of IEEE-802.1Q-2005"
    ::= { cie1000MstpConfigBridgeParams 6 }

cie1000MstpConfigBridgeParamsBpduFiltering OBJECT-TYPE
    SYNTAX      TruthValue
    MAX-ACCESS  read-write
    STATUS      current
    DESCRIPTION
        "BPDU filtering for edge ports. Control whether a port explicitly
         configured as Edge will transmit and receive BPDUs"
    ::= { cie1000MstpConfigBridgeParams 7 }

cie1000MstpConfigBridgeParamsBpduGuard OBJECT-TYPE
    SYNTAX      TruthValue
    MAX-ACCESS  read-write
    STATUS      current
    DESCRIPTION
        "BPDU guard for edge ports. Control whether a port explicitly configured
         as Edge will disable itself upon reception of a BPDU. The port will
         enter the error-disabled state, and will be removed from the active
         topology. "
    ::= { cie1000MstpConfigBridgeParams 8 }

cie1000MstpConfigBridgeParamsErrorRecoveryDelay OBJECT-TYPE
    SYNTAX      Unsigned32
    MAX-ACCESS  read-write
    STATUS      current
    DESCRIPTION
        "The number of seconds until a STP inconsistent port is recovered. Valid
         values are zero (recovery disabled) or between 30 and 86400 (24 hours)"
    ::= { cie1000MstpConfigBridgeParams 9 }

cie1000MstpConfigMstiParamTable OBJECT-TYPE
    SYNTAX      SEQUENCE OF CIE1000MstpConfigMstiParamEntry
    MAX-ACCESS  not-accessible
    STATUS      current
    DESCRIPTION
        "This is a table of the bridge instance (MSTIs) parameters"
    ::= { cie1000MstpConfig 2 }

cie1000MstpConfigMstiParamEntry OBJECT-TYPE
    SYNTAX      CIE1000MstpConfigMstiParamEntry
    MAX-ACCESS  not-accessible
    STATUS      current
    DESCRIPTION
        "Each MSTI has a set of parameters"
    INDEX       { cie1000MstpConfigMstiParamInstance }
    ::= { cie1000MstpConfigMstiParamTable 1 }

CIE1000MstpConfigMstiParamEntry ::= SEQUENCE {
    cie1000MstpConfigMstiParamInstance  Integer32,
    cie1000MstpConfigMstiParamPriority  CIE1000Unsigned8
}

cie1000MstpConfigMstiParamInstance OBJECT-TYPE
    SYNTAX      Integer32 (0..255)
    MAX-ACCESS  accessible-for-notify
    STATUS      current
    DESCRIPTION
        "Bridge instance number. The CIST = 0, MSTI1 = 1, etc"
    ::= { cie1000MstpConfigMstiParamEntry 1 }

cie1000MstpConfigMstiParamPriority OBJECT-TYPE
    SYNTAX      CIE1000Unsigned8
    MAX-ACCESS  read-write
    STATUS      current
    DESCRIPTION
        "Bridge Priority"
    ::= { cie1000MstpConfigMstiParamEntry 2 }

cie1000MstpConfigMstiConfig OBJECT IDENTIFIER
    ::= { cie1000MstpConfig 3 }

cie1000MstpConfigMstiConfigId OBJECT IDENTIFIER
    ::= { cie1000MstpConfigMstiConfig 1 }

cie1000MstpConfigMstiConfigIdName OBJECT-TYPE
    SYNTAX      CIE1000DisplayString (SIZE(0..31))
    MAX-ACCESS  read-write
    STATUS      current
    DESCRIPTION
        "The configuration name"
    ::= { cie1000MstpConfigMstiConfigId 1 }

cie1000MstpConfigMstiConfigIdRevision OBJECT-TYPE
    SYNTAX      CIE1000Unsigned16
    MAX-ACCESS  read-write
    STATUS      current
    DESCRIPTION
        "The configuration revision"
    ::= { cie1000MstpConfigMstiConfigId 2 }

cie1000MstpConfigMstiConfigTable OBJECT-TYPE
    SYNTAX      SEQUENCE OF CIE1000MstpConfigMstiConfigEntry
    MAX-ACCESS  not-accessible
    STATUS      current
    DESCRIPTION
        "This is the 802.1Q - 8.9 MST Configuration table
         
         For the purposes of calculating the Configuration Digest, the MST
         Configuration Table is considered to contain 4096 consecutive single
         octet elements, where each element of the table (with the exception of
         the first and last) contains an MSTID value."
    ::= { cie1000MstpConfigMstiConfig 2 }

cie1000MstpConfigMstiConfigEntry OBJECT-TYPE
    SYNTAX      CIE1000MstpConfigMstiConfigEntry
    MAX-ACCESS  not-accessible
    STATUS      current
    DESCRIPTION
        "The first element of the table contains the value 0, the second element
         the MSTID value corresponding to VID 1, the third element the MSTID
         value corresponding to VID 2, and so on, with the next to last element
         of the table containing the MSTID value corresponding to VID 4094, and
         the last element containing the value 0."
    INDEX       { cie1000MstpConfigMstiConfigVid }
    ::= { cie1000MstpConfigMstiConfigTable 1 }

CIE1000MstpConfigMstiConfigEntry ::= SEQUENCE {
    cie1000MstpConfigMstiConfigVid    Integer32,
    cie1000MstpConfigMstiConfigMstid  CIE1000Unsigned8
}

cie1000MstpConfigMstiConfigVid OBJECT-TYPE
    SYNTAX      Integer32 (1..4095)
    MAX-ACCESS  accessible-for-notify
    STATUS      current
    DESCRIPTION
        "Vlan id"
    ::= { cie1000MstpConfigMstiConfigEntry 1 }

cie1000MstpConfigMstiConfigMstid OBJECT-TYPE
    SYNTAX      CIE1000Unsigned8
    MAX-ACCESS  read-write
    STATUS      current
    DESCRIPTION
        "The MSTID value associated with the vlan id"
    ::= { cie1000MstpConfigMstiConfigEntry 2 }

cie1000MstpConfigMstiConfigVlanBitmapTable OBJECT-TYPE
    SYNTAX      SEQUENCE OF CIE1000MstpConfigMstiConfigVlanBitmapEntry
    MAX-ACCESS  not-accessible
    STATUS      current
    DESCRIPTION
        "This is the 802.1Q - 8.9 MST Configuration table
         
         For the purposes of calculating the Configuration Digest, the MST
         Configuration Table is considered to contain 8 consecutive single octet
         elements, where each element of the table contains an vlan bitmap
         (vlans that have the MSTI value specified are set to one)."
    ::= { cie1000MstpConfigMstiConfig 3 }

cie1000MstpConfigMstiConfigVlanBitmapEntry OBJECT-TYPE
    SYNTAX      CIE1000MstpConfigMstiConfigVlanBitmapEntry
    MAX-ACCESS  not-accessible
    STATUS      current
    DESCRIPTION
        "The first element of the table contains vlan bitmap corresponding to
         MSTI 0, the second element contains vlan bitmap corresponding to MSTI 1
         until the 7th element. MSTI range is 0-7."
    INDEX       { cie1000MstpConfigMstiConfigVlanBitmapMstiValue }
    ::= { cie1000MstpConfigMstiConfigVlanBitmapTable 1 }

CIE1000MstpConfigMstiConfigVlanBitmapEntry ::= SEQUENCE {
    cie1000MstpConfigMstiConfigVlanBitmapMstiValue          Integer32,
    cie1000MstpConfigMstiConfigVlanBitmapAccessVlans0To1K   CIE1000VlanListQuarter,
    cie1000MstpConfigMstiConfigVlanBitmapAccessVlans1KTo2K  CIE1000VlanListQuarter,
    cie1000MstpConfigMstiConfigVlanBitmapAccessVlans2KTo3K  CIE1000VlanListQuarter,
    cie1000MstpConfigMstiConfigVlanBitmapAccessVlans3KTo4K  CIE1000VlanListQuarter
}

cie1000MstpConfigMstiConfigVlanBitmapMstiValue OBJECT-TYPE
    SYNTAX      Integer32 (0..7)
    MAX-ACCESS  accessible-for-notify
    STATUS      current
    DESCRIPTION
        "MSTI value."
    ::= { cie1000MstpConfigMstiConfigVlanBitmapEntry 1 }

cie1000MstpConfigMstiConfigVlanBitmapAccessVlans0To1K OBJECT-TYPE
    SYNTAX      CIE1000VlanListQuarter
    MAX-ACCESS  read-write
    STATUS      current
    DESCRIPTION
        "First quarter of bit-array indicating the enabled access VLANs."
    ::= { cie1000MstpConfigMstiConfigVlanBitmapEntry 2 }

cie1000MstpConfigMstiConfigVlanBitmapAccessVlans1KTo2K OBJECT-TYPE
    SYNTAX      CIE1000VlanListQuarter
    MAX-ACCESS  read-write
    STATUS      current
    DESCRIPTION
        "Second quarter of bit-array indicating the enabled access VLANs."
    ::= { cie1000MstpConfigMstiConfigVlanBitmapEntry 3 }

cie1000MstpConfigMstiConfigVlanBitmapAccessVlans2KTo3K OBJECT-TYPE
    SYNTAX      CIE1000VlanListQuarter
    MAX-ACCESS  read-write
    STATUS      current
    DESCRIPTION
        "Third quarter of bit-array indicating the enabled access VLANs."
    ::= { cie1000MstpConfigMstiConfigVlanBitmapEntry 4 }

cie1000MstpConfigMstiConfigVlanBitmapAccessVlans3KTo4K OBJECT-TYPE
    SYNTAX      CIE1000VlanListQuarter
    MAX-ACCESS  read-write
    STATUS      current
    DESCRIPTION
        "Last quarter of bit-array indicating the enabled access VLANs."
    ::= { cie1000MstpConfigMstiConfigVlanBitmapEntry 5 }

cie1000MstpConfigCistInterfaceParamTable OBJECT-TYPE
    SYNTAX      SEQUENCE OF CIE1000MstpConfigCistInterfaceParamEntry
    MAX-ACCESS  not-accessible
    STATUS      current
    DESCRIPTION
        "This is a table of the CIST physical interface parameters"
    ::= { cie1000MstpConfig 4 }

cie1000MstpConfigCistInterfaceParamEntry OBJECT-TYPE
    SYNTAX      CIE1000MstpConfigCistInterfaceParamEntry
    MAX-ACCESS  not-accessible
    STATUS      current
    DESCRIPTION
        "Each CIST physical interface has a set of parameters"
    INDEX       { cie1000MstpConfigCistInterfaceParamInterfaceNo }
    ::= { cie1000MstpConfigCistInterfaceParamTable 1 }

CIE1000MstpConfigCistInterfaceParamEntry ::= SEQUENCE {
    cie1000MstpConfigCistInterfaceParamInterfaceNo           CIE1000InterfaceIndex,
    cie1000MstpConfigCistInterfaceParamEnable                TruthValue,
    cie1000MstpConfigCistInterfaceParamAdminEdgePort         TruthValue,
    cie1000MstpConfigCistInterfaceParamAdminAutoEdgePort     TruthValue,
    cie1000MstpConfigCistInterfaceParamAdminPointToPointMAC  CIE1000MstpPoint2Point,
    cie1000MstpConfigCistInterfaceParamRestrictedRole        TruthValue,
    cie1000MstpConfigCistInterfaceParamRestrictedTcn         TruthValue,
    cie1000MstpConfigCistInterfaceParamBpduGuard             TruthValue
}

cie1000MstpConfigCistInterfaceParamInterfaceNo OBJECT-TYPE
    SYNTAX      CIE1000InterfaceIndex
    MAX-ACCESS  accessible-for-notify
    STATUS      current
    DESCRIPTION
        "Logical interface number."
    ::= { cie1000MstpConfigCistInterfaceParamEntry 1 }

cie1000MstpConfigCistInterfaceParamEnable OBJECT-TYPE
    SYNTAX      TruthValue
    MAX-ACCESS  read-write
    STATUS      current
    DESCRIPTION
        "Control whether port is controlled by xSTP. If disabled, the port
         forwarding state follow the MAC state"
    ::= { cie1000MstpConfigCistInterfaceParamEntry 2 }

cie1000MstpConfigCistInterfaceParamAdminEdgePort OBJECT-TYPE
    SYNTAX      TruthValue
    MAX-ACCESS  read-write
    STATUS      current
    DESCRIPTION
        "adminEdgePort parameter - 18.3.3 of IEEE Std 802.1D"
    ::= { cie1000MstpConfigCistInterfaceParamEntry 3 }

cie1000MstpConfigCistInterfaceParamAdminAutoEdgePort OBJECT-TYPE
    SYNTAX      TruthValue
    MAX-ACCESS  read-write
    STATUS      current
    DESCRIPTION
        "adminAutoEdgePort parameter - 17.13.3 of IEEE Std 802.1D"
    ::= { cie1000MstpConfigCistInterfaceParamEntry 4 }

cie1000MstpConfigCistInterfaceParamAdminPointToPointMAC OBJECT-TYPE
    SYNTAX      CIE1000MstpPoint2Point
    MAX-ACCESS  read-write
    STATUS      current
    DESCRIPTION
        "adminPointToPointMAC parameter - 6.4.3 of IEEE Std 802.1D"
    ::= { cie1000MstpConfigCistInterfaceParamEntry 5 }

cie1000MstpConfigCistInterfaceParamRestrictedRole OBJECT-TYPE
    SYNTAX      TruthValue
    MAX-ACCESS  read-write
    STATUS      current
    DESCRIPTION
        "restrictedRole parameter - 13.25.14 of IEEE Std 802.1Q-2005"
    ::= { cie1000MstpConfigCistInterfaceParamEntry 6 }

cie1000MstpConfigCistInterfaceParamRestrictedTcn OBJECT-TYPE
    SYNTAX      TruthValue
    MAX-ACCESS  read-write
    STATUS      current
    DESCRIPTION
        "restrictedRole parameter - 13.25.15 of IEEE Std 802.1Q-2005"
    ::= { cie1000MstpConfigCistInterfaceParamEntry 7 }

cie1000MstpConfigCistInterfaceParamBpduGuard OBJECT-TYPE
    SYNTAX      TruthValue
    MAX-ACCESS  read-write
    STATUS      current
    DESCRIPTION
        "If enabled, causes the port to disable itself upon receiving valid
         BPDU's. Contrary to the similar bridge setting, the port Edge status
         does not effect this setting. A port entering error-disabled state due
         to this setting is subject to the bridge ErrorRecoveryDelay setting as
         well"
    ::= { cie1000MstpConfigCistInterfaceParamEntry 8 }

cie1000MstpConfigAggrParams OBJECT IDENTIFIER
    ::= { cie1000MstpConfig 5 }

cie1000MstpConfigAggrParamsEnable OBJECT-TYPE
    SYNTAX      TruthValue
    MAX-ACCESS  read-write
    STATUS      current
    DESCRIPTION
        "Control whether port is controlled by xSTP. If disabled, the port
         forwarding state follow the MAC state"
    ::= { cie1000MstpConfigAggrParams 1 }

cie1000MstpConfigAggrParamsAdminEdgePort OBJECT-TYPE
    SYNTAX      TruthValue
    MAX-ACCESS  read-write
    STATUS      current
    DESCRIPTION
        "adminEdgePort parameter - 18.3.3 of IEEE Std 802.1D"
    ::= { cie1000MstpConfigAggrParams 2 }

cie1000MstpConfigAggrParamsAdminAutoEdgePort OBJECT-TYPE
    SYNTAX      TruthValue
    MAX-ACCESS  read-write
    STATUS      current
    DESCRIPTION
        "adminAutoEdgePort parameter - 17.13.3 of IEEE Std 802.1D"
    ::= { cie1000MstpConfigAggrParams 3 }

cie1000MstpConfigAggrParamsAdminPointToPointMAC OBJECT-TYPE
    SYNTAX      CIE1000MstpPoint2Point
    MAX-ACCESS  read-write
    STATUS      current
    DESCRIPTION
        "adminPointToPointMAC parameter - 6.4.3 of IEEE Std 802.1D"
    ::= { cie1000MstpConfigAggrParams 4 }

cie1000MstpConfigAggrParamsRestrictedRole OBJECT-TYPE
    SYNTAX      TruthValue
    MAX-ACCESS  read-write
    STATUS      current
    DESCRIPTION
        "restrictedRole parameter - 13.25.14 of IEEE Std 802.1Q-2005"
    ::= { cie1000MstpConfigAggrParams 5 }

cie1000MstpConfigAggrParamsRestrictedTcn OBJECT-TYPE
    SYNTAX      TruthValue
    MAX-ACCESS  read-write
    STATUS      current
    DESCRIPTION
        "restrictedRole parameter - 13.25.15 of IEEE Std 802.1Q-2005"
    ::= { cie1000MstpConfigAggrParams 6 }

cie1000MstpConfigAggrParamsBpduGuard OBJECT-TYPE
    SYNTAX      TruthValue
    MAX-ACCESS  read-write
    STATUS      current
    DESCRIPTION
        "If enabled, causes the port to disable itself upon receiving valid
         BPDU's. Contrary to the similar bridge setting, the port Edge status
         does not effect this setting. A port entering error-disabled state due
         to this setting is subject to the bridge ErrorRecoveryDelay setting as
         well"
    ::= { cie1000MstpConfigAggrParams 7 }

cie1000MstpConfigMstiInterfaceParamTable OBJECT-TYPE
    SYNTAX      SEQUENCE OF CIE1000MstpConfigMstiInterfaceParamEntry
    MAX-ACCESS  not-accessible
    STATUS      current
    DESCRIPTION
        "This is a table of the MSTI interface parameters"
    ::= { cie1000MstpConfig 6 }

cie1000MstpConfigMstiInterfaceParamEntry OBJECT-TYPE
    SYNTAX      CIE1000MstpConfigMstiInterfaceParamEntry
    MAX-ACCESS  not-accessible
    STATUS      current
    DESCRIPTION
        "Each MSTI interface has a set of parameters"
    INDEX       { cie1000MstpConfigMstiInterfaceParamInterfaceNo,
                  cie1000MstpConfigMstiInterfaceParamInstance }
    ::= { cie1000MstpConfigMstiInterfaceParamTable 1 }

CIE1000MstpConfigMstiInterfaceParamEntry ::= SEQUENCE {
    cie1000MstpConfigMstiInterfaceParamInterfaceNo        CIE1000InterfaceIndex,
    cie1000MstpConfigMstiInterfaceParamInstance           Integer32,
    cie1000MstpConfigMstiInterfaceParamAdminPathCost      Unsigned32,
    cie1000MstpConfigMstiInterfaceParamAdminPortPriority  CIE1000Unsigned8
}

cie1000MstpConfigMstiInterfaceParamInterfaceNo OBJECT-TYPE
    SYNTAX      CIE1000InterfaceIndex
    MAX-ACCESS  accessible-for-notify
    STATUS      current
    DESCRIPTION
        "Logical interface number."
    ::= { cie1000MstpConfigMstiInterfaceParamEntry 1 }

cie1000MstpConfigMstiInterfaceParamInstance OBJECT-TYPE
    SYNTAX      Integer32 (0..255)
    MAX-ACCESS  accessible-for-notify
    STATUS      current
    DESCRIPTION
        "Bridge instance number. The CIST = 0, MSTI1 = 1, etc"
    ::= { cie1000MstpConfigMstiInterfaceParamEntry 2 }

cie1000MstpConfigMstiInterfaceParamAdminPathCost OBJECT-TYPE
    SYNTAX      Unsigned32
    MAX-ACCESS  read-write
    STATUS      current
    DESCRIPTION
        "Path Cost - 13.37.1 of 802.1Q-2005"
    ::= { cie1000MstpConfigMstiInterfaceParamEntry 3 }

cie1000MstpConfigMstiInterfaceParamAdminPortPriority OBJECT-TYPE
    SYNTAX      CIE1000Unsigned8
    MAX-ACCESS  read-write
    STATUS      current
    DESCRIPTION
        "priority field for the Port Identifier - 13.24.12 of 802.1Q-2005"
    ::= { cie1000MstpConfigMstiInterfaceParamEntry 4 }

cie1000MstpConfigMstiAggrParamTable OBJECT-TYPE
    SYNTAX      SEQUENCE OF CIE1000MstpConfigMstiAggrParamEntry
    MAX-ACCESS  not-accessible
    STATUS      current
    DESCRIPTION
        "This is a table of the MSTI aggregations parameters"
    ::= { cie1000MstpConfig 7 }

cie1000MstpConfigMstiAggrParamEntry OBJECT-TYPE
    SYNTAX      CIE1000MstpConfigMstiAggrParamEntry
    MAX-ACCESS  not-accessible
    STATUS      current
    DESCRIPTION
        "The aggregations for each MSTI has a set of parameters"
    INDEX       { cie1000MstpConfigMstiAggrParamInstance }
    ::= { cie1000MstpConfigMstiAggrParamTable 1 }

CIE1000MstpConfigMstiAggrParamEntry ::= SEQUENCE {
    cie1000MstpConfigMstiAggrParamInstance           Integer32,
    cie1000MstpConfigMstiAggrParamAdminPathCost      Unsigned32,
    cie1000MstpConfigMstiAggrParamAdminPortPriority  CIE1000Unsigned8
}

cie1000MstpConfigMstiAggrParamInstance OBJECT-TYPE
    SYNTAX      Integer32 (0..255)
    MAX-ACCESS  accessible-for-notify
    STATUS      current
    DESCRIPTION
        "Bridge instance number. The CIST = 0, MSTI1 = 1, etc"
    ::= { cie1000MstpConfigMstiAggrParamEntry 1 }

cie1000MstpConfigMstiAggrParamAdminPathCost OBJECT-TYPE
    SYNTAX      Unsigned32
    MAX-ACCESS  read-write
    STATUS      current
    DESCRIPTION
        "Path Cost - 13.37.1 of 802.1Q-2005"
    ::= { cie1000MstpConfigMstiAggrParamEntry 3 }

cie1000MstpConfigMstiAggrParamAdminPortPriority OBJECT-TYPE
    SYNTAX      CIE1000Unsigned8
    MAX-ACCESS  read-write
    STATUS      current
    DESCRIPTION
        "priority field for the Port Identifier - 13.24.12 of 802.1Q-2005"
    ::= { cie1000MstpConfigMstiAggrParamEntry 4 }

cie1000MstpStatus OBJECT IDENTIFIER
    ::= { cie1000MstpMibObjects 3 }

cie1000MstpStatusBridgeTable OBJECT-TYPE
    SYNTAX      SEQUENCE OF CIE1000MstpStatusBridgeEntry
    MAX-ACCESS  not-accessible
    STATUS      current
    DESCRIPTION
        "This table represent the status of the bridge instances"
    ::= { cie1000MstpStatus 1 }

cie1000MstpStatusBridgeEntry OBJECT-TYPE
    SYNTAX      CIE1000MstpStatusBridgeEntry
    MAX-ACCESS  not-accessible
    STATUS      current
    DESCRIPTION
        "A MSTP Bridge instance set of status objects"
    INDEX       { cie1000MstpStatusBridgeInstance }
    ::= { cie1000MstpStatusBridgeTable 1 }

CIE1000MstpStatusBridgeEntry ::= SEQUENCE {
    cie1000MstpStatusBridgeInstance                 Integer32,
    cie1000MstpStatusBridgeBridgeId                 OCTET STRING,
    cie1000MstpStatusBridgeTimeSinceTopologyChange  Unsigned32,
    cie1000MstpStatusBridgeTopologyChangeCount      Unsigned32,
    cie1000MstpStatusBridgeTopologyChange           TruthValue,
    cie1000MstpStatusBridgeDesignatedRoot           OCTET STRING,
    cie1000MstpStatusBridgeRootPathCost             Unsigned32,
    cie1000MstpStatusBridgeRootPort                 Unsigned32,
    cie1000MstpStatusBridgeMaxAge                   Unsigned32,
    cie1000MstpStatusBridgeForwardDelay             Unsigned32,
    cie1000MstpStatusBridgeBridgeMaxAge             Unsigned32,
    cie1000MstpStatusBridgeBridgeHelloTime          Unsigned32,
    cie1000MstpStatusBridgeBridgeForwardDelay       Unsigned32,
    cie1000MstpStatusBridgeTxHoldCount              Unsigned32,
    cie1000MstpStatusBridgeForceVersion             CIE1000MSTPForceVersion,
    cie1000MstpStatusBridgeCistRegionalRoot         OCTET STRING,
    cie1000MstpStatusBridgeCistInternalPathCost     Unsigned32,
    cie1000MstpStatusBridgeMaxHops                  CIE1000Unsigned8
}

cie1000MstpStatusBridgeInstance OBJECT-TYPE
    SYNTAX      Integer32 (0..255)
    MAX-ACCESS  accessible-for-notify
    STATUS      current
    DESCRIPTION
        "Bridge instance number. The CIST = 0, MSTI1 = 1, etc"
    ::= { cie1000MstpStatusBridgeEntry 1 }

cie1000MstpStatusBridgeBridgeId OBJECT-TYPE
    SYNTAX      OCTET STRING (SIZE(8))
    MAX-ACCESS  read-only
    STATUS      current
    DESCRIPTION
        "Bridge Identifier of this bridge"
    ::= { cie1000MstpStatusBridgeEntry 2 }

cie1000MstpStatusBridgeTimeSinceTopologyChange OBJECT-TYPE
    SYNTAX      Unsigned32
    MAX-ACCESS  read-only
    STATUS      current
    DESCRIPTION
        "The count in seconds of the time elapsed since the Topology Change flag
         was last True"
    ::= { cie1000MstpStatusBridgeEntry 3 }

cie1000MstpStatusBridgeTopologyChangeCount OBJECT-TYPE
    SYNTAX      Unsigned32
    MAX-ACCESS  read-only
    STATUS      current
    DESCRIPTION
        "The count of the times the Topology Change flag parameter for the
         Bridge has been set since the Bridge was powered on or initialized"
    ::= { cie1000MstpStatusBridgeEntry 4 }

cie1000MstpStatusBridgeTopologyChange OBJECT-TYPE
    SYNTAX      TruthValue
    MAX-ACCESS  read-only
    STATUS      current
    DESCRIPTION
        "Topology Change Flag current status"
    ::= { cie1000MstpStatusBridgeEntry 5 }

cie1000MstpStatusBridgeDesignatedRoot OBJECT-TYPE
    SYNTAX      OCTET STRING (SIZE(8))
    MAX-ACCESS  read-only
    STATUS      current
    DESCRIPTION
        "Designated Root Bridge"
    ::= { cie1000MstpStatusBridgeEntry 6 }

cie1000MstpStatusBridgeRootPathCost OBJECT-TYPE
    SYNTAX      Unsigned32
    MAX-ACCESS  read-only
    STATUS      current
    DESCRIPTION
        "Root Path Cost"
    ::= { cie1000MstpStatusBridgeEntry 7 }

cie1000MstpStatusBridgeRootPort OBJECT-TYPE
    SYNTAX      Unsigned32
    MAX-ACCESS  read-only
    STATUS      current
    DESCRIPTION
        "Root Port"
    ::= { cie1000MstpStatusBridgeEntry 8 }

cie1000MstpStatusBridgeMaxAge OBJECT-TYPE
    SYNTAX      Unsigned32
    MAX-ACCESS  read-only
    STATUS      current
    DESCRIPTION
        "Max Age, IEEE-802.1D-2004 sect 13.23.7"
    ::= { cie1000MstpStatusBridgeEntry 9 }

cie1000MstpStatusBridgeForwardDelay OBJECT-TYPE
    SYNTAX      Unsigned32
    MAX-ACCESS  read-only
    STATUS      current
    DESCRIPTION
        "Forward Delay, IEEE-802.1D-2004 sect 13.23.7"
    ::= { cie1000MstpStatusBridgeEntry 10 }

cie1000MstpStatusBridgeBridgeMaxAge OBJECT-TYPE
    SYNTAX      Unsigned32
    MAX-ACCESS  read-only
    STATUS      current
    DESCRIPTION
        "Bridge Max Age, IEEE-802.1D-2004 sect 13.23.4"
    ::= { cie1000MstpStatusBridgeEntry 11 }

cie1000MstpStatusBridgeBridgeHelloTime OBJECT-TYPE
    SYNTAX      Unsigned32
    MAX-ACCESS  read-only
    STATUS      current
    DESCRIPTION
        "Bridge Hello Time, IEEE-802.1D-2004 sect 13.23.4"
    ::= { cie1000MstpStatusBridgeEntry 12 }

cie1000MstpStatusBridgeBridgeForwardDelay OBJECT-TYPE
    SYNTAX      Unsigned32
    MAX-ACCESS  read-only
    STATUS      current
    DESCRIPTION
        "Bridge Forward Delay, IEEE-802.1D-2004 sect 13.23.4"
    ::= { cie1000MstpStatusBridgeEntry 13 }

cie1000MstpStatusBridgeTxHoldCount OBJECT-TYPE
    SYNTAX      Unsigned32
    MAX-ACCESS  read-only
    STATUS      current
    DESCRIPTION
        "Hold Time / Transmission Limit, IEEE-802.1D-2004 sect 13.22"
    ::= { cie1000MstpStatusBridgeEntry 14 }

cie1000MstpStatusBridgeForceVersion OBJECT-TYPE
    SYNTAX      CIE1000MSTPForceVersion
    MAX-ACCESS  read-only
    STATUS      current
    DESCRIPTION
        "Value of the Force Protocol Version parameter - IEEE-802.1D-2004 sect
         17.16.1"
    ::= { cie1000MstpStatusBridgeEntry 15 }

cie1000MstpStatusBridgeCistRegionalRoot OBJECT-TYPE
    SYNTAX      OCTET STRING (SIZE(8))
    MAX-ACCESS  read-only
    STATUS      current
    DESCRIPTION
        "CIST Regional Root Identifier (13.16.4)"
    ::= { cie1000MstpStatusBridgeEntry 16 }

cie1000MstpStatusBridgeCistInternalPathCost OBJECT-TYPE
    SYNTAX      Unsigned32
    MAX-ACCESS  read-only
    STATUS      current
    DESCRIPTION
        "CIST Path Cost"
    ::= { cie1000MstpStatusBridgeEntry 17 }

cie1000MstpStatusBridgeMaxHops OBJECT-TYPE
    SYNTAX      CIE1000Unsigned8
    MAX-ACCESS  read-only
    STATUS      current
    DESCRIPTION
        "MaxHops (13.22.1)"
    ::= { cie1000MstpStatusBridgeEntry 18 }

cie1000MstpStatusInterfaceTable OBJECT-TYPE
    SYNTAX      SEQUENCE OF CIE1000MstpStatusInterfaceEntry
    MAX-ACCESS  not-accessible
    STATUS      current
    DESCRIPTION
        "This table represent the status of the interface instances"
    ::= { cie1000MstpStatus 2 }

cie1000MstpStatusInterfaceEntry OBJECT-TYPE
    SYNTAX      CIE1000MstpStatusInterfaceEntry
    MAX-ACCESS  not-accessible
    STATUS      current
    DESCRIPTION
        "A MSTP interface instance set of status objects"
    INDEX       { cie1000MstpStatusInterfaceInterfaceNo,
                  cie1000MstpStatusInterfaceInstance }
    ::= { cie1000MstpStatusInterfaceTable 1 }

CIE1000MstpStatusInterfaceEntry ::= SEQUENCE {
    cie1000MstpStatusInterfaceInterfaceNo           CIE1000InterfaceIndex,
    cie1000MstpStatusInterfaceInstance              Integer32,
    cie1000MstpStatusInterfaceEnabled               TruthValue,
    cie1000MstpStatusInterfaceActive                TruthValue,
    cie1000MstpStatusInterfaceParentPort            Unsigned32,
    cie1000MstpStatusInterfaceUpTime                Unsigned32,
    cie1000MstpStatusInterfacePortState             CIE1000MstpPortState,
    cie1000MstpStatusInterfacePortId                OCTET STRING,
    cie1000MstpStatusInterfacePathCost              Unsigned32,
    cie1000MstpStatusInterfaceDesignatedRoot        OCTET STRING,
    cie1000MstpStatusInterfaceDesignatedCost        Unsigned32,
    cie1000MstpStatusInterfaceDesignatedBridge      OCTET STRING,
    cie1000MstpStatusInterfaceDesignatedPort        OCTET STRING,
    cie1000MstpStatusInterfaceTcAck                 TruthValue,
    cie1000MstpStatusInterfaceHelloTime             Unsigned32,
    cie1000MstpStatusInterfaceAdminEdgePort         TruthValue,
    cie1000MstpStatusInterfaceOperEdgePort          TruthValue,
    cie1000MstpStatusInterfaceAutoEdgePort          TruthValue,
    cie1000MstpStatusInterfaceMacOperational        TruthValue,
    cie1000MstpStatusInterfaceAdminPointToPointMAC  CIE1000MstpPoint2Point,
    cie1000MstpStatusInterfaceOperPointToPointMAC   TruthValue,
    cie1000MstpStatusInterfaceRestrictedRole        TruthValue,
    cie1000MstpStatusInterfaceRestrictedTcn         TruthValue,
    cie1000MstpStatusInterfacePortRole              CIE1000DisplayString,
    cie1000MstpStatusInterfaceDisputed              TruthValue
}

cie1000MstpStatusInterfaceInterfaceNo OBJECT-TYPE
    SYNTAX      CIE1000InterfaceIndex
    MAX-ACCESS  accessible-for-notify
    STATUS      current
    DESCRIPTION
        "Logical interface number."
    ::= { cie1000MstpStatusInterfaceEntry 1 }

cie1000MstpStatusInterfaceInstance OBJECT-TYPE
    SYNTAX      Integer32 (0..255)
    MAX-ACCESS  accessible-for-notify
    STATUS      current
    DESCRIPTION
        "Bridge instance number. The CIST = 0, MSTI1 = 1, etc"
    ::= { cie1000MstpStatusInterfaceEntry 2 }

cie1000MstpStatusInterfaceEnabled OBJECT-TYPE
    SYNTAX      TruthValue
    MAX-ACCESS  read-only
    STATUS      current
    DESCRIPTION
        "Whether port is controlled by xSTP"
    ::= { cie1000MstpStatusInterfaceEntry 3 }

cie1000MstpStatusInterfaceActive OBJECT-TYPE
    SYNTAX      TruthValue
    MAX-ACCESS  read-only
    STATUS      current
    DESCRIPTION
        "Whether port is active"
    ::= { cie1000MstpStatusInterfaceEntry 4 }

cie1000MstpStatusInterfaceParentPort OBJECT-TYPE
    SYNTAX      Unsigned32
    MAX-ACCESS  read-only
    STATUS      current
    DESCRIPTION
        "Parent port if physical port is aggregated. (Otherwise 0xffff)"
    ::= { cie1000MstpStatusInterfaceEntry 5 }

cie1000MstpStatusInterfaceUpTime OBJECT-TYPE
    SYNTAX      Unsigned32
    MAX-ACCESS  read-only
    STATUS      current
    DESCRIPTION
        "seconds of the time elapsed since the Port was last reset or
         initialized"
    ::= { cie1000MstpStatusInterfaceEntry 6 }

cie1000MstpStatusInterfacePortState OBJECT-TYPE
    SYNTAX      CIE1000MstpPortState
    MAX-ACCESS  read-only
    STATUS      current
    DESCRIPTION
        "Current state of the Port"
    ::= { cie1000MstpStatusInterfaceEntry 7 }

cie1000MstpStatusInterfacePortId OBJECT-TYPE
    SYNTAX      OCTET STRING (SIZE(2))
    MAX-ACCESS  read-only
    STATUS      current
    DESCRIPTION
        "Unique Port identifier comprising two parts, the Port Number and the
         Port Priority field"
    ::= { cie1000MstpStatusInterfaceEntry 8 }

cie1000MstpStatusInterfacePathCost OBJECT-TYPE
    SYNTAX      Unsigned32
    MAX-ACCESS  read-only
    STATUS      current
    DESCRIPTION
        "Path Cost (17.16.5 of IEEE Std 802.1D)"
    ::= { cie1000MstpStatusInterfaceEntry 9 }

cie1000MstpStatusInterfaceDesignatedRoot OBJECT-TYPE
    SYNTAX      OCTET STRING (SIZE(8))
    MAX-ACCESS  read-only
    STATUS      current
    DESCRIPTION
        "Designated Root"
    ::= { cie1000MstpStatusInterfaceEntry 10 }

cie1000MstpStatusInterfaceDesignatedCost OBJECT-TYPE
    SYNTAX      Unsigned32
    MAX-ACCESS  read-only
    STATUS      current
    DESCRIPTION
        "Designated Cost"
    ::= { cie1000MstpStatusInterfaceEntry 11 }

cie1000MstpStatusInterfaceDesignatedBridge OBJECT-TYPE
    SYNTAX      OCTET STRING (SIZE(8))
    MAX-ACCESS  read-only
    STATUS      current
    DESCRIPTION
        "Designated Bridge"
    ::= { cie1000MstpStatusInterfaceEntry 12 }

cie1000MstpStatusInterfaceDesignatedPort OBJECT-TYPE
    SYNTAX      OCTET STRING (SIZE(2))
    MAX-ACCESS  read-only
    STATUS      current
    DESCRIPTION
        "Designated Port"
    ::= { cie1000MstpStatusInterfaceEntry 13 }

cie1000MstpStatusInterfaceTcAck OBJECT-TYPE
    SYNTAX      TruthValue
    MAX-ACCESS  read-only
    STATUS      current
    DESCRIPTION
        "Topology Change Acknowledge"
    ::= { cie1000MstpStatusInterfaceEntry 14 }

cie1000MstpStatusInterfaceHelloTime OBJECT-TYPE
    SYNTAX      Unsigned32
    MAX-ACCESS  read-only
    STATUS      current
    DESCRIPTION
        "Hello Time"
    ::= { cie1000MstpStatusInterfaceEntry 15 }

cie1000MstpStatusInterfaceAdminEdgePort OBJECT-TYPE
    SYNTAX      TruthValue
    MAX-ACCESS  read-only
    STATUS      current
    DESCRIPTION
        "adminEdgePort (18.3.3 of IEEE Std 802.1D)"
    ::= { cie1000MstpStatusInterfaceEntry 16 }

cie1000MstpStatusInterfaceOperEdgePort OBJECT-TYPE
    SYNTAX      TruthValue
    MAX-ACCESS  read-only
    STATUS      current
    DESCRIPTION
        "operEdgePort (18.3.4 of IEEE Std 802.1D)"
    ::= { cie1000MstpStatusInterfaceEntry 17 }

cie1000MstpStatusInterfaceAutoEdgePort OBJECT-TYPE
    SYNTAX      TruthValue
    MAX-ACCESS  read-only
    STATUS      current
    DESCRIPTION
        "autoEdgePort (17.13.3 of IEEE Std 802.1D)"
    ::= { cie1000MstpStatusInterfaceEntry 18 }

cie1000MstpStatusInterfaceMacOperational OBJECT-TYPE
    SYNTAX      TruthValue
    MAX-ACCESS  read-only
    STATUS      current
    DESCRIPTION
        "Current state of the MAC Operational parameter (6.4.2 of IEEE Std
         802.1D,)"
    ::= { cie1000MstpStatusInterfaceEntry 19 }

cie1000MstpStatusInterfaceAdminPointToPointMAC OBJECT-TYPE
    SYNTAX      CIE1000MstpPoint2Point
    MAX-ACCESS  read-only
    STATUS      current
    DESCRIPTION
        "Current state of the adminPointToPointMAC parameter (6.4.3 of IEEE Std
         802.1D)"
    ::= { cie1000MstpStatusInterfaceEntry 20 }

cie1000MstpStatusInterfaceOperPointToPointMAC OBJECT-TYPE
    SYNTAX      TruthValue
    MAX-ACCESS  read-only
    STATUS      current
    DESCRIPTION
        "Current state of the operPointToPointMAC parameter (6.4.3 of IEEE Std
         802.1D)"
    ::= { cie1000MstpStatusInterfaceEntry 21 }

cie1000MstpStatusInterfaceRestrictedRole OBJECT-TYPE
    SYNTAX      TruthValue
    MAX-ACCESS  read-only
    STATUS      current
    DESCRIPTION
        "Current state of the restrictedRole parameter for the Port (13.25.14)"
    ::= { cie1000MstpStatusInterfaceEntry 22 }

cie1000MstpStatusInterfaceRestrictedTcn OBJECT-TYPE
    SYNTAX      TruthValue
    MAX-ACCESS  read-only
    STATUS      current
    DESCRIPTION
        "Current state of the restrictedTcn parameter for the Port (13.25.15)"
    ::= { cie1000MstpStatusInterfaceEntry 23 }

cie1000MstpStatusInterfacePortRole OBJECT-TYPE
    SYNTAX      CIE1000DisplayString (SIZE(0..15))
    MAX-ACCESS  read-only
    STATUS      current
    DESCRIPTION
        "Current Port Role"
    ::= { cie1000MstpStatusInterfaceEntry 24 }

cie1000MstpStatusInterfaceDisputed OBJECT-TYPE
    SYNTAX      TruthValue
    MAX-ACCESS  read-only
    STATUS      current
    DESCRIPTION
        "Current value of the disputed variable for the CIST Port"
    ::= { cie1000MstpStatusInterfaceEntry 25 }

cie1000MstpStatusInterfaceStatisticsTable OBJECT-TYPE
    SYNTAX      SEQUENCE OF CIE1000MstpStatusInterfaceStatisticsEntry
    MAX-ACCESS  not-accessible
    STATUS      current
    DESCRIPTION
        "This table represent the statistics of the CIST interfaces"
    ::= { cie1000MstpStatus 3 }

cie1000MstpStatusInterfaceStatisticsEntry OBJECT-TYPE
    SYNTAX      CIE1000MstpStatusInterfaceStatisticsEntry
    MAX-ACCESS  not-accessible
    STATUS      current
    DESCRIPTION
        "A CIST interface set of statistics"
    INDEX       { cie1000MstpStatusInterfaceStatisticsInterfaceNo }
    ::= { cie1000MstpStatusInterfaceStatisticsTable 1 }

CIE1000MstpStatusInterfaceStatisticsEntry ::= SEQUENCE {
    cie1000MstpStatusInterfaceStatisticsInterfaceNo            CIE1000InterfaceIndex,
    cie1000MstpStatusInterfaceStatisticsStpFrameXmits          Unsigned32,
    cie1000MstpStatusInterfaceStatisticsStpFrameReceived       Unsigned32,
    cie1000MstpStatusInterfaceStatisticsRstpFrameXmits         Unsigned32,
    cie1000MstpStatusInterfaceStatisticsRstpFrameReceived      Unsigned32,
    cie1000MstpStatusInterfaceStatisticsMstpFrameXmits         Unsigned32,
    cie1000MstpStatusInterfaceStatisticsMstpFrameReceived      Unsigned32,
    cie1000MstpStatusInterfaceStatisticsUnknownFramesReceived  Unsigned32,
    cie1000MstpStatusInterfaceStatisticsIllegalFrameReceived   Unsigned32,
    cie1000MstpStatusInterfaceStatisticsTcnFrameXmits          Unsigned32,
    cie1000MstpStatusInterfaceStatisticsTcnFrameReceived       Unsigned32
}

cie1000MstpStatusInterfaceStatisticsInterfaceNo OBJECT-TYPE
    SYNTAX      CIE1000InterfaceIndex
    MAX-ACCESS  accessible-for-notify
    STATUS      current
    DESCRIPTION
        "Logical interface number."
    ::= { cie1000MstpStatusInterfaceStatisticsEntry 1 }

cie1000MstpStatusInterfaceStatisticsStpFrameXmits OBJECT-TYPE
    SYNTAX      Unsigned32
    MAX-ACCESS  read-only
    STATUS      current
    DESCRIPTION
        "Number of STP frames transmitted"
    ::= { cie1000MstpStatusInterfaceStatisticsEntry 2 }

cie1000MstpStatusInterfaceStatisticsStpFrameReceived OBJECT-TYPE
    SYNTAX      Unsigned32
    MAX-ACCESS  read-only
    STATUS      current
    DESCRIPTION
        "Number of STP frames received"
    ::= { cie1000MstpStatusInterfaceStatisticsEntry 3 }

cie1000MstpStatusInterfaceStatisticsRstpFrameXmits OBJECT-TYPE
    SYNTAX      Unsigned32
    MAX-ACCESS  read-only
    STATUS      current
    DESCRIPTION
        "Number of RSTP frames transmitted"
    ::= { cie1000MstpStatusInterfaceStatisticsEntry 4 }

cie1000MstpStatusInterfaceStatisticsRstpFrameReceived OBJECT-TYPE
    SYNTAX      Unsigned32
    MAX-ACCESS  read-only
    STATUS      current
    DESCRIPTION
        "Number of RSTP frames received"
    ::= { cie1000MstpStatusInterfaceStatisticsEntry 5 }

cie1000MstpStatusInterfaceStatisticsMstpFrameXmits OBJECT-TYPE
    SYNTAX      Unsigned32
    MAX-ACCESS  read-only
    STATUS      current
    DESCRIPTION
        "Number of MSTP frames transmitted"
    ::= { cie1000MstpStatusInterfaceStatisticsEntry 6 }

cie1000MstpStatusInterfaceStatisticsMstpFrameReceived OBJECT-TYPE
    SYNTAX      Unsigned32
    MAX-ACCESS  read-only
    STATUS      current
    DESCRIPTION
        "Number of MSTP frames received"
    ::= { cie1000MstpStatusInterfaceStatisticsEntry 7 }

cie1000MstpStatusInterfaceStatisticsUnknownFramesReceived OBJECT-TYPE
    SYNTAX      Unsigned32
    MAX-ACCESS  read-only
    STATUS      current
    DESCRIPTION
        "Number of unknown frames received and discarded in error"
    ::= { cie1000MstpStatusInterfaceStatisticsEntry 8 }

cie1000MstpStatusInterfaceStatisticsIllegalFrameReceived OBJECT-TYPE
    SYNTAX      Unsigned32
    MAX-ACCESS  read-only
    STATUS      current
    DESCRIPTION
        "Number of illegal frames received and discarded in error"
    ::= { cie1000MstpStatusInterfaceStatisticsEntry 9 }

cie1000MstpStatusInterfaceStatisticsTcnFrameXmits OBJECT-TYPE
    SYNTAX      Unsigned32
    MAX-ACCESS  read-only
    STATUS      current
    DESCRIPTION
        "Number of TCN frames transmitted"
    ::= { cie1000MstpStatusInterfaceStatisticsEntry 10 }

cie1000MstpStatusInterfaceStatisticsTcnFrameReceived OBJECT-TYPE
    SYNTAX      Unsigned32
    MAX-ACCESS  read-only
    STATUS      current
    DESCRIPTION
        "Number of TCN frames received"
    ::= { cie1000MstpStatusInterfaceStatisticsEntry 11 }

cie1000MstpMibConformance OBJECT IDENTIFIER
    ::= { cie1000MstpMib 2 }

cie1000MstpMibCompliances OBJECT IDENTIFIER
    ::= { cie1000MstpMibConformance 1 }

cie1000MstpMibGroups OBJECT IDENTIFIER
    ::= { cie1000MstpMibConformance 2 }

cie1000MstpConfigBridgeParamsInfoGroup OBJECT-GROUP
    OBJECTS     { cie1000MstpConfigBridgeParamsBridgeMaxAge,
                  cie1000MstpConfigBridgeParamsBridgeHelloTime,
                  cie1000MstpConfigBridgeParamsBridgeForwardDelay,
                  cie1000MstpConfigBridgeParamsForceVersion,
                  cie1000MstpConfigBridgeParamsTxHoldCount,
                  cie1000MstpConfigBridgeParamsMaxHops,
                  cie1000MstpConfigBridgeParamsBpduFiltering,
                  cie1000MstpConfigBridgeParamsBpduGuard,
                  cie1000MstpConfigBridgeParamsErrorRecoveryDelay }
    STATUS      current
    DESCRIPTION
        "A collection of objects."
    ::= { cie1000MstpMibGroups 1 }

cie1000MstpConfigMstiParamTableInfoGroup OBJECT-GROUP
    OBJECTS     { cie1000MstpConfigMstiParamInstance,
                  cie1000MstpConfigMstiParamPriority }
    STATUS      current
    DESCRIPTION
        "A collection of objects."
    ::= { cie1000MstpMibGroups 2 }

cie1000MstpConfigMstiConfigIdInfoGroup OBJECT-GROUP
    OBJECTS     { cie1000MstpConfigMstiConfigIdName,
                  cie1000MstpConfigMstiConfigIdRevision }
    STATUS      current
    DESCRIPTION
        "A collection of objects."
    ::= { cie1000MstpMibGroups 3 }

cie1000MstpConfigMstiConfigTableInfoGroup OBJECT-GROUP
    OBJECTS     { cie1000MstpConfigMstiConfigVid,
                  cie1000MstpConfigMstiConfigMstid }
    STATUS      current
    DESCRIPTION
        "A collection of objects."
    ::= { cie1000MstpMibGroups 4 }

cie1000MstpConfigMstiConfigVlanBitmapTableInfoGroup OBJECT-GROUP
    OBJECTS     { cie1000MstpConfigMstiConfigVlanBitmapMstiValue,
                  cie1000MstpConfigMstiConfigVlanBitmapAccessVlans0To1K,
                  cie1000MstpConfigMstiConfigVlanBitmapAccessVlans1KTo2K,
                  cie1000MstpConfigMstiConfigVlanBitmapAccessVlans2KTo3K,
                  cie1000MstpConfigMstiConfigVlanBitmapAccessVlans3KTo4K }
    STATUS      current
    DESCRIPTION
        "A collection of objects."
    ::= { cie1000MstpMibGroups 5 }

cie1000MstpConfigCistInterfaceParamTableInfoGroup OBJECT-GROUP
    OBJECTS     { cie1000MstpConfigCistInterfaceParamInterfaceNo,
                  cie1000MstpConfigCistInterfaceParamEnable,
                  cie1000MstpConfigCistInterfaceParamAdminEdgePort,
                  cie1000MstpConfigCistInterfaceParamAdminAutoEdgePort,
                  cie1000MstpConfigCistInterfaceParamAdminPointToPointMAC,
                  cie1000MstpConfigCistInterfaceParamRestrictedRole,
                  cie1000MstpConfigCistInterfaceParamRestrictedTcn,
                  cie1000MstpConfigCistInterfaceParamBpduGuard }
    STATUS      current
    DESCRIPTION
        "A collection of objects."
    ::= { cie1000MstpMibGroups 6 }

cie1000MstpConfigAggrParamsInfoGroup OBJECT-GROUP
    OBJECTS     { cie1000MstpConfigAggrParamsEnable,
                  cie1000MstpConfigAggrParamsAdminEdgePort,
                  cie1000MstpConfigAggrParamsAdminAutoEdgePort,
                  cie1000MstpConfigAggrParamsAdminPointToPointMAC,
                  cie1000MstpConfigAggrParamsRestrictedRole,
                  cie1000MstpConfigAggrParamsRestrictedTcn,
                  cie1000MstpConfigAggrParamsBpduGuard }
    STATUS      current
    DESCRIPTION
        "A collection of objects."
    ::= { cie1000MstpMibGroups 7 }

cie1000MstpConfigMstiInterfaceParamTableInfoGroup OBJECT-GROUP
    OBJECTS     { cie1000MstpConfigMstiInterfaceParamInterfaceNo,
                  cie1000MstpConfigMstiInterfaceParamInstance,
                  cie1000MstpConfigMstiInterfaceParamAdminPathCost,
                  cie1000MstpConfigMstiInterfaceParamAdminPortPriority }
    STATUS      current
    DESCRIPTION
        "A collection of objects."
    ::= { cie1000MstpMibGroups 8 }

cie1000MstpConfigMstiAggrParamTableInfoGroup OBJECT-GROUP
    OBJECTS     { cie1000MstpConfigMstiAggrParamInstance,
                  cie1000MstpConfigMstiAggrParamAdminPathCost,
                  cie1000MstpConfigMstiAggrParamAdminPortPriority }
    STATUS      current
    DESCRIPTION
        "A collection of objects."
    ::= { cie1000MstpMibGroups 9 }

cie1000MstpStatusBridgeTableInfoGroup OBJECT-GROUP
    OBJECTS     { cie1000MstpStatusBridgeInstance,
                  cie1000MstpStatusBridgeBridgeId,
                  cie1000MstpStatusBridgeTimeSinceTopologyChange,
                  cie1000MstpStatusBridgeTopologyChangeCount,
                  cie1000MstpStatusBridgeTopologyChange,
                  cie1000MstpStatusBridgeDesignatedRoot,
                  cie1000MstpStatusBridgeRootPathCost,
                  cie1000MstpStatusBridgeRootPort,
                  cie1000MstpStatusBridgeMaxAge,
                  cie1000MstpStatusBridgeForwardDelay,
                  cie1000MstpStatusBridgeBridgeMaxAge,
                  cie1000MstpStatusBridgeBridgeHelloTime,
                  cie1000MstpStatusBridgeBridgeForwardDelay,
                  cie1000MstpStatusBridgeTxHoldCount,
                  cie1000MstpStatusBridgeForceVersion,
                  cie1000MstpStatusBridgeCistRegionalRoot,
                  cie1000MstpStatusBridgeCistInternalPathCost,
                  cie1000MstpStatusBridgeMaxHops }
    STATUS      current
    DESCRIPTION
        "A collection of objects."
    ::= { cie1000MstpMibGroups 10 }

cie1000MstpStatusInterfaceTableInfoGroup OBJECT-GROUP
    OBJECTS     { cie1000MstpStatusInterfaceInterfaceNo,
                  cie1000MstpStatusInterfaceInstance,
                  cie1000MstpStatusInterfaceEnabled,
                  cie1000MstpStatusInterfaceActive,
                  cie1000MstpStatusInterfaceParentPort,
                  cie1000MstpStatusInterfaceUpTime,
                  cie1000MstpStatusInterfacePortState,
                  cie1000MstpStatusInterfacePortId,
                  cie1000MstpStatusInterfacePathCost,
                  cie1000MstpStatusInterfaceDesignatedRoot,
                  cie1000MstpStatusInterfaceDesignatedCost,
                  cie1000MstpStatusInterfaceDesignatedBridge,
                  cie1000MstpStatusInterfaceDesignatedPort,
                  cie1000MstpStatusInterfaceTcAck,
                  cie1000MstpStatusInterfaceHelloTime,
                  cie1000MstpStatusInterfaceAdminEdgePort,
                  cie1000MstpStatusInterfaceOperEdgePort,
                  cie1000MstpStatusInterfaceAutoEdgePort,
                  cie1000MstpStatusInterfaceMacOperational,
                  cie1000MstpStatusInterfaceAdminPointToPointMAC,
                  cie1000MstpStatusInterfaceOperPointToPointMAC,
                  cie1000MstpStatusInterfaceRestrictedRole,
                  cie1000MstpStatusInterfaceRestrictedTcn,
                  cie1000MstpStatusInterfacePortRole,
                  cie1000MstpStatusInterfaceDisputed }
    STATUS      current
    DESCRIPTION
        "A collection of objects."
    ::= { cie1000MstpMibGroups 11 }

cie1000MstpStatusInterfaceStatisticsTableInfoGroup OBJECT-GROUP
    OBJECTS     { cie1000MstpStatusInterfaceStatisticsInterfaceNo,
                  cie1000MstpStatusInterfaceStatisticsStpFrameXmits,
                  cie1000MstpStatusInterfaceStatisticsStpFrameReceived,
                  cie1000MstpStatusInterfaceStatisticsRstpFrameXmits,
                  cie1000MstpStatusInterfaceStatisticsRstpFrameReceived,
                  cie1000MstpStatusInterfaceStatisticsMstpFrameXmits,
                  cie1000MstpStatusInterfaceStatisticsMstpFrameReceived,
                  cie1000MstpStatusInterfaceStatisticsUnknownFramesReceived,
                  cie1000MstpStatusInterfaceStatisticsIllegalFrameReceived,
                  cie1000MstpStatusInterfaceStatisticsTcnFrameXmits,
                  cie1000MstpStatusInterfaceStatisticsTcnFrameReceived }
    STATUS      current
    DESCRIPTION
        "A collection of objects."
    ::= { cie1000MstpMibGroups 12 }

cie1000MstpMibCompliance MODULE-COMPLIANCE
    STATUS      current
    DESCRIPTION
        "The compliance statement for the implementation."

    MODULE      -- this module

    MANDATORY-GROUPS { cie1000MstpConfigBridgeParamsInfoGroup,
                       cie1000MstpConfigMstiParamTableInfoGroup,
                       cie1000MstpConfigMstiConfigIdInfoGroup,
                       cie1000MstpConfigMstiConfigTableInfoGroup,
                       cie1000MstpConfigMstiConfigVlanBitmapTableInfoGroup,
                       cie1000MstpConfigCistInterfaceParamTableInfoGroup,
                       cie1000MstpConfigAggrParamsInfoGroup,
                       cie1000MstpConfigMstiInterfaceParamTableInfoGroup,
                       cie1000MstpConfigMstiAggrParamTableInfoGroup,
                       cie1000MstpStatusBridgeTableInfoGroup,
                       cie1000MstpStatusInterfaceTableInfoGroup,
                       cie1000MstpStatusInterfaceStatisticsTableInfoGroup }

    ::= { cie1000MstpMibCompliances 1 }

END
