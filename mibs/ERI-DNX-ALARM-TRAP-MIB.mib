ERI-DNX-ALARM-TRAP-MIB DEFINITIONS ::= BEGIN

IMPORTS
	MODULE-IDENTITY, NOTIFICATION-TYPE
	    FROM SNMPv2-SMI
    eriMibs
        FROM ERI-ROOT-SMI
	trapSequence, trapResourceKey, trapTime,
	trapResourceAddress, trapResourceType, trapType, 
	trapState, trapSeverity, dnxTrapEnterprise
		FROM ERI-DNX-SMC-MIB;

eriDNXAlarmTrapMIB MODULE-IDENTITY
      LAST-UPDATED    "200305060000Z"
      ORGANIZATION    "Eastern Research, Inc."
      CONTACT-INFO
                      "Customer Service
                Postal: Eastern Research, Inc.
                        225 Executive Drive
                        Moorestown, NJ 08057
                Phone:  +1-800-337-4374
                Email:  support@erinc.com"
      DESCRIPTION
              "The ERI Enterprise MIB Module for the DNX Alarm Traps."

      REVISION        "200305060000Z"
      DESCRIPTION
              "Nevio Poljak - eri_DnxRoot MIB Rev 2.1 (SW Rel. 15.2)
               Removed SMC Station Clock Traps which are no longer supported
               and added Stratum3 Device Trap which was missing.
               Added DS0DP InTest and TestOff Informational Events."

      REVISION        "200301100000Z"
      DESCRIPTION
              "Neeraj Bhatt - eri_DnxRoot MIB Rev 01.2
               Added a new trap for the Laser Off detection with major 
               Alarm Severity."

      REVISION        "200208200000Z"
      DESCRIPTION
              "Nevio Poljak - eri_DnxRoot MIB Rev 01.0
               Changed Alarm severity of Receiving AIS from Major to 
               Informational for T1/E1, HDS3, STS1, E3, and STM1/OC3 T1/E1.
               Added Informational Trap for Sa4 National Bit Match for all 
               E1 devices."

      REVISION        "200207030000Z"
      DESCRIPTION
              "Nevio Poljak - eri_DnxRoot MIB Rev 01.0
               Added Alarms for Dnx-1u Circuit Card missing and Optical
               Transport Overhead SF and SD detection.
               Removed Alarm for Dnx-1u Power Supply Rear card missing."

      REVISION        "200206050000Z"
      DESCRIPTION
              "Nevio Poljak - eri_DnxRoot MIB Rev 01.0
               Converted to SMIv2 format and Added New Dnx-1u Alarms
               and Event Traps."

      REVISION        "200204080000Z"
      DESCRIPTION
              "Nevio Poljak - Software Release 14.2
               Re-assigned Alarm severity of DBNotInSync & SlotMismatch
               to Minor."

      REVISION        "200203110000Z"
      DESCRIPTION
              "Nevio Poljak - Software Release 14.1
               Added Traps for Xlink Cable Mismatch Alarm and renamed
               Power Supply Not Present Events to Set/Clear Alarm Traps."

      REVISION        "200112050000Z"
      DESCRIPTION
              "Nevio Poljak - Software Release 14.0
               Added Traps for E3 Device Card Alarms and Events."

      REVISION        "200109300000Z"
      DESCRIPTION
              "Barry L. Bengel - Software Release 13.0
               Initial Release."

  	::= { eriMibs 12 }


-- *************************************************************************
--  Special Device Level Events used when device resets
-- *************************************************************************

evntDevColdStart NOTIFICATION-TYPE
        OBJECTS  {
            trapSequence,
            trapResourceKey,
            trapTime,
            trapResourceAddress,
            trapResourceType,
            trapType,
            trapState,
            trapSeverity
            }
        STATUS current
        DESCRIPTION
            "Informational event for a Device application module Cold
            start-up."
        ::= { dnxTrapEnterprise 1 }

evntDevWarmStart NOTIFICATION-TYPE
        OBJECTS  {
            trapSequence,
            trapResourceKey,
            trapTime,
            trapResourceAddress,
            trapResourceType,
            trapType,
            trapState,
            trapSeverity
            }
        STATUS current
        DESCRIPTION
            "Informational event for a Device application module Warm reset."
        ::= { dnxTrapEnterprise 2 }

-- *************************************************************************
--  Slot Level Alarms/Events; base = 100
-- *************************************************************************

setSlotMismatch NOTIFICATION-TYPE
        OBJECTS  {
            trapSequence,
            trapResourceKey,
            trapTime,
            trapResourceAddress,
            trapResourceType,
            trapType,
            trapState,
            trapSeverity
            }
        STATUS current
        DESCRIPTION
            "Minor Alarm for a slot configuration mismatch."
        ::= { dnxTrapEnterprise 101 }

setSlotMissing NOTIFICATION-TYPE
        OBJECTS  {
            trapSequence,
            trapResourceKey,
            trapTime,
            trapResourceAddress,
            trapResourceType,
            trapType,
            trapState,
            trapSeverity
            }
        STATUS current
        DESCRIPTION
            "Critical Alarm for an empty slot."
        ::= { dnxTrapEnterprise 102 }

clearSlotMismatch NOTIFICATION-TYPE
        OBJECTS  {
            trapSequence,
            trapResourceKey,
            trapTime,
            trapResourceAddress,
            trapResourceType,
            trapType,
            trapState,
            trapSeverity
            }
        STATUS current
        DESCRIPTION
            "Clears the Minor Alarm for slot config mismatch."
        ::= { dnxTrapEnterprise 141 }

clearSlotMissing NOTIFICATION-TYPE
        OBJECTS  {
            trapSequence,
            trapResourceKey,
            trapTime,
            trapResourceAddress,
            trapResourceType,
            trapType,
            trapState,
            trapSeverity
            }
        STATUS current
        DESCRIPTION
            "Clears the Critical Alarm for slot missing."
        ::= { dnxTrapEnterprise 142 }

-- *************************************************************************
--  Device Level Alarms/Events; base = 200
-- *************************************************************************

evntDevOnline NOTIFICATION-TYPE
        OBJECTS  {
            trapSequence,
            trapResourceKey,
            trapTime,
            trapResourceAddress,
            trapResourceType,
            trapType,
            trapState,
            trapSeverity
            }
        STATUS current
        DESCRIPTION
            "Informational Event for Device reporting Online state."
        ::= { dnxTrapEnterprise 201 }

evntDevStandby NOTIFICATION-TYPE
        OBJECTS  {
            trapSequence,
            trapResourceKey,
            trapTime,
            trapResourceAddress,
            trapResourceType,
            trapType,
            trapState,
            trapSeverity
            }
        STATUS current
        DESCRIPTION
            "Informational Event for Device reporting Standby state."
        ::= { dnxTrapEnterprise 202 }

setDevFrameSyncNotPresent NOTIFICATION-TYPE
        OBJECTS  {
            trapSequence,
            trapResourceKey,
            trapTime,
            trapResourceAddress,
            trapResourceType,
            trapType,
            trapState,
            trapSeverity
            }
        STATUS current
        DESCRIPTION
            "Critical Alarm for Device without Frame Sync pulse."
        ::= { dnxTrapEnterprise 203 }

setDevSystemClockNotPresent NOTIFICATION-TYPE
        OBJECTS  {
            trapSequence,
            trapResourceKey,
            trapTime,
            trapResourceAddress,
            trapResourceType,
            trapType,
            trapState,
            trapSeverity
            }
        STATUS current
        DESCRIPTION
            "Critical Alarm for Device that lost system clock."
        ::= { dnxTrapEnterprise 204 }

setDevDataBaseNotInsync NOTIFICATION-TYPE
        OBJECTS  {
            trapSequence,
            trapResourceKey,
            trapTime,
            trapResourceAddress,
            trapResourceType,
            trapType,
            trapState,
            trapSeverity
            }
        STATUS current
        DESCRIPTION
            "Minor Alarm for system manager (SMC/XNM) configuration DB out
             of sync with redundant system manager."
        ::= { dnxTrapEnterprise 206 }

setDevFreeRunError NOTIFICATION-TYPE
        OBJECTS  {
            trapSequence,
            trapResourceKey,
            trapTime,
            trapResourceAddress,
            trapResourceType,
            trapType,
            trapState,
            trapSeverity
            }
        STATUS current
        DESCRIPTION
            "Critical Alarm for Device clock freerun error."
        ::= { dnxTrapEnterprise 207 }

setDevOffline NOTIFICATION-TYPE
        OBJECTS  {
            trapSequence,
            trapResourceKey,
            trapTime,
            trapResourceAddress,
            trapResourceType,
            trapType,
            trapState,
            trapSeverity
            }
        STATUS current
        DESCRIPTION
            "Critical Alarm for Device in offline state."
        ::= { dnxTrapEnterprise 208 }

setDevDefective NOTIFICATION-TYPE
        OBJECTS  {
            trapSequence,
            trapResourceKey,
            trapTime,
            trapResourceAddress,
            trapResourceType,
            trapType,
            trapState,
            trapSeverity
            }
        STATUS current
        DESCRIPTION
            "Critical Alarm for defective Device module."
        ::= { dnxTrapEnterprise 209 }

setDevBusError NOTIFICATION-TYPE
        OBJECTS  {
            trapSequence,
            trapResourceKey,
            trapTime,
            trapResourceAddress,
            trapResourceType,
            trapType,
            trapState,
            trapSeverity
            }
        STATUS current
        DESCRIPTION
            "Critical Alarm for Device with supervisory bus communications
             problem."
        ::= { dnxTrapEnterprise 210 }

setDevStratum3ClkFailure NOTIFICATION-TYPE
        OBJECTS  {
            trapSequence,
            trapResourceKey,
            trapTime,
            trapResourceAddress,
            trapResourceType,
            trapType,
            trapState,
            trapSeverity
            }
        STATUS current
        DESCRIPTION
            "Critical Alarm for SMC Device with loss of Stratum3 Clock."
        ::= { dnxTrapEnterprise 216 }

setDevCircuitCardMissing NOTIFICATION-TYPE
        OBJECTS  {
            trapSequence,
            trapResourceKey,
            trapTime,
            trapResourceAddress,
            trapResourceType,
            trapType,
            trapState,
            trapSeverity
            }
        STATUS current
        DESCRIPTION
            "Critical Alarm for Device with missing hardware."
        ::= { dnxTrapEnterprise 219 }

setDevConfigError NOTIFICATION-TYPE
        OBJECTS  {
            trapSequence,
            trapResourceKey,
            trapTime,
            trapResourceAddress,
            trapResourceType,
            trapType,
            trapState,
            trapSeverity
            }
        STATUS current
        DESCRIPTION
            "Major Alarm for Device configuration error."
        ::= { dnxTrapEnterprise 225 }

setDevNoRearCard NOTIFICATION-TYPE
        OBJECTS  {
            trapSequence,
            trapResourceKey,
            trapTime,
            trapResourceAddress,
            trapResourceType,
            trapType,
            trapState,
            trapSeverity
            }
        STATUS current
        DESCRIPTION
            "Critical Alarm for Device that cannot detect rear card."
        ::= { dnxTrapEnterprise 228 }

evntDevOutOfService NOTIFICATION-TYPE
        OBJECTS  {
            trapSequence,
            trapResourceKey,
            trapTime,
            trapResourceAddress,
            trapResourceType,
            trapType,
            trapState,
            trapSeverity
            }
        STATUS current
        DESCRIPTION
            "Informational Event for Device reporting Out-Of-Service state."
        ::= { dnxTrapEnterprise 231 }

evntDevNotOnline NOTIFICATION-TYPE
        OBJECTS  {
            trapSequence,
            trapResourceKey,
            trapTime,
            trapResourceAddress,
            trapResourceType,
            trapType,
            trapState,
            trapSeverity
            }
        STATUS current
        DESCRIPTION
            "Informational Event for Device transition from Online state
             to some other state."
        ::= { dnxTrapEnterprise 241 }

evntDevNotStandby NOTIFICATION-TYPE
        OBJECTS  {
            trapSequence,
            trapResourceKey,
            trapTime,
            trapResourceAddress,
            trapResourceType,
            trapType,
            trapState,
            trapSeverity
            }
        STATUS current
        DESCRIPTION
            "Informational Event for Device transition from Standby state
             to some other state."
        ::= { dnxTrapEnterprise 242 }

clearDevFrameSyncNotPresent NOTIFICATION-TYPE
        OBJECTS  {
            trapSequence,
            trapResourceKey,
            trapTime,
            trapResourceAddress,
            trapResourceType,
            trapType,
            trapState,
            trapSeverity
            }
        STATUS current
        DESCRIPTION
            "Clears the Critical Alarm for Device without Frame Sync pulse."
        ::= { dnxTrapEnterprise 243 }

clearDevSystemClockNotPresent NOTIFICATION-TYPE
        OBJECTS  {
            trapSequence,
            trapResourceKey,
            trapTime,
            trapResourceAddress,
            trapResourceType,
            trapType,
            trapState,
            trapSeverity
            }
        STATUS current
        DESCRIPTION
            "Clears the Critical Alarm for Device that lost system clock."
        ::= { dnxTrapEnterprise 244 }

clearDevDataBaseNotInsync NOTIFICATION-TYPE
        OBJECTS  {
            trapSequence,
            trapResourceKey,
            trapTime,
            trapResourceAddress,
            trapResourceType,
            trapType,
            trapState,
            trapSeverity
            }
        STATUS current
        DESCRIPTION
            "Clears the Minor Alarm for system manager (SMC/XNM)
            configuration DB out of sync with redundant system manager."
        ::= { dnxTrapEnterprise 246 }

clearDevFreeRunError NOTIFICATION-TYPE
        OBJECTS  {
            trapSequence,
            trapResourceKey,
            trapTime,
            trapResourceAddress,
            trapResourceType,
            trapType,
            trapState,
            trapSeverity
            }
        STATUS current
        DESCRIPTION
            "Clears the Critical Alarm for Device clock freerun error."
        ::= { dnxTrapEnterprise 247 }

clearDevOffline NOTIFICATION-TYPE
        OBJECTS  {
            trapSequence,
            trapResourceKey,
            trapTime,
            trapResourceAddress,
            trapResourceType,
            trapType,
            trapState,
            trapSeverity
            }
        STATUS current
        DESCRIPTION
                "Clears the Critical Alarm for Device in an offline state."
        ::= { dnxTrapEnterprise 248 }

clearDevDefective NOTIFICATION-TYPE
        OBJECTS  {
            trapSequence,
            trapResourceKey,
            trapTime,
            trapResourceAddress,
            trapResourceType,
            trapType,
            trapState,
            trapSeverity
            }
        STATUS current
        DESCRIPTION
                "Clears the Critical Alarm for defective Device module."
        ::= { dnxTrapEnterprise 249 }

clearDevBusError NOTIFICATION-TYPE
        OBJECTS  {
            trapSequence,
            trapResourceKey,
            trapTime,
            trapResourceAddress,
            trapResourceType,
            trapType,
            trapState,
            trapSeverity
            }
        STATUS current
        DESCRIPTION
                "Clears the Critical Alarm for Device with supervisory bus
                 communications problem."
        ::= { dnxTrapEnterprise 250 }

clearDevStratum3ClkFailure NOTIFICATION-TYPE
        OBJECTS  {
            trapSequence,
            trapResourceKey,
            trapTime,
            trapResourceAddress,
            trapResourceType,
            trapType,
            trapState,
            trapSeverity
            }
        STATUS current
        DESCRIPTION
            "Clears the Critical Alarm for SMC Device with loss of Stratum3 Clock."
        ::= { dnxTrapEnterprise 256 }

clearDevCircuitCardMissing NOTIFICATION-TYPE
        OBJECTS  {
            trapSequence,
            trapResourceKey,
            trapTime,
            trapResourceAddress,
            trapResourceType,
            trapType,
            trapState,
            trapSeverity
            }
        STATUS current
        DESCRIPTION
            "Clears the Critical Alarm for Device with missing hardware."
        ::= { dnxTrapEnterprise 259 }

clearDevConfigError NOTIFICATION-TYPE
        OBJECTS  {
            trapSequence,
            trapResourceKey,
            trapTime,
            trapResourceAddress,
            trapResourceType,
            trapType,
            trapState,
            trapSeverity
            }
        STATUS current
        DESCRIPTION
                "Clears the Critical Alarm for Device configuration error."
        ::= { dnxTrapEnterprise 265 }

clearDevNoRearCard NOTIFICATION-TYPE
        OBJECTS  {
            trapSequence,
            trapResourceKey,
            trapTime,
            trapResourceAddress,
            trapResourceType,
            trapType,
            trapState,
            trapSeverity
            }
        STATUS current
        DESCRIPTION
                "Clears the Critical Alarm for Device that cannot detect
                 rear card."
        ::= { dnxTrapEnterprise 268 }

evntDevInService NOTIFICATION-TYPE
        OBJECTS  {
            trapSequence,
            trapResourceKey,
            trapTime,
            trapResourceAddress,
            trapResourceType,
            trapType,
            trapState,
            trapSeverity
            }
        STATUS current
        DESCRIPTION
            "Informational Event for Device reporting In Service state."
        ::= { dnxTrapEnterprise 271 }

-- *************************************************************************
--  T1/E1 Port Level Alarms/Events; base = 300
-- *************************************************************************

setT1E1RcvFarEndLOF NOTIFICATION-TYPE
        OBJECTS  {
            trapSequence,
            trapResourceKey,
            trapTime,
            trapResourceAddress,
            trapResourceType,
            trapType,
            trapState,
            trapSeverity
            }
        STATUS current
        DESCRIPTION
            "Major Alarm for receiving far end loss of frame (receiving
            yellow alarm)."
        ::= { dnxTrapEnterprise 301 }

setT1E1NearEndSendLOF NOTIFICATION-TYPE
        OBJECTS  {
            trapSequence,
            trapResourceKey,
            trapTime,
            trapResourceAddress,
            trapResourceType,
            trapType,
            trapState,
            trapSeverity
            }
        STATUS current
        DESCRIPTION
            "Major Alarm for near end sending loss of frame (transmitting
            yellow alarm)."
        ::= { dnxTrapEnterprise 302 }

evntT1E1RcvingAIS NOTIFICATION-TYPE
        OBJECTS  {
            trapSequence,
            trapResourceKey,
            trapTime,
            trapResourceAddress,
            trapResourceType,
            trapType,
            trapState,
            trapSeverity
            }
        STATUS current
        DESCRIPTION
            "Informational Event for far end sending alarm indication signal."
        ::= { dnxTrapEnterprise 303 }

setT1E1NearEndSendingAIS NOTIFICATION-TYPE
        OBJECTS  {
            trapSequence,
            trapResourceKey,
            trapTime,
            trapResourceAddress,
            trapResourceType,
            trapType,
            trapState,
            trapSeverity
            }
        STATUS current
        DESCRIPTION
            "Major Alarm for near end sending alarm indication signal."
        ::= { dnxTrapEnterprise 304 }

setT1E1NearEndLOF NOTIFICATION-TYPE
        OBJECTS  {
            trapSequence,
            trapResourceKey,
            trapTime,
            trapResourceAddress,
            trapResourceType,
            trapType,
            trapState,
            trapSeverity
            }
        STATUS current
        DESCRIPTION
            "Major Alarm for near end loss of frame (red alarm)."
        ::= { dnxTrapEnterprise 305 }

setT1E1NearEndLossOfSignal NOTIFICATION-TYPE
        OBJECTS  {
            trapSequence,
            trapResourceKey,
            trapTime,
            trapResourceAddress,
            trapResourceType,
            trapType,
            trapState,
            trapSeverity
            }
        STATUS current
        DESCRIPTION
            "Major Alarm for near end loss of signal."
        ::= { dnxTrapEnterprise 306 }

evntT1E1NearEndLooped NOTIFICATION-TYPE
        OBJECTS  {
            trapSequence,
            trapResourceKey,
            trapTime,
            trapResourceAddress,
            trapResourceType,
            trapType,
            trapState,
            trapSeverity
            }
        STATUS current
        DESCRIPTION
            "Informational Event for T1/E1 near end looped."
        ::= { dnxTrapEnterprise 307 }

setT1E1Ts16AIS NOTIFICATION-TYPE
        OBJECTS  {
            trapSequence,
            trapResourceKey,
            trapTime,
            trapResourceAddress,
            trapResourceType,
            trapType,
            trapState,
            trapSeverity
            }
        STATUS current
        DESCRIPTION
            "Major Alarm for E1 TS16 alarm indication signal."
        ::= { dnxTrapEnterprise 308 }

setT1E1FarEndSendingTs16LOMF NOTIFICATION-TYPE
        OBJECTS  {
            trapSequence,
            trapResourceKey,
            trapTime,
            trapResourceAddress,
            trapResourceType,
            trapType,
            trapState,
            trapSeverity
            }
        STATUS current
        DESCRIPTION
            "Major Alarm for far end sending TS16 LOMF."
        ::= { dnxTrapEnterprise 309 }

setT1E1NearEndSendingTs16LOMF NOTIFICATION-TYPE
        OBJECTS  {
            trapSequence,
            trapResourceKey,
            trapTime,
            trapResourceAddress,
            trapResourceType,
            trapType,
            trapState,
            trapSeverity
            }
        STATUS current
        DESCRIPTION
            "Major Alarm for near end sending TS16 LOMF."
        ::= { dnxTrapEnterprise 310 }

setT1E1OtherLineStatus NOTIFICATION-TYPE
        OBJECTS  {
            trapSequence,
            trapResourceKey,
            trapTime,
            trapResourceAddress,
            trapResourceType,
            trapType,
            trapState,
            trapSeverity
            }
        STATUS current
        DESCRIPTION
            "Major Alarm for other line status."
        ::= { dnxTrapEnterprise 312 }

setT1E1NearEndUnavailableSig NOTIFICATION-TYPE
        OBJECTS  {
            trapSequence,
            trapResourceKey,
            trapTime,
            trapResourceAddress,
            trapResourceType,
            trapType,
            trapState,
            trapSeverity
            }
        STATUS current
        DESCRIPTION
            "Major Alarm for near end in unavailable signal state."
        ::= { dnxTrapEnterprise 313 }

evntT1E1CarrierEquipOutOfService NOTIFICATION-TYPE
        OBJECTS  {
            trapSequence,
            trapResourceKey,
            trapTime,
            trapResourceAddress,
            trapResourceType,
            trapType,
            trapState,
            trapSeverity
            }
        STATUS current
        DESCRIPTION
            "Informational Event for T1/E1 carrier equipment
             out-of-service."
        ::= { dnxTrapEnterprise 314 }

evntE1NationalSa4TxRxSame NOTIFICATION-TYPE
        OBJECTS  {
            trapSequence,
            trapResourceKey,
            trapTime,
            trapResourceAddress,
            trapResourceType,
            trapType,
            trapState,
            trapSeverity
            }
        STATUS current
        DESCRIPTION
            "Informational Event for E1 Sa4 National Bit Send/Receive 
            matching value."
        ::= { dnxTrapEnterprise 316 }

setT1E1NearEndTxSlip NOTIFICATION-TYPE
        OBJECTS  {
            trapSequence,
            trapResourceKey,
            trapTime,
            trapResourceAddress,
            trapResourceType,
            trapType,
            trapState,
            trapSeverity
            }
        STATUS current
        DESCRIPTION
            "Major Alarm for T1/E1 near end transmit slip."
        ::= { dnxTrapEnterprise 321 }

setT1E1NearEndRxSlip NOTIFICATION-TYPE
        OBJECTS  {
            trapSequence,
            trapResourceKey,
            trapTime,
            trapResourceAddress,
            trapResourceType,
            trapType,
            trapState,
            trapSeverity
            }
        STATUS current
        DESCRIPTION
            "Major Alarm for T1/E1 near end receive slip."
        ::= { dnxTrapEnterprise 322 }

setT1E1NearEndSeverErroredFrame NOTIFICATION-TYPE
        OBJECTS  {
            trapSequence,
            trapResourceKey,
            trapTime,
            trapResourceAddress,
            trapResourceType,
            trapType,
            trapState,
            trapSeverity
            }
        STATUS current
        DESCRIPTION
            "Major Alarm for T1/E1 near end severely errored frame."
        ::= { dnxTrapEnterprise 323 }

setT1E1ChangeFrameAlignment NOTIFICATION-TYPE
        OBJECTS  {
            trapSequence,
            trapResourceKey,
            trapTime,
            trapResourceAddress,
            trapResourceType,
            trapType,
            trapState,
            trapSeverity
            }
        STATUS current
        DESCRIPTION
            "Major Alarm for T1/E1 change in frame alignment."
        ::= { dnxTrapEnterprise 324 }

setT1E1ConfigError NOTIFICATION-TYPE
        OBJECTS  {
            trapSequence,
            trapResourceKey,
            trapTime,
            trapResourceAddress,
            trapResourceType,
            trapType,
            trapState,
            trapSeverity
            }
        STATUS current
        DESCRIPTION
            "Major Alarm for T1/E1 configuration error."
        ::= { dnxTrapEnterprise 325 }

evntT1E1InTest NOTIFICATION-TYPE
        OBJECTS  {
            trapSequence,
            trapResourceKey,
            trapTime,
            trapResourceAddress,
            trapResourceType,
            trapType,
            trapState,
            trapSeverity
            }
        STATUS current
        DESCRIPTION
            "Informational Event for T1/E1 in test."
        ::= { dnxTrapEnterprise 330 }

evntT1E1OutOfService NOTIFICATION-TYPE
        OBJECTS  {
            trapSequence,
            trapResourceKey,
            trapTime,
            trapResourceAddress,
            trapResourceType,
            trapType,
            trapState,
            trapSeverity
            }
        STATUS current
        DESCRIPTION
            "Informational Event for T1/E1 out-of-service."
        ::= { dnxTrapEnterprise 331 }

clearT1E1RcvFarEndLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for receiving far end loss of frame
            (yellow alarm)."
        ::= { dnxTrapEnterprise 341 }

clearT1E1NearEndSendLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for near end sending loss of frame
            (yellow alarm)."
        ::= { dnxTrapEnterprise 342 }

evntT1E1StoppedRcvingAIS NOTIFICATION-TYPE
        OBJECTS  {
            trapSequence,
            trapResourceKey,
            trapTime,
            trapResourceAddress,
            trapResourceType,
            trapType,
            trapState,
            trapSeverity
            }
        STATUS current
        DESCRIPTION
            "Informational Event when far end stops sending alarm indication signal."
        ::= { dnxTrapEnterprise 343 }

clearT1E1NearEndSendingAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for near end sending alarm indication
             signal."
        ::= { dnxTrapEnterprise 344 }

clearT1E1NearEndLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for near end loss of frame (red alarm)."
        ::= { dnxTrapEnterprise 345 }

clearT1E1NearEndLossOfSignal NOTIFICATION-TYPE
        OBJECTS  {
            trapSequence,
            trapResourceKey,
            trapTime,
            trapResourceAddress,
            trapResourceType,
            trapType,
            trapState,
            trapSeverity
            }
        STATUS current
        DESCRIPTION
            "Clears the Major Alarm for near end loss of signal."
        ::= { dnxTrapEnterprise 346 }

evntT1E1NearEndLoopOff NOTIFICATION-TYPE
        OBJECTS  {
            trapSequence,
            trapResourceKey,
            trapTime,
            trapResourceAddress,
            trapResourceType,
            trapType,
            trapState,
            trapSeverity
            }
        STATUS current
        DESCRIPTION
            "Informational Event for T1/E1 near end loop off."
        ::= { dnxTrapEnterprise 347 }

clearT1E1Ts16AIS NOTIFICATION-TYPE
        OBJECTS  {
            trapSequence,
            trapResourceKey,
            trapTime,
            trapResourceAddress,
            trapResourceType,
            trapType,
            trapState,
            trapSeverity
            }
        STATUS current
        DESCRIPTION
            "Clears the Major Alarm for E1 TS16 alarm indication signal."
        ::= { dnxTrapEnterprise 348 }

clearT1E1FarEndSendingTs16LOMF NOTIFICATION-TYPE
        OBJECTS  {
            trapSequence,
            trapResourceKey,
            trapTime,
            trapResourceAddress,
            trapResourceType,
            trapType,
            trapState,
            trapSeverity
            }
        STATUS current
        DESCRIPTION
            "Clears the Major Alarm for far end sending TS16 LOMF."
        ::= { dnxTrapEnterprise 349 }

clearT1E1NearEndSendingTs16LOMF NOTIFICATION-TYPE
        OBJECTS  {
            trapSequence,
            trapResourceKey,
            trapTime,
            trapResourceAddress,
            trapResourceType,
            trapType,
            trapState,
            trapSeverity
            }
        STATUS current
        DESCRIPTION
            "Clears the Major Alarm for near end sending TS16 LOMF."
        ::= { dnxTrapEnterprise 350 }

clearT1E1OtherLineStatus NOTIFICATION-TYPE
        OBJECTS  {
            trapSequence,
            trapResourceKey,
            trapTime,
            trapResourceAddress,
            trapResourceType,
            trapType,
            trapState,
            trapSeverity
            }
        STATUS current
        DESCRIPTION
            "Clears the Major Alarm for other line status."
        ::= { dnxTrapEnterprise 352 }

clearT1E1NearEndUnavailableSig NOTIFICATION-TYPE
        OBJECTS  {
            trapSequence,
            trapResourceKey,
            trapTime,
            trapResourceAddress,
            trapResourceType,
            trapType,
            trapState,
            trapSeverity
            }
        STATUS current
        DESCRIPTION
            "Clears the Major Alarm for near end in unavailable
             signal state."
        ::= { dnxTrapEnterprise 353 }

evntT1E1CarrierEquipInService NOTIFICATION-TYPE
        OBJECTS  {
            trapSequence,
            trapResourceKey,
            trapTime,
            trapResourceAddress,
            trapResourceType,
            trapType,
            trapState,
            trapSeverity
            }
        STATUS current
        DESCRIPTION
            "Informational Event for T1/E1 carrier equipment
             in-service."
        ::= { dnxTrapEnterprise 354 }

evntE1NationalSa4TxRxDiff NOTIFICATION-TYPE
        OBJECTS  {
            trapSequence,
            trapResourceKey,
            trapTime,
            trapResourceAddress,
            trapResourceType,
            trapType,
            trapState,
            trapSeverity
            }
        STATUS current
        DESCRIPTION
            "Informational Event for E1 Sa4 National Bit Send/Receive 
            different value."
        ::= { dnxTrapEnterprise 356 }

clearT1E1NearEndTxSlip NOTIFICATION-TYPE
        OBJECTS  {
            trapSequence,
            trapResourceKey,
            trapTime,
            trapResourceAddress,
            trapResourceType,
            trapType,
            trapState,
            trapSeverity
            }
        STATUS current
        DESCRIPTION
            "Clears the Major Alarm for T1/E1 near end transmit slip."
        ::= { dnxTrapEnterprise 361 }

clearT1E1NearEndRxSlip NOTIFICATION-TYPE
        OBJECTS  {
            trapSequence,
            trapResourceKey,
            trapTime,
            trapResourceAddress,
            trapResourceType,
            trapType,
            trapState,
            trapSeverity
            }
        STATUS current
        DESCRIPTION
            "Major Alarm for T1/E1 near end receive slip."
        ::= { dnxTrapEnterprise 362 }

clearT1E1NearEndSeverErroredFrame NOTIFICATION-TYPE
        OBJECTS  {
            trapSequence,
            trapResourceKey,
            trapTime,
            trapResourceAddress,
            trapResourceType,
            trapType,
            trapState,
            trapSeverity
            }
        STATUS current
        DESCRIPTION
            "Clears the Major Alarm for T1/E1 near end severely errored
             frame."
        ::= { dnxTrapEnterprise 363 }

clearT1E1ChangeFrameAlignment NOTIFICATION-TYPE
        OBJECTS  {
            trapSequence,
            trapResourceKey,
            trapTime,
            trapResourceAddress,
            trapResourceType,
            trapType,
            trapState,
            trapSeverity
            }
        STATUS current
        DESCRIPTION
            "Clears the Major Alarm for T1/E1 change in frame alignment."
        ::= { dnxTrapEnterprise 364 }

clearT1E1ConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for T1/E1 configuration error."
        ::= { dnxTrapEnterprise 365 }

evntT1E1TestOff NOTIFICATION-TYPE
        OBJECTS  {
            trapSequence,
            trapResourceKey,
            trapTime,
            trapResourceAddress,
            trapResourceType,
            trapType,
            trapState,
            trapSeverity
            }
        STATUS current
        DESCRIPTION
            "Informational Event for T1/E1 test off."
        ::= { dnxTrapEnterprise 370 }

evntT1E1InService NOTIFICATION-TYPE
        OBJECTS  {
            trapSequence,
            trapResourceKey,
            trapTime,
            trapResourceAddress,
            trapResourceType,
            trapType,
            trapState,
            trapSeverity
            }
        STATUS current
        DESCRIPTION
            "Informational Event for T1/E1 in-service."
        ::= { dnxTrapEnterprise 371 }

-- *************************************************************************
--  High Speed Port Level Alarms/Events; base = 400
-- *************************************************************************

setHsRcvFIFOError NOTIFICATION-TYPE
        OBJECTS  {
            trapSequence,
            trapResourceKey,
            trapTime,
            trapResourceAddress,
            trapResourceType,
            trapType,
            trapState,
            trapSeverity
            }
        STATUS current
        DESCRIPTION
            "Major Alarm for receive FIFO error."
        ::= { dnxTrapEnterprise 401 }

setHsXmtFIFOError NOTIFICATION-TYPE
        OBJECTS  {
            trapSequence,
            trapResourceKey,
            trapTime,
            trapResourceAddress,
            trapResourceType,
            trapType,
            trapState,
            trapSeverity
            }
        STATUS current
        DESCRIPTION
            "Major Alarm for transmit FIFO error."
        ::= { dnxTrapEnterprise 402 }

setHsClockEdgeError NOTIFICATION-TYPE
        OBJECTS  {
            trapSequence,
            trapResourceKey,
            trapTime,
            trapResourceAddress,
            trapResourceType,
            trapType,
            trapState,
            trapSeverity
            }
        STATUS current
        DESCRIPTION
            "Major Alarm for clock edge error."
        ::= { dnxTrapEnterprise 403 }

setHsCarrierFailure NOTIFICATION-TYPE
        OBJECTS  {
            trapSequence,
            trapResourceKey,
            trapTime,
            trapResourceAddress,
            trapResourceType,
            trapType,
            trapState,
            trapSeverity
            }
        STATUS current
        DESCRIPTION
            "Major Alarm for high speed carrier failure."
        ::= { dnxTrapEnterprise 404 }

evntHsNearEndLooped NOTIFICATION-TYPE
        OBJECTS  {
            trapSequence,
            trapResourceKey,
            trapTime,
            trapResourceAddress,
            trapResourceType,
            trapType,
            trapState,
            trapSeverity
            }
        STATUS current
        DESCRIPTION
            "Informational event for high speed near end looped."
        ::= { dnxTrapEnterprise 407 }

evntHsNoBtsAssigned NOTIFICATION-TYPE
        OBJECTS  {
            trapSequence,
            trapResourceKey,
            trapTime,
            trapResourceAddress,
            trapResourceType,
            trapType,
            trapState,
            trapSeverity
            }
        STATUS current
        DESCRIPTION
            "Informational event for no backplane timeslot assigned."
        ::= { dnxTrapEnterprise 424 }

setHsConfigError NOTIFICATION-TYPE
        OBJECTS  {
            trapSequence,
            trapResourceKey,
            trapTime,
            trapResourceAddress,
            trapResourceType,
            trapType,
            trapState,
            trapSeverity
            }
        STATUS current
        DESCRIPTION
            "Major Alarm for high speed configuration error."
        ::= { dnxTrapEnterprise 425 }

evntHsInTest NOTIFICATION-TYPE
        OBJECTS  {
            trapSequence,
            trapResourceKey,
            trapTime,
            trapResourceAddress,
            trapResourceType,
            trapType,
            trapState,
            trapSeverity
            }
        STATUS current
        DESCRIPTION
            "Informational event for high speed in test."
        ::= { dnxTrapEnterprise 430 }

evntHsOutOfService NOTIFICATION-TYPE
        OBJECTS  {
            trapSequence,
            trapResourceKey,
            trapTime,
            trapResourceAddress,
            trapResourceType,
            trapType,
            trapState,
            trapSeverity
            }
        STATUS current
        DESCRIPTION
            "Informational event for high speed out-of-service."
        ::= { dnxTrapEnterprise 431 }

clearHsRcvFIFOError NOTIFICATION-TYPE
        OBJECTS  {
            trapSequence,
            trapResourceKey,
            trapTime,
            trapResourceAddress,
            trapResourceType,
            trapType,
            trapState,
            trapSeverity
            }
        STATUS current
        DESCRIPTION
            "Clears the Major Alarm for receive FIFO error."
        ::= { dnxTrapEnterprise 441 }

clearHsXmtFIFOError NOTIFICATION-TYPE
        OBJECTS  {
            trapSequence,
            trapResourceKey,
            trapTime,
            trapResourceAddress,
            trapResourceType,
            trapType,
            trapState,
            trapSeverity
            }
        STATUS current
        DESCRIPTION
            "Clears the Major Alarm for transmit FIFO error."
        ::= { dnxTrapEnterprise 442 }

clearHsClockEdgeError NOTIFICATION-TYPE
        OBJECTS  {
            trapSequence,
            trapResourceKey,
            trapTime,
            trapResourceAddress,
            trapResourceType,
            trapType,
            trapState,
            trapSeverity
            }
        STATUS current
        DESCRIPTION
            "Clears the Major Alarm for clock edge error."
        ::= { dnxTrapEnterprise 443 }

clearHsCarrierFailure NOTIFICATION-TYPE
        OBJECTS  {
            trapSequence,
            trapResourceKey,
            trapTime,
            trapResourceAddress,
            trapResourceType,
            trapType,
            trapState,
            trapSeverity
            }
        STATUS current
        DESCRIPTION
            "Clears the Major Alarm for high speed carrier failure."
        ::= { dnxTrapEnterprise 444 }

evntHsNearEndLoopOff NOTIFICATION-TYPE
        OBJECTS  {
            trapSequence,
            trapResourceKey,
            trapTime,
            trapResourceAddress,
            trapResourceType,
            trapType,
            trapState,
            trapSeverity
            }
        STATUS current
        DESCRIPTION
            "Informational event for high speed near end loop off."
        ::= { dnxTrapEnterprise 447 }

evntHsBtsAssigned NOTIFICATION-TYPE
        OBJECTS  {
            trapSequence,
            trapResourceKey,
            trapTime,
            trapResourceAddress,
            trapResourceType,
            trapType,
            trapState,
            trapSeverity
            }
        STATUS current
        DESCRIPTION
            "Informational event for backplane timeslot assigned."
        ::= { dnxTrapEnterprise 464 }

clearHsConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for high speed configuration error."
        ::= { dnxTrapEnterprise 465 }

evntHsTestOff NOTIFICATION-TYPE
        OBJECTS  {
            trapSequence,
            trapResourceKey,
            trapTime,
            trapResourceAddress,
            trapResourceType,
            trapType,
            trapState,
            trapSeverity
            }
        STATUS current
        DESCRIPTION
            "Informational event for high speed test off."
        ::= { dnxTrapEnterprise 470 }

evntHsInService NOTIFICATION-TYPE
        OBJECTS  {
            trapSequence,
            trapResourceKey,
            trapTime,
            trapResourceAddress,
            trapResourceType,
            trapType,
            trapState,
            trapSeverity
            }
        STATUS current
        DESCRIPTION
            "Informational event for high speed in-service."
        ::= { dnxTrapEnterprise 471 }

-- *************************************************************************
--  T3 Port Level Alarms/Events; base = 500
-- *************************************************************************

setT3RcvFarEndLOF NOTIFICATION-TYPE
        OBJECTS  {
            trapSequence,
            trapResourceKey,
            trapTime,
            trapResourceAddress,
            trapResourceType,
            trapType,
            trapState,
            trapSeverity
            }
        STATUS current
        DESCRIPTION
            "Major Alarm for receiving far end loss of frame (receiving
            yellow alarm)."
        ::= { dnxTrapEnterprise 501 }

setT3NearEndSendLOF NOTIFICATION-TYPE
        OBJECTS  {
            trapSequence,
            trapResourceKey,
            trapTime,
            trapResourceAddress,
            trapResourceType,
            trapType,
            trapState,
            trapSeverity
            }
        STATUS current
        DESCRIPTION
            "Major Alarm for near end sending loss of frame (transmitting
             yellow alarm)."
        ::= { dnxTrapEnterprise 502 }

setT3FarEndSendingAIS NOTIFICATION-TYPE
        OBJECTS  {
            trapSequence,
            trapResourceKey,
            trapTime,
            trapResourceAddress,
            trapResourceType,
            trapType,
            trapState,
            trapSeverity
            }
        STATUS current
        DESCRIPTION
            "Major Alarm for far end sending alarm indication signal."
        ::= { dnxTrapEnterprise 503 }

setT3NearEndSendingAIS NOTIFICATION-TYPE
        OBJECTS  {
            trapSequence,
            trapResourceKey,
            trapTime,
            trapResourceAddress,
            trapResourceType,
            trapType,
            trapState,
            trapSeverity
            }
        STATUS current
        DESCRIPTION
            "Major Alarm for near end sending alarm indication signal."
        ::= { dnxTrapEnterprise 504 }

setT3NearEndLOF NOTIFICATION-TYPE
        OBJECTS  {
            trapSequence,
            trapResourceKey,
            trapTime,
            trapResourceAddress,
            trapResourceType,
            trapType,
            trapState,
            trapSeverity
            }
        STATUS current
        DESCRIPTION
            "Major Alarm for near end loss of frame."
        ::= { dnxTrapEnterprise 505 }

setT3NearEndLossOfSignal NOTIFICATION-TYPE
        OBJECTS  {
            trapSequence,
            trapResourceKey,
            trapTime,
            trapResourceAddress,
            trapResourceType,
            trapType,
            trapState,
            trapSeverity
            }
        STATUS current
        DESCRIPTION
            "Major Alarm for near end loss of signal."
        ::= { dnxTrapEnterprise 506 }

evntT3NearEndLooped NOTIFICATION-TYPE
        OBJECTS  {
            trapSequence,
            trapResourceKey,
            trapTime,
            trapResourceAddress,
            trapResourceType,
            trapType,
            trapState,
            trapSeverity
            }
        STATUS current
        DESCRIPTION
            "Informational Event for T3 near end looped."
        ::= { dnxTrapEnterprise 507 }

setT3OtherLineStatus NOTIFICATION-TYPE
        OBJECTS  {
            trapSequence,
            trapResourceKey,
            trapTime,
            trapResourceAddress,
            trapResourceType,
            trapType,
            trapState,
            trapSeverity
            }
        STATUS current
        DESCRIPTION
            "Major Alarm for T3 other line status."
        ::= { dnxTrapEnterprise 512 }

setT3NearEndUnavailableSig NOTIFICATION-TYPE
        OBJECTS  {
            trapSequence,
            trapResourceKey,
            trapTime,
            trapResourceAddress,
            trapResourceType,
            trapType,
            trapState,
            trapSeverity
            }
        STATUS current
        DESCRIPTION
            "Major Alarm for near end in unavailable signal state."
        ::= { dnxTrapEnterprise 513 }

evntT3CarrierEquipOutOfService NOTIFICATION-TYPE
        OBJECTS  {
            trapSequence,
            trapResourceKey,
            trapTime,
            trapResourceAddress,
            trapResourceType,
            trapType,
            trapState,
            trapSeverity
            }
        STATUS current
        DESCRIPTION
            "Informational Event for T3 carrier equipment out-of-service."
        ::= { dnxTrapEnterprise 514 }

setT3NearEndSeverErroredFrame NOTIFICATION-TYPE
        OBJECTS  {
            trapSequence,
            trapResourceKey,
            trapTime,
            trapResourceAddress,
            trapResourceType,
            trapType,
            trapState,
            trapSeverity
            }
        STATUS current
        DESCRIPTION
            "Major Alarm for near end severely errored frame."
        ::= { dnxTrapEnterprise 515 }

setT3TxRxClockFailure NOTIFICATION-TYPE
        OBJECTS  {
            trapSequence,
            trapResourceKey,
            trapTime,
            trapResourceAddress,
            trapResourceType,
            trapType,
            trapState,
            trapSeverity
            }
        STATUS current
        DESCRIPTION
            "Major Alarm for T3 Transmit/Receive clock failure."
        ::= { dnxTrapEnterprise 516 }

setT3FarEndBlockError NOTIFICATION-TYPE
        OBJECTS  {
            trapSequence,
            trapResourceKey,
            trapTime,
            trapResourceAddress,
            trapResourceType,
            trapType,
            trapState,
            trapSeverity
            }
        STATUS current
        DESCRIPTION
            "Major Alarm for T3 far end block error."
        ::= { dnxTrapEnterprise 517 }

setT3PbitCbitParityError NOTIFICATION-TYPE
        OBJECTS  {
            trapSequence,
            trapResourceKey,
            trapTime,
            trapResourceAddress,
            trapResourceType,
            trapType,
            trapState,
            trapSeverity
            }
        STATUS current
        DESCRIPTION
            "Major Alarm for P-bit or C-bit parity error."
        ::= { dnxTrapEnterprise 518 }

setT3MbitsInError NOTIFICATION-TYPE
        OBJECTS  {
            trapSequence,
            trapResourceKey,
            trapTime,
            trapResourceAddress,
            trapResourceType,
            trapType,
            trapState,
            trapSeverity
            }
        STATUS current
        DESCRIPTION
            "Major Alarm for M-bits in error."
        ::= { dnxTrapEnterprise 519 }

setT3LIUOtherStatus NOTIFICATION-TYPE
        OBJECTS  {
            trapSequence,
            trapResourceKey,
            trapTime,
            trapResourceAddress,
            trapResourceType,
            trapType,
            trapState,
            trapSeverity
            }
        STATUS current
        DESCRIPTION
            "Major Alarm for T3 LIU other status."
        ::= { dnxTrapEnterprise 520 }

setT3LIUExcessZeros NOTIFICATION-TYPE
        OBJECTS  {
            trapSequence,
            trapResourceKey,
            trapTime,
            trapResourceAddress,
            trapResourceType,
            trapType,
            trapState,
            trapSeverity
            }
        STATUS current
        DESCRIPTION
            "Major Alarm for T3 LIU excessive zeroes."
        ::= { dnxTrapEnterprise 522 }

setT3LIUCodingViolation NOTIFICATION-TYPE
        OBJECTS  {
            trapSequence,
            trapResourceKey,
            trapTime,
            trapResourceAddress,
            trapResourceType,
            trapType,
            trapState,
            trapSeverity
            }
        STATUS current
        DESCRIPTION
            "Major Alarm for T3 LIU line coding violation."
        ::= { dnxTrapEnterprise 523 }

setT3LIUPrbsError NOTIFICATION-TYPE
        OBJECTS  {
            trapSequence,
            trapResourceKey,
            trapTime,
            trapResourceAddress,
            trapResourceType,
            trapType,
            trapState,
            trapSeverity
            }
        STATUS current
        DESCRIPTION
            "Major Alarm for T3 LIU PRBS error."
        ::= { dnxTrapEnterprise 524 }

setT3ConfigError NOTIFICATION-TYPE
        OBJECTS  {
            trapSequence,
            trapResourceKey,
            trapTime,
            trapResourceAddress,
            trapResourceType,
            trapType,
            trapState,
            trapSeverity
            }
        STATUS current
        DESCRIPTION
            "Major Alarm for T3 configuration error."
        ::= { dnxTrapEnterprise 525 }

evntT3InTest NOTIFICATION-TYPE
        OBJECTS  {
            trapSequence,
            trapResourceKey,
            trapTime,
            trapResourceAddress,
            trapResourceType,
            trapType,
            trapState,
            trapSeverity
            }
        STATUS current
        DESCRIPTION
            "Informational Event for T3 in test."
        ::= { dnxTrapEnterprise 530 }

evntT3OutOfService NOTIFICATION-TYPE
        OBJECTS  {
            trapSequence,
            trapResourceKey,
            trapTime,
            trapResourceAddress,
            trapResourceType,
            trapType,
            trapState,
            trapSeverity
            }
        STATUS current
        DESCRIPTION
            "Informational Event for T3 out-of-service."
        ::= { dnxTrapEnterprise 531 }

clearT3RcvFarEndLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for receiving far end loss of frame
             (receiving yellow alarm)."
        ::= { dnxTrapEnterprise 541 }

clearT3NearEndSendLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for near end sending loss of frame
             (transmitting yellow alarm)."
        ::= { dnxTrapEnterprise 542 }

clearT3FarEndSendingAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for far end sending alarm indication
             signal."
        ::= { dnxTrapEnterprise 543 }

clearT3NearEndSendingAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for near end sending alarm indication
             signal."
        ::= { dnxTrapEnterprise 544 }

clearT3NearEndLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for near end loss of frame."
        ::= { dnxTrapEnterprise 545 }

clearT3NearEndLossOfSignal NOTIFICATION-TYPE
        OBJECTS  {
            trapSequence,
            trapResourceKey,
            trapTime,
            trapResourceAddress,
            trapResourceType,
            trapType,
            trapState,
            trapSeverity
            }
        STATUS current
        DESCRIPTION
            "Clears the Major Alarm for near end loss of signal."
        ::= { dnxTrapEnterprise 546 }

evntT3NearEndLoopOff NOTIFICATION-TYPE
        OBJECTS  {
            trapSequence,
            trapResourceKey,
            trapTime,
            trapResourceAddress,
            trapResourceType,
            trapType,
            trapState,
            trapSeverity
            }
        STATUS current
        DESCRIPTION
            "Informational Event for T3 near end loop off."
        ::= { dnxTrapEnterprise 547 }

clearT3OtherLineStatus NOTIFICATION-TYPE
        OBJECTS  {
            trapSequence,
            trapResourceKey,
            trapTime,
            trapResourceAddress,
            trapResourceType,
            trapType,
            trapState,
            trapSeverity
            }
        STATUS current
        DESCRIPTION
            "Clears the Major Alarm for T3 other line status."
        ::= { dnxTrapEnterprise 552 }

clearT3NearEndUnavailableSig NOTIFICATION-TYPE
        OBJECTS  {
            trapSequence,
            trapResourceKey,
            trapTime,
            trapResourceAddress,
            trapResourceType,
            trapType,
            trapState,
            trapSeverity
            }
        STATUS current
        DESCRIPTION
            "Clears the Major Alarm for near end in unavailable signal
             state."
        ::= { dnxTrapEnterprise 553 }

evntT3CarrierEquipInService NOTIFICATION-TYPE
        OBJECTS  {
            trapSequence,
            trapResourceKey,
            trapTime,
            trapResourceAddress,
            trapResourceType,
            trapType,
            trapState,
            trapSeverity
            }
        STATUS current
        DESCRIPTION
            "Informational Event for T3 carrier equipment in-service."
        ::= { dnxTrapEnterprise 554 }

clearT3NearEndSeverErroredFrame NOTIFICATION-TYPE
        OBJECTS  {
            trapSequence,
            trapResourceKey,
            trapTime,
            trapResourceAddress,
            trapResourceType,
            trapType,
            trapState,
            trapSeverity
            }
        STATUS current
        DESCRIPTION
            "Clears the Major Alarm for near end severely errored frame."
        ::= { dnxTrapEnterprise 555 }

clearT3TxRxClockFailure NOTIFICATION-TYPE
        OBJECTS  {
            trapSequence,
            trapResourceKey,
            trapTime,
            trapResourceAddress,
            trapResourceType,
            trapType,
            trapState,
            trapSeverity
            }
        STATUS current
        DESCRIPTION
            "Clears the Major Alarm for T3 Transmit/Receive clock failure."
        ::= { dnxTrapEnterprise 556 }

clearT3FarEndBlockError NOTIFICATION-TYPE
        OBJECTS  {
            trapSequence,
            trapResourceKey,
            trapTime,
            trapResourceAddress,
            trapResourceType,
            trapType,
            trapState,
            trapSeverity
            }
        STATUS current
        DESCRIPTION
            "Clears the Major Alarm for T3 far end block error."
        ::= { dnxTrapEnterprise 557 }

clearT3PbitCbitParityError NOTIFICATION-TYPE
        OBJECTS  {
            trapSequence,
            trapResourceKey,
            trapTime,
            trapResourceAddress,
            trapResourceType,
            trapType,
            trapState,
            trapSeverity
            }
        STATUS current
        DESCRIPTION
            "Clears the Major Alarm for P-bit or C-bit parity error."
        ::= { dnxTrapEnterprise 558 }

clearT3MbitsInError NOTIFICATION-TYPE
        OBJECTS  {
            trapSequence,
            trapResourceKey,
            trapTime,
            trapResourceAddress,
            trapResourceType,
            trapType,
            trapState,
            trapSeverity
            }
        STATUS current
        DESCRIPTION
            "Clears the Major Alarm for M-bits in error."
        ::= { dnxTrapEnterprise 559 }

clearT3LIUOtherStatus NOTIFICATION-TYPE
        OBJECTS  {
            trapSequence,
            trapResourceKey,
            trapTime,
            trapResourceAddress,
            trapResourceType,
            trapType,
            trapState,
            trapSeverity
            }
        STATUS current
        DESCRIPTION
            "Clears the Major Alarm for T3 LIU other status."
        ::= { dnxTrapEnterprise 560 }

clearT3LIUExcessZeros NOTIFICATION-TYPE
        OBJECTS  {
            trapSequence,
            trapResourceKey,
            trapTime,
            trapResourceAddress,
            trapResourceType,
            trapType,
            trapState,
            trapSeverity
            }
        STATUS current
        DESCRIPTION
            "Clears the Major Alarm for T3 LIU excessive zeroes."
        ::= { dnxTrapEnterprise 562 }

clearT3LIUCodingViolation NOTIFICATION-TYPE
        OBJECTS  {
            trapSequence,
            trapResourceKey,
            trapTime,
            trapResourceAddress,
            trapResourceType,
            trapType,
            trapState,
            trapSeverity
            }
        STATUS current
        DESCRIPTION
            "Clears the Major Alarm for T3 LIU line coding violation."
        ::= { dnxTrapEnterprise 563 }

clearT3LIUPrbsError NOTIFICATION-TYPE
        OBJECTS  {
            trapSequence,
            trapResourceKey,
            trapTime,
            trapResourceAddress,
            trapResourceType,
            trapType,
            trapState,
            trapSeverity
            }
        STATUS current
        DESCRIPTION
            "Clears the Major Alarm for T3 LIU PRBS error."
        ::= { dnxTrapEnterprise 564 }

clearT3ConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for T3 configuration error."
        ::= { dnxTrapEnterprise 565 }

evntT3TestOff NOTIFICATION-TYPE
        OBJECTS  {
            trapSequence,
            trapResourceKey,
            trapTime,
            trapResourceAddress,
            trapResourceType,
            trapType,
            trapState,
            trapSeverity
            }
        STATUS current
        DESCRIPTION
            "Informational Event for T3 test off."
        ::= { dnxTrapEnterprise 570 }

evntT3InService NOTIFICATION-TYPE
        OBJECTS  {
            trapSequence,
            trapResourceKey,
            trapTime,
            trapResourceAddress,
            trapResourceType,
            trapType,
            trapState,
            trapSeverity
            }
        STATUS current
        DESCRIPTION
            "Informational Event for T3 in-service."
        ::= { dnxTrapEnterprise 571 }

-- *************************************************************************
--  Power Supply Alarms/Events; base = 600
-- *************************************************************************

setPowerSupplyNotPresent NOTIFICATION-TYPE
        OBJECTS  {
            trapSequence,
            trapResourceKey,
            trapTime,
            trapResourceAddress,
            trapResourceType,
            trapType,
            trapState,
            trapSeverity
            }
        STATUS current
        DESCRIPTION
            "Major Alarm for power supply not present."
        ::= { dnxTrapEnterprise 601 }

setPowerSupplyProblem NOTIFICATION-TYPE
        OBJECTS  {
            trapSequence,
            trapResourceKey,
            trapTime,
            trapResourceAddress,
            trapResourceType,
            trapType,
            trapState,
            trapSeverity
            }
        STATUS current
        DESCRIPTION
            "Major Alarm for power supply problem."
        ::= { dnxTrapEnterprise 602 }

clearPowerSupplyNotPresent NOTIFICATION-TYPE
        OBJECTS  {
            trapSequence,
            trapResourceKey,
            trapTime,
            trapResourceAddress,
            trapResourceType,
            trapType,
            trapState,
            trapSeverity
            }
        STATUS current
        DESCRIPTION
            "Clears the Major Alarm for power supply not present."
        ::= { dnxTrapEnterprise 641 }

clearPowerSupplyProblem NOTIFICATION-TYPE
        OBJECTS  {
            trapSequence,
            trapResourceKey,
            trapTime,
            trapResourceAddress,
            trapResourceType,
            trapType,
            trapState,
            trapSeverity
            }
        STATUS current
        DESCRIPTION
            "Clears the Major Alarm for power supply problem."
        ::= { dnxTrapEnterprise 642 }

-- *************************************************************************
--  Quad OCU Port Level Alarms/Events; base = 700
-- *************************************************************************

setOcuNearEndLOS NOTIFICATION-TYPE
        OBJECTS  {
            trapSequence,
            trapResourceKey,
            trapTime,
            trapResourceAddress,
            trapResourceType,
            trapType,
            trapState,
            trapSeverity
            }
        STATUS current
        DESCRIPTION
            "Major Alarm for Quad OCU near end loss of signal."
        ::= { dnxTrapEnterprise 706 }

setOcuOtherLineStatus NOTIFICATION-TYPE
        OBJECTS  {
            trapSequence,
            trapResourceKey,
            trapTime,
            trapResourceAddress,
            trapResourceType,
            trapType,
            trapState,
            trapSeverity
            }
        STATUS current
        DESCRIPTION
            "Major Alarm for Quad OCU other line status."
        ::= { dnxTrapEnterprise 712 }

setOcuNearEndSeverErroredFrame NOTIFICATION-TYPE
        OBJECTS  {
            trapSequence,
            trapResourceKey,
            trapTime,
            trapResourceAddress,
            trapResourceType,
            trapType,
            trapState,
            trapSeverity
            }
        STATUS current
        DESCRIPTION
            "Major Alarm for Quad OCU near end severely errored frame."
        ::= { dnxTrapEnterprise 723 }

setOcuConfigError NOTIFICATION-TYPE
        OBJECTS  {
            trapSequence,
            trapResourceKey,
            trapTime,
            trapResourceAddress,
            trapResourceType,
            trapType,
            trapState,
            trapSeverity
            }
        STATUS current
        DESCRIPTION
            "Major Alarm for Quad OCU configuration error."
        ::= { dnxTrapEnterprise 725 }

evntOcuOutOfService NOTIFICATION-TYPE
        OBJECTS  {
            trapSequence,
            trapResourceKey,
            trapTime,
            trapResourceAddress,
            trapResourceType,
            trapType,
            trapState,
            trapSeverity
            }
        STATUS current
        DESCRIPTION
            "Informational Event for Quad OCU out-of-service."
        ::= { dnxTrapEnterprise 731 }

clearOcuNearEndLOS NOTIFICATION-TYPE
        OBJECTS  {
            trapSequence,
            trapResourceKey,
            trapTime,
            trapResourceAddress,
            trapResourceType,
            trapType,
            trapState,
            trapSeverity
            }
        STATUS current
        DESCRIPTION
            "Clears the Major Alarm for Quad OCU near end loss of signal."
        ::= { dnxTrapEnterprise 746 }

clearOcuOtherLineStatus NOTIFICATION-TYPE
        OBJECTS  {
            trapSequence,
            trapResourceKey,
            trapTime,
            trapResourceAddress,
            trapResourceType,
            trapType,
            trapState,
            trapSeverity
            }
        STATUS current
        DESCRIPTION
            "Clears the Major Alarm for Quad OCU other line status."
        ::= { dnxTrapEnterprise 752 }

clearOcuNearEndSeverErroredFrame NOTIFICATION-TYPE
        OBJECTS  {
            trapSequence,
            trapResourceKey,
            trapTime,
            trapResourceAddress,
            trapResourceType,
            trapType,
            trapState,
            trapSeverity
            }
        STATUS current
        DESCRIPTION
            "Clears the Major Alarm for Quad OCU near end severely errored
             frame."
        ::= { dnxTrapEnterprise 763 }

clearOcuConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for Quad OCU configuration error."
        ::= { dnxTrapEnterprise 765 }

evntOcuInService NOTIFICATION-TYPE
        OBJECTS  {
            trapSequence,
            trapResourceKey,
            trapTime,
            trapResourceAddress,
            trapResourceType,
            trapType,
            trapState,
            trapSeverity
            }
        STATUS current
        DESCRIPTION
            "Informational Event for Quad OCU in-service."
        ::= { dnxTrapEnterprise 771 }

-- *************************************************************************
--  Test Access Module Port Level Alarms/Events; base = 800
-- *************************************************************************

setTamConfigError NOTIFICATION-TYPE
        OBJECTS  {
            trapSequence,
            trapResourceKey,
            trapTime,
            trapResourceAddress,
            trapResourceType,
            trapType,
            trapState,
            trapSeverity
            }
        STATUS current
        DESCRIPTION
            "Major Alarm for TAM configuration error."
        ::= { dnxTrapEnterprise 825 }

evntTamOutOfService NOTIFICATION-TYPE
        OBJECTS  {
            trapSequence,
            trapResourceKey,
            trapTime,
            trapResourceAddress,
            trapResourceType,
            trapType,
            trapState,
            trapSeverity
            }
        STATUS current
        DESCRIPTION
            "Informational Event for TAM out-of-service."
        ::= { dnxTrapEnterprise 831 }

clearTamConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for TAM configuration error."
        ::= { dnxTrapEnterprise 865 }

evntTamInService NOTIFICATION-TYPE
        OBJECTS  {
            trapSequence,
            trapResourceKey,
            trapTime,
            trapResourceAddress,
            trapResourceType,
            trapType,
            trapState,
            trapSeverity
            }
        STATUS current
        DESCRIPTION
            "Informational Event for TAM in-service."
        ::= { dnxTrapEnterprise 871 }
                                 
-- *************************************************************************
--  Voice Port Level Alarms/Events; base = 900
-- *************************************************************************

setVoiceConfigError NOTIFICATION-TYPE
        OBJECTS  {
            trapSequence,
            trapResourceKey,
            trapTime,
            trapResourceAddress,
            trapResourceType,
            trapType,
            trapState,
            trapSeverity
            }
        STATUS current
        DESCRIPTION
            "Major Alarm for Voice Port configuration error."
        ::= { dnxTrapEnterprise 925 }

evntVoiceOutOfService NOTIFICATION-TYPE
        OBJECTS  {
            trapSequence,
            trapResourceKey,
            trapTime,
            trapResourceAddress,
            trapResourceType,
            trapType,
            trapState,
            trapSeverity
            }
        STATUS current
        DESCRIPTION
            "Informational Event for Voice Port out-of-service."
        ::= { dnxTrapEnterprise 931 }

clearVoiceConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for Voice Port configuration error."
        ::= { dnxTrapEnterprise 965 }

evntVoiceInService NOTIFICATION-TYPE
        OBJECTS  {
            trapSequence,
            trapResourceKey,
            trapTime,
            trapResourceAddress,
            trapResourceType,
            trapType,
            trapState,
            trapSeverity
            }
        STATUS current
        DESCRIPTION
            "Informational Event for Voice Port in-service."
        ::= { dnxTrapEnterprise 971 }

-- *************************************************************************
--  Protection Switch Level Alarms/Events; base = 1000
-- *************************************************************************

evntPsxDevOnline NOTIFICATION-TYPE
        OBJECTS  {
            trapSequence,
            trapResourceKey,
            trapTime,
            trapResourceAddress,
            trapResourceType,
            trapType,
            trapState,
            trapSeverity
            }
        STATUS current
        DESCRIPTION
            "Informational Event for Protection Switch Device Online."
        ::= { dnxTrapEnterprise 1001 }

setPsxPowerSupplyANotOk NOTIFICATION-TYPE
        OBJECTS  {
            trapSequence,
            trapResourceKey,
            trapTime,
            trapResourceAddress,
            trapResourceType,
            trapType,
            trapState,
            trapSeverity
            }
        STATUS current
        DESCRIPTION
            "Major Alarm for PSX Power Supply A problem."
        ::= { dnxTrapEnterprise 1003 }

setPsxPowerSupplyBNotOk NOTIFICATION-TYPE
        OBJECTS  {
            trapSequence,
            trapResourceKey,
            trapTime,
            trapResourceAddress,
            trapResourceType,
            trapType,
            trapState,
            trapSeverity
            }
        STATUS current
        DESCRIPTION
            "Major Alarm for PSX Power Supply B problem."
        ::= { dnxTrapEnterprise 1004 }

setPsxFan01NotOk NOTIFICATION-TYPE
        OBJECTS  {
            trapSequence,
            trapResourceKey,
            trapTime,
            trapResourceAddress,
            trapResourceType,
            trapType,
            trapState,
            trapSeverity
            }
        STATUS current
        DESCRIPTION
            "Major Alarm for PSX Fan 01 problem."
        ::= { dnxTrapEnterprise 1005 }

setPsxFan02NotOk NOTIFICATION-TYPE
        OBJECTS  {
            trapSequence,
            trapResourceKey,
            trapTime,
            trapResourceAddress,
            trapResourceType,
            trapType,
            trapState,
            trapSeverity
            }
        STATUS current
        DESCRIPTION
            "Major Alarm for PSX Fan 02 problem."
        ::= { dnxTrapEnterprise 1006 }

setPsxFan03NotOk NOTIFICATION-TYPE
        OBJECTS  {
            trapSequence,
            trapResourceKey,
            trapTime,
            trapResourceAddress,
            trapResourceType,
            trapType,
            trapState,
            trapSeverity
            }
        STATUS current
        DESCRIPTION
            "Major Alarm for PSX Fan 03 problem."
        ::= { dnxTrapEnterprise 1007 }

setPsxDualBroadbandNotSupported NOTIFICATION-TYPE
        OBJECTS  {
            trapSequence,
            trapResourceKey,
            trapTime,
            trapResourceAddress,
            trapResourceType,
            trapType,
            trapState,
            trapSeverity
            }
        STATUS current
        DESCRIPTION
            "Major Alarm for PSX Dual Broadband protection group not
             supported."
        ::= { dnxTrapEnterprise 1008 }

evntPsxNewControllerRev NOTIFICATION-TYPE
        OBJECTS  {
            trapSequence,
            trapResourceKey,
            trapTime,
            trapResourceAddress,
            trapResourceType,
            trapType,
            trapState,
            trapSeverity
            }
        STATUS current
        DESCRIPTION
            "Informational Event for PSX new controller revision."
        ::= { dnxTrapEnterprise 1009 }
-- kept for backwards compatibilty

evntPsxLineCard01Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 01 missing."
        ::= { dnxTrapEnterprise 1014 }

evntPsxLineCard02Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 02 missing."
        ::= { dnxTrapEnterprise 1015 }

evntPsxLineCard03Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 03 missing."
        ::= { dnxTrapEnterprise 1016 }

evntPsxLineCard04Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 04 missing."
        ::= { dnxTrapEnterprise 1017 }

evntPsxLineCard05Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 05 missing."
        ::= { dnxTrapEnterprise 1018 }

evntPsxLineCard06Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 06 missing."
        ::= { dnxTrapEnterprise 1019 }

evntPsxLineCard07Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 07 missing."
        ::= { dnxTrapEnterprise 1020 }

evntPsxLineCard08Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 08 missing."
        ::= { dnxTrapEnterprise 1021 }

evntPsxLineCard09Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 09 missing."
        ::= { dnxTrapEnterprise 1022 }

evntPsxLineCard10Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 10 missing."
        ::= { dnxTrapEnterprise 1023 }

evntPsxLineCard11Missing NOTIFICATION-TYPE
        OBJECTS  {
            trapSequence,
            trapResourceKey,
            trapTime,
            trapResourceAddress,
            trapResourceType,
            trapType,
            trapState,
            trapSeverity
            }
        STATUS current
        DESCRIPTION
            "Informational Event for PSX line card 11 missing."
        ::= { dnxTrapEnterprise 1024 }

clearPsxPowerSupplyANotOk NOTIFICATION-TYPE
        OBJECTS  {
            trapSequence,
            trapResourceKey,
            trapTime,
            trapResourceAddress,
            trapResourceType,
            trapType,
            trapState,
            trapSeverity
            }
        STATUS current
        DESCRIPTION
            "Clears the Major Alarm for PSX Power Supply A problem."
        ::= { dnxTrapEnterprise 1043 }

clearPsxPowerSupplyBNotOk NOTIFICATION-TYPE
        OBJECTS  {
            trapSequence,
            trapResourceKey,
            trapTime,
            trapResourceAddress,
            trapResourceType,
            trapType,
            trapState,
            trapSeverity
            }
        STATUS current
        DESCRIPTION
            "Clears the Major Alarm for PSX Power Supply B problem."
        ::= { dnxTrapEnterprise 1044 }

clearPsxFan01NotOk NOTIFICATION-TYPE
        OBJECTS  {
            trapSequence,
            trapResourceKey,
            trapTime,
            trapResourceAddress,
            trapResourceType,
            trapType,
            trapState,
            trapSeverity
            }
        STATUS current
        DESCRIPTION
            "Clears the Major Alarm for PSX Fan 01 problem."
        ::= { dnxTrapEnterprise 1045 }

clearPsxFan02NotOk NOTIFICATION-TYPE
        OBJECTS  {
            trapSequence,
            trapResourceKey,
            trapTime,
            trapResourceAddress,
            trapResourceType,
            trapType,
            trapState,
            trapSeverity
            }
        STATUS current
        DESCRIPTION
            "Clears the Major Alarm for PSX Fan 02 problem."
        ::= { dnxTrapEnterprise 1046 }

clearPsxFan03NotOk NOTIFICATION-TYPE
        OBJECTS  {
            trapSequence,
            trapResourceKey,
            trapTime,
            trapResourceAddress,
            trapResourceType,
            trapType,
            trapState,
            trapSeverity
            }
        STATUS current
        DESCRIPTION
            "Clears the Major Alarm for PSX Fan 03 problem."
        ::= { dnxTrapEnterprise 1047 }

clearPsxDualBroadbandNotSupported NOTIFICATION-TYPE
        OBJECTS  {
            trapSequence,
            trapResourceKey,
            trapTime,
            trapResourceAddress,
            trapResourceType,
            trapType,
            trapState,
            trapSeverity
            }
        STATUS current
        DESCRIPTION
            "Clears the Major Alarm for PSX Dual Broadband protection group
             not supported."
        ::= { dnxTrapEnterprise 1048 }

evntPsxLineCard01Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 01 present."
        ::= { dnxTrapEnterprise 1054 }

evntPsxLineCard02Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 02 present."
        ::= { dnxTrapEnterprise 1055 }

evntPsxLineCard03Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 03 present."
        ::= { dnxTrapEnterprise 1056 }

evntPsxLineCard04Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 04 present."
        ::= { dnxTrapEnterprise 1057 }

evntPsxLineCard05Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 05 present."
        ::= { dnxTrapEnterprise 1058 }

evntPsxLineCard06Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 06 present."
        ::= { dnxTrapEnterprise 1059 }

evntPsxLineCard07Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 07 present."
        ::= { dnxTrapEnterprise 1060 }

evntPsxLineCard08Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 08 present."
        ::= { dnxTrapEnterprise 1061 }

evntPsxLineCard09Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 09 present."
        ::= { dnxTrapEnterprise 1062 }

evntPsxLineCard10Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 10 present."
        ::= { dnxTrapEnterprise 1063 }

evntPsxLineCard11Present NOTIFICATION-TYPE
        OBJECTS  {
            trapSequence,
            trapResourceKey,
            trapTime,
            trapResourceAddress,
            trapResourceType,
            trapType,
            trapState,
            trapSeverity
            }
        STATUS current
        DESCRIPTION
            "Informational Event for PSX line card 11 present."
        ::= { dnxTrapEnterprise 1064 }

-- *************************************************************************
--  Protection Switch Line Card Level Alarms/Events; base = 1100
-- *************************************************************************

setPsxLineCardRelaySwitchToSpare NOTIFICATION-TYPE
        OBJECTS  {
            trapSequence,
            trapResourceKey,
            trapTime,
            trapResourceAddress,
            trapResourceType,
            trapType,
            trapState,
            trapSeverity
            }
        STATUS current
        DESCRIPTION
            "Major Alarm for PSX Line Card switched to spare."
        ::= { dnxTrapEnterprise 1102 }

setPsxLineCardCableMissing NOTIFICATION-TYPE
        OBJECTS  {
            trapSequence,
            trapResourceKey,
            trapTime,
            trapResourceAddress,
            trapResourceType,
            trapType,
            trapState,
            trapSeverity
            }
        STATUS current
        DESCRIPTION
            "Critical Alarm for PSX Line Card cable missing."
        ::= { dnxTrapEnterprise 1103 }

setPsxLineCardMissing NOTIFICATION-TYPE
        OBJECTS  {
            trapSequence,
            trapResourceKey,
            trapTime,
            trapResourceAddress,
            trapResourceType,
            trapType,
            trapState,
            trapSeverity
            }
        STATUS current
        DESCRIPTION
            "Major Alarm for PSX Line Card missing."
        ::= { dnxTrapEnterprise 1106 }

setPsxLineCardMismatch NOTIFICATION-TYPE
        OBJECTS  {
            trapSequence,
            trapResourceKey,
            trapTime,
            trapResourceAddress,
            trapResourceType,
            trapType,
            trapState,
            trapSeverity
            }
        STATUS current
        DESCRIPTION
            "Major Alarm for PSX Line Card type mismatch."
        ::= { dnxTrapEnterprise 1107 }

setPsxLineCardRelayMalfunction NOTIFICATION-TYPE
        OBJECTS  {
            trapSequence,
            trapResourceKey,
            trapTime,
            trapResourceAddress,
            trapResourceType,
            trapType,
            trapState,
            trapSeverity
            }
        STATUS current
        DESCRIPTION
            "Major Alarm for PSX Line Card realy malfunction."
        ::= { dnxTrapEnterprise 1108 }

clearPsxLineCardRelaySwitchToSpare NOTIFICATION-TYPE
        OBJECTS  {
            trapSequence,
            trapResourceKey,
            trapTime,
            trapResourceAddress,
            trapResourceType,
            trapType,
            trapState,
            trapSeverity
            }
        STATUS current
        DESCRIPTION
            "Clears the Major Alarm for PSX Line Card switched to spare."
        ::= { dnxTrapEnterprise 1142 }

clearPsxLineCardCableMissing NOTIFICATION-TYPE
        OBJECTS  {
            trapSequence,
            trapResourceKey,
            trapTime,
            trapResourceAddress,
            trapResourceType,
            trapType,
            trapState,
            trapSeverity
            }
        STATUS current
        DESCRIPTION
            "Clears the Critical Alarm for PSX Line Card cable missing."
        ::= { dnxTrapEnterprise 1143 }

clearPsxLineCardMissing NOTIFICATION-TYPE
        OBJECTS  {
            trapSequence,
            trapResourceKey,
            trapTime,
            trapResourceAddress,
            trapResourceType,
            trapType,
            trapState,
            trapSeverity
            }
        STATUS current
        DESCRIPTION
            "Clears the Major Alarm for PSX Line Card missing."
        ::= { dnxTrapEnterprise 1146 }

clearPsxLineCardMismatch NOTIFICATION-TYPE
        OBJECTS  {
            trapSequence,
            trapResourceKey,
            trapTime,
            trapResourceAddress,
            trapResourceType,
            trapType,
            trapState,
            trapSeverity
            }
        STATUS current
        DESCRIPTION
            "Clears the Major Alarm for PSX Line Card type mismatch."
        ::= { dnxTrapEnterprise 1147 }

clearPsxLineCardRelayMalfunction NOTIFICATION-TYPE
        OBJECTS  {
            trapSequence,
            trapResourceKey,
            trapTime,
            trapResourceAddress,
            trapResourceType,
            trapType,
            trapState,
            trapSeverity
            }
        STATUS current
        DESCRIPTION
            "Clears the Major Alarm for PSX Line Card realy malfunction."
        ::= { dnxTrapEnterprise 1148 }

-- *************************************************************************
--  Router Port Level Alarms/Events; base = 1200
-- *************************************************************************

setRtrUserAlarm1 NOTIFICATION-TYPE
        OBJECTS  {
            trapSequence,
            trapResourceKey,
            trapTime,
            trapResourceAddress,
            trapResourceType,
            trapType,
            trapState,
            trapSeverity
            }
        STATUS current
        DESCRIPTION
            "Major Alarm for Router User Alarm 1."
        ::= { dnxTrapEnterprise 1201 }

setRtrUserAlarm2 NOTIFICATION-TYPE
        OBJECTS  {
            trapSequence,
            trapResourceKey,
            trapTime,
            trapResourceAddress,
            trapResourceType,
            trapType,
            trapState,
            trapSeverity
            }
        STATUS current
        DESCRIPTION
            "Major Alarm for Router User Alarm 2."
        ::= { dnxTrapEnterprise 1202 }

setRtrUserAlarm3 NOTIFICATION-TYPE
        OBJECTS  {
            trapSequence,
            trapResourceKey,
            trapTime,
            trapResourceAddress,
            trapResourceType,
            trapType,
            trapState,
            trapSeverity
            }
        STATUS current
        DESCRIPTION
            "Major Alarm for Router User Alarm 3."
        ::= { dnxTrapEnterprise 1203 }

setRtrConfigError NOTIFICATION-TYPE
        OBJECTS  {
            trapSequence,
            trapResourceKey,
            trapTime,
            trapResourceAddress,
            trapResourceType,
            trapType,
            trapState,
            trapSeverity
            }
        STATUS current
        DESCRIPTION
            "Major Alarm for Router configuration error."
        ::= { dnxTrapEnterprise 1225 }

evntRtrOutOfService NOTIFICATION-TYPE
        OBJECTS  {
            trapSequence,
            trapResourceKey,
            trapTime,
            trapResourceAddress,
            trapResourceType,
            trapType,
            trapState,
            trapSeverity
            }
        STATUS current
        DESCRIPTION
            "Informational Event for Router out-of-service."
        ::= { dnxTrapEnterprise 1231 }

clearRtrUserAlarm1 NOTIFICATION-TYPE
        OBJECTS  {
            trapSequence,
            trapResourceKey,
            trapTime,
            trapResourceAddress,
            trapResourceType,
            trapType,
            trapState,
            trapSeverity
            }
        STATUS current
        DESCRIPTION
            "Clears the Major Alarm for Router User Alarm 1."
        ::= { dnxTrapEnterprise 1241 }

clearRtrUserAlarm2 NOTIFICATION-TYPE
        OBJECTS  {
            trapSequence,
            trapResourceKey,
            trapTime,
            trapResourceAddress,
            trapResourceType,
            trapType,
            trapState,
            trapSeverity
            }
        STATUS current
        DESCRIPTION
            "Clears the Major Alarm for Router User Alarm 2."
        ::= { dnxTrapEnterprise 1242 }

clearRtrUserAlarm3 NOTIFICATION-TYPE
        OBJECTS  {
            trapSequence,
            trapResourceKey,
            trapTime,
            trapResourceAddress,
            trapResourceType,
            trapType,
            trapState,
            trapSeverity
            }
        STATUS current
        DESCRIPTION
            "Clears the Major Alarm for Router User Alarm 3."
        ::= { dnxTrapEnterprise 1243 }

clearRtrConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for Router configuration error."
        ::= { dnxTrapEnterprise 1265 }

evntRtrInService NOTIFICATION-TYPE
        OBJECTS  {
            trapSequence,
            trapResourceKey,
            trapTime,
            trapResourceAddress,
            trapResourceType,
            trapType,
            trapState,
            trapSeverity
            }
        STATUS current
        DESCRIPTION
            "Informational Event for Router in-service."
        ::= { dnxTrapEnterprise 1271 }

-- *************************************************************************
--  STS-1 Port Level Alarms/Events; base = 1300
-- *************************************************************************

setSts1RcvFarEndLOF NOTIFICATION-TYPE
        OBJECTS  {
            trapSequence,
            trapResourceKey,
            trapTime,
            trapResourceAddress,
            trapResourceType,
            trapType,
            trapState,
            trapSeverity
            }
        STATUS current
        DESCRIPTION
            "Major Alarm for STS1 receiving far end loss of frame
             (receiving yellow alarm)."
        ::= { dnxTrapEnterprise 1301 }

setSts1NearEndSendLOF NOTIFICATION-TYPE
        OBJECTS  {
            trapSequence,
            trapResourceKey,
            trapTime,
            trapResourceAddress,
            trapResourceType,
            trapType,
            trapState,
            trapSeverity
            }
        STATUS current
        DESCRIPTION
            "Major Alarm for STS1 near end sending loss of frame
             (transmitting yellow alarm)."
        ::= { dnxTrapEnterprise 1302 }

evntSts1RcvingAIS NOTIFICATION-TYPE
        OBJECTS  {
            trapSequence,
            trapResourceKey,
            trapTime,
            trapResourceAddress,
            trapResourceType,
            trapType,
            trapState,
            trapSeverity
            }
        STATUS current
        DESCRIPTION
            "Informational Event for STS1 far end sending alarm indication signal."
        ::= { dnxTrapEnterprise 1303 }

setSts1NearEndSendingAIS NOTIFICATION-TYPE
        OBJECTS  {
            trapSequence,
            trapResourceKey,
            trapTime,
            trapResourceAddress,
            trapResourceType,
            trapType,
            trapState,
            trapSeverity
            }
        STATUS current
        DESCRIPTION
            "Major Alarm for STS1 near end sending alarm indication signal."
        ::= { dnxTrapEnterprise 1304 }

setSts1NearEndLOF NOTIFICATION-TYPE
        OBJECTS  {
            trapSequence,
            trapResourceKey,
            trapTime,
            trapResourceAddress,
            trapResourceType,
            trapType,
            trapState,
            trapSeverity
            }
        STATUS current
        DESCRIPTION
            "Major Alarm for STS1 near end loss of frame (red alarm)."
        ::= { dnxTrapEnterprise 1305 }

evntSts1NearEndLooped NOTIFICATION-TYPE
        OBJECTS  {
            trapSequence,
            trapResourceKey,
            trapTime,
            trapResourceAddress,
            trapResourceType,
            trapType,
            trapState,
            trapSeverity
            }
        STATUS current
        DESCRIPTION
            "Informational Event for STS1 near end looped."
        ::= { dnxTrapEnterprise 1307 }

setSts1NearEndLOP NOTIFICATION-TYPE
        OBJECTS  {
            trapSequence,
            trapResourceKey,
            trapTime,
            trapResourceAddress,
            trapResourceType,
            trapType,
            trapState,
            trapSeverity
            }
        STATUS current
        DESCRIPTION
            "Major Alarm for STS1 near end loss of pointer."
        ::= { dnxTrapEnterprise 1308 }

setSts1NearEndOOF NOTIFICATION-TYPE
        OBJECTS  {
            trapSequence,
            trapResourceKey,
            trapTime,
            trapResourceAddress,
            trapResourceType,
            trapType,
            trapState,
            trapSeverity
            }
        STATUS current
        DESCRIPTION
            "Major Alarm for STS1 near end out-of-frame."
        ::= { dnxTrapEnterprise 1309 }

setSts1NearEndAIS NOTIFICATION-TYPE
        OBJECTS  {
            trapSequence,
            trapResourceKey,
            trapTime,
            trapResourceAddress,
            trapResourceType,
            trapType,
            trapState,
            trapSeverity
            }
        STATUS current
        DESCRIPTION
            "Major Alarm for STS1 alarm indication signal detected."
        ::= { dnxTrapEnterprise 1310 }

setSts1OtherLineStatus NOTIFICATION-TYPE
        OBJECTS  {
            trapSequence,
            trapResourceKey,
            trapTime,
            trapResourceAddress,
            trapResourceType,
            trapType,
            trapState,
            trapSeverity
            }
        STATUS current
        DESCRIPTION
            "Major Alarm for STS1 other line status."
        ::= { dnxTrapEnterprise 1312 }

setSts1NearEndUnavailableSig NOTIFICATION-TYPE
        OBJECTS  {
            trapSequence,
            trapResourceKey,
            trapTime,
            trapResourceAddress,
            trapResourceType,
            trapType,
            trapState,
            trapSeverity
            }
        STATUS current
        DESCRIPTION
            "Major Alarm for STS1 near end loss of signal."
        ::= { dnxTrapEnterprise 1313 }

evntSts1CarrierEquipOutOfService NOTIFICATION-TYPE
        OBJECTS  {
            trapSequence,
            trapResourceKey,
            trapTime,
            trapResourceAddress,
            trapResourceType,
            trapType,
            trapState,
            trapSeverity
            }
        STATUS current
        DESCRIPTION
            "Informational event for STS1 carrier equipment out-of-service."
        ::= { dnxTrapEnterprise 1314 }

setSts1TxRxClockFailure NOTIFICATION-TYPE
        OBJECTS  {
            trapSequence,
            trapResourceKey,
            trapTime,
            trapResourceAddress,
            trapResourceType,
            trapType,
            trapState,
            trapSeverity
            }
        STATUS current
        DESCRIPTION
            "Major Alarm for STS1 Transmit/Receive clock failure."
        ::= { dnxTrapEnterprise 1316 }

setSts1NearEndLOMF NOTIFICATION-TYPE
        OBJECTS  {
            trapSequence,
            trapResourceKey,
            trapTime,
            trapResourceAddress,
            trapResourceType,
            trapType,
            trapState,
            trapSeverity
            }
        STATUS current
        DESCRIPTION
            "Major Alarm for STS1 loss of multi-frame indication."
        ::= { dnxTrapEnterprise 1317 }

setSts1NearEndTraceError NOTIFICATION-TYPE
        OBJECTS  {
            trapSequence,
            trapResourceKey,
            trapTime,
            trapResourceAddress,
            trapResourceType,
            trapType,
            trapState,
            trapSeverity
            }
        STATUS current
        DESCRIPTION
            "Major Alarm for error received in path trace."
        ::= { dnxTrapEnterprise 1318 }

setSts1LIUDigitalLOS NOTIFICATION-TYPE
        OBJECTS  {
            trapSequence,
            trapResourceKey,
            trapTime,
            trapResourceAddress,
            trapResourceType,
            trapType,
            trapState,
            trapSeverity
            }
        STATUS current
        DESCRIPTION
            "Major Alarm for STS1 LIU digital loss of signal."
        ::= { dnxTrapEnterprise 1320 }

setSts1LIUAnalogLOS NOTIFICATION-TYPE
        OBJECTS  {
            trapSequence,
            trapResourceKey,
            trapTime,
            trapResourceAddress,
            trapResourceType,
            trapType,
            trapState,
            trapSeverity
            }
        STATUS current
        DESCRIPTION
            "Major Alarm for STS1 LIU analog loss of signal."
        ::= { dnxTrapEnterprise 1321 }

setSts1LIUExcessZeros NOTIFICATION-TYPE
        OBJECTS  {
            trapSequence,
            trapResourceKey,
            trapTime,
            trapResourceAddress,
            trapResourceType,
            trapType,
            trapState,
            trapSeverity
            }
        STATUS current
        DESCRIPTION
            "Major Alarm for STS1 LIU excessive zeros."
        ::= { dnxTrapEnterprise 1322 }

setSts1LIUCodingViolation NOTIFICATION-TYPE
        OBJECTS  {
            trapSequence,
            trapResourceKey,
            trapTime,
            trapResourceAddress,
            trapResourceType,
            trapType,
            trapState,
            trapSeverity
            }
        STATUS current
        DESCRIPTION
            "Major Alarm for STS1 LIU line coding violation."
        ::= { dnxTrapEnterprise 1323 }

setSts1LIUPrbsError NOTIFICATION-TYPE
        OBJECTS  {
            trapSequence,
            trapResourceKey,
            trapTime,
            trapResourceAddress,
            trapResourceType,
            trapType,
            trapState,
            trapSeverity
            }
        STATUS current
        DESCRIPTION
            "Major Alarm for STS1 LIU PRBS error."
        ::= { dnxTrapEnterprise 1324 }

setSts1ConfigError NOTIFICATION-TYPE
        OBJECTS  {
            trapSequence,
            trapResourceKey,
            trapTime,
            trapResourceAddress,
            trapResourceType,
            trapType,
            trapState,
            trapSeverity
            }
        STATUS current
        DESCRIPTION
            "Major Alarm for STS1 configuration error."
        ::= { dnxTrapEnterprise 1325 }

evntSts1InTest NOTIFICATION-TYPE
        OBJECTS  {
            trapSequence,
            trapResourceKey,
            trapTime,
            trapResourceAddress,
            trapResourceType,
            trapType,
            trapState,
            trapSeverity
            }
        STATUS current
        DESCRIPTION
            "Informational event for STS1 in test."
        ::= { dnxTrapEnterprise 1330 }

evntSts1OutOfService NOTIFICATION-TYPE
        OBJECTS  {
            trapSequence,
            trapResourceKey,
            trapTime,
            trapResourceAddress,
            trapResourceType,
            trapType,
            trapState,
            trapSeverity
            }
        STATUS current
        DESCRIPTION
            "Informational event for STS1 out-of-service."
        ::= { dnxTrapEnterprise 1331 }

clearSts1RcvFarEndLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 receiving far end loss of
             frame (receiving yellow alarm)."
        ::= { dnxTrapEnterprise 1341 }

clearSts1NearEndSendLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 near end sending loss of frame
            (transmitting yellow alarm)."
        ::= { dnxTrapEnterprise 1342 }

evntSts1StoppedRcvingAIS NOTIFICATION-TYPE
        OBJECTS  {
            trapSequence,
            trapResourceKey,
            trapTime,
            trapResourceAddress,
            trapResourceType,
            trapType,
            trapState,
            trapSeverity
            }
        STATUS current
        DESCRIPTION
            "Informational Event when STS1 far end stops sending alarm
             indication signal."
        ::= { dnxTrapEnterprise 1343 }

clearSts1NearEndSendingAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 near end sending alarm
             indication signal."
        ::= { dnxTrapEnterprise 1344 }

clearSts1NearEndLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 near end loss of frame
             (red alarm)."
        ::= { dnxTrapEnterprise 1345 }

evntSts1NearEndLoopOff NOTIFICATION-TYPE
        OBJECTS  {
            trapSequence,
            trapResourceKey,
            trapTime,
            trapResourceAddress,
            trapResourceType,
            trapType,
            trapState,
            trapSeverity
            }
        STATUS current
        DESCRIPTION
            "Informational Event for STS1 near end loop off."
        ::= { dnxTrapEnterprise 1347 }

clearSts1NearEndLOP NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 near end loss of pointer."
        ::= { dnxTrapEnterprise 1348 }

clearSts1NearEndOOF NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 near end out-of-frame."
        ::= { dnxTrapEnterprise 1349 }

clearSts1NearEndAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 alarm indication signal
             detected."
        ::= { dnxTrapEnterprise 1350 }

clearSts1OtherLineStatus NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 other line status."
        ::= { dnxTrapEnterprise 1352 }

clearSts1NearEndUnavailableSig NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 near end loss of signal."
        ::= { dnxTrapEnterprise 1353 }

evntSts1CarrierEquipInService NOTIFICATION-TYPE
        OBJECTS  {
            trapSequence,
            trapResourceKey,
            trapTime,
            trapResourceAddress,
            trapResourceType,
            trapType,
            trapState,
            trapSeverity
            }
        STATUS current
        DESCRIPTION
            "Informational event for STS1 carrier equipment in-service."
        ::= { dnxTrapEnterprise 1354 }

clearSts1TxRxClockFailure NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 Transmit/Receive clock
             failure."
        ::= { dnxTrapEnterprise 1356 }

clearSts1NearEndLOMF NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 loss of multi-frame indication."
        ::= { dnxTrapEnterprise 1357 }

clearSts1NearEndTraceError NOTIFICATION-TYPE
        OBJECTS  {
            trapSequence,
            trapResourceKey,
            trapTime,
            trapResourceAddress,
            trapResourceType,
            trapType,
            trapState,
            trapSeverity
            }
        STATUS current
        DESCRIPTION
            "Clears the Major Alarm for error received in path trace."
        ::= { dnxTrapEnterprise 1358 }

clearSts1LIUDigitalLOS NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 LIU digital loss of signal."
        ::= { dnxTrapEnterprise 1360 }

clearSts1LIUAnalogLOS NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 LIU analog loss of signal."
        ::= { dnxTrapEnterprise 1361 }

clearSts1LIUExcessZeros NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 LIU excessive zeros."
        ::= { dnxTrapEnterprise 1362 }

clearSts1LIUCodingViolation NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 LIU line coding violation."
        ::= { dnxTrapEnterprise 1363 }

clearSts1LIUPrbsError NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 LIU PRBS error."
        ::= { dnxTrapEnterprise 1364 }

clearSts1ConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for STS1 configuration error."
        ::= { dnxTrapEnterprise 1365 }

evntSts1TestOff NOTIFICATION-TYPE
        OBJECTS  {
            trapSequence,
            trapResourceKey,
            trapTime,
            trapResourceAddress,
            trapResourceType,
            trapType,
            trapState,
            trapSeverity
            }
        STATUS current
        DESCRIPTION
            "Informational event for STS1 test off."
        ::= { dnxTrapEnterprise 1370 }

evntSts1InService NOTIFICATION-TYPE
        OBJECTS  {
            trapSequence,
            trapResourceKey,
            trapTime,
            trapResourceAddress,
            trapResourceType,
            trapType,
            trapState,
            trapSeverity
            }
        STATUS current
        DESCRIPTION
            "Informational event for STS1 in-service."
        ::= { dnxTrapEnterprise 1371 }

-- *************************************************************************
--  Hybrid DS3 Port Level Alarms/Events; base = 1400
-- *************************************************************************

evntHt3RcvingAIS NOTIFICATION-TYPE
        OBJECTS  {
            trapSequence,
            trapResourceKey,
            trapTime,
            trapResourceAddress,
            trapResourceType,
            trapType,
            trapState,
            trapSeverity
            }
        STATUS current
        DESCRIPTION
            "Informational Event for Hybrid DS3 far end sending alarm indication
             signal."
        ::= { dnxTrapEnterprise 1403 }

setHt3NearEndSendingAIS NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 near end sending alarm indication
             signal."
        ::= { dnxTrapEnterprise 1404 }

setHt3NearEndOOF NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 near end out-of-frame."
        ::= { dnxTrapEnterprise 1405 }

setHt3NearEndLossOfSignal NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 near end loss of signal."
        ::= { dnxTrapEnterprise 1406 }

evntHt3NearEndLooped NOTIFICATION-TYPE
        OBJECTS  {
            trapSequence,
            trapResourceKey,
            trapTime,
            trapResourceAddress,
            trapResourceType,
            trapType,
            trapState,
            trapSeverity
            }
        STATUS current
        DESCRIPTION
            "Informational Event for Hybrid DS3 near end looped."
        ::= { dnxTrapEnterprise 1407 }

setHt3NearEndLOF NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 loss of frame (red alarm)."
        ::= { dnxTrapEnterprise 1408 }

setHt3FarEndRcvFailure NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 far end received failure error."
        ::= { dnxTrapEnterprise 1409 }

setHt3NearEndLCVError NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 near end line code violation error."
        ::= { dnxTrapEnterprise 1411 }

setHt3NearEndFERRError NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 near end framing error."
        ::= { dnxTrapEnterprise 1412 }

setHt3NearEndExcessZeros NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 near end excessive zeros."
        ::= { dnxTrapEnterprise 1413 }

evntHt3CarrierEquipOutOfService NOTIFICATION-TYPE
        OBJECTS  {
            trapSequence,
            trapResourceKey,
            trapTime,
            trapResourceAddress,
            trapResourceType,
            trapType,
            trapState,
            trapSeverity
            }
        STATUS current
        DESCRIPTION
            "Informational Event for Hybrid DS3 carrier equipment
             out-of-service."
        ::= { dnxTrapEnterprise 1414 }

setHt3FarEndBlockError NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 far end block error."
        ::= { dnxTrapEnterprise 1417 }

setHt3PbitCbitParityError NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 P-bit or C-bit parity error."
        ::= { dnxTrapEnterprise 1418 }

setHt3ChangeInFrameAlignment NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 CFA Indication."
        ::= { dnxTrapEnterprise 1419 }

setHt3LIUDigitalLOS NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 LIU digital loss of signal."
        ::= { dnxTrapEnterprise 1420 }

setHt3LIUAnalogLOS NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 LIU analog loss of signal."
        ::= { dnxTrapEnterprise 1421 }

setHt3LIUExcessZeros NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 LIU excessive zeros."
        ::= { dnxTrapEnterprise 1422 }

setHt3LIUCodingViolation NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 LIU line coding violation."
        ::= { dnxTrapEnterprise 1423 }

setHt3LIUPrbsError NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 LIU PRBS Error."
        ::= { dnxTrapEnterprise 1424 }

setHt3ConfigError NOTIFICATION-TYPE
        OBJECTS  {
            trapSequence,
            trapResourceKey,
            trapTime,
            trapResourceAddress,
            trapResourceType,
            trapType,
            trapState,
            trapSeverity
            }
        STATUS current
        DESCRIPTION
            "Major Alarm for Hybrid DS3 configuration error."
        ::= { dnxTrapEnterprise 1425 }

evntHt3InTest NOTIFICATION-TYPE
        OBJECTS  {
            trapSequence,
            trapResourceKey,
            trapTime,
            trapResourceAddress,
            trapResourceType,
            trapType,
            trapState,
            trapSeverity
            }
        STATUS current
        DESCRIPTION
            "Informational Event for Hybrid DS3 in test."
        ::= { dnxTrapEnterprise 1430 }

evntHt3OutOfService NOTIFICATION-TYPE
        OBJECTS  {
            trapSequence,
            trapResourceKey,
            trapTime,
            trapResourceAddress,
            trapResourceType,
            trapType,
            trapState,
            trapSeverity
            }
        STATUS current
        DESCRIPTION
            "Informational Event for Hybrid DS3 out-of-service."
        ::= { dnxTrapEnterprise 1431 }

evntHt3StoppedRcvingAIS NOTIFICATION-TYPE
        OBJECTS  {
            trapSequence,
            trapResourceKey,
            trapTime,
            trapResourceAddress,
            trapResourceType,
            trapType,
            trapState,
            trapSeverity
            }
        STATUS current
        DESCRIPTION
            "Informational Event when Hybrid DS3 far end stops sending alarm
             indication signal."
        ::= { dnxTrapEnterprise 1443 }

clearHt3NearEndSendingAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 near end sending alarm
             indication signal."
        ::= { dnxTrapEnterprise 1444 }

clearHt3NearEndOOF NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 near end out-of-frame."
        ::= { dnxTrapEnterprise 1445 }

clearHt3NearEndLossOfSignal NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 near end loss of signal."
        ::= { dnxTrapEnterprise 1446 }

evntHt3NearEndLoopOff NOTIFICATION-TYPE
        OBJECTS  {
            trapSequence,
            trapResourceKey,
            trapTime,
            trapResourceAddress,
            trapResourceType,
            trapType,
            trapState,
            trapSeverity
            }
        STATUS current
        DESCRIPTION
            "Informational Event for Hybrid DS3 near end loop off."
        ::= { dnxTrapEnterprise 1447 }

clearHt3NearEndLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 loss of frame
             (red alarm)."
        ::= { dnxTrapEnterprise 1448 }

clearHt3FarEndRcvFailure NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 far end received failure
             error."
        ::= { dnxTrapEnterprise 1449 }

clearHt3NearEndLCVError NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 near end line code
             violation error."
        ::= { dnxTrapEnterprise 1451 }

clearHt3NearEndFERRError NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 near end framing error."
        ::= { dnxTrapEnterprise 1452 }

clearHt3NearEndExcessZeros NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 near end excessive
             zeros."
        ::= { dnxTrapEnterprise 1453 }

evntHt3CarrierEquipInService NOTIFICATION-TYPE
        OBJECTS  {
            trapSequence,
            trapResourceKey,
            trapTime,
            trapResourceAddress,
            trapResourceType,
            trapType,
            trapState,
            trapSeverity
            }
        STATUS current
        DESCRIPTION
            "Informational Event for Hybrid DS3 carrier equipment
             in-service."
        ::= { dnxTrapEnterprise 1454 }

clearHt3FarEndBlockError NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 far end block error."
        ::= { dnxTrapEnterprise 1457 }

clearHt3PbitCbitParityError NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 P-bit or C-bit
             parity error."
        ::= { dnxTrapEnterprise 1458 }

clearHt3ChangeInFrameAlignment NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 CFA Indication."
        ::= { dnxTrapEnterprise 1459 }

clearHt3LIUDigitalLOS NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 LIU digital loss
             of signal."
        ::= { dnxTrapEnterprise 1460 }

clearHt3LIUAnalogLOS NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 LIU analog loss
             of signal."
        ::= { dnxTrapEnterprise 1461 }

clearHt3LIUExcessZeros NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 LIU excessive zeros."
        ::= { dnxTrapEnterprise 1462 }

clearHt3LIUCodingViolation NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 LIU line coding
             violation."
        ::= { dnxTrapEnterprise 1463 }

clearHt3LIUPrbsError NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 LIU PRBS Error."
        ::= { dnxTrapEnterprise 1464 }

clearHt3ConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for Hybrid DS3 configuration error."
        ::= { dnxTrapEnterprise 1465 }

evntHt3TestOff NOTIFICATION-TYPE
        OBJECTS  {
            trapSequence,
            trapResourceKey,
            trapTime,
            trapResourceAddress,
            trapResourceType,
            trapType,
            trapState,
            trapSeverity
            }
        STATUS current
        DESCRIPTION
            "Informational Event for Hybrid DS3 test off."
        ::= { dnxTrapEnterprise 1470 }

evntHt3InService NOTIFICATION-TYPE
        OBJECTS  {
            trapSequence,
            trapResourceKey,
            trapTime,
            trapResourceAddress,
            trapResourceType,
            trapType,
            trapState,
            trapSeverity
            }
        STATUS current
        DESCRIPTION
            "Informational Event for Hybrid DS3 in-service."
        ::= { dnxTrapEnterprise 1471 }

-- *************************************************************************
--  GR-303 Alarms/Events; base = 1500
-- *************************************************************************

evntGr303OutOfService NOTIFICATION-TYPE
        OBJECTS  {
            trapSequence,
            trapResourceKey,
            trapTime,
            trapResourceAddress,
            trapResourceType,
            trapType,
            trapState,
            trapSeverity
            }
        STATUS current
        DESCRIPTION
            "Informational Event for GR-303 out-of-service."
        ::= { dnxTrapEnterprise 1531 }

evntGr303InService NOTIFICATION-TYPE
        OBJECTS  {
            trapSequence,
            trapResourceKey,
            trapTime,
            trapResourceAddress,
            trapResourceType,
            trapType,
            trapState,
            trapSeverity
            }
        STATUS current
        DESCRIPTION
            "Informational Event for GR-303 in-service."
        ::= { dnxTrapEnterprise 1571 }

-- *************************************************************************
--  X-link Level Alarms/Events; base = 1600
-- *************************************************************************

setXlinkCableMismatch NOTIFICATION-TYPE
        OBJECTS  {
            trapSequence,
            trapResourceKey,
            trapTime,
            trapResourceAddress,
            trapResourceType,
            trapType,
            trapState,
            trapSeverity
            }
        STATUS current
        DESCRIPTION
            "Major Alarm for X-Link Cable/Configuration Nest ID mismatch."
        ::= { dnxTrapEnterprise 1606 }

setXlinkSerializerError NOTIFICATION-TYPE
        OBJECTS  {
            trapSequence,
            trapResourceKey,
            trapTime,
            trapResourceAddress,
            trapResourceType,
            trapType,
            trapState,
            trapSeverity
            }
        STATUS current
        DESCRIPTION
            "Major Alarm for X-Link serializer error."
        ::= { dnxTrapEnterprise 1615 }

setXlinkFramerError NOTIFICATION-TYPE
        OBJECTS  {
            trapSequence,
            trapResourceKey,
            trapTime,
            trapResourceAddress,
            trapResourceType,
            trapType,
            trapState,
            trapSeverity
            }
        STATUS current
        DESCRIPTION
            "Major Alarm for X-Link Framer error."
        ::= { dnxTrapEnterprise 1616 }

setXlinkBertError NOTIFICATION-TYPE
        OBJECTS  {
            trapSequence,
            trapResourceKey,
            trapTime,
            trapResourceAddress,
            trapResourceType,
            trapType,
            trapState,
            trapSeverity
            }
        STATUS current
        DESCRIPTION
            "Major Alarm for X-Link BERT error."
        ::= { dnxTrapEnterprise 1617 }

setXlinkClockError NOTIFICATION-TYPE
        OBJECTS  {
            trapSequence,
            trapResourceKey,
            trapTime,
            trapResourceAddress,
            trapResourceType,
            trapType,
            trapState,
            trapSeverity
            }
        STATUS current
        DESCRIPTION
            "Major Alarm for X-Link clock error."
        ::= { dnxTrapEnterprise 1618 }

setXlinkInUseError NOTIFICATION-TYPE
        OBJECTS  {
            trapSequence,
            trapResourceKey,
            trapTime,
            trapResourceAddress,
            trapResourceType,
            trapType,
            trapState,
            trapSeverity
            }
        STATUS current
        DESCRIPTION
            "Major Alarm for X-Link in use error."
        ::= { dnxTrapEnterprise 1620 }

setXlinkCrcError NOTIFICATION-TYPE
        OBJECTS  {
            trapSequence,
            trapResourceKey,
            trapTime,
            trapResourceAddress,
            trapResourceType,
            trapType,
            trapState,
            trapSeverity
            }
        STATUS current
        DESCRIPTION
            "Major Alarm for X-Link CRC error."
        ::= { dnxTrapEnterprise 1621 }

clearXlinkCableMismatch NOTIFICATION-TYPE
        OBJECTS  {
            trapSequence,
            trapResourceKey,
            trapTime,
            trapResourceAddress,
            trapResourceType,
            trapType,
            trapState,
            trapSeverity
            }
        STATUS current
        DESCRIPTION
            "Clears the Major Alarm for X-Link Cable/Configuration Nest ID 
            mismatch."
        ::= { dnxTrapEnterprise 1646 }

clearXlinkSerializerError NOTIFICATION-TYPE
        OBJECTS  {
            trapSequence,
            trapResourceKey,
            trapTime,
            trapResourceAddress,
            trapResourceType,
            trapType,
            trapState,
            trapSeverity
            }
        STATUS current
        DESCRIPTION
            "Clears the Major Alarm for X-Link serializer error."
        ::= { dnxTrapEnterprise 1655 }

clearXlinkFramerError NOTIFICATION-TYPE
        OBJECTS  {
            trapSequence,
            trapResourceKey,
            trapTime,
            trapResourceAddress,
            trapResourceType,
            trapType,
            trapState,
            trapSeverity
            }
        STATUS current
        DESCRIPTION
            "Clears the Major Alarm for X-Link Framer error."
        ::= { dnxTrapEnterprise 1656 }

clearXlinkBertError NOTIFICATION-TYPE
        OBJECTS  {
            trapSequence,
            trapResourceKey,
            trapTime,
            trapResourceAddress,
            trapResourceType,
            trapType,
            trapState,
            trapSeverity
            }
        STATUS current
        DESCRIPTION
            "Clears the Major Alarm for X-Link BERT error."
        ::= { dnxTrapEnterprise 1657 }

clearXlinkClockError NOTIFICATION-TYPE
        OBJECTS  {
            trapSequence,
            trapResourceKey,
            trapTime,
            trapResourceAddress,
            trapResourceType,
            trapType,
            trapState,
            trapSeverity
            }
        STATUS current
        DESCRIPTION
            "Clears the Major Alarm for X-Link clock error."
        ::= { dnxTrapEnterprise 1658 }

clearXlinkInUseError NOTIFICATION-TYPE
        OBJECTS  {
            trapSequence,
            trapResourceKey,
            trapTime,
            trapResourceAddress,
            trapResourceType,
            trapType,
            trapState,
            trapSeverity
            }
        STATUS current
        DESCRIPTION
            "Clears the Major Alarm for X-Link in use error."
        ::= { dnxTrapEnterprise 1660 }

clearXlinkCrcError NOTIFICATION-TYPE
        OBJECTS  {
            trapSequence,
            trapResourceKey,
            trapTime,
            trapResourceAddress,
            trapResourceType,
            trapType,
            trapState,
            trapSeverity
            }
        STATUS current
        DESCRIPTION
            "Clears the Major Alarm for X-Link CRC error."
        ::= { dnxTrapEnterprise 1661 }

-- *************************************************************************
--  Nest Level Alarms/Events; base = 1700
-- *************************************************************************

setNestMismatch NOTIFICATION-TYPE
        OBJECTS  {
            trapSequence,
            trapResourceKey,
            trapTime,
            trapResourceAddress,
            trapResourceType,
            trapType,
            trapState,
            trapSeverity
            }
        STATUS current
        DESCRIPTION
            "Critical Alarm for nest mismatch."
        ::= { dnxTrapEnterprise 1701 }

setNestMissing NOTIFICATION-TYPE
        OBJECTS  {
            trapSequence,
            trapResourceKey,
            trapTime,
            trapResourceAddress,
            trapResourceType,
            trapType,
            trapState,
            trapSeverity
            }
        STATUS current
        DESCRIPTION
            "Critical Alarm for nest missing."
        ::= { dnxTrapEnterprise 1702 }

setNestOffline NOTIFICATION-TYPE
        OBJECTS  {
            trapSequence,
            trapResourceKey,
            trapTime,
            trapResourceAddress,
            trapResourceType,
            trapType,
            trapState,
            trapSeverity
            }
        STATUS current
        DESCRIPTION
            "Critical Alarm for nest offline."
        ::= { dnxTrapEnterprise 1705 }

setNestCriticalAlarm NOTIFICATION-TYPE
        OBJECTS  {
            trapSequence,
            trapResourceKey,
            trapTime,
            trapResourceAddress,
            trapResourceType,
            trapType,
            trapState,
            trapSeverity
            }
        STATUS current
        DESCRIPTION
            "Summary Critical Alarm for nest."
        ::= { dnxTrapEnterprise 1706 }

setNestMajorAlarm NOTIFICATION-TYPE
        OBJECTS  {
            trapSequence,
            trapResourceKey,
            trapTime,
            trapResourceAddress,
            trapResourceType,
            trapType,
            trapState,
            trapSeverity
            }
        STATUS current
        DESCRIPTION
            "Summary Major Alarm for nest."
        ::= { dnxTrapEnterprise 1707 }

setNestMinorAlarm NOTIFICATION-TYPE
        OBJECTS  {
            trapSequence,
            trapResourceKey,
            trapTime,
            trapResourceAddress,
            trapResourceType,
            trapType,
            trapState,
            trapSeverity
            }
        STATUS current
        DESCRIPTION
            "Summary Minor Alarm for nest."
        ::= { dnxTrapEnterprise 1708 }

setNestSwMismatch NOTIFICATION-TYPE
        OBJECTS  {
            trapSequence,
            trapResourceKey,
            trapTime,
            trapResourceAddress,
            trapResourceType,
            trapType,
            trapState,
            trapSeverity
            }
        STATUS current
        DESCRIPTION
            "Minor Alarm for unit firmware image mismatch."
        ::= { dnxTrapEnterprise 1709 }

clearNestMismatch NOTIFICATION-TYPE
        OBJECTS  {
            trapSequence,
            trapResourceKey,
            trapTime,
            trapResourceAddress,
            trapResourceType,
            trapType,
            trapState,
            trapSeverity
            }
        STATUS current
        DESCRIPTION
            "Clears the Critical Alarm for nest mismatch."
        ::= { dnxTrapEnterprise 1741 }

clearNestMissing NOTIFICATION-TYPE
        OBJECTS  {
            trapSequence,
            trapResourceKey,
            trapTime,
            trapResourceAddress,
            trapResourceType,
            trapType,
            trapState,
            trapSeverity
            }
        STATUS current
        DESCRIPTION
            "Clears the Critical Alarm for nest missing."
        ::= { dnxTrapEnterprise 1742 }

clearNestOffline NOTIFICATION-TYPE
        OBJECTS  {
            trapSequence,
            trapResourceKey,
            trapTime,
            trapResourceAddress,
            trapResourceType,
            trapType,
            trapState,
            trapSeverity
            }
        STATUS current
        DESCRIPTION
            "Clears the Critical Alarm for nest offline."
        ::= { dnxTrapEnterprise 1745 }

clearNestCriticalAlarm NOTIFICATION-TYPE
        OBJECTS  {
            trapSequence,
            trapResourceKey,
            trapTime,
            trapResourceAddress,
            trapResourceType,
            trapType,
            trapState,
            trapSeverity
            }
        STATUS current
        DESCRIPTION
            "Clears the Summary Critical Alarm for nest."
        ::= { dnxTrapEnterprise 1746 }

clearNestMajorAlarm NOTIFICATION-TYPE
        OBJECTS  {
            trapSequence,
            trapResourceKey,
            trapTime,
            trapResourceAddress,
            trapResourceType,
            trapType,
            trapState,
            trapSeverity
            }
        STATUS current
        DESCRIPTION
            "Clears the Summary Major Alarm for nest."
        ::= { dnxTrapEnterprise 1747 }

clearNestMinorAlarm NOTIFICATION-TYPE
        OBJECTS  {
            trapSequence,
            trapResourceKey,
            trapTime,
            trapResourceAddress,
            trapResourceType,
            trapType,
            trapState,
            trapSeverity
            }
        STATUS current
        DESCRIPTION
            "Clears the Summary Minor Alarm for nest."
        ::= { dnxTrapEnterprise 1748 }

clearNestSwMismatch NOTIFICATION-TYPE
        OBJECTS  {
            trapSequence,
            trapResourceKey,
            trapTime,
            trapResourceAddress,
            trapResourceType,
            trapType,
            trapState,
            trapSeverity
            }
        STATUS current
        DESCRIPTION
            "Clears the Minor Alarm for unit firmware image mismatch."
        ::= { dnxTrapEnterprise 1749 }

-- *************************************************************************
--  Node Level Alarms/Events; base = 1800
-- *************************************************************************

setNodeCriticalAlarm NOTIFICATION-TYPE
        OBJECTS  {
            trapSequence,
            trapResourceKey,
            trapTime,
            trapResourceAddress,
            trapResourceType,
            trapType,
            trapState,
            trapSeverity
            }
        STATUS current
        DESCRIPTION
            "Critical Alarm for the node."
        ::= { dnxTrapEnterprise 1801 }

setNodeMajorAlarm NOTIFICATION-TYPE
        OBJECTS  {
            trapSequence,
            trapResourceKey,
            trapTime,
            trapResourceAddress,
            trapResourceType,
            trapType,
            trapState,
            trapSeverity
            }
        STATUS current
        DESCRIPTION
            "Major Alarm for the node."
        ::= { dnxTrapEnterprise 1802 }

setNodeMinorAlarm NOTIFICATION-TYPE
        OBJECTS  {
            trapSequence,
            trapResourceKey,
            trapTime,
            trapResourceAddress,
            trapResourceType,
            trapType,
            trapState,
            trapSeverity
            }
        STATUS current
        DESCRIPTION
            "Minor Alarm for the node."
        ::= { dnxTrapEnterprise 1803 }

clearNodeCriticalAlarm NOTIFICATION-TYPE
        OBJECTS  {
            trapSequence,
            trapResourceKey,
            trapTime,
            trapResourceAddress,
            trapResourceType,
            trapType,
            trapState,
            trapSeverity
            }
        STATUS current
        DESCRIPTION
            "Clears the Critical Alarm for the node."
        ::= { dnxTrapEnterprise 1841 }

clearNodeMajorAlarm NOTIFICATION-TYPE
        OBJECTS  {
            trapSequence,
            trapResourceKey,
            trapTime,
            trapResourceAddress,
            trapResourceType,
            trapType,
            trapState,
            trapSeverity
            }
        STATUS current
        DESCRIPTION
            "Clears the Major Alarm for the node."
        ::= { dnxTrapEnterprise 1842 }

clearNodeMinorAlarm NOTIFICATION-TYPE
        OBJECTS  {
            trapSequence,
            trapResourceKey,
            trapTime,
            trapResourceAddress,
            trapResourceType,
            trapType,
            trapState,
            trapSeverity
            }
        STATUS current
        DESCRIPTION
            "Clears the Minor Alarm for the node."
        ::= { dnxTrapEnterprise 1843 }

-- *************************************************************************
--  DS0-DP Port Level Alarms/Events; base = 1900
-- *************************************************************************

setDs0DpPortLossOfSignal NOTIFICATION-TYPE
        OBJECTS  {
            trapSequence,
            trapResourceKey,
            trapTime,
            trapResourceAddress,
            trapResourceType,
            trapType,
            trapState,
            trapSeverity
            }
        STATUS current
        DESCRIPTION
            "Major Alarm for DS0-DP port loss of signal."
        ::= { dnxTrapEnterprise 1901 }

setDs0DpPortBPV NOTIFICATION-TYPE
        OBJECTS  {
            trapSequence,
            trapResourceKey,
            trapTime,
            trapResourceAddress,
            trapResourceType,
            trapType,
            trapState,
            trapSeverity
            }
        STATUS current
        DESCRIPTION
            "Major Alarm for DS0-DP port bi-polar violations."
        ::= { dnxTrapEnterprise 1902 }

setDs0DpPortConfigError NOTIFICATION-TYPE
        OBJECTS  {
            trapSequence,
            trapResourceKey,
            trapTime,
            trapResourceAddress,
            trapResourceType,
            trapType,
            trapState,
            trapSeverity
            }
        STATUS current
        DESCRIPTION
            "Major Alarm for DS0-DP port configuration error."
        ::= { dnxTrapEnterprise 1925 }

evntDs0DpPortInTest NOTIFICATION-TYPE
        OBJECTS  {
            trapSequence,
            trapResourceKey,
            trapTime,
            trapResourceAddress,
            trapResourceType,
            trapType,
            trapState,
            trapSeverity
            }
        STATUS current
        DESCRIPTION
            "Informational Event for DS0-DP port in test."
        ::= { dnxTrapEnterprise 1930 }

evntDs0DpPortOutOfService NOTIFICATION-TYPE
        OBJECTS  {
            trapSequence,
            trapResourceKey,
            trapTime,
            trapResourceAddress,
            trapResourceType,
            trapType,
            trapState,
            trapSeverity
            }
        STATUS current
        DESCRIPTION
            "Informational Event for DS0-DP port out-of-service."
        ::= { dnxTrapEnterprise 1931 }

clearDs0DpPortLossOfSignal NOTIFICATION-TYPE
        OBJECTS  {
            trapSequence,
            trapResourceKey,
            trapTime,
            trapResourceAddress,
            trapResourceType,
            trapType,
            trapState,
            trapSeverity
            }
        STATUS current
        DESCRIPTION
            "Clears the Major Alarm for DS0-DP port loss of signal."
        ::= { dnxTrapEnterprise 1941 }

clearDs0DpPortBPV NOTIFICATION-TYPE
        OBJECTS  {
            trapSequence,
            trapResourceKey,
            trapTime,
            trapResourceAddress,
            trapResourceType,
            trapType,
            trapState,
            trapSeverity
            }
        STATUS current
        DESCRIPTION
            "Clears the Major Alarm for DS0-DP port bi-polar violations."
        ::= { dnxTrapEnterprise 1942 }

clearDs0DpPortConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for DS0-DP port configuration error."
        ::= { dnxTrapEnterprise 1965 }

evntDs0DpPortTestOff NOTIFICATION-TYPE
        OBJECTS  {
            trapSequence,
            trapResourceKey,
            trapTime,
            trapResourceAddress,
            trapResourceType,
            trapType,
            trapState,
            trapSeverity
            }
        STATUS current
        DESCRIPTION
            "Informational Event for DS0-DP port test off."
        ::= { dnxTrapEnterprise 1970 }

evntDs0DpPortInService NOTIFICATION-TYPE
        OBJECTS  {
            trapSequence,
            trapResourceKey,
            trapTime,
            trapResourceAddress,
            trapResourceType,
            trapType,
            trapState,
            trapSeverity
            }
        STATUS current
        DESCRIPTION
            "Informational Event for DS0-DP port in-service."
        ::= { dnxTrapEnterprise 1971 }

-- *************************************************************************
--  DS0-DP Bits Level Alarms/Events; base = 2000
-- *************************************************************************

setDs0DpBitsLossOfSignal NOTIFICATION-TYPE
        OBJECTS  {
            trapSequence,
            trapResourceKey,
            trapTime,
            trapResourceAddress,
            trapResourceType,
            trapType,
            trapState,
            trapSeverity
            }
        STATUS current
        DESCRIPTION
            "Major Alarm for DS0-DP bits loss of signal."
        ::= { dnxTrapEnterprise 2001 }

setDs0DpBitsBPV NOTIFICATION-TYPE
        OBJECTS  {
            trapSequence,
            trapResourceKey,
            trapTime,
            trapResourceAddress,
            trapResourceType,
            trapType,
            trapState,
            trapSeverity
            }
        STATUS current
        DESCRIPTION
            "Major Alarm for DS0-DP bits bi-polar violations."
        ::= { dnxTrapEnterprise 2002 }

clearDs0DpBitsLossOfSignal NOTIFICATION-TYPE
        OBJECTS  {
            trapSequence,
            trapResourceKey,
            trapTime,
            trapResourceAddress,
            trapResourceType,
            trapType,
            trapState,
            trapSeverity
            }
        STATUS current
        DESCRIPTION
            "Clears the Major Alarm for DS0-DP bits loss of signal."
        ::= { dnxTrapEnterprise 2041 }

clearDs0DpBitsBPV NOTIFICATION-TYPE
        OBJECTS  {
            trapSequence,
            trapResourceKey,
            trapTime,
            trapResourceAddress,
            trapResourceType,
            trapType,
            trapState,
            trapSeverity
            }
        STATUS current
        DESCRIPTION
            "Clears the Major Alarm for DS0-DP bits bi-polar violations."
        ::= { dnxTrapEnterprise 2042 }

-- *************************************************************************
--  Optical T1/E1 Port Level Alarms/Events; base = 2200
-- *************************************************************************

setOpticalT1E1RedAlarm NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port in Red Alarm state."
        ::= { dnxTrapEnterprise 2201 }

setOpticalT1E1NearEndSendLOF NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port near end sending loss
            of frame (transmitting yellow alarm)."
        ::= { dnxTrapEnterprise 2202 }

evntOpticalT1E1RcvingAIS NOTIFICATION-TYPE
        OBJECTS  {
            trapSequence,
            trapResourceKey,
            trapTime,
            trapResourceAddress,
            trapResourceType,
            trapType,
            trapState,
            trapSeverity
            }
        STATUS current
        DESCRIPTION
            "Informational event for Optical T1/E1 port far end sending alarm indication
            signal."
        ::= { dnxTrapEnterprise 2203 }

setOpticalT1E1NearEndSendingAIS NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port near end sending alarm indication
            signal."
        ::= { dnxTrapEnterprise 2204 }

setOpticalT1E1NearEndLOF NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port near end loss of frame (red alarm)."
        ::= { dnxTrapEnterprise 2205 }

evntOpticalT1E1NearEndLooped NOTIFICATION-TYPE
        OBJECTS  {
            trapSequence,
            trapResourceKey,
            trapTime,
            trapResourceAddress,
            trapResourceType,
            trapType,
            trapState,
            trapSeverity
            }
        STATUS current
        DESCRIPTION
            "Informational event for Optical T1/E1 port in near end loop."
        ::= { dnxTrapEnterprise 2207 }

setOpticalT1E1LossOfPointer NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port Loss of Pointer."
        ::= { dnxTrapEnterprise 2208 }

setOpticalT1E1OutOfFrame NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port Out of Frame."
        ::= { dnxTrapEnterprise 2209 }

setOpticalT1E1DetectedAIS NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port detecting Alarm Indication Signal."
        ::= { dnxTrapEnterprise 2210 }

setOpticalT1E1NearEndLOS NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port in near end Loss of Signal."
        ::= { dnxTrapEnterprise 2213 }

evntOpticalE1NationalSa4TxRxSame NOTIFICATION-TYPE
        OBJECTS  {
            trapSequence,
            trapResourceKey,
            trapTime,
            trapResourceAddress,
            trapResourceType,
            trapType,
            trapState,
            trapSeverity
            }
        STATUS current
        DESCRIPTION
            "Informational Event for Optical E1 Sa4 National Bit Send/Receive 
            matching value."
        ::= { dnxTrapEnterprise 2216 }

setOpticalT1E1RcvFarEndYellow NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port receiving yellow alarm."
        ::= { dnxTrapEnterprise 2217 }

setOpticalT1E1NearEndSEF NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port near end severely errored frames."
        ::= { dnxTrapEnterprise 2218 }

setOpticalT1E1Tug2LOP NOTIFICATION-TYPE
        OBJECTS  {
            trapSequence,
            trapResourceKey,
            trapTime,
            trapResourceAddress,
            trapResourceType,
            trapType,
            trapState,
            trapSeverity
            }
        STATUS current
        DESCRIPTION
            "Major Alarm for Optical Tributary Unit Group Level 2
            loss of pointer."
        ::= { dnxTrapEnterprise 2219 }

setOpticalT1E1Tug2RDI NOTIFICATION-TYPE
        OBJECTS  {
            trapSequence,
            trapResourceKey,
            trapTime,
            trapResourceAddress,
            trapResourceType,
            trapType,
            trapState,
            trapSeverity
            }
        STATUS current
        DESCRIPTION
            "Major Alarm for Optical Tributary Unit Group Level 2
            Remote Defect Indication."
        ::= { dnxTrapEnterprise 2220 }

setOpticalT1E1Tug2RFI NOTIFICATION-TYPE
        OBJECTS  {
            trapSequence,
            trapResourceKey,
            trapTime,
            trapResourceAddress,
            trapResourceType,
            trapType,
            trapState,
            trapSeverity
            }
        STATUS current
        DESCRIPTION
            "Major Alarm for Optical Tributary Unit Group Level 2
            Remote Failure Indication."
        ::= { dnxTrapEnterprise 2221 }

setOpticalT1E1Tug2AIS NOTIFICATION-TYPE
        OBJECTS  {
            trapSequence,
            trapResourceKey,
            trapTime,
            trapResourceAddress,
            trapResourceType,
            trapType,
            trapState,
            trapSeverity
            }
        STATUS current
        DESCRIPTION
            "Major Alarm for Optical Tributary Unit Group Level 2
            Alarm Indication Signal."
        ::= { dnxTrapEnterprise 2222 }

setOpticalT1E1Tug2PSLM NOTIFICATION-TYPE
        OBJECTS  {
            trapSequence,
            trapResourceKey,
            trapTime,
            trapResourceAddress,
            trapResourceType,
            trapType,
            trapState,
            trapSeverity
            }
        STATUS current
        DESCRIPTION
            "Major Alarm for Optical Tributary Unit Group Level 2
            Path Signal Label Mismatch."
        ::= { dnxTrapEnterprise 2223 }

setOpticalT1E1Tug2PSLU NOTIFICATION-TYPE
        OBJECTS  {
            trapSequence,
            trapResourceKey,
            trapTime,
            trapResourceAddress,
            trapResourceType,
            trapType,
            trapState,
            trapSeverity
            }
        STATUS current
        DESCRIPTION
            "Major Alarm for Optical Tributary Unit Group Level 2
            Path Signal Label Unstable."
        ::= { dnxTrapEnterprise 2224 }

setOpticalT1E1ConfigError NOTIFICATION-TYPE
        OBJECTS  {
            trapSequence,
            trapResourceKey,
            trapTime,
            trapResourceAddress,
            trapResourceType,
            trapType,
            trapState,
            trapSeverity
            }
        STATUS current
        DESCRIPTION
            "Major Alarm for Optical T1/E1 port Configuration Error."
        ::= { dnxTrapEnterprise 2225 }

evntOpticalT1E1InTest NOTIFICATION-TYPE
        OBJECTS  {
            trapSequence,
            trapResourceKey,
            trapTime,
            trapResourceAddress,
            trapResourceType,
            trapType,
            trapState,
            trapSeverity
            }
        STATUS current
        DESCRIPTION
            "Informational event for Optical T1/E1 port in test."
        ::= { dnxTrapEnterprise 2230 }

evntOpticalT1E1OutOfService NOTIFICATION-TYPE
        OBJECTS  {
            trapSequence,
            trapResourceKey,
            trapTime,
            trapResourceAddress,
            trapResourceType,
            trapType,
            trapState,
            trapSeverity
            }
        STATUS current
        DESCRIPTION
            "Informational event for Optical T1/E1 port out of service."
        ::= { dnxTrapEnterprise 2231 }

clearOpticalT1E1RedAlarm NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port in Red Alarm state."
        ::= { dnxTrapEnterprise 2241 }

clearOpticalT1E1NearEndSendLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port near end sending loss
            of frame."
        ::= { dnxTrapEnterprise 2242 }

evntOpticalT1E1StoppedRcvingAIS NOTIFICATION-TYPE
        OBJECTS  {
            trapSequence,
            trapResourceKey,
            trapTime,
            trapResourceAddress,
            trapResourceType,
            trapType,
            trapState,
            trapSeverity
            }
        STATUS current
        DESCRIPTION
            "Informational event when Optical T1/E1 port far end stops sending alarm
            indication signal."
        ::= { dnxTrapEnterprise 2243 }

clearOpticalT1E1NearEndSendingAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port near end sending alarm
            indication signal."
        ::= { dnxTrapEnterprise 2244 }

clearOpticalT1E1NearEndLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port near end loss of frame."
        ::= { dnxTrapEnterprise 2245 }

evntOpticalT1E1NearEndLoopOff NOTIFICATION-TYPE
        OBJECTS  {
            trapSequence,
            trapResourceKey,
            trapTime,
            trapResourceAddress,
            trapResourceType,
            trapType,
            trapState,
            trapSeverity
            }
        STATUS current
        DESCRIPTION
            "Informational event for Optical T1/E1 port near end loop off."
        ::= { dnxTrapEnterprise 2247 }

clearOpticalT1E1LossOfPointer NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port loss of pointer."
        ::= { dnxTrapEnterprise 2248 }

clearOpticalT1E1OutOfFrame NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port out of frame."
        ::= { dnxTrapEnterprise 2249 }

clearOpticalT1E1DetectedAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port detected Alarm
            Indication Signal."
        ::= { dnxTrapEnterprise 2250 }

clearOpticalT1E1NearEndLOS NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port near end
            loss of signal."
        ::= { dnxTrapEnterprise 2253 }

evntOpticalE1NationalSa4TxRxDiff NOTIFICATION-TYPE
        OBJECTS  {
            trapSequence,
            trapResourceKey,
            trapTime,
            trapResourceAddress,
            trapResourceType,
            trapType,
            trapState,
            trapSeverity
            }
        STATUS current
        DESCRIPTION
            "Informational Event for Optical E1 Sa4 National Bit Send/Receive 
            different value."
        ::= { dnxTrapEnterprise 2256 }

clearOpticalT1E1RcvFarEndYellow NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port receiving yellow alarm."
        ::= { dnxTrapEnterprise 2257 }

clearOpticalT1E1NearEndSEF NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port near end severely
            errored frames."
        ::= { dnxTrapEnterprise 2258 }

clearOpticalT1E1Tug2LOP NOTIFICATION-TYPE
        OBJECTS  {
            trapSequence,
            trapResourceKey,
            trapTime,
            trapResourceAddress,
            trapResourceType,
            trapType,
            trapState,
            trapSeverity
            }
        STATUS current
        DESCRIPTION
            "Clears the Major Alarm for TUG 2 loss of pointer."
        ::= { dnxTrapEnterprise 2259 }

clearOpticalT1E1Tug2RDI NOTIFICATION-TYPE
        OBJECTS  {
            trapSequence,
            trapResourceKey,
            trapTime,
            trapResourceAddress,
            trapResourceType,
            trapType,
            trapState,
            trapSeverity
            }
        STATUS current
        DESCRIPTION
            "Clears the Major Alarm for TUG 2 remote defect indication."
        ::= { dnxTrapEnterprise 2260 }

clearOpticalT1E1Tug2RFI NOTIFICATION-TYPE
        OBJECTS  {
            trapSequence,
            trapResourceKey,
            trapTime,
            trapResourceAddress,
            trapResourceType,
            trapType,
            trapState,
            trapSeverity
            }
        STATUS current
        DESCRIPTION
            "Clears the Major Alarm for TUG 2 remote failure indication."
        ::= { dnxTrapEnterprise 2261 }

clearOpticalT1E1Tug2AIS NOTIFICATION-TYPE
        OBJECTS  {
            trapSequence,
            trapResourceKey,
            trapTime,
            trapResourceAddress,
            trapResourceType,
            trapType,
            trapState,
            trapSeverity
            }
        STATUS current
        DESCRIPTION
            "Clears the Major Alarm for TUG 2 Alarm Indication Signal."
        ::= { dnxTrapEnterprise 2262 }

clearOpticalT1E1Tug2PSLM NOTIFICATION-TYPE
        OBJECTS  {
            trapSequence,
            trapResourceKey,
            trapTime,
            trapResourceAddress,
            trapResourceType,
            trapType,
            trapState,
            trapSeverity
            }
        STATUS current
        DESCRIPTION
            "Clears the Major Alarm for TUG 2 Path Signal Label Mismatch."
        ::= { dnxTrapEnterprise 2263 }

clearOpticalT1E1Tug2PSLU NOTIFICATION-TYPE
        OBJECTS  {
            trapSequence,
            trapResourceKey,
            trapTime,
            trapResourceAddress,
            trapResourceType,
            trapType,
            trapState,
            trapSeverity
            }
        STATUS current
        DESCRIPTION
            "Clears the Major Alarm for TUG 2 Path Signal Label Unstable."
        ::= { dnxTrapEnterprise 2264 }

clearOpticalT1E1ConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical T1/E1 port Config Error."
        ::= { dnxTrapEnterprise 2265 }

evntOpticalT1E1TestOff NOTIFICATION-TYPE
        OBJECTS  {
            trapSequence,
            trapResourceKey,
            trapTime,
            trapResourceAddress,
            trapResourceType,
            trapType,
            trapState,
            trapSeverity
            }
        STATUS current
        DESCRIPTION
            "Informational event for Optical T1/E1 port out of test."
        ::= { dnxTrapEnterprise 2270 }

evntOpticalT1E1InService NOTIFICATION-TYPE
        OBJECTS  {
            trapSequence,
            trapResourceKey,
            trapTime,
            trapResourceAddress,
            trapResourceType,
            trapType,
            trapState,
            trapSeverity
            }
        STATUS current
        DESCRIPTION
            "Informational event for Optical T1/E1 port in service."
        ::= { dnxTrapEnterprise 2271 }

-- *************************************************************************
--  Optival Payload Level Alarms/Events; base = 2300
-- *************************************************************************

setVtNearEndLOP NOTIFICATION-TYPE
        OBJECTS  {
            trapSequence,
            trapResourceKey,
            trapTime,
            trapResourceAddress,
            trapResourceType,
            trapType,
            trapState,
            trapSeverity
            }
        STATUS current
        DESCRIPTION
            "Major Alarm for Optical Virtual Tributary near end loss of pointer."
        ::= { dnxTrapEnterprise 2301 }

setVtNearEndAIS NOTIFICATION-TYPE
        OBJECTS  {
            trapSequence,
            trapResourceKey,
            trapTime,
            trapResourceAddress,
            trapResourceType,
            trapType,
            trapState,
            trapSeverity
            }
        STATUS current
        DESCRIPTION
            "Major Alarm for Optical Virtual Tributary near end alarm
            indication signal."
        ::= { dnxTrapEnterprise 2302 }

setPayloadPathLOP NOTIFICATION-TYPE
        OBJECTS  {
            trapSequence,
            trapResourceKey,
            trapTime,
            trapResourceAddress,
            trapResourceType,
            trapType,
            trapState,
            trapSeverity
            }
        STATUS current
        DESCRIPTION
            "Major Alarm for Optical Payload loss of pointer."
        ::= { dnxTrapEnterprise 2303 }

setPayloadPathAIS NOTIFICATION-TYPE
        OBJECTS  {
            trapSequence,
            trapResourceKey,
            trapTime,
            trapResourceAddress,
            trapResourceType,
            trapType,
            trapState,
            trapSeverity
            }
        STATUS current
        DESCRIPTION
            "Major Alarm for Optical Payload alarm indication signal."
        ::= { dnxTrapEnterprise 2304 }

setPayloadPathRDI NOTIFICATION-TYPE
        OBJECTS  {
            trapSequence,
            trapResourceKey,
            trapTime,
            trapResourceAddress,
            trapResourceType,
            trapType,
            trapState,
            trapSeverity
            }
        STATUS current
        DESCRIPTION
            "Major Alarm for Optical Payload remote defect indication."
        ::= { dnxTrapEnterprise 2305 }

evntPayloadNearEndLineLooped NOTIFICATION-TYPE
        OBJECTS  {
            trapSequence,
            trapResourceKey,
            trapTime,
            trapResourceAddress,
            trapResourceType,
            trapType,
            trapState,
            trapSeverity
            }
        STATUS current
        DESCRIPTION
            "Informational event for Optical Payload in near end line loop."
        ::= { dnxTrapEnterprise 2307 }

evntPayloadNearEndLocalLooped NOTIFICATION-TYPE
        OBJECTS  {
            trapSequence,
            trapResourceKey,
            trapTime,
            trapResourceAddress,
            trapResourceType,
            trapType,
            trapState,
            trapSeverity
            }
        STATUS current
        DESCRIPTION
            "Informational event for Optical Payload in near end local loop."
        ::= { dnxTrapEnterprise 2308 }

evntPayloadInTest NOTIFICATION-TYPE
        OBJECTS  {
            trapSequence,
            trapResourceKey,
            trapTime,
            trapResourceAddress,
            trapResourceType,
            trapType,
            trapState,
            trapSeverity
            }
        STATUS current
        DESCRIPTION
            "Informational event for Optical Payload in test."
        ::= { dnxTrapEnterprise 2330 }

clearVtNearEndLOP NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Virtual Tributary near end
            loss of pointer."
        ::= { dnxTrapEnterprise 2341 }

clearVtNearEndAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Virtual Tributary near end alarm
            indication signal."
        ::= { dnxTrapEnterprise 2342 }

clearPayloadPathLOP NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Payload loss of pointer."
        ::= { dnxTrapEnterprise 2343 }

clearPayloadPathAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Payload alarm indication signal."
        ::= { dnxTrapEnterprise 2344 }

clearPayloadPathRDI NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Payload remote defect indication."
        ::= { dnxTrapEnterprise 2345 }

evntPayloadNearEndLineLoopOff NOTIFICATION-TYPE
        OBJECTS  {
            trapSequence,
            trapResourceKey,
            trapTime,
            trapResourceAddress,
            trapResourceType,
            trapType,
            trapState,
            trapSeverity
            }
        STATUS current
        DESCRIPTION
            "Informational event for Optical Payload in near end line loop off."
        ::= { dnxTrapEnterprise 2347 }

evntPayloadNearEndLocalLoopOff NOTIFICATION-TYPE
        OBJECTS  {
            trapSequence,
            trapResourceKey,
            trapTime,
            trapResourceAddress,
            trapResourceType,
            trapType,
            trapState,
            trapSeverity
            }
        STATUS current
        DESCRIPTION
            "Informational event for Optical Payload in near end local loop off."
        ::= { dnxTrapEnterprise 2348 }

evntPayloadTestOff NOTIFICATION-TYPE
        OBJECTS  {
            trapSequence,
            trapResourceKey,
            trapTime,
            trapResourceAddress,
            trapResourceType,
            trapType,
            trapState,
            trapSeverity
            }
        STATUS current
        DESCRIPTION
            "Informational event for Optical Payload out of test."
        ::= { dnxTrapEnterprise 2370 }

-- *************************************************************************
--  Optical Transport Overhead Level Alarms/Events; base = 2400
-- *************************************************************************

setTransOverheadAIS NOTIFICATION-TYPE
        OBJECTS  {
            trapSequence,
            trapResourceKey,
            trapTime,
            trapResourceAddress,
            trapResourceType,
            trapType,
            trapState,
            trapSeverity
            }
        STATUS current
        DESCRIPTION
            "Major Alarm for Optical Transport Overhead alarm indication signal."
        ::= { dnxTrapEnterprise 2401 }

setTransOverheadRDI NOTIFICATION-TYPE
        OBJECTS  {
            trapSequence,
            trapResourceKey,
            trapTime,
            trapResourceAddress,
            trapResourceType,
            trapType,
            trapState,
            trapSeverity
            }
        STATUS current
        DESCRIPTION
            "Major Alarm for Optical Transport Overhead remote defect indication."
        ::= { dnxTrapEnterprise 2402 }

setTransOverheadOOF NOTIFICATION-TYPE
        OBJECTS  {
            trapSequence,
            trapResourceKey,
            trapTime,
            trapResourceAddress,
            trapResourceType,
            trapType,
            trapState,
            trapSeverity
            }
        STATUS current
        DESCRIPTION
            "Major Alarm for Optical Transport Overhead out of frame."
        ::= { dnxTrapEnterprise 2403 }

setTransOverheadLOF NOTIFICATION-TYPE
        OBJECTS  {
            trapSequence,
            trapResourceKey,
            trapTime,
            trapResourceAddress,
            trapResourceType,
            trapType,
            trapState,
            trapSeverity
            }
        STATUS current
        DESCRIPTION
            "Major Alarm for Optical Transport Overhead loss of frame."
        ::= { dnxTrapEnterprise 2404 }

setTransOverheadLOS NOTIFICATION-TYPE
        OBJECTS  {
            trapSequence,
            trapResourceKey,
            trapTime,
            trapResourceAddress,
            trapResourceType,
            trapType,
            trapState,
            trapSeverity
            }
        STATUS current
        DESCRIPTION
            "Major Alarm for Optical Transport Overhead loss of signal."
        ::= { dnxTrapEnterprise 2405 }

evntTransOverheadNearEndSysLineLooped NOTIFICATION-TYPE
        OBJECTS  {
            trapSequence,
            trapResourceKey,
            trapTime,
            trapResourceAddress,
            trapResourceType,
            trapType,
            trapState,
            trapSeverity
            }
        STATUS current
        DESCRIPTION
            "Informational event for Optical Transport Overhead in near end
            system line loop."
        ::= { dnxTrapEnterprise 2407 }

evntTransOverheadNearEndPathLineLooped NOTIFICATION-TYPE
        OBJECTS  {
            trapSequence,
            trapResourceKey,
            trapTime,
            trapResourceAddress,
            trapResourceType,
            trapType,
            trapState,
            trapSeverity
            }
        STATUS current
        DESCRIPTION
            "Informational event for Optical Transport Overhead in near end
            path line loop."
        ::= { dnxTrapEnterprise 2408 }

evntTransOverheadNearEndLocalLooped NOTIFICATION-TYPE
        OBJECTS  {
            trapSequence,
            trapResourceKey,
            trapTime,
            trapResourceAddress,
            trapResourceType,
            trapType,
            trapState,
            trapSeverity
            }
        STATUS current
        DESCRIPTION
            "Informational event for Optical Transport Overhead in near end
            local loop."
        ::= { dnxTrapEnterprise 2409 }

setTransOverheadSfDetect NOTIFICATION-TYPE
        OBJECTS  {
            trapSequence,
            trapResourceKey,
            trapTime,
            trapResourceAddress,
            trapResourceType,
            trapType,
            trapState,
            trapSeverity
            }
        STATUS current
        DESCRIPTION
            "Major Alarm for Optical Transport Overhead signal failure detected."
        ::= { dnxTrapEnterprise 2413 }

setTransOverheadSdDetect NOTIFICATION-TYPE
        OBJECTS  {
            trapSequence,
            trapResourceKey,
            trapTime,
            trapResourceAddress,
            trapResourceType,
            trapType,
            trapState,
            trapSeverity
            }
        STATUS current
        DESCRIPTION
            "Major Alarm for Optical Transport Overhead signal degrade detected."
        ::= { dnxTrapEnterprise 2414 }

setTransOverheadDetectLaserOffDetect NOTIFICATION-TYPE
        OBJECTS  {
            trapSequence,
            trapResourceKey,
            trapTime,
            trapResourceAddress,
            trapResourceType,
            trapType,
            trapState,
            trapSeverity
            }
        STATUS current
        DESCRIPTION
            "Major Alarm for Optical Transport Overhead signal laser off detected."
        ::= { dnxTrapEnterprise 2415 }

evntTransOverheadInTest NOTIFICATION-TYPE
        OBJECTS  {
            trapSequence,
            trapResourceKey,
            trapTime,
            trapResourceAddress,
            trapResourceType,
            trapType,
            trapState,
            trapSeverity
            }
        STATUS current
        DESCRIPTION
            "Informational event for Optical Transport Overhead in test."
        ::= { dnxTrapEnterprise 2430 }

clearTransOverheadAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Transport Overhead alarm
            indication signal."
        ::= { dnxTrapEnterprise 2441 }

clearTransOverheadRDI NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Transport Overhead remote
            defect indication."
        ::= { dnxTrapEnterprise 2442 }

clearTransOverheadOOF NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Transport Overhead out of frame."
        ::= { dnxTrapEnterprise 2443 }

clearTransOverheadLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Transport Overhead loss of frame."
        ::= { dnxTrapEnterprise 2444 }

clearTransOverheadLOS NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Transport Overhead loss of signal."
        ::= { dnxTrapEnterprise 2445 }

evntTransOverheadNearEndSysLineLoopOff NOTIFICATION-TYPE
        OBJECTS  {
            trapSequence,
            trapResourceKey,
            trapTime,
            trapResourceAddress,
            trapResourceType,
            trapType,
            trapState,
            trapSeverity
            }
        STATUS current
        DESCRIPTION
            "Informational event for Optical Transport Overhead near end
            system line loop off."
        ::= { dnxTrapEnterprise 2447 }

evntTransOverheadNearEndPathLineLoopOff NOTIFICATION-TYPE
        OBJECTS  {
            trapSequence,
            trapResourceKey,
            trapTime,
            trapResourceAddress,
            trapResourceType,
            trapType,
            trapState,
            trapSeverity
            }
        STATUS current
        DESCRIPTION
            "Informational event for Optical Transport Overhead near end
            path line loop off."
        ::= { dnxTrapEnterprise 2448 }

evntTransOverheadNearEndLocalLoopOff NOTIFICATION-TYPE
        OBJECTS  {
            trapSequence,
            trapResourceKey,
            trapTime,
            trapResourceAddress,
            trapResourceType,
            trapType,
            trapState,
            trapSeverity
            }
        STATUS current
        DESCRIPTION
            "Informational event for Optical Transport Overhead near end
            local loop off."
        ::= { dnxTrapEnterprise 2449 }

clearTransOverheadSfDetect NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Transport Overhead 
            signal failure detected."
        ::= { dnxTrapEnterprise 2453 }

clearTransOverheadSdDetect NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Transport Overhead 
            signal degrade detected."
        ::= { dnxTrapEnterprise 2454 }

clearTransOverheadLaserOffDetect NOTIFICATION-TYPE
        OBJECTS  {
            trapSequence,
            trapResourceKey,
            trapTime,
            trapResourceAddress,
            trapResourceType,
            trapType,
            trapState,
            trapSeverity
            }
        STATUS current
        DESCRIPTION
            "Clears the Major Alarm for Optical Transport Overhead 
            signal Laser Off detected."
        ::= { dnxTrapEnterprise 2455 }

evntTransOverheadTestOff NOTIFICATION-TYPE
        OBJECTS  {
            trapSequence,
            trapResourceKey,
            trapTime,
            trapResourceAddress,
            trapResourceType,
            trapType,
            trapState,
            trapSeverity
            }
        STATUS current
        DESCRIPTION
            "Informational event for Optical Transport Overhead out of test."
        ::= { dnxTrapEnterprise 2470 }

-- *************************************************************************
--  E3 Port Level Alarms/Events; base = 2500
-- *************************************************************************

setE3RcvFarEndLOF NOTIFICATION-TYPE
        OBJECTS  {
            trapSequence,
            trapResourceKey,
            trapTime,
            trapResourceAddress,
            trapResourceType,
            trapType,
            trapState,
            trapSeverity
            }
        STATUS current
        DESCRIPTION
            "Major Alarm for receiving far end loss of frame (receiving
            yellow alarm)."
        ::= { dnxTrapEnterprise 2501 }

setE3NearEndSendLOF NOTIFICATION-TYPE
        OBJECTS  {
            trapSequence,
            trapResourceKey,
            trapTime,
            trapResourceAddress,
            trapResourceType,
            trapType,
            trapState,
            trapSeverity
            }
        STATUS current
        DESCRIPTION
            "Major Alarm for near end sending loss of frame (transmitting
             yellow alarm)."
        ::= { dnxTrapEnterprise 2502 }

evntE3RcvingAIS NOTIFICATION-TYPE
        OBJECTS  {
            trapSequence,
            trapResourceKey,
            trapTime,
            trapResourceAddress,
            trapResourceType,
            trapType,
            trapState,
            trapSeverity
            }
        STATUS current
        DESCRIPTION
            "Informational Event for far end sending alarm indication signal."
        ::= { dnxTrapEnterprise 2503 }

setE3NearEndSendingAIS NOTIFICATION-TYPE
        OBJECTS  {
            trapSequence,
            trapResourceKey,
            trapTime,
            trapResourceAddress,
            trapResourceType,
            trapType,
            trapState,
            trapSeverity
            }
        STATUS current
        DESCRIPTION
            "Major Alarm for near end sending alarm indication signal."
        ::= { dnxTrapEnterprise 2504 }

setE3NearEndLOF NOTIFICATION-TYPE
        OBJECTS  {
            trapSequence,
            trapResourceKey,
            trapTime,
            trapResourceAddress,
            trapResourceType,
            trapType,
            trapState,
            trapSeverity
            }
        STATUS current
        DESCRIPTION
            "Major Alarm for near end loss of frame."
        ::= { dnxTrapEnterprise 2505 }

setE3NearEndLossOfSignal NOTIFICATION-TYPE
        OBJECTS  {
            trapSequence,
            trapResourceKey,
            trapTime,
            trapResourceAddress,
            trapResourceType,
            trapType,
            trapState,
            trapSeverity
            }
        STATUS current
        DESCRIPTION
            "Major Alarm for near end loss of signal."
        ::= { dnxTrapEnterprise 2506 }

evntE3NearEndLooped NOTIFICATION-TYPE
        OBJECTS  {
            trapSequence,
            trapResourceKey,
            trapTime,
            trapResourceAddress,
            trapResourceType,
            trapType,
            trapState,
            trapSeverity
            }
        STATUS current
        DESCRIPTION
            "Informational Event for E3 near end looped."
        ::= { dnxTrapEnterprise 2507 }

setE3OtherLineStatus NOTIFICATION-TYPE
        OBJECTS  {
            trapSequence,
            trapResourceKey,
            trapTime,
            trapResourceAddress,
            trapResourceType,
            trapType,
            trapState,
            trapSeverity
            }
        STATUS current
        DESCRIPTION
            "Major Alarm for E3 other line status."
        ::= { dnxTrapEnterprise 2512 }

setE3NearEndUnavailableSig NOTIFICATION-TYPE
        OBJECTS  {
            trapSequence,
            trapResourceKey,
            trapTime,
            trapResourceAddress,
            trapResourceType,
            trapType,
            trapState,
            trapSeverity
            }
        STATUS current
        DESCRIPTION
            "Major Alarm for near end in unavailable signal state."
        ::= { dnxTrapEnterprise 2513 }

evntE3CarrierEquipOutOfService NOTIFICATION-TYPE
        OBJECTS  {
            trapSequence,
            trapResourceKey,
            trapTime,
            trapResourceAddress,
            trapResourceType,
            trapType,
            trapState,
            trapSeverity
            }
        STATUS current
        DESCRIPTION
            "Informational Event for E3 carrier equipment out-of-service."
        ::= { dnxTrapEnterprise 2514 }

setE3NearEndSeverErroredFrame NOTIFICATION-TYPE
        OBJECTS  {
            trapSequence,
            trapResourceKey,
            trapTime,
            trapResourceAddress,
            trapResourceType,
            trapType,
            trapState,
            trapSeverity
            }
        STATUS current
        DESCRIPTION
            "Major Alarm for near end severely errored frame."
        ::= { dnxTrapEnterprise 2515 }

setE3TxRxClockFailure NOTIFICATION-TYPE
        OBJECTS  {
            trapSequence,
            trapResourceKey,
            trapTime,
            trapResourceAddress,
            trapResourceType,
            trapType,
            trapState,
            trapSeverity
            }
        STATUS current
        DESCRIPTION
            "Major Alarm for E3 Transmit/Receive clock failure."
        ::= { dnxTrapEnterprise 2516 }

setE3FarEndBlockError NOTIFICATION-TYPE
        OBJECTS  {
            trapSequence,
            trapResourceKey,
            trapTime,
            trapResourceAddress,
            trapResourceType,
            trapType,
            trapState,
            trapSeverity
            }
        STATUS current
        DESCRIPTION
            "Major Alarm for E3 far end block error."
        ::= { dnxTrapEnterprise 2517 }

setE3MbitsInError NOTIFICATION-TYPE
        OBJECTS  {
            trapSequence,
            trapResourceKey,
            trapTime,
            trapResourceAddress,
            trapResourceType,
            trapType,
            trapState,
            trapSeverity
            }
        STATUS current
        DESCRIPTION
            "Major Alarm for M-bits in error."
        ::= { dnxTrapEnterprise 2519 }

setE3LIUOtherStatus NOTIFICATION-TYPE
        OBJECTS  {
            trapSequence,
            trapResourceKey,
            trapTime,
            trapResourceAddress,
            trapResourceType,
            trapType,
            trapState,
            trapSeverity
            }
        STATUS current
        DESCRIPTION
            "Major Alarm for E3 LIU other status."
        ::= { dnxTrapEnterprise 2520 }

setE3LIUCodingViolation NOTIFICATION-TYPE
        OBJECTS  {
            trapSequence,
            trapResourceKey,
            trapTime,
            trapResourceAddress,
            trapResourceType,
            trapType,
            trapState,
            trapSeverity
            }
        STATUS current
        DESCRIPTION
            "Major Alarm for E3 LIU line coding violation."
        ::= { dnxTrapEnterprise 2523 }

setE3ConfigError NOTIFICATION-TYPE
        OBJECTS  {
            trapSequence,
            trapResourceKey,
            trapTime,
            trapResourceAddress,
            trapResourceType,
            trapType,
            trapState,
            trapSeverity
            }
        STATUS current
        DESCRIPTION
            "Major Alarm for E3 configuration error."
        ::= { dnxTrapEnterprise 2525 }

evntE3InTest NOTIFICATION-TYPE
        OBJECTS  {
            trapSequence,
            trapResourceKey,
            trapTime,
            trapResourceAddress,
            trapResourceType,
            trapType,
            trapState,
            trapSeverity
            }
        STATUS current
        DESCRIPTION
            "Informational Event for E3 in test."
        ::= { dnxTrapEnterprise 2530 }

evntE3OutOfService NOTIFICATION-TYPE
        OBJECTS  {
            trapSequence,
            trapResourceKey,
            trapTime,
            trapResourceAddress,
            trapResourceType,
            trapType,
            trapState,
            trapSeverity
            }
        STATUS current
        DESCRIPTION
            "Informational Event for E3 out-of-service."
        ::= { dnxTrapEnterprise 2531 }

clearE3RcvFarEndLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for receiving far end loss of frame
             (receiving yellow alarm)."
        ::= { dnxTrapEnterprise 2541 }

clearE3NearEndSendLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for near end sending loss of frame
             (transmitting yellow alarm)."
        ::= { dnxTrapEnterprise 2542 }

evntE3StoppedRcvingAIS NOTIFICATION-TYPE
        OBJECTS  {
            trapSequence,
            trapResourceKey,
            trapTime,
            trapResourceAddress,
            trapResourceType,
            trapType,
            trapState,
            trapSeverity
            }
        STATUS current
        DESCRIPTION
            "Informational Event when far end stops sending alarm indication
             signal."
        ::= { dnxTrapEnterprise 2543 }

clearE3NearEndSendingAIS NOTIFICATION-TYPE
        OBJECTS  {
            trapSequence,
            trapResourceKey,
            trapTime,
            trapResourceAddress,
            trapResourceType,
            trapType,
            trapState,
            trapSeverity
            }
        STATUS current
        DESCRIPTION
            "Clears the Major Alarm for near end sending alarm indication
             signal."
        ::= { dnxTrapEnterprise 2544 }

clearE3NearEndLOF NOTIFICATION-TYPE
        OBJECTS  {
            trapSequence,
            trapResourceKey,
            trapTime,
            trapResourceAddress,
            trapResourceType,
            trapType,
            trapState,
            trapSeverity
            }
        STATUS current
        DESCRIPTION
            "Clears the Major Alarm for near end loss of frame."
        ::= { dnxTrapEnterprise 2545 }

clearE3NearEndLossOfSignal NOTIFICATION-TYPE
        OBJECTS  {
            trapSequence,
            trapResourceKey,
            trapTime,
            trapResourceAddress,
            trapResourceType,
            trapType,
            trapState,
            trapSeverity
            }
        STATUS current
        DESCRIPTION
            "Clears the Major Alarm for near end loss of signal."
        ::= { dnxTrapEnterprise 2546 }

evntE3NearEndLoopOff NOTIFICATION-TYPE
        OBJECTS  {
            trapSequence,
            trapResourceKey,
            trapTime,
            trapResourceAddress,
            trapResourceType,
            trapType,
            trapState,
            trapSeverity
            }
        STATUS current
        DESCRIPTION
            "Informational Event for E3 near end loop off."
        ::= { dnxTrapEnterprise 2547 }

clearE3OtherLineStatus NOTIFICATION-TYPE
        OBJECTS  {
            trapSequence,
            trapResourceKey,
            trapTime,
            trapResourceAddress,
            trapResourceType,
            trapType,
            trapState,
            trapSeverity
            }
        STATUS current
        DESCRIPTION
            "Clears the Major Alarm for E3 other line status."
        ::= { dnxTrapEnterprise 2552 }

clearE3NearEndUnavailableSig NOTIFICATION-TYPE
        OBJECTS  {
            trapSequence,
            trapResourceKey,
            trapTime,
            trapResourceAddress,
            trapResourceType,
            trapType,
            trapState,
            trapSeverity
            }
        STATUS current
        DESCRIPTION
            "Clears the Major Alarm for near end in unavailable signal
             state."
        ::= { dnxTrapEnterprise 2553 }

evntE3CarrierEquipInService NOTIFICATION-TYPE
        OBJECTS  {
            trapSequence,
            trapResourceKey,
            trapTime,
            trapResourceAddress,
            trapResourceType,
            trapType,
            trapState,
            trapSeverity
            }
        STATUS current
        DESCRIPTION
            "Informational Event for E3 carrier equipment in-service."
        ::= { dnxTrapEnterprise 2554 }

clearE3NearEndSeverErroredFrame NOTIFICATION-TYPE
        OBJECTS  {
            trapSequence,
            trapResourceKey,
            trapTime,
            trapResourceAddress,
            trapResourceType,
            trapType,
            trapState,
            trapSeverity
            }
        STATUS current
        DESCRIPTION
            "Clears the Major Alarm for near end severely errored frame."
        ::= { dnxTrapEnterprise 2555 }

clearE3TxRxClockFailure NOTIFICATION-TYPE
        OBJECTS  {
            trapSequence,
            trapResourceKey,
            trapTime,
            trapResourceAddress,
            trapResourceType,
            trapType,
            trapState,
            trapSeverity
            }
        STATUS current
        DESCRIPTION
            "Clears the Major Alarm for E3 Transmit/Receive clock failure."
        ::= { dnxTrapEnterprise 2556 }

clearE3FarEndBlockError NOTIFICATION-TYPE
        OBJECTS  {
            trapSequence,
            trapResourceKey,
            trapTime,
            trapResourceAddress,
            trapResourceType,
            trapType,
            trapState,
            trapSeverity
            }
        STATUS current
        DESCRIPTION
            "Clears the Major Alarm for E3 far end block error."
        ::= { dnxTrapEnterprise 2557 }

clearE3MbitsInError NOTIFICATION-TYPE
        OBJECTS  {
            trapSequence,
            trapResourceKey,
            trapTime,
            trapResourceAddress,
            trapResourceType,
            trapType,
            trapState,
            trapSeverity
            }
        STATUS current
        DESCRIPTION
            "Clears the Major Alarm for M-bits in error."
        ::= { dnxTrapEnterprise 2559 }

clearE3LIUOtherStatus NOTIFICATION-TYPE
        OBJECTS  {
            trapSequence,
            trapResourceKey,
            trapTime,
            trapResourceAddress,
            trapResourceType,
            trapType,
            trapState,
            trapSeverity
            }
        STATUS current
        DESCRIPTION
            "Clears the Major Alarm for E3 LIU other status."
        ::= { dnxTrapEnterprise 2560 }

clearE3LIUCodingViolation NOTIFICATION-TYPE
        OBJECTS  {
            trapSequence,
            trapResourceKey,
            trapTime,
            trapResourceAddress,
            trapResourceType,
            trapType,
            trapState,
            trapSeverity
            }
        STATUS current
        DESCRIPTION
            "Clears the Major Alarm for E3 LIU line coding violation."
        ::= { dnxTrapEnterprise 2563 }

clearE3ConfigError NOTIFICATION-TYPE
        OBJECTS  {
            trapSequence,
            trapResourceKey,
            trapTime,
            trapResourceAddress,
            trapResourceType,
            trapType,
            trapState,
            trapSeverity
            }
        STATUS current
        DESCRIPTION
            "Clears the Major Alarm for E3 configuration error."
        ::= { dnxTrapEnterprise 2565 }

evntE3TestOff NOTIFICATION-TYPE
        OBJECTS  {
            trapSequence,
            trapResourceKey,
            trapTime,
            trapResourceAddress,
            trapResourceType,
            trapType,
            trapState,
            trapSeverity
            }
        STATUS current
        DESCRIPTION
            "Informational Event for E3 test off."
        ::= { dnxTrapEnterprise 2570 }

evntE3InService NOTIFICATION-TYPE
        OBJECTS  {
            trapSequence,
            trapResourceKey,
            trapTime,
            trapResourceAddress,
            trapResourceType,
            trapType,
            trapState,
            trapSeverity
            }
        STATUS current
        DESCRIPTION
            "Informational Event for E3 in-service."
        ::= { dnxTrapEnterprise 2571 }

-- *************************************************************************
--  Dnx-1u Contact Closure Port Level Alarms/Events; base = 2600
-- *************************************************************************

setContactClosureInputAlarm NOTIFICATION-TYPE
        OBJECTS  {
            trapSequence,
            trapResourceKey,
            trapTime,
            trapResourceAddress,
            trapResourceType,
            trapType,
            trapState,
            trapSeverity
            }
        STATUS current
        DESCRIPTION
            "Major Alarm for Activated Contact Closure Input Port."
        ::= { dnxTrapEnterprise 2601 }

setContactClosureCfgError NOTIFICATION-TYPE
        OBJECTS  {
            trapSequence,
            trapResourceKey,
            trapTime,
            trapResourceAddress,
            trapResourceType,
            trapType,
            trapState,
            trapSeverity
            }
        STATUS current
        DESCRIPTION
            "Minor Alarm for Contact Closure Port configuration error."
        ::= { dnxTrapEnterprise 2625 }

clearContactClosureInputAlarm NOTIFICATION-TYPE
        OBJECTS  {
            trapSequence,
            trapResourceKey,
            trapTime,
            trapResourceAddress,
            trapResourceType,
            trapType,
            trapState,
            trapSeverity
            }
        STATUS current
        DESCRIPTION
            "Clears Major Alarm for Activated Contact Closure Input Port."
        ::= { dnxTrapEnterprise 2641 }

clearContactClosureCfgError NOTIFICATION-TYPE
        OBJECTS  {
            trapSequence,
            trapResourceKey,
            trapTime,
            trapResourceAddress,
            trapResourceType,
            trapType,
            trapState,
            trapSeverity
            }
        STATUS current
        DESCRIPTION
            "Clears Minor Alarm for Contact Closure Port configuration error."
        ::= { dnxTrapEnterprise 2665 }

-- *************************************************************************
--  Dnx-1u Voltage Measurement Port Level Alarms/Events; base = 2700
-- *************************************************************************

setVoltMeasureAlarm NOTIFICATION-TYPE
        OBJECTS  {
            trapSequence,
            trapResourceKey,
            trapTime,
            trapResourceAddress,
            trapResourceType,
            trapType,
            trapState,
            trapSeverity
            }
        STATUS current
        DESCRIPTION
            "Major Alarm for Voltage Port exceeding limit boundary."
        ::= { dnxTrapEnterprise 2701 }

setVoltMeasureCfgError NOTIFICATION-TYPE
        OBJECTS  {
            trapSequence,
            trapResourceKey,
            trapTime,
            trapResourceAddress,
            trapResourceType,
            trapType,
            trapState,
            trapSeverity
            }
        STATUS current
        DESCRIPTION
            "Minor Alarm for Voltage Port configuration error."
        ::= { dnxTrapEnterprise 2725 }

clearVoltMeasureAlarm NOTIFICATION-TYPE
        OBJECTS  {
            trapSequence,
            trapResourceKey,
            trapTime,
            trapResourceAddress,
            trapResourceType,
            trapType,
            trapState,
            trapSeverity
            }
        STATUS current
        DESCRIPTION
            "Clears Major Alarm for Voltage Port exceeding limit boundary."
        ::= { dnxTrapEnterprise 2741 }

clearVoltMeasureCfgError NOTIFICATION-TYPE
        OBJECTS  {
            trapSequence,
            trapResourceKey,
            trapTime,
            trapResourceAddress,
            trapResourceType,
            trapType,
            trapState,
            trapSeverity
            }
        STATUS current
        DESCRIPTION
            "Clears Minor Alarm for Voltage Port configuration error."
        ::= { dnxTrapEnterprise 2765 }

-- *************************************************************************
--  Dnx-1u Asynchronous Port Level Alarms/Events; base = 2800
-- *************************************************************************

setAsyncRxFifoError NOTIFICATION-TYPE
        OBJECTS  {
            trapSequence,
            trapResourceKey,
            trapTime,
            trapResourceAddress,
            trapResourceType,
            trapType,
            trapState,
            trapSeverity
            }
        STATUS current
        DESCRIPTION
            "Major Alarm for Asynchronous Port FIFO Error on Receive."
        ::= { dnxTrapEnterprise 2801 }
        
setAsyncTxFifoError NOTIFICATION-TYPE
        OBJECTS  {
            trapSequence,
            trapResourceKey,
            trapTime,
            trapResourceAddress,
            trapResourceType,
            trapType,
            trapState,
            trapSeverity
            }
        STATUS current
        DESCRIPTION
            "Major Alarm for Asynchronous Port FIFO Error on Transmit."
        ::= { dnxTrapEnterprise 2802 }

setAsyncOverrunError NOTIFICATION-TYPE
        OBJECTS  {
            trapSequence,
            trapResourceKey,
            trapTime,
            trapResourceAddress,
            trapResourceType,
            trapType,
            trapState,
            trapSeverity
            }
        STATUS current
        DESCRIPTION
            "Minor Alarm for Asynchronous Port Overrun Error."
        ::= { dnxTrapEnterprise 2803 }

setAsyncParityError NOTIFICATION-TYPE
        OBJECTS  {
            trapSequence,
            trapResourceKey,
            trapTime,
            trapResourceAddress,
            trapResourceType,
            trapType,
            trapState,
            trapSeverity
            }
        STATUS current
        DESCRIPTION
            "Minor Alarm for Asynchronous Port Parity Error."
        ::= { dnxTrapEnterprise 2804 }

setAsyncFramingError NOTIFICATION-TYPE
        OBJECTS  {
            trapSequence,
            trapResourceKey,
            trapTime,
            trapResourceAddress,
            trapResourceType,
            trapType,
            trapState,
            trapSeverity
            }
        STATUS current
        DESCRIPTION
            "Minor Alarm for Asynchronous Port Framing Error."
        ::= { dnxTrapEnterprise 2805 }

clearAsyncRxFifoError NOTIFICATION-TYPE
        OBJECTS  {
            trapSequence,
            trapResourceKey,
            trapTime,
            trapResourceAddress,
            trapResourceType,
            trapType,
            trapState,
            trapSeverity
            }
        STATUS current
        DESCRIPTION
            "Clears Major Alarm for Asynchronous Port FIFO Error on Receive."
        ::= { dnxTrapEnterprise 2841 }
        
clearAsyncTxFifoError NOTIFICATION-TYPE
        OBJECTS  {
            trapSequence,
            trapResourceKey,
            trapTime,
            trapResourceAddress,
            trapResourceType,
            trapType,
            trapState,
            trapSeverity
            }
        STATUS current
        DESCRIPTION
            "Clears Major Alarm for Asynchronous Port FIFO Error on Transmit."
        ::= { dnxTrapEnterprise 2842 }

clearAsyncOverrunError NOTIFICATION-TYPE
        OBJECTS  {
            trapSequence,
            trapResourceKey,
            trapTime,
            trapResourceAddress,
            trapResourceType,
            trapType,
            trapState,
            trapSeverity
            }
        STATUS current
        DESCRIPTION
            "Clears Minor Alarm for Asynchronous Port Overrun Error."
        ::= { dnxTrapEnterprise 2843 }

clearAsyncParityError NOTIFICATION-TYPE
        OBJECTS  {
            trapSequence,
            trapResourceKey,
            trapTime,
            trapResourceAddress,
            trapResourceType,
            trapType,
            trapState,
            trapSeverity
            }
        STATUS current
        DESCRIPTION
            "Clears Minor Alarm for Asynchronous Port Parity Error."
        ::= { dnxTrapEnterprise 2844 }

clearAsyncFramingError NOTIFICATION-TYPE
        OBJECTS  {
            trapSequence,
            trapResourceKey,
            trapTime,
            trapResourceAddress,
            trapResourceType,
            trapType,
            trapState,
            trapSeverity
            }
        STATUS current
        DESCRIPTION
            "Clears Minor Alarm for Asynchronous Port Framing Error."
        ::= { dnxTrapEnterprise 2845 }

-- *************************************************************************
--  Dnx-1u Temperature Sensor Device Level Alarms/Events; base = 2900
-- *************************************************************************

setTempSensorOutOfRange NOTIFICATION-TYPE
        OBJECTS  {
            trapSequence,
            trapResourceKey,
            trapTime,
            trapResourceAddress,
            trapResourceType,
            trapType,
            trapState,
            trapSeverity
            }
        STATUS current
        DESCRIPTION
            "Critical Alarm for System Temperature exceeding known operating 
            limits."
        ::= { dnxTrapEnterprise 2901 }

clearTempSensorOutOfRange NOTIFICATION-TYPE
        OBJECTS  {
            trapSequence,
            trapResourceKey,
            trapTime,
            trapResourceAddress,
            trapResourceType,
            trapType,
            trapState,
            trapSeverity
            }
        STATUS current
        DESCRIPTION
            "Clears Critical Alarm for System Temperature exceeding known 
            operating limits."
        ::= { dnxTrapEnterprise 2941 }

-- *************************************************************************
--  Dnx-1u Router Virual Wan Port Level Alarms/Events; base = 3000
-- *************************************************************************

setVWanError NOTIFICATION-TYPE
        OBJECTS  {
            trapSequence,
            trapResourceKey,
            trapTime,
            trapResourceAddress,
            trapResourceType,
            trapType,
            trapState,
            trapSeverity
            }
        STATUS current
        DESCRIPTION
            "Major Alarm for Virtual WAN Port communications error."
        ::= { dnxTrapEnterprise 3001 }

setVWanCfgError NOTIFICATION-TYPE
        OBJECTS  {
            trapSequence,
            trapResourceKey,
            trapTime,
            trapResourceAddress,
            trapResourceType,
            trapType,
            trapState,
            trapSeverity
            }
        STATUS current
        DESCRIPTION
            "Minor Alarm for Virtual WAN Port configuration error."
        ::= { dnxTrapEnterprise 3025 }

clearVWanError NOTIFICATION-TYPE
        OBJECTS  {
            trapSequence,
            trapResourceKey,
            trapTime,
            trapResourceAddress,
            trapResourceType,
            trapType,
            trapState,
            trapSeverity
            }
        STATUS current
        DESCRIPTION
            "Clears Major Alarm for Virtual WAN Port communications error."
        ::= { dnxTrapEnterprise 3041 }

clearVWanCfgError NOTIFICATION-TYPE
        OBJECTS  {
            trapSequence,
            trapResourceKey,
            trapTime,
            trapResourceAddress,
            trapResourceType,
            trapType,
            trapState,
            trapSeverity
            }
        STATUS current
        DESCRIPTION
            "Clears Minor Alarm for Virtual WAN Port configuration error."
        ::= { dnxTrapEnterprise 3065 }

-- *************************************************************************
--  Dnx-1u Power Supply Device Level Alarms/Events; base = 3100
-- *************************************************************************

set1uPowerSupplyOffline NOTIFICATION-TYPE
        OBJECTS  {
            trapSequence,
            trapResourceKey,
            trapTime,
            trapResourceAddress,
            trapResourceType,
            trapType,
            trapState,
            trapSeverity
            }
        STATUS current
        DESCRIPTION
            "Major Alarm for DNX-1u Power Supply in Offline State."
        ::= { dnxTrapEnterprise 3108 }

set1uPowerSupplyDefective NOTIFICATION-TYPE
        OBJECTS  {
            trapSequence,
            trapResourceKey,
            trapTime,
            trapResourceAddress,
            trapResourceType,
            trapType,
            trapState,
            trapSeverity
            }
        STATUS current
        DESCRIPTION
            "Critical Alarm for DNX-1u Power Supply in Failed State."
        ::= { dnxTrapEnterprise 3109 }
        
set1uPowerSupplyFanFailure NOTIFICATION-TYPE
        OBJECTS  {
            trapSequence,
            trapResourceKey,
            trapTime,
            trapResourceAddress,
            trapResourceType,
            trapType,
            trapState,
            trapSeverity
            }
        STATUS current
        DESCRIPTION
            "Critical Alarm for DNX-1u Power Supply Fan in Failed State."
        ::= { dnxTrapEnterprise 3110 }
        
evnt1uPowerSupplyFanOn NOTIFICATION-TYPE
        OBJECTS  {
            trapSequence,
            trapResourceKey,
            trapTime,
            trapResourceAddress,
            trapResourceType,
            trapType,
            trapState,
            trapSeverity
            }
        STATUS current
        DESCRIPTION
            "Informational event for DNX-1u Power Supply Fan On."
        ::= { dnxTrapEnterprise 3116 }

set1uPowerSupplyCircuitMissing NOTIFICATION-TYPE
        OBJECTS  {
            trapSequence,
            trapResourceKey,
            trapTime,
            trapResourceAddress,
            trapResourceType,
            trapType,
            trapState,
            trapSeverity
            }
        STATUS current
        DESCRIPTION
            "Critical Alarm for DNX-1u Power Supply missing hardware."
        ::= { dnxTrapEnterprise 3119 }

set1uPowerSupplyCfgMismatch NOTIFICATION-TYPE
        OBJECTS  {
            trapSequence,
            trapResourceKey,
            trapTime,
            trapResourceAddress,
            trapResourceType,
            trapType,
            trapState,
            trapSeverity
            }
        STATUS current
        DESCRIPTION
            "Major Alarm for DNX-1u Power Supply configuration error."
        ::= { dnxTrapEnterprise 3125 }
        
clear1uPowerSupplyOffline NOTIFICATION-TYPE
        OBJECTS  {
            trapSequence,
            trapResourceKey,
            trapTime,
            trapResourceAddress,
            trapResourceType,
            trapType,
            trapState,
            trapSeverity
            }
        STATUS current
        DESCRIPTION
            "Clears Major Alarm for DNX-1u Power Supply in Offline State."
        ::= { dnxTrapEnterprise 3148 }

clear1uPowerSupplyDefective NOTIFICATION-TYPE
        OBJECTS  {
            trapSequence,
            trapResourceKey,
            trapTime,
            trapResourceAddress,
            trapResourceType,
            trapType,
            trapState,
            trapSeverity
            }
        STATUS current
        DESCRIPTION
            "Clears Critical Alarm for DNX-1u Power Supply in Failed State."
        ::= { dnxTrapEnterprise 3149 }
        
clear1uPowerSupplyFanFailure NOTIFICATION-TYPE
        OBJECTS  {
            trapSequence,
            trapResourceKey,
            trapTime,
            trapResourceAddress,
            trapResourceType,
            trapType,
            trapState,
            trapSeverity
            }
        STATUS current
        DESCRIPTION
            "Clears Critical Alarm for DNX-1u Power Supply Fan in Failed State."
        ::= { dnxTrapEnterprise 3150 }
        
evnt1uPowerSupplyFanOff NOTIFICATION-TYPE
        OBJECTS  {
            trapSequence,
            trapResourceKey,
            trapTime,
            trapResourceAddress,
            trapResourceType,
            trapType,
            trapState,
            trapSeverity
            }
        STATUS current
        DESCRIPTION
            "Informational event for DNX-1u Power Supply Fan Off."
        ::= { dnxTrapEnterprise 3156 }

clear1uPowerSupplyCircuitMissing NOTIFICATION-TYPE
        OBJECTS  {
            trapSequence,
            trapResourceKey,
            trapTime,
            trapResourceAddress,
            trapResourceType,
            trapType,
            trapState,
            trapSeverity
            }
        STATUS current
        DESCRIPTION
            "Clears the Critical Alarm for DNX-1u Power Supply missing hardware."
        ::= { dnxTrapEnterprise 3159 }

clear1uPowerSupplyCfgMismatch NOTIFICATION-TYPE
        OBJECTS  {
            trapSequence,
            trapResourceKey,
            trapTime,
            trapResourceAddress,
            trapResourceType,
            trapType,
            trapState,
            trapSeverity
            }
        STATUS current
        DESCRIPTION
            "Clears Major Alarm for DNX-1u Power Supply configuration error."
        ::= { dnxTrapEnterprise 3165 }
        
END
