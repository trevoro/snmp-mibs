USR-TD-MIB DEFINITIONS ::= BEGIN
	 IMPORTS
         Counter32, Integer32,
         OBJECT-IDENTITY, OBJECT-TYPE , MODULE-IDENTITY
                FROM SNMPv2-SMI
         TruthValue 
                FROM SNMPv2-TC
         common
                FROM USR-DEFINITIONS-MIB ;
usrTundisp   MODULE-IDENTITY
             LAST-UPDATED "200204061334Z"
             ORGANIZATION "CommWorks Corporation, a 3Com Company"
             CONTACT-INFO "Customer Support"
             DESCRIPTION
                     "The commWorks enterprise defined MIB objects for
                      the tunnel dispatcher."
--           REVISION "200204061334Z"
--           DESCRIPTION " Added MODULE-IDENTITY and corrected
--                         SNMPv2 syntax."
            ::= { common 68 }
usrTDGlobal  OBJECT-IDENTITY
           STATUS          current
           DESCRIPTION
              "The root of the TD global Object-Identifiers."
           ::= { usrTundisp 1 }
usrTDStatsTable OBJECT-TYPE
           SYNTAX          SEQUENCE OF UsrTDStatsEntry 
           MAX-ACCESS      not-accessible
           STATUS          current
           DESCRIPTION
              ""
           ::= { usrTDGlobal 1  }
usrTDStatsEntry OBJECT-TYPE
           SYNTAX          UsrTDStatsEntry 
           MAX-ACCESS      not-accessible
           STATUS          current
           DESCRIPTION
              "."
           INDEX { usrTDConfigIndex }
           ::= {usrTDStatsTable 1 }
UsrTDStatsEntry ::= SEQUENCE {
           usrTDStatsIndex Integer32,
           usrTDNumPPTPTunnelsSwitchedtoL2TP
                   Counter32,
           usrTDNumPPTPTunnelsSwitchedtoPPTP
                   Counter32,
           usrTDNumL2TPTunnelSwitchedtoPPTP
                   Counter32,
           usrTDNumL2TPTunnelSwitchedtoL2TP 
                   Counter32 ,
           usrTDNumActivePPTPTunnelsSwitchedtoL2TP
                   Counter32 ,
           usrTDNumActivePPTPTunnelsSwitchedtoPPTP
                   Counter32,
           usrTDNumActiveL2TPTunnelsSwitchedtoPPTP
                   Counter32,
           usrTDNumActiveL2TPTunnelsSwitchedtoL2TP
                   Counter32
 }
usrTDStatsIndex  OBJECT-TYPE
    SYNTAX Integer32
    MAX-ACCESS      read-only
    STATUS          current
    DESCRIPTION
            " A unique value for each tundispatcher protocol stack. "
         ::= { usrTDStatsEntry 1 }
usrTDNumPPTPTunnelsSwitchedtoL2TP OBJECT-TYPE
           SYNTAX          Counter32
           MAX-ACCESS      read-only
           STATUS          current
           DESCRIPTION
               "Defines the number of PPTPTunnelsSwitchedtoL2TP." 
           ::= { usrTDStatsEntry 2 }
usrTDNumPPTPTunnelsSwitchedtoPPTP OBJECT-TYPE
           SYNTAX          Counter32
           MAX-ACCESS      read-only
           STATUS          current
           DESCRIPTION
               "Defines the number of usrTDNumPPTPTunnelsSwitchedtoPPTP."   
           ::= { usrTDStatsEntry 3 }
usrTDNumL2TPTunnelSwitchedtoPPTP OBJECT-TYPE   
           SYNTAX          Counter32
           MAX-ACCESS      read-only
           STATUS          current
           DESCRIPTION
               "Defines the number of usrTDNumL2TPTunnelSwitchedtoPPTP."
           ::= { usrTDStatsEntry 4 }
usrTDNumL2TPTunnelSwitchedtoL2TP OBJECT-TYPE   
           SYNTAX          Counter32
           MAX-ACCESS      read-only
           STATUS          current
           DESCRIPTION
               "Defines the number of usrTDNumL2TPTunnelSwitchedtoL2TP."
           ::= { usrTDStatsEntry 5 }
usrTDNumActivePPTPTunnelsSwitchedtoL2TP OBJECT-TYPE
	  SYNTAX 	Counter32
          MAX-ACCESS    read-only
	  STATUS          current
          DESCRIPTION
                 "Defines the number of usrTDNumActivePPTPTunnelsSwitchedtoL2TP."
           ::= { usrTDStatsEntry 6 }
usrTDNumActivePPTPTunnelsSwitchedtoPPTP OBJECT-TYPE
          SYNTAX        Counter32
          MAX-ACCESS    read-only
          STATUS          current 
          DESCRIPTION 
                 "Defines the number of usrTDNumActivePPTPTunnelsSwitchedtoPPTP."
           ::= { usrTDStatsEntry 7 }
usrTDNumActiveL2TPTunnelsSwitchedtoPPTP OBJECT-TYPE 
          SYNTAX        Counter32
          MAX-ACCESS    read-only
          STATUS        current
          DESCRIPTION
                 "Defines the number of usrTDNumActiveL2TPTunnelsSwitchedtoL2TP."
          ::= { usrTDStatsEntry 8 }
usrTDNumActiveL2TPTunnelsSwitchedtoL2TP OBJECT-TYPE 
          SYNTAX        Counter32
          MAX-ACCESS    read-only
          STATUS        current  
          DESCRIPTION
                 "Defines the number of usrTDNumActiveL2TPTunnelsSwitchedtoL2TP."
          ::= { usrTDStatsEntry 9 } 
usrTDConfigTable OBJECT-TYPE
           SYNTAX          SEQUENCE OF UsrTDConfigEntry
           MAX-ACCESS      not-accessible
           STATUS          current
           DESCRIPTION
              ""
           ::= { usrTDGlobal 2 }
usrTDConfigEntry OBJECT-TYPE
           SYNTAX          UsrTDConfigEntry
           MAX-ACCESS      not-accessible
           STATUS          current
           DESCRIPTION
              "."
           INDEX { usrTDConfigIndex }
           ::= {usrTDConfigTable 1 }
UsrTDConfigEntry ::= SEQUENCE {
           usrTDConfigIndex Integer32,
           usrTunnelSwitchEnabled TruthValue
 }
usrTDConfigIndex  OBJECT-TYPE
    SYNTAX Integer32
    MAX-ACCESS      read-only
    STATUS          current
    DESCRIPTION
            " A unique value for each tundispatcher protocol stack. "
         ::= { usrTDConfigEntry 1 }
usrTunnelSwitchEnabled  OBJECT-TYPE
       SYNTAX          TruthValue
       MAX-ACCESS      read-write
       STATUS          current
       DESCRIPTION
            "Defines.If Load Balancing is enabled or not."
       DEFVAL          { true }
       ::= { usrTDConfigEntry 2 }
END    -- End of USR-TD-MIB DEFINITIONS
-- ************************************************************************
--
--	usr_NPPTP.mib - An enterprise specific MIB file for the 
--                      Point to Point tunneling protocol 
--
-- Author:         Ajoy K Singh 
--
