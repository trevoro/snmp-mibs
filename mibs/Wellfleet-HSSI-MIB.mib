Wellfleet-HSSI-MIB DEFINITIONS ::= BEGIN

-- Created by mdl2asn version 3.1
-- Creation date: Wed Aug 30 16:42:20 EDT 1995


    IMPORTS

      Counter, Gauge, TimeTicks
        FROM RFC1155-SMI
      OBJECT-TYPE
        FROM RFC-1212
      wfLine
        FROM Wellfleet-COMMON-MIB;


    wfHssiTable OBJECT-TYPE
        SYNTAX	SEQUENCE OF WfHssiEntry
        ACCESS	not-accessible
        STATUS	mandatory
        DESCRIPTION
                "HSSI line record"
        ::= { wfLine 7 }

    wfHssiEntry OBJECT-TYPE
        SYNTAX	WfHssiEntry
        ACCESS	not-accessible
        STATUS	mandatory
        DESCRIPTION
                "An entry in the HSSI table"
        INDEX	{ wfHssiSlot,
    		  wfHssiConnector }
        ::= { wfHssiTable 1 }

    WfHssiEntry ::= SEQUENCE {
    	    wfHssiDelete
    		INTEGER,
    	    wfHssiDisable
    		INTEGER,
    	    wfHssiState
    		INTEGER,
    	    wfHssiSlot
    		INTEGER,
    	    wfHssiConnector
    		INTEGER,
    	    wfHssiCct
    		INTEGER,
    	    wfHssiBofl
    		INTEGER,
    	    wfHssiBoflTmo
    		INTEGER,
    	    wfHssiMtu
    		INTEGER,
    	    wfHssiMadr
    		OCTET STRING,
    	    wfHssiService
    		INTEGER,
    	    wfHssiWanProtocol
    		INTEGER,
    	    wfHssiTransmissionInterface
    		INTEGER,
    	    wfHssiExternalClkSpeed
    		INTEGER,
    	    wfHssiCrcSize
    		INTEGER,
    	    wfHssiInternalClkTestMode
    		INTEGER,
    	    wfHssiRxOctets
    		Counter,
    	    wfHssiRxFrames
    		Counter,
    	    wfHssiTxOctets
    		Counter,
    	    wfHssiTxFrames
    		Counter,
    	    wfHssiInDiscards
    		Counter,
    	    wfHssiInErrors
    		Counter,
    	    wfHssiOutDiscards
    		Counter,
    	    wfHssiOutErrors
    		Counter,
    	    wfHssiRxLongFrames
    		Counter,
    	    wfHssiTxClipFrames
    		Counter,
    	    wfHssiRxReplenMisses
    		Counter,
    	    wfHssiLastRxErrorCtrl
    		INTEGER,
    	    wfHssiRxCrcErrors
    		Counter,
    	    wfHssiRxOverruns
    		Counter,
    	    wfHssiRxAborts
    		Counter,
    	    wfHssiLastTxErrorCtrl
    		INTEGER,
    	    wfHssiTxAborts
    		Counter,
    	    wfHssiTxUnderruns
    		Counter,
    	    wfHssiRxRingErrors
    		Counter,
    	    wfHssiLastRxRingState
    		INTEGER,
    	    wfHssiRxRingOverruns
    		Counter,
    	    wfHssiTxRingErrors
    		Counter,
    	    wfHssiLastTxRingState
    		INTEGER,
    	    wfHssiPortOpErrors
    		Counter,
    	    wfHssiInternOpErrors
    		Counter,
    	    wfHssiHostErrors
    		Counter,
    	    wfHssiRxProcessings
    		Counter,
    	    wfHssiTxProcessings
    		Counter,
    	    wfHssiTxCmplProcessings
    		Counter,
    	    wfHssiIntrProcessings
    		Counter,
    	    wfHssiBoflNum
    		INTEGER,
    	    wfHssiBoflLen
    		INTEGER,
    	    wfHssiRxBufferLength
    		INTEGER,
    	    wfHssiMemPageLength
    		INTEGER,
    	    wfHssiRxRingLength
    		INTEGER,
    	    wfHssiTxRingLength
    		INTEGER,
    	    wfHssiRxFifoWatermark
    		INTEGER,
    	    wfHssiTxFifoWatermark
    		INTEGER,
    	    wfHssiMaxRxMemory
    		INTEGER,
    	    wfHssiLinkInterface
    		INTEGER,
    	    wfHssiTurboBofl
    		INTEGER,
    	    wfHssiCfgRxQueueLength
    		INTEGER,
    	    wfHssiCfgTxQueueLength
    		INTEGER,
    	    wfHssiLineNumber
    		INTEGER,
    	    wfHssiCfgCngstCtlEnable
    		INTEGER,
    	    wfHssiLastChange
    		TimeTicks,
    	    wfHssiOutQLen
    		Gauge,
	    wfHssiCarrLossDebounceTmo
    		INTEGER,
	    wfHssiModule
    		INTEGER,
	    wfHssiActualConnector
    		INTEGER,
	    wfHssiLoopback
    		INTEGER,
	    wfHssiReceiveAllFrames
    		INTEGER
        }

    wfHssiDelete OBJECT-TYPE
        SYNTAX	INTEGER {
    		    created(1),
    		    deleted(2)
    		}
        ACCESS	read-write
        STATUS	mandatory
        DESCRIPTION
                "Create/Delete parameter"
        DEFVAL	{ created }
        ::= { wfHssiEntry 1 }

    wfHssiDisable OBJECT-TYPE
        SYNTAX	INTEGER {
    		    enabled(1),
    		    disabled(2)
    		}
        ACCESS	read-write
        STATUS	mandatory
        DESCRIPTION
                "Enable/Disable parameter"
        DEFVAL	{ enabled }
        ::= { wfHssiEntry 2 }

    wfHssiState OBJECT-TYPE
        SYNTAX	INTEGER {
    		    up(1),
    		    lmiwait(2),
    		    boflwait(3),
    		    cawait(4),
    		    init(5),
    		    notpresent(6),
		    dteloopback(7),
		    dceloopback(8),
		    dceloopbackwait(9),
		    dceloopbacktmo(10),
                    lineloopbofltest(19),
                    notpres(20)
    		}
        ACCESS	read-only
        STATUS	mandatory
        DESCRIPTION
                "Line Driver state variable, Not Present, Init, Down, Up"
        DEFVAL	{ notpres }
        ::= { wfHssiEntry 3 }

    wfHssiSlot OBJECT-TYPE
        SYNTAX	INTEGER(1..14)
        ACCESS	read-only
        STATUS	mandatory
        DESCRIPTION
                "Instance ID Slot, filled in by driver"
        ::= { wfHssiEntry 4 }

    wfHssiConnector OBJECT-TYPE
        SYNTAX	INTEGER {
    		    one(1),
    		    two(2),
    		    three(3),
    		    four(4)
    		}
        ACCESS	read-only
        STATUS	mandatory
        DESCRIPTION
                "Instance ID Connector, filled in by driver"
        ::= { wfHssiEntry 5 }

    wfHssiCct OBJECT-TYPE
        SYNTAX	INTEGER(1..1023)
        ACCESS	read-write
        STATUS	mandatory
        DESCRIPTION
                "CCT number for this line instance"
        ::= { wfHssiEntry 6 }

    wfHssiBofl OBJECT-TYPE
        SYNTAX	INTEGER {
    		    enabled(1),
    		    disabled(2)
    		}
        ACCESS	read-write
        STATUS	mandatory
        DESCRIPTION
                "breath of life parameter"
        DEFVAL	{ enabled }
        ::= { wfHssiEntry 7 }

    wfHssiBoflTmo OBJECT-TYPE
        SYNTAX	INTEGER(1..60)
        ACCESS	read-write
        STATUS	mandatory
        DESCRIPTION
                "breath of life frequency in seconds"
        DEFVAL	{ 1 }
        ::= { wfHssiEntry 8 }

    wfHssiMtu OBJECT-TYPE
        SYNTAX	INTEGER(3..4608)
        ACCESS	read-write
        STATUS	mandatory
        DESCRIPTION
                "MTU parameter, this is buffer size for HSSI media, fixed"
        DEFVAL	{ 4608 }
        ::= { wfHssiEntry 9 }

    wfHssiMadr OBJECT-TYPE
        SYNTAX	OCTET STRING
        ACCESS	read-only
        STATUS	mandatory
        DESCRIPTION
                "Line MAC address, fixed - line driver fills in from the 48 bit
                address stored in the serial number prom for this connector."
        ::= { wfHssiEntry 10 }

    wfHssiService OBJECT-TYPE
        SYNTAX	INTEGER {
    		    transparent(1),
    		    undefined(2)
    		}
        ACCESS	read-write
        STATUS	mandatory
        DESCRIPTION
                "Service type for this circuit. Transparent is raw HDLC mode, and is the
                only service provided on the current HSSI product"
        DEFVAL	{ transparent }
        ::= { wfHssiEntry 11 }

    wfHssiWanProtocol OBJECT-TYPE
        SYNTAX	INTEGER {
    		    standard(1),
    		    passthru(2),
    		    ppp(3),
    		    smds(4),
    		    framerelay(5),
    		    atm(6),
    		    sw(7),
    		    switch(8)
    		}
        ACCESS	read-write
        STATUS	mandatory
        DESCRIPTION
                "WAN protocol selection is provided via this parameter. The
                supported protocols can be selected per interface."
        DEFVAL	{ standard }
        ::= { wfHssiEntry 12 }

    wfHssiTransmissionInterface OBJECT-TYPE
        SYNTAX	INTEGER {
    		    dsone(1),
    		    dsthree(3)
    		}
        ACCESS	read-write
        STATUS	mandatory
        DESCRIPTION
                "T1 or T3,  in the future OC1, OC3 and OC12.  Used for MIB selection"
        DEFVAL	{ dsthree }
        ::= { wfHssiEntry 13 }

    wfHssiExternalClkSpeed OBJECT-TYPE
        SYNTAX	INTEGER(307200..52638515)
        ACCESS	read-write
        STATUS	mandatory
        DESCRIPTION
                "External Clock Speed, Used in the future for route selection"
        DEFVAL	{ 46359642 }
        ::= { wfHssiEntry 14 }

    wfHssiCrcSize OBJECT-TYPE
        SYNTAX	INTEGER {
    		    crc16bit(1),
    		    crc32bit(2)
    		}
        ACCESS	read-write
        STATUS	mandatory
        DESCRIPTION
                "CRC size parameter, 16 bit standard CCITT or extended 32 bit CRC"
        DEFVAL	{ crc32bit }
        ::= { wfHssiEntry 15 }

    wfHssiInternalClkTestMode OBJECT-TYPE
        SYNTAX	INTEGER {
    		    enabled(1),
    		    disabled(2)
    		}
        ACCESS	read-write
        STATUS	mandatory
        DESCRIPTION
                "Enables internal transmit clock generation. Should NEVER be enabled for
                normal operation."
        DEFVAL	{ disabled }
        ::= { wfHssiEntry 16 }

    wfHssiRxOctets OBJECT-TYPE
        SYNTAX	Counter
        ACCESS	read-only
        STATUS	mandatory
        DESCRIPTION
                "Number of bytes received without error"
        ::= { wfHssiEntry 17 }

    wfHssiRxFrames OBJECT-TYPE
        SYNTAX	Counter
        ACCESS	read-only
        STATUS	mandatory
        DESCRIPTION
                "Number of frames received without error"
        ::= { wfHssiEntry 18 }

    wfHssiTxOctets OBJECT-TYPE
        SYNTAX	Counter
        ACCESS	read-only
        STATUS	mandatory
        DESCRIPTION
                "Number of bytes transmitted without error"
        ::= { wfHssiEntry 19 }

    wfHssiTxFrames OBJECT-TYPE
        SYNTAX	Counter
        ACCESS	read-only
        STATUS	mandatory
        DESCRIPTION
                "Number of frames transmitted without error"
        ::= { wfHssiEntry 20 }

    wfHssiInDiscards OBJECT-TYPE
        SYNTAX	Counter
        ACCESS	read-only
        STATUS	mandatory
        DESCRIPTION
                "Number of error-free inbound packets discarded. Usually due to lack of
                memory resources."
        ::= { wfHssiEntry 21 }

    wfHssiInErrors OBJECT-TYPE
        SYNTAX	Counter
        ACCESS	read-only
        STATUS	mandatory
        DESCRIPTION
                "Number of inbound packets not delivered to higher-layer protocol because
                of errors."
        ::= { wfHssiEntry 22 }

    wfHssiOutDiscards OBJECT-TYPE
        SYNTAX	Counter
        ACCESS	read-only
        STATUS	mandatory
        DESCRIPTION
                "Number of error-free outbound packets discarded. Usually due to lack of
                transmission bandwidth."
        ::= { wfHssiEntry 23 }

    wfHssiOutErrors OBJECT-TYPE
        SYNTAX	Counter
        ACCESS	read-only
        STATUS	mandatory
        DESCRIPTION
                "Number of outbound packets that could not be transmitted because of
                errors."
        ::= { wfHssiEntry 24 }

    wfHssiRxLongFrames OBJECT-TYPE
        SYNTAX	Counter
        ACCESS	read-only
        STATUS	mandatory
        DESCRIPTION
                "Number of Long frames dropped on receive because of length"
        ::= { wfHssiEntry 25 }

    wfHssiTxClipFrames OBJECT-TYPE
        SYNTAX	Counter
        ACCESS	read-only
        STATUS	mandatory
        DESCRIPTION
                "Number of frames clipped in the transmit routine"
        ::= { wfHssiEntry 26 }

    wfHssiRxReplenMisses OBJECT-TYPE
        SYNTAX	Counter
        ACCESS	read-only
        STATUS	mandatory
        DESCRIPTION
                "Number of failed attempts by the line driver to aquire a packet buffer"
        ::= { wfHssiEntry 27 }

    wfHssiLastRxErrorCtrl OBJECT-TYPE
        SYNTAX	INTEGER
        ACCESS	read-only
        STATUS	mandatory
        DESCRIPTION
                "Last errored receive descriptor's control field"
        ::= { wfHssiEntry 28 }

    wfHssiRxCrcErrors OBJECT-TYPE
        SYNTAX	Counter
        ACCESS	read-only
        STATUS	mandatory
        DESCRIPTION
                "Number of frames received with CRC errors"
        ::= { wfHssiEntry 29 }

    wfHssiRxOverruns OBJECT-TYPE
        SYNTAX	Counter
        ACCESS	read-only
        STATUS	mandatory
        DESCRIPTION
                "Number of frames received with fifo overrun errors"
        ::= { wfHssiEntry 30 }

    wfHssiRxAborts OBJECT-TYPE
        SYNTAX	Counter
        ACCESS	read-only
        STATUS	mandatory
        DESCRIPTION
                "Number of frames received with abort status"
        ::= { wfHssiEntry 31 }

    wfHssiLastTxErrorCtrl OBJECT-TYPE
        SYNTAX	INTEGER
        ACCESS	read-only
        STATUS	mandatory
        DESCRIPTION
                "Last errored transmit descriptor's control field"
        ::= { wfHssiEntry 32 }

    wfHssiTxAborts OBJECT-TYPE
        SYNTAX	Counter
        ACCESS	read-only
        STATUS	mandatory
        DESCRIPTION
                "Number of transmit frames with internal abort errors"
        ::= { wfHssiEntry 33 }

    wfHssiTxUnderruns OBJECT-TYPE
        SYNTAX	Counter
        ACCESS	read-only
        STATUS	mandatory
        DESCRIPTION
                "Number of transmit frames aborted with underrun errors"
        ::= { wfHssiEntry 34 }

    wfHssiRxRingErrors OBJECT-TYPE
        SYNTAX	Counter
        ACCESS	read-only
        STATUS	mandatory
        DESCRIPTION
                "Number of receive ring error events"
        ::= { wfHssiEntry 35 }

    wfHssiLastRxRingState OBJECT-TYPE
        SYNTAX	INTEGER
        ACCESS	read-only
        STATUS	mandatory
        DESCRIPTION
                "Last 8 bit value from the recv ring state register"
        ::= { wfHssiEntry 36 }

    wfHssiRxRingOverruns OBJECT-TYPE
        SYNTAX	Counter
        ACCESS	read-only
        STATUS	mandatory
        DESCRIPTION
                "Number of receive ring overrun events"
        ::= { wfHssiEntry 37 }

    wfHssiTxRingErrors OBJECT-TYPE
        SYNTAX	Counter
        ACCESS	read-only
        STATUS	mandatory
        DESCRIPTION
                "Number of transmit ring error events"
        ::= { wfHssiEntry 38 }

    wfHssiLastTxRingState OBJECT-TYPE
        SYNTAX	INTEGER
        ACCESS	read-only
        STATUS	mandatory
        DESCRIPTION
                "Last 8 bit value from the transmit ring state register"
        ::= { wfHssiEntry 39 }

    wfHssiPortOpErrors OBJECT-TYPE
        SYNTAX	Counter
        ACCESS	read-only
        STATUS	mandatory
        DESCRIPTION
                "Number of port operation error events"
        ::= { wfHssiEntry 40 }

    wfHssiInternOpErrors OBJECT-TYPE
        SYNTAX	Counter
        ACCESS	read-only
        STATUS	mandatory
        DESCRIPTION
                "Number of internal operation error events"
        ::= { wfHssiEntry 41 }

    wfHssiHostErrors OBJECT-TYPE
        SYNTAX	Counter
        ACCESS	read-only
        STATUS	mandatory
        DESCRIPTION
                "Number of parity errs on host accesses to directly accessable registers."
        ::= { wfHssiEntry 42 }

    wfHssiRxProcessings OBJECT-TYPE
        SYNTAX	Counter
        ACCESS	read-only
        STATUS	mandatory
        DESCRIPTION
                "Number of receive frame processings (RINT)"
        ::= { wfHssiEntry 43 }

    wfHssiTxProcessings OBJECT-TYPE
        SYNTAX	Counter
        ACCESS	read-only
        STATUS	mandatory
        DESCRIPTION
                "Number of transmit processings, invokations of transmit routine"
        ::= { wfHssiEntry 44 }

    wfHssiTxCmplProcessings OBJECT-TYPE
        SYNTAX	Counter
        ACCESS	read-only
        STATUS	mandatory
        DESCRIPTION
                "Number of transmit complete processings (TINT)"
        ::= { wfHssiEntry 45 }

    wfHssiIntrProcessings OBJECT-TYPE
        SYNTAX	Counter
        ACCESS	read-only
        STATUS	mandatory
        DESCRIPTION
                "Number of Interrupt processings,  invokations of intr routine"
        ::= { wfHssiEntry 46 }

    wfHssiBoflNum OBJECT-TYPE
        SYNTAX	INTEGER(1..127)
        ACCESS	read-write
        STATUS	mandatory
        DESCRIPTION
                "Number of breath of life packets per breath of life"
        DEFVAL	{ 5 }
        ::= { wfHssiEntry 47 }

    wfHssiBoflLen OBJECT-TYPE
        SYNTAX	INTEGER(22..4450)
        ACCESS	read-write
        STATUS	mandatory
        DESCRIPTION
                "breath of life packet length"
        DEFVAL	{ 100 }
        ::= { wfHssiEntry 48 }

    wfHssiRxBufferLength OBJECT-TYPE
        SYNTAX	INTEGER {
    		    length4k(64),
    		    length8k(128)
    		}
        ACCESS	read-write
        STATUS	mandatory
        DESCRIPTION
                "Performance tunning parameter controls Receive buffer size."
        DEFVAL	{ length4k }
        ::= { wfHssiEntry 49 }

    wfHssiMemPageLength OBJECT-TYPE
        SYNTAX	INTEGER {
    		    length32(1),
    		    length256(3)
    		}
        ACCESS	read-write
        STATUS	mandatory
        DESCRIPTION
                "Performance tunning parameter controls device memory access burst length."
        DEFVAL	{ length32 }
        ::= { wfHssiEntry 50 }

    wfHssiRxRingLength OBJECT-TYPE
        SYNTAX	INTEGER
        ACCESS	read-only
        STATUS	mandatory
        DESCRIPTION
                "Current Receive Queue Length."
        ::= { wfHssiEntry 51 }

    wfHssiTxRingLength OBJECT-TYPE
        SYNTAX	INTEGER
        ACCESS	read-only
        STATUS	mandatory
        DESCRIPTION
                "Current Transmit Queue Length."
        ::= { wfHssiEntry 52 }

    wfHssiRxFifoWatermark OBJECT-TYPE
        SYNTAX	INTEGER(2..255)
        ACCESS	read-write
        STATUS	mandatory
        DESCRIPTION
                "Performance tunning parameter controls the receive watermark."
        DEFVAL	{ 2 }
        ::= { wfHssiEntry 53 }

    wfHssiTxFifoWatermark OBJECT-TYPE
        SYNTAX	INTEGER(2..255)
        ACCESS	read-write
        STATUS	mandatory
        DESCRIPTION
                "Performance tunning parameter controls the transmit watermark."
        DEFVAL	{ 16 }
        ::= { wfHssiEntry 54 }

    wfHssiMaxRxMemory OBJECT-TYPE
        SYNTAX	INTEGER(1..255)
        ACCESS	read-write
        STATUS	mandatory
        DESCRIPTION
                "Performance tunning parameter controls fifo area allowed for receive."
        DEFVAL	{ 1 }
        ::= { wfHssiEntry 55 }

    wfHssiLinkInterface OBJECT-TYPE
        SYNTAX	INTEGER {
    		    default(1),
    		    ace25(2),
    		    ace32(3)
    		}
        ACCESS	read-write
        STATUS	mandatory
        DESCRIPTION
                "Only for DEBUG."
        DEFVAL	{ default }
        ::= { wfHssiEntry 56 }

    wfHssiTurboBofl OBJECT-TYPE
        SYNTAX	INTEGER {
    		    enabled(1),
    		    disabled(2)
    		}
        ACCESS	read-write
        STATUS	mandatory
        DESCRIPTION
                "Only for DEBUG, Turbo breath of life parameter"
        DEFVAL	{ disabled }
        ::= { wfHssiEntry 57 }

    wfHssiCfgRxQueueLength OBJECT-TYPE
        SYNTAX	INTEGER(0..255)
        ACCESS	read-write
        STATUS	mandatory
        DESCRIPTION
                "Configured Receive Queue Length. Values other than zero over-ride the
                router selected values.  A value of zero has a special meaning.  Zero
                causes router based default values to be used.  Values larger than the
                compiled ring size are truncated to the compiled ring size. "
        ::= { wfHssiEntry 58 }

    wfHssiCfgTxQueueLength OBJECT-TYPE
        SYNTAX	INTEGER(0..255)
        ACCESS	read-write
        STATUS	mandatory
        DESCRIPTION
                "Configured Transmit Queue Length. Values other than zero over-ride the
                router selected values.  A value of zero has a special meaning.  Zero
                causes router based default values to be used.  Values larger than the
                compiled ring size are truncated to the compiled ring size. "
        ::= { wfHssiEntry 59 }

    wfHssiLineNumber OBJECT-TYPE
        SYNTAX	INTEGER
        ACCESS	read-write
        STATUS	mandatory
        DESCRIPTION
                "line number for this line instance"
        ::= { wfHssiEntry 60 }

    wfHssiCfgCngstCtlEnable OBJECT-TYPE
        SYNTAX	INTEGER {
    		    enable(1),
    		    disable(2)
    		}
        ACCESS	read-write
        STATUS	mandatory
        DESCRIPTION
                "Configured Congestion Control Enable. Enable or disable BNX switch
                congestion control on this HSSI port. Note that this has relevance only
                in the BNX switch and (currently) Frame Relay and SMDS switching
                functionality. If enabled, congestion control will monitor the levels of
                traffic and congestion and mark and drop certain packets as per of
                Frame Relay or SMDS protocols. See BNX doc for details on the
                congestion control strategy."
        DEFVAL	{ disable }
        ::= { wfHssiEntry 61 }

    wfHssiLastChange OBJECT-TYPE
        SYNTAX	TimeTicks
        ACCESS	read-only
        STATUS	mandatory
        DESCRIPTION
                "The value of SysUpTime at the time the interface entered it's current
                operational state (UP state).  SysUpTime is defined as the time (in
                hundredths of a second) since the network management portion of the
                system was last re-initialized.  Usually the time since boot."
        ::= { wfHssiEntry 62 }

    wfHssiOutQLen OBJECT-TYPE
        SYNTAX	Gauge
        ACCESS	read-only
        STATUS	mandatory
        DESCRIPTION
                "The instantaneous current length of the output packet queue (in packets)."
        ::= { wfHssiEntry 63 }

    wfHssiCarrLossDebounceTmo OBJECT-TYPE
	SYNTAX	INTEGER(0..2147483647)
	ACCESS	read-write
	STATUS	mandatory
	DESCRIPTION
		"This attribute determines how many seconds to wait before
		transitioning to the Carrier Lost state when the Carrier Signal
		is lost.  When set to 0 (default), the Driver will immediately
		transition to the lost state upon detecting Carrier Loss.  If
		the Carrier Signal returns prior to reaching this threshold,
		the Driver will not enter the Carrier Lost state at all."
	DEFVAL	{ 0 }
	::= { wfHssiEntry 64 }

    wfHssiModule OBJECT-TYPE
        SYNTAX  INTEGER {
                    one(1),
                    two(2),
                    three(3),
                    four(4)
                }
        ACCESS  read-only
        STATUS  mandatory
        DESCRIPTION
                "Module number for ASN platform, filled in by driver. For
                non-ASN platforms this attribute will not be used."
        ::= { wfHssiEntry 65 }

    wfHssiActualConnector OBJECT-TYPE
        SYNTAX  INTEGER {
                    one(1),
                    two(2),
                    three(3),
                    four(4),
                    five(5),
                    six(6),
                    seven(7),
                    eight(8)
                }
        ACCESS  read-only
        STATUS  mandatory
        DESCRIPTION
                "Actual connector number for ASN platform, filled in
                by driver. For non-ASN platforms, this attribute will
                not be used."
        ::= { wfHssiEntry 66 }

    wfHssiLoopback OBJECT-TYPE
        SYNTAX  INTEGER {
                    none(1),
                    localdigital(2),
                    localline(3),
                    remoteline(4)
                }
      ACCESS  read-write
        STATUS  mandatory
        DESCRIPTION
                "Loopback type requested, Local Digital (Loop A), Local Line
                (Loop B), Remote Line (Loop C), or none"
      DEFVAL  { none }
        ::= { wfHssiEntry 67 }

    wfHssiReceiveAllFrames OBJECT-TYPE
        SYNTAX  INTEGER {
                    enabled(1),
                    disabled(2)
                }
        ACCESS  read-write
        STATUS  mandatory
        DESCRIPTION
                "This attribute enables delivery of all receive frames to the 
                 HSSI device driver for processing.  When disabled,  frames 
                 less than 4 bytes in length are filtered out of the receive 
                 frame stream before reaching the device driver.  
                 It is necessary to enable the attribute when running Frame Relay
                 switched virtual circuits (SVC) in order to allow the reception 
                 of 3 byte frames."
        DEFVAL  { disabled }
        ::= { wfHssiEntry 68 }

    END  -- Wellfleet-HSSI-MIB
