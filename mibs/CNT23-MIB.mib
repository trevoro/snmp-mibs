--
--          Computer Network Technology, Corp.
--              6000 Nathan Lane North 
--              Plymouth, Minnesota  55442   
--
--                phone:  (763) 268-6000
--                  fax:  (763) 268-6800
--              support:  1-800-NET-TECH
--                email:  cnt.com
--
--	MIB Version:     1.5
--	Product Family:  CNT Zeus(2) MasterAgent(3) 
--
-- +------------+ if you change this mib, you increment the version number.
-- | Attention! | Also, this MIB is supported by the master agent, and
-- +------------+ that agent must also be compiled with this mib version.
--

CNT23-MIB DEFINITIONS ::= BEGIN

	IMPORTS
		TimeTicks, enterprises, Counter
			FROM RFC1065-SMI
		OBJECT-TYPE
			FROM RFC-1212
			DisplayString FROM RFC1213-MIB
		cnt2Snmp FROM CNT2-MIB;

---     cnt             OBJECT IDENTIFIER ::= { enterprises 333 }
---     cnt2            OBJECT IDENTIFIER ::= { cnt 2 }

---     cnt2Snmp        OBJECT IDENTIFIER ::= { cnt2 3 }


	-- Subagent Information --

	cnt2SubAgent	OBJECT IDENTIFIER ::= { cnt2Snmp 1 }


        cnt2RegistrationNum OBJECT-TYPE
            SYNTAX  INTEGER
            ACCESS  read-only
            STATUS  mandatory
            DESCRIPTION
                    "The number of registerations received from
                     subagents."
            ::= { cnt2SubAgent 1 }

	-- Registration Table --

        cnt2RegistrationTable OBJECT-TYPE
            SYNTAX  SEQUENCE OF Cnt2RegistrationEntry
            ACCESS  not-accessible
            STATUS  mandatory
            DESCRIPTION
                    "A list of registration entries.  The number of
                    registrations is given by the value of
                    cnt2RegstrationNum."
            ::= { cnt2SubAgent 2 }

        cnt2RegistrationEntry OBJECT-TYPE
            SYNTAX  Cnt2RegistrationEntry
            ACCESS  not-accessible
            STATUS  mandatory
            DESCRIPTION
                    "A subagent entry containing objects known about the
                    subagents by the master agent."
            INDEX   { cnt2RegisterIndex }
            ::= { cnt2RegistrationTable 1 }

        Cnt2RegistrationEntry ::=
            SEQUENCE {
                cnt2RegisterIndex
                    INTEGER,
                cnt2RegisterSlot
                    INTEGER,
                cnt2RegisterProtocol
                    INTEGER,
                cnt2RegisterTransport
                    INTEGER,
                cnt2RegisterAgentDescr
                    DisplayString,
                cnt2RegisterGroup
                    OBJECT IDENTIFIER,
                cnt2RegisterMibVersion
                    DisplayString,
                cnt2RegisterUpTime
                    TimeTicks,
                cnt2RegisterRowInstance
                    DisplayString
            }

        cnt2RegisterIndex OBJECT-TYPE
            SYNTAX  INTEGER
            ACCESS  read-only
            STATUS  mandatory
            DESCRIPTION
                    "A unique value for each registration.  Its value
                    ranges between 1 and the value of cnt2RegistrationNum.
                    The order in which entries exist in this table identifies
                    the chronological order in which subagent registrations
                    occurred."
            ::= { cnt2RegistrationEntry 1 }

        cnt2RegisterSlot OBJECT-TYPE
            SYNTAX  INTEGER
            ACCESS  read-only
            STATUS  mandatory
            DESCRIPTION
                    "The slot number for this subagent if it is connected
                    over the switch.  If it is TCP or UDP connected, this
                    value is 0."
            ::= { cnt2RegistrationEntry 2 }

        cnt2RegisterProtocol OBJECT-TYPE
            SYNTAX  INTEGER {
                        none(1),          -- none of the following
                        dpiv2(2),
                        smux(3),
                        local(4)
                    }
            ACCESS  read-only
            STATUS  mandatory
            DESCRIPTION
                    "The protocol used to interface to this subagent."
            ::= { cnt2RegistrationEntry 3 }

        cnt2RegisterTransport OBJECT-TYPE
            SYNTAX  INTEGER {
                        switch(1),
                        tcp(2),
                        udp(3),
                        memory(4),
			fl(5),
                        direct(6)
                    }
            ACCESS  read-only
            STATUS  mandatory
            DESCRIPTION
                    "The transport method/protocol underlying the
                    master/subagent protocol that is used to interface
                    to this subagent."
            ::= { cnt2RegistrationEntry 4 }

        cnt2RegisterAgentDescr OBJECT-TYPE
            SYNTAX  DisplayString (SIZE (0..255))
            ACCESS  read-only
            STATUS  mandatory
            DESCRIPTION
                    "A textual string containing a description of the 
                    registering subagent."
            ::= { cnt2RegistrationEntry 5 }

        cnt2RegisterGroup OBJECT-TYPE
            SYNTAX  OBJECT IDENTIFIER
            ACCESS  read-only
            STATUS  mandatory
            DESCRIPTION
                    "The group object identifier used by the subagent to
                    register.  If the subagent registered a row, this
                    will reflect the table identifier."
            ::= { cnt2RegistrationEntry 6 }

        cnt2RegisterMibVersion OBJECT-TYPE
            SYNTAX  DisplayString (SIZE (0..255))
            ACCESS  read-only
            STATUS  mandatory
            DESCRIPTION
                    "A textual string containing a reference to the body
                    administering the registered tree and the version of
                    the registered tree.  The string will be in one of the
                    following forms:
                          RFC xxxx - xxxx is the RFC number,
                          CNT x.y  - x is the major version, y is the
                                     minor version,
                          IETF vv/mmm/yy - (IETF Draft), vv is the version,
                                     mmm is a three character month code,
                                     yy is the year,
                          NAME vv/mmm/yy - NAME is a Standards Body name,
                                     vv is the version,
                                     mmm is a three character month code,
                                     yy is the year."
            ::= { cnt2RegistrationEntry 7 }

        cnt2RegisterUpTime OBJECT-TYPE
            SYNTAX  TimeTicks
            ACCESS  read-only
            STATUS  mandatory
            DESCRIPTION
                    "The time that the subagent has been registered,
                    relative to the master agent."
            ::= { cnt2RegistrationEntry 8 }

        cnt2RegisterRowInstance OBJECT-TYPE
            SYNTAX  DisplayString (SIZE (0..255))
            ACCESS  read-only
            STATUS  mandatory
            DESCRIPTION
                    "A textual string containing the following format:
                    *.x1[.x2.x3...xn], where
                        *  - the OID range registered by the subagent,
                        xn - object idenifier representing instance OIDs
                             registered by the subagent.
                    when appended to cnt2RegisterGroup, the entire OID
                    is the group and row registered by the subagent."
            ::= { cnt2RegistrationEntry 9 }

        END
