--
-- Copyright (c) 1999-2000 Dell
-- Module Name: arymgr.mib
-- Abstract:
--	Defines the Dell OpenManage Array Manager SNMP interface.
-- Authors:
--
-- Revision History:
--	ND (8/30/99)  0.1 - Original draft	
--  ND (12/3/99)  0.2 - Expanded the trap list by adding the Perc2Provider alerts  
--  ND (1/28/00)  0.3 - Added the arrayMgrGlobalStatus variable
--  GM (4/25/00)  0.4 - Changed MIB OID from 10890.7 to 10893.1.1
--  GM (5/25/00)  0.5 - Added several new variables
--  GM (11/29/00) 0.6 - Added two variables and 660F trap defs. 

ArrayManager-MIB DEFINITIONS ::= BEGIN

	IMPORTS
		enterprises
			FROM RFC1155-SMI
		OBJECT-TYPE
			FROM RFC-1212
        TRAP-TYPE
            FROM RFC-1215
		DisplayString
			FROM RFC1213-MIB;

		dell			OBJECT IDENTIFIER ::= { enterprises 674 }
		storage			OBJECT IDENTIFIER ::= { dell 10893 }
		software		OBJECT IDENTIFIER ::= { storage 1 }
        arrayManager		OBJECT IDENTIFIER ::= { software 1 }
		
-- ArrayManager MIB
	arrayMgrSoftwareVersion OBJECT-TYPE
		SYNTAX DisplayString
		ACCESS read-only
		STATUS mandatory
		DESCRIPTION
			"Version information for the Dell OpenManage
			 Array Manager software."
			::= {arrayManager 1}
	                              
	arrayMgrGlobalStatus OBJECT-TYPE
		SYNTAX INTEGER {
			critical (1),
			warning  (2),
			normal   (3),
			unknown  (4) }
		ACCESS read-only
		STATUS mandatory
		DESCRIPTION
			"Global health information for the Dell
			 Array Manager software."
			::= {arrayManager 2}

	arrayMgrSoftwareManufacturer OBJECT-TYPE
		SYNTAX DisplayString
		ACCESS read-only
		STATUS mandatory
		DESCRIPTION
			"Manufacturer information for the Dell
			 Array Manager software."
			::= {arrayManager 3}

	arrayMgrSoftwareProduct OBJECT-TYPE
		SYNTAX DisplayString
		ACCESS read-only
		STATUS mandatory
		DESCRIPTION
			"Product information for the Dell
			 Array Manager software."
			::= {arrayManager 4}

	arrayMgrSoftwareDescription OBJECT-TYPE
		SYNTAX DisplayString
		ACCESS read-only
		STATUS mandatory
		DESCRIPTION
			"Product Description for the Dell
			 Array Manager software."
			::= {arrayManager 5}
	                              
-- Following Array Manager objects are used in Trap generation

	aryMgrEvts OBJECT IDENTIFIER ::= { arrayManager 200 }
    
    controllerNameEv  OBJECT-TYPE
		SYNTAX	DisplayString
		ACCESS	read-only
		STATUS	mandatory
		DESCRIPTION
			"Controller Name for which trap is generated."
	::= { aryMgrEvts 201 }
	
	channelNumberEv  OBJECT-TYPE
		SYNTAX	INTEGER
		ACCESS	read-only
		STATUS	mandatory
		DESCRIPTION
			"Channel Number for which trap is generated."
	::= { aryMgrEvts 202 }

	targetIDEv  OBJECT-TYPE
		SYNTAX	INTEGER
		ACCESS	read-only
		STATUS	mandatory
		DESCRIPTION
			"SCSI ID of the device for which trap is generated."
	::= { aryMgrEvts 203 }   
	
	virtualDiskNameEv  OBJECT-TYPE
		SYNTAX	DisplayString
		ACCESS	read-only
		STATUS	mandatory
		DESCRIPTION
			"Virtual Disk for which trap is generated."
	::= { aryMgrEvts 204 }
                        
	arrayDiskNameEv  OBJECT-TYPE
		SYNTAX	DisplayString
		ACCESS	read-only
		STATUS	mandatory
		DESCRIPTION
			"Array Disk for which trap is generated."
	::= { aryMgrEvts 205 }

	oldVDConfigEv  OBJECT-TYPE
		SYNTAX	DisplayString
		ACCESS	read-only
		STATUS	mandatory
		DESCRIPTION
			"Current Virtual Disk configuration for which trap is generated"
	::= { aryMgrEvts 206 }

	newVDConfigEv  OBJECT-TYPE
		SYNTAX	DisplayString
		ACCESS	read-only
		STATUS	mandatory
		DESCRIPTION
			"New Virtual Disk configuration for which trap is generated."
	::= { aryMgrEvts 207 }
	
	enclosureNumberEv  OBJECT-TYPE
		SYNTAX	INTEGER
		ACCESS	read-only
		STATUS	mandatory
		DESCRIPTION
			"Enclosure for which the trap is generated."
	::= { aryMgrEvts 208 }

	unitNumberEv  OBJECT-TYPE
		SYNTAX	INTEGER
		ACCESS	read-only
		STATUS	mandatory
		DESCRIPTION
			"Unit number for which the trap is generated."
	::= { aryMgrEvts 209 }

-- Trap definitions which use variables defined in this MIB.

-- Array Disk related traps.

	arrayDiskFailed TRAP-TYPE
		ENTERPRISE aryMgrEvts
		VARIABLES {   
			controllerNameEv,
			arrayDiskNameEv
		}
		DESCRIPTION
			"%s,  %s failed."
	--#TYPE "Array Manager Event: Array Disk Failed"
	--#ARGUMENTS { 0, 1 }
	--#SEVERITY ERROR
	--#STATE FAILED
	::= 500

	arrayDiskRemoved TRAP-TYPE
		ENTERPRISE aryMgrEvts
		VARIABLES { 
			controllerNameEv,
			arrayDiskNameEv
		}
		DESCRIPTION
			"%s, %s removed."
	--#TYPE 		"Array Manager Event: Array Disk removed"
	--#ARGUMENTS 	{ 0, 1 }
	--#SEVERITY 	Warning
	--#STATE 		FAILED
	::= 501
           
	arrayDiskOffline TRAP-TYPE
		ENTERPRISE aryMgrEvts
		VARIABLES { 
			controllerNameEv,			
			arrayDiskNameEv
		}
		DESCRIPTION
			"%s, %s offline."
	--#TYPE 		"Array Manager Event: Array Disk offline"
	--#ARGUMENTS	{ 0, 1 }
	--#SEVERITY 	Warning
	--#STATE 		Degraded
	::= 502
            
	arrayDiskDegraded TRAP-TYPE
		ENTERPRISE aryMgrEvts
		VARIABLES { 
			controllerNameEv,			
			arrayDiskNameEv
		}
		DESCRIPTION
			"%s, %s degraded."
	--#TYPE 		"Array Manager Event: Array Disk degraded"
	--#ARGUMENTS	{ 0, 1 }
	--#SEVERITY 	Warning
	--#STATE 		Degraded
	::= 503
           
	arrayDiskInserted TRAP-TYPE
		ENTERPRISE aryMgrEvts
		VARIABLES { 
			controllerNameEv,			
			arrayDiskNameEv
		}
		DESCRIPTION
			"%s, %s inserted."
	--#TYPE 		"Array Manager Event: Array Disk inserted"
	--#ARGUMENTS	{ 0, 1 }
	--#SEVERITY 	Informational
	--#STATE 		Operational
	::= 504
                
    virtualDiskCreated TRAP-TYPE
		ENTERPRISE aryMgrEvts
		VARIABLES {          
			controllerNameEv,			
			virtualDiskNameEv
		}
		DESCRIPTION
			"%s, virtual disk (%s) created."
	--#TYPE 		"Array Manager Event: Virtual Disk created"
	--#ARGUMENTS	{ 0, 1 }
	--#SEVERITY 	Informational
	--#STATE 		operational
	::= 505
	
	virtualDiskDeleted TRAP-TYPE
		ENTERPRISE aryMgrEvts
		VARIABLES {          
			controllerNameEv,			
			virtualDiskNameEv
		}
		DESCRIPTION
			"%s, virtual disk (%s) deleted."
	--#TYPE 		"Array Manager Event: Virtual Disk deleted"
	--#ARGUMENTS	{ 0, 1 }
	--#SEVERITY 	Warning
	--#STATE 		Failed
	::= 506
	       
	virtualDiskConfigChanged TRAP-TYPE
		ENTERPRISE aryMgrEvts
		VARIABLES {          
			controllerNameEv,			
			virtualDiskNameEv,
			oldVDConfigEv,
			newVDConfigEv
		}
		DESCRIPTION
			"%s, virtual disk (%s) configuration changed from %s to %s"
	--#TYPE 		"Array Manager Event: Virtual Disk created"
	--#ARGUMENTS	{ 0, 1, 2, 3 }
	--#SEVERITY 	Informational
	--#STATE 		operational
	::= 507
	       
	virtualDiskFailed TRAP-TYPE
		ENTERPRISE aryMgrEvts
		VARIABLES {          
			controllerNameEv,			
			virtualDiskNameEv
		}
		DESCRIPTION
			"%s, virtual disk (%s) failed."
	--#TYPE 		"Array Manager Event: Virtual Disk failed"
	--#ARGUMENTS	{ 0, 1 }
	--#SEVERITY 	Error
	--#STATE 		Failed
	::= 508              
	
	virtualDiskDegraded TRAP-TYPE
		ENTERPRISE aryMgrEvts
		VARIABLES {          
			controllerNameEv,			
			virtualDiskNameEv
		}
		DESCRIPTION
			"%s, virtual disk (%s) degraded."
	--#TYPE 		"Array Manager Event: Virtual Disk degraded"
	--#ARGUMENTS	{ 0, 1 }
	--#SEVERITY 	Warning
	--#STATE 		Degraded
	::= 509

	vdFailedRedundancy TRAP-TYPE
		ENTERPRISE aryMgrEvts
		VARIABLES {          
			controllerNameEv,			
			virtualDiskNameEv
		}
		DESCRIPTION
			"%s, virtual disk (%s) is no longer redundant."
	--#TYPE 		"Array Manager Event: Virtual Disk failed redundancy"
	--#ARGUMENTS	{ 0, 1 }
	--#SEVERITY 	Warning
	--#STATE 		Degraded
	::= 510

-- Task started related traps
           
	checkConsistencyStarted TRAP-TYPE
		ENTERPRISE aryMgrEvts
		VARIABLES {          
			controllerNameEv,			
			virtualDiskNameEv
		}
		DESCRIPTION
			"%s, virtual disk (%s) check consistency started."
	--#TYPE 		"Array Manager Event: Virtual Disk check consistency started"
	--#ARGUMENTS	{ 0, 1 }
	--#SEVERITY 	Informational
	--#STATE 		Operational
	::= 520

	vdFormatStarted TRAP-TYPE
		ENTERPRISE aryMgrEvts
		VARIABLES {          
			controllerNameEv,			
			virtualDiskNameEv
		}
		DESCRIPTION
			"%s, virtual disk (%s) format started."
	--#TYPE 		"Array Manager Event: Virtual Disk format started"
	--#ARGUMENTS	{ 0, 1 }
	--#SEVERITY 	Warning
	--#STATE 		Operational
	::= 521
    
    adFormatStarted TRAP-TYPE
		ENTERPRISE aryMgrEvts
		VARIABLES {          
			controllerNameEv,			
			arrayDiskNameEv
		}
		DESCRIPTION
			"%s, %s format started."
	--#TYPE 		"Array Manager Event: Array Disk format started"
	--#ARGUMENTS	{ 0, 1 }
	--#SEVERITY 	Warning
	--#STATE 		Operational
	::= 522
    
    vdInitializeStarted TRAP-TYPE
		ENTERPRISE aryMgrEvts
		VARIABLES {          
			controllerNameEv,			
			virtualDiskNameEv
		}
		DESCRIPTION
			"%s, virtual disk (%s) initialization started."
	--#TYPE 		"Array Manager Event: Virtual Disk initialization started"
	--#ARGUMENTS	{ 0, 1 }
	--#SEVERITY 	Informational
	--#STATE 		Operational
	::= 523
    
    adInitializeStarted TRAP-TYPE
		ENTERPRISE aryMgrEvts
		VARIABLES {          
			controllerNameEv,			
			arrayDiskNameEv
		}
		DESCRIPTION
			"%s, %s initialize started."
	--#TYPE 		"Array Manager Event: Array Disk initialize started"
	--#ARGUMENTS	{ 0, 1 }
	--#SEVERITY 	Warning
	--#STATE 		Operational
	::= 524
    
    vdReconfigStarted TRAP-TYPE
		ENTERPRISE aryMgrEvts
		VARIABLES {          
			controllerNameEv,			
			virtualDiskNameEv,
			oldVDConfigEv,
			newVDConfigEv
		}
		DESCRIPTION
			"%s, virtual disk (%s) reconfiguration from 
			%s stripe size to %s stripe size started."
	--#TYPE 		"Array Manager Event: Virtual Disk Reconfiguration started"
	--#ARGUMENTS	{ 0, 1, 2, 3 }
	--#SEVERITY 	Warning
	--#STATE 		Operational
	::= 525

	vdRebuildStarted TRAP-TYPE
		ENTERPRISE aryMgrEvts
		VARIABLES {          
			controllerNameEv,			
			virtualDiskNameEv
		}
		DESCRIPTION
			"%s, virtual disk (%s) rebuild started."
	--#TYPE 		"Array Manager Event: Virtual Disk rebuild started"
	--#ARGUMENTS	{ 0, 1 }
	--#SEVERITY 	Warning
	--#STATE 		Operational
	::= 526

	adRebuildStarted TRAP-TYPE
		ENTERPRISE aryMgrEvts
		VARIABLES {          
			controllerNameEv,			
			arrayDiskNameEv
		}
		DESCRIPTION
			"%s, %s rebuild started."
	--#TYPE 		"Array Manager Event: Array Disk rebuild started"
	--#ARGUMENTS	{ 0, 1 }
	--#SEVERITY 	Warning
	--#STATE 		Operational
	::= 527
	
	adDiagStarted TRAP-TYPE
		ENTERPRISE aryMgrEvts
		VARIABLES {          
			controllerNameEv,			
			arrayDiskNameEv
		}
		DESCRIPTION
			"%s, %s diagnostics started."
	--#TYPE 		"Array Manager Event: Array Disk diagnostics started"
	--#ARGUMENTS	{ 0, 1 }
	--#SEVERITY 	Warning
	--#STATE 		Operational
	::= 528

-- Task cancellation related traps
	
	checkConsistencyCancelled TRAP-TYPE
		ENTERPRISE aryMgrEvts
		VARIABLES {          
			controllerNameEv,			
			virtualDiskNameEv
		}
		DESCRIPTION
			"%s, virtual disk (%s) consistency check cancelled."
	--#TYPE 		"Array Manager Event: Virtual Disk check consistency cancelled"
	--#ARGUMENTS	{ 0, 1 }
	--#SEVERITY 	Informational
	--#STATE 		Operational
	::= 529
	
	vdFormatCancelled TRAP-TYPE
		ENTERPRISE aryMgrEvts
		VARIABLES {          
			controllerNameEv,			
			virtualDiskNameEv
		}
		DESCRIPTION
			"%s, virtual disk (%s) format cancelled."
	--#TYPE 		"Array Manager Event: Virtual Disk format cancelled"
	--#ARGUMENTS	{ 0, 1 }
	--#SEVERITY 	Warning
	--#STATE 		Operational
	::= 530
    
    adFormatCancelled TRAP-TYPE
		ENTERPRISE aryMgrEvts
		VARIABLES {          
			controllerNameEv,			
			arrayDiskNameEv
		}
		DESCRIPTION
			"%s, %s format cancelled."
	--#TYPE 		"Array Manager Event: Array Disk format cancelled"
	--#ARGUMENTS	{ 0, 1 }
	--#SEVERITY 	Warning
	--#STATE 		Operational
	::= 531
	
	vdInitializeCancelled TRAP-TYPE
		ENTERPRISE aryMgrEvts
		VARIABLES {          
			controllerNameEv,			
			virtualDiskNameEv
		}
		DESCRIPTION
			"%s, virtual disk (%s) initialization cancelled."
	--#TYPE 		"Array Manager Event: Virtual Disk initialization cancelled"
	--#ARGUMENTS	{ 0, 1 }
	--#SEVERITY 	Warning
	--#STATE 		Operational
	::= 532
	  
	adInitializeCancelled TRAP-TYPE
		ENTERPRISE aryMgrEvts
		VARIABLES {          
			controllerNameEv,			
			arrayDiskNameEv
		}
		DESCRIPTION
			"%s, %s initialize cancelled."
	--#TYPE 		"Array Manager Event: Array Disk initialize cancelled"
	--#ARGUMENTS	{ 0, 1 }
	--#SEVERITY 	Warning
	--#STATE 		Operational
	::= 533
    
    vdReconfigCancelled TRAP-TYPE
		ENTERPRISE aryMgrEvts
		VARIABLES {          
			controllerNameEv,			
			virtualDiskNameEv
		}
		DESCRIPTION
			"%s, virtual disk (%s) reconfiguration cancelled."
	--#TYPE 		"Array Manager Event: Virtual Disk Reconfiguration cancelled"
	--#ARGUMENTS	{ 0, 1 }
	--#SEVERITY 	Warning
	--#STATE 		Operational
	::= 534

	vdRebuildCancelled TRAP-TYPE
		ENTERPRISE aryMgrEvts
		VARIABLES {          
			controllerNameEv,			
			virtualDiskNameEv
		}
		DESCRIPTION
			"%s, virtual disk (%s) rebuild cancelled."
	--#TYPE 		"Array Manager Event: Virtual Disk rebuild cancelled"
	--#ARGUMENTS	{ 0, 1 }
	--#SEVERITY 	Warning
	--#STATE 		Operational
	::= 535

	adRebuildCancelled TRAP-TYPE
		ENTERPRISE aryMgrEvts
		VARIABLES {          
			controllerNameEv,			
			arrayDiskNameEv
		}
		DESCRIPTION
			"%s, %s rebuild cancelled."
	--#TYPE 		"Array Manager Event: Array Disk rebuild cancelled"
	--#ARGUMENTS	{ 0, 1 }
	--#SEVERITY 	Warning
	--#STATE 		Operational
	::= 536

	adDiagCancelled TRAP-TYPE
		ENTERPRISE aryMgrEvts
		VARIABLES {          
			controllerNameEv,			
			arrayDiskNameEv
		}
		DESCRIPTION
			"%s, %s diagnostics cancelled."
	--#TYPE 		"Array Manager Event: Array Disk diagnostics cancelled"
	--#ARGUMENTS	{ 0, 1 }
	--#SEVERITY 	Warning
	--#STATE 		Operational
	::= 537
	
-- Task Failed related traps

	checkConsistencyFailed TRAP-TYPE
		ENTERPRISE aryMgrEvts
		VARIABLES {          
			controllerNameEv,			
			virtualDiskNameEv
		}
		DESCRIPTION
			"%s, virtual disk (%s) consistency check failed."
	--#TYPE 		"Array Manager Event: Virtual Disk check consistency failed"
	--#ARGUMENTS	{ 0, 1 }
	--#SEVERITY 	Error
	--#STATE 		Failed
	::= 538
	       
	vdFormatFailed TRAP-TYPE
		ENTERPRISE aryMgrEvts
		VARIABLES {          
			controllerNameEv,			
			virtualDiskNameEv
		}
		DESCRIPTION
			"%s, virtual disk (%s) format failed."
	--#TYPE 		"Array Manager Event: Virtual Disk format failed"
	--#ARGUMENTS	{ 0, 1 }
	--#SEVERITY 	Error
	--#STATE 		Failed
	::= 539
    
   	adFormatFailed TRAP-TYPE
		ENTERPRISE aryMgrEvts
		VARIABLES {          
			controllerNameEv,			
			arrayDiskNameEv
		}
		DESCRIPTION
			"%s, %s format failed."
	--#TYPE 		"Array Manager Event: Array Disk format failed"
	--#ARGUMENTS	{ 0, 1 }
	--#SEVERITY 	Error
	--#STATE 		Failed
	::= 540

	vdInitializeFailed TRAP-TYPE
		ENTERPRISE aryMgrEvts
		VARIABLES {          
			controllerNameEv,			
			virtualDiskNameEv
		}
		DESCRIPTION
			"%s, virtual disk (%s) initialization Failed."
	--#TYPE 		"Array Manager Event: Virtual Disk initialization Failed"
	--#ARGUMENTS	{ 0, 1 }
	--#SEVERITY 	Error
	--#STATE 		Failed
	::= 541

	adInitializeFailed TRAP-TYPE
		ENTERPRISE aryMgrEvts
		VARIABLES {          
			controllerNameEv,			
			arrayDiskNameEv
		}
		DESCRIPTION
			"%s, %s initialize failed."
	--#TYPE 		"Array Manager Event: Array Disk initialize failed"
	--#ARGUMENTS	{ 0, 1 }
	--#SEVERITY 	Error
	--#STATE 		Failed
	::= 542

	vdReconfigFailed TRAP-TYPE
		ENTERPRISE aryMgrEvts
		VARIABLES {          
			controllerNameEv,			
			virtualDiskNameEv
		}
		DESCRIPTION
			"%s, virtual disk (%s) reconfiguration failed."
	--#TYPE 		"Array Manager Event: Virtual Disk Reconfiguration failed"
	--#ARGUMENTS	{ 0, 1 }
	--#SEVERITY 	Error
	--#STATE 		Failed
	::= 543

	vdRebuildFailed TRAP-TYPE
		ENTERPRISE aryMgrEvts
		VARIABLES {          
			controllerNameEv,
			
			virtualDiskNameEv
		}
		DESCRIPTION
			"%s, virtual disk (%s) rebuild failed."
	--#TYPE 		"Array Manager Event: Virtual Disk rebuild failed"
	--#ARGUMENTS	{ 0, 1 }
	--#SEVERITY 	Error
	--#STATE 		Failed
	::= 544

	adRebuildFailed TRAP-TYPE
		ENTERPRISE aryMgrEvts
		VARIABLES {          
			controllerNameEv,			
			arrayDiskNameEv
		}
		DESCRIPTION
			"%s, %s rebuild failed."
	--#TYPE 		"Array Manager Event: Array Disk rebuild failed"
	--#ARGUMENTS	{ 0, 1 }
	--#SEVERITY 	Error
	--#STATE 		Failed
	::= 545
   
   	adDiagFailed TRAP-TYPE
		ENTERPRISE aryMgrEvts
		VARIABLES {          
			controllerNameEv,			
			arrayDiskNameEv
		}
		DESCRIPTION
			"%s, %s diagnostics failed."
	--#TYPE 		"Array Manager Event: Array Disk diagnostics failed"
	--#ARGUMENTS	{ 0, 1 }
	--#SEVERITY 	Error
	--#STATE 		Failed
	::= 546

-- Task completed related Traps
   
   checkConsistencyCompleted TRAP-TYPE
		ENTERPRISE aryMgrEvts
		VARIABLES {          
			controllerNameEv,			
			virtualDiskNameEv
		}
		DESCRIPTION
			"%s, virtual disk (%s) consistency check completed."
	--#TYPE 		"Array Manager Event: Virtual Disk check consistency completed"
	--#ARGUMENTS	{ 0, 1 }
	--#SEVERITY 	Informational
	--#STATE 		Operational
	::= 547

	vdFormatCompleted TRAP-TYPE
		ENTERPRISE aryMgrEvts
		VARIABLES {          
			controllerNameEv,			
			virtualDiskNameEv
		}
		DESCRIPTION
			"%s, virtual disk (%s) format completed."
	--#TYPE 		"Array Manager Event: Virtual Disk format completed"
	--#ARGUMENTS	{ 0, 1 }
	--#SEVERITY 	Informational
	--#STATE 		Operational
	::= 548

    adFormatCompleted TRAP-TYPE
		ENTERPRISE aryMgrEvts
		VARIABLES {          
			controllerNameEv,			
			arrayDiskNameEv
		}
		DESCRIPTION
			"%s, %s format completed."
	--#TYPE 		"Array Manager Event: Array Disk format completed"
	--#ARGUMENTS	{ 0, 1 }
	--#SEVERITY 	Informational
	--#STATE 		Operational
	::= 549  
  
 	vdInitializeCompleted TRAP-TYPE
		ENTERPRISE aryMgrEvts
		VARIABLES {          
			controllerNameEv,			
			virtualDiskNameEv
		}
		DESCRIPTION
			"%s, virtual disk (%s) initialization completed."
	--#TYPE 		"Array Manager Event: Virtual Disk initialization completed"
	--#ARGUMENTS	{ 0, 1 }
	--#SEVERITY 	Informational
	--#STATE 		Operational
	::= 550

	adInitializeCompleted TRAP-TYPE
		ENTERPRISE aryMgrEvts
		VARIABLES {          
			controllerNameEv,			
			arrayDiskNameEv
		}
		DESCRIPTION
			"%s, %s initialize completed."
	--#TYPE 		"Array Manager Event: Array Disk initialize completed"
	--#ARGUMENTS	{ 0, 1 }
	--#SEVERITY 	Informational
	--#STATE 		Operational
	::= 551 
	         
	vdReconfigCompleted TRAP-TYPE
		ENTERPRISE aryMgrEvts
		VARIABLES {          
			controllerNameEv,			
			virtualDiskNameEv
		}
		DESCRIPTION
			"%s, virtual disk (%s) reconfiguration completed."
	--#TYPE 		"Array Manager Event: Virtual Disk Reconfiguration completed"
	--#ARGUMENTS	{ 0, 1 }
	--#SEVERITY 	Warning
	--#STATE 		Operational
	::= 552

	vdRebuildCompleted TRAP-TYPE
		ENTERPRISE aryMgrEvts
		VARIABLES {          
			controllerNameEv,			
			virtualDiskNameEv
		}
		DESCRIPTION
			"%s, virtual disk (%s) rebuild completed."
	--#TYPE 		"Array Manager Event: Virtual Disk rebuild completed"
	--#ARGUMENTS	{ 0, 1 }
	--#SEVERITY 	Informational
	--#STATE 		Operational
	::= 553
          
	adRebuildCompleted TRAP-TYPE
		ENTERPRISE aryMgrEvts
		VARIABLES {          
			controllerNameEv,			
			arrayDiskNameEv
		}
		DESCRIPTION
			"%s, %s rebuild completed."
	--#TYPE 		"Array Manager Event: Array Disk rebuild completed"
	--#ARGUMENTS	{ 0, 1 }
	--#SEVERITY 	Informational
	--#STATE 		Operational
	::= 554
	
	adDiagCompleted TRAP-TYPE
		ENTERPRISE aryMgrEvts
		VARIABLES {          
			controllerNameEv,			
			arrayDiskNameEv
		}
		DESCRIPTION
			"%s, %s diagnostics completed."
	--#TYPE 		"Array Manager Event: Array Disk diagnostics completed"
	--#ARGUMENTS	{ 0, 1 }
	--#SEVERITY 	Informational
	--#STATE 		Operational
	::= 555

-- Perc, Perc 2/SC and Perc 2/DC SMART alert related traps

	percPredictiveFailure TRAP-TYPE
		ENTERPRISE aryMgrEvts
		VARIABLES {          
			controllerNameEv,			
			arrayDiskNameEv
		}
		DESCRIPTION
			"%s, %s reported predictive failure."
	--#TYPE 		"Array Manager Event: Predictive Failure reported"
	--#ARGUMENTS	{ 0, 1 }
	--#SEVERITY 	Warning
	--#STATE 		Operational
	::= 570
           
	percSCSISenseData TRAP-TYPE
		ENTERPRISE aryMgrEvts
		VARIABLES {          
			controllerNameEv,			
			arrayDiskNameEv
		}
		DESCRIPTION
			"%s, %s SCSI sense failure."
	--#TYPE 		"Array Manager Event: SCSI sense data"
	--#ARGUMENTS	{ 0, 1 }
	--#SEVERITY 	Warning
	--#STATE 		Operational
	::= 571

-- Perc 2 and Perc 2/Di Controller Battery related traps
    
    cntrlBatteryNeedsReconditioning	TRAP-TYPE
		ENTERPRISE aryMgrEvts
		VARIABLES {          
			controllerNameEv
		}
		DESCRIPTION
			"%s battery needs reconditioning."
	--#TYPE 		"Array Manager Event: Perc 2 Battery needs reconditioning"
	--#ARGUMENTS	{ 0 }
	--#SEVERITY 	Warning
	--#STATE 		Operational
	::= 579

	cntrlBatteryLow	TRAP-TYPE
		ENTERPRISE aryMgrEvts
		VARIABLES {          
			controllerNameEv
		}
		DESCRIPTION
			"%s battery low"
	--#TYPE 		"Array Manager Event: Perc 2 Battery low"
	--#ARGUMENTS	{ 0 }
	--#SEVERITY 	Warning
	--#STATE 		Operational
	::= 580

	cntrlBatteryRecondition	TRAP-TYPE
		ENTERPRISE aryMgrEvts
		VARIABLES {          
			controllerNameEv			
		}
		DESCRIPTION
			"%s battery is reconditioning."
	--#TYPE 		"Array Manager Event: Perc 2 Battery reconditioning"
	--#ARGUMENTS	{ 0, 1 }
	--#SEVERITY 	Informational
	--#STATE 		Operational
	::= 581
           
	cntrlBatteryReconComplete	TRAP-TYPE
		ENTERPRISE aryMgrEvts
		VARIABLES {          
			controllerNameEv
		}
		DESCRIPTION
			"%s battery reconditioning completed."
	--#TYPE 		"Array Manager Event: Perc 2 Battery reconditioning completed"
	--#ARGUMENTS	{ 0 }
	--#SEVERITY 	Informational
	--#STATE 		Operational
	::= 582

-- Controller operations related traps.

	cntrlPauseIO	TRAP-TYPE
		ENTERPRISE aryMgrEvts
		VARIABLES {          
			controllerNameEv
		}
		DESCRIPTION
			"%s I/O paused, I/O will automatically resume after the allotted time."
	--#TYPE 		"Array Manager Event: Pause I/O"
	--#ARGUMENTS	{ 0 }
	--#SEVERITY 	Warning
	--#STATE 		Operational
	::= 583

	cntrlResumeIO	TRAP-TYPE
		ENTERPRISE aryMgrEvts
		VARIABLES {          
			controllerNameEv
		}
		DESCRIPTION
			"%s I/O resumed."
	--#TYPE 		"Array Manager Event: Resume I/O"
	--#ARGUMENTS	{ 0 }
	--#SEVERITY 	Informational
	--#STATE 		Operational
	::= 584
           
-- Perc 2 and Perc 2/Si, Perc 2/Di, Perc 3/Si and Perc 3/Di SMART alerts

	perc2SmartFPTExceeded	TRAP-TYPE
		ENTERPRISE aryMgrEvts
		VARIABLES {          
			controllerNameEv,			
			arrayDiskNameEv
		}
		DESCRIPTION
			"%s SMART:FPT_EXCEEDED on %s."
	--#TYPE 		"Array Manager Event: Smart FPT Exceeded"
	--#ARGUMENTS	{ 0, 1 }
	--#SEVERITY 	Informational
	--#STATE 		Operational
	::= 585

	perc2SmartConfigChange	TRAP-TYPE
		ENTERPRISE aryMgrEvts
		VARIABLES {          
			controllerNameEv,			
			arrayDiskNameEv
		}
		DESCRIPTION
			"%s SMART configuration change on %s."
	--#TYPE 		"Array Manager Event: Smart Config Change"
	--#ARGUMENTS	{ 0, 1 }
	--#SEVERITY 	Warning
	--#STATE 		Operational
	::= 586
           
	perc2SmartWarning	TRAP-TYPE
		ENTERPRISE aryMgrEvts
		VARIABLES {          
			controllerNameEv,			
			arrayDiskNameEv
		}
		DESCRIPTION
			"%s SMART Warning on %s."
	--#TYPE 		"Array Manager Event: Smart Warning"
	--#ARGUMENTS	{ 0, 1 }
	--#SEVERITY 	Warning
	--#STATE 		Operational
	::= 587          
	
	perc2SmartWarningTemp	TRAP-TYPE
		ENTERPRISE aryMgrEvts
		VARIABLES {          
			controllerNameEv,			
			arrayDiskNameEv
		}
		DESCRIPTION
			"%s SMART Warning temperature on %s."
	--#TYPE 		"Array Manager Event: Smart warning temperature"
	--#ARGUMENTS	{ 0, 1 }
	--#SEVERITY 	Warning
	--#STATE 		Operational
	::= 588
	
	perc2SmartWarningDegraded	TRAP-TYPE
		ENTERPRISE aryMgrEvts
		VARIABLES {          
			controllerNameEv,			
			arrayDiskNameEv
		}
		DESCRIPTION
			"%s SMART warning degraded on %s."
	--#TYPE 		"Array Manager Event: Smart warning degraded"
	--#ARGUMENTS	{ 0, 1 }
	--#SEVERITY 	Warning
	--#STATE 		Operational
	::= 589

	perc2SmartFPTExceededTest	TRAP-TYPE
		ENTERPRISE aryMgrEvts
		VARIABLES {          
			controllerNameEv,
			arrayDiskNameEv
		}
		DESCRIPTION
			"%s, On %s the failure prediction threshold exceeded due to test-No action needed."
	--#TYPE 		"Array Manager Event: Smart Config Change"
	--#ARGUMENTS	{ 0, 1 }
	--#SEVERITY 	Warning
	--#STATE 		Operational
	::= 590

-- PV660F Events
-- Dell event = 700 Vendor event = 1
pv660fEvent_PHYSDEV_ONLINE    TRAP-TYPE
    ENTERPRISE  aryMgrEvts
    VARIABLES   {
	
	controllerNameEv,
	channelNumberEv,
	targetIDEv
	
    }
          DESCRIPTION
           "A hard disk has been placed online."
           --#SUMMARY  "[ctl: %d chn: %d tgt: %d :] A hard disk has been placed online." 
           --#ARGUMENTS {0,1,2}
           --#SEVERITY INFORMATION
           --#TIMEINDEX 4
           --#STATE OPERATIONAL
           ::= 700

-- Dell event = 701 Vendor event = 2
pv660fEvent_PHYSDEV_HOTSPARE    TRAP-TYPE
    ENTERPRISE  aryMgrEvts
    VARIABLES   {
	
	controllerNameEv,
	channelNumberEv,
	targetIDEv
	
    }
          DESCRIPTION
           "A hard disk added as hot spare."
           --#SUMMARY  "[ctl: %d chn: %d tgt: %d :] A hard disk added as hot spare." 
           --#ARGUMENTS {0,1,2}
           --#SEVERITY INFORMATION
           --#TIMEINDEX 4
           --#STATE OPERATIONAL
           ::= 701

-- Dell event = 702 Vendor event = 3
pv660fEvent_PHYSDEV_HARD_ERROR    TRAP-TYPE
    ENTERPRISE  aryMgrEvts
    VARIABLES   {
	
	controllerNameEv,
	channelNumberEv,
	targetIDEv
	
    }
          DESCRIPTION
           "Hard disk error found."
           --#SUMMARY  "[ctl: %d chn: %d tgt: %d :] Hard disk error found." 
           --#ARGUMENTS {0,1,2}
           --#SEVERITY WARNING
           --#TIMEINDEX 4
           --#STATE OPERATIONAL
           ::= 702

-- Dell event = 703 Vendor event = 4
pv660fEvent_PHYSDEV_PFA    TRAP-TYPE
    ENTERPRISE  aryMgrEvts
    VARIABLES   {
	
	controllerNameEv,
	channelNumberEv,
	targetIDEv
	
    }
          DESCRIPTION
           "Hard disk PFA condition found, this disk may fail soon."
           --#SUMMARY  "[ctl: %d chn: %d tgt: %d :] Hard disk PFA condition found, this disk may fail soon." 
           --#ARGUMENTS {0,1,2}
           --#SEVERITY WARNING
           --#TIMEINDEX 4
           --#STATE OPERATIONAL
           ::= 703

-- Dell event = 704 Vendor event = 5
pv660fEvent_PHYSDEV_AUTO_REBUILD_START    TRAP-TYPE
    ENTERPRISE  aryMgrEvts
    VARIABLES   {
	
	controllerNameEv,
	channelNumberEv,
	targetIDEv
	
    }
          DESCRIPTION
           "An automatic rebuild has started."
           --#SUMMARY  "[ctl: %d chn: %d tgt: %d :] An automatic rebuild has started." 
           --#ARGUMENTS {0,1,2}
           --#SEVERITY INFORMATION
           --#TIMEINDEX 4
           --#STATE OPERATIONAL
           ::= 704

-- Dell event = 705 Vendor event = 6
pv660fEvent_PHYSDEV_MANUAL_REBUILD_START    TRAP-TYPE
    ENTERPRISE  aryMgrEvts
    VARIABLES   {
	
	controllerNameEv,
	channelNumberEv,
	targetIDEv
	
    }
          DESCRIPTION
           "A rebuild has started."
           --#SUMMARY  "[ctl: %d chn: %d tgt: %d :] A rebuild has started." 
           --#ARGUMENTS {0,1,2}
           --#SEVERITY INFORMATION
           --#TIMEINDEX 4
           --#STATE OPERATIONAL
           ::= 705

-- Dell event = 706 Vendor event = 7
pv660fEvent_PHYSDEV_REBUILD_DONE    TRAP-TYPE
    ENTERPRISE  aryMgrEvts
    VARIABLES   {
	
	controllerNameEv,
	channelNumberEv,
	targetIDEv
	
    }
          DESCRIPTION
           "Rebuild is over."
           --#SUMMARY  "[ctl: %d chn: %d tgt: %d :] Rebuild is over." 
           --#ARGUMENTS {0,1,2}
           --#SEVERITY INFORMATION
           --#TIMEINDEX 4
           --#STATE OPERATIONAL
           ::= 706

-- Dell event = 707 Vendor event = 8
pv660fEvent_PHYSDEV_REBUILD_CANCELED    TRAP-TYPE
    ENTERPRISE  aryMgrEvts
    VARIABLES   {
	
	controllerNameEv,
	channelNumberEv,
	targetIDEv
	
    }
          DESCRIPTION
           "Rebuild is cancelled."
           --#SUMMARY  "[ctl: %d chn: %d tgt: %d :] Rebuild is cancelled." 
           --#ARGUMENTS {0,1,2}
           --#SEVERITY WARNING
           --#TIMEINDEX 4
           --#STATE OPERATIONAL
           ::= 707

-- Dell event = 708 Vendor event = 9
pv660fEvent_PHYSDEV_REBUILD_ERROR    TRAP-TYPE
    ENTERPRISE  aryMgrEvts
    VARIABLES   {
	
	controllerNameEv,
	channelNumberEv,
	targetIDEv
	
    }
          DESCRIPTION
           "Rebuild stopped with error."
           --#SUMMARY  "[ctl: %d chn: %d tgt: %d :] Rebuild stopped with error." 
           --#ARGUMENTS {0,1,2}
           --#SEVERITY ERROR
           --#TIMEINDEX 4
           --#STATE NONOPERATIONAL
           ::= 708

-- Dell event = 709 Vendor event = 10
pv660fEvent_PHYSDEV_REBUILD_NEWDEV_FAILED    TRAP-TYPE
    ENTERPRISE  aryMgrEvts
    VARIABLES   {
	
	controllerNameEv,
	channelNumberEv,
	targetIDEv
	
    }
          DESCRIPTION
           "Rebuild stopped with error. New device failed."
           --#SUMMARY  "[ctl: %d chn: %d tgt: %d :] Rebuild stopped with error. New device failed." 
           --#ARGUMENTS {0,1,2}
           --#SEVERITY ERROR
           --#TIMEINDEX 4
           --#STATE NONOPERATIONAL
           ::= 709

-- Dell event = 710 Vendor event = 11
pv660fEvent_PHYSDEV_REBUILD_SYSDEV_FAILED    TRAP-TYPE
    ENTERPRISE  aryMgrEvts
    VARIABLES   {
	
	controllerNameEv,
	channelNumberEv,
	targetIDEv
	
    }
          DESCRIPTION
           "Rebuild stopped because logical drive failed."
           --#SUMMARY  "[ctl: %d chn: %d tgt: %d :] Rebuild stopped because logical drive failed." 
           --#ARGUMENTS {0,1,2}
           --#SEVERITY ERROR
           --#TIMEINDEX 4
           --#STATE NONOPERATIONAL
           ::= 710

-- Dell event = 711 Vendor event = 12
pv660fEvent_PHYSDEV_DEAD    TRAP-TYPE
    ENTERPRISE  aryMgrEvts
    VARIABLES   {
	
	controllerNameEv,
	channelNumberEv,
	targetIDEv
	
    }
          DESCRIPTION
           "A hard disk has failed."
           --#SUMMARY  "[ctl: %d chn: %d tgt: %d :] A hard disk has failed." 
           --#ARGUMENTS {0,1,2}
           --#SEVERITY SERIOUS
           --#TIMEINDEX 4
           --#STATE OPERATIONAL
           ::= 711

-- Dell event = 712 Vendor event = 13
pv660fEvent_PHYSDEV_FOUND    TRAP-TYPE
    ENTERPRISE  aryMgrEvts
    VARIABLES   {
	
	controllerNameEv,
	channelNumberEv,
	targetIDEv
	
    }
          DESCRIPTION
           "A new hard disk has been found."
           --#SUMMARY  "[ctl: %d chn: %d tgt: %d :] A new hard disk has been found." 
           --#ARGUMENTS {0,1,2}
           --#SEVERITY INFORMATION
           --#TIMEINDEX 4
           --#STATE OPERATIONAL
           ::= 712

-- Dell event = 713 Vendor event = 14
pv660fEvent_PHYSDEV_GONE    TRAP-TYPE
    ENTERPRISE  aryMgrEvts
    VARIABLES   {
	
	controllerNameEv,
	channelNumberEv,
	targetIDEv
	
    }
          DESCRIPTION
           "A hard disk has been removed."
           --#SUMMARY  "[ctl: %d chn: %d tgt: %d :] A hard disk has been removed." 
           --#ARGUMENTS {0,1,2}
           --#SEVERITY INFORMATION
           --#TIMEINDEX 4
           --#STATE OPERATIONAL
           ::= 713

-- Dell event = 714 Vendor event = 15
pv660fEvent_PHYSDEV_UNCONFIGURED    TRAP-TYPE
    ENTERPRISE  aryMgrEvts
    VARIABLES   {
	
	controllerNameEv,
	channelNumberEv,
	targetIDEv
	
    }
          DESCRIPTION
           "A previously configured disk is now available."
           --#SUMMARY  "[ctl: %d chn: %d tgt: %d :] A previously configured disk is now available." 
           --#ARGUMENTS {0,1,2}
           --#SEVERITY INFORMATION
           --#TIMEINDEX 4
           --#STATE OPERATIONAL
           ::= 714

-- Dell event = 715 Vendor event = 16
pv660fEvent_PHYSDEV_EXPANDCAPACITY_START    TRAP-TYPE
    ENTERPRISE  aryMgrEvts
    VARIABLES   {
	
	controllerNameEv,
	channelNumberEv,
	targetIDEv
	
    }
          DESCRIPTION
           "Expand Capacity Started."
           --#SUMMARY  "[ctl: %d chn: %d tgt: %d :] Expand Capacity Started." 
           --#ARGUMENTS {0,1,2}
           --#SEVERITY INFORMATION
           --#TIMEINDEX 4
           --#STATE OPERATIONAL
           ::= 715

-- Dell event = 716 Vendor event = 17
pv660fEvent_PHYSDEV_EXPANDCAPACITY_DONE    TRAP-TYPE
    ENTERPRISE  aryMgrEvts
    VARIABLES   {
	
	controllerNameEv,
	channelNumberEv,
	targetIDEv
	
    }
          DESCRIPTION
           "Expand Capacity Completed."
           --#SUMMARY  "[ctl: %d chn: %d tgt: %d :] Expand Capacity Completed." 
           --#ARGUMENTS {0,1,2}
           --#SEVERITY INFORMATION
           --#TIMEINDEX 4
           --#STATE OPERATIONAL
           ::= 716

-- Dell event = 717 Vendor event = 18
pv660fEvent_PHYSDEV_EXPANDCAPACITY_ERROR    TRAP-TYPE
    ENTERPRISE  aryMgrEvts
    VARIABLES   {
	
	controllerNameEv,
	channelNumberEv,
	targetIDEv
	
    }
          DESCRIPTION
           "Expand Capacity Stopped with error."
           --#SUMMARY  "[ctl: %d chn: %d tgt: %d :] Expand Capacity Stopped with error." 
           --#ARGUMENTS {0,1,2}
           --#SEVERITY ERROR
           --#TIMEINDEX 4
           --#STATE NONOPERATIONAL
           ::= 717

-- Dell event = 718 Vendor event = 19
pv660fEvent_PHYSDEV_COMMAND_TIMEOUT    TRAP-TYPE
    ENTERPRISE  aryMgrEvts
    VARIABLES   {
	
	controllerNameEv,
	channelNumberEv,
	targetIDEv
	
    }
          DESCRIPTION
           "SCSI command timeout on hard device."
           --#SUMMARY  "[ctl: %d chn: %d tgt: %d :] SCSI command timeout on hard device." 
           --#ARGUMENTS {0,1,2}
           --#SEVERITY WARNING
           --#TIMEINDEX 4
           --#STATE OPERATIONAL
           ::= 718

-- Dell event = 719 Vendor event = 20
pv660fEvent_PHYSDEV_COMMAND_ABORT    TRAP-TYPE
    ENTERPRISE  aryMgrEvts
    VARIABLES   {
	
	controllerNameEv,
	channelNumberEv,
	targetIDEv
	
    }
          DESCRIPTION
           "SCSI command abort on hard disk."
           --#SUMMARY  "[ctl: %d chn: %d tgt: %d :] SCSI command abort on hard disk." 
           --#ARGUMENTS {0,1,2}
           --#SEVERITY CRITICAL
           --#TIMEINDEX 4
           --#STATE OPERATIONAL
           ::= 719

-- Dell event = 720 Vendor event = 21
pv660fEvent_PHYSDEV_COMMAND_RETRIED    TRAP-TYPE
    ENTERPRISE  aryMgrEvts
    VARIABLES   {
	
	controllerNameEv,
	channelNumberEv,
	targetIDEv
	
    }
          DESCRIPTION
           "SCSI command retried on hard disk."
           --#SUMMARY  "[ctl: %d chn: %d tgt: %d :] SCSI command retried on hard disk." 
           --#ARGUMENTS {0,1,2}
           --#SEVERITY WARNING
           --#TIMEINDEX 4
           --#STATE OPERATIONAL
           ::= 720

-- Dell event = 721 Vendor event = 22
pv660fEvent_PHYSDEV_PARITY_ERROR    TRAP-TYPE
    ENTERPRISE  aryMgrEvts
    VARIABLES   {
	
	controllerNameEv,
	channelNumberEv,
	targetIDEv
	
    }
          DESCRIPTION
           "Parity error found."
           --#SUMMARY  "[ctl: %d chn: %d tgt: %d :] Parity error found." 
           --#ARGUMENTS {0,1,2}
           --#SEVERITY WARNING
           --#TIMEINDEX 4
           --#STATE OPERATIONAL
           ::= 721

-- Dell event = 722 Vendor event = 23
pv660fEvent_PHYSDEV_SOFT_ERROR    TRAP-TYPE
    ENTERPRISE  aryMgrEvts
    VARIABLES   {
	
	controllerNameEv,
	channelNumberEv,
	targetIDEv
	
    }
          DESCRIPTION
           "Soft error found."
           --#SUMMARY  "[ctl: %d chn: %d tgt: %d :] Soft error found." 
           --#ARGUMENTS {0,1,2}
           --#SEVERITY WARNING
           --#TIMEINDEX 4
           --#STATE OPERATIONAL
           ::= 722

-- Dell event = 723 Vendor event = 24
pv660fEvent_PHYSDEV_MISC_ERROR    TRAP-TYPE
    ENTERPRISE  aryMgrEvts
    VARIABLES   {
	
	controllerNameEv,
	channelNumberEv,
	targetIDEv
	
    }
          DESCRIPTION
           "Misc error found."
           --#SUMMARY  "[ctl: %d chn: %d tgt: %d :] Misc error found." 
           --#ARGUMENTS {0,1,2}
           --#SEVERITY WARNING
           --#TIMEINDEX 4
           --#STATE OPERATIONAL
           ::= 723

-- Dell event = 724 Vendor event = 25
pv660fEvent_PHYSDEV_RESET    TRAP-TYPE
    ENTERPRISE  aryMgrEvts
    VARIABLES   {
	
	controllerNameEv,
	channelNumberEv,
	targetIDEv
	
    }
          DESCRIPTION
           "SCSI device reset."
           --#SUMMARY  "[ctl: %d chn: %d tgt: %d :] SCSI device reset." 
           --#ARGUMENTS {0,1,2}
           --#SEVERITY INFORMATION
           --#TIMEINDEX 4
           --#STATE OPERATIONAL
           ::= 724

-- Dell event = 725 Vendor event = 26
pv660fEvent_PHYSDEV_ACTIVESPARE    TRAP-TYPE
    ENTERPRISE  aryMgrEvts
    VARIABLES   {
	
	controllerNameEv,
	channelNumberEv,
	targetIDEv
	
    }
          DESCRIPTION
           "Active spare found.-"
           --#SUMMARY  "[ctl: %d chn: %d tgt: %d :] Active spare found.-" 
           --#ARGUMENTS {0,1,2}
           --#SEVERITY INFORMATION
           --#TIMEINDEX 4
           --#STATE OPERATIONAL
           ::= 725

-- Dell event = 726 Vendor event = 27
pv660fEvent_PHYSDEV_WARMSPARE    TRAP-TYPE
    ENTERPRISE  aryMgrEvts
    VARIABLES   {
	
	controllerNameEv,
	channelNumberEv,
	targetIDEv
	
    }
          DESCRIPTION
           "Warm spare found.-"
           --#SUMMARY  "[ctl: %d chn: %d tgt: %d :] Warm spare found.-" 
           --#ARGUMENTS {0,1,2}
           --#SEVERITY INFORMATION
           --#TIMEINDEX 4
           --#STATE OPERATIONAL
           ::= 726

-- Dell event = 727 Vendor event = 28
pv660fEvent_PHYSDEV_REQSENSE    TRAP-TYPE
    ENTERPRISE  aryMgrEvts
    VARIABLES   {
	
	controllerNameEv,
	channelNumberEv,
	targetIDEv
	
    }
          DESCRIPTION
           "Request Sense Data available."
           --#SUMMARY  "[ctl: %d chn: %d tgt: %d :] Request Sense Data available." 
           --#ARGUMENTS {0,1,2}
           --#SEVERITY ERROR
           --#TIMEINDEX 4
           --#STATE NONOPERATIONAL
           ::= 727

-- Dell event = 728 Vendor event = 29
pv660fEvent_PHYSDEV_INIT_STARTED    TRAP-TYPE
    ENTERPRISE  aryMgrEvts
    VARIABLES   {
	
	controllerNameEv,
	channelNumberEv,
	targetIDEv
	
    }
          DESCRIPTION
           "Initialization started."
           --#SUMMARY  "[ctl: %d chn: %d tgt: %d :] Initialization started." 
           --#ARGUMENTS {0,1,2}
           --#SEVERITY INFORMATION
           --#TIMEINDEX 4
           --#STATE OPERATIONAL
           ::= 728

-- Dell event = 729 Vendor event = 30
pv660fEvent_PHYSDEV_INIT_DONE    TRAP-TYPE
    ENTERPRISE  aryMgrEvts
    VARIABLES   {
	
	controllerNameEv,
	channelNumberEv,
	targetIDEv
	
    }
          DESCRIPTION
           "Initialization completed."
           --#SUMMARY  "[ctl: %d chn: %d tgt: %d :] Initialization completed." 
           --#ARGUMENTS {0,1,2}
           --#SEVERITY INFORMATION
           --#TIMEINDEX 4
           --#STATE OPERATIONAL
           ::= 729

-- Dell event = 730 Vendor event = 31
pv660fEvent_PHYSDEV_INIT_FAILED    TRAP-TYPE
    ENTERPRISE  aryMgrEvts
    VARIABLES   {
	
	controllerNameEv,
	channelNumberEv,
	targetIDEv
	
    }
          DESCRIPTION
           "Initialization failed."
           --#SUMMARY  "[ctl: %d chn: %d tgt: %d :] Initialization failed." 
           --#ARGUMENTS {0,1,2}
           --#SEVERITY WARNING
           --#TIMEINDEX 4
           --#STATE OPERATIONAL
           ::= 730

-- Dell event = 731 Vendor event = 32
pv660fEvent_PHYSDEV_INIT_CANCELED    TRAP-TYPE
    ENTERPRISE  aryMgrEvts
    VARIABLES   {
	
	controllerNameEv,
	channelNumberEv,
	targetIDEv
	
    }
          DESCRIPTION
           "Initialization canceled."
           --#SUMMARY  "[ctl: %d chn: %d tgt: %d :] Initialization canceled." 
           --#ARGUMENTS {0,1,2}
           --#SEVERITY SERIOUS
           --#TIMEINDEX 4
           --#STATE OPERATIONAL
           ::= 731

-- Dell event = 732 Vendor event = 33
pv660fEvent_PHYSDEV_WRITEREC_DEAD    TRAP-TYPE
    ENTERPRISE  aryMgrEvts
    VARIABLES   {
	
	controllerNameEv,
	channelNumberEv,
	targetIDEv
	
    }
          DESCRIPTION
           "A hard disk failed because write recovery failed."
           --#SUMMARY  "[ctl: %d chn: %d tgt: %d :] A hard disk failed because write recovery failed." 
           --#ARGUMENTS {0,1,2}
           --#SEVERITY SERIOUS
           --#TIMEINDEX 4
           --#STATE OPERATIONAL
           ::= 732

-- Dell event = 733 Vendor event = 34
pv660fEvent_PHYSDEV_RESET_DEAD    TRAP-TYPE
    ENTERPRISE  aryMgrEvts
    VARIABLES   {
	
	controllerNameEv,
	channelNumberEv,
	targetIDEv
	
    }
          DESCRIPTION
           "A hard disk failed because SCSI bus reset failed."
           --#SUMMARY  "[ctl: %d chn: %d tgt: %d :] A hard disk failed because SCSI bus reset failed." 
           --#ARGUMENTS {0,1,2}
           --#SEVERITY SERIOUS
           --#TIMEINDEX 4
           --#STATE OPERATIONAL
           ::= 733

-- Dell event = 734 Vendor event = 35
pv660fEvent_PHYSDEV_DBLCC_DEAD    TRAP-TYPE
    ENTERPRISE  aryMgrEvts
    VARIABLES   {
	
	controllerNameEv,
	channelNumberEv,
	targetIDEv
	
    }
          DESCRIPTION
           "A hard disk failed because double check condition occured."
           --#SUMMARY  "[ctl: %d chn: %d tgt: %d :] A hard disk failed because double check condition occured." 
           --#ARGUMENTS {0,1,2}
           --#SEVERITY SERIOUS
           --#TIMEINDEX 4
           --#STATE OPERATIONAL
           ::= 734

-- Dell event = 735 Vendor event = 36
pv660fEvent_PHYSDEV_REMOVED_DEAD    TRAP-TYPE
    ENTERPRISE  aryMgrEvts
    VARIABLES   {
	
	controllerNameEv,
	channelNumberEv,
	targetIDEv
	
    }
          DESCRIPTION
           "A hard disk failed because device is missing."
           --#SUMMARY  "[ctl: %d chn: %d tgt: %d :] A hard disk failed because device is missing." 
           --#ARGUMENTS {0,1,2}
           --#SEVERITY SERIOUS
           --#TIMEINDEX 4
           --#STATE OPERATIONAL
           ::= 735

-- Dell event = 736 Vendor event = 37
pv660fEvent_PHYSDEV_GROSSERR_DEAD    TRAP-TYPE
    ENTERPRISE  aryMgrEvts
    VARIABLES   {
	
	controllerNameEv,
	channelNumberEv,
	targetIDEv
	
    }
          DESCRIPTION
           "A hard disk failed because of gross error on SCSI processor."
           --#SUMMARY  "[ctl: %d chn: %d tgt: %d :] A hard disk failed because of gross error on SCSI processor." 
           --#ARGUMENTS {0,1,2}
           --#SEVERITY SERIOUS
           --#TIMEINDEX 4
           --#STATE OPERATIONAL
           ::= 736

-- Dell event = 737 Vendor event = 38
pv660fEvent_PHYSDEV_BADTAG_DEAD    TRAP-TYPE
    ENTERPRISE  aryMgrEvts
    VARIABLES   {
	
	controllerNameEv,
	channelNumberEv,
	targetIDEv
	
    }
          DESCRIPTION
           "A hard disk failed because of bad tag from the device."
           --#SUMMARY  "[ctl: %d chn: %d tgt: %d :] A hard disk failed because of bad tag from the device." 
           --#ARGUMENTS {0,1,2}
           --#SEVERITY SERIOUS
           --#TIMEINDEX 4
           --#STATE OPERATIONAL
           ::= 737

-- Dell event = 738 Vendor event = 39
pv660fEvent_PHYSDEV_SCSITMO_DEAD    TRAP-TYPE
    ENTERPRISE  aryMgrEvts
    VARIABLES   {
	
	controllerNameEv,
	channelNumberEv,
	targetIDEv
	
    }
          DESCRIPTION
           "A hard disk failed because command to the device timed out."
           --#SUMMARY  "[ctl: %d chn: %d tgt: %d :] A hard disk failed because command to the device timed out." 
           --#ARGUMENTS {0,1,2}
           --#SEVERITY SERIOUS
           --#TIMEINDEX 4
           --#STATE OPERATIONAL
           ::= 738

-- Dell event = 739 Vendor event = 40
pv660fEvent_PHYSDEV_SYSRESET_DEAD    TRAP-TYPE
    ENTERPRISE  aryMgrEvts
    VARIABLES   {
	
	controllerNameEv,
	channelNumberEv,
	targetIDEv
	
    }
          DESCRIPTION
           "A hard disk failed because of the system reset."
           --#SUMMARY  "[ctl: %d chn: %d tgt: %d :] A hard disk failed because of the system reset." 
           --#ARGUMENTS {0,1,2}
           --#SEVERITY SERIOUS
           --#TIMEINDEX 4
           --#STATE OPERATIONAL
           ::= 739

-- Dell event = 740 Vendor event = 41
pv660fEvent_PHYSDEV_BSYPAR_DEAD    TRAP-TYPE
    ENTERPRISE  aryMgrEvts
    VARIABLES   {
	
	controllerNameEv,
	channelNumberEv,
	targetIDEv
	
    }
          DESCRIPTION
           "A hard disk failed because of busy status or parity error."
           --#SUMMARY  "[ctl: %d chn: %d tgt: %d :] A hard disk failed because of busy status or parity error." 
           --#ARGUMENTS {0,1,2}
           --#SEVERITY SERIOUS
           --#TIMEINDEX 4
           --#STATE OPERATIONAL
           ::= 740

-- Dell event = 741 Vendor event = 42
pv660fEvent_PHYSDEV_BYCMD_DEAD    TRAP-TYPE
    ENTERPRISE  aryMgrEvts
    VARIABLES   {
	
	controllerNameEv,
	channelNumberEv,
	targetIDEv
	
    }
          DESCRIPTION
           "A hard disk set to failed state by host."
           --#SUMMARY  "[ctl: %d chn: %d tgt: %d :] A hard disk set to failed state by host." 
           --#ARGUMENTS {0,1,2}
           --#SEVERITY SERIOUS
           --#TIMEINDEX 4
           --#STATE OPERATIONAL
           ::= 741

-- Dell event = 742 Vendor event = 43
pv660fEvent_PHYSDEV_SELTMO_DEAD    TRAP-TYPE
    ENTERPRISE  aryMgrEvts
    VARIABLES   {
	
	controllerNameEv,
	channelNumberEv,
	targetIDEv
	
    }
          DESCRIPTION
           "A hard disk failed because access to the device met with a selection time out."
           --#SUMMARY  "[ctl: %d chn: %d tgt: %d :] A hard disk failed because access to the device met with a selection time out." 
           --#ARGUMENTS {0,1,2}
           --#SEVERITY SERIOUS
           --#TIMEINDEX 4
           --#STATE OPERATIONAL
           ::= 742

-- Dell event = 743 Vendor event = 44
pv660fEvent_PHYSDEV_SEQERR_DEAD    TRAP-TYPE
    ENTERPRISE  aryMgrEvts
    VARIABLES   {
	
	controllerNameEv,
	channelNumberEv,
	targetIDEv
	
    }
          DESCRIPTION
           "A hard disk failed because of a sequence error in the SCSI bus phase handling."
           --#SUMMARY  "[ctl: %d chn: %d tgt: %d :] A hard disk failed because of a sequence error in the SCSI bus phase handling." 
           --#ARGUMENTS {0,1,2}
           --#SEVERITY SERIOUS
           --#TIMEINDEX 4
           --#STATE OPERATIONAL
           ::= 743

-- Dell event = 744 Vendor event = 45
pv660fEvent_PHYSDEV_UNKNOWNSTS_DEAD    TRAP-TYPE
    ENTERPRISE  aryMgrEvts
    VARIABLES   {
	
	controllerNameEv,
	channelNumberEv,
	targetIDEv
	
    }
          DESCRIPTION
           "A hard disk failed because device returned an unknown status."
           --#SUMMARY  "[ctl: %d chn: %d tgt: %d :] A hard disk failed because device returned an unknown status." 
           --#ARGUMENTS {0,1,2}
           --#SEVERITY SERIOUS
           --#TIMEINDEX 4
           --#STATE OPERATIONAL
           ::= 744

-- Dell event = 745 Vendor event = 46
pv660fEvent_PHYSDEV_NOTRDY_DEAD    TRAP-TYPE
    ENTERPRISE  aryMgrEvts
    VARIABLES   {
	
	controllerNameEv,
	channelNumberEv,
	targetIDEv
	
    }
          DESCRIPTION
           "A hard disk failed because device is not ready."
           --#SUMMARY  "[ctl: %d chn: %d tgt: %d :] A hard disk failed because device is not ready." 
           --#ARGUMENTS {0,1,2}
           --#SEVERITY SERIOUS
           --#TIMEINDEX 4
           --#STATE OPERATIONAL
           ::= 745

-- Dell event = 746 Vendor event = 47
pv660fEvent_PHYSDEV_MISSING_DEAD    TRAP-TYPE
    ENTERPRISE  aryMgrEvts
    VARIABLES   {
	
	controllerNameEv,
	channelNumberEv,
	targetIDEv
	
    }
          DESCRIPTION
           "A hard disk failed because device was not found on start up."
           --#SUMMARY  "[ctl: %d chn: %d tgt: %d :] A hard disk failed because device was not found on start up." 
           --#ARGUMENTS {0,1,2}
           --#SEVERITY SERIOUS
           --#TIMEINDEX 4
           --#STATE OPERATIONAL
           ::= 746

-- Dell event = 747 Vendor event = 48
pv660fEvent_PHYSDEV_CODWRFAIL_DEAD    TRAP-TYPE
    ENTERPRISE  aryMgrEvts
    VARIABLES   {
	
	controllerNameEv,
	channelNumberEv,
	targetIDEv
	
    }
          DESCRIPTION
           "A hard disk failed because write operation of the 'Configuration On Disk' failed."
           --#SUMMARY  "[ctl: %d chn: %d tgt: %d :] A hard disk failed because write operation of the 'Configuration On Disk' failed." 
           --#ARGUMENTS {0,1,2}
           --#SEVERITY SERIOUS
           --#TIMEINDEX 4
           --#STATE OPERATIONAL
           ::= 747

-- Dell event = 748 Vendor event = 49
pv660fEvent_PHYSDEV_BDTWRFAIL_DEAD    TRAP-TYPE
    ENTERPRISE  aryMgrEvts
    VARIABLES   {
	
	controllerNameEv,
	channelNumberEv,
	targetIDEv
	
    }
          DESCRIPTION
           "A hard disk failed because write operation of 'Bad Data Table' failed."
           --#SUMMARY  "[ctl: %d chn: %d tgt: %d :] A hard disk failed because write operation of 'Bad Data Table' failed." 
           --#ARGUMENTS {0,1,2}
           --#SEVERITY SERIOUS
           --#TIMEINDEX 4
           --#STATE OPERATIONAL
           ::= 748

-- Dell event = 749 Vendor event = 50
pv660fEvent_PHYSDEV_OFFLINE    TRAP-TYPE
    ENTERPRISE  aryMgrEvts
    VARIABLES   {
	
	controllerNameEv,
	channelNumberEv,
	targetIDEv
	
    }
          DESCRIPTION
           "Physical device status changed to offline."
           --#SUMMARY  "[ctl: %d chn: %d tgt: %d :] Physical device status changed to offline." 
           --#ARGUMENTS {0,1,2}
           --#SEVERITY WARNING
           --#TIMEINDEX 4
           --#STATE OPERATIONAL
           ::= 749

-- Dell event = 750 Vendor event = 51
pv660fEvent_PHYSDEV_STANDBY    TRAP-TYPE
    ENTERPRISE  aryMgrEvts
    VARIABLES   {
	
	controllerNameEv,
	channelNumberEv,
	targetIDEv
	
    }
          DESCRIPTION
           "Physical device status changed to Hot Spare."
           --#SUMMARY  "[ctl: %d chn: %d tgt: %d :] Physical device status changed to Hot Spare." 
           --#ARGUMENTS {0,1,2}
           --#SEVERITY WARNING
           --#TIMEINDEX 4
           --#STATE OPERATIONAL
           ::= 750

-- Dell event = 751 Vendor event = 52
pv660fEvent_PHYSDEV_REBUILD    TRAP-TYPE
    ENTERPRISE  aryMgrEvts
    VARIABLES   {
	
	controllerNameEv,
	channelNumberEv,
	targetIDEv
	
    }
          DESCRIPTION
           "Physical device status changed to rebuild."
           --#SUMMARY  "[ctl: %d chn: %d tgt: %d :] Physical device status changed to rebuild." 
           --#ARGUMENTS {0,1,2}
           --#SEVERITY WARNING
           --#TIMEINDEX 4
           --#STATE OPERATIONAL
           ::= 751

-- Dell event = 752 Vendor event = 53
pv660fEvent_PHYSDEV_ID_MISMATCH    TRAP-TYPE
    ENTERPRISE  aryMgrEvts
    VARIABLES   {
	
	controllerNameEv,
	channelNumberEv,
	targetIDEv
	
    }
          DESCRIPTION
           "Physical device ID did not match."
           --#SUMMARY  "[ctl: %d chn: %d tgt: %d :] Physical device ID did not match." 
           --#ARGUMENTS {0,1,2}
           --#SEVERITY WARNING
           --#TIMEINDEX 4
           --#STATE OPERATIONAL
           ::= 752

-- Dell event = 753 Vendor event = 54
pv660fEvent_PHYSDEV_FAILED_START    TRAP-TYPE
    ENTERPRISE  aryMgrEvts
    VARIABLES   {
	
	controllerNameEv,
	channelNumberEv,
	targetIDEv
	
    }
          DESCRIPTION
           "Physical device failed to start."
           --#SUMMARY  "[ctl: %d chn: %d tgt: %d :] Physical device failed to start." 
           --#ARGUMENTS {0,1,2}
           --#SEVERITY WARNING
           --#TIMEINDEX 4
           --#STATE OPERATIONAL
           ::= 753

-- Dell event = 754 Vendor event = 55
pv660fEvent_PHYSDEV_OFFSET_SET    TRAP-TYPE
    ENTERPRISE  aryMgrEvts
    VARIABLES   {
	
	controllerNameEv,
	channelNumberEv,
	targetIDEv
	
    }
          DESCRIPTION
           "Physical device negotiated different offset than config."
           --#SUMMARY  "[ctl: %d chn: %d tgt: %d :] Physical device negotiated different offset than config." 
           --#ARGUMENTS {0,1,2}
           --#SEVERITY WARNING
           --#TIMEINDEX 4
           --#STATE OPERATIONAL
           ::= 754

-- Dell event = 755 Vendor event = 56
pv660fEvent_PHYSDEV_SET_BUS_WIDTH    TRAP-TYPE
    ENTERPRISE  aryMgrEvts
    VARIABLES   {
	
	controllerNameEv,
	channelNumberEv,
	targetIDEv
	
    }
          DESCRIPTION
           "Physical device negotiated different bus width than config."
           --#SUMMARY  "[ctl: %d chn: %d tgt: %d :] Physical device negotiated different bus width than config." 
           --#ARGUMENTS {0,1,2}
           --#SEVERITY WARNING
           --#TIMEINDEX 4
           --#STATE OPERATIONAL
           ::= 755

-- Dell event = 756 Vendor event = 57
pv660fEvent_PHYSDEV_MISSING_ONSTARTUP    TRAP-TYPE
    ENTERPRISE  aryMgrEvts
    VARIABLES   {
	
	controllerNameEv,
	channelNumberEv,
	targetIDEv
	
    }
          DESCRIPTION
           "Physical drive missing on startup."
           --#SUMMARY  "[ctl: %d chn: %d tgt: %d :] Physical drive missing on startup." 
           --#ARGUMENTS {0,1,2}
           --#SEVERITY SERIOUS
           --#TIMEINDEX 4
           --#STATE OPERATIONAL
           ::= 756

-- Dell event = 757 Vendor event = 58
pv660fEvent_PHYSDEV_REBUILD_START_FAILED    TRAP-TYPE
    ENTERPRISE  aryMgrEvts
    VARIABLES   {
	
	controllerNameEv,
	channelNumberEv,
	targetIDEv
	
    }
          DESCRIPTION
           "Rebuild startup failed due to lower disk capacity."
           --#SUMMARY  "[ctl: %d chn: %d tgt: %d :] Rebuild startup failed due to lower disk capacity." 
           --#ARGUMENTS {0,1,2}
           --#SEVERITY WARNING
           --#TIMEINDEX 4
           --#STATE OPERATIONAL
           ::= 757

-- Dell event = 758 Vendor event = 59
pv660fEvent_PHYSDEV_MOVING_TO_OTHER_CHN    TRAP-TYPE
    ENTERPRISE  aryMgrEvts
    VARIABLES   {
	
	controllerNameEv,
	channelNumberEv,
	targetIDEv
	
    }
          DESCRIPTION
           "Physical drive is switching from a channel to the other channel."
           --#SUMMARY  "[ctl: %d chn: %d tgt: %d :] Physical drive is switching from a channel to the other channel." 
           --#ARGUMENTS {0,1,2}
           --#SEVERITY WARNING
           --#TIMEINDEX 4
           --#STATE OPERATIONAL
           ::= 758

-- Dell event = 759 Vendor event = 60
pv660fEvent_PHYSDEV_OFFLINE_DEVICE_MADE_ONLINE    TRAP-TYPE
    ENTERPRISE  aryMgrEvts
    VARIABLES   {
	
	controllerNameEv,
	channelNumberEv,
	targetIDEv
	
    }
          DESCRIPTION
           "Temporary-Dead physical drive is automatically made online."
           --#SUMMARY  "[ctl: %d chn: %d tgt: %d :] Temporary-Dead physical drive is automatically made online." 
           --#ARGUMENTS {0,1,2}
           --#SEVERITY ERROR
           --#TIMEINDEX 4
           --#STATE NONOPERATIONAL
           ::= 759

-- Dell event = 760 Vendor event = 61
pv660fEvent_PHYSDEV_STANDBY_REBUILD_START    TRAP-TYPE
    ENTERPRISE  aryMgrEvts
    VARIABLES   {
	
	controllerNameEv,
	channelNumberEv,
	targetIDEv
	
    }
          DESCRIPTION
           "A standby rebuild has started."
           --#SUMMARY  "[ctl: %d chn: %d tgt: %d :] A standby rebuild has started." 
           --#ARGUMENTS {0,1,2}
           --#SEVERITY INFORMATION
           --#TIMEINDEX 4
           --#STATE OPERATIONAL
           ::= 760

-- Dell event = 761 Vendor event = 96
pv660fEvent_FIBREDEV_LOOPID_SOFTADDR_OCCURRED    TRAP-TYPE
    ENTERPRISE  aryMgrEvts
    VARIABLES   {
	
	controllerNameEv,
	channelNumberEv
	
    }
          DESCRIPTION
           "Device Loop Id Conflict (Soft Addressing) Detected."
           --#SUMMARY  "[ctl: %d chn: %d :] Device Loop Id Conflict (Soft Addressing) Detected." 
           --#ARGUMENTS {0,1}
           --#SEVERITY SERIOUS
           --#TIMEINDEX 3
           --#STATE OPERATIONAL
           ::= 761

-- Dell event = 762 Vendor event = 128
pv660fEvent_SYSDEV_CHECK_START    TRAP-TYPE
    ENTERPRISE  aryMgrEvts
    VARIABLES   {
	
	controllerNameEv,
	virtualDiskNameEv
	
    }
          DESCRIPTION
           "Consistency check is started."
           --#SUMMARY  "[ctl: %d logdrv: %d :] Consistency check is started." 
           --#ARGUMENTS {0,1}
           --#SEVERITY INFORMATION
           --#TIMEINDEX 3
           --#STATE OPERATIONAL
           ::= 762

-- Dell event = 763 Vendor event = 129
pv660fEvent_SYSDEV_CHECK_DONE    TRAP-TYPE
    ENTERPRISE  aryMgrEvts
    VARIABLES   {
	
	controllerNameEv,
	virtualDiskNameEv
	
    }
          DESCRIPTION
           "Consistency check is finished."
           --#SUMMARY  "[ctl: %d logdrv: %d :] Consistency check is finished." 
           --#ARGUMENTS {0,1}
           --#SEVERITY INFORMATION
           --#TIMEINDEX 3
           --#STATE OPERATIONAL
           ::= 763

-- Dell event = 764 Vendor event = 130
pv660fEvent_SYSDEV_CHECK_CANCELED    TRAP-TYPE
    ENTERPRISE  aryMgrEvts
    VARIABLES   {
	
	controllerNameEv,
	virtualDiskNameEv
	
    }
          DESCRIPTION
           "Consistency check is cancelled."
           --#SUMMARY  "[ctl: %d logdrv: %d :] Consistency check is cancelled." 
           --#ARGUMENTS {0,1}
           --#SEVERITY WARNING
           --#TIMEINDEX 3
           --#STATE OPERATIONAL
           ::= 764

-- Dell event = 765 Vendor event = 131
pv660fEvent_SYSDEV_CHECK_ERROR    TRAP-TYPE
    ENTERPRISE  aryMgrEvts
    VARIABLES   {
	
	controllerNameEv,
	virtualDiskNameEv
	
    }
          DESCRIPTION
           "Consistency check on logical drive error."
           --#SUMMARY  "[ctl: %d logdrv: %d :] Consistency check on logical drive error." 
           --#ARGUMENTS {0,1}
           --#SEVERITY ERROR
           --#TIMEINDEX 3
           --#STATE NONOPERATIONAL
           ::= 765

-- Dell event = 766 Vendor event = 132
pv660fEvent_SYSDEV_CHECK_SYSDEV_FAILED    TRAP-TYPE
    ENTERPRISE  aryMgrEvts
    VARIABLES   {
	
	controllerNameEv,
	virtualDiskNameEv
	
    }
          DESCRIPTION
           "Consistency check on logical drive failed."
           --#SUMMARY  "[ctl: %d logdrv: %d :] Consistency check on logical drive failed." 
           --#ARGUMENTS {0,1}
           --#SEVERITY ERROR
           --#TIMEINDEX 3
           --#STATE NONOPERATIONAL
           ::= 766

-- Dell event = 767 Vendor event = 133
pv660fEvent_SYSDEV_CHECK_PHYSDEV_FAILED    TRAP-TYPE
    ENTERPRISE  aryMgrEvts
    VARIABLES   {
	
	controllerNameEv,
	virtualDiskNameEv
	
    }
          DESCRIPTION
           "Consistency check failed due to physical device failure."
           --#SUMMARY  "[ctl: %d logdrv: %d :] Consistency check failed due to physical device failure." 
           --#ARGUMENTS {0,1}
           --#SEVERITY SERIOUS
           --#TIMEINDEX 3
           --#STATE OPERATIONAL
           ::= 767

-- Dell event = 768 Vendor event = 134
pv660fEvent_SYSDEV_OFFLINE    TRAP-TYPE
    ENTERPRISE  aryMgrEvts
    VARIABLES   {
	
	controllerNameEv,
	virtualDiskNameEv
	
    }
          DESCRIPTION
           "Logical drive has been made offline."
           --#SUMMARY  "[ctl: %d logdrv: %d :] Logical drive has been made offline." 
           --#ARGUMENTS {0,1}
           --#SEVERITY SERIOUS
           --#TIMEINDEX 3
           --#STATE OPERATIONAL
           ::= 768

-- Dell event = 769 Vendor event = 135
pv660fEvent_SYSDEV_CRITICAL    TRAP-TYPE
    ENTERPRISE  aryMgrEvts
    VARIABLES   {
	
	controllerNameEv,
	virtualDiskNameEv
	
    }
          DESCRIPTION
           "Logical drive is critical."
           --#SUMMARY  "[ctl: %d logdrv: %d :] Logical drive is critical." 
           --#ARGUMENTS {0,1}
           --#SEVERITY ERROR
           --#TIMEINDEX 3
           --#STATE NONOPERATIONAL
           ::= 769

-- Dell event = 770 Vendor event = 136
pv660fEvent_SYSDEV_ONLINE    TRAP-TYPE
    ENTERPRISE  aryMgrEvts
    VARIABLES   {
	
	controllerNameEv,
	virtualDiskNameEv
	
    }
          DESCRIPTION
           "Logical drive has been placed online."
           --#SUMMARY  "[ctl: %d logdrv: %d :] Logical drive has been placed online." 
           --#ARGUMENTS {0,1}
           --#SEVERITY INFORMATION
           --#TIMEINDEX 3
           --#STATE OPERATIONAL
           ::= 770

-- Dell event = 771 Vendor event = 137
pv660fEvent_SYSDEV_AUTO_REBUILD_START    TRAP-TYPE
    ENTERPRISE  aryMgrEvts
    VARIABLES   {
	
	controllerNameEv,
	virtualDiskNameEv
	
    }
          DESCRIPTION
           "An automatic rebuild has started on logical drive."
           --#SUMMARY  "[ctl: %d logdrv: %d :] An automatic rebuild has started on logical drive." 
           --#ARGUMENTS {0,1}
           --#SEVERITY INFORMATION
           --#TIMEINDEX 3
           --#STATE OPERATIONAL
           ::= 771

-- Dell event = 772 Vendor event = 138
pv660fEvent_SYSDEV_MANUAL_REBUILD_START    TRAP-TYPE
    ENTERPRISE  aryMgrEvts
    VARIABLES   {
	
	controllerNameEv,
	virtualDiskNameEv
	
    }
          DESCRIPTION
           "A manual rebuild has started on logical drive."
           --#SUMMARY  "[ctl: %d logdrv: %d :] A manual rebuild has started on logical drive." 
           --#ARGUMENTS {0,1}
           --#SEVERITY INFORMATION
           --#TIMEINDEX 3
           --#STATE OPERATIONAL
           ::= 772

-- Dell event = 773 Vendor event = 139
pv660fEvent_SYSDEV_REBUILD_DONE    TRAP-TYPE
    ENTERPRISE  aryMgrEvts
    VARIABLES   {
	
	controllerNameEv,
	virtualDiskNameEv
	
    }
          DESCRIPTION
           "Rebuild on logical drive is over."
           --#SUMMARY  "[ctl: %d logdrv: %d :] Rebuild on logical drive is over." 
           --#ARGUMENTS {0,1}
           --#SEVERITY INFORMATION
           --#TIMEINDEX 3
           --#STATE OPERATIONAL
           ::= 773

-- Dell event = 774 Vendor event = 140
pv660fEvent_SYSDEV_REBUILD_CANCELED    TRAP-TYPE
    ENTERPRISE  aryMgrEvts
    VARIABLES   {
	
	controllerNameEv,
	virtualDiskNameEv
	
    }
          DESCRIPTION
           "Rebuild on logical drive is cancelled."
           --#SUMMARY  "[ctl: %d logdrv: %d :] Rebuild on logical drive is cancelled." 
           --#ARGUMENTS {0,1}
           --#SEVERITY WARNING
           --#TIMEINDEX 3
           --#STATE OPERATIONAL
           ::= 774

-- Dell event = 775 Vendor event = 141
pv660fEvent_SYSDEV_REBUILD_ERROR    TRAP-TYPE
    ENTERPRISE  aryMgrEvts
    VARIABLES   {
	
	controllerNameEv,
	virtualDiskNameEv
	
    }
          DESCRIPTION
           "Rebuild stopped with error."
           --#SUMMARY  "[ctl: %d logdrv: %d :] Rebuild stopped with error." 
           --#ARGUMENTS {0,1}
           --#SEVERITY ERROR
           --#TIMEINDEX 3
           --#STATE NONOPERATIONAL
           ::= 775

-- Dell event = 776 Vendor event = 142
pv660fEvent_SYSDEV_REBUILD_NEWDEV_FAILED    TRAP-TYPE
    ENTERPRISE  aryMgrEvts
    VARIABLES   {
	
	controllerNameEv,
	virtualDiskNameEv
	
    }
          DESCRIPTION
           "Rebuild stopped with error. New device failed."
           --#SUMMARY  "[ctl: %d logdrv: %d :] Rebuild stopped with error. New device failed." 
           --#ARGUMENTS {0,1}
           --#SEVERITY ERROR
           --#TIMEINDEX 3
           --#STATE NONOPERATIONAL
           ::= 776

-- Dell event = 777 Vendor event = 143
pv660fEvent_SYSDEV_REBUILD_SYSDEV_FAILED    TRAP-TYPE
    ENTERPRISE  aryMgrEvts
    VARIABLES   {
	
	controllerNameEv,
	virtualDiskNameEv
	
    }
          DESCRIPTION
           "Rebuild stopped because logical drive failed."
           --#SUMMARY  "[ctl: %d logdrv: %d :] Rebuild stopped because logical drive failed." 
           --#ARGUMENTS {0,1}
           --#SEVERITY ERROR
           --#TIMEINDEX 3
           --#STATE NONOPERATIONAL
           ::= 777

-- Dell event = 778 Vendor event = 144
pv660fEvent_SYSDEV_INIT_STARTED    TRAP-TYPE
    ENTERPRISE  aryMgrEvts
    VARIABLES   {
	
	controllerNameEv,
	virtualDiskNameEv
	
    }
          DESCRIPTION
           "Logical drive initialization started."
           --#SUMMARY  "[ctl: %d logdrv: %d :] Logical drive initialization started." 
           --#ARGUMENTS {0,1}
           --#SEVERITY INFORMATION
           --#TIMEINDEX 3
           --#STATE OPERATIONAL
           ::= 778

-- Dell event = 779 Vendor event = 145
pv660fEvent_SYSDEV_INIT_DONE    TRAP-TYPE
    ENTERPRISE  aryMgrEvts
    VARIABLES   {
	
	controllerNameEv,
	virtualDiskNameEv
	
    }
          DESCRIPTION
           "Logical drive initialization done."
           --#SUMMARY  "[ctl: %d logdrv: %d :] Logical drive initialization done." 
           --#ARGUMENTS {0,1}
           --#SEVERITY INFORMATION
           --#TIMEINDEX 3
           --#STATE OPERATIONAL
           ::= 779

-- Dell event = 780 Vendor event = 146
pv660fEvent_SYSDEV_INIT_CANCELED    TRAP-TYPE
    ENTERPRISE  aryMgrEvts
    VARIABLES   {
	
	controllerNameEv,
	virtualDiskNameEv
	
    }
          DESCRIPTION
           "Logical drive initialization cancelled."
           --#SUMMARY  "[ctl: %d logdrv: %d :] Logical drive initialization cancelled." 
           --#ARGUMENTS {0,1}
           --#SEVERITY WARNING
           --#TIMEINDEX 3
           --#STATE OPERATIONAL
           ::= 780

-- Dell event = 781 Vendor event = 147
pv660fEvent_SYSDEV_INIT_FAILED    TRAP-TYPE
    ENTERPRISE  aryMgrEvts
    VARIABLES   {
	
	controllerNameEv,
	virtualDiskNameEv
	
    }
          DESCRIPTION
           "Logical drive initialization failed."
           --#SUMMARY  "[ctl: %d logdrv: %d :] Logical drive initialization failed." 
           --#ARGUMENTS {0,1}
           --#SEVERITY ERROR
           --#TIMEINDEX 3
           --#STATE NONOPERATIONAL
           ::= 781

-- Dell event = 782 Vendor event = 148
pv660fEvent_SYSDEV_FOUND    TRAP-TYPE
    ENTERPRISE  aryMgrEvts
    VARIABLES   {
	
	controllerNameEv,
	virtualDiskNameEv
	
    }
          DESCRIPTION
           "A logical drive has been found."
           --#SUMMARY  "[ctl: %d logdrv: %d :] A logical drive has been found." 
           --#ARGUMENTS {0,1}
           --#SEVERITY INFORMATION
           --#TIMEINDEX 3
           --#STATE OPERATIONAL
           ::= 782

-- Dell event = 783 Vendor event = 149
pv660fEvent_SYSDEV_GONE    TRAP-TYPE
    ENTERPRISE  aryMgrEvts
    VARIABLES   {
	
	controllerNameEv,
	virtualDiskNameEv
	
    }
          DESCRIPTION
           "A logical drive has been deleted."
           --#SUMMARY  "[ctl: %d logdrv: %d :] A logical drive has been deleted." 
           --#ARGUMENTS {0,1}
           --#SEVERITY INFORMATION
           --#TIMEINDEX 3
           --#STATE OPERATIONAL
           ::= 783

-- Dell event = 784 Vendor event = 150
pv660fEvent_SYSDEV_EXPANDCAPACITY_START    TRAP-TYPE
    ENTERPRISE  aryMgrEvts
    VARIABLES   {
	
	controllerNameEv,
	virtualDiskNameEv
	
    }
          DESCRIPTION
           "Expand Capacity Started."
           --#SUMMARY  "[ctl: %d logdrv: %d :] Expand Capacity Started." 
           --#ARGUMENTS {0,1}
           --#SEVERITY INFORMATION
           --#TIMEINDEX 3
           --#STATE OPERATIONAL
           ::= 784

-- Dell event = 785 Vendor event = 151
pv660fEvent_SYSDEV_EXPANDCAPACITY_DONE    TRAP-TYPE
    ENTERPRISE  aryMgrEvts
    VARIABLES   {
	
	controllerNameEv,
	virtualDiskNameEv
	
    }
          DESCRIPTION
           "Expand Capacity Completed."
           --#SUMMARY  "[ctl: %d logdrv: %d :] Expand Capacity Completed." 
           --#ARGUMENTS {0,1}
           --#SEVERITY INFORMATION
           --#TIMEINDEX 3
           --#STATE OPERATIONAL
           ::= 785

-- Dell event = 786 Vendor event = 152
pv660fEvent_SYSDEV_EXPANDCAPACITY_ERROR    TRAP-TYPE
    ENTERPRISE  aryMgrEvts
    VARIABLES   {
	
	controllerNameEv,
	virtualDiskNameEv
	
    }
          DESCRIPTION
           "Expand Capacity stopped with error."
           --#SUMMARY  "[ctl: %d logdrv: %d :] Expand Capacity stopped with error." 
           --#ARGUMENTS {0,1}
           --#SEVERITY ERROR
           --#TIMEINDEX 3
           --#STATE NONOPERATIONAL
           ::= 786

-- Dell event = 787 Vendor event = 153
pv660fEvent_SYSDEV_BADBLOCK    TRAP-TYPE
    ENTERPRISE  aryMgrEvts
    VARIABLES   {
	
	controllerNameEv,
	virtualDiskNameEv
	
    }
          DESCRIPTION
           "Bad Blocks found."
           --#SUMMARY  "[ctl: %d logdrv: %d :] Bad Blocks found." 
           --#ARGUMENTS {0,1}
           --#SEVERITY CRITICAL
           --#TIMEINDEX 3
           --#STATE OPERATIONAL
           ::= 787

-- Dell event = 788 Vendor event = 154
pv660fEvent_SYSDEV_SIZECHANGED    TRAP-TYPE
    ENTERPRISE  aryMgrEvts
    VARIABLES   {
	
	controllerNameEv,
	virtualDiskNameEv
	
    }
          DESCRIPTION
           "System drive size changed."
           --#SUMMARY  "[ctl: %d logdrv: %d :] System drive size changed." 
           --#ARGUMENTS {0,1}
           --#SEVERITY INFORMATION
           --#TIMEINDEX 3
           --#STATE OPERATIONAL
           ::= 788

-- Dell event = 789 Vendor event = 155
pv660fEvent_SYSDEV_TYPECHANGED    TRAP-TYPE
    ENTERPRISE  aryMgrEvts
    VARIABLES   {
	
	controllerNameEv,
	virtualDiskNameEv
	
    }
          DESCRIPTION
           "System drive type changed."
           --#SUMMARY  "[ctl: %d logdrv: %d :] System drive type changed." 
           --#ARGUMENTS {0,1}
           --#SEVERITY INFORMATION
           --#TIMEINDEX 3
           --#STATE OPERATIONAL
           ::= 789

-- Dell event = 790 Vendor event = 156
pv660fEvent_SYSDEV_BADDATABLOCK    TRAP-TYPE
    ENTERPRISE  aryMgrEvts
    VARIABLES   {
	
	controllerNameEv,
	virtualDiskNameEv
	
    }
          DESCRIPTION
           "Bad data blocks found. Possible data loss."
           --#SUMMARY  "[ctl: %d logdrv: %d :] Bad data blocks found. Possible data loss." 
           --#ARGUMENTS {0,1}
           --#SEVERITY SERIOUS
           --#TIMEINDEX 3
           --#STATE OPERATIONAL
           ::= 790

-- Dell event = 791 Vendor event = 157
pv660fEvent_SYSDEV_WR_LUN_MAP    TRAP-TYPE
    ENTERPRISE  aryMgrEvts
    VARIABLES   {
	
	controllerNameEv
	
    }
          DESCRIPTION
           "System drive LUN mapping has been written to config."
           --#SUMMARY  "[ctl: %d :] System drive LUN mapping has been written to config." 
           --#ARGUMENTS {0}
           --#SEVERITY WARNING
           --#TIMEINDEX 2
           --#STATE OPERATIONAL
           ::= 791

-- Dell event = 792 Vendor event = 158
pv660fEvent_SYSDEV_DATAREAD_FROM_BLOCK_IN_BDT    TRAP-TYPE
    ENTERPRISE  aryMgrEvts
    VARIABLES   {
	
	controllerNameEv,
	virtualDiskNameEv
	
    }
          DESCRIPTION
           "Attempt to read data from block that is marked in Bad Data Table"
           --#SUMMARY  "[ctl: %d logdrv: %d :] Attempt to read data from block that is marked in Bad Data Table" 
           --#ARGUMENTS {0,1}
           --#SEVERITY SERIOUS
           --#TIMEINDEX 3
           --#STATE OPERATIONAL
           ::= 792

-- Dell event = 793 Vendor event = 159
pv660fEvent_SYSDEV_DATA_FOR_BLOCK_LOST    TRAP-TYPE
    ENTERPRISE  aryMgrEvts
    VARIABLES   {
	
	controllerNameEv,
	virtualDiskNameEv
	
    }
          DESCRIPTION
           "Data for Disk Block has been lost due to Logical Drive problem"
           --#SUMMARY  "[ctl: %d logdrv: %d :] Data for Disk Block has been lost due to Logical Drive problem" 
           --#ARGUMENTS {0,1}
           --#SEVERITY ERROR
           --#TIMEINDEX 3
           --#STATE NONOPERATIONAL
           ::= 793

-- Dell event = 794 Vendor event = 160
pv660fEvent_SYSDEV_OFFLINE_DEVICE_MADE_AVAILABLE_WITH_DATALOSS    TRAP-TYPE
    ENTERPRISE  aryMgrEvts
    VARIABLES   {
	
	controllerNameEv,
	virtualDiskNameEv
	
    }
          DESCRIPTION
           "Temporary-Offline RAID5/RAID3 array is available to the user again with the possibility of data loss in the array."
           --#SUMMARY  "[ctl: %d logdrv: %d :] Temporary-Offline RAID5/RAID3 array is available to the user again with the possibility of data loss in the array." 
           --#ARGUMENTS {0,1}
           --#SEVERITY ERROR
           --#TIMEINDEX 3
           --#STATE NONOPERATIONAL
           ::= 794

-- Dell event = 795 Vendor event = 161
pv660fEvent_SYSDEV_OFFLINE_DEVICE_MADE_AVAILABLE    TRAP-TYPE
    ENTERPRISE  aryMgrEvts
    VARIABLES   {
	
	controllerNameEv,
	virtualDiskNameEv
	
    }
          DESCRIPTION
           "Temporary-Offline RAID0+1/RAID1/RAID0/JBOD array is available to the user again."
           --#SUMMARY  "[ctl: %d logdrv: %d :] Temporary-Offline RAID0+1/RAID1/RAID0/JBOD array is available to the user again." 
           --#ARGUMENTS {0,1}
           --#SEVERITY ERROR
           --#TIMEINDEX 3
           --#STATE NONOPERATIONAL
           ::= 795

-- Dell event = 796 Vendor event = 162
pv660fEvent_SYSDEV_STANDBY_REBUILD_START    TRAP-TYPE
    ENTERPRISE  aryMgrEvts
    VARIABLES   {
	
	controllerNameEv,
	virtualDiskNameEv
	
    }
          DESCRIPTION
           "An standby rebuild has started on logical drive."
           --#SUMMARY  "[ctl: %d logdrv: %d :] An standby rebuild has started on logical drive." 
           --#ARGUMENTS {0,1}
           --#SEVERITY INFORMATION
           --#TIMEINDEX 3
           --#STATE OPERATIONAL
           ::= 796

-- Dell event = 797 Vendor event = 256
pv660fEvent_FMTFAN_FAILED    TRAP-TYPE
    ENTERPRISE  aryMgrEvts
    VARIABLES   {
	
	controllerNameEv,
	enclosureNumberEv,
	unitNumberEv
	
    }
          DESCRIPTION
           "Fan failure."
           --#SUMMARY  "[ctl: %d enclosure: %d unit: %d :] Fan failure." 
           --#ARGUMENTS {0,1,2}
           --#SEVERITY SERIOUS
           --#TIMEINDEX 4
           --#STATE OPERATIONAL
           ::= 797

-- Dell event = 798 Vendor event = 257
pv660fEvent_FMTFAN_OK    TRAP-TYPE
    ENTERPRISE  aryMgrEvts
    VARIABLES   {
	
	controllerNameEv,
	enclosureNumberEv,
	unitNumberEv
	
    }
          DESCRIPTION
           "Fan has been restored."
           --#SUMMARY  "[ctl: %d enclosure: %d unit: %d :] Fan has been restored." 
           --#ARGUMENTS {0,1,2}
           --#SEVERITY INFORMATION
           --#TIMEINDEX 4
           --#STATE OPERATIONAL
           ::= 798

-- Dell event = 799 Vendor event = 258
pv660fEvent_AEMI_FAN_FAILED    TRAP-TYPE
    ENTERPRISE  aryMgrEvts
    VARIABLES   {
	
	controllerNameEv,
	channelNumberEv,
	targetIDEv,
	unitNumberEv
	
    }
          DESCRIPTION
           "Fan failure."
           --#SUMMARY  "[ctl: %d chn: %d tgt: %d Fan: %d :] Fan failure." 
           --#ARGUMENTS {0,1,2,3}
           --#SEVERITY SERIOUS
           --#TIMEINDEX 5
           --#STATE OPERATIONAL
           ::= 799

-- Dell event = 800 Vendor event = 259
pv660fEvent_FMTFAN_NOTPRESENT    TRAP-TYPE
    ENTERPRISE  aryMgrEvts
    VARIABLES   {
	
	controllerNameEv,
	enclosureNumberEv
	
    }
          DESCRIPTION
           "Storage cabinet fan is not present."
           --#SUMMARY  "[ctl: %d enclosure: %d :] Storage cabinet fan is not present." 
           --#ARGUMENTS {0,1}
           --#SEVERITY INFORMATION
           --#TIMEINDEX 3
           --#STATE OPERATIONAL
           ::= 800

-- Dell event = 801 Vendor event = 272
pv660fEvent_FMTPOWER_FAILED    TRAP-TYPE
    ENTERPRISE  aryMgrEvts
    VARIABLES   {
	
	controllerNameEv,
	enclosureNumberEv,
	unitNumberEv
	
    }
          DESCRIPTION
           "Power supply failure."
           --#SUMMARY  "[ctl: %d enclosure: %d unit: %d :] Power supply failure." 
           --#ARGUMENTS {0,1,2}
           --#SEVERITY SERIOUS
           --#TIMEINDEX 4
           --#STATE OPERATIONAL
           ::= 801

-- Dell event = 802 Vendor event = 273
pv660fEvent_FMTPOWER_OK    TRAP-TYPE
    ENTERPRISE  aryMgrEvts
    VARIABLES   {
	
	controllerNameEv,
	enclosureNumberEv,
	unitNumberEv
	
    }
          DESCRIPTION
           "Power supply has been restored."
           --#SUMMARY  "[ctl: %d enclosure: %d unit: %d :] Power supply has been restored." 
           --#ARGUMENTS {0,1,2}
           --#SEVERITY INFORMATION
           --#TIMEINDEX 4
           --#STATE OPERATIONAL
           ::= 802

-- Dell event = 803 Vendor event = 274
pv660fEvent_AEMI_PWR_SUPPLY_FAILED    TRAP-TYPE
    ENTERPRISE  aryMgrEvts
    VARIABLES   {
	
	controllerNameEv,
	channelNumberEv,
	targetIDEv,
	unitNumberEv
	
    }
          DESCRIPTION
           "Power supply failure."
           --#SUMMARY  "[ctl: %d chn: %d tgt: %d Power Supply: %d :] Power supply failure." 
           --#ARGUMENTS {0,1,2,3}
           --#SEVERITY SERIOUS
           --#TIMEINDEX 5
           --#STATE OPERATIONAL
           ::= 803

-- Dell event = 804 Vendor event = 275
pv660fEvent_FMTPOWER_NOTPRESENT    TRAP-TYPE
    ENTERPRISE  aryMgrEvts
    VARIABLES   {
	
	controllerNameEv,
	enclosureNumberEv
	
    }
          DESCRIPTION
           "Storage cabinet power supply is not present."
           --#SUMMARY  "[ctl: %d enclosure: %d :] Storage cabinet power supply is not present." 
           --#ARGUMENTS {0,1}
           --#SEVERITY INFORMATION
           --#TIMEINDEX 3
           --#STATE OPERATIONAL
           ::= 804

-- Dell event = 805 Vendor event = 288
pv660fEvent_FMTHEAT_BAD    TRAP-TYPE
    ENTERPRISE  aryMgrEvts
    VARIABLES   {
	
	controllerNameEv,
	channelNumberEv,
	targetIDEv,
	unitNumberEv
	
    }
          DESCRIPTION
           "Over temperature. Temperature is above 70 degrees Celsius."
           --#SUMMARY  "[ctl: %d chn: %d tgt: %d Heat Sensor: %d :] Over temperature. Temperature is above 70 degrees Celsius." 
           --#ARGUMENTS {0,1,2,3}
           --#SEVERITY SERIOUS
           --#TIMEINDEX 5
           --#STATE OPERATIONAL
           ::= 805

-- Dell event = 806 Vendor event = 289
pv660fEvent_FMTHEAT_CRITICAL    TRAP-TYPE
    ENTERPRISE  aryMgrEvts
    VARIABLES   {
	
	controllerNameEv,
	enclosureNumberEv,
	unitNumberEv
	
    }
          DESCRIPTION
           "Temperature is above 50 degrees Celsius."
           --#SUMMARY  "[ctl: %d enclosure: %d unit: %d :] Temperature is above 50 degrees Celsius." 
           --#ARGUMENTS {0,1,2}
           --#SEVERITY WARNING
           --#TIMEINDEX 4
           --#STATE OPERATIONAL
           ::= 806

-- Dell event = 807 Vendor event = 290
pv660fEvent_FMTHEAT_OK    TRAP-TYPE
    ENTERPRISE  aryMgrEvts
    VARIABLES   {
	
	controllerNameEv,
	enclosureNumberEv,
	unitNumberEv
	
    }
          DESCRIPTION
           "Normal temperature has been restored."
           --#SUMMARY  "[ctl: %d enclosure: %d unit: %d :] Normal temperature has been restored." 
           --#ARGUMENTS {0,1,2}
           --#SEVERITY INFORMATION
           --#TIMEINDEX 4
           --#STATE OPERATIONAL
           ::= 807

-- Dell event = 808 Vendor event = 291
pv660fEvent_AEMI_OVER_TEMPERATURE    TRAP-TYPE
    ENTERPRISE  aryMgrEvts
    VARIABLES   {
	
	controllerNameEv,
	channelNumberEv,
	targetIDEv,
	unitNumberEv
	
    }
          DESCRIPTION
           "Over temperature."
           --#SUMMARY  "[ctl: %d chn: %d tgt: %d Heat Sensor: %d :] Over temperature." 
           --#ARGUMENTS {0,1,2,3}
           --#SEVERITY SERIOUS
           --#TIMEINDEX 5
           --#STATE OPERATIONAL
           ::= 808

-- Dell event = 809 Vendor event = 292
pv660fEvent_FMTHEAT_NOTPRESENT    TRAP-TYPE
    ENTERPRISE  aryMgrEvts
    VARIABLES   {
	
	controllerNameEv,
	enclosureNumberEv
	
    }
          DESCRIPTION
           "Storage cabinet temperature sensor is not present."
           --#SUMMARY  "[ctl: %d enclosure: %d :] Storage cabinet temperature sensor is not present." 
           --#ARGUMENTS {0,1}
           --#SEVERITY INFORMATION
           --#TIMEINDEX 3
           --#STATE OPERATIONAL
           ::= 809

-- Dell event = 810 Vendor event = 304
pv660fEvent_FMTSTWK_FAILED    TRAP-TYPE
    ENTERPRISE  aryMgrEvts
    VARIABLES   {
	
	controllerNameEv,
	channelNumberEv
	
    }
          DESCRIPTION
           "Storage Works enclosure reported failure state."
           --#SUMMARY  "[ctl: %d chn: %d :] Storage Works enclosure reported failure state." 
           --#ARGUMENTS {0,1}
           --#SEVERITY SERIOUS
           --#TIMEINDEX 3
           --#STATE OPERATIONAL
           ::= 810

-- Dell event = 811 Vendor event = 305
pv660fEvent_FMTSTWK_CRITICAL    TRAP-TYPE
    ENTERPRISE  aryMgrEvts
    VARIABLES   {
	
	controllerNameEv,
	channelNumberEv
	
    }
          DESCRIPTION
           "Storage Works enclosure reported critical state."
           --#SUMMARY  "[ctl: %d chn: %d :] Storage Works enclosure reported critical state." 
           --#ARGUMENTS {0,1}
           --#SEVERITY WARNING
           --#TIMEINDEX 3
           --#STATE OPERATIONAL
           ::= 811

-- Dell event = 812 Vendor event = 306
pv660fEvent_FMTSTWK_OK    TRAP-TYPE
    ENTERPRISE  aryMgrEvts
    VARIABLES   {
	
	controllerNameEv,
	channelNumberEv
	
    }
          DESCRIPTION
           "Storage Works enclosure reported normal state."
           --#SUMMARY  "[ctl: %d chn: %d :] Storage Works enclosure reported normal state." 
           --#ARGUMENTS {0,1}
           --#SEVERITY INFORMATION
           --#TIMEINDEX 3
           --#STATE OPERATIONAL
           ::= 812

-- Dell event = 813 Vendor event = 307
pv660fEvent_FMT_UPS_DISABLED    TRAP-TYPE
    ENTERPRISE  aryMgrEvts
    VARIABLES   {
	
	controllerNameEv
	
    }
          DESCRIPTION
           "Uninterruptible Power Supply Disabled."
           --#SUMMARY  "[ctl: %d :] Uninterruptible Power Supply Disabled." 
           --#ARGUMENTS {0}
           --#SEVERITY INFORMATION
           --#TIMEINDEX 2
           --#STATE OPERATIONAL
           ::= 813

-- Dell event = 814 Vendor event = 308
pv660fEvent_FMT_UPS_AC_FAIL    TRAP-TYPE
    ENTERPRISE  aryMgrEvts
    VARIABLES   {
	
	controllerNameEv
	
    }
          DESCRIPTION
           "Uninterruptible Power Supply AC Failed."
           --#SUMMARY  "[ctl: %d :] Uninterruptible Power Supply AC Failed." 
           --#ARGUMENTS {0}
           --#SEVERITY INFORMATION
           --#TIMEINDEX 2
           --#STATE OPERATIONAL
           ::= 814

-- Dell event = 815 Vendor event = 309
pv660fEvent_FMT_UPS_BAT_LOW    TRAP-TYPE
    ENTERPRISE  aryMgrEvts
    VARIABLES   {
	
	controllerNameEv
	
    }
          DESCRIPTION
           "Uninterruptible Power Supply Battery Low."
           --#SUMMARY  "[ctl: %d :] Uninterruptible Power Supply Battery Low." 
           --#ARGUMENTS {0}
           --#SEVERITY WARNING
           --#TIMEINDEX 2
           --#STATE OPERATIONAL
           ::= 815

-- Dell event = 816 Vendor event = 310
pv660fEvent_FMT_UPS_FAILED    TRAP-TYPE
    ENTERPRISE  aryMgrEvts
    VARIABLES   {
	
	controllerNameEv
	
    }
          DESCRIPTION
           "Uninterruptible Power Supply Failed."
           --#SUMMARY  "[ctl: %d :] Uninterruptible Power Supply Failed." 
           --#ARGUMENTS {0}
           --#SEVERITY SERIOUS
           --#TIMEINDEX 2
           --#STATE OPERATIONAL
           ::= 816

-- Dell event = 817 Vendor event = 311
pv660fEvent_FMT_UPS_OK    TRAP-TYPE
    ENTERPRISE  aryMgrEvts
    VARIABLES   {
	
	controllerNameEv
	
    }
          DESCRIPTION
           "Uninterruptible Power Supply Normal."
           --#SUMMARY  "[ctl: %d :] Uninterruptible Power Supply Normal." 
           --#ARGUMENTS {0}
           --#SEVERITY INFORMATION
           --#TIMEINDEX 2
           --#STATE OPERATIONAL
           ::= 817

-- Dell event = 818 Vendor event = 320
pv660fEvent_ENCLFAN_FAILED    TRAP-TYPE
    ENTERPRISE  aryMgrEvts
    VARIABLES   {
	
	controllerNameEv,
	enclosureNumberEv,
	unitNumberEv
	
    }
          DESCRIPTION
           "Fan failure."
           --#SUMMARY  "[ctl: %d enclosure: %d unit: %d :] Fan failure." 
           --#ARGUMENTS {0,1,2}
           --#SEVERITY SERIOUS
           --#TIMEINDEX 4
           --#STATE OPERATIONAL
           ::= 818

-- Dell event = 819 Vendor event = 321
pv660fEvent_ENCLFAN_OK    TRAP-TYPE
    ENTERPRISE  aryMgrEvts
    VARIABLES   {
	
	controllerNameEv,
	enclosureNumberEv,
	unitNumberEv
	
    }
          DESCRIPTION
           "Fan has been restored."
           --#SUMMARY  "[ctl: %d enclosure: %d unit: %d :] Fan has been restored." 
           --#ARGUMENTS {0,1,2}
           --#SEVERITY INFORMATION
           --#TIMEINDEX 4
           --#STATE OPERATIONAL
           ::= 819

-- Dell event = 820 Vendor event = 322
pv660fEvent_ENCLFAN_NOTPRESENT    TRAP-TYPE
    ENTERPRISE  aryMgrEvts
    VARIABLES   {
	
	controllerNameEv,
	enclosureNumberEv,
	unitNumberEv
	
    }
          DESCRIPTION
           "Fan is not present."
           --#SUMMARY  "[ctl: %d enclosure: %d unit: %d :] Fan is not present." 
           --#ARGUMENTS {0,1,2}
           --#SEVERITY INFORMATION
           --#TIMEINDEX 4
           --#STATE OPERATIONAL
           ::= 820

-- Dell event = 821 Vendor event = 323
pv660fEvent_ENCLPOWER_FAILED    TRAP-TYPE
    ENTERPRISE  aryMgrEvts
    VARIABLES   {
	
	controllerNameEv,
	enclosureNumberEv,
	unitNumberEv
	
    }
          DESCRIPTION
           "Power supply failure."
           --#SUMMARY  "[ctl: %d enclosure: %d unit: %d :] Power supply failure." 
           --#ARGUMENTS {0,1,2}
           --#SEVERITY SERIOUS
           --#TIMEINDEX 4
           --#STATE OPERATIONAL
           ::= 821

-- Dell event = 822 Vendor event = 324
pv660fEvent_ENCLPOWER_OK    TRAP-TYPE
    ENTERPRISE  aryMgrEvts
    VARIABLES   {
	
	controllerNameEv,
	enclosureNumberEv,
	unitNumberEv
	
    }
          DESCRIPTION
           "Power supply has been restored."
           --#SUMMARY  "[ctl: %d enclosure: %d unit: %d :] Power supply has been restored." 
           --#ARGUMENTS {0,1,2}
           --#SEVERITY INFORMATION
           --#TIMEINDEX 4
           --#STATE OPERATIONAL
           ::= 822

-- Dell event = 823 Vendor event = 325
pv660fEvent_ENCLPOWER_NOTPRESENT    TRAP-TYPE
    ENTERPRISE  aryMgrEvts
    VARIABLES   {
	
	controllerNameEv,
	enclosureNumberEv,
	unitNumberEv
	
    }
          DESCRIPTION
           "Power supply is not present."
           --#SUMMARY  "[ctl: %d enclosure: %d unit: %d :] Power supply is not present." 
           --#ARGUMENTS {0,1,2}
           --#SEVERITY INFORMATION
           --#TIMEINDEX 4
           --#STATE OPERATIONAL
           ::= 823

-- Dell event = 824 Vendor event = 326
pv660fEvent_ENCLHEAT_BAD    TRAP-TYPE
    ENTERPRISE  aryMgrEvts
    VARIABLES   {
	
	controllerNameEv,
	enclosureNumberEv,
	unitNumberEv
	
    }
          DESCRIPTION
           "Temperature is over safe limit. Failure imminent."
           --#SUMMARY  "[ctl: %d enclosure: %d unit: %d :] Temperature is over safe limit. Failure imminent." 
           --#ARGUMENTS {0,1,2}
           --#SEVERITY SERIOUS
           --#TIMEINDEX 4
           --#STATE OPERATIONAL
           ::= 824

-- Dell event = 825 Vendor event = 327
pv660fEvent_ENCLHEAT_CRITICAL    TRAP-TYPE
    ENTERPRISE  aryMgrEvts
    VARIABLES   {
	
	controllerNameEv,
	enclosureNumberEv,
	unitNumberEv
	
    }
          DESCRIPTION
           "Temperature is above working limit."
           --#SUMMARY  "[ctl: %d enclosure: %d unit: %d :] Temperature is above working limit." 
           --#ARGUMENTS {0,1,2}
           --#SEVERITY WARNING
           --#TIMEINDEX 4
           --#STATE OPERATIONAL
           ::= 825

-- Dell event = 826 Vendor event = 328
pv660fEvent_ENCLHEAT_OK    TRAP-TYPE
    ENTERPRISE  aryMgrEvts
    VARIABLES   {
	
	controllerNameEv,
	enclosureNumberEv,
	unitNumberEv
	
    }
          DESCRIPTION
           "Normal temperature has been restored."
           --#SUMMARY  "[ctl: %d enclosure: %d unit: %d :] Normal temperature has been restored." 
           --#ARGUMENTS {0,1,2}
           --#SEVERITY INFORMATION
           --#TIMEINDEX 4
           --#STATE OPERATIONAL
           ::= 826

-- Dell event = 827 Vendor event = 329
pv660fEvent_ENCLHEAT_NOTPRESENT    TRAP-TYPE
    ENTERPRISE  aryMgrEvts
    VARIABLES   {
	
	controllerNameEv,
	enclosureNumberEv,
	unitNumberEv
	
    }
          DESCRIPTION
           "Temperature sensor is not present."
           --#SUMMARY  "[ctl: %d enclosure: %d unit: %d :] Temperature sensor is not present." 
           --#ARGUMENTS {0,1,2}
           --#SEVERITY INFORMATION
           --#TIMEINDEX 4
           --#STATE OPERATIONAL
           ::= 827

-- Dell event = 828 Vendor event = 330
pv660fEvent_ENCLACCESS_CRITICAL    TRAP-TYPE
    ENTERPRISE  aryMgrEvts
    VARIABLES   {
	
	controllerNameEv,
	enclosureNumberE
	
    }
          DESCRIPTION
           "Enclosure access critical."
           --#SUMMARY  "[ctl: %d enclosure: %d :] Enclosure access critical." 
           --#ARGUMENTS {0,1}
           --#SEVERITY WARNING
           --#TIMEINDEX 3
           --#STATE OPERATIONAL
           ::= 828

-- Dell event = 829 Vendor event = 331
pv660fEvent_ENCLACCESS_OK    TRAP-TYPE
    ENTERPRISE  aryMgrEvts
    VARIABLES   {
	
	controllerNameEv,
	enclosureNumberE
	
    }
          DESCRIPTION
           "Enclosure access has been restored."
           --#SUMMARY  "[ctl: %d enclosure: %d :] Enclosure access has been restored." 
           --#ARGUMENTS {0,1}
           --#SEVERITY INFORMATION
           --#TIMEINDEX 3
           --#STATE OPERATIONAL
           ::= 829

-- Dell event = 830 Vendor event = 332
pv660fEvent_ENCLACCESS_OFFLINE    TRAP-TYPE
    ENTERPRISE  aryMgrEvts
    VARIABLES   {
	
	controllerNameEv,
	enclosureNumberEv,
	unitNumberEv
	
    }
          DESCRIPTION
           "Enclosure access is offline."
           --#SUMMARY  "[ctl: %d enclosure: %d unit: %d :] Enclosure access is offline." 
           --#ARGUMENTS {0,1,2}
           --#SEVERITY SERIOUS
           --#TIMEINDEX 4
           --#STATE OPERATIONAL
           ::= 830

-- Dell event = 831 Vendor event = 333
pv660fEvent_ENCLSES_SOFTADDR_OCCURRED    TRAP-TYPE
    ENTERPRISE  aryMgrEvts
    VARIABLES   {
	
	controllerNameEv,
	enclosureNumberEv
	
    }
          DESCRIPTION
           "Enclosure Soft Addressing Detected."
           --#SUMMARY  "[ctl: %d enclosure: %d :] Enclosure Soft Addressing Detected." 
           --#ARGUMENTS {0,1}
           --#SEVERITY SERIOUS
           --#TIMEINDEX 3
           --#STATE OPERATIONAL
           ::= 831

-- Dell event = 832 Vendor event = 334
pv660fEvent_ENCLACCESS_READY    TRAP-TYPE
    ENTERPRISE  aryMgrEvts
    VARIABLES   {
	
	controllerNameEv
	
    }
          DESCRIPTION
           "Enclosure services ready"
           --#SUMMARY  "[ctl: %d :] Enclosure services ready" 
           --#ARGUMENTS {0}
           --#SEVERITY INFORMATION
           --#TIMEINDEX 2
           --#STATE OPERATIONAL
           ::= 832

-- Dell event = 833 Vendor event = 335
pv660fEvent_ENCLHEAT_UNKNOWN    TRAP-TYPE
    ENTERPRISE  aryMgrEvts
    VARIABLES   {
	
	controllerNameEv,
	enclosureNumberEv,
	unitNumberEv
	
    }
          DESCRIPTION
           "Access to temperature sensor has been lost."
           --#SUMMARY  "[ctl: %d enclosure: %d unit: %d :] Access to temperature sensor has been lost." 
           --#ARGUMENTS {0,1,2}
           --#SEVERITY INFORMATION
           --#TIMEINDEX 4
           --#STATE OPERATIONAL
           ::= 833

-- Dell event = 834 Vendor event = 336
pv660fEvent_ENCLPOWER_UNKNOWN    TRAP-TYPE
    ENTERPRISE  aryMgrEvts
    VARIABLES   {
	
	controllerNameEv,
	enclosureNumberEv,
	unitNumberEv
	
    }
          DESCRIPTION
           "Access to power supply status information has been lost."
           --#SUMMARY  "[ctl: %d enclosure: %d unit: %d :] Access to power supply status information has been lost." 
           --#ARGUMENTS {0,1,2}
           --#SEVERITY INFORMATION
           --#TIMEINDEX 4
           --#STATE OPERATIONAL
           ::= 834

-- Dell event = 835 Vendor event = 337
pv660fEvent_ENCLFAN_UNKNOWN    TRAP-TYPE
    ENTERPRISE  aryMgrEvts
    VARIABLES   {
	
	controllerNameEv,
	enclosureNumberEv,
	unitNumberEv
	
    }
          DESCRIPTION
           "Access to fan status information has been lost."
           --#SUMMARY  "[ctl: %d enclosure: %d unit: %d :] Access to fan status information has been lost." 
           --#ARGUMENTS {0,1,2}
           --#SEVERITY INFORMATION
           --#TIMEINDEX 4
           --#STATE OPERATIONAL
           ::= 835

-- Dell event = 836 Vendor event = 384
pv660fEvent_SYSTEM_STARTED    TRAP-TYPE
    ENTERPRISE  aryMgrEvts
          DESCRIPTION
           "Array management server software started successfully."
           --#SUMMARY  "    Array management server software started successfully.%d" 
           --#ARGUMENTS {0}
           --#SEVERITY INFORMATION
           --#TIMEINDEX 1
           --#STATE OPERATIONAL
           ::= 836

-- Dell event = 837 Vendor event = 385
pv660fEvent_CTLDEV_WRITEBACK_ERROR    TRAP-TYPE
    ENTERPRISE  aryMgrEvts
    VARIABLES   {
	
	controllerNameEv
	
    }
          DESCRIPTION
           "Write back error."
           --#SUMMARY  "[ctl: %d :] Write back error." 
           --#ARGUMENTS {0}
           --#SEVERITY ERROR
           --#TIMEINDEX 2
           --#STATE NONOPERATIONAL
           ::= 837

-- Dell event = 838 Vendor event = 386
pv660fEvent_CTLDEV_STATE_TABLE_FULL    TRAP-TYPE
    ENTERPRISE  aryMgrEvts
    VARIABLES   {
	
	controllerNameEv
	
    }
          DESCRIPTION
           "Internal log structures getting full,PLEASE SHUTDOWN AND RESET THE SYSTEM IN THE NEAR FUTURE."
           --#SUMMARY  "[ctl: %d :] Internal log structures getting full,PLEASE SHUTDOWN AND RESET THE SYSTEM IN THE NEAR FUTURE." 
           --#ARGUMENTS {0}
           --#SEVERITY WARNING
           --#TIMEINDEX 2
           --#STATE OPERATIONAL
           ::= 838

-- Dell event = 839 Vendor event = 388
pv660fEvent_CTLDEV_DEAD    TRAP-TYPE
    ENTERPRISE  aryMgrEvts
    VARIABLES   {
	
	controllerNameEv
	
    }
          DESCRIPTION
           "Controller is dead. System is disconnecting from this controller."
           --#SUMMARY  "[ctl: %d :] Controller is dead. System is disconnecting from this controller." 
           --#ARGUMENTS {0}
           --#SEVERITY CRITICAL
           --#TIMEINDEX 2
           --#STATE OPERATIONAL
           ::= 839

-- Dell event = 840 Vendor event = 389
pv660fEvent_CTLDEV_RESET    TRAP-TYPE
    ENTERPRISE  aryMgrEvts
    VARIABLES   {
	
	controllerNameEv
	
    }
          DESCRIPTION
           "Controller has been reset."
           --#SUMMARY  "[ctl: %d :] Controller has been reset." 
           --#ARGUMENTS {0}
           --#SEVERITY WARNING
           --#TIMEINDEX 2
           --#STATE OPERATIONAL
           ::= 840

-- Dell event = 841 Vendor event = 390
pv660fEvent_CTLDEV_FOUND    TRAP-TYPE
    ENTERPRISE  aryMgrEvts
    VARIABLES   {
	
	controllerNameEv
	
    }
          DESCRIPTION
           "Controller is found."
           --#SUMMARY  "[ctl: %d :] Controller is found." 
           --#ARGUMENTS {0}
           --#SEVERITY INFORMATION
           --#TIMEINDEX 2
           --#STATE OPERATIONAL
           ::= 841

-- Dell event = 842 Vendor event = 391
pv660fEvent_CTLDEV_GONE    TRAP-TYPE
    ENTERPRISE  aryMgrEvts
    VARIABLES   {
	
	controllerNameEv
	
    }
          DESCRIPTION
           "Controller is gone. System is disconnecting from this controller."
           --#SUMMARY  "[ctl: %d :] Controller is gone. System is disconnecting from this controller." 
           --#ARGUMENTS {0}
           --#SEVERITY CRITICAL
           --#TIMEINDEX 2
           --#STATE OPERATIONAL
           ::= 842

-- Dell event = 843 Vendor event = 392
pv660fEvent_CTLDEV_BBU_FOUND    TRAP-TYPE
    ENTERPRISE  aryMgrEvts
    VARIABLES   {
	
	controllerNameEv
	
    }
          DESCRIPTION
           "BBU Present."
           --#SUMMARY  "[ctl: %d :] BBU Present." 
           --#ARGUMENTS {0}
           --#SEVERITY INFORMATION
           --#TIMEINDEX 2
           --#STATE OPERATIONAL
           ::= 843

-- Dell event = 844 Vendor event = 393
pv660fEvent_CTLDEV_BBU_POWER_LOW    TRAP-TYPE
    ENTERPRISE  aryMgrEvts
    VARIABLES   {
	
	controllerNameEv
	
    }
          DESCRIPTION
           "BBU Power Low."
           --#SUMMARY  "[ctl: %d :] BBU Power Low." 
           --#ARGUMENTS {0}
           --#SEVERITY WARNING
           --#TIMEINDEX 2
           --#STATE OPERATIONAL
           ::= 844

-- Dell event = 845 Vendor event = 394
pv660fEvent_CTLDEV_BBU_POWER_OK    TRAP-TYPE
    ENTERPRISE  aryMgrEvts
    VARIABLES   {
	
	controllerNameEv
	
    }
          DESCRIPTION
           "BBU Power OK."
           --#SUMMARY  "[ctl: %d :] BBU Power OK." 
           --#ARGUMENTS {0}
           --#SEVERITY INFORMATION
           --#TIMEINDEX 2
           --#STATE OPERATIONAL
           ::= 845

-- Dell event = 846 Vendor event = 395
pv660fEvent_CTLDEV_POWER_OFF    TRAP-TYPE
    ENTERPRISE  aryMgrEvts
    VARIABLES   {
	
	controllerNameEv
	
    }
          DESCRIPTION
           "Controller is gone. System is disconnecting from this controller."
           --#SUMMARY  "[ctl: %d :] Controller is gone. System is disconnecting from this controller." 
           --#ARGUMENTS {0}
           --#SEVERITY CRITICAL
           --#TIMEINDEX 2
           --#STATE OPERATIONAL
           ::= 846

-- Dell event = 847 Vendor event = 396
pv660fEvent_CTLDEV_POWER_ON    TRAP-TYPE
    ENTERPRISE  aryMgrEvts
    VARIABLES   {
	
	controllerNameEv
	
    }
          DESCRIPTION
           "Controller powered on"
           --#SUMMARY  "[ctl: %d :] Controller powered on" 
           --#ARGUMENTS {0}
           --#SEVERITY INFORMATION
           --#TIMEINDEX 2
           --#STATE OPERATIONAL
           ::= 847

-- Dell event = 848 Vendor event = 397
pv660fEvent_CTLDEV_ONLINE    TRAP-TYPE
    ENTERPRISE  aryMgrEvts
    VARIABLES   {
	
	controllerNameEv
	
    }
          DESCRIPTION
           "Controller is online."
           --#SUMMARY  "[ctl: %d :] Controller is online." 
           --#ARGUMENTS {0}
           --#SEVERITY INFORMATION
           --#TIMEINDEX 2
           --#STATE OPERATIONAL
           ::= 848

-- Dell event = 849 Vendor event = 398
pv660fEvent_CTLDEV_OFFLINE    TRAP-TYPE
    ENTERPRISE  aryMgrEvts
    VARIABLES   {
	
	controllerNameEv
	
    }
          DESCRIPTION
           "Controller is gone. System is disconnecting from this controller."
           --#SUMMARY  "[ctl: %d :] Controller is gone. System is disconnecting from this controller." 
           --#ARGUMENTS {0}
           --#SEVERITY CRITICAL
           --#TIMEINDEX 2
           --#STATE OPERATIONAL
           ::= 849

-- Dell event = 850 Vendor event = 399
pv660fEvent_CTLDEV_CRITICAL    TRAP-TYPE
    ENTERPRISE  aryMgrEvts
    VARIABLES   {
	
	controllerNameEv
	
    }
          DESCRIPTION
           "Controller's partner is gone, controller is in failover mode now."
           --#SUMMARY  "[ctl: %d :] Controller's partner is gone, controller is in failover mode now." 
           --#ARGUMENTS {0}
           --#SEVERITY WARNING
           --#TIMEINDEX 2
           --#STATE OPERATIONAL
           ::= 850

-- Dell event = 851 Vendor event = 400
pv660fEvent_CTLDEV_BBU_RECOND_START    TRAP-TYPE
    ENTERPRISE  aryMgrEvts
    VARIABLES   {
	
	controllerNameEv
	
    }
          DESCRIPTION
           "BBU reconditioning is started."
           --#SUMMARY  "[ctl: %d :] BBU reconditioning is started." 
           --#ARGUMENTS {0}
           --#SEVERITY INFORMATION
           --#TIMEINDEX 2
           --#STATE OPERATIONAL
           ::= 851

-- Dell event = 852 Vendor event = 401
pv660fEvent_CTLDEV_BBU_RECOND_DONE    TRAP-TYPE
    ENTERPRISE  aryMgrEvts
    VARIABLES   {
	
	controllerNameEv
	
    }
          DESCRIPTION
           "BBU reconditioning is finished."
           --#SUMMARY  "[ctl: %d :] BBU reconditioning is finished." 
           --#ARGUMENTS {0}
           --#SEVERITY INFORMATION
           --#TIMEINDEX 2
           --#STATE OPERATIONAL
           ::= 852

-- Dell event = 853 Vendor event = 402
pv660fEvent_CTLDEV_BBU_RECOND_ABORT    TRAP-TYPE
    ENTERPRISE  aryMgrEvts
    VARIABLES   {
	
	controllerNameEv
	
    }
          DESCRIPTION
           "BBU reconditioning is canceled."
           --#SUMMARY  "[ctl: %d :] BBU reconditioning is canceled." 
           --#ARGUMENTS {0}
           --#SEVERITY INFORMATION
           --#TIMEINDEX 2
           --#STATE OPERATIONAL
           ::= 853

-- Dell event = 854 Vendor event = 403
pv660fEvent_CTLDEV_INSTALLATION_ABORTED    TRAP-TYPE
    ENTERPRISE  aryMgrEvts
    VARIABLES   {
	
	controllerNameEv
	
    }
          DESCRIPTION
           "Installation aborted."
           --#SUMMARY  "[ctl: %d :] Installation aborted." 
           --#ARGUMENTS {0}
           --#SEVERITY SERIOUS
           --#TIMEINDEX 2
           --#STATE OPERATIONAL
           ::= 854

-- Dell event = 855 Vendor event = 404
pv660fEvent_CTLDEV_FIRMWARE_MISMATCH    TRAP-TYPE
    ENTERPRISE  aryMgrEvts
    VARIABLES   {
	
	controllerNameEv,
	channelNumberEv,
	targetIDEv
	
    }
          DESCRIPTION
           "Controller firmware mismatch."
           --#SUMMARY  "[ctl: %d chn: %d tgt: %d :] Controller firmware mismatch." 
           --#ARGUMENTS {0,1,2}
           --#SEVERITY SERIOUS
           --#TIMEINDEX 4
           --#STATE OPERATIONAL
           ::= 855

-- Dell event = 856 Vendor event = 405
pv660fEvent_CTLDEV_BBU_NORESPONSE    TRAP-TYPE
    ENTERPRISE  aryMgrEvts
    VARIABLES   {
	
	controllerNameEv,
	channelNumberEv,
	targetIDEv
	
    }
          DESCRIPTION
           "BBU removed."
           --#SUMMARY  "[ctl: %d chn: %d tgt: %d :] BBU removed." 
           --#ARGUMENTS {0,1,2}
           --#SEVERITY WARNING
           --#TIMEINDEX 4
           --#STATE OPERATIONAL
           ::= 856

-- Dell event = 857 Vendor event = 406
pv660fEvent_CTLDEV_WARM_BOOT_ERROR    TRAP-TYPE
    ENTERPRISE  aryMgrEvts
    VARIABLES   {
	
	controllerNameEv,
	channelNumberEv,
	targetIDEv
	
    }
          DESCRIPTION
           "WARM BOOT failed."
           --#SUMMARY  "[ctl: %d chn: %d tgt: %d :] WARM BOOT failed." 
           --#ARGUMENTS {0,1,2}
           --#SEVERITY SERIOUS
           --#TIMEINDEX 4
           --#STATE OPERATIONAL
           ::= 857

-- Dell event = 858 Vendor event = 411
pv660fEvent_CTLDEV_CONSERV_CACHE_MODE    TRAP-TYPE
    ENTERPRISE  aryMgrEvts
    VARIABLES   {
	
	controllerNameEv
	
    }
          DESCRIPTION
           "Controller entered Conservative Cache Mode."
           --#SUMMARY  "[ctl: %d :] Controller entered Conservative Cache Mode." 
           --#ARGUMENTS {0}
           --#SEVERITY WARNING
           --#TIMEINDEX 2
           --#STATE OPERATIONAL
           ::= 858

-- Dell event = 859 Vendor event = 412
pv660fEvent_CTLDEV_NORMAL_CACHE_MODE    TRAP-TYPE
    ENTERPRISE  aryMgrEvts
    VARIABLES   {
	
	controllerNameEv
	
    }
          DESCRIPTION
           "Controller entered Normal Cache Mode."
           --#SUMMARY  "[ctl: %d :] Controller entered Normal Cache Mode." 
           --#ARGUMENTS {0}
           --#SEVERITY WARNING
           --#TIMEINDEX 2
           --#STATE OPERATIONAL
           ::= 859

-- Dell event = 860 Vendor event = 413
pv660fEvent_CTLDEV_DEV_START_CMPLT    TRAP-TYPE
    ENTERPRISE  aryMgrEvts
    VARIABLES   {
	
	controllerNameEv
	
    }
          DESCRIPTION
           "Controller Device Start Complete."
           --#SUMMARY  "[ctl: %d :] Controller Device Start Complete." 
           --#ARGUMENTS {0}
           --#SEVERITY WARNING
           --#TIMEINDEX 2
           --#STATE OPERATIONAL
           ::= 860

-- Dell event = 861 Vendor event = 414
pv660fEvent_CTLDEV_SOFT_ECC_CORRECTED    TRAP-TYPE
    ENTERPRISE  aryMgrEvts
    VARIABLES   {
	
	controllerNameEv
	
    }
          DESCRIPTION
           "Soft ECC error Corrected."
           --#SUMMARY  "[ctl: %d :] Soft ECC error Corrected." 
           --#ARGUMENTS {0}
           --#SEVERITY WARNING
           --#TIMEINDEX 2
           --#STATE OPERATIONAL
           ::= 861

-- Dell event = 862 Vendor event = 415
pv660fEvent_CTLDEV_HARD_ECC_CORRECTED    TRAP-TYPE
    ENTERPRISE  aryMgrEvts
    VARIABLES   {
	
	controllerNameEv,
	channelNumberEv,
	targetIDEv
	
    }
          DESCRIPTION
           "Hard ECC error Corrected."
           --#SUMMARY  "[ctl: %d chn: %d tgt: %d :] Hard ECC error Corrected." 
           --#ARGUMENTS {0,1,2}
           --#SEVERITY WARNING
           --#TIMEINDEX 4
           --#STATE OPERATIONAL
           ::= 862

-- Dell event = 863 Vendor event = 416
pv660fEvent_CTLDEV_BBU_RECOND_NEEDED    TRAP-TYPE
    ENTERPRISE  aryMgrEvts
    VARIABLES   {
	
	controllerNameEv
	
    }
          DESCRIPTION
           "BBU Recondition Needed."
           --#SUMMARY  "[ctl: %d :] BBU Recondition Needed." 
           --#ARGUMENTS {0}
           --#SEVERITY SERIOUS
           --#TIMEINDEX 2
           --#STATE OPERATIONAL
           ::= 863

-- Dell event = 864 Vendor event = 417
pv660fEvent_CTLDEV_REMOVED_PTNR    TRAP-TYPE
    ENTERPRISE  aryMgrEvts
    VARIABLES   {
	
	controllerNameEv
	
    }
          DESCRIPTION
           "Controller's Partner Has Been Removed."
           --#SUMMARY  "[ctl: %d :] Controller's Partner Has Been Removed." 
           --#ARGUMENTS {0}
           --#SEVERITY WARNING
           --#TIMEINDEX 2
           --#STATE OPERATIONAL
           ::= 864

-- Dell event = 865 Vendor event = 418
pv660fEvent_CTLDEV_BBU_OUT_OF_SERVICE    TRAP-TYPE
    ENTERPRISE  aryMgrEvts
    VARIABLES   {
	
	controllerNameEv
	
    }
          DESCRIPTION
           "BBU out of service."
           --#SUMMARY  "[ctl: %d :] BBU out of service." 
           --#ARGUMENTS {0}
           --#SEVERITY ERROR
           --#TIMEINDEX 2
           --#STATE NONOPERATIONAL
           ::= 865

-- Dell event = 866 Vendor event = 419
pv660fEvent_CTLDEV_UPDATE_PTNR_STATUS    TRAP-TYPE
    ENTERPRISE  aryMgrEvts
    VARIABLES   {
	
	controllerNameEv
	
    }
          DESCRIPTION
           "Updated partner's status."
           --#SUMMARY  "[ctl: %d :] Updated partner's status." 
           --#ARGUMENTS {0}
           --#SEVERITY WARNING
           --#TIMEINDEX 2
           --#STATE OPERATIONAL
           ::= 866

-- Dell event = 867 Vendor event = 420
pv660fEvent_CTLDEV_RELINQUISH_PTNR    TRAP-TYPE
    ENTERPRISE  aryMgrEvts
    VARIABLES   {
	
	controllerNameEv
	
    }
          DESCRIPTION
           "Relinquished partner."
           --#SUMMARY  "[ctl: %d :] Relinquished partner." 
           --#ARGUMENTS {0}
           --#SEVERITY WARNING
           --#TIMEINDEX 2
           --#STATE OPERATIONAL
           ::= 867

-- Dell event = 868 Vendor event = 421
pv660fEvent_CTLDEV_INSERTED_PTNR    TRAP-TYPE
    ENTERPRISE  aryMgrEvts
    VARIABLES   {
	
	controllerNameEv
	
    }
          DESCRIPTION
           "Inserted Partner."
           --#SUMMARY  "[ctl: %d :] Inserted Partner." 
           --#ARGUMENTS {0}
           --#SEVERITY WARNING
           --#TIMEINDEX 2
           --#STATE OPERATIONAL
           ::= 868

-- Dell event = 869 Vendor event = 422
pv660fEvent_CTLDEV_DUAL_ENABLED    TRAP-TYPE
    ENTERPRISE  aryMgrEvts
    VARIABLES   {
	
	controllerNameEv
	
    }
          DESCRIPTION
           "Dual Controllers Enabled."
           --#SUMMARY  "[ctl: %d :] Dual Controllers Enabled." 
           --#ARGUMENTS {0}
           --#SEVERITY WARNING
           --#TIMEINDEX 2
           --#STATE OPERATIONAL
           ::= 869

-- Dell event = 870 Vendor event = 423
pv660fEvent_CTLDEV_KILL_PTNR    TRAP-TYPE
    ENTERPRISE  aryMgrEvts
    VARIABLES   {
	
	controllerNameEv
	
    }
          DESCRIPTION
           "Killed Partner."
           --#SUMMARY  "[ctl: %d :] Killed Partner." 
           --#ARGUMENTS {0}
           --#SEVERITY WARNING
           --#TIMEINDEX 2
           --#STATE OPERATIONAL
           ::= 870

-- Dell event = 871 Vendor event = 424
pv660fEvent_CTLDEV_NEXUS    TRAP-TYPE
    ENTERPRISE  aryMgrEvts
    VARIABLES   {
	
	controllerNameEv
	
    }
          DESCRIPTION
           "Dual Controllers entered Nexus."
           --#SUMMARY  "[ctl: %d :] Dual Controllers entered Nexus." 
           --#ARGUMENTS {0}
           --#SEVERITY WARNING
           --#TIMEINDEX 2
           --#STATE OPERATIONAL
           ::= 871

-- Dell event = 872 Vendor event = 425
pv660fEvent_CTLDEV_BAD_BOOTROM_IMAGE    TRAP-TYPE
    ENTERPRISE  aryMgrEvts
    VARIABLES   {
	
	controllerNameEv
	
    }
          DESCRIPTION
           "Controller Boot ROM Image needs to be reloaded."
           --#SUMMARY  "[ctl: %d :] Controller Boot ROM Image needs to be reloaded." 
           --#ARGUMENTS {0}
           --#SEVERITY SERIOUS
           --#TIMEINDEX 2
           --#STATE OPERATIONAL
           ::= 872

-- Dell event = 873 Vendor event = 426
pv660fEvent_CTLDEV_BAD_MAC_ADDRESS    TRAP-TYPE
    ENTERPRISE  aryMgrEvts
    VARIABLES   {
	
	controllerNameEv
	
    }
          DESCRIPTION
           "Controller is using default non-unique world-wide name."
           --#SUMMARY  "[ctl: %d :] Controller is using default non-unique world-wide name." 
           --#ARGUMENTS {0}
           --#SEVERITY CRITICAL
           --#TIMEINDEX 2
           --#STATE OPERATIONAL
           ::= 873

-- Dell event = 874 Vendor event = 427
pv660fEvent_CTLDEV_MIRROR_RACE_RECOVERY_FAILED    TRAP-TYPE
    ENTERPRISE  aryMgrEvts
    VARIABLES   {
	
	controllerNameEv
	
    }
          DESCRIPTION
           "Mirror Race recovery failed."
           --#SUMMARY  "[ctl: %d :] Mirror Race recovery failed." 
           --#ARGUMENTS {0}
           --#SEVERITY ERROR
           --#TIMEINDEX 2
           --#STATE NONOPERATIONAL
           ::= 874

-- Dell event = 875 Vendor event = 428
pv660fEvent_CTLDEV_MIRROR_CRITICAL_DRIVE    TRAP-TYPE
    ENTERPRISE  aryMgrEvts
    VARIABLES   {
	
	controllerNameEv
	
    }
          DESCRIPTION
           "Mirror Race on critical drive."
           --#SUMMARY  "[ctl: %d :] Mirror Race on critical drive." 
           --#ARGUMENTS {0}
           --#SEVERITY CRITICAL
           --#TIMEINDEX 2
           --#STATE OPERATIONAL
           ::= 875

-- Dell event = 876 Vendor event = 512
pv660fEvent_SYSTEM_STARTED_NEW    TRAP-TYPE
    ENTERPRISE  aryMgrEvts
    DESCRIPTION
           "System started.-"
           --#SUMMARY  "    System started.-%d" 
           --#ARGUMENTS {0}
           --#SEVERITY INFORMATION
           --#TIMEINDEX 1
           --#STATE OPERATIONAL
           ::= 876

-- Dell event = 877 Vendor event = 513
pv660fEvent_SYSTEM_SIZE_TABLE_FULL    TRAP-TYPE
    ENTERPRISE  aryMgrEvts
    DESCRIPTION
           "Size table full.-"
           --#SUMMARY  "    Size table full.-%d" 
           --#ARGUMENTS {0}
           --#SEVERITY INFORMATION
           --#TIMEINDEX 1
           --#STATE OPERATIONAL
           ::= 877

-- Dell event = 878 Vendor event = 514
pv660fEvent_SYSTEM_USER_LOGGED_IN    TRAP-TYPE
    ENTERPRISE  aryMgrEvts
    DESCRIPTION
           "User logged in.-"
           --#SUMMARY  "    User logged in.-%d" 
           --#ARGUMENTS {0}
           --#SEVERITY INFORMATION
           --#TIMEINDEX 1
           --#STATE OPERATIONAL
           ::= 878

-- Dell event = 879 Vendor event = 515
pv660fEvent_SYSTEM_USER_LOGGED_OUT    TRAP-TYPE
    ENTERPRISE  aryMgrEvts
    DESCRIPTION
           "User logged out.-"
           --#SUMMARY  "    User logged out.-%d" 
           --#ARGUMENTS {0}
           --#SEVERITY INFORMATION
           --#TIMEINDEX 1
           --#STATE OPERATIONAL
           ::= 879

-- Dell event = 880 Vendor event = 516
pv660fEvent_SYSTEM_ALIVE    TRAP-TYPE
    ENTERPRISE  aryMgrEvts
    DESCRIPTION
           "Server alive."
           --#SUMMARY  "    Server alive.%d" 
           --#ARGUMENTS {0}
           --#SEVERITY INFORMATION
           --#TIMEINDEX 1
           --#STATE OPERATIONAL
           ::= 880

-- Dell event = 881 Vendor event = 517
pv660fEvent_SYSTEM_DEAD    TRAP-TYPE
    ENTERPRISE  aryMgrEvts
    DESCRIPTION
           "Lost connection to server, or server is down."
           --#SUMMARY  "    Lost connection to server, or server is down.%d" 
           --#ARGUMENTS {0}
           --#SEVERITY SERIOUS
           --#TIMEINDEX 1
           --#STATE OPERATIONAL
           ::= 881

-- Dell event = 882 Vendor event = 518
pv660fEvent_AUTOBOOT_CHANGED    TRAP-TYPE
    ENTERPRISE  aryMgrEvts
    VARIABLES   {
	
	controllerNameEv
	
    }
          DESCRIPTION
           "Automatic reboot count has changed."
           --#SUMMARY  "[ctl: %d :] Automatic reboot count has changed." 
           --#ARGUMENTS {0}
           --#SEVERITY INFORMATION
           --#TIMEINDEX 2
           --#STATE OPERATIONAL
           ::= 882

-- Dell event = 883 Vendor event = 640
pv660fEvent_CHANNEL_FAILED    TRAP-TYPE
    ENTERPRISE  aryMgrEvts
    VARIABLES   {
	
	controllerNameEv,
	channelNumberEv
	
    }
          DESCRIPTION
           "Channel Failed."
           --#SUMMARY  "[ctl: %d chn: %d :] Channel Failed." 
           --#ARGUMENTS {0,1}
           --#SEVERITY WARNING
           --#TIMEINDEX 3
           --#STATE OPERATIONAL
           ::= 883

-- Dell event = 884 Vendor event = 641
pv660fEvent_CHANNEL_OK    TRAP-TYPE
    ENTERPRISE  aryMgrEvts
    VARIABLES   {
	
	controllerNameEv,
	channelNumberEv
	
    }
          DESCRIPTION
           "Channel Online."
           --#SUMMARY  "[ctl: %d chn: %d :] Channel Online." 
           --#ARGUMENTS {0,1}
           --#SEVERITY WARNING
           --#TIMEINDEX 3
           --#STATE OPERATIONAL
           ::= 884

-- Dell event = 885 Vendor event = 642
pv660fEvent_CHANNEL_SCSI_BUS_DEAD    TRAP-TYPE
    ENTERPRISE  aryMgrEvts
    VARIABLES   {
	
	controllerNameEv,
	channelNumberEv
	
    }
          DESCRIPTION
           "Back End SCSI Bus Dead."
           --#SUMMARY  "[ctl: %d chn: %d :] Back End SCSI Bus Dead." 
           --#ARGUMENTS {0,1}
           --#SEVERITY SERIOUS
           --#TIMEINDEX 3
           --#STATE OPERATIONAL
           ::= 885

-- Dell event = 886 Vendor event = 643
pv660fEvent_CHANNEL_SCSI_BUS_ALIVE    TRAP-TYPE
    ENTERPRISE  aryMgrEvts
    VARIABLES   {
	
	controllerNameEv,
	channelNumberEv
	
    }
          DESCRIPTION
           "Back End SCSI Bus Alive."
           --#SUMMARY  "[ctl: %d chn: %d :] Back End SCSI Bus Alive." 
           --#ARGUMENTS {0,1}
           --#SEVERITY INFORMATION
           --#TIMEINDEX 3
           --#STATE OPERATIONAL
           ::= 886

-- Dell event = 887 Vendor event = 644
pv660fEvent_CHANNEL_FIBER_DEAD    TRAP-TYPE
    ENTERPRISE  aryMgrEvts
    VARIABLES   {
	
	controllerNameEv,
	channelNumberEv
	
    }
          DESCRIPTION
           "Back End Fibre Dead."
           --#SUMMARY  "[ctl: %d chn: %d :] Back End Fibre Dead." 
           --#ARGUMENTS {0,1}
           --#SEVERITY SERIOUS
           --#TIMEINDEX 3
           --#STATE OPERATIONAL
           ::= 887

-- Dell event = 888 Vendor event = 645
pv660fEvent_CHANNEL_FIBER_ALIVE    TRAP-TYPE
    ENTERPRISE  aryMgrEvts
    VARIABLES   {
	
	controllerNameEv,
	channelNumberEv
	
    }
          DESCRIPTION
           "Back End Fibre Alive."
           --#SUMMARY  "[ctl: %d chn: %d :] Back End Fibre Alive." 
           --#ARGUMENTS {0,1}
           --#SEVERITY INFORMATION
           --#TIMEINDEX 3
           --#STATE OPERATIONAL
           ::= 888

-- Dell event = 889 Vendor event = 700
pv660fEvent_LOG_EMPTY    TRAP-TYPE
    ENTERPRISE  aryMgrEvts
    VARIABLES   {
	
	controllerNameEv
	
    }
          DESCRIPTION
           "Event Log Empty."
           --#SUMMARY  "[ctl: %d :] Event Log Empty." 
           --#ARGUMENTS {0}
           --#SEVERITY WARNING
           --#TIMEINDEX 2
           --#STATE OPERATIONAL
           ::= 889

-- Dell event = 890 Vendor event = 701
pv660fEvent_LOG_OUT_SYNC    TRAP-TYPE
    ENTERPRISE  aryMgrEvts
    VARIABLES   {
	
	controllerNameEv
	
    }
          DESCRIPTION
           "Event Log Entries Lost."
           --#SUMMARY  "[ctl: %d :] Event Log Entries Lost." 
           --#ARGUMENTS {0}
           --#SEVERITY WARNING
           --#TIMEINDEX 2
           --#STATE OPERATIONAL
           ::= 890

-- Dell event = 891 Vendor event = 702
pv660fEvent_LOG_REQUEST_SENSE    TRAP-TYPE
    ENTERPRISE  aryMgrEvts
    VARIABLES   {
	
	controllerNameEv,
	channelNumberEv,
	targetIDEv
	
    }
          DESCRIPTION
           "Request Sense"
           --#SUMMARY  "[ctl: %d chn: %d tgt: %d :] Request Sense" 
           --#ARGUMENTS {0,1,2}
           --#SEVERITY WARNING
           --#TIMEINDEX 4
           --#STATE OPERATIONAL
           ::= 891

-- Dell event = 892 Vendor event = 703
pv660fEvent_LOG_SET_RTC    TRAP-TYPE
    ENTERPRISE  aryMgrEvts
    VARIABLES   {
	
	controllerNameEv,
	channelNumberEv
	
    }
          DESCRIPTION
           "Set Real Time Clock."
           --#SUMMARY  "[ctl: %d chn: %d :] Set Real Time Clock." 
           --#ARGUMENTS {0,1}
           --#SEVERITY WARNING
           --#TIMEINDEX 3
           --#STATE OPERATIONAL
           ::= 892

-- Dell event = 893 Vendor event = 800
pv660fEvent_CFG_NEW    TRAP-TYPE
    ENTERPRISE  aryMgrEvts
    VARIABLES   {
	
	controllerNameEv
	
    }
          DESCRIPTION
           "New Configuration Received."
           --#SUMMARY  "[ctl: %d :] New Configuration Received." 
           --#ARGUMENTS {0}
           --#SEVERITY WARNING
           --#TIMEINDEX 2
           --#STATE OPERATIONAL
           ::= 893

-- Dell event = 894 Vendor event = 801
pv660fEvent_CFG_CLEAR    TRAP-TYPE
    ENTERPRISE  aryMgrEvts
    VARIABLES   {
	
	controllerNameEv

    }
          DESCRIPTION
           "Configuration Cleared."
           --#SUMMARY  "[ctl: %d :] Configuration Cleared." 
           --#ARGUMENTS {0}
           --#SEVERITY WARNING
           --#TIMEINDEX 2
           --#STATE OPERATIONAL
           ::= 894

-- Dell event = 895 Vendor event = 802
pv660fEvent_CFG_INVALID    TRAP-TYPE
    ENTERPRISE  aryMgrEvts
    VARIABLES   {
	
	controllerNameEv
	
    }
          DESCRIPTION
           "Configuration Invalid."
           --#SUMMARY  "[ctl: %d :] Configuration Invalid." 
           --#ARGUMENTS {0}
           --#SEVERITY WARNING
           --#TIMEINDEX 2
           --#STATE OPERATIONAL
           ::= 895

-- Dell event = 896 Vendor event = 803
pv660fEvent_CFG_COD_ACCESS_ERROR    TRAP-TYPE
    ENTERPRISE  aryMgrEvts
    VARIABLES   {
	
	controllerNameEv
	
    }
          DESCRIPTION
           "Configuration On Disk Access Error."
           --#SUMMARY  "[ctl: %d :] Configuration On Disk Access Error." 
           --#ARGUMENTS {0}
           --#SEVERITY WARNING
           --#TIMEINDEX 2
           --#STATE OPERATIONAL
           ::= 896

-- Dell event = 897 Vendor event = 804
pv660fEvent_CFG_COD_CONVERTED    TRAP-TYPE
    ENTERPRISE  aryMgrEvts
    VARIABLES   {
	
	controllerNameEv
	
    }
          DESCRIPTION
           "Configuration On Disk Converted."
           --#SUMMARY  "[ctl: %d :] Configuration On Disk Converted." 
           --#ARGUMENTS {0}
           --#SEVERITY WARNING
           --#TIMEINDEX 2
           --#STATE OPERATIONAL
           ::= 897

-- Dell event = 898 Vendor event = 805
pv660fEvent_CFG_COD_IMPORT_FAILED    TRAP-TYPE
    ENTERPRISE  aryMgrEvts
    VARIABLES   {
	
	controllerNameEv
	
    }
          DESCRIPTION
           "Configuration On Disk Import Failed."
           --#SUMMARY  "[ctl: %d :] Configuration On Disk Import Failed." 
           --#ARGUMENTS {0}
           --#SEVERITY WARNING
           --#TIMEINDEX 2
           --#STATE OPERATIONAL
           ::= 898

-- Dell event = 899 Vendor event = 806
pv660fEvent_DEBUG_DUMP_GENERATED    TRAP-TYPE
    ENTERPRISE  aryMgrEvts
    VARIABLES   {
	
	controllerNameEv
	
    }
          DESCRIPTION
           "A Debug Dump exists on this system."
           --#SUMMARY  "[ctl: %d :] A Debug Dump exists on this system." 
           --#ARGUMENTS {0}
           --#SEVERITY INFORMATION
           --#TIMEINDEX 2
           --#STATE OPERATIONAL
           ::= 899

-- Dell event = 900 Vendor event = 807
pv660fEvent_DEBUG_DUMP_GENERATED_PARTNER    TRAP-TYPE
    ENTERPRISE  aryMgrEvts
    VARIABLES   {
	
	controllerNameEv
	
    }
          DESCRIPTION
           "A Debug Dump exists on this system."
           --#SUMMARY  "[ctl: %d :] A Debug Dump exists on this system." 
           --#ARGUMENTS {0}
           --#SEVERITY INFORMATION
           --#TIMEINDEX 2
           --#STATE OPERATIONAL
           ::= 900

-- Dell event = 901 Vendor event = 896
pv660fEvent_FATAL_HANG    TRAP-TYPE
    ENTERPRISE  aryMgrEvts
    DESCRIPTION
           "Internal Controller is in the hung state."
           --#SUMMARY  "    Internal Controller is in the hung state.%d" 
           --#ARGUMENTS {0}
           --#SEVERITY SERIOUS
           --#TIMEINDEX 1
           --#STATE OPERATIONAL
           ::= 901

-- Dell event = 902 Vendor event = 897
pv660fEvent_FATAL_BRKP    TRAP-TYPE
    ENTERPRISE  aryMgrEvts
    DESCRIPTION
           "Internal Controller has encountered a Firmware breakpoint."
           --#SUMMARY  "    Internal Controller has encountered a Firmware breakpoint.%d" 
           --#ARGUMENTS {0}
           --#SEVERITY SERIOUS
           --#TIMEINDEX 1
           --#STATE OPERATIONAL
           ::= 902

-- Dell event = 903 Vendor event = 912
pv660fEvent_I960_HW_ERR    TRAP-TYPE
    ENTERPRISE  aryMgrEvts
    DESCRIPTION
           "Internal Controller has encountered i960 processor specific error."
           --#SUMMARY  "    Internal Controller has encountered i960 processor specific error.%d" 
           --#ARGUMENTS {0}
           --#SEVERITY SERIOUS
           --#TIMEINDEX 1
           --#STATE OPERATIONAL
           ::= 903

-- Dell event = 904 Vendor event = 928
pv660fEvent_SARM_HW_ERR    TRAP-TYPE
    ENTERPRISE  aryMgrEvts
    DESCRIPTION
           "Internal Controller has encountered Strong-ARM processor specific error"
           --#SUMMARY  "    Internal Controller has encountered Strong-ARM processor specific error%d" 
           --#ARGUMENTS {0}
           --#SEVERITY SERIOUS
           --#TIMEINDEX 1
           --#STATE OPERATIONAL
           ::= 904

END
