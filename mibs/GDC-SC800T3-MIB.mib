-- ****************************************************************************
--                             sc800T3.mib
-- ****************************************************************************

-- Copyright 1998 General DataComm Inc., All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- This MIB module uses the extended OBJECT-TYPE macro as
-- defined in RFC 1212.

-- Note:  All rows in all tables defined within this MIB module are
-- virtual.  They can neither be created or deleted by management
-- operations.



-- ****************************************************************************
--                        revision History
-- ****************************************************************************

-- Version   Date	Name

-- 1.00A     19-May-98  J. Costa     	Initial Revision
-- 1.00B     19-Jan-99  C. Amorossi     1) Remove alarm sc800t3ReceivedYellow
--					2) Add maskable alarms sc800t3ES, 
--					   sc800t3SES, sc800t3SAS, sc800t3UAS,
--					   sc8003ESline, sc800t3RAI
-- 					3) Add windows/thresholds for 
--					   sc800t3ES, sc800t3SES, sc800t3SAS,
--					   sc800t3UAS, sc800t3ESline
--					4) Remove windows/thresholds for
--					   sc800t3LossOfSignal, sc800t3AIS,
--					   sc800t3OutOfFrame
--					5) Update comment for alarm scan
--					6) Change description of 
--					   sc800t3CurrentNearEndStat, 
--					   sc800t3CurrentFarEndStat,
--					   sc800t3NearEndIntervalStats,
--					   sc800t3FarEndIntervalStats
--					7) Change number of valid intervals
--					   from 96 to 31
--					8) Added sc800t3NetworkIdleStatus and
--					   sc800t3NetworkTransmitIdleStatus to
--					   sc800t3NetworkConfigTable
--					9) Change Total Statistics to Current
--					   Day Statistics
--					10)Added Previous Day Statistics
--					11)Added enums to sc800t3ResetStatistics
-- 1.00C     06-Apr-99  J. Bassett      1) Added End to end w/selftest
--                                      2) Added Ses BER threshold 
--                                      3) Commented out sc800t3DteStat - not supported
-- 1.00D     02-Jun-99  J. Bassett      1) Added thresGT100000 and thresGT1000000 to
--                                         sc800t3AlarmCountThreshold
--                                      2) Added sc800t3NearEndResetStats, sc800t3FarEndResetStats,
--                                         sc800t3NearEndStatLastInitial, sc800t3FarEndStatLastInitial;
--                                         removed sc800t3ResetStatistics
--                                      3) Removed Tx & Rx Invert and External Txmt Clk
--                                      4) Removed INS, CV, AIS, OOF, NS, and TM/ALM leds; removed
--                                         TM switch
--                                      5) Added NTWK, TM, ALM leds
--                                      6) Removed front panel test condition; removed excess zeros
--                                         alarm mask
--                                      7) Removed exczeros, excess error rate and front panel test
--                                      8) Expanded bit error counter to 16 bits
--                                      9) Added local alarm masks
--                                      10)Renumbered alarm OIDs
--                                      11)Added remote status to sc800t3DiagTestResults
--                                      12)Removed sc800t3NetworkLineCoding,
--                                         sc800t3ChannelRate
--                                      13)Changed names of channel config entries;
--                                         added DTELoopTimeout; corrected description of
--                                         sc800t3ChannelDTEtest
--                                      14)Added sc800t3InbandLoopback, sc800t3DTELoopTimeout
--                                      15)Removed sc800t3DiagT3SelfTestPattern
-- 1.00E     19-Jul-99  J. Bassett      1) Changed TxClkSrc definitions
--                                      2) Added sc800t3EraseFlash
-- 1.00F     01-Sep-99  J. Bassett      Reordered alarm oids so that the following order is 
--                                      observed:  non maskable, maskable, and thresh/windows
-- 1.00G     07-Sep-99  J. Bassett      1) Added sc800t3POSTFail to alarm table
--                                      2) Added objects for previous near and far end 15 min
--                                         statistics - sc800t3PreviousNearEndStat,
--                                         sc800t3PreviousFarEndStat  
--                       
-- ****************************************************************************


-- ****************************************************************************
--                       mib definitions begin
-- ****************************************************************************


GDC-SC800T3-MIB DEFINITIONS ::= BEGIN

IMPORTS	
	OBJECT-TYPE			FROM RFC-1212
	DisplayString			FROM RFC1213-MIB
	gdc				FROM GDCCMN-MIB
	SCinstance			FROM GDCMACRO-MIB;

ds3                     OBJECT IDENTIFIER ::= { gdc 19 }
sc800t3                 OBJECT IDENTIFIER ::= { ds3 1 }

sc800t3Version          OBJECT IDENTIFIER ::= { sc800t3 1 }
sc800t3Configuration    OBJECT IDENTIFIER ::= { sc800t3 2 }
sc800t3Diagnostics      OBJECT IDENTIFIER ::= { sc800t3 3 }
sc800t3Maintenance      OBJECT IDENTIFIER ::= { sc800t3 4 }
sc800t3Alarms           OBJECT IDENTIFIER ::= { sc800t3 5 }
sc800t3Performance      OBJECT IDENTIFIER ::= { sc800t3 6 }
sc800t3AlarmConfig      OBJECT IDENTIFIER ::= { sc800t3 7 }
sc800t3LocalAlarms      OBJECT IDENTIFIER ::= { sc800t3 8 }

--****************************************************************************
-- 	SCinstance is defined as the addressing/indexing method of accessing
--	table objects in this MIB. The SCinstance represents the SpectraComm
--	shelf Slot, Line, Drop and interface address.
--	Represented as SLDi, (Slot, Line, Drop, interface).
--
-- 	For the sc800t3: 
--
--		Byte		Range (dec.)		Identifies	
--		----		------------		----------
--		[S]lot		1 - 32			Physical Slot
--							1-16:  1st Shelf
--							17-32: 2nd Shelf
--
--		[L]ine		1
--		
--		[D]rop		0		
--
--		[i]nterface     0    			0: Unit
--
-- ****************************************************************************

sc800t3MIBversion OBJECT-TYPE
    SYNTAX DisplayString (SIZE (5))
    ACCESS read-only
    STATUS mandatory
    DESCRIPTION
        "Identifies the version of the MIB. The format of the version
        is x.yzT, where 'x' identifies the major revision number, 'y'
        identifies the minor revision number, 'z' identifies the
        typographical revision, and T identifies the test revision.
        Upon formal release, no designation for the test revision will
        be present. Acceptable values for the individual revision
        components are as follows:
        x: 1 - 9,    y: 0 - 9,    z: 0 - 9,    T: A - Z"
    ::= { sc800t3Version 1 }


-- ****************************************************************************
--                                Version Table
-- ****************************************************************************
sc800t3VersionTable OBJECT-TYPE
    SYNTAX SEQUENCE OF Sc800t3VersionEntry
    ACCESS not-accessible
    STATUS mandatory
    DESCRIPTION " "
    ::= { sc800t3Version 2  }

sc800t3VersionEntry OBJECT-TYPE
    SYNTAX Sc800t3VersionEntry
    ACCESS not-accessible
    STATUS mandatory
    DESCRIPTION
        "An entry in the GDC SC800T3 Version Table."
    INDEX	{ sc800t3VersionIndex }
    ::= { sc800t3VersionTable 1 }

Sc800t3VersionEntry ::=
    SEQUENCE {
	sc800t3VersionIndex    		SCinstance,
	sc800t3ActiveFirmwareRev 	DisplayString,
	sc800t3StandbyFirmwareRev	DisplayString,
	sc800t3StoredFirmwareStatus	INTEGER,
	sc800t3SwitchActiveFirmware	INTEGER,
	sc800t3DownloadingMode          INTEGER,
        sc800t3EraseFlash               INTEGER
    }

sc800t3VersionIndex OBJECT-TYPE
    SYNTAX SCinstance
    ACCESS read-only
    STATUS mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3VersionEntry 1 }

sc800t3ActiveFirmwareRev OBJECT-TYPE
    SYNTAX DisplayString (SIZE(8))
    ACCESS read-only
    STATUS mandatory
    DESCRIPTION
        "The version number of the firmware currently executing.
	 The format is MM.NN.BB where:
	
		MM: Major Revision (0-99)
		NN: Minor Revision (0-99)
		BB: Bug Fix Revision (0-99)"
    ::= { sc800t3VersionEntry 2 }

sc800t3StandbyFirmwareRev OBJECT-TYPE
    SYNTAX DisplayString (SIZE(8))
    ACCESS read-only
    STATUS mandatory
    DESCRIPTION
        "The version number of the firmware stored (in a compressed format) 
         but not currently executing.

	
		MM: Major Revision (0-99)
		NN: Minor Revision (0-99)
		BB: Bug Fix Revision (0-99)

	"
    ::= { sc800t3VersionEntry 3 }

sc800t3StoredFirmwareStatus OBJECT-TYPE
    SYNTAX INTEGER {
        statBlank(1),                       
        statDownLoading(2),
	statOK(3),
	statCheckSumBad(4),    
	statUnZipping(5),
	statBadUnZip(6),
	statDownloadAborted(7)
                    
    }
    ACCESS read-only
    STATUS mandatory
    DESCRIPTION
        "This object represents the state of the Non-Active or Stored firmware:

        statBlank(1)    	Factory Default                  
        statDownLoading(2)	In process of downloading firmware

	statOK(3)		Zipped version checksum succesful (OK to switch)
				(can set sc800t3SwitchActive to switchActive(2))
				
	statCheckSumBad(4)    	Failed checksum after download
	statUnZipping(5)	In process of uncompressing into active area
	statBadUnZip(6)      	Failed last uncompress 
	statDownloadAborted(7)  Download aborted by user"
    ::= { sc800t3VersionEntry 4 }

sc800t3SwitchActiveFirmware OBJECT-TYPE
    SYNTAX INTEGER {
        switchNorm(1),                  -- Read only
        switchActive(2)			-- Write only
    }
    ACCESS read-write
    STATUS mandatory
    DESCRIPTION
        "This object is used to switch the active executing firmware from the version 
	in sc800t3ActiveRev to the version in sc800t3StoredRev.

	When a  switchActive(2) is set (write only) the element will:
		1) reboot
		2) uncompress stored code into active area
		3) perform checksum on active area
		4) Set sc800t3StoredStatus object to indicate results
		5) If succesfull:
			update sc800t3ActiveFirmwareRev and sc800t3StoredFirmwareRev
			and begin executing
		   If failed: 
			replace active area with previous revision


	The switchNorm(1) enumeration will always be read. 

	Setting switchActive(2) when the sc800t3StoredStatus is not statOK(3) will
	result in an error.
	"
    ::= { sc800t3VersionEntry 5 }

sc800t3DownloadingMode OBJECT-TYPE
    SYNTAX INTEGER {
        disableAll(1),
        enableAndWait(2),
	enableAndSwitch(3)
    }
    ACCESS read-write
    STATUS mandatory
    DESCRIPTION
        "This object is used to configure the download mode:

        disableAll(1)		Prevents any firmware downloading to SC800T3

        enableAndWait(2)        Allows downloading zipped code to be stored
				only!
								
	enableAndSwitch(3)	Allows downloading and then unzips and begins
				executing the new code"

    ::= { sc800t3VersionEntry 6 }

sc800t3EraseFlash OBJECT-TYPE
    SYNTAX INTEGER {
        normal(1),    -- read-only
        erase(2)      -- write-only
    }
    ACCESS read-write
    STATUS mandatory
    DESCRIPTION
        "A set of this object to erase(2) will erase the application
         stored in flash.  After setting this object, there should
         be a delay of at least 2 minutes before downloading the
         unit."
    ::= { sc800t3VersionEntry 7}

-- ****************************************************************************
--                        Channel Configuration table
-- ****************************************************************************
sc800t3ChannelConfigTable OBJECT-TYPE
    SYNTAX SEQUENCE OF Sc800t3ChannelConfigEntry
    ACCESS not-accessible
    STATUS mandatory
    DESCRIPTION
    "The GDC SC800T3 Channel Configuration table."
    ::= { sc800t3Configuration 1 }

sc800t3ChannelConfigEntry OBJECT-TYPE
    SYNTAX Sc800t3ChannelConfigEntry
    ACCESS not-accessible
    STATUS mandatory
    DESCRIPTION
    "The sc800t3 Channel Configuration table entry."
    INDEX { sc800t3ChannelConfigIndex }
    ::= { sc800t3ChannelConfigTable 1 }

Sc800t3ChannelConfigEntry ::=
    SEQUENCE {
        sc800t3ChannelConfigIndex       SCinstance,
        sc800t3ForcedDCE 		INTEGER,
        sc800t3ChannelDTEtest    	INTEGER,
        sc800t3DTELoopTimeout           INTEGER
    }

sc800t3ChannelConfigIndex OBJECT-TYPE
    SYNTAX SCinstance
    ACCESS read-only
    STATUS mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3ChannelConfigEntry 1 }

sc800t3ForcedDCE OBJECT-TYPE
    SYNTAX INTEGER {
        followsDte(1),		-- local DCE follows DTE
        forcedOn(2)		-- local DCE forced on
    }
    ACCESS read-write
    STATUS mandatory
    DESCRIPTION
        "Controls the operation of Data Communications Equipment (DCE) signal.
        The value followsDte(1) indicates that the channel's DCE follows
        Data Terminal Equipment (DTE) ready. The value forcedOn(2) indicates 
	that DCE is forced on."
    ::= { sc800t3ChannelConfigEntry 2 }

sc800t3ChannelDTEtest OBJECT-TYPE
    SYNTAX INTEGER {
        disabled(1),		-- DTE test disabled
        enabled(2)		-- DTE test enabled
    }
    ACCESS read-write
    STATUS mandatory
    DESCRIPTION
	"DTE interface supporting loop A and loop B tests.  See ANSI TIA/EIA-613-1993
	specification for details on encoding of inter changes."
    ::= { sc800t3ChannelConfigEntry 3 }

sc800t3DTELoopTimeout  OBJECT-TYPE
    SYNTAX INTEGER {
        disabled(1),		-- DTE loop time out disabled
        enabled(2)		-- DTE loop time out enabled
    }
    ACCESS read-write
    STATUS mandatory
    DESCRIPTION
	"Enables/disables DTE loop time out."
    ::= { sc800t3ChannelConfigEntry 4 }

-- ****************************************************************************
--                     Network Configuration table
-- ****************************************************************************

sc800t3NetworkConfigTable OBJECT-TYPE
    SYNTAX SEQUENCE OF Sc800t3NetworkConfigEntry
    ACCESS not-accessible
    STATUS mandatory
    DESCRIPTION
    "The GDC SC800T3 Network Configuration table."
    ::= { sc800t3Configuration 2 }
 
sc800t3NetworkConfigEntry OBJECT-TYPE
    SYNTAX Sc800t3NetworkConfigEntry
    ACCESS not-accessible
    STATUS mandatory
    DESCRIPTION
    "The sc800t3 Network Configuration table entry."
    INDEX { sc800t3NetworkConfigIndex }
    ::= { sc800t3NetworkConfigTable 1 }
 
Sc800t3NetworkConfigEntry ::=
    SEQUENCE {
        sc800t3NetworkConfigIndex 		SCinstance,
        sc800t3NetworkFrameType			INTEGER,
        sc800t3NetworkTransmitClockSource	INTEGER,
        sc800t3NetworkAISLoopdown   		INTEGER,
        sc800t3NetworkLineType			INTEGER,
	sc800t3NetworkIdleStatus		INTEGER,
	sc800t3NetworkTransmitIdleStatus	INTEGER,
        sc800t3NetworkSesBERThreshold           INTEGER,
        sc800t3InbandLoopback                   INTEGER
    }

sc800t3NetworkConfigIndex OBJECT-TYPE
     SYNTAX SCinstance
     ACCESS read-only
     STATUS mandatory
     DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
     ::= { sc800t3NetworkConfigEntry 1 }
 
sc800t3NetworkFrameType OBJECT-TYPE
     SYNTAX INTEGER {
         m13(1),		-- M-13 framing type
         cbitParity(2)		-- C-bit parity framing
     }
     ACCESS read-write
     STATUS mandatory
     DESCRIPTION
        "Is the framing type of the network interface.  Setting the
	value of the object to m13(1) configures the network interface
	to M-13 framing.  Setting the value of this object to 
	cbitParity configures the network interface 20 C-bit parity
	framing"
     ::= { sc800t3NetworkConfigEntry 2 }

sc800t3NetworkTransmitClockSource OBJECT-TYPE
     SYNTAX INTEGER {
	internal(1),            -- internal transmit clock source
	receive(2)		-- network transmit clock source
     }
     ACCESS read-write
     STATUS mandatory
     DESCRIPTION
    	"The DSU transmit clock source option.
	 This is the selection for the transmitter
	 timing clock source."
     ::= { sc800t3NetworkConfigEntry 3 }
 
sc800t3NetworkAISLoopdown OBJECT-TYPE
     SYNTAX INTEGER (4..60)	-- disable, 5..60 seconds
     ACCESS read-write
     STATUS mandatory
     DESCRIPTION
         "The time in seconds when receiving a continuous AIS signal
         before a remotely initiated loopback is terminated.  When this
         object has the value 4, then there is no time limit and the
         loop must be terminated by remotely issued in-band loopdown
         codes.  When the object has a value between 5 and 60, then
         this is time in seconds of continuous AIS signal before
         the loopback is terminated."
    ::= { sc800t3NetworkConfigEntry 4 }
 
sc800t3NetworkLineType OBJECT-TYPE
     SYNTAX INTEGER {
         longCable(1),		-- 50 - 450 ft, DS-3 mode 
         shortCable(2)		-- 0 to 100 ft, DSX-3
     }
     ACCESS read-write
     STATUS mandatory
     DESCRIPTION
         "The operating mode of the interface.  Setting the value of
         this object to longCable(1) configures the interface as
         standard DS-3.  Setting the value of this object to
         shortCable(2) configures the interface to operate as a standard
         cross-connect DSX-3."
     ::= { sc800t3NetworkConfigEntry 5 }

sc800t3NetworkIdleStatus OBJECT-TYPE
     SYNTAX INTEGER {
         notReceived(1),
         received(2)
     }
     ACCESS read-only
     STATUS mandatory
     DESCRIPTION
         "Returns a value of received(2) when the sc800t3 receives 
          a DS3 idle from the network."
     ::= { sc800t3NetworkConfigEntry 6 }

sc800t3NetworkTransmitIdleStatus OBJECT-TYPE
     SYNTAX INTEGER {
         inactive(1),
         active(2)
     }
     ACCESS read-write
     STATUS mandatory
     DESCRIPTION
         "When set to active(2), the sc800t3 will transmit a DS3 idle  
          signal to the network."
     ::= { sc800t3NetworkConfigEntry 7 }

sc800t3NetworkSesBERThreshold OBJECT-TYPE
     SYNTAX INTEGER {
         thresone(1),   -- 1X10^-6 (44)
         thresseven(2)  -- 7.5X10^-5 (2444)
     }
     ACCESS read-write
     STATUS mandatory
     DESCRIPTION
         "When set to thresone(1), the SES BER threshold will be set to 
          1X10^-6 and when it is set to thresseven(2), it will be set to 
          7.5X10^-5."
     ::= { sc800t3NetworkConfigEntry 8 } 

sc800t3InbandLoopback OBJECT-TYPE
     SYNTAX INTEGER {
         disabled(1),   -- Inband loop back disabled
         enabled(2)     -- Inband loop back enabled
     }
     ACCESS read-write
     STATUS mandatory
     DESCRIPTION
	 "Enables/disables the inband loop back."
     ::= { sc800t3NetworkConfigEntry 9 } 

-- ****************************************************************************
--                        Diagnostics table
-- ****************************************************************************
sc800t3DiagTable OBJECT-TYPE
    SYNTAX SEQUENCE OF Sc800t3DiagEntry
    ACCESS not-accessible
    STATUS mandatory
    DESCRIPTION
        "The SC800T3 Diagnostics table."
    ::= { sc800t3Diagnostics 1 }
 
sc800t3DiagEntry OBJECT-TYPE
    SYNTAX Sc800t3DiagEntry
    ACCESS not-accessible
    STATUS mandatory
    DESCRIPTION
        "The SNMPSC800T3 Diagnostics table entry."
    INDEX { sc800t3DiagIndex }
    ::= { sc800t3DiagTable 1 }
 
Sc800t3DiagEntry ::=
    SEQUENCE {
        sc800t3DiagIndex 		SCinstance,
        sc800t3DiagTestDuration 	INTEGER,
        sc800t3InsertBitError 		INTEGER,
        sc800t3DiagT3Test 		INTEGER,
	sc800t3DiagTestResults  	OCTET STRING,
	sc800t3DiagResetTestResults	INTEGER
 }

sc800t3DiagIndex OBJECT-TYPE
    SYNTAX SCinstance
    ACCESS read-only
    STATUS mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3DiagEntry 1 }
 
sc800t3DiagTestDuration OBJECT-TYPE
    SYNTAX INTEGER     {
	testTime30Secs(1),
        testTime1Min(2),
        testTime2Mins(3),
        testTime3Mins(4),
        testTime4Mins(5),
        testTime5Mins(6),
        testTime6Mins(7),
        testTime7Mins(8),
        testTime8Mins(9),
        testTime9Mins(10),
        testTime10Mins(11),
        testTime15Mins(12),
        testTime20Mins(13),
        testTime25Mins(14),
        testTime30Mins(15),
	testTimeInfinite(16)
    }
    ACCESS read-write
    STATUS mandatory
    DESCRIPTION
        "Selects the duration to run a diagnostic test."
    ::= { sc800t3DiagEntry 2 }

sc800t3InsertBitError OBJECT-TYPE
    SYNTAX INTEGER {
	insertBitErrorNorm(1),		-- Read Only
	insertOneBitError(2)		         	
    }
    ACCESS read-write
    STATUS mandatory
    DESCRIPTION
	"A set of 2 will insert one bit error for test.
	 Management may only write a 2.  A 1 will always be read."
    ::= { sc800t3DiagEntry 3 }

sc800t3DiagT3Test OBJECT-TYPE
    SYNTAX INTEGER {
	t3NoTest(1),		        -- no test active
	t3LineLoopback(2),		-- towards Network
	t3PayLoadLoopback(3),		-- towards Network
	t3LocalLoopback(4),	        -- towards DTE interface
	t3LocalLoopbackST(5),		-- uses internal gen/checker
	t3DTELoopback(6),		-- towards DTE interface
	t3RemoteLineLoopback(7),	-- only in C-bit parity mode
	t3RemoteLineLoopbackST(8),	-- only in C-bit parity mode
	t3RemotePayload(9),		-- only in C-bit parity mode
	t3RemotePayloadST(10),		-- only in C-bit parity mode
        t3EndToEndST(11)
    }
    ACCESS read-write
    STATUS mandatory
    DESCRIPTION
	"A set of 2-11 starts the specified test
	 and a set of t3NoTest(1) stops the current running test. A
	 get returns the current active test."
    ::= { sc800t3DiagEntry 4 }

sc800t3DiagTestResults OBJECT-TYPE
    SYNTAX OCTET STRING (SIZE(3))
    ACCESS read-only
    STATUS mandatory
    DESCRIPTION
        "Returns a the folowing bytes.
 	   Octet 1  	bit 7 - F/U
		    	bit 6 - 1: Test complete
		    	bit 5 - 1: Test aborted
		    	bit 4 - F/U
		    	bit 3 - remote status          0: inactive 1: active
		    	bit 2 - 1: Bit errors over range
	     	    	bit 1 - Bit Errors
		    	bit 0 - Bit Errors

	   Octet 2      bit 7 - F/U
			bit 6 - 2^13       
			bit 5 - 2^12
			bit 4 - 2^11
			bit 3 - 2^10
			bit 2 - 2^9 	Bit Error Count
			bit 1 - 2^8
			bit 0 - 2^7

	   Octet 3      bit 7 - F/U
			bit 6 - 2^6
			bit 5 - 2^5
			bit 4 - 2^4
			bit 3 - 2^3
			bit 2 - 2^2
			bit 1 - 2^1
			bit 0 - 2^0"

    ::= { sc800t3DiagEntry 5 }

sc800t3DiagResetTestResults OBJECT-TYPE
    SYNTAX INTEGER {
        normal(1),            -- read only
        resetTestResult(2)    -- write only
    }
    ACCESS read-write
    STATUS mandatory
    DESCRIPTION
        "This object will clear the results register while 
	running any test except for Network Delay.
	
 	Starting a new test will automatically zero out
	the register. 

	A normal(1) will always be read.  Management will set a
	resetTestResult(2) to reset the test results.
	"
    ::= { sc800t3DiagEntry 6 }

-- ****************************************************************************
--                        Maintenance Table
-- ****************************************************************************

sc800t3MaintenanceTable OBJECT-TYPE
    SYNTAX SEQUENCE OF Sc800t3MaintenanceEntry
    ACCESS not-accessible
    STATUS mandatory
    DESCRIPTION
    "The table describes the maintenance functions for the sc800t3. "
    ::= { sc800t3Maintenance 1 }


sc800t3MaintenanceEntry OBJECT-TYPE
    SYNTAX Sc800t3MaintenanceEntry
    ACCESS not-accessible
    STATUS mandatory
    DESCRIPTION
    "An entry in the GDC maintenance Table"
    INDEX { sc800t3MaintenanceIndex }
    ::= { sc800t3MaintenanceTable 1 }


Sc800t3MaintenanceEntry ::=
SEQUENCE {
	sc800t3MaintenanceIndex      	SCinstance,
	sc800t3LedStatus		OCTET STRING,
        sc800t3SoftReset		INTEGER,
	sc800t3DefaultInit		INTEGER,
        sc800t3ValidNearEndIntervals 	INTEGER,
        sc800t3ValidFarEndIntervals  	INTEGER,	
	sc800t3ShelfType		INTEGER,
	sc800t3TwinPackPowerSupply	INTEGER,
	sc800t3TestAllLeds		INTEGER,
        sc800t3NearEndResetStats        INTEGER,
        sc800t3FarEndResetStats         INTEGER,
        sc800t3NearEndStatLastInitial   INTEGER,
        sc800t3FarEndStatLastInitial    INTEGER		
 }

sc800t3MaintenanceIndex OBJECT-TYPE
    SYNTAX SCinstance
    ACCESS read-only
    STATUS mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3MaintenanceEntry 1 }

sc800t3LedStatus OBJECT-TYPE
    SYNTAX OCTET STRING (SIZE(3))
    ACCESS read-only
    STATUS mandatory
    DESCRIPTION
   "Returns a bitwise snapshot of the front panel LED state and front panel switches.
 		Octet 1         bit 7 - f/u
				bit 6 - NTWK          0:LED off   1:LED on
				bit 5 - TM            0:LED off   1:LED on
				bit 4 - ALM           0:LED off   1:LED on
				bit 3 - f/u
				bit 2 - f/u
				bit 1 - f/u    
				bit 0 - f/u    

		Octet 2         bit 7 - f/u
				bit 6 - f/u
				bit 5 - f/u
				bit 4 - f/u
				bit 3 - f/u
				bit 2 - f/u
				bit 1 - f/u
				bit 0 - f/u       

		Octet 3         bit 7 - f/u
				bit 6 - f/u
				bit 5 - f/u
				bit 4 - f/u   
				bit 3 - f/u    
				bit 2 - f/u    
				bit 1 - f/u   
				bit 0 - f/u        
	"
    ::= { sc800t3MaintenanceEntry 2 }


sc800t3SoftReset	OBJECT-TYPE
     SYNTAX INTEGER
     {
          norm(1),          		-- read-only
          reset(2) 			-- write-only
     }
     ACCESS read-write
     STATUS mandatory
     DESCRIPTION
     "Supports the action of soft resetting the unit.  When this
     object is set to reset(1), then the unit performs a soft reset.
     The value norm will be returned when the reset is complete.
     The value of norm can not be set by management."
     ::= { sc800t3MaintenanceEntry 3 }

sc800t3DefaultInit OBJECT-TYPE
     SYNTAX INTEGER
     {
         normal(1),		-- read-only
         factoryDefault(2)	-- write-only
     }
     ACCESS read-write
     STATUS mandatory
     DESCRIPTION
     "This is used to allow the NonVolatile Configuration to be set to
     a factory default state.  When this value is set to factoryDefault,
     the unit will reset to the default configuration. The value of normal
     will be returned when the initialization is complete. The value normal
     can not be set by management."
     ::= { sc800t3MaintenanceEntry 4 }

sc800t3ValidNearEndIntervals OBJECT-TYPE
    SYNTAX  INTEGER (0..31)
    ACCESS  read-only
    STATUS  mandatory
    DESCRIPTION
        "The number of  previous  near end intervals  for  which
        valid data was collected.  The value will be 31
        unless the interface was brought on-line within
        the last 7.75 hours, in which case the value will
        be the number of complete 15 minute intervals
        since the interface has been online."
    ::= { sc800t3MaintenanceEntry 5 }
 
sc800t3ValidFarEndIntervals OBJECT-TYPE
    SYNTAX  INTEGER (0..31)
    ACCESS  read-only
    STATUS  mandatory
    DESCRIPTION
        "The number of  previous  far end intervals  for  which
        valid data was collected.  The value will be 31
        unless the interface was brought on-line within
        the last 7.75 hours, in which case the value will
        be the number of complete 15 minute intervals
        since the interface has been online."
    ::= { sc800t3MaintenanceEntry 6 }
 
sc800t3ShelfType OBJECT-TYPE
     SYNTAX INTEGER
     {
         spectracomm(1),
         twinPack(2)
     }
     ACCESS read-only
     STATUS mandatory
     DESCRIPTION
     "Type of shelf the sc800t3 is located in."
     ::= { sc800t3MaintenanceEntry 7 }

sc800t3TwinPackPowerSupply OBJECT-TYPE
     SYNTAX INTEGER
     {
	 none(1),
         bottomOnly(2),
         topOnly(3),
	 both(4)
     }
     ACCESS read-only
     STATUS mandatory
     DESCRIPTION
     "Power supplies currently installed in Twin Pack. When the sc800t3 is located in
      a Spectracomm shelf none(1) will always be returned."
     ::= { sc800t3MaintenanceEntry 8 }

sc800t3TestAllLeds OBJECT-TYPE
     SYNTAX INTEGER
     {
         allLedsON(1),
         allLedsOFF(2)
     }
     ACCESS read-write
     STATUS mandatory
     DESCRIPTION
     "This variable is used to test the front panel leds and individual 
      segments of the display.  A one (1) will turn all leds and display 
      segments on.  They will remain on until a two (2) is set or the card is 
      rebooted" 
     ::= { sc800t3MaintenanceEntry 9 }

sc800t3NearEndResetStats OBJECT-TYPE
     SYNTAX INTEGER
     {
	norm(1),
	reset(2)
     }
     ACCESS read-write
     STATUS mandatory
     DESCRIPTION
        "Supports the action of soft resetting the sc800t3ValidNearEndIntervals
        object.  When this object is set to reset(2), then the unit
        will reset the sc800t3ValidNearEndIntervals object to zero.
        The value of norm(1) can not be set by management."
     ::= { sc800t3MaintenanceEntry 10 }

sc800t3FarEndResetStats OBJECT-TYPE
     SYNTAX INTEGER
     {
	norm(1),
	reset(2)
     }
     ACCESS read-write
     STATUS mandatory
     DESCRIPTION
        "Supports the action of soft resetting the sc800t3ValidFarEndIntervals
        object.  When this object is set to reset(2), then the unit
        will reset the sc800t3ValidFarEndIntervals object to zero.
        The value of norm(1) can not be set by management."
     ::= { sc800t3MaintenanceEntry 11 }
	
sc800t3NearEndStatLastInitial OBJECT-TYPE
     SYNTAX INTEGER (1..2147483647)
     ACCESS read-only
     STATUS mandatory
     DESCRIPTION
	"Number of seconds from midnight Dec 31 1969 up until sc800t3ValidNearEndIntervals was 
         last initialized to zero."
     ::= { sc800t3MaintenanceEntry 12 }

sc800t3FarEndStatLastInitial OBJECT-TYPE
     SYNTAX INTEGER (1..2147483647)
     ACCESS read-only
     STATUS mandatory
     DESCRIPTION
	"Number of seconds from midnight Dec 31 1969 up until sc800t3ValidFarEndIntervals was 
         last initialized to zero."
     ::= { sc800t3MaintenanceEntry 13 }

-- ****************************************************************************
--                     Alarm Tables
-- ****************************************************************************

sc800t3NoResponse              	OBJECT IDENTIFIER ::= { sc800t3Alarms 1 }
sc800t3DiagRxErrAlm          	OBJECT IDENTIFIER ::= { sc800t3Alarms 2 }
sc800t3PowerUpAlm            	OBJECT IDENTIFIER ::= { sc800t3Alarms 3 }
sc800t3POSTFail                 OBJECT IDENTIFIER ::= { sc800t3Alarms 4 }
sc800t3UnsolicitedTest      	OBJECT IDENTIFIER ::= { sc800t3Alarms 5 }
sc800t3ConfigChange         	OBJECT IDENTIFIER ::= { sc800t3Alarms 6 }
sc800t3TimingLoss             	OBJECT IDENTIFIER ::= { sc800t3Alarms 7 }
sc800t3LossOfSignal            	OBJECT IDENTIFIER ::= { sc800t3Alarms 8 }
sc800t3OutOfFrame              	OBJECT IDENTIFIER ::= { sc800t3Alarms 9 }
sc800t3AIS                 	OBJECT IDENTIFIER ::= { sc800t3Alarms 10 }
sc800t3DTEReadyLoss             OBJECT IDENTIFIER ::= { sc800t3Alarms 11 }
sc800t3DTETXCLKLoss             OBJECT IDENTIFIER ::= { sc800t3Alarms 12 }
sc800t3RXDNoTrans               OBJECT IDENTIFIER ::= { sc800t3Alarms 13 }
sc800t3TXDNoTrans               OBJECT IDENTIFIER ::= { sc800t3Alarms 14 }
sc800t3RemoteNotResponding     	OBJECT IDENTIFIER ::= { sc800t3Alarms 15 }
sc800t3TopPowerSupplyFail     	OBJECT IDENTIFIER ::= { sc800t3Alarms 16 }
sc800t3BottomPowerSupplyFail    OBJECT IDENTIFIER ::= { sc800t3Alarms 17 }
sc800t3DTETest                  OBJECT IDENTIFIER ::= { sc800t3Alarms 18 }
sc800t3RAI                      OBJECT IDENTIFIER ::= { sc800t3Alarms 19 }
sc800t3ES                       OBJECT IDENTIFIER ::= { sc800t3Alarms 20 }
sc800t3SES		      	OBJECT IDENTIFIER ::= { sc800t3Alarms 21 }
sc800t3SAS		      	OBJECT IDENTIFIER ::= { sc800t3Alarms 22 }
sc800t3UAS		      	OBJECT IDENTIFIER ::= { sc800t3Alarms 23 }
sc800t3CodeViolations           OBJECT IDENTIFIER ::= { sc800t3Alarms 24 }
sc800t3ESline			OBJECT IDENTIFIER ::= { sc800t3Alarms 25 }

 -- ALARM               	     Maskable    thres    Type
 -- ============================================================================
 -- sc800t3NoResponse			no	 no    	 major
 -- sc800t3DiagRxErrAlm			no	 no	 major
 -- sc800t3PowerUpAlm			no	 no      major
 -- sc800t3POSTFail                     no       no      major
 -- sc800t3UnsolicitedTest		yes	 no	 major
 -- sc800t3ConfigChange			yes	 no	 major
 -- sc800t3TimingLoss			yes	 no	 major
 -- sc800t3LossOfSignal			yes	 no   	 major
 -- sc800t3OutOfFrame			yes	 no 	 major
 -- sc800t3AIS	          		yes	 no 	 major
 -- sc800t3DTEReadyLoss			yes	 no	 major
 -- sc800t3DTETXCLKLoss			yes	 no	 major
 -- sc800t3RXDNoTrans			yes	 no	 major
 -- sc800t3TXDNoTrans			yes	 no	 major
 -- sc800t3RemoteNotResponding		yes	 no	 major	
 -- sc800t3TopPowerSupplyFail		yes	 no	 minor	
 -- sc800t3BottomPowerSupplyFail	yes	 no	 minor	
 -- sc800t3DTETest         		yes	 no	 major	
 -- sc800t3RAI                          yes      no      major
 -- sc800t3ES                           yes      yes     minor
 -- sc800t3SES    			yes	 yes	 major
 -- sc800t3SAS				yes	 yes	 major
 -- sc800t3UAS				yes	 yes	 major
 -- sc800t3CodeViolations               Yes      yes     minor
 -- sc800t3ESline			yes	 yes	 major

--	Alarm Scan octet String (scmNodeCurrentAlarms in scmNodeTable from GDCSCM-MIB)
--	1.7	f/u
--	1.6	f/u
--	1.5	OOF 
--	1.4	Power-Up
--	1.3	AIS	
--	1.2	f/u
--	1.1	Timing Loss
--	1.0	f/u
--
--	2.7	f/u
--	2.6	f/u
--	2.5	f/u
--	2.4	DTE Test
--	2.3	f/u
--	2.2	TXD Loss (transitions)
--	2.1	RXD Loss (transitions)
--	2.0	LOS	
--
--	3.7	f/u
--	3.6     POST Failed	
--	3.5	Unsolicited Test
--	3.4	Config Change
--	3.3	Top Supply Fail
--	3.2	Bottom Supply Fail
--	3.1	Remote Not Resp
--	3.0	DTE Transmit Clock Loss
--
--	4.7	f/u
--	4.6	DTE Ready Loss
--	4.5	f/u
--	4.4	f/u
--	4.3	f/u	
--	4.2	f/u	
--	4.1	f/u 	
--	4.0	RAI	

--	5.7	f/u
--	5.6	f/u
--	5.5	ES line
--	5.4	ES
--	5.3	SES
--	5.2	SAS - Severely Errored Frame/AIS	
--	5.1	UAS 	
--	5.0	Code Violations

-- ****************************************************************************
--   			 Alarm Thresholds
-- ****************************************************************************
sc800t3AlarmConfigTable OBJECT-TYPE
     SYNTAX SEQUENCE OF Sc800t3AlarmConfigEntry
     ACCESS not-accessible
     STATUS mandatory
     DESCRIPTION
         "The sc800t3AlarmConfigTable contains entries that configure alarm
         reporting.  The structure of the table is such that alarm
         configuration is supported on a unit and interface basis, and
         then on an alarm type basis within the interface.  For
         simplicity sake alarms, be they unit or interface
         related, are represented in one table."
     ::= { sc800t3AlarmConfig 1 }
 
sc800t3AlarmConfigEntry OBJECT-TYPE
     SYNTAX Sc800t3AlarmConfigEntry
     ACCESS not-accessible
     STATUS mandatory
     DESCRIPTION
         "An entry in the GDC Alarm Configuration table."
     INDEX { sc800t3AlarmConfigIndex, sc800t3AlarmConfigIdentifier }
     ::= { sc800t3AlarmConfigTable 1 }
 
Sc800t3AlarmConfigEntry ::=
     SEQUENCE {
         sc800t3AlarmConfigIndex
             SCinstance,
         sc800t3AlarmConfigIdentifier
             OBJECT IDENTIFIER,
         sc800t3AlarmCountWindow
             INTEGER,
         sc800t3AlarmCountThreshold
             INTEGER
     }
 
sc800t3AlarmConfigIndex OBJECT-TYPE
     SYNTAX SCinstance
     ACCESS read-only
     STATUS mandatory
     DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
     ::= { sc800t3AlarmConfigEntry 1 }
 
sc800t3AlarmConfigIdentifier OBJECT-TYPE
     SYNTAX OBJECT IDENTIFIER
     ACCESS read-only
     STATUS mandatory
     DESCRIPTION
    "format: iso.org.dod.internet.private.enterprises.gdc.
             ds3.sc800t3.sc800t3Alarms.ALM
     example:  1.3.6.1.4.1.498.19.1.5.ALM
     where ALM = 1 for sc800t3NoResponse alarm, 2 for sc800t3DiagRxErr alarm,
                 etc., as specified in the Alarm Definitions above."
     ::= { sc800t3AlarmConfigEntry 2 }
 
sc800t3AlarmCountWindow OBJECT-TYPE
    SYNTAX INTEGER{
        reportAll(1),
        last1sec(2),
        last1min(3),
        last1hr(4),
        reportWhen(5)
    }
    ACCESS  read-write
    STATUS  mandatory
    DESCRIPTION
    "This variable sets/reads the alarm window.
 
    This window is used with the alarm threshold to determine
    how long the alarm should be active before reporting."
    ::= { sc800t3AlarmConfigEntry 3 }
 
sc800t3AlarmCountThreshold OBJECT-TYPE
    SYNTAX INTEGER {
        thresGT10(1),
        thresGT100(2),
        thresGT1000(3),
        thresGT10000(4),
        thresGT100000(5),
        thresGT1000000(6)
    }
    ACCESS  read-write
    STATUS  mandatory
    DESCRIPTION
    "This function sets/reads the alarm threshold criteria.
 
    This threshold is used along with the the alarm window to
    determine the number of instances in a given time frame for
    an alarm to occur before the alarm is considered active."
    ::= { sc800t3AlarmConfigEntry 4 }

-- ********************************************************************
--  			Performance Tables
-- ********************************************************************

-- ********************************************************************
--  			Current Near End
-- ********************************************************************
sc800t3CurrentNearEndTable 	OBJECT-TYPE
	 SYNTAX  SEQUENCE OF Sc800t3CurrentNearEndEntry
	 ACCESS  not-accessible
	 STATUS  mandatory
	 DESCRIPTION
		 "Gives the statistic count for the current
		  15 minute interval."
	 ::= { sc800t3Performance 1 }


sc800t3CurrentNearEndEntry 	OBJECT-TYPE
	 SYNTAX  Sc800t3CurrentNearEndEntry
	 ACCESS  not-accessible
	 STATUS  mandatory
	 DESCRIPTION
		 "An entry in the sc800t3 CurrentNearEnd table."
	 INDEX   { sc800t3CurrentNearEndIndex }
	 ::= { sc800t3CurrentNearEndTable 1 }

Sc800t3CurrentNearEndEntry ::=
    SEQUENCE {
        sc800t3CurrentNearEndIndex SCinstance,
        sc800t3CurrentNearEndStat	OCTET STRING
 	  }

sc800t3CurrentNearEndIndex OBJECT-TYPE
    SYNTAX  SCinstance
    ACCESS  read-only
    STATUS  mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3CurrentNearEndEntry 1 }

sc800t3CurrentNearEndStat OBJECT-TYPE
	 SYNTAX OCTET STRING (SIZE (11))
	 ACCESS read-only
	 STATUS mandatory
	 DESCRIPTION
		"Returns a bitwise snapshot of the statistics.

		Octet 1  bit 7 - parity   
			 bit 6 - Invalid Data Flag
			 bit 5 - n/a
			 bit 4 - n/a
			 bit 3 - n/a
			 bit 2 - 2^9    Errored Seconds (ES)
			 bit 1 - 2^8
			 bit 0 - 2^7 

		Octet 2  bit 7 - parity   
			 bit 6 - 2^6    Errored Seconds (ES)
			 bit 5 - 2^5 
			 bit 4 - 2^4 
			 bit 3 - 2^3 
			 bit 2 - 2^2 
			 bit 1 - 2^1
			 bit 0 - 2^0

		Octet 3  bit 7 - parity Severely Errored Seconds (SES)  
			 bit 6 - Invalid Data Flag
			 bit 5 - 2^5
			 bit 4 - 2^4
			 bit 3 - 2^3
			 bit 2 - 2^2
			 bit 1 - 2^1
			 bit 0 - 2^0

		Octet 4  bit 7 - parity Severely Errored Frames (SAS)  
			 bit 6 - Invalid Data Flag
			 bit 5 - 2^5
			 bit 4 - 2^4
			 bit 3 - 2^3
			 bit 2 - 2^2
			 bit 1 - 2^1
			 bit 0 - 2^0 

		Octet 5  bit 7 - parity Unavailable Seconds (UAS)  
			 bit 6 - Invalid Data Flag
			 bit 5 - 2^5 
			 bit 4 - 2^4 
			 bit 3 - 2^3 
			 bit 2 - 2^2 
			 bit 1 - 2^1 
			 bit 0 - 2^0

		Octet 6  bit 7 - parity Code Violations (CV)    	  
			 bit 6 - Invalid Data Flag
			 bit 5 - n/a 
			 bit 4 - n/a 
			 bit 3 - n/a 
			 bit 2 - n/a
			 bit 1 - n/a
			 bit 0 - n/a

		Octet 7  bit 7 - parity   
			 bit 6 - 2^13   Code Violations (CV)
			 bit 5 - 2^12
			 bit 4 - 2^11
			 bit 3 - 2^10
			 bit 2 - 2^9
			 bit 1 - 2^8
			 bit 0 - 2^7 

		Octet 8  bit 7 - parity   
			 bit 6 - 2^6    Code Violations (CV)
			 bit 5 - 2^5 
			 bit 4 - 2^4 
			 bit 3 - 2^3 
			 bit 2 - 2^2
			 bit 1 - 2^1
			 bit 0 - 2^0 

		Octet 9  bit 7 - parity   
			 bit 6 - Invalid Data Flag
			 bit 5 - n/a
			 bit 4 - n/a
			 bit 3 - n/a
			 bit 2 - 2^9    Errored Seconds Line (ESl)
			 bit 1 - 2^8
			 bit 0 - 2^7 

		Octet 10 bit 7 - parity   
			 bit 6 - 2^6    Errored Seconds Line (ESl)
			 bit 5 - 2^5 
			 bit 4 - 2^4 
			 bit 3 - 2^3 
			 bit 2 - 2^2 
			 bit 1 - 2^1
			 bit 0 - 2^0

		Octet 11 bit 7 - parity   
			 bit 6 - 2^6 	Percent Complete
			 bit 5 - 2^5
			 bit 4 - 2^4
			 bit 3 - 2^3
			 bit 2 - 2^2
			 bit 1 - 2^1
			 bit 0 - 2^0"

    ::= { sc800t3CurrentNearEndEntry 2 }
 

-- ********************************************************************
--  			Current Far End
-- ********************************************************************
sc800t3CurrentFarEndTable 	OBJECT-TYPE
	 SYNTAX  SEQUENCE OF Sc800t3CurrentFarEndEntry
	 ACCESS  not-accessible
	 STATUS  mandatory
	 DESCRIPTION
		 "Gives the statistic count for the current
		  15 minute interval."
	 ::= { sc800t3Performance 3 }


sc800t3CurrentFarEndEntry 	OBJECT-TYPE
	 SYNTAX  Sc800t3CurrentFarEndEntry
	 ACCESS  not-accessible
	 STATUS  mandatory
	 DESCRIPTION
		 "An entry in the sc800t3 CurrentFarEnd table."
	 INDEX   { sc800t3CurrentFarEndIndex }
	 ::= { sc800t3CurrentFarEndTable 1 }

Sc800t3CurrentFarEndEntry ::=
    SEQUENCE {
        sc800t3CurrentFarEndIndex  	SCinstance,
        sc800t3CurrentFarEndStat	OCTET STRING
 	  }

sc800t3CurrentFarEndIndex 	OBJECT-TYPE
    SYNTAX  SCinstance
    ACCESS  read-only
    STATUS  mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3CurrentFarEndEntry 1 }

sc800t3CurrentFarEndStat OBJECT-TYPE
	 SYNTAX OCTET STRING (SIZE (9))
	 ACCESS read-only
	 STATUS mandatory
	 DESCRIPTION
		"Returns a bitwise snapshot of the  statistics.

		Octet 1  bit 7 - parity   
			 bit 6 - Invalid Data Flag
			 bit 5 - n/a
			 bit 4 - n/a
			 bit 3 - n/a
			 bit 2 - 2^9    Errored Seconds (ES)
			 bit 1 - 2^8
			 bit 0 - 2^7 

		Octet 2  bit 7 - parity   
			 bit 6 - 2^6    Errored Seconds (ES)
			 bit 5 - 2^5 
			 bit 4 - 2^4 
			 bit 3 - 2^3 
			 bit 2 - 2^2 
			 bit 1 - 2^1
			 bit 0 - 2^0

		Octet 3  bit 7 - parity Severely Errored Seconds (SES)  
			 bit 6 - Invalid Data Flag
			 bit 5 - 2^5
			 bit 4 - 2^4
			 bit 3 - 2^3
			 bit 2 - 2^2
			 bit 1 - 2^1
			 bit 0 - 2^0

		Octet 4  bit 7 - parity Severely Errored Frames (SAS)  
			 bit 6 - Invalid Data Flag
			 bit 5 - 2^5
			 bit 4 - 2^4
			 bit 3 - 2^3
			 bit 2 - 2^2
			 bit 1 - 2^1
			 bit 0 - 2^0 

		Octet 5  bit 7 - parity Unavailable Seconds (UAS)  
			 bit 6 - Invalid Data Flag
			 bit 5 - 2^5 
			 bit 4 - 2^4 
			 bit 3 - 2^3 
			 bit 2 - 2^2 
			 bit 1 - 2^1 
			 bit 0 - 2^0

		Octet 6  bit 7 - parity Code Violations (CV)    	  
			 bit 6 - Invalid Data Flag
			 bit 5 - n/a 
			 bit 4 - n/a 
			 bit 3 - n/a 
			 bit 2 - n/a
			 bit 1 - n/a
			 bit 0 - n/a

		Octet 7  bit 7 - parity   
			 bit 6 - 2^13	Code Violations (CV)    	
			 bit 5 - 2^12
			 bit 4 - 2^11
			 bit 3 - 2^10
			 bit 2 - 2^9
			 bit 1 - 2^8
			 bit 0 - 2^7

		Octet 8  bit 7 - parity   
			 bit 6 - 2^6    Code Violations (CV)
			 bit 5 - 2^5
			 bit 4 - 2^4
			 bit 3 - 2^3
			 bit 2 - 2^2
			 bit 1 - 2^1
			 bit 0 - 2^0 

		Octet 9  bit 7 - parity   
			 bit 6 - 2^6 	Percent Complete
			 bit 5 - 2^5
			 bit 4 - 2^4
			 bit 3 - 2^3
			 bit 2 - 2^2
			 bit 1 - 2^1
			 bit 0 - 2^0"

    ::= { sc800t3CurrentFarEndEntry 2 }
 

-- ********************************************************************
--  			Current Day Near End
-- ********************************************************************
sc800t3CurrentDayNearEndTable 	OBJECT-TYPE
	 SYNTAX  SEQUENCE OF Sc800t3CurrentDayNearEndEntry
	 ACCESS  not-accessible
	 STATUS  mandatory
	 DESCRIPTION
		 "Gives totals for the current day of all
		  the near end statistics."
	 ::= { sc800t3Performance 4 }

sc800t3CurrentDayNearEndEntry 	OBJECT-TYPE
	 SYNTAX  Sc800t3CurrentDayNearEndEntry
	 ACCESS  not-accessible
	 STATUS  mandatory
	 DESCRIPTION
		 "An entry in the sc800t3 CurrentDayNearEndTable."
	 INDEX   { sc800t3CurrentDayNearEndIndex }
	 ::= { sc800t3CurrentDayNearEndTable 1 }

Sc800t3CurrentDayNearEndEntry ::=
    SEQUENCE {
        sc800t3CurrentDayNearEndIndex  	SCinstance,
        sc800t3CurrentDayNearEndStat		OCTET STRING
 	  }

sc800t3CurrentDayNearEndIndex 	OBJECT-TYPE
    SYNTAX  SCinstance
    ACCESS  read-only
    STATUS  mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3CurrentDayNearEndEntry 1 }

sc800t3CurrentDayNearEndStat OBJECT-TYPE
	 SYNTAX OCTET STRING (SIZE (18))
	 ACCESS read-only
	 STATUS mandatory
	 DESCRIPTION
		"Returns a bitwise snapshot of the  statistics.

		Octet 1  bit 7 - parity   
			 bit 6 - Invalid Data Flag
			 bit 5 - n/a
			 bit 4 - n/a
			 bit 3 - n/a
			 bit 2 - n/a
			 bit 1 - 2^15   Errored Seconds (ES)
			 bit 0 - 2^14

		Octet 2  bit 7 - parity   
			 bit 6 - 2^13   Errored Seconds (ES)
			 bit 5 - 2^12
			 bit 4 - 2^11
			 bit 3 - 2^10
			 bit 2 - 2^9
			 bit 1 - 2^8
			 bit 0 - 2^7

		Octet 3  bit 7 - parity   
			 bit 6 - 2^6	Errored Seconds (ES)
			 bit 5 - 2^5
			 bit 4 - 2^4
			 bit 3 - 2^3
			 bit 2 - 2^2
			 bit 1 - 2^1
			 bit 0 - 2^0

		Octet 4  bit 7 - parity Severely Errored Seconds (SES) 
			 bit 6 - Invalid Data Flag
			 bit 5 - n/a
			 bit 4 - 2^11
			 bit 3 - 2^10
			 bit 2 - 2^9
			 bit 1 - 2^8
			 bit 0 - 2^7

		Octet 5  bit 7 - parity   
			 bit 6 - 2^6  	Severely Errored Seconds (SES)
			 bit 5 - 2^5
			 bit 4 - 2^4 
			 bit 3 - 2^3 
			 bit 2 - 2^2
			 bit 1 - 2^1
			 bit 0 - 2^0

		Octet 6  bit 7 - parity Severely Errored Frame (SAS)	  
			 bit 6 - Invalid Data Flag
			 bit 5 - n/a
			 bit 4 - 2^11
			 bit 3 - 2^10
			 bit 2 - 2^9
			 bit 1 - 2^8
			 bit 0 - 2^7

		Octet 7  bit 7 - parity   
			 bit 6 - 2^6    Severely Errored Frame (SAS)	
			 bit 5 - 2^5
			 bit 4 - 2^4
			 bit 3 - 2^3
			 bit 2 - 2^2
			 bit 1 - 2^1 
			 bit 0 - 2^0 

		Octet 8  bit 7 - parity Unavailable Seconds (UAS)
			 bit 6 - Invalid Data Flag
			 bit 5 - n/a
			 bit 4 - 2^11
			 bit 3 - 2^10
			 bit 2 - 2^9
			 bit 1 - 2^8
			 bit 0 - 2^7

		Octet 9  bit 7 - parity   
			 bit 6 - 2^6 	Unavailable Seconds (UAS)
			 bit 5 - 2^5
			 bit 4 - 2^4
			 bit 3 - 2^3
			 bit 2 - 2^2
			 bit 1 - 2^1
			 bit 0 - 2^0

		Octet 10 bit 7 - parity Code Violations (CV)
			 bit 6 - Invalid Data Flag
			 bit 5 - 2^19
			 bit 4 - 2^18
			 bit 3 - 2^17
			 bit 2 - 2^16
			 bit 1 - 2^15
			 bit 0 - 2^14

		Octet 11 bit 7 - parity   
			 bit 6 - 2^13 	Code Violations (CV)
			 bit 5 - 2^12
			 bit 4 - 2^11
			 bit 3 - 2^10
			 bit 2 - 2^9
			 bit 1 - 2^8
			 bit 0 - 2^7

	        Octet 12 bit 7 - parity   
			 bit 6 - 2^6 	Code Violations (CV)
			 bit 5 - 2^5
			 bit 4 - 2^4
			 bit 3 - 2^3
			 bit 2 - 2^2
			 bit 1 - 2^1
			 bit 0 - 2^0

		Octet 13 bit 7 - parity   
			 bit 6 - Invalid Data Flag
			 bit 5 - n/a
			 bit 4 - n/a
			 bit 3 - n/a
			 bit 2 - n/a	
			 bit 1 - 2^15   Errored Seconds Line (ESl)
			 bit 0 - 2^14

		Octet 14 bit 7 - parity   
			 bit 6 - 2^13   Errored Seconds Line (ESl)
			 bit 5 - 2^12
			 bit 4 - 2^11
			 bit 3 - 2^10
			 bit 2 - 2^9
			 bit 1 - 2^8
			 bit 0 - 2^7

		Octet 15 bit 7 - parity   
			 bit 6 - 2^6	Errored Seconds Line (ESl)
			 bit 5 - 2^5
			 bit 4 - 2^4
			 bit 3 - 2^3
			 bit 2 - 2^2
			 bit 1 - 2^1
			 bit 0 - 2^0

		Octet 16 bit 7 - parity   
			 bit 6 - Invalid Data Flag
			 bit 5 - n/a
			 bit 4 - n/a
			 bit 3 - n/a
			 bit 2 - n/a	
			 bit 1 - 2^15   FC-P Path Failure Events
			 bit 0 - 2^14

		Octet 17 bit 7 - parity   
			 bit 6 - 2^13   FC-P Path Failure Events
			 bit 5 - 2^12
			 bit 4 - 2^11
			 bit 3 - 2^10
			 bit 2 - 2^9
			 bit 1 - 2^8
			 bit 0 - 2^7

		Octet 18 bit 7 - parity   
			 bit 6 - 2^6	FC-P Path Failure Events
			 bit 5 - 2^5
			 bit 4 - 2^4
			 bit 3 - 2^3
			 bit 2 - 2^2
			 bit 1 - 2^1
			 bit 0 - 2^0"

    ::= { sc800t3CurrentDayNearEndEntry 2 }
 
-- ********************************************************************
--  			Current Day Far End
-- ********************************************************************
sc800t3CurrentDayFarEndTable 	OBJECT-TYPE
	 SYNTAX  SEQUENCE OF Sc800t3CurrentDayFarEndEntry
	 ACCESS  not-accessible
	 STATUS  mandatory
	 DESCRIPTION
		 "Gives totals for the current day of
		  all the Far End statistics."
	 ::= { sc800t3Performance 6 }

sc800t3CurrentDayFarEndEntry 	OBJECT-TYPE
	 SYNTAX  Sc800t3CurrentDayFarEndEntry
	 ACCESS  not-accessible
	 STATUS  mandatory
	 DESCRIPTION
		 "An entry in the sc800t3CurrentDayFarEndTable."
	 INDEX   { sc800t3CurrentDayFarEndIndex }
	 ::= { sc800t3CurrentDayFarEndTable 1 }

Sc800t3CurrentDayFarEndEntry ::=
    SEQUENCE {
        sc800t3CurrentDayFarEndIndex  	SCinstance,
        sc800t3CurrentDayFarEndStat		OCTET STRING
 	  }

sc800t3CurrentDayFarEndIndex 	OBJECT-TYPE
    SYNTAX  SCinstance
    ACCESS  read-only
    STATUS  mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3CurrentDayFarEndEntry 1 }

sc800t3CurrentDayFarEndStat OBJECT-TYPE
	 SYNTAX OCTET STRING (SIZE (15))
	 ACCESS read-only
	 STATUS mandatory
	 DESCRIPTION
		"Returns a bitwise snapshot of the  statistics.

		Octet 1  bit 7 - parity   
			 bit 6 - Invalid Data Flag
			 bit 5 - n/a
			 bit 4 - n/a
			 bit 3 - n/a
			 bit 2 - n/a
			 bit 1 - 2^15   Errored Seconds (ES)
			 bit 0 - 2^14

		Octet 2  bit 7 - parity   
			 bit 6 - 2^13   Errored Seconds (ES)
			 bit 5 - 2^12
			 bit 4 - 2^11
			 bit 3 - 2^10
			 bit 2 - 2^9
			 bit 1 - 2^8
			 bit 0 - 2^7

		Octet 3  bit 7 - parity   
			 bit 6 - 2^6	Errored Seconds (ES)
			 bit 5 - 2^5
			 bit 4 - 2^4
			 bit 3 - 2^3
			 bit 2 - 2^2
			 bit 1 - 2^1
			 bit 0 - 2^0

		Octet 4  bit 7 - parity Severely Errored Seconds (SES) 
			 bit 6 - Invalid Data Flag
			 bit 5 - n/a
			 bit 4 - 2^11
			 bit 3 - 2^10
			 bit 2 - 2^9
			 bit 1 - 2^8
			 bit 0 - 2^7

		Octet 5  bit 7 - parity   
			 bit 6 - 2^6  	Severely Errored Seconds (SES)
			 bit 5 - 2^5
			 bit 4 - 2^4 
			 bit 3 - 2^3 
			 bit 2 - 2^2
			 bit 1 - 2^1
			 bit 0 - 2^0

		Octet 6  bit 7 - parity Severely Errored Frame (SAS)	  
			 bit 6 - Invalid Data Flag
			 bit 5 - n/a
			 bit 4 - 2^11
			 bit 3 - 2^10
			 bit 2 - 2^9
			 bit 1 - 2^8
			 bit 0 - 2^7

		Octet 7  bit 7 - parity   
			 bit 6 - 2^6    Severely Errored Frame (SAS)	
			 bit 5 - 2^5
			 bit 4 - 2^4
			 bit 3 - 2^3
			 bit 2 - 2^2
			 bit 1 - 2^1 
			 bit 0 - 2^0 

		Octet 8  bit 7 - parity Unavailable Seconds (UAS)
			 bit 6 - Invalid Data Flag
			 bit 5 - n/a
			 bit 4 - 2^11
			 bit 3 - 2^10
			 bit 2 - 2^9
			 bit 1 - 2^8
			 bit 0 - 2^7

		Octet 9  bit 7 - parity   
			 bit 6 - 2^6 	Unavailable Seconds (UAS)
			 bit 5 - 2^5
			 bit 4 - 2^4
			 bit 3 - 2^3
			 bit 2 - 2^2
			 bit 1 - 2^1
			 bit 0 - 2^0

		Octet 10 bit 7 - parity Code Violations (CV)
			 bit 6 - Invalid Data Flag
			 bit 5 - 2^19
			 bit 4 - 2^18
			 bit 3 - 2^17
			 bit 2 - 2^16
			 bit 1 - 2^15
			 bit 0 - 2^14

		Octet 11 bit 7 - parity   
			 bit 6 - 2^13 	Code Violations (CV)
			 bit 5 - 2^12
			 bit 4 - 2^11
			 bit 3 - 2^10
			 bit 2 - 2^9
			 bit 1 - 2^8
			 bit 0 - 2^7

	        Octet 12 bit 7 - parity   
			 bit 6 - 2^6 	Code Violations (CV)
			 bit 5 - 2^5
			 bit 4 - 2^4
			 bit 3 - 2^3
			 bit 2 - 2^2
			 bit 1 - 2^1
			 bit 0 - 2^0 

		Octet 13 bit 7 - parity FCCP-PFE Path Failure Events
			 bit 6 - Invalid Data Flag
			 bit 5 - n/a 
			 bit 4 - n/a 
			 bit 3 - n/a 
			 bit 2 - n/a 
			 bit 1 - 2^15
			 bit 0 - 2^14

		Octet 14 bit 7 - parity   
			 bit 6 - 2^13 	FCCP-PFE Path Failure Events
			 bit 5 - 2^12
			 bit 4 - 2^11
			 bit 3 - 2^10
			 bit 2 - 2^9
			 bit 1 - 2^8
			 bit 0 - 2^7

	        Octet 15 bit 7 - parity   
			 bit 6 - 2^6 	FCCP-PFE Path Failure Events
			 bit 5 - 2^5
			 bit 4 - 2^4
			 bit 3 - 2^3
			 bit 2 - 2^2
			 bit 1 - 2^1
			 bit 0 - 2^0"

    ::= { sc800t3CurrentDayFarEndEntry 2 }
 

-- ********************************************************************
--  			Previous Day Near End
-- ********************************************************************
sc800t3PreviousDayNearEndTable 	OBJECT-TYPE
	 SYNTAX  SEQUENCE OF Sc800t3PreviousDayNearEndEntry
	 ACCESS  not-accessible
	 STATUS  mandatory
	 DESCRIPTION
		 "Gives totals for the previous day of all
		  the near end statistics."
	 ::= { sc800t3Performance 2 }

sc800t3PreviousDayNearEndEntry 	OBJECT-TYPE
	 SYNTAX  Sc800t3PreviousDayNearEndEntry
	 ACCESS  not-accessible
	 STATUS  mandatory
	 DESCRIPTION
		 "An entry in the sc800t3 PreviousDayNearEndTable."
	 INDEX   { sc800t3PreviousDayNearEndIndex }
	 ::= { sc800t3PreviousDayNearEndTable 1 }

Sc800t3PreviousDayNearEndEntry ::=
    SEQUENCE {
        sc800t3PreviousDayNearEndIndex  	SCinstance,
        sc800t3PreviousDayNearEndStat		OCTET STRING
 	  }

sc800t3PreviousDayNearEndIndex 	OBJECT-TYPE
    SYNTAX  SCinstance
    ACCESS  read-only
    STATUS  mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3PreviousDayNearEndEntry 1 }

sc800t3PreviousDayNearEndStat OBJECT-TYPE
	 SYNTAX OCTET STRING (SIZE (18))
	 ACCESS read-only
	 STATUS mandatory
	 DESCRIPTION
		"Returns a bitwise snapshot of the  statistics.

		Octet 1  bit 7 - parity   
			 bit 6 - Invalid Data Flag
			 bit 5 - n/a
			 bit 4 - n/a
			 bit 3 - n/a
			 bit 2 - n/a
			 bit 1 - 2^15   Errored Seconds (ES)
			 bit 0 - 2^14

		Octet 2  bit 7 - parity   
			 bit 6 - 2^13   Errored Seconds (ES)
			 bit 5 - 2^12
			 bit 4 - 2^11
			 bit 3 - 2^10
			 bit 2 - 2^9
			 bit 1 - 2^8
			 bit 0 - 2^7

		Octet 3  bit 7 - parity   
			 bit 6 - 2^6	Errored Seconds (ES)
			 bit 5 - 2^5
			 bit 4 - 2^4
			 bit 3 - 2^3
			 bit 2 - 2^2
			 bit 1 - 2^1
			 bit 0 - 2^0

		Octet 4  bit 7 - parity Severely Errored Seconds (SES) 
			 bit 6 - Invalid Data Flag
			 bit 5 - n/a
			 bit 4 - 2^11
			 bit 3 - 2^10
			 bit 2 - 2^9
			 bit 1 - 2^8
			 bit 0 - 2^7

		Octet 5  bit 7 - parity   
			 bit 6 - 2^6  	Severely Errored Seconds (SES)
			 bit 5 - 2^5
			 bit 4 - 2^4 
			 bit 3 - 2^3 
			 bit 2 - 2^2
			 bit 1 - 2^1
			 bit 0 - 2^0

		Octet 6  bit 7 - parity Severely Errored Frame (SAS)	  
			 bit 6 - Invalid Data Flag
			 bit 5 - n/a
			 bit 4 - 2^11
			 bit 3 - 2^10
			 bit 2 - 2^9
			 bit 1 - 2^8
			 bit 0 - 2^7

		Octet 7  bit 7 - parity   
			 bit 6 - 2^6    Severely Errored Frame (SAS)	
			 bit 5 - 2^5
			 bit 4 - 2^4
			 bit 3 - 2^3
			 bit 2 - 2^2
			 bit 1 - 2^1 
			 bit 0 - 2^0 

		Octet 8  bit 7 - parity Unavailable Seconds (UAS)
			 bit 6 - Invalid Data Flag
			 bit 5 - n/a
			 bit 4 - 2^11
			 bit 3 - 2^10
			 bit 2 - 2^9
			 bit 1 - 2^8
			 bit 0 - 2^7

		Octet 9  bit 7 - parity   
			 bit 6 - 2^6 	Unavailable Seconds (UAS)
			 bit 5 - 2^5
			 bit 4 - 2^4
			 bit 3 - 2^3
			 bit 2 - 2^2
			 bit 1 - 2^1
			 bit 0 - 2^0

		Octet 10 bit 7 - parity Code Violations (CV)
			 bit 6 - Invalid Data Flag
			 bit 5 - 2^19
			 bit 4 - 2^18
			 bit 3 - 2^17
			 bit 2 - 2^16
			 bit 1 - 2^15
			 bit 0 - 2^14

		Octet 11 bit 7 - parity   
			 bit 6 - 2^13 	Code Violations (CV)
			 bit 5 - 2^12
			 bit 4 - 2^11
			 bit 3 - 2^10
			 bit 2 - 2^9
			 bit 1 - 2^8
			 bit 0 - 2^7

	        Octet 12 bit 7 - parity   
			 bit 6 - 2^6 	Code Violations (CV)
			 bit 5 - 2^5
			 bit 4 - 2^4
			 bit 3 - 2^3
			 bit 2 - 2^2
			 bit 1 - 2^1
			 bit 0 - 2^0

		Octet 13 bit 7 - parity   
			 bit 6 - Invalid Data Flag
			 bit 5 - n/a
			 bit 4 - n/a
			 bit 3 - n/a
			 bit 2 - n/a	
			 bit 1 - 2^15   Errored Seconds Line (ESl)
			 bit 0 - 2^14

		Octet 14 bit 7 - parity   
			 bit 6 - 2^13   Errored Seconds Line (ESl)
			 bit 5 - 2^12
			 bit 4 - 2^11
			 bit 3 - 2^10
			 bit 2 - 2^9
			 bit 1 - 2^8
			 bit 0 - 2^7

		Octet 15 bit 7 - parity   
			 bit 6 - 2^6	Errored Seconds Line (ESl)
			 bit 5 - 2^5
			 bit 4 - 2^4
			 bit 3 - 2^3
			 bit 2 - 2^2
			 bit 1 - 2^1
			 bit 0 - 2^0

		Octet 16 bit 7 - parity   
			 bit 6 - Invalid Data Flag
			 bit 5 - n/a
			 bit 4 - n/a
			 bit 3 - n/a
			 bit 2 - n/a	
			 bit 1 - 2^15   FC-P Path Failure Events
			 bit 0 - 2^14

		Octet 17 bit 7 - parity   
			 bit 6 - 2^13   FC-P Path Failure Events
			 bit 5 - 2^12
			 bit 4 - 2^11
			 bit 3 - 2^10
			 bit 2 - 2^9
			 bit 1 - 2^8
			 bit 0 - 2^7

		Octet 18 bit 7 - parity   
			 bit 6 - 2^6	FC-P Path Failure Events
			 bit 5 - 2^5
			 bit 4 - 2^4
			 bit 3 - 2^3
			 bit 2 - 2^2
			 bit 1 - 2^1
			 bit 0 - 2^0"

    ::= { sc800t3PreviousDayNearEndEntry 2 }
 
-- ********************************************************************
--  			Previous Day Far End
-- ********************************************************************
sc800t3PreviousDayFarEndTable 	OBJECT-TYPE
	 SYNTAX  SEQUENCE OF Sc800t3PreviousDayFarEndEntry
	 ACCESS  not-accessible
	 STATUS  mandatory
	 DESCRIPTION
		 "Gives totals for the previous day of
		  all the Far End statistics."
	 ::= { sc800t3Performance 5 }

sc800t3PreviousDayFarEndEntry 	OBJECT-TYPE
	 SYNTAX  Sc800t3PreviousDayFarEndEntry
	 ACCESS  not-accessible
	 STATUS  mandatory
	 DESCRIPTION
		 "An entry in the sc800t3PreviousDayFarEndTable."
	 INDEX   { sc800t3PreviousDayFarEndIndex }
	 ::= { sc800t3PreviousDayFarEndTable 1 }

Sc800t3PreviousDayFarEndEntry ::=
    SEQUENCE {
        sc800t3PreviousDayFarEndIndex  	SCinstance,
        sc800t3PreviousDayFarEndStat		OCTET STRING
 	  }

sc800t3PreviousDayFarEndIndex 	OBJECT-TYPE
    SYNTAX  SCinstance
    ACCESS  read-only
    STATUS  mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3PreviousDayFarEndEntry 1 }

sc800t3PreviousDayFarEndStat OBJECT-TYPE
	 SYNTAX OCTET STRING (SIZE (15))
	 ACCESS read-only
	 STATUS mandatory
	 DESCRIPTION
		"Returns a bitwise snapshot of the  statistics.

		Octet 1  bit 7 - parity   
			 bit 6 - Invalid Data Flag
			 bit 5 - n/a
			 bit 4 - n/a
			 bit 3 - n/a
			 bit 2 - n/a
			 bit 1 - 2^15   Errored Seconds (ES)
			 bit 0 - 2^14

		Octet 2  bit 7 - parity   
			 bit 6 - 2^13   Errored Seconds (ES)
			 bit 5 - 2^12
			 bit 4 - 2^11
			 bit 3 - 2^10
			 bit 2 - 2^9
			 bit 1 - 2^8
			 bit 0 - 2^7

		Octet 3  bit 7 - parity   
			 bit 6 - 2^6	Errored Seconds (ES)
			 bit 5 - 2^5
			 bit 4 - 2^4
			 bit 3 - 2^3
			 bit 2 - 2^2
			 bit 1 - 2^1
			 bit 0 - 2^0

		Octet 4  bit 7 - parity Severely Errored Seconds (SES) 
			 bit 6 - Invalid Data Flag
			 bit 5 - n/a
			 bit 4 - 2^11
			 bit 3 - 2^10
			 bit 2 - 2^9
			 bit 1 - 2^8
			 bit 0 - 2^7

		Octet 5  bit 7 - parity   
			 bit 6 - 2^6  	Severely Errored Seconds (SES)
			 bit 5 - 2^5
			 bit 4 - 2^4 
			 bit 3 - 2^3 
			 bit 2 - 2^2
			 bit 1 - 2^1
			 bit 0 - 2^0

		Octet 6  bit 7 - parity Severely Errored Frame (SAS)	  
			 bit 6 - Invalid Data Flag
			 bit 5 - n/a
			 bit 4 - 2^11
			 bit 3 - 2^10
			 bit 2 - 2^9
			 bit 1 - 2^8
			 bit 0 - 2^7

		Octet 7  bit 7 - parity   
			 bit 6 - 2^6    Severely Errored Frame (SAS)	
			 bit 5 - 2^5
			 bit 4 - 2^4
			 bit 3 - 2^3
			 bit 2 - 2^2
			 bit 1 - 2^1 
			 bit 0 - 2^0 

		Octet 8  bit 7 - parity Unavailable Seconds (UAS)
			 bit 6 - Invalid Data Flag
			 bit 5 - n/a
			 bit 4 - 2^11
			 bit 3 - 2^10
			 bit 2 - 2^9
			 bit 1 - 2^8
			 bit 0 - 2^7

		Octet 9  bit 7 - parity   
			 bit 6 - 2^6 	Unavailable Seconds (UAS)
			 bit 5 - 2^5
			 bit 4 - 2^4
			 bit 3 - 2^3
			 bit 2 - 2^2
			 bit 1 - 2^1
			 bit 0 - 2^0

		Octet 10 bit 7 - parity Code Violations (CV)
			 bit 6 - Invalid Data Flag
			 bit 5 - 2^19
			 bit 4 - 2^18
			 bit 3 - 2^17
			 bit 2 - 2^16
			 bit 1 - 2^15
			 bit 0 - 2^14

		Octet 11 bit 7 - parity   
			 bit 6 - 2^13 	Code Violations (CV)
			 bit 5 - 2^12
			 bit 4 - 2^11
			 bit 3 - 2^10
			 bit 2 - 2^9
			 bit 1 - 2^8
			 bit 0 - 2^7

	        Octet 12 bit 7 - parity   
			 bit 6 - 2^6 	Code Violations (CV)
			 bit 5 - 2^5
			 bit 4 - 2^4
			 bit 3 - 2^3
			 bit 2 - 2^2
			 bit 1 - 2^1
			 bit 0 - 2^0 

		Octet 13 bit 7 - parity FCCP-PFE Path Failure Events
			 bit 6 - Invalid Data Flag
			 bit 5 - n/a 
			 bit 4 - n/a 
			 bit 3 - n/a 
			 bit 2 - n/a 
			 bit 1 - 2^15
			 bit 0 - 2^14

		Octet 14 bit 7 - parity   
			 bit 6 - 2^13 	FCCP-PFE Path Failure Events
			 bit 5 - 2^12
			 bit 4 - 2^11
			 bit 3 - 2^10
			 bit 2 - 2^9
			 bit 1 - 2^8
			 bit 0 - 2^7

	        Octet 15 bit 7 - parity   
			 bit 6 - 2^6 	FCCP-PFE Path Failure Events
			 bit 5 - 2^5
			 bit 4 - 2^4
			 bit 3 - 2^3
			 bit 2 - 2^2
			 bit 1 - 2^1
			 bit 0 - 2^0"

    ::= { sc800t3PreviousDayFarEndEntry 2 }

-- ********************************************************************
--  			Interval Near End
-- ********************************************************************
sc800t3NearEndIntervalTable 	OBJECT-TYPE
    SYNTAX  SEQUENCE OF Sc800t3NearEndIntervalEntry
    ACCESS  not-accessible
    STATUS  mandatory
    DESCRIPTION
        "The sc800t3 Near End Interval table."
    ::= { sc800t3Performance 7 }

sc800t3NearEndIntervalEntry 	OBJECT-TYPE
    SYNTAX  Sc800t3NearEndIntervalEntry
    ACCESS  not-accessible
    STATUS  mandatory
    DESCRIPTION
        "An entry in the Interval table."
    INDEX   { sc800t3NearEndIntervalIndex, sc800t3NearEndIntervalNumber }
    ::= { sc800t3NearEndIntervalTable 1 }

Sc800t3NearEndIntervalEntry ::=
    SEQUENCE {
        sc800t3NearEndIntervalIndex		SCinstance,
        sc800t3NearEndIntervalNumber		INTEGER,
        sc800t3NearEndIntervalStats		OCTET STRING
}

sc800t3NearEndIntervalIndex OBJECT-TYPE
    SYNTAX  SCinstance
    ACCESS  read-only
    STATUS  mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3NearEndIntervalEntry 1 }

sc800t3NearEndIntervalNumber 	OBJECT-TYPE
    SYNTAX  INTEGER (1..31)
    ACCESS  read-only
    STATUS  mandatory
    DESCRIPTION
        "A number between 1 and 31, where 1 is the most recently completed 
        minute interval and 31 is the least recently completed 15 minutes  
        interval   (assuming   that  all  31  intervals  are valid)."
    ::= { sc800t3NearEndIntervalEntry 2 }

sc800t3NearEndIntervalStats OBJECT-TYPE
	 SYNTAX OCTET STRING (SIZE (11))
	 ACCESS read-only
	 STATUS mandatory
	 DESCRIPTION
		"Returns a bitwise snapshot of the  statistics.

		Octet 1  bit 7 - parity   
			 bit 6 - Invalid Data Flag
			 bit 5 - n/a
			 bit 4 - n/a
			 bit 3 - n/a
			 bit 2 - 2^9    Errored Seconds (ES)
			 bit 1 - 2^8
			 bit 0 - 2^7 

		Octet 2  bit 7 - parity   
			 bit 6 - 2^6    Errored Seconds (ES)
			 bit 5 - 2^5 
			 bit 4 - 2^4 
			 bit 3 - 2^3 
			 bit 2 - 2^2 
			 bit 1 - 2^1
			 bit 0 - 2^0

		Octet 3  bit 7 - parity Severely Errored Seconds (SES)  
			 bit 6 - Invalid Data Flag
			 bit 5 - 2^5
			 bit 4 - 2^4
			 bit 3 - 2^3
			 bit 2 - 2^2
			 bit 1 - 2^1
			 bit 0 - 2^0

		Octet 4  bit 7 - parity Severely Errored Frames (SAS)  
			 bit 6 - Invalid Data Flag
			 bit 5 - 2^5
			 bit 4 - 2^4
			 bit 3 - 2^3
			 bit 2 - 2^2
			 bit 1 - 2^1
			 bit 0 - 2^0 

		Octet 5  bit 7 - parity Unavailable Seconds (UAS)  
			 bit 6 - Invalid Data Flag
			 bit 5 - 2^5 
			 bit 4 - 2^4 
			 bit 3 - 2^3 
			 bit 2 - 2^2 
			 bit 1 - 2^1 
			 bit 0 - 2^0

		Octet 6  bit 7 - parity Code Violations (CV)    	  
			 bit 6 - Invalid Data Flag
			 bit 5 - n/a 
			 bit 4 - n/a 
			 bit 3 - n/a 
			 bit 2 - n/a
			 bit 1 - n/a
			 bit 0 - n/a

		Octet 7  bit 7 - parity   
			 bit 6 - 2^13   Code Violations (CV)
			 bit 5 - 2^12
			 bit 4 - 2^11
			 bit 3 - 2^10
			 bit 2 - 2^9
			 bit 1 - 2^8
			 bit 0 - 2^7

		Octet 8  bit 7 - parity   
			 bit 6 - 2^6    Code Violations (CV)
			 bit 5 - 2^5 
			 bit 4 - 2^4 
			 bit 3 - 2^3 
			 bit 2 - 2^2
			 bit 1 - 2^1
			 bit 0 - 2^0

		Octet 9  bit 7 - parity   
			 bit 6 - Invalid Data Flag
			 bit 5 - n/a
			 bit 4 - n/a
			 bit 3 - n/a
			 bit 2 - 2^9    Errored Seconds Line (ESl)
			 bit 1 - 2^8
			 bit 0 - 2^7 

		Octet 10 bit 7 - parity   
			 bit 6 - 2^6    Errored Seconds Line (ESl)
			 bit 5 - 2^5 
			 bit 4 - 2^4 
			 bit 3 - 2^3 
			 bit 2 - 2^2 
			 bit 1 - 2^1
			 bit 0 - 2^0

		Octet 11 bit 7 - parity   
			 bit 6 - n/a    Interval (1-31)
			 bit 5 - n/a 
			 bit 4 - 2^4 
			 bit 3 - 2^3 
			 bit 2 - 2^2 
			 bit 1 - 2^1
			 bit 0 - 2^0"
    ::= { sc800t3NearEndIntervalEntry 3 }

-- ********************************************************************
--  			Interval Far End
-- ********************************************************************
sc800t3FarEndIntervalTable 	OBJECT-TYPE
    SYNTAX  SEQUENCE OF Sc800t3FarEndIntervalEntry
    ACCESS  not-accessible
    STATUS  mandatory
    DESCRIPTION
        "The sc800t3 Far End Interval table."
    ::= { sc800t3Performance 9 }

sc800t3FarEndIntervalEntry 	OBJECT-TYPE
    SYNTAX  Sc800t3FarEndIntervalEntry
    ACCESS  not-accessible
    STATUS  mandatory
    DESCRIPTION
        "An entry in the Interval table."
    INDEX   { sc800t3FarEndIntervalIndex, sc800t3FarEndIntervalNumber }
    ::= { sc800t3FarEndIntervalTable 1 }

Sc800t3FarEndIntervalEntry ::=
    SEQUENCE {
        sc800t3FarEndIntervalIndex	SCinstance,
        sc800t3FarEndIntervalNumber	INTEGER,
        sc800t3FarEndIntervalStats	OCTET STRING
}

sc800t3FarEndIntervalIndex OBJECT-TYPE
    SYNTAX  SCinstance
    ACCESS  read-only
    STATUS  mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3FarEndIntervalEntry 1 }

sc800t3FarEndIntervalNumber 	OBJECT-TYPE
    SYNTAX  INTEGER (1..31)
    ACCESS  read-only
    STATUS  mandatory
    DESCRIPTION
        "A number between 1 and 31, where 1 is the most recently completed 
        minute interval and 31 is the least recently completed 15 minutes  
        interval   (assuming   that  all  31  intervals  are valid)."
    ::= { sc800t3FarEndIntervalEntry 2 }

sc800t3FarEndIntervalStats OBJECT-TYPE
	 SYNTAX OCTET STRING (SIZE (9))
	 ACCESS read-only
	 STATUS mandatory
	 DESCRIPTION
		"Returns a bitwise snapshot of the statistics.

		Octet 1  bit 7 - parity   
			 bit 6 - Invalid Data Flag
			 bit 5 - n/a
			 bit 4 - n/a
			 bit 3 - n/a
			 bit 2 - 2^9    Errored Seconds (ES)
			 bit 1 - 2^8
			 bit 0 - 2^7 

		Octet 2  bit 7 - parity   
			 bit 6 - 2^6    Errored Seconds (ES)
			 bit 5 - 2^5 
			 bit 4 - 2^4 
			 bit 3 - 2^3 
			 bit 2 - 2^2 
			 bit 1 - 2^1
			 bit 0 - 2^0

		Octet 3  bit 7 - parity Severely Errored Seconds (SES)  
			 bit 6 - Invalid Data Flag
			 bit 5 - 2^5
			 bit 4 - 2^4
			 bit 3 - 2^3
			 bit 2 - 2^2
			 bit 1 - 2^1
			 bit 0 - 2^0

		Octet 4  bit 7 - parity Severely Errored Frames (SAS)  
			 bit 6 - Invalid Data Flag
			 bit 5 - 2^5
			 bit 4 - 2^4
			 bit 3 - 2^3
			 bit 2 - 2^2
			 bit 1 - 2^1
			 bit 0 - 2^0 

		Octet 5  bit 7 - parity Unavailable Seconds (UAS)  
			 bit 6 - Invalid Data Flag
			 bit 5 - 2^5 
			 bit 4 - 2^4 
			 bit 3 - 2^3 
			 bit 2 - 2^2 
			 bit 1 - 2^1 
			 bit 0 - 2^0

		Octet 6  bit 7 - parity Code Violations (CV)    	  
			 bit 6 - Invalid Data Flag
			 bit 5 - n/a 
			 bit 4 - n/a 
			 bit 3 - n/a 
			 bit 2 - n/a
			 bit 1 - n/a
			 bit 0 - n/a

		Octet 7  bit 7 - parity   
			 bit 6 - 2^13   Code Violations (CV)
			 bit 5 - 2^12
			 bit 4 - 2^11
			 bit 3 - 2^10
			 bit 2 - 2^9
			 bit 1 - 2^8
			 bit 0 - 2^7

		Octet 8  bit 7 - parity   
			 bit 6 - 2^6    Code Violations (CV)
			 bit 5 - 2^5 
			 bit 4 - 2^4 
			 bit 3 - 2^3 
			 bit 2 - 2^2
			 bit 1 - 2^1
			 bit 0 - 2^0

		Octet 9  bit 7 - parity   
			 bit 6 - n/a    Interval (1-31)
			 bit 5 - n/a 
			 bit 4 - 2^4 
			 bit 3 - 2^3 
			 bit 2 - 2^2 
			 bit 1 - 2^1
			 bit 0 - 2^0"

    ::= { sc800t3FarEndIntervalEntry 3}

-- ********************************************************************
--  			Previous Near End
-- ********************************************************************
sc800t3PreviousNearEndTable 	OBJECT-TYPE
	 SYNTAX  SEQUENCE OF Sc800t3PreviousNearEndEntry
	 ACCESS  not-accessible
	 STATUS  mandatory
	 DESCRIPTION
		 "Gives the statistic count for the previous
		  15 minute interval."
	 ::= { sc800t3Performance 10 }


sc800t3PreviousNearEndEntry 	OBJECT-TYPE
	 SYNTAX  Sc800t3PreviousNearEndEntry
	 ACCESS  not-accessible
	 STATUS  mandatory
	 DESCRIPTION
		 "An entry in the sc800t3 PreviousNearEnd table."
	 INDEX   { sc800t3PreviousNearEndIndex }
	 ::= { sc800t3PreviousNearEndTable 1 }

Sc800t3PreviousNearEndEntry ::=
    SEQUENCE {
        sc800t3PreviousNearEndIndex SCinstance,
        sc800t3PreviousNearEndStat	OCTET STRING
 	  }

sc800t3PreviousNearEndIndex OBJECT-TYPE
    SYNTAX  SCinstance
    ACCESS  read-only
    STATUS  mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3PreviousNearEndEntry 1 }

sc800t3PreviousNearEndStat OBJECT-TYPE
	 SYNTAX OCTET STRING (SIZE (11))
	 ACCESS read-only
	 STATUS mandatory
	 DESCRIPTION
		"Returns a bitwise snapshot of the statistics.

		Octet 1  bit 7 - f/u   
			 bit 6 - Invalid Data Flag
			 bit 5 - n/a
			 bit 4 - n/a
			 bit 3 - n/a
			 bit 2 - 2^9    Errored Seconds (ES)
			 bit 1 - 2^8
			 bit 0 - 2^7 

		Octet 2  bit 7 - f/u   
			 bit 6 - 2^6    Errored Seconds (ES)
			 bit 5 - 2^5 
			 bit 4 - 2^4 
			 bit 3 - 2^3 
			 bit 2 - 2^2 
			 bit 1 - 2^1
			 bit 0 - 2^0

		Octet 3  bit 7 - f/u Severely Errored Seconds (SES)  
			 bit 6 - Invalid Data Flag
			 bit 5 - 2^5
			 bit 4 - 2^4
			 bit 3 - 2^3
			 bit 2 - 2^2
			 bit 1 - 2^1
			 bit 0 - 2^0

		Octet 4  bit 7 - f/u Severely Errored Frames (SAS)  
			 bit 6 - Invalid Data Flag
			 bit 5 - 2^5
			 bit 4 - 2^4
			 bit 3 - 2^3
			 bit 2 - 2^2
			 bit 1 - 2^1
			 bit 0 - 2^0 

		Octet 5  bit 7 - f/u Unavailable Seconds (UAS)  
			 bit 6 - Invalid Data Flag
			 bit 5 - 2^5 
			 bit 4 - 2^4 
			 bit 3 - 2^3 
			 bit 2 - 2^2 
			 bit 1 - 2^1 
			 bit 0 - 2^0

		Octet 6  bit 7 - f/u Code Violations (CV)    	  
			 bit 6 - Invalid Data Flag
			 bit 5 - n/a 
			 bit 4 - n/a 
			 bit 3 - n/a 
			 bit 2 - n/a
			 bit 1 - n/a
			 bit 0 - n/a

		Octet 7  bit 7 - f/u   
			 bit 6 - 2^13   Code Violations (CV)
			 bit 5 - 2^12
			 bit 4 - 2^11
			 bit 3 - 2^10
			 bit 2 - 2^9
			 bit 1 - 2^8
			 bit 0 - 2^7 

		Octet 8  bit 7 - f/u   
			 bit 6 - 2^6    Code Violations (CV)
			 bit 5 - 2^5 
			 bit 4 - 2^4 
			 bit 3 - 2^3 
			 bit 2 - 2^2
			 bit 1 - 2^1
			 bit 0 - 2^0 

		Octet 9  bit 7 - fu   
			 bit 6 - Invalid Data Flag
			 bit 5 - n/a
			 bit 4 - n/a
			 bit 3 - n/a
			 bit 2 - 2^9    Errored Seconds Line (ESl)
			 bit 1 - 2^8
			 bit 0 - 2^7 

		Octet 10 bit 7 - f/u   
			 bit 6 - 2^6    Errored Seconds Line (ESl)
			 bit 5 - 2^5 
			 bit 4 - 2^4 
			 bit 3 - 2^3 
			 bit 2 - 2^2 
			 bit 1 - 2^1
			 bit 0 - 2^0

		Octet 11 bit 7 - f/u   
			 bit 6 - 2^6 	Percent Complete
			 bit 5 - 2^5
			 bit 4 - 2^4
			 bit 3 - 2^3
			 bit 2 - 2^2
			 bit 1 - 2^1
			 bit 0 - 2^0"

    ::= { sc800t3PreviousNearEndEntry 2 }
 

-- ********************************************************************
--  			Previous Far End
-- ********************************************************************
sc800t3PreviousFarEndTable 	OBJECT-TYPE
	 SYNTAX  SEQUENCE OF Sc800t3PreviousFarEndEntry
	 ACCESS  not-accessible
	 STATUS  mandatory
	 DESCRIPTION
		 "Gives the statistic count for the previous
		  15 minute interval."
	 ::= { sc800t3Performance 11 }


sc800t3PreviousFarEndEntry 	OBJECT-TYPE
	 SYNTAX  Sc800t3PreviousFarEndEntry
	 ACCESS  not-accessible
	 STATUS  mandatory
	 DESCRIPTION
		 "An entry in the sc800t3 PreviousFarEnd table."
	 INDEX   { sc800t3PreviousFarEndIndex }
	 ::= { sc800t3PreviousFarEndTable 1 }

Sc800t3PreviousFarEndEntry ::=
    SEQUENCE {
        sc800t3PreviousFarEndIndex  	SCinstance,
        sc800t3PreviousFarEndStat	OCTET STRING
 	  }

sc800t3PreviousFarEndIndex 	OBJECT-TYPE
    SYNTAX  SCinstance
    ACCESS  read-only
    STATUS  mandatory
    DESCRIPTION
        "Integer value which uniquely identifies the SC800T3 to which this
         entry is applicable. SCinstance is defined to be SLDi where:
         S (byte value) - physical shelf slot location (01-32)
         L (byte value) - line number (01)
         D (byte value) - drop number (00)
         i (byte value) - interface number (00)"
    ::= { sc800t3PreviousFarEndEntry 1 }

sc800t3PreviousFarEndStat OBJECT-TYPE
	 SYNTAX OCTET STRING (SIZE (8))
	 ACCESS read-only
	 STATUS mandatory
	 DESCRIPTION
		"Returns a bitwise snapshot of the  statistics.

		Octet 1  bit 7 - f/u   
			 bit 6 - Invalid Data Flag
			 bit 5 - n/a
			 bit 4 - n/a
			 bit 3 - n/a
			 bit 2 - 2^9    Errored Seconds (ES)
			 bit 1 - 2^8
			 bit 0 - 2^7 

		Octet 2  bit 7 - f/u   
			 bit 6 - 2^6    Errored Seconds (ES)
			 bit 5 - 2^5 
			 bit 4 - 2^4 
			 bit 3 - 2^3 
			 bit 2 - 2^2 
			 bit 1 - 2^1
			 bit 0 - 2^0

		Octet 3  bit 7 - f/u Severely Errored Seconds (SES)  
			 bit 6 - Invalid Data Flag
			 bit 5 - 2^5
			 bit 4 - 2^4
			 bit 3 - 2^3
			 bit 2 - 2^2
			 bit 1 - 2^1
			 bit 0 - 2^0

		Octet 4  bit 7 - f/u Severely Errored Frames (SAS)  
			 bit 6 - Invalid Data Flag
			 bit 5 - 2^5
			 bit 4 - 2^4
			 bit 3 - 2^3
			 bit 2 - 2^2
			 bit 1 - 2^1
			 bit 0 - 2^0 

		Octet 5  bit 7 - f/u Unavailable Seconds (UAS)  
			 bit 6 - Invalid Data Flag
			 bit 5 - 2^5 
			 bit 4 - 2^4 
			 bit 3 - 2^3 
			 bit 2 - 2^2 
			 bit 1 - 2^1 
			 bit 0 - 2^0

		Octet 6  bit 7 - f/u Code Violations (CV)    	  
			 bit 6 - Invalid Data Flag
			 bit 5 - n/a 
			 bit 4 - n/a 
			 bit 3 - n/a 
			 bit 2 - n/a
			 bit 1 - n/a
			 bit 0 - n/a

		Octet 7  bit 7 - f/u   
			 bit 6 - 2^13	Code Violations (CV)    	
			 bit 5 - 2^12
			 bit 4 - 2^11
			 bit 3 - 2^10
			 bit 2 - 2^9
			 bit 1 - 2^8
			 bit 0 - 2^7

		Octet 8  bit 7 - f/u   
			 bit 6 - 2^6    Code Violations (CV)
			 bit 5 - 2^5
			 bit 4 - 2^4
			 bit 3 - 2^3
			 bit 2 - 2^2
			 bit 1 - 2^1
			 bit 0 - 2^0" 

    ::= { sc800t3PreviousFarEndEntry 2 }

 -- ********************************************************************
 -- GDC Local SC800T3 Alarm Configuration
 -- ********************************************************************

 sc800t3LocalAlarmConfigTable OBJECT-TYPE
     SYNTAX SEQUENCE OF Sc800t3LocalAlarmConfigEntry
     ACCESS not-accessible
     STATUS mandatory
     DESCRIPTION
	 "The sc800t3LocalAlarmConfigTable contains entries that configure 
	 alarm
	 reporting.  The structure of the table is such that alarm
	 configuration is supported on a unit and interface basis, and
	 then on an alarm type basis within the interface.  For
	 simplicity sake alarms, be they unit or interface
	 related, are represented in one table."
     ::= { sc800t3LocalAlarms 1 }

 sc800t3LocalAlarmConfigEntry OBJECT-TYPE
     SYNTAX Sc800t3LocalAlarmConfigEntry
     ACCESS not-accessible
     STATUS mandatory
     DESCRIPTION
	 "An entry in the GDC Local Alarm Configuration table."
     INDEX { sc800t3LocalAlarmConfigIndex }
     ::= { sc800t3LocalAlarmConfigTable 1 }

 Sc800t3LocalAlarmConfigEntry ::=
     SEQUENCE {
	 sc800t3LocalAlarmConfigIndex
	     SCinstance,
	 sc800t3OOF
	     INTEGER,
	 sc800t3AISLOCAL
	     INTEGER,
	 sc800t3TIMLOS
	     INTEGER,
	 sc800t3TXDLOS
	     INTEGER,
	 sc800t3RXDLOS
	     INTEGER,
	 sc800t3LOS
	     INTEGER,
	 sc800t3TPSFAIL
	     INTEGER,
	 sc800t3BPSFAIL
	     INTEGER,
	 sc800t3DTECLKLOS
	     INTEGER,
	 sc800t3DTERDYLOS
	     INTEGER,
	 sc800t3RAILOCAL
	     INTEGER,
	 sc800t3THRESHESL
	     INTEGER,
         sc800t3THRESHES
             INTEGER,
         sc800t3THRESHSES
             INTEGER,
         sc800t3THRESHSAS
             INTEGER,
         sc800t3THRESHUAS
             INTEGER,
         sc800t3THRESHCV
             INTEGER
     }

 sc800t3LocalAlarmConfigIndex OBJECT-TYPE
     SYNTAX SCinstance
     ACCESS read-only
     STATUS mandatory
     DESCRIPTION
	 "The index value which uniquely identifies the interface to
	 which this entry is applicable."
     ::= { sc800t3LocalAlarmConfigEntry 1 }

 sc800t3OOF       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 2 }

 sc800t3AISLOCAL       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 3 }

 sc800t3TIMLOS       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 4 }

 sc800t3TXDLOS       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 5 }

 sc800t3RXDLOS       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 6 }

 sc800t3LOS       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 7 }

 sc800t3TPSFAIL       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 8 }

 sc800t3BPSFAIL       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 9 }

 sc800t3DTECLKLOS       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 10 }

 sc800t3DTERDYLOS       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 11 }

 sc800t3RAILOCAL    OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 12 }

 sc800t3THRESHESL    OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 13 }

 sc800t3THRESHES    OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 14 }

 sc800t3THRESHSES    OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 15 }

 sc800t3THRESHSAS    OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 16 }

 sc800t3THRESHUAS    OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 17 }

 sc800t3THRESHCV    OBJECT-TYPE
	SYNTAX  INTEGER {
			disabled(1),
			enabledMajor(2),
			enabledMinor(3)
			}
	ACCESS  read-write
	STATUS  mandatory
	DESCRIPTION
		"Disables or enables the alarm on the Major buss or Minor
		buss."
     ::= { sc800t3LocalAlarmConfigEntry 18 }

-- ****************************************************************************
--                       mib definitions end
-- ****************************************************************************

END
