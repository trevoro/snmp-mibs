-- ZyXEL Communications Corporation
-- Private Enterprise MIB definition 
  
-- This file describes the ZyXEL Communications Corporation Enterprise MIB.
-- It contains ZyXEL products OIDs, and common managed objects.

-- $Log: ZYXEL-STORM-CONTROL-MIB.mib $ 
-- Revision 1.4  2012/09/19 07:46:51  Kevin 
-- if it's leaf node, revise the vender name from zyxel to zy 
-- Revision 1.3  2012/08/22 09:49:20  Kevin 
-- clean warning for SNMPc 
-- Revision 1.2  2012/07/05 06:24:41  Kevin 
-- 1. upgrade from SNMP to SNMPv2  
-- 2. clean warning 
-- Revision 1.1  2012/05/30 07:50:47  Kevin 
-- Initial revision 

ZYXEL-STORM-CONTROL-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelStormControl MODULE-IDENTITY
		LAST-UPDATED	"201207010000Z"    
		ORGANIZATION "Enterprise Solution ZyXEL"     
		CONTACT-INFO
			""	   
		DESCRIPTION
			"The subtree for storm control"
		::= { esMgmt 78 }

	zyxelStormControlSetup   	OBJECT IDENTIFIER ::= { zyxelStormControl 1 }
  
-- *******************************************************************
-- *
-- * zyxelStormControlSetup
-- *
-- *******************************************************************

-- zyxelStromControlState
		zyStromControlState OBJECT-TYPE
        SYNTAX  EnabledStatus
        MAX-ACCESS  read-write
        STATUS  current
        DESCRIPTION
                    "Enabled/Disabled traffic storm control on the switch."
        ::= { zyxelStormControlSetup 1 }

-- zyxelStromControlPortTable
        zyxelStromControlPortTable OBJECT-TYPE
        SYNTAX	SEQUENCE OF ZyxelStromControlPortEntry
        MAX-ACCESS  not-accessible
        STATUS  current
        DESCRIPTION
                 	"The table cantains storm control port configuration."
        ::= { zyxelStormControlSetup 2 }
        
		zyxelStromControlPortEntry OBJECT-TYPE
        SYNTAX	ZyxelStromControlPortEntry
        MAX-ACCESS	not-accessible
        STATUS	current
        DESCRIPTION    	
					"A entry cantains storm control port configuration."
        INDEX          	{ dot1dBasePort }
        ::= { zyxelStromControlPortTable 1 }

        ZyxelStromControlPortEntry ::=
           SEQUENCE {
        	zyStromControlPortBroadcastState	EnabledStatus,
			zyStromControlPortBroadcastRate		INTEGER,
			zyStromControlPortMulticastState	EnabledStatus,
			zyStromControlPortMulticastRate		INTEGER,
			zyStromControlPortDlfState			EnabledStatus,
			zyStromControlPortDlfRate			INTEGER
           }

        zyStromControlPortBroadcastState OBJECT-TYPE
        SYNTAX  EnabledStatus
        MAX-ACCESS  read-write
        STATUS  current
        DESCRIPTION
                      	"Enabled/Disabled broadcast rate limit on the indicated port."
        ::= { zyxelStromControlPortEntry 1 }
        
        zyStromControlPortBroadcastRate OBJECT-TYPE
        SYNTAX  INTEGER
        MAX-ACCESS  read-write
        STATUS  current
        DESCRIPTION
                      	"Allowed broadcast rate in pkts/s. 
						For FE port, the maximum value is 148800 pkts/s. 
						For GE port, the maximum value is 262143 pkts/s."
        ::= { zyxelStromControlPortEntry 2 }
        
        zyStromControlPortMulticastState OBJECT-TYPE
        SYNTAX  EnabledStatus
        MAX-ACCESS  read-write
        STATUS  current
        DESCRIPTION
                      	"Enabled/Disabled multicast rate limit on the indicated port."
        ::= { zyxelStromControlPortEntry 3 }

        zyStromControlPortMulticastRate OBJECT-TYPE
        SYNTAX  INTEGER
        MAX-ACCESS  read-write
        STATUS  current
        DESCRIPTION
                      	"Allowed mullticast rate in pkts/s. 
						For FE port, the maximum value is 148800 pkts/s. 
						For GE port, the maximum value is 262143 pkts/s."
        ::= { zyxelStromControlPortEntry 4 }

        zyStromControlPortDlfState OBJECT-TYPE
        SYNTAX  EnabledStatus
        MAX-ACCESS  read-write
        STATUS  current
        DESCRIPTION
                      	"Enabled/Disabled destination lookup failure frames rate limit on the indicated port."
        ::= { zyxelStromControlPortEntry 5 }

        zyStromControlPortDlfRate OBJECT-TYPE
        SYNTAX  INTEGER
        MAX-ACCESS  read-write
        STATUS  current
        DESCRIPTION
                      	"Allowed destination lookup failure frames rate in pkts/s. 
						For FE port, the maximum value is 148800 pkts/s. 
						For GE port, the maximum value is 262143 pkts/s."
        ::= { zyxelStromControlPortEntry 6 }


END
