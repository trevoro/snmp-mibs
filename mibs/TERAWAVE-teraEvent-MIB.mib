TERAWAVE-teraEvent-MIB DEFINITIONS ::= BEGIN
        -- Created by sml2mib compiler 
        IMPORTS

	Counter32 FROM SNMPv2-SMI
 enterprises,  OBJECT-TYPE,  Counter,  Gauge,  TimeTicks
        FROM RFC1155-SMI;

terawave OBJECT IDENTIFIER ::=  { enterprises 4513 }

teratraps OBJECT IDENTIFIER ::=  { terawave 1 }

teraAlarms OBJECT IDENTIFIER ::=  { teratraps 1 }

     -- teraLocalEventTable

teraLocalEventTable OBJECT-TYPE
     SYNTAX SEQUENCE OF TeraLocalEventTableEntryType
     ACCESS not-accessible
     STATUS mandatory
     DESCRIPTION
          " table teraLocalEventTable"
     ::= { teraAlarms 11 }

teraLocalEventTableEntry OBJECT-TYPE
          SYNTAX TeraLocalEventTableEntryType
          ACCESS not-accessible
          STATUS mandatory
          DESCRIPTION
               " table entry teraLocalEventTableEntry "
          INDEX {                   teraLocalEventIndex }
     ::= { teraLocalEventTable 1 }

TeraLocalEventTableEntryType ::= SEQUENCE {
          teraLocalEventIndex   
             Counter32 (1..65535),
          teraLocalEventPort   
             INTEGER,
          teraLocalEventPortType   
             INTEGER,
          teraLocalEventCardType   
             INTEGER,
          teraLocalEventSlot   
             INTEGER,
          teraLocalEventPhysPort   
             INTEGER,
          teraLocalEventType   
             INTEGER,
          teraLocalEventSeverity   
             INTEGER,
          teraLocalEventTime   
             OCTET STRING,
          teraLocalEventMessage   
             OCTET STRING,
          teraLocalEventTimeInSecs   
             INTEGER
}

teraLocalEventIndex OBJECT-TYPE
          SYNTAX Counter32 (1..65535)
          ACCESS read-only
          STATUS mandatory
          DESCRIPTION
               ""
          ::= { teraLocalEventTableEntry 1 }

teraLocalEventPort OBJECT-TYPE
          SYNTAX INTEGER
          ACCESS read-only
          STATUS mandatory
          DESCRIPTION
               ""
          ::= { teraLocalEventTableEntry 2 }

teraLocalEventPortType OBJECT-TYPE
          SYNTAX INTEGER
          ACCESS read-only
          STATUS mandatory
          DESCRIPTION
               ""
          ::= { teraLocalEventTableEntry 3 }

teraLocalEventCardType OBJECT-TYPE
          SYNTAX INTEGER
          ACCESS read-only
          STATUS mandatory
          DESCRIPTION
               ""
          ::= { teraLocalEventTableEntry 4 }

teraLocalEventSlot OBJECT-TYPE
          SYNTAX INTEGER
          ACCESS read-only
          STATUS mandatory
          DESCRIPTION
               ""
          ::= { teraLocalEventTableEntry 5 }

teraLocalEventPhysPort OBJECT-TYPE
          SYNTAX INTEGER
          ACCESS read-only
          STATUS mandatory
          DESCRIPTION
               ""
          ::= { teraLocalEventTableEntry 6 }

teraLocalEventType OBJECT-TYPE
          SYNTAX INTEGER
          ACCESS read-only
          STATUS mandatory
          DESCRIPTION
               ""
          ::= { teraLocalEventTableEntry 7 }

teraLocalEventSeverity OBJECT-TYPE
          SYNTAX INTEGER
                  {
                  nominal(1),
                  informational(2),
                  minor(3),
                  major(4),
                  critical(5)
                  }
          ACCESS read-only
          STATUS mandatory
          DESCRIPTION
               ""
          ::= { teraLocalEventTableEntry 8 }

teraLocalEventTime OBJECT-TYPE
          SYNTAX OCTET STRING
          ACCESS read-only
          STATUS mandatory
          DESCRIPTION
               ""
          ::= { teraLocalEventTableEntry 9 }

teraLocalEventMessage OBJECT-TYPE
          SYNTAX OCTET STRING
          ACCESS read-only
          STATUS mandatory
          DESCRIPTION
               ""
          ::= { teraLocalEventTableEntry 10 }

teraLocalEventTimeInSecs OBJECT-TYPE
          SYNTAX INTEGER
          ACCESS read-only
          STATUS mandatory
          DESCRIPTION
               ""
          ::= { teraLocalEventTableEntry 11 }

     -- teraLocalRmonEventTable

teraLocalRmonEventTable OBJECT-TYPE
     SYNTAX SEQUENCE OF TeraLocalRmonEventTableEntryType
     ACCESS not-accessible
     STATUS mandatory
     DESCRIPTION
          " table teraLocalRmonEventTable"
     ::= { teraAlarms 12 }

teraLocalRmonEventTableEntry OBJECT-TYPE
          SYNTAX TeraLocalRmonEventTableEntryType
          ACCESS not-accessible
          STATUS mandatory
          DESCRIPTION
               " table entry teraLocalRmonEventTableEntry "
          INDEX {                   teraLocalRmonEventIndex }
     ::= { teraLocalRmonEventTable 1 }

TeraLocalRmonEventTableEntryType ::= SEQUENCE {
          teraLocalRmonEventIndex   
             Counter32 (1..65535),
          teraLocalRmonEventAlarmIndex   
             Counter32,
          teraLocalRmonEventTrapType   
             INTEGER,
          teraLocalRmonEventSampleValue   
             INTEGER,
          teraLocalRmonEventSampeThreshold   
             INTEGER,
          teraLocalRmonEventTime   
             OCTET STRING,
          teraLocalRmonEventTimeInSecs   
             INTEGER
}

teraLocalRmonEventIndex OBJECT-TYPE
          SYNTAX Counter32 (1..65535)
          ACCESS read-only
          STATUS mandatory
          DESCRIPTION
               ""
          ::= { teraLocalRmonEventTableEntry 1 }

teraLocalRmonEventAlarmIndex OBJECT-TYPE
          SYNTAX Counter32
          ACCESS read-only
          STATUS mandatory
          DESCRIPTION
               ""
          ::= { teraLocalRmonEventTableEntry 2 }

teraLocalRmonEventTrapType OBJECT-TYPE
          SYNTAX INTEGER
                  {
                  rising(1),
                  falling(2),
                  both(3)
                  }
          ACCESS read-only
          STATUS mandatory
          DESCRIPTION
               ""
          ::= { teraLocalRmonEventTableEntry 3 }

teraLocalRmonEventSampleValue OBJECT-TYPE
          SYNTAX INTEGER
          ACCESS read-only
          STATUS mandatory
          DESCRIPTION
               ""
          ::= { teraLocalRmonEventTableEntry 4 }

teraLocalRmonEventSampeThreshold OBJECT-TYPE
          SYNTAX INTEGER
          ACCESS read-only
          STATUS mandatory
          DESCRIPTION
               ""
          ::= { teraLocalRmonEventTableEntry 5 }

teraLocalRmonEventTime OBJECT-TYPE
          SYNTAX OCTET STRING
          ACCESS read-only
          STATUS mandatory
          DESCRIPTION
               ""
          ::= { teraLocalRmonEventTableEntry 6 }

teraLocalRmonEventTimeInSecs OBJECT-TYPE
          SYNTAX INTEGER
          ACCESS read-only
          STATUS mandatory
          DESCRIPTION
               ""
          ::= { teraLocalRmonEventTableEntry 7 }

     -- teraLocalTcaEventTable

teraLocalTcaEventTable OBJECT-TYPE
     SYNTAX SEQUENCE OF TeraLocalTcaEventTableEntryType
     ACCESS not-accessible
     STATUS mandatory
     DESCRIPTION
          " table teraLocalTcaEventTable"
     ::= { teraAlarms 13 }

teraLocalTcaEventTableEntry OBJECT-TYPE
          SYNTAX TeraLocalTcaEventTableEntryType
          ACCESS not-accessible
          STATUS mandatory
          DESCRIPTION
               " table entry teraLocalTcaEventTableEntry "
          INDEX {                   teraLocalTcaEventIndex }
     ::= { teraLocalTcaEventTable 1 }

TeraLocalTcaEventTableEntryType ::= SEQUENCE {
          teraLocalTcaEventIndex   
             Counter32 (1..65535),
          teraLocalTcaEventAlarmIndex   
             Counter32,
          teraLocalTcaEventTrapType   
             INTEGER,
          teraLocalTcaEventSampleValue   
             INTEGER,
          teraLocalTcaEventSampeThreshold   
             INTEGER,
          teraLocalTcaEventTime   
             OCTET STRING,
          teraLocalTcaEventTimeInSecs   
             INTEGER
}

teraLocalTcaEventIndex OBJECT-TYPE
          SYNTAX Counter32 (1..65535)
          ACCESS read-only
          STATUS mandatory
          DESCRIPTION
               ""
          ::= { teraLocalTcaEventTableEntry 1 }

teraLocalTcaEventAlarmIndex OBJECT-TYPE
          SYNTAX Counter32
          ACCESS read-only
          STATUS mandatory
          DESCRIPTION
               ""
          ::= { teraLocalTcaEventTableEntry 2 }

teraLocalTcaEventTrapType OBJECT-TYPE
          SYNTAX INTEGER
                  {
                  rising(1),
                  falling(2),
                  both(3)
                  }
          ACCESS read-only
          STATUS mandatory
          DESCRIPTION
               ""
          ::= { teraLocalTcaEventTableEntry 3 }

teraLocalTcaEventSampleValue OBJECT-TYPE
          SYNTAX INTEGER
          ACCESS read-only
          STATUS mandatory
          DESCRIPTION
               ""
          ::= { teraLocalTcaEventTableEntry 4 }

teraLocalTcaEventSampeThreshold OBJECT-TYPE
          SYNTAX INTEGER
          ACCESS read-only
          STATUS mandatory
          DESCRIPTION
               ""
          ::= { teraLocalTcaEventTableEntry 5 }

teraLocalTcaEventTime OBJECT-TYPE
          SYNTAX OCTET STRING
          ACCESS read-only
          STATUS mandatory
          DESCRIPTION
               ""
          ::= { teraLocalTcaEventTableEntry 6 }

teraLocalTcaEventTimeInSecs OBJECT-TYPE
          SYNTAX INTEGER
          ACCESS read-only
          STATUS mandatory
          DESCRIPTION
               ""
          ::= { teraLocalTcaEventTableEntry 7 }

END
