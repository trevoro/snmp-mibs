-- *****************************************************************************
-- Unisphere-Data-PPPoE-Profile-CONF
--
-- SNMP Agent Capabilities definitions for the PPPoE Profile MIB.
--
-- Copyright (c) 2001, 2002 Unisphere Networks, Inc.  All rights reserved.
-- *****************************************************************************

Unisphere-Data-PPPoE-Profile-CONF DEFINITIONS ::= BEGIN

IMPORTS
    MODULE-IDENTITY
        FROM SNMPv2-SMI
    AGENT-CAPABILITIES
        FROM SNMPv2-CONF
    usdProfileAgents
        FROM Unisphere-Data-Agents
    usdPppoeProfileGroup, usdPppoeProfileGroup2, usdPppoeProfileGroup3
        FROM Unisphere-Data-PPPOE-PROFILE-MIB;

usdPppoeProfileAgent MODULE-IDENTITY
    LAST-UPDATED "200208152038Z"  -- 15-Aug-02 04:38 PM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the PPPoE Profile component of
        the SNMP agent in the Unisphere Data Routing Switch family of products."
    -- Revision History
    REVISION    "200208152038Z"  -- 15-Aug-02 04:38 PM EDT  - RX 4.0
    DESCRIPTION
        "Added PADI flag and packet trace support."
    REVISION    "200205311821Z"  -- 31-May-02 02:21 PM EDT  - RX 3.2
    DESCRIPTION
        "The initial release of this management information module."
    ::= { usdProfileAgents 4 }


-- *****************************************************************************
-- PPPoE Profile agent capabilities
-- *****************************************************************************
usdPppoeProfileAgentV1 AGENT-CAPABILITIES
    PRODUCT-RELEASE
        "Version 1 of the PPPoE Profile component of the Unisphere Routing
        Switch SNMP agent.  This version of the PPPoE Profile component was
        supported in the Unisphere RX 3.0 and 3.1 system releases."
    STATUS      obsolete
    DESCRIPTION
        "The MIB supported by the SNMP agent for the PPPoE Profile application
        in the Unisphere Routing Switch.  These capabilities became obsolete
        when the duplicate MAC address indicator and AC-NAME were added."
    SUPPORTS    Unisphere-Data-PPPOE-PROFILE-MIB
        INCLUDES  {
            usdPppoeProfileGroup }
    ::= { usdPppoeProfileAgent 1 }

usdPppoeProfileAgentV2 AGENT-CAPABILITIES
    PRODUCT-RELEASE
        "Version 2 of the PPPoE Profile component of the Unisphere Routing
        Switch SNMP agent.  This version of the PPPoE Profile component was
        supported in the Unisphere RX 3.2 and subsequent 3.x system releases."
    STATUS      obsolete
    DESCRIPTION
        "The MIB supported by the SNMP agent for the PPPoE Profile application
        in the Unisphere Routing Switch.  These capabilities became obsolete
        when support was added for PADI flag and packet trace."
    SUPPORTS    Unisphere-Data-PPPOE-PROFILE-MIB
        INCLUDES  {
            usdPppoeProfileGroup2 }
    ::= { usdPppoeProfileAgent 2 }

usdPppoeProfileAgentV3 AGENT-CAPABILITIES
    PRODUCT-RELEASE
        "Version 3 of the PPPoE Profile component of the Unisphere Routing
        Switch SNMP agent.  This version of the PPPoE Profile component is
        supported in the Unisphere RX 4.0 and subsequent system releases."
    STATUS      current
    DESCRIPTION
        "The MIB supported by the SNMP agent for the PPPoE Profile application
        in the Unisphere Routing Switch."
    SUPPORTS    Unisphere-Data-PPPOE-PROFILE-MIB
        INCLUDES  {
            usdPppoeProfileGroup3 }
    ::= { usdPppoeProfileAgent 3 }

END
