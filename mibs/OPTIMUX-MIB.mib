OPTIMUX-MIB 	DEFINITIONS ::= BEGIN
--Title:    OPTIMUX   MIB
--
-- Copyright 1993 RAD Data Communications, Ltd.
-- All Rights Reserved.  
-- It is RAD's intent to encourage the widespread use of
-- this Specification in connection with the management of
-- RAD products. RAD grants vendors, end-users,
-- and other interested parties a non-exclusive license to
-- use this Specification in connection with the management
-- of RAD products.
-- This Specification is supplied "as is," and RAD makes
-- no warranty, either express or implied, as to the use,
-- operation, condition, or performance of the Specification.
IMPORTS
	DisplayString	                    FROM RFC1213-MIB
 	enterprises, IpAddress			                FROM RFC1155-SMI
	OBJECT-TYPE                     	FROM RFC-1212
	TRAP-TYPE                           FROM RFC-1215
  ifIndex, InterfaceIndex, ifAlias				FROM IF-MIB
 	dsx1LoopbackStatus, dsx1LineStatus, dsx1LineStatusLastChange 					FROM DS1-MIB
	dsx3LoopbackStatus, dsx3LineStatus                  FROM DS3-MIB
	radSysWanEvents, agnLed, agnIndication, atmInterfaceAlarmStatus, alarmSeverity, alarmState				FROM RAD-MIB
	NOTIFICATION-TYPE, OBJECT-IDENTITY, Integer32, Counter32 FROM SNMPv2-SMI
	RowStatus, MacAddress, TAddress FROM SNMPv2-TC
	SnmpAdminString FROM SNMP-FRAMEWORK-MIB
	VlanIndex FROM SWL2MGMT-MIB
	MmAliasTag, MmAliasAddress, MmTAddressTag, MmEndpointID, MmH323EndpointType, MmGatekeeperID FROM MULTI-MEDIA-MIB-TC;
	--radWan, agnIndication               FROM RAD-GEN-MIB;
--                RAD-OPTIMUX MIB   
--Title:     RAD's   OPTIMUX PRODUCT MIB
--Version:   2.0
--Date:      14/01/97
--By:        Michele Hallak
--File:      optimux2.txt
--
rad OBJECT IDENTIFIER ::= { enterprises 164 }
radWan       OBJECT IDENTIFIER ::= { rad 3 }  --rad WAN Tree
radGen        OBJECT IDENTIFIER ::= { rad 6}  --General information
--Last update: 19-Sep-2004 by Smadar Tauber
optimux OBJECT IDENTIFIER ::= { radWan 5 }
-- One Optimux is sometimes connected to another optimux (or other device)
-- via its link. Therefore, in some cases, the SNMP agent sitting on
-- one device is responsible of the second (remote)
-- device. This table supplies information for both
-- devices, while the first is the local one and the second
-- is the remote one.
optMxConfigTable OBJECT-TYPE
     SYNTAX  SEQUENCE OF OptMxConfigEntry
     MAX-ACCESS  not-accessible
     STATUS  current
     DESCRIPTION
     "This table contains parameters of configuration
	  for each member of the couple of Optimux."
     ::= { optimux 1 }
 optMxConfigEntry OBJECT-TYPE
     SYNTAX OptMxConfigEntry 
     MAX-ACCESS  not-accessible
     STATUS  current
     DESCRIPTION
         "An entry in the Optimux Config  table."
     INDEX   { optIndex }
     ::= { optMxConfigTable 1 }
     OptMxConfigEntry ::=
              SEQUENCE {
         optIndex   		INTEGER,
	     optHWVersion       DisplayString,
 	     optSWVersion       DisplayString,
         optPSPrimary 		INTEGER,
	     optPSSecondary 	INTEGER,
	     optLinkActive     	InterfaceIndex,
	     optSelectLink      INTEGER,
	     optGrpPayLoadLoop  INTEGER,
	     optGrpClockSource  INTEGER,
	     optRedundancyStatus INTEGER,
	     optRedundancyCnf   INTEGER,
	     optFarEndType      INTEGER,
	     optServiceChEnable INTEGER,  
	     optMaskChAlr       Integer32,
	     optAisEnable       INTEGER,
	     optFarMng          INTEGER,
	     optClockDivision   INTEGER,
	     optDteLoopEnable   INTEGER,
	     optGrpClockSourcePrt Integer32,
	     optIncomingAlarm   INTEGER,
	     optDefChannelSet   INTEGER,
	     optWaitToRestore	Integer32,
	     optEnforcedLink	INTEGER,
	     optFlipUponEvent   Integer32,
		 optHwMaskChAlr     Integer32,
		 optServiceChExist  INTEGER
	        }
optIndex OBJECT-TYPE
SYNTAX  INTEGER {local(1), remote(2) }
MAX-ACCESS  read-only
STATUS  current
DESCRIPTION
"optIndex = 1 is for local Optimux.
 optIndex = 2 is for remote Optimux."
 ::= { optMxConfigEntry 1 }
optHWVersion OBJECT-TYPE
   SYNTAX  DisplayString
   MAX-ACCESS  read-only
   STATUS  current
   DESCRIPTION
    "HW Version of the device."
    ::= { optMxConfigEntry 2 }
optSWVersion OBJECT-TYPE
    SYNTAX  DisplayString
    MAX-ACCESS  read-only
    STATUS  current
    DESCRIPTION
     "SW Version of the device."
     ::= { optMxConfigEntry 3 }
optPSPrimary OBJECT-TYPE
    SYNTAX  INTEGER {
		unknown(1),
		fault(3),
		active(4),
		none(6)
    }
    MAX-ACCESS  read-only
    STATUS  current
    DESCRIPTION
     "The status of the primary Power Supply Unit."
    DEFVAL { active }
     ::= { optMxConfigEntry 4 }
optPSSecondary OBJECT-TYPE
     SYNTAX  INTEGER {
		unknown(1),
		fault(3),
		active(4),
		none(6)
      }
     MAX-ACCESS  read-only
     STATUS  current
     DESCRIPTION
     "The status of the secondary Power Supply Unit."
     DEFVAL { none }
              ::= { optMxConfigEntry 5 }
optLinkActive OBJECT-TYPE
     SYNTAX  InterfaceIndex
     MAX-ACCESS  read-only
     STATUS  current
     DESCRIPTION
     "This object indicates which link is active. 
      For Optimux-4 it may be: 5, 6 or 105, 106
      For FOMi-E3/T3 it may be: 51, 61 or 151, 161.
      For Optimux-T3 it may be: 51 or 61.
      For Optimux-155/1 refer to product spec." 
      ::= { optMxConfigEntry 6 }
optSelectLink OBJECT-TYPE
     SYNTAX  INTEGER {
		autoredundancy(1),
--		autoWoReturn(4),   not in use for this version of Opt-4-C
		main(5),
		back(6)
     }
     MAX-ACCESS  read-write
     STATUS   current
     DESCRIPTION
     "This object is used by Optimuxes.
	  - For Optimux 4E1/T1 Old Look: 
	    This MIB object enables the user to force the device to use specific link.
        autoredundancy= Main (Link 1) is the default link. When it will fail, the 
                        device will use Backup (Link 2). If Main recovers, it 
                        automatically returns to Main.
        autoWoReturn  = Automatic Without Return. Main (Link 1) is the default link. 
                        When it will fail, the device will use Backup (Link 2). 
                        If Main recovers, it will NOT return to Main. It will 
	                    continue using Backup.
				        This option is supported only by LRS cards.
	    main         =  Forces the device to start immediately use of Main (Link 1),
	                    no matter what is its state and stay there. No Redundancy.
	    back         =  Forces the device to start immediately use of Backup (Link 2),
	                    no matter what is its state and stay there. No Redundancy.
	  - For Optimux-T3, Optimux-155, Optimux-XL and OP-4 (New Look):
	    This MIB object is used to select which Link will be used as MAIN.
		Therefore:
	    autoredundancy - not supported 
	    main = Link A is MAIN (=default).
	    back = Link B is MAIN."
      DEFVAL { autoredundancy }
      ::= { optMxConfigEntry 7 }
optGrpPayLoadLoop OBJECT-TYPE
     SYNTAX  INTEGER {
		off(2), on(3)
     }
     MAX-ACCESS  read-write
     STATUS   current
     DESCRIPTION
    	"Performs payload loop ( remote loop) to 4 E1 channels
         at once."
      DEFVAL { off }
      ::= { optMxConfigEntry 8 }
optGrpClockSource OBJECT-TYPE
     SYNTAX  INTEGER {
	 notApplicable(1), 
	 localInternal(2), 
	 localExternal(3), 
	 loopTiming(4),
	 transparent(5)
     }
     MAX-ACCESS  read-write
     STATUS   current
     DESCRIPTION
     "For Optimux XL:
        If dsx3TransmitClockSource = localTiming(2), then the user
        can configure this field as:
        localInternal(2) = use the internal clock of the device
        localExternal(3) = use the external clock connected to the port
        dedicated to clock.
      For FomiE3/T3 this object is always applicable. 
        localExternal(3) = station clock
        transparent(5)   = the device takes the clock info from the data.
        For FomiE3/T3 with HSSI electrical interface, only the following 
        are valid: localInternal(2) and transparent(5).
      For Optimux-T3 the applicable values are (2), (3), (4).
      For Optimux-155/1 the applicable values are (2), (3), (4), (5)."
      DEFVAL { notApplicable }
      ::= { optMxConfigEntry 9 }
optRedundancyStatus OBJECT-TYPE
     SYNTAX  INTEGER {
	  available(2), notAvailable(3)
     }
     MAX-ACCESS  read-only
     STATUS   current
     DESCRIPTION
     "If there are two modules 'links', then this field
      should be set to available(2). If there is only one
      module 'link', this field should be set to notAvailable(3)."
      DEFVAL { available }
      ::= { optMxConfigEntry 10 }
optRedundancyCnf  OBJECT-TYPE
     SYNTAX  INTEGER {
	off(2), auto(3), manual(4), forcedBU(6)
     }
     MAX-ACCESS  read-write
     STATUS   current
     DESCRIPTION
     "This object is used by Optimux-XL, FomiE3/T3, Optimux-T3 and Optimux-155.
      For Optimux-XL:
        If optRedundancyStatus = notAvailable(3), then this field
        can be off(2) or forcedBU(6). 
         - off(2) = forcedMain:	forces the device to start immediately use of 
                    Main (Link 1), no matter what is its state and stay there
	     - forcedBU(6)  =  forces the device to start immediately use of 
	                       Backup (Link 2),	no matter what is its state and stay there.
						   This value is not supported by Optimux-T3.
        Else, user can configure this field as:
        auto(3) = switch back to main link when valid.
        manual(4) = don't switch back to main link = automatic w/o return.
      For FomiE3/T3 all values are applicable unconditioned.
      For Optimux-T3 and OP-4 New Look, values off(2), auto(3), manual(4) 
        are applicable unconditioned.
      For Optimux-155/1 values off (2) = Protection Lockout, auto (3) and manual (4)"
      DEFVAL { auto }
      ::= { optMxConfigEntry 11 }
optFarEndType  OBJECT-TYPE
     SYNTAX  INTEGER 
     {
	 unknown     (1), 
	 optimux4Sa  (2), 
	 optimux4Card(3),
	 fomiE3T3Sa  (4),
	 fomiE3T3Card(5),
	 optimuxXL16 (6),
	 optimuxXLE1 (7),
	 optimux4E1L (8),
	 optimux4T1L (9),
	 optimuxXLT1 (10),
	 op16E1L	 (11),	-- 19" box
	 op16E1LS	 (12),	-- half 19" box (single)
	 opXLE1		 (13),	-- Optimux-XL New-Look
	 opXLT1		 (14),	-- Optimux-XL New-Look
	 opXL16E1    (15),	-- Optimux-XL New-Look
	 op4E1		 (16),	-- Op-4E1 SA New-Look
	 op4T1		 (17),	-- Op-4T1 SA New-Look
	 fdsl101     (18),
	 fdsl201     (19),
	 notApplicable(255)
     }
     MAX-ACCESS  read-only
     STATUS   current
     DESCRIPTION
     "Far-End type of product.
      This object is especially relevant for the local optimux.
	  notApplicable - for devices that don't have a far-end unit."
      ::= { optMxConfigEntry 12 }
optServiceChEnable  OBJECT-TYPE
     SYNTAX  INTEGER 
     {
     notApplicable(1),
	 disabled  (2), 
	 enabled   (3)
     }
     MAX-ACCESS   read-write
     STATUS   current
     DESCRIPTION
     "Service Channel Enable/Disable for each Optimux (local/remote)."
      ::= { optMxConfigEntry 13 }
optMaskChAlr  OBJECT-TYPE
     SYNTAX  Integer32 
     MAX-ACCESS   read-write
     STATUS   current
     DESCRIPTION
     "Mask Channel Alarm.
      This object is applicable only for Optimux cards.
      The value of this object is a sum of 2**n, where n is a bit assigned to 
      a certain Channel.  Bit='1' means masked.
	  For Optimux-4:
        Bit0: CH1 ; Bit1: CH2 ; Bit2: CH3 ; Bit3: CH4 (Bit='1' means masked).
        Examples:
        - 15 : means that all Channels are masked.
        -  9 : means that Alarms of CH 1 and CH 4 are masked.
      For Optimux-T3:
        Bit0: CH1 ; Bit1: CH2 ; Bit2: CH3 ;.. Bit20: CH21 OR Bit27: CH28.
      For FDSL:
        Bit0..Bit12 : CH1..CH12; Bit13: ETH ; Bit14..Bit15: Uplink1..Uplink2."
      ::= { optMxConfigEntry 14 }
optAisEnable OBJECT-TYPE
      SYNTAX  INTEGER
      {
       notApplicable (1),
       disable       (2),
       enable        (3)
      }            
      MAX-ACCESS  read-write
      STATUS  current
      DESCRIPTION
      "AIS enable/disable.
       notApplicable - for devices that do not support this feature."
      ::= { optMxConfigEntry 15 }
optFarMng  OBJECT-TYPE
      SYNTAX  INTEGER
	      {
		notApplicable (1),
		no            (2),
		yes           (3)
	      }
      MAX-ACCESS  read-write
      STATUS  current
      DESCRIPTION
      "This object is used by Optimux-XL and FomiE3/T3.
       Is there possibility of Far-End Management (no/yes).
       This object is applicable only for the Local device.
       notApplicable - for Remote device and devices that do not support it.
       no -  far-end device is NOT I-Type so it doesn't have a management 
             link to its pair-device.
       yes - far-end device is I-Type so it has a management link to its 
             pair-device."
      ::= { optMxConfigEntry 16 } 
optClockDivision  OBJECT-TYPE
      SYNTAX  INTEGER
	      {
		notApplicable (1),
		noDivision    (2),
		half          (3),
		quarter       (4)
	      }
      MAX-ACCESS  read-write
      STATUS  current
      DESCRIPTION
      "This object is applicable only for FomiE3/T3 having an HSSI Electrical
       interface.
       It gives the possibility of Clock Division, so that Clock Rate will
       be less than T3/E3.
       notApplicable - for a device that does not support it
       noDivision -  Clock stays as is (Internal or Transparent)
       half       - Clock will be half the original (divided by 2)
       quarter    - Clock will be a quarter of the original (divided by 4)."
      ::= { optMxConfigEntry 17 } 
optDteLoopEnable OBJECT-TYPE
      SYNTAX  INTEGER
      {
       notApplicable (1),
       disable       (2),
       enable        (3)
      }            
      MAX-ACCESS  read-write
      STATUS  current
      DESCRIPTION
      "DTE Loop enable/disable (for example loop command requested 
       by router).
	   This object is applicable only for products having HSSI interface.
       notApplicable - for devices that do not support this feature."
      ::= { optMxConfigEntry 18 }
optGrpClockSourcePrt OBJECT-TYPE
     SYNTAX  Integer32
     MAX-ACCESS  read-write
     STATUS   current
     DESCRIPTION
     "This object is applicable for Optimux-T3, when optGrpClockSource=localExternal.
	       It enables the user to select the Channel or Station Clock from which 
	       the Clock is received.
           Valid values:
           0 = notApplicable
           1..28 (= CH1..CH28).
	       73 = Station Clock.
           Only T1 Channels can be used as Clock Source.
      For Optimux-155/1 refer to product spec for port indexing."
      ::= { optMxConfigEntry 19 }
optIncomingAlarm OBJECT-TYPE
     SYNTAX  INTEGER 
     {
      notApplicable (1),
	  off(2), 
	  on(3)
     }
     MAX-ACCESS  read-only
     STATUS  current
     DESCRIPTION
     "State of the Incoming Alarm (On/Off), via Alarm Relay connector.
      This object is applicable only for Optimux-T3."
      ::= { optMxConfigEntry 20 }
optDefChannelSet OBJECT-TYPE
     SYNTAX  INTEGER 
     {
      notApplicable (1),
	  t1(2), 
	  e1(3)
     }
     MAX-ACCESS  read-write
     STATUS  current
     DESCRIPTION
     "Default configuration for all Optimux Channels: T1 or E1.
      This object is applicable only for Optimux-T3."
      ::= { optMxConfigEntry 21 }
optWaitToRestore OBJECT-TYPE
     SYNTAX  Integer32 
     MAX-ACCESS  read-write
     STATUS  current
     DESCRIPTION
     "This parameter defines the time (sec) device has to wait in the redundant 
      state until it goes back to the default Link."
      ::= { optMxConfigEntry 22 }
optEnforcedLink OBJECT-TYPE
     SYNTAX  INTEGER 
     {
      notApplicable (1),
	  noEnforcement(2), 
	  main(3),			   -- Forced Switch
	  backup(4)		   -- Forced Switch
     }
     MAX-ACCESS  read-write
     STATUS  current
     DESCRIPTION
     "This parameter is not applicable when optRedundancyCnf = off.
      It enables user to enforce a Link in spite of the redundancy mechanism.
      Selecting the noEnforcement(2) value cause return to the usual rules of the 
      redundancy mechanism.
      main (3) and backup (4)  are unconditional (force)."
      ::= { optMxConfigEntry 23 }
optFlipUponEvent  OBJECT-TYPE
     SYNTAX       Integer32
     MAX-ACCESS   read-write
     STATUS       current
     DESCRIPTION
     "This object allows user to define if Flip to the other port will
      be performed (or not), for certain possible events.
      Each event is represented by a bit. The value of the object is a sum
      of 2**n, according to the bits having '1' value.
	  '1' - means that Flip should occur due to this event.
      Bit 0 (LSB) = SD (Signal Degraded)."
     ::= { optMxConfigEntry 24 }
optHwMaskChAlr  OBJECT-TYPE
     SYNTAX  Integer32 
     MAX-ACCESS   read-only
     STATUS   current
     DESCRIPTION
     "Mask Channel Alarm done by the HW dip-switches.
      This object is applicable only for Optimux cards.
      The value of this object is a sum of 2**n, where n is a bit assigned to 
      a certain Channel.
	  For Optimux-16E1:
        Bit0: CH1 ; Bit1: CH2 ; Bit2: CH3 ;.. Bit15: CH16 (Bit='1' means masked).
        Examples:
        -  9 : means that Alarms of CH 1 and CH 4 are masked."
      ::= { optMxConfigEntry 25}
optServiceChExist  OBJECT-TYPE
     SYNTAX  INTEGER 
     {
     notApplicable(1),
	 notExist     (2), 
	 exist        (3)
     }
     MAX-ACCESS   read-only
     STATUS   current
     DESCRIPTION
     "Service Channel Existence indication for each Optimux (local/remote)."
      ::= { optMxConfigEntry 26}
-- This table is for XL Optimux, Optimux-T3, FOMi-E3/T3 SA, Optimux-155/1, Optimux 155 DS3
optMxModuleTable OBJECT-TYPE
     SYNTAX  SEQUENCE OF OptMxModuleEntry
     MAX-ACCESS  not-accessible
     STATUS  current
     DESCRIPTION
        "This table defines the type of the module
      enrolled in each slot."
     ::= { optimux 2 }
 optMxModuleEntry OBJECT-TYPE
     SYNTAX OptMxModuleEntry 
     MAX-ACCESS  not-accessible
     STATUS  current
     DESCRIPTION
     "An entry in the Optimux Module  table."
     INDEX   { optMdIdx, optMdSltIdx }
     ::= { optMxModuleTable 1 }
 OptMxModuleEntry ::=
              SEQUENCE {
 		optMdIdx	           INTEGER,
	 	optMdSltIdx 	       Integer32,
 		optMdType 	           INTEGER,
	    optMdHWVersion         DisplayString,
	    optMdModLed 	       OCTET STRING,
	    optMdWaveLength        INTEGER,
	    optMdTimingMode	       INTEGER,
	    optMdStatusIndication  Integer32 
	          }
 optMdIdx OBJECT-TYPE
 SYNTAX  INTEGER {local(1), remote(2) }
 MAX-ACCESS  read-only
 STATUS  current
 DESCRIPTION
 " optMdIdx = 1 is for local Optimux.
   optMdIdx = 2 is for remote Optimux."
  ::= { optMxModuleEntry 1 }
 optMdSltIdx OBJECT-TYPE
    SYNTAX  Integer32
    MAX-ACCESS  read-only
    STATUS  current
    DESCRIPTION
     "For Optimux XL:
        Slot A = 1, Slot B = 2, Slot C = 3, Slot D = 4,
        Slot Link = 5, Slot BU = 6 .
      For FomiE3/R3:
        Slot of Station Clock = 3, Slot of Electrical Link = 4,
        Slot of Optical Main Link = 5, Slot of Optical Backup Link = 6 .
      For Optimux-T3:
        Slot of Station Clock (internal card)= 3, Slot A = 5, Slot B = 6.
      For Optimux-155/1:
        E1/T1 Slot A - 1, E1/T1 Slot B- 2, LINK-A - 5, LINK-B - 6
        I/O-1 - 11, I/O-2 -12 ...I/O-6 - 16
      For Optimux-155 DS3:
        Common Logic+E3/T3 Slot A - 1, Common Logic+E3/T3 Slot B- 2, LINK-A - 5, LINK-B - 6"       
     ::= { optMxModuleEntry 2 }
optMdType OBJECT-TYPE
    SYNTAX  INTEGER {
		unknown(1),
		noModule(2),
		e3linkCX34(3),
		e3linkOPT1(4),
		t3linkOPT1(5),
		eth1Port(6),
		e1FourUTP(7),
		e1TwoPort(8),
		e1TwoUB(9),
		t1FourPort(10),
		t1TwoPort(11),
		e1FourRJ45(12),  -- special for XL/16
		e1FourBNC(13),   -- special for XL/16
		e1FourMiniBNC(14),
		sfLink(15),      -- single fiber
		stationClk(16),  -- for E1/E3 products only (not for XL/T1)
		hssi(17),          
		stationClkT3(18),  -- for FOMi-T3 and Optimux-T3 only
		t3linkCX45(19),    -- for FOMi-T3 and Optimux-T3 only
		hs4(20),		   -- for HSM with 4 ports
		hs2(21),		   -- for HSM with 2 ports
		hs1(22),		   -- for HSM with 1 port
		hs1x8M(23),		   -- for HSM with 1 port and 8M
		fastEth(24), 	   -- for fast ethernet with 1 port
		nX64(25),		   -- for N x 64 E1 module
		nX64AndUnbalanced2E1(26), -- N X 64 and unbalanced 2 E1 ports
		nX64AndBalanced2E1(27), -- N X 64 and balanced 2 E1 ports
		nX64T1(28),		   
		nX64T1AndUnbalanced2T1(29), -- N X 64 T1 and unbalanced 2 T1 ports
		nX64T1AndBalanced2T1(30), -- N X 64 T1 and balanced 2 T1 ports
        ds1channels    (31),-- E1/T1 ports of TELCO connector (Balanced)
        op155Fiber   (32),-- OP-155-1 & OP-155-3 Fiber link
        op155SingleFiber(33),-- OP-155-1 Single Fiber Link
        op155coax    (34),-- OP-155-1 & OP-155-3 Coax Link
        op63e1       (35),-- Optimux 155/1 63 E1 main access card
		op84t1       (36),-- Optimux 155/1 84 T1 main access card
 	    op155Ds3Cl   (37),-- Optimux 155/3 Common Logic card with E3 or T3
		ds1channelsUnbalanced (38), -- E1/T1 ports of TELCO connector (Unbalanced)
		fastEthNew(39) 	   -- for new HW fast ethernet with 1 port
	   					}
    MAX-ACCESS  read-only
    STATUS  current
    DESCRIPTION
     "Module Type and number of connectors."
     ::= { optMxModuleEntry 3 }
optMdHWVersion OBJECT-TYPE
    SYNTAX  DisplayString
    MAX-ACCESS  read-only
    STATUS  current
    DESCRIPTION
     "HW Version of the module."
     ::= { optMxModuleEntry 4 }
optMdModLed OBJECT-TYPE
    SYNTAX  OCTET STRING
    MAX-ACCESS  read-only
    STATUS  current
    DESCRIPTION
     "The meaning of each bit depends on the module type."
     ::= { optMxModuleEntry 5 }
optMdWaveLength OBJECT-TYPE
    SYNTAX  INTEGER {
		notApplicable(1),
		nm850(2),
		nm1300(3),
		nm1300Laser(4),
		nm1550Laser(5)
	}
    MAX-ACCESS  read-only
    STATUS  current
    DESCRIPTION
     "Wave Length of T3/E3 Optical Links in [nm] and specification if Laser or not."
     ::= { optMxModuleEntry 6 }
optMdTimingMode OBJECT-TYPE
    SYNTAX  INTEGER {
		notApplicable(1),
		internal(2),
		external(3),
		lbt(4)		
					}
    MAX-ACCESS  read-write
    STATUS  current
    DESCRIPTION
     "The Module Timing mode."
     ::= { optMxModuleEntry 7 }
optMdStatusIndication OBJECT-TYPE
     SYNTAX  Integer32
     MAX-ACCESS  read-only
     STATUS   current
     DESCRIPTION
     "Indication of Alarm and test status of 
      all interfaces served  by a module.
      For Optimux155,  Each interface will be represented by 2 
	  bits  where the 1st  bit (right) will specify alarm status
	  and the 2nd bit will specify test status.
      e.g
      00 - normal
      01 - alarm active
      11 - alarm active + testing
      10 - testing
      For bits assignment per interface refer to product spec."
      ::= { optMxModuleEntry 8 }
-- This table is for Optimux T3 that can be in a ring
optimuxRing OBJECT IDENTIFIER  ::=  {optimux 3}
 optFramerPortTable		OBJECT-TYPE
     SYNTAX  SEQUENCE OF OptFramerPortEntry
     MAX-ACCESS  not-accessible
     STATUS  current
     DESCRIPTION
        "This table defines the connection of every ch of the framer."
     ::= {optimuxRing 1}
optFramerPortEntry OBJECT-TYPE
     SYNTAX OptFramerPortEntry 
     MAX-ACCESS  not-accessible
     STATUS  current
     DESCRIPTION
     "An entry in the Optimux Framer port Connections  table."
     INDEX   { optFramerPortIdx }
     ::= { optFramerPortTable 1 }
OptFramerPortEntry ::=
              SEQUENCE {
 		optFramerPortIdx	    Integer32,
	 	optFramerPortConn 		Integer32,
		optFramerPortType		INTEGER,
		optFramerPortFeIpAddr	IpAddress
 	   	    	        }
optFramerPortIdx OBJECT-TYPE
    SYNTAX  Integer32
    MAX-ACCESS  read-only
    STATUS  current
    DESCRIPTION
    " The channel of the Framer. Valid values:1..31."
     ::= { optFramerPortEntry 1 }
optFramerPortConn OBJECT-TYPE
    SYNTAX  Integer32
    MAX-ACCESS  read-write
    STATUS  current
    DESCRIPTION
    "This parameter defines the Framer channel connection.
     The values will be as follows:
     Loop(1),Ch1(2),Ch2(3)....,Ch28(29)."
    ::= { optFramerPortEntry 2 }
optFramerPortType OBJECT-TYPE
    SYNTAX  INTEGER{
	notApplicable (1),
	e1			  (2),
	t1			  (3)
	}			
    MAX-ACCESS  read-write
    STATUS  current
    DESCRIPTION
     "This parameter defines the Framer port (E1 or T1)."
     ::= { optFramerPortEntry 3 }
optFramerPortFeIpAddr	OBJECT-TYPE
   SYNTAX  	IpAddress
   MAX-ACCESS  read-write
   STATUS  current
   DESCRIPTION
   "The IP Address of the opposite optimux in the ring,which this channel connected to."
     ::= { optFramerPortEntry 4 }	
optFramerConnChanges 	OBJECT-TYPE
	SYNTAX  			Integer32
	MAX-ACCESS  		read-write
	STATUS 				current
	DESCRIPTION
	"The number of changes in Framer connection table that occured 
	 since last time there was a reset to this parameter"
	::= {optimuxRing 2}
optRing 	OBJECT-TYPE
	SYNTAX  INTEGER {
	pointToPoint(2),
	ring(3),
	drop(4)
	}
	MAX-ACCESS  read-only
	STATUS 		current
	DESCRIPTION
	"Indication about Optimux special behavior:
	pointToPoint(2): regular operation mode (Point to Point).
	ring(3): this optimux is part of a ring.
	operations made on this device may affect other optimuxes in the Ring and vice versa.
	drop(4): enables connection between T3 tributary channel and physical E1/T1 port.
	In this mode there may be no connection between this Optimux and another Optimux
	While working in this mode optimux CANNOT be in PTP or Ring topology. "
	::= {optimuxRing 3 }
optRingNeTable OBJECT-TYPE
     SYNTAX  SEQUENCE OF OptRingNeEntry
     MAX-ACCESS  not-accessible
     STATUS  current
     DESCRIPTION
     "This table defines which optimuxes are in the ring and the 
      IP Address of each one."
     ::= { optimuxRing 4}
optRingNeEntry OBJECT-TYPE
     SYNTAX OptRingNeEntry 
     MAX-ACCESS  not-accessible
     STATUS  current
     DESCRIPTION
     "An entry in the Optimux Ring Connections  table."
     INDEX   { optRingNeIdx }
     ::= { optRingNeTable 1 }
OptRingNeEntry ::=
     SEQUENCE {
	 optRingNeIdx	   	Integer32,
     optRingNeIpAddr   	IpAddress
     }
optRingNeIdx 	OBJECT-TYPE
   SYNTAX  Integer32
   MAX-ACCESS  read-only
   STATUS  current
   DESCRIPTION
   "The index of the optimux, starting with next optimux to the current optimux. 
   Valid values:1..28.
   The index is according to the order of optimux connections in the ring.
   Example: 
   1=next optimux to the current, in the ring
   2=next optimux in the ring, after the one having index=1
   etc..
   Last index will be the current optimux, that close the ring. "
   ::= { optRingNeEntry 1 }
optRingNeIpAddr	OBJECT-TYPE
   SYNTAX  	IpAddress
   MAX-ACCESS  read-only
   STATUS  current
   DESCRIPTION
   "The IP Address of each optimux in the ring, according to optRingNeIdx."
   ::= { optRingNeEntry 2 }	
-- Traps
--NOTIFICATIONS
optimuxEvents OBJECT-IDENTITY
      STATUS  current
	  DESCRIPTION
	  "The events for Optimux."
	  ::= { optimux 0 }
optMxConfigChange NOTIFICATION-TYPE
      OBJECTS  {optIndex,  agnLed }
      STATUS  current
      DESCRIPTION
	  "The trap is sent every time there is a change in
	   the state of one of the PS.."
      ::= { optimuxEvents 1 }
optMxAgentFault NOTIFICATION-TYPE
      OBJECTS  {agnIndication,  agnLed }
      STATUS  current
      DESCRIPTION
	  "The trap is sent every time there is a change in
	   the agnIndication variable.
	   For Optimux XL family, from ver 4.1 and up, this trap should be sent 
	   upon any change in the agnNearFarConnection variable"
      ::= { optimuxEvents 2 }
optLineStatusChange NOTIFICATION-TYPE
      OBJECTS { dsx1LineStatus,
                dsx1LineStatusLastChange }
      STATUS  current
	  DESCRIPTION
      "optLineStatusChange trap is sent when the value of an instance 
       dsx1LineStatus changes. It can be utilized by an NMS to trigger polls.
       When the line status change results from a higher level line status 
       change (i.e. ds3), then no traps for the ds1 are sent."
      ::= { optimuxEvents 3 }
optSlotChange NOTIFICATION-TYPE
        OBJECTS { optMdIdx, optMdSltIdx }
        STATUS  current
        DESCRIPTION
        "This trap alerts the console if there is module
         enrollement/de-enrollement "
        ::= { optimuxEvents 4 }
optLoopbackStatusChange NOTIFICATION-TYPE
      OBJECTS { ifIndex, dsx1LoopbackStatus, dsx3LoopbackStatus }
      STATUS  current
      DESCRIPTION
      "This trap alerts the console if there is changes in the
      loopback status of some of the line."
      ::= { optimuxEvents 5 }
optXlLineStatusChange NOTIFICATION-TYPE
      OBJECTS { ifIndex,  optMdModLed, dsx1LineStatus, dsx3LineStatus }
      STATUS  current
      DESCRIPTION
       "optXlLineStatusChange trap is sent when the value of an instance 
        dsx1LineStatus changes. It can be utilized by an NMS to trigger polls."
      ::= { optimuxEvents 6 }
-- END
-- 
-- file :v:\doc\rdv\mib\ver510\webrnger.txt
-- 
--Version:   1.0
--Date:   26.04.98              
--By:       Ilana Schvetz
--File:      webwrDhcpIpAddressLeaseTimeranger.txt
--
--Last Update: Yig'al Hachmon-20 August 2004
radRouter     OBJECT IDENTIFIER ::= { rad 11 }  
rtrBridge     OBJECT IDENTIFIER ::= { radRouter 7 }
webranger OBJECT IDENTIFIER ::= { rtrBridge 2 }
wrSysConfig OBJECT IDENTIFIER ::= { webranger 1 }
wrBraodcastCtrlCmd OBJECT-TYPE
       SYNTAX INTEGER {
	   block    (1),
	   forward  (2),
       blockLinkPropagation (3)
	   }
       MAX-ACCESS read-write
       STATUS current
       DESCRIPTION
       "This parameter is a command to the webranger CPU. It
        enables blocking or forwarding broadcast frames, which
        may cause a trigger to a connection.
	  	block (1)   - blocks the broadcast frames.
	  	forward (2) - forwards the broadcast frames.
        blockLinkPropagation (3) - blocks the broadcast frames to the links, tx
        to the LAN. "
       ::= { wrSysConfig 1 }
wrFrSelfLearningMode OBJECT-TYPE
       SYNTAX INTEGER {
	   off (1),
	   on  (2)
	   }
       MAX-ACCESS read-write
       STATUS current
       DESCRIPTION
       "This parameter enables the webranger to learn the DLCi's
        configuration and maintanance protocol. 
        off - will get the configuration by setting it.
        on - disables configuration and start self learning."
       ::= { wrSysConfig 2 }
wrGratuitousArp OBJECT-TYPE
       SYNTAX INTEGER {
	   disable (2),
	   enable  (3)
	   }
       MAX-ACCESS read-write
       STATUS current
       DESCRIPTION
       "This parameter enables/disables the Gratuitous ARP feature.
        When enabled, the feature means: when receiving ARP with sender's 
        Source IP Address that already exists in the ARP table - replace 
        MAC Address with sender's Source MAC Address."
       ::= { wrSysConfig 3 }
wrIpRouterInfo OBJECT IDENTIFIER ::= { webranger 2 }
wrConfigIpDhcp OBJECT IDENTIFIER ::= { wrIpRouterInfo 1 }
wrConfigIpDNS OBJECT IDENTIFIER ::= { wrIpRouterInfo 2 }
wrDhcpAction OBJECT-TYPE
       SYNTAX INTEGER { 
       disable (2),
       enable (3)	   
       }
       MAX-ACCESS read-write
       STATUS current
       DESCRIPTION
       "Activating (disable/enable) DHCP server operation.
        Since DHCP Server and DHCP Relay cannot reside in same device,
        DHCP Relay may be enabled (per interface), only if server action is disabled.
        For some devices, this object is used in order to enable/disable 
        the DHCP Client. See device SDS."
       ::= { wrConfigIpDhcp 1 }
wrDhcpTable OBJECT-TYPE
       SYNTAX SEQUENCE OF WrDhcpEntry
       MAX-ACCESS not-accessible
       STATUS current
       DESCRIPTION
          "A list of DHCP entries. The number of entries is up to
           DHCP current entries, according to the WEBRANger model."
       ::= { wrConfigIpDhcp 2 }
    wrDhcpEntry OBJECT-TYPE
       SYNTAX  WrDhcpEntry
       MAX-ACCESS  not-accessible
       STATUS  current
       DESCRIPTION
           "DHCP parameters per entry of the DHCP table."
       INDEX   { wrDhcpLowIpAddress }
       ::= { wrDhcpTable 1 }
    WrDhcpEntry ::=
       SEQUENCE {
              wrDhcpLowIpAddress
                 IpAddress,
              wrDhcpHighIpAddress
                 IpAddress,
			  wrDhcpIpMaskAddress
                 IpAddress,
			  wrDhcpDefaultGateway
                 IpAddress,
			  wrDhcpPrimaryDNS
                 IpAddress,
			  wrDhcpSecondaryDNS
                 IpAddress,
			  wrDhcpInterface
                 INTEGER,
			  wrDhcpRowStatus
                 RowStatus,
			  wrDhcpIpAddressLeaseTime 
			     Integer32,
			  wrDhcpPoolName 
				  SnmpAdminString 
				   }
wrDhcpLowIpAddress OBJECT-TYPE
       SYNTAX IpAddress
       MAX-ACCESS read-create
       STATUS current
       DESCRIPTION
           "DHCP Low Ip Address."
       ::= { wrDhcpEntry 1 }
wrDhcpHighIpAddress OBJECT-TYPE
       SYNTAX IpAddress
       MAX-ACCESS read-create
       STATUS current
       DESCRIPTION
           "DHCP High Ip Address."
       ::= { wrDhcpEntry 2 }
wrDhcpIpMaskAddress OBJECT-TYPE
       SYNTAX IpAddress
       MAX-ACCESS read-create
       STATUS current
       DESCRIPTION
           "IP mask Address."
       ::= { wrDhcpEntry 3 }
wrDhcpDefaultGateway OBJECT-TYPE
       SYNTAX IpAddress
       MAX-ACCESS read-create
       STATUS current
       DESCRIPTION
           "Default Gateway's IP Address."
       ::= { wrDhcpEntry 4 }
wrDhcpPrimaryDNS OBJECT-TYPE
       SYNTAX IpAddress
       MAX-ACCESS read-create
       STATUS current
       DESCRIPTION
           "Primary DNS."
       ::= { wrDhcpEntry 5 }
wrDhcpSecondaryDNS OBJECT-TYPE
	   SYNTAX IpAddress  
	   MAX-ACCESS read-create
       STATUS current
       DESCRIPTION
           "Secondary DNS."
       ::= { wrDhcpEntry 6 }
wrDhcpInterface OBJECT-TYPE
       SYNTAX INTEGER { 
       all (1),
       lan1 (2),
       lan2(3),
       anyLan(4),
       wan (5)
       }
       MAX-ACCESS read-create
       STATUS current
       DESCRIPTION
           "The IP addresse allocation is done according to the 
           interface type from which the DHCP request arrives."
       ::= { wrDhcpEntry 7 }
wrDhcpRowStatus OBJECT-TYPE
      SYNTAX  RowStatus
      MAX-ACCESS  read-create
      STATUS  current
      DESCRIPTION
          "This attribute allows to create/delete a row in this table.
          For creating a row, the NMS should set 
          wrDhcpRowStatus.id = active(1).
          For destroying a row, the NMS should set:
          wrDhcpStatus.id = destroy(6).
          Only rows with status active(1) are relevant.
		  The only possible supported RowStatus vaules are
		  active  (1) and destroy (6)."
      ::= { wrDhcpEntry 8 }
wrDhcpIpAddressLeaseTime OBJECT-TYPE 
       SYNTAX   Integer32
       MAX-ACCESS  read-create
       STATUS  current
       DESCRIPTION
          "Allocated IP Address lease time in seconds. 
           A zero  value specifies no time limitation."
     ::= { wrDhcpEntry 9 }
wrDhcpPoolName OBJECT-TYPE 
       SYNTAX SnmpAdminString (SIZE (1..10)) 
       MAX-ACCESS  read-create
       STATUS  current
       DESCRIPTION
          "DHCP pool name  - string with max length of 10  characters"
        ::= { wrDhcpEntry 10 }
-- DHCP (Dynamic Host Configuration Protocol) Pool Allocation Table
dhcpPoolAllocTable OBJECT-TYPE
    SYNTAX SEQUENCE OF DhcpPoolAllocEntry
    MAX-ACCESS not-accessible
    STATUS current
    DESCRIPTION
       "A list of  DHCP  Pool Allocation entries.
       	Each entry (row) consist of a single IP Address belonging to DHCP pool 
       	whose lowest IP address is dhcpPoolAllocLowIpAddress. 
       	This IP address may be offered for leasing, or may already be 
       	leased (in use) by Host it's MacAddress is dhcpPoolAllocMacAddress.
       	Time left for leasing period is indicated by dhcpPoolAllocTimeLeft.
        All posible statuses of IP address are indicated and controlled
        by dhcpPoolAllocFlags"
    ::= { wrConfigIpDhcp 3 }
dhcpPoolAllocEntry OBJECT-TYPE
    SYNTAX  DhcpPoolAllocEntry
    MAX-ACCESS  not-accessible
    STATUS  current
    DESCRIPTION
        "DHCP Pool Allocation parameters per entry of the DHCP Pool Allocation table."
    INDEX   {dhcpPoolAllocLowIpAddress, dhcpPoolAllocLeasingIpAddress}
    ::= { dhcpPoolAllocTable 1 }
DhcpPoolAllocEntry ::=
     SEQUENCE {
            dhcpPoolAllocLowIpAddress
               IpAddress,
            dhcpPoolAllocLeasingIpAddress
               IpAddress,
            dhcpPoolAllocMacAddress
               MacAddress,
            dhcpPoolAllocTimeLeft
              Integer32, 
            dhcpPoolAllocFlags
               INTEGER,
            dhcpPoolAllocFreeCmd
               INTEGER
               }
dhcpPoolAllocLowIpAddress  OBJECT-TYPE
     SYNTAX IpAddress
     MAX-ACCESS read-only
     STATUS current
     DESCRIPTION
         "Lowest IP address of this pool, value eqaul to wrDhcpLowIpAddress for 
          the pool."
     ::= { dhcpPoolAllocEntry 1 }
dhcpPoolAllocLeasingIpAddress OBJECT-TYPE
     SYNTAX IpAddress
     MAX-ACCESS read-only
     STATUS current
     DESCRIPTION
         "Single IP Address belonging to dhcp pool whose Lowest Ip Address is 
         dhcpPoolAllocLowIpAddress. This IP address may be offered for leasing
         or may be leased by Host its MacAddress is dhcpPoolAllocMacAddress.
         All posible statuses of IP address are indicated by dhcpPoolAllocFlags     "
     ::= { dhcpPoolAllocEntry 2 }
dhcpPoolAllocMacAddress OBJECT-TYPE
     SYNTAX  MacAddress
     MAX-ACCESS read-only
     STATUS current
	 DESCRIPTION
     "MAC Address to which the IP address has been leased "
     ::= { dhcpPoolAllocEntry 3 }
dhcpPoolAllocTimeLeft OBJECT-TYPE
     SYNTAX Integer32 
     MAX-ACCESS read-only
     STATUS current
	 DESCRIPTION
         "IP address leasing time left in seconds "
     ::= { dhcpPoolAllocEntry 4 }
dhcpPoolAllocFlags OBJECT-TYPE
     SYNTAX INTEGER
            {
             notApplicable (1),
			 free (2),
			 inUse (3),
			 offered (4),
			 forbidden (5)         
             } 
     MAX-ACCESS read-only
     STATUS current
     DESCRIPTION
     "These flags indicates status of each IP address. 
     User may change value to free, via dhcpPoolAllocFreeCmd "
     ::= { dhcpPoolAllocEntry 5 }
dhcpPoolAllocFreeCmd OBJECT-TYPE
     SYNTAX INTEGER
            {
             off (2),
			 on (3)
             } 
     MAX-ACCESS read-write
     STATUS current
     DESCRIPTION
	"Setting this attribute to On (3), will enforce the agent to 
	 Free this entry.
	 The Agent will change the value of this MIB object to off(2) 
	 automatically, after performing the command.
	 Setting this object to off(2), will do nothing"
     ::= { dhcpPoolAllocEntry 6 }
--DHCP Relay Table
dhcpRelayTable OBJECT-TYPE
    SYNTAX SEQUENCE OF DhcpRelayEntry
    MAX-ACCESS not-accessible
    STATUS current
    DESCRIPTION
       "A list of DHCP relay entries."
    ::= { wrConfigIpDhcp 4 }
dhcpRelayEntry OBJECT-TYPE
    SYNTAX  DhcpRelayEntry
    MAX-ACCESS  not-accessible
    STATUS  current
    DESCRIPTION
        "DHCP Relay parameters per entry of the DHCP relay table."
    INDEX   { ifIndex }
    ::= { dhcpRelayTable 1 }
DhcpRelayEntry ::=
     SEQUENCE {
			dhcpRelayAction
			   INTEGER, 
            dhcpRelayServerIpAddress
               IpAddress,
            dhcpRelayMaxHop
               Integer32
               }
dhcpRelayAction OBJECT-TYPE
     SYNTAX INTEGER
            {
			disable (2),
            enable (3) 
			 } 
     MAX-ACCESS read-write
     STATUS current
     DESCRIPTION
	"Setting this attribute to enable (3), will  
	 enable DHCP Relay action for this interface 
	 (Only if DHCP Server is disabled for device - wrDhcpAction=disable).
	 dhcpRelayServerIpAddressaddress should not be 0.0.0.0 when enable is set"
     ::= { dhcpRelayEntry 1 }
dhcpRelayServerIpAddress OBJECT-TYPE
     SYNTAX IpAddress
     MAX-ACCESS read-write
     STATUS current
     DESCRIPTION
         "DHCP Server IP Address."
     ::= { dhcpRelayEntry 2 }
dhcpRelayMaxHop OBJECT-TYPE
     SYNTAX Integer32 
     MAX-ACCESS read-write
     STATUS current
          DESCRIPTION
         "Maximum number of hops till DHCP Server.
          upper limit is 16 hops"
     DEFVAL {16}
     ::= { dhcpRelayEntry 3 }
wrDhcpPort OBJECT-TYPE
	  SYNTAX  INTEGER
	  { 
       notApplicable	(1),
       all          	(2),
       outOfBand 		(3),
       lan1 			(4),
	   lan2				(5)
       }
      MAX-ACCESS  read-write
      STATUS  current
      DESCRIPTION
          "This parameter defines the port that DHCP flow will be actiavted."
      ::= { wrConfigIpDhcp 5}
--DHCP Client Table
dhcpClientTable OBJECT-TYPE
    SYNTAX SEQUENCE OF DhcpClientEntry
    MAX-ACCESS not-accessible
    STATUS current
    DESCRIPTION
    "A list of DHCP client entries."
    ::= { wrConfigIpDhcp 6 }
dhcpClientEntry OBJECT-TYPE
    SYNTAX  DhcpClientEntry
    MAX-ACCESS  not-accessible
    STATUS  current
    DESCRIPTION
    "DHCP Client parameters per entry of the DHCP Client table."
    INDEX   { ifIndex }
    ::= { dhcpClientTable 1 }
DhcpClientEntry ::=
     SEQUENCE {
	 dhcpClientAction
	 INTEGER, 
     dhcpClientServerIpAddress
     IpAddress,
     dhcpClientLeaseExpirationTime
     Integer32,
	 dhcpClientStatus
	 DisplayString
     }
dhcpClientAction OBJECT-TYPE
     SYNTAX INTEGER
      {
	 	disable (2),
        enable (3) 
	  } 
     MAX-ACCESS read-write
     STATUS current
     DESCRIPTION
	"This parameter default value is enable(3).
	 Setting this attribute to disable (2), will  
	 disable DHCP Client action for this interface.
	 This parameter can be changed to disable (2) only 
	 (it cannot be changed from disable to enable)."
     ::= { dhcpClientEntry 1 }
dhcpClientServerIpAddress OBJECT-TYPE
     SYNTAX IpAddress
     MAX-ACCESS read-write
     STATUS current
     DESCRIPTION
     "DHCP Server IP Address."
     ::= { dhcpClientEntry 2 }
dhcpClientLeaseExpirationTime OBJECT-TYPE
     SYNTAX Integer32 
     MAX-ACCESS read-only
     STATUS current
     DESCRIPTION
     "This parameter holds the time (in minutes) left until lease expiration."
     ::= { dhcpClientEntry 3 }
dhcpClientStatus OBJECT-TYPE
     SYNTAX DisplayString
     MAX-ACCESS read-only
     STATUS current
     DESCRIPTION
     "This parametr displays the DHCP status."
     ::= { dhcpClientEntry 4 }
--DHCP Interface Client Table
dhcpIfClientTable OBJECT-TYPE
    SYNTAX SEQUENCE OF DhcpIfClientEntry
    MAX-ACCESS not-accessible
    STATUS current
    DESCRIPTION
    "DHCP client entries for each Interface."
    ::= { wrConfigIpDhcp 7 }
dhcpIfClientEntry OBJECT-TYPE
    SYNTAX  DhcpIfClientEntry
    MAX-ACCESS  not-accessible
    STATUS  current
    DESCRIPTION
    "DHCP Clients per entry of the DHCP Interface Client table."
    INDEX   { ifIndex, dhcpIfClientIpAddress }
    ::= { dhcpIfClientTable 1 }
DhcpIfClientEntry ::=
     SEQUENCE {
	 dhcpIfClientIpAddress
     IpAddress,
     dhcpIfClientRowStatus
	 RowStatus
     }
dhcpIfClientIpAddress OBJECT-TYPE
     SYNTAX IpAddress
     MAX-ACCESS read-create
     STATUS current
     DESCRIPTION
     "DHCP Client IP Address."
     ::= { dhcpIfClientEntry 2 }
dhcpIfClientRowStatus OBJECT-TYPE
     SYNTAX      RowStatus
     MAX-ACCESS  read-create
     STATUS      current
     DESCRIPTION
     "The row status used for creating, modifying, and deleting instances 
     of the columnar objects in the dhcpIfClientTable.
     For Vmux Devices, it will be possible only to Delete instances.
     The addition of Clients will be done automatically by the Server according
     to Network messages that are sent by the Clients; not via SNMP.
     In order to Delete a Client, this MIB object should be set to: destroy (6)."
     ::= { dhcpIfClientEntry 3 }
dhcpServerAction OBJECT-TYPE
    SYNTAX  INTEGER {
       noOp(2),       
       deleteAllClients(3)
     }
    MAX-ACCESS  read-write
    STATUS  current
    DESCRIPTION
	"This variable enables the operator to perform one of the
	specified actions on the Server.
      deleteAllClients (3) is an option that is used for a device functioning as a server.
      It will remove all the clients from all the interfaces of the device.
      When the operation is complete, the agent will return a noOp (2) value."
   ::= { wrConfigIpDhcp 8 }
wrDNSRelayAction OBJECT-TYPE
       SYNTAX INTEGER { 
       notApplicable (1),
       disable       (2),
       enable        (3) 
       }
       MAX-ACCESS read-write
       STATUS current
       DESCRIPTION
       "When Enabled, device will act as a DNS Relay:
        whenever the device receives a DNS request from its host,
        it will forward it to the DNS server 
        as if the request was initiated by the  device itself.
        The reply from the DNS server is forwarded by the
        device to the host as if the device 
        was	answering the request."
       ::= { wrConfigIpDNS  1 }
wrConfigIpxRouterInfo OBJECT IDENTIFIER ::= { webranger 3 }
wrAutoLearnLanIpxNets OBJECT-TYPE
       SYNTAX INTEGER { 
       disable (2),
       enable (3)
       }
       MAX-ACCESS read-write
       STATUS current
       DESCRIPTION
           "Activating (disable/enable) the auto-learn operation."
       ::= { wrConfigIpxRouterInfo 1 }
wrLanIpxNetTable OBJECT-TYPE
       SYNTAX SEQUENCE OF WrLanIpxNetEntry
       MAX-ACCESS not-accessible
       STATUS current
       DESCRIPTION
           "Lan IPX nets Table."
       ::= { wrConfigIpxRouterInfo 2 }
wrLanIpxNetEntry OBJECT-TYPE
SYNTAX WrLanIpxNetEntry
MAX-ACCESS not-accessible
       STATUS current
       DESCRIPTION
          "IPX Nets per frame type & LAN port. The table entries 
           will be created by the agent"
INDEX   { wrLanifIndex, wrLanIpxFrameType }
       ::= { wrLanIpxNetTable 1 }
WrLanIpxNetEntry ::=
       SEQUENCE {
         wrLanifIndex
               Integer32,
         wrLanIpxFrameType
               INTEGER,
         wrIpxNetAddress
	           IpAddress
          }
wrLanifIndex OBJECT-TYPE 
          SYNTAX Integer32
          MAX-ACCESS  read-only
          STATUS  current
          DESCRIPTION
             "LAN port ifIndex."
          ::= { wrLanIpxNetEntry 1 }
wrLanIpxFrameType OBJECT-TYPE 
          SYNTAX  INTEGER{ 
          t8023 (1),
          ethernet (2),
          t8022(3),
          snap (4)
          }
          MAX-ACCESS  read-only
          STATUS  current
          DESCRIPTION
             "Frame Type"
          ::= { wrLanIpxNetEntry 2 }
wrIpxNetAddress OBJECT-TYPE 
          SYNTAX IpAddress
          MAX-ACCESS  read-write
          STATUS  current
          DESCRIPTION
             "Net address per Frame Type & LAN port."
          ::= { wrLanIpxNetEntry 3 }
wrDialInIpxNet OBJECT-TYPE
       SYNTAX IpAddress
       MAX-ACCESS read-write
       STATUS current
       DESCRIPTION
           "Net address through a link."
       ::= { wrConfigIpxRouterInfo 3 }
-- The RIP/SAP Interface Configuration Table.
    ripSapIfConfTable OBJECT-TYPE
        SYNTAX   SEQUENCE OF RipSapIfConfEntry
        MAX-ACCESS   not-accessible
        STATUS   current
        DESCRIPTION
           "A list of Interfaces which require separate
           configuration in RIP/SAP."
       ::= { wrConfigIpxRouterInfo 4 }
   ripSapIfConfEntry OBJECT-TYPE
       SYNTAX   RipSapIfConfEntry
       MAX-ACCESS   not-accessible
       STATUS   current
       DESCRIPTION
          "A Single Routing Domain in a single Subnet."
      INDEX { ripSapIfConfIfIndex }
      ::= { ripSapIfConfTable 1 }
    RipSapIfConfEntry ::=
        SEQUENCE {
            ripSapIfConfIfIndex
                Integer32,
            ripSapIfConfMode
                INTEGER,
            ripSapIfConfStatus
                RowStatus
    }
    ripSapIfConfIfIndex OBJECT-TYPE
        SYNTAX   Integer32
        MAX-ACCESS   read-only
        STATUS   current
        DESCRIPTION
           "The interface ifIndex."
       ::= { ripSapIfConfEntry 1 }
    ripSapIfConfMode OBJECT-TYPE
        SYNTAX   INTEGER {
		off(1),
		on (2)
		}
        MAX-ACCESS   read-create
        STATUS   current
        DESCRIPTION
           "The ifIndex RIP/SAP mode."
       ::= { ripSapIfConfEntry 2 }
    ripSapIfConfStatus OBJECT-TYPE
       SYNTAX RowStatus
       MAX-ACCESS read-create
       STATUS current
       DESCRIPTION
           "This attribute allows to create/delete a row in this table.
            For creating a row, the NMS should set 
            ripSapIfConfStatus.id1 = active(1).
            For destroying a row, the NMS should set:
            ripSapIfConfStatus.id1 = destroy(6).
            Only rows with status active(1) are relevant.
		    The only possible supported RowStatus vaules are
		    active  (1) and destroy (6)."
       ::= { ripSapIfConfEntry 3 }
wrInterface OBJECT IDENTIFIER ::= { webranger 4 }
wrIpAddressTable OBJECT-TYPE
       SYNTAX SEQUENCE OF WrIpAddressEntry
       MAX-ACCESS not-accessible
       STATUS current
       DESCRIPTION
           "Link IP addresses Table."
       ::= { wrInterface 1 }
wrIpAddressEntry OBJECT-TYPE
       SYNTAX WrIpAddressEntry
       MAX-ACCESS not-accessible
       STATUS current
       DESCRIPTION
          "Ip Address per Link"
       INDEX   { wrIpIfIndex }
       ::= { wrIpAddressTable 1 }
WrIpAddressEntry ::=
       SEQUENCE {
           wrIpIfIndex
		      Integer32,
           wrIpAddress
              IpAddress,
           wrIpMask
              IpAddress,
		   wrIpRowStatus
		      RowStatus
}
wrIpIfIndex OBJECT-TYPE
       SYNTAX Integer32
       MAX-ACCESS read-only
       STATUS current
       DESCRIPTION
           "Port interface index."
       ::= { wrIpAddressEntry 1 }
wrIpAddress OBJECT-TYPE
       SYNTAX IpAddress
       MAX-ACCESS read-create
       STATUS current
       DESCRIPTION
           "Link IP Address."
       ::= { wrIpAddressEntry 2 }
wrIpMask OBJECT-TYPE
       SYNTAX IpAddress
       MAX-ACCESS read-create
       STATUS current
       DESCRIPTION
           "Link IP mask Address."
       ::= { wrIpAddressEntry 3 }
wrIpRowStatus OBJECT-TYPE
       SYNTAX RowStatus
       MAX-ACCESS read-create
       STATUS current
       DESCRIPTION
           "This attribute allows to create/delete a row in this table.
            For creating a row, the NMS should set 
            wrIpRowStatus.id1 = active(1).
            For destroying a row, the NMS should set:
            wrIpRowStatus.id1 = destroy(6).
            Only rows with status active(1) are relevant.
		    The only possible supported RowStatus vaules are
		    active  (1) and destroy (6)." 
       ::= { wrIpAddressEntry 4 }
wrSpoofingTable OBJECT-TYPE
       SYNTAX SEQUENCE OF WrSpoofingEntry
       MAX-ACCESS not-accessible
       STATUS current
       DESCRIPTION
           "Spoofing Table."
       ::= { wrInterface 2 }
wrSpoofingEntry OBJECT-TYPE
       SYNTAX WrSpoofingEntry
       MAX-ACCESS not-accessible
       STATUS current
       DESCRIPTION
          "Spoofing per Link"
       INDEX   { wrSpoofingIfIndex }
       ::= { wrSpoofingTable 1 }
WrSpoofingEntry ::=
       SEQUENCE {
           wrSpoofingIfIndex
		      Integer32,
           wrSpoofingAction
		      Integer32,
           wrSpoofingAgingStation
              Integer32,
		   wrSpoofingRowStatus
		      RowStatus
}
wrSpoofingIfIndex OBJECT-TYPE
       SYNTAX Integer32
       MAX-ACCESS read-only
       STATUS current
       DESCRIPTION
           "Port interface index."
       ::= { wrSpoofingEntry 1 }
wrSpoofingAction  OBJECT-TYPE
       SYNTAX Integer32 
       MAX-ACCESS read-create
       STATUS current
       DESCRIPTION
	       "Spoofing action is applied by bit code:
            enable        :  bit 0 set (disable: bit 0 is 0)
            keepAlive     :  bit 1
               ...        :  bit 2
            and so on.
            For the above example, to set spoofing to keepAlive action,
            the object's value will be 3 = [ 2**0 + 2**1 ] 
            Only the Remote WEBRANger will accept this object !
                  -------                                  "
       ::= { wrSpoofingEntry 2 }
wrSpoofingAgingStation  OBJECT-TYPE
       SYNTAX Integer32 
       MAX-ACCESS read-create
       STATUS current
       DESCRIPTION
         " Aging time of stations list, in min. The agent 'translates'
           the time entered in minutes, to 10 min. resolution, as
		   follows: 
		   1..10  min - 10 min
		   11..20 min - 20 min
		   and so on...
		   0 is not a valid value.
           Only the Remote WEBRANger will accept this object !
                    ----------------                          "
       ::= { wrSpoofingEntry 3 }
wrSpoofingRowStatus OBJECT-TYPE
       SYNTAX RowStatus
       MAX-ACCESS read-create
       STATUS current
       DESCRIPTION
           "This attribute allows to create/delete a row in this table.
            For creating a row, the NMS should set 
            wrSpoofingRowStatus.id1 = active(1).
            For destroying a row, the NMS should set:
            wrSpoofingRowStatus.id1 = destroy(6).
            Only rows with status active(1) are relevant.
		    The only possible supported RowStatus vaules are
		    active  (1) and destroy (6)."
       ::= { wrSpoofingEntry 4 }
wrLanIfTable OBJECT-TYPE
       SYNTAX SEQUENCE OF WrLanIfEntry
       MAX-ACCESS not-accessible
       STATUS current
       DESCRIPTION
           "Link IP addresses Table."
       ::= { wrInterface 3 }
wrLanIfEntry OBJECT-TYPE
       SYNTAX WrLanIfEntry
       MAX-ACCESS not-accessible
       STATUS current
       DESCRIPTION
          "Ip Address per Link"
       INDEX   { wrLanIfIndex }
       ::= { wrLanIfTable 1 }
WrLanIfEntry ::=
       SEQUENCE {
           wrLanIfIndex
		      Integer32,
           wrLanBridgeRouterMode
              INTEGER,
		   wrLanIfState
		      INTEGER,
		   wrLanIfRdnTimeout
		      Integer32
       }
wrLanIfIndex OBJECT-TYPE
       SYNTAX Integer32
       MAX-ACCESS read-only
       STATUS current
       DESCRIPTION
           "Port interface index."
       ::= { wrLanIfEntry 1 }
wrLanBridgeRouterMode OBJECT-TYPE
     SYNTAX INTEGER {
              unknown         (1),
              bridge          (2),
              ipRouter        (3),
              ipxRouter       (4),
              ipAndIpxRouter  (5),
              bRouter         (6),
			  ipBrouter       (7),
			  ipxBrouter      (8),
			  ipAndIpxBrouter (9),
			  bridgeAndStp    (10)
              }
     MAX-ACCESS read-write
     STATUS current
     DESCRIPTION
         "This parameter indicates whether the link is Bridge 
          or Router	and specifies the Router's type."
     ::= { wrLanIfEntry 2 }
wrLanIfState OBJECT-TYPE
       SYNTAX INTEGER {      
              disable(2),
              enable (3),
			  redundancy(4)
	      }
       MAX-ACCESS read-write
       STATUS current
       DESCRIPTION
	   "The LAN is  disabled or enabled.
	    For LAN 2 it can be also 'redundancy'."
       ::= { wrLanIfEntry 3 }
wrLanIfRdnTimeout OBJECT-TYPE
       SYNTAX Integer32       
       MAX-ACCESS read-write
       STATUS current
       DESCRIPTION
	   "LAN Redundancy Timeout in seconds.
	    Applicable when wrLanIfState=redundancy."
       ::= { wrLanIfEntry 4 }
wrSyncCnfgTable OBJECT-TYPE
       SYNTAX SEQUENCE OF WrSyncCnfgEntry
       MAX-ACCESS not-accessible
       STATUS current
       DESCRIPTION
           "Configuration table for Async interface."
       ::= { wrInterface 4 }
wrSyncCnfgEntry OBJECT-TYPE
       SYNTAX WrSyncCnfgEntry
       MAX-ACCESS not-accessible
       STATUS current
       DESCRIPTION
          "Configuration table"
       INDEX   { wrSyncIfIndex }
       ::= { wrSyncCnfgTable 1 }
WrSyncCnfgEntry ::=
       SEQUENCE {
           wrSyncIfIndex
		      Integer32,
           wrSyncClkMode
              INTEGER,
           wrSyncClkRate
              INTEGER
       }
wrSyncIfIndex OBJECT-TYPE
       SYNTAX Integer32
       MAX-ACCESS read-only
       STATUS current
       DESCRIPTION
           "Sync interface index."
       ::= { wrSyncCnfgEntry 1 }
wrSyncClkMode OBJECT-TYPE
     SYNTAX INTEGER {
              notApplicable   (1),
              manual          (2),
              program         (3)
              }
     MAX-ACCESS read-write
     STATUS current
     DESCRIPTION
         "Clock Mode."
     ::= { wrSyncCnfgEntry 2 }
wrSyncClkRate OBJECT-TYPE
     SYNTAX INTEGER {
              notApplicable   (1),
              r16             (2),
              r32             (3),
              r48             (4),
              r64             (5),
              r96             (6),
              r128            (7),
			  r256            (8),
			  r768            (9)
              }
     MAX-ACCESS read-write
     STATUS current
     DESCRIPTION
         "Clock Rate in. Rate can be changed if Clock Mode is Program only."
     ::= { wrSyncCnfgEntry 3 }
wrFrCnfgTable OBJECT-TYPE
       SYNTAX SEQUENCE OF WrFrCnfgEntry
       MAX-ACCESS not-accessible
       STATUS current
       DESCRIPTION
           "Configuration table for Fr parameters that do not exist in RFC2115."
       ::= { wrInterface 5 }
wrFrCnfgEntry OBJECT-TYPE
       SYNTAX WrFrCnfgEntry
       MAX-ACCESS not-accessible
       STATUS current
       DESCRIPTION
           "Configuration entry for Fr parameters that do not exist in RFC2115."
       INDEX   { ifIndex }
       ::= { wrFrCnfgTable 1 }
WrFrCnfgEntry ::=
       SEQUENCE {
           wrFrDlciLearningMode
		      INTEGER,
		   wrFrCllmMessages
              INTEGER
       }
wrFrDlciLearningMode OBJECT-TYPE
       SYNTAX INTEGER {
	   off (2),
	   on  (3)
	   }
       MAX-ACCESS read-write
       STATUS current
       DESCRIPTION
           "This parameter enables the webranger to learn the DLCi's
            configuration and maintanance protocol for the current interface. 
            off - the WR will read the user's configuration for this interface.
            on -  the WR will begin self learning of the current interface's maintanance
                  protocol and DLCIs."
       ::= { wrFrCnfgEntry 1 }
wrFrCllmMessages OBJECT-TYPE
       SYNTAX INTEGER {
	   disable (2),
	   enable  (3)
	   }
       MAX-ACCESS read-write
       STATUS current
       DESCRIPTION
           "This parameter enables/disables the Webranger to Tx/Rx CLLM
            (Consolidated Link Layer Management) messages via DLCI 1023.
            The CLLM messages are link layer control messages. They can be used for example
		    in cases of congestion. The CLLM message contains a code for cause of congestion
		    and list of all DLCIs that should act to reduce data transmission."
       ::= { wrFrCnfgEntry 2 }
-- 
-- file :v:\doc\rdv\mib\ver485\iprouter.txt
-- 
--Version:   1.0
--Date:      31.01.99              
--By:        Ilana Schvetz
--File:      ipRouter.txt
--
--Last Update: Ilana Schvetz 09/01/02
--radRouter     OBJECT IDENTIFIER ::= { rad 11 }  
--rtrBridge     OBJECT IDENTIFIER ::= { radRouter 7 }
ipRouter OBJECT IDENTIFIER ::= { rtrBridge 3 }
rtrIfIpTable OBJECT-TYPE
       SYNTAX SEQUENCE OF RtrIfIpEntry
       MAX-ACCESS not-accessible
       STATUS current
       DESCRIPTION
          "Router interfaces table."
       ::= { ipRouter 1 }
rtrIfIpEntry OBJECT-TYPE
       SYNTAX  RtrIfIpEntry
       MAX-ACCESS  not-accessible
       STATUS  current
       DESCRIPTION
	   "An entry in table rtrIfIpTable."
       INDEX   { rtrIfIp }
       ::= { rtrIfIpTable 1 }
RtrIfIpEntry ::=
       SEQUENCE {
              rtrIfIp             IpAddress,
			  rtrIfRowStatus      RowStatus,
              rtrIfIpMask         IpAddress,
			  rtrIfIndex          Integer32,
			  rtrIfMng            INTEGER,
			  rtrIfVlanId		  VlanIndex
          }
rtrIfIp OBJECT-TYPE
       SYNTAX IpAddress
       MAX-ACCESS read-create
       STATUS current
       DESCRIPTION
           "IP Address."
       ::= { rtrIfIpEntry 1 }
rtrIfRowStatus OBJECT-TYPE
      SYNTAX  RowStatus
      MAX-ACCESS  read-create
      STATUS  current
      DESCRIPTION
          "."
      ::= { rtrIfIpEntry 2 }
rtrIfIpMask OBJECT-TYPE
       SYNTAX IpAddress
       MAX-ACCESS read-create
       STATUS current
       DESCRIPTION
           "IP mask Address."
       ::= { rtrIfIpEntry 3 }
rtrIfIndex OBJECT-TYPE
       SYNTAX Integer32
       MAX-ACCESS read-create
       STATUS current
       DESCRIPTION
           "The ifIndex connection, on which the IP is determined."
       ::= { rtrIfIpEntry 4 }
rtrIfMng OBJECT-TYPE
       SYNTAX INTEGER { 
           no  (1),
           yes (2)
       }
       MAX-ACCESS read-create
       STATUS current
       DESCRIPTION
           "An IP interface might be determined as a management 
           connection (under the product limitations)."
       ::= { rtrIfIpEntry 5 }
rtrIfVlanId OBJECT-TYPE
       SYNTAX      VlanIndex
       MAX-ACCESS  read-create
       STATUS      current
       DESCRIPTION
           "The VLAN ID assigned to Tagged frames transmitted 
            from this port.
            The value inserted should be a defined VLAN."
       ::= { rtrIfIpEntry 6 }
-- Brouter Table
brtrIfTable OBJECT-TYPE
       SYNTAX SEQUENCE OF BrtrIfEntry
       MAX-ACCESS not-accessible
       STATUS current
       DESCRIPTION
          "LAN interface table."
       ::= { ipRouter 2 }
brtrIfEntry OBJECT-TYPE
       SYNTAX  BrtrIfEntry
       MAX-ACCESS  not-accessible
       STATUS  current
       DESCRIPTION
           "The entries of this table will be created by agent."
       INDEX   { brtrIfIndex }
       ::= { brtrIfTable 1 }
BrtrIfEntry ::=
       SEQUENCE {
              brtrIfIndex         Integer32,
			  brtrIfMode          INTEGER,
			  brtrIfMaxFrameSize  Integer32
  	    }
brtrIfIndex OBJECT-TYPE
       SYNTAX Integer32
       MAX-ACCESS read-only
       STATUS current
       DESCRIPTION
           "The index of the interface (LAN or ATM)."
       ::= { brtrIfEntry 1 }
brtrIfMode OBJECT-TYPE
       SYNTAX INTEGER { 
           bridge    (1),
           router    (2),
           brouter   (3),
		   off       (4)
       }
       MAX-ACCESS read-write
       STATUS current
       DESCRIPTION
           "Connection Mode."
       ::= { brtrIfEntry 2 }
brtrIfMaxFrameSize OBJECT-TYPE
       SYNTAX Integer32
       MAX-ACCESS read-write
       STATUS current
       DESCRIPTION
           "Frame Max Size."
       ::= { brtrIfEntry 3 }
rtrArpAgingTime OBJECT-TYPE
       SYNTAX Integer32
       MAX-ACCESS read-write
       STATUS current
       DESCRIPTION
           "ARP Aging Time. Applicable for a Router Mode 
           and for a Brouter Mode."
       ::= { ipRouter 3 }
-- Brouter LAN If table
brtrLanIfTable OBJECT-TYPE
       SYNTAX SEQUENCE OF BrtrLanIfEntry
       MAX-ACCESS not-accessible
       STATUS current
       DESCRIPTION
          "LAN interface table."
       ::= { ipRouter 4 }
brtrLanIfEntry OBJECT-TYPE
       SYNTAX  BrtrLanIfEntry
       MAX-ACCESS  not-accessible
       STATUS  current
       DESCRIPTION
           "The entries of this table will be created by agent ."
       INDEX   { brtrLanIfIndex }
       ::= { brtrLanIfTable 1 }
BrtrLanIfEntry ::=
       SEQUENCE {
              brtrLanIfIndex            Integer32,
			  brtrLanIpAddress          IpAddress,
			  brtrLanIpMask             IpAddress,
              brtrLanMaxRateEnable      INTEGER,
              brtrLanMaxRate            Integer32,
              brtrLanMng                INTEGER,
              brtrLanDefaultRouter      IpAddress
       }
brtrLanIfIndex OBJECT-TYPE
       SYNTAX Integer32
       MAX-ACCESS read-only
       STATUS current
       DESCRIPTION
           "The index of the LAN entity (physical interface)."
       ::= { brtrLanIfEntry 1 }
brtrLanIpAddress OBJECT-TYPE
       SYNTAX IpAddress
       MAX-ACCESS read-write
       STATUS current
       DESCRIPTION
           "Host IP address. Applicable for bridge mode connection only."
       ::= { brtrLanIfEntry 2 }
brtrLanIpMask OBJECT-TYPE
       SYNTAX IpAddress
       MAX-ACCESS read-write
       STATUS current
       DESCRIPTION
           "Host IP Mask. Applicable for bridge mode connection only."
       ::= { brtrLanIfEntry 3 }
brtrLanMaxRateEnable OBJECT-TYPE
       SYNTAX INTEGER { 
          disable (1),
          enable  (2)
       }
       MAX-ACCESS read-only
       STATUS current
       DESCRIPTION
           "This parameter determines the HW ability of the LAN 
           card according to HW."
       ::= { brtrLanIfEntry 4 }
brtrLanMaxRate OBJECT-TYPE
       SYNTAX Integer32
       MAX-ACCESS read-write
       STATUS current
       DESCRIPTION
           "Max Rate."
       ::= { brtrLanIfEntry 5 }
brtrLanMng OBJECT-TYPE
       SYNTAX INTEGER { 
           no  (1),
           yes (2)
       }
       MAX-ACCESS read-write
       STATUS current
       DESCRIPTION
           "An IP interface might be determined as a management 
           connection (under the product limitations)."
       ::= { brtrLanIfEntry 6 }
brtrLanDefaultRouter OBJECT-TYPE
       SYNTAX IpAddress
       MAX-ACCESS read-write
       STATUS current
       DESCRIPTION
           "Default Router's (Gateway's) IP Address.
            For each LAN interface there may be a different Default Router."
       ::= { brtrLanIfEntry 7 }
rtrIsdnIfTable OBJECT-TYPE
       SYNTAX SEQUENCE OF RtrIsdnIfEntry
       MAX-ACCESS not-accessible
       STATUS current
       DESCRIPTION
          "This table contains ISDN parameters that do not appear in the standard MIBs."
       ::= { ipRouter 5 }
rtrIsdnIfEntry OBJECT-TYPE
       SYNTAX  RtrIsdnIfEntry
       MAX-ACCESS  not-accessible
       STATUS  current
       DESCRIPTION
           "Entries for ISDN parameters that do not appear in the standard MIBs."
       AUGMENTS    { isdnSignalingEntry }
--        INDEX { isdnSignalingIndex }
       ::= { rtrIsdnIfTable 1 }
RtrIsdnIfEntry ::=
       SEQUENCE {
              rtrIsdnIfMinNumBchans            Integer32,
              rtrIsdnIfMaxNumBchans            Integer32
       }
rtrIsdnIfMinNumBchans OBJECT-TYPE
       SYNTAX Integer32
       MAX-ACCESS read-create
       STATUS current
       DESCRIPTION
           "Minimum number of B channels that the ISDN Dialer of the router will use
            for Dialing out.
            This parameter will be used for the BOD (Bandwidth On Demand) feature.
            Dial up on B channels is according to the need of bandwidth for router 
            data transfer. Voice calls have a higher priority than router data.
            In case of few time slots the voice calls will cause disconnection of
            data channels up to the limit of minimum number of B channels."
       ::= { rtrIsdnIfEntry 1 }
rtrIsdnIfMaxNumBchans OBJECT-TYPE
       SYNTAX Integer32
       MAX-ACCESS read-create
       STATUS current
       DESCRIPTION
           "Maximum number of B channels that the ISDN Dialer of the router will use
            for Dialing out.
            This parameter will be used for the BOD (Bandwidth On Demand) feature.
            Dial up on B channels is according to the need of bandwidth for router 
            data transfer. Voice calls have a higher priority than router data.
            No more than MAX B channels will be used by the ISDN dialer."                     
       ::= {rtrIsdnIfEntry  2 }
rtrLcrTable OBJECT-TYPE
       SYNTAX SEQUENCE OF RtrLcrEntry
       MAX-ACCESS not-accessible
       STATUS current
       DESCRIPTION
          "Least Cost Routing Table.
           The user will be able to set a prefix for an outgoing number
           that arrives with a predefined prefix in order to redirect
           the number for the LCR process to be achieved."
       ::= { ipRouter 6 }
rtrLcrEntry OBJECT-TYPE
       SYNTAX  RtrLcrEntry
       MAX-ACCESS  not-accessible
       STATUS  current
       DESCRIPTION
           "Least Cost Routing Entry."
       INDEX   { ifIndex, rtrLcrOutIfIndex }
       ::= { rtrLcrTable 1 }
RtrLcrEntry ::=
       SEQUENCE {
              rtrLcrOutIfIndex      InterfaceIndex,
			  rtrLcrRowStatus       RowStatus,
              rtrLcrInPrefix        DisplayString,
			  rtrLcrOutPrefix       DisplayString
       }
rtrLcrOutIfIndex OBJECT-TYPE
       SYNTAX InterfaceIndex
       MAX-ACCESS not-accessible
       STATUS current
       DESCRIPTION
           "The outgoing interface Number of the current route.
            The incoming interface number is the value of ifIndex."
       ::= { rtrLcrEntry 1 }
rtrLcrRowStatus OBJECT-TYPE
      SYNTAX  RowStatus
      MAX-ACCESS  read-create
      STATUS  current
      DESCRIPTION
          "Row Status for adding/destroying rows."
      ::= { rtrLcrEntry 2 }
rtrLcrInPrefix OBJECT-TYPE
       SYNTAX DisplayString
       MAX-ACCESS read-create
       STATUS current
       DESCRIPTION
           "This prefix is part of the called number existing in the incoming packet."                     
       ::= {rtrLcrEntry  3 }
rtrLcrOutPrefix OBJECT-TYPE
       SYNTAX DisplayString
       MAX-ACCESS read-create
       STATUS current
       DESCRIPTION
           "This prefix will be inserted into the outgoing packet."
       ::= {rtrLcrEntry  4 }
--radRouter     OBJECT IDENTIFIER ::= { rad 11 }  
multicastGen    OBJECT IDENTIFIER ::= { radRouter 8 } -- General Multicast Parameters
multicastMode  OBJECT-TYPE
      SYNTAX INTEGER {
      disable  (2),        
      wanToLan (3),      
      wanToLanIgmp (4),
	  lanToWan (5),
      bidirectional(6),
      transparent(7)
      }
	  MAX-ACCESS read-write
      STATUS current
      DESCRIPTION
      "According to this mode the packets will be forwarded.
       If disable (2) is selected, there will be no multicast."
      ::= { multicastGen 1 }
-- 
-- file :v:\doc\rdv\mib\ver505\v5.txt
-- 
--Title:  RAD's WAN V5.1 Interface MIB
--By:     Smadar Tauber
--Date :  03.11.1998
--Last Update: 22-Sep-03 
--By: Smadar Tauber
--File:  v:\doc\rdv\mib\ver505\v5.txt
--IMPORTS
--      enterprises                            FROM RFC1155-SMI
--      DisplayString                          FROM RFC1213-MIB
--      IpAddress                              FROM RFC1155-SMI
--      OCTET STRING                           FROM RFC1213-MIB
--      OBJECT-TYPE                            FROM RFC-1212;
wanGen   OBJECT IDENTIFIER ::= {radWan 1}
diverseIfWanGen OBJECT IDENTIFIER ::= {wanGen 6} --(see mpmx.txt)
v51If OBJECT IDENTIFIER ::= {diverseIfWanGen 6}
v51General 	  OBJECT IDENTIFIER ::= {v51If 1}
v51Variant    OBJECT IDENTIFIER ::= {v51If 2}
v51Ml         OBJECT IDENTIFIER ::= {v51If 3}
v51AccessPort OBJECT IDENTIFIER ::= {v51If 4}
--NPL parameters (for most of the manual parameters see TDSoft MIB)
npl OBJECT IDENTIFIER ::= {v51General 1}
nplMode  OBJECT-TYPE
      SYNTAX  INTEGER
       {
          auto  (2),
          manual(3)
       }
      MAX-ACCESS  read-write
      STATUS  current
      DESCRIPTION
      "NPL Mode."
      ::= { npl 1 }
nplCountry  OBJECT-TYPE
      SYNTAX  INTEGER
       {
          none    (1),
          france  (2),
          germany (3)
       }
      MAX-ACCESS  read-write
      STATUS  current
      DESCRIPTION
      "National Protocol Country."
      ::= { npl 2 }
nplVoicePathDuration  OBJECT-TYPE
      SYNTAX  Integer32
      MAX-ACCESS  read-write
      STATUS  current
      DESCRIPTION
      "Maximum time of a voice path, in msec."
      ::= { npl 3 }
--NPL Pulse table
nplPulseTable  OBJECT-TYPE
     SYNTAX SEQUENCE OF NplPulseEntry
     MAX-ACCESS not-accessible
     STATUS  current
     DESCRIPTION
      "NPL Pulse table. This table is written directly to the agent."
     ::= { npl 4 }
nplPulseEntry OBJECT-TYPE
      SYNTAX NplPulseEntry
      MAX-ACCESS not-accessible
      STATUS current
	  DESCRIPTION
	  "An entry in table nplPulseTable."
      INDEX {nplPulseType}
      ::= { nplPulseTable 1}
NplPulseEntry ::=
      SEQUENCE {
      nplPulseType         INTEGER,
	  nplPulseValid        INTEGER,
      nplPulseDurationType Integer32,
      nplPulseOnTime       Integer32,
      nplPulseOffTime      Integer32
      }
nplPulseType OBJECT-TYPE
      SYNTAX  INTEGER
      {
      meteringPulse1   (1),
      meteringPulse2   (2),
      initRinging1     (3),
      initRinging2     (4),
      normalBattery  (237),
      noBattery      (250),
      reducedBattery (251),
      reversePolarity(254),
      normalPolarity (255)
            }
      MAX-ACCESS  read-only
      STATUS  current
      DESCRIPTION
      "Pulse Type"
      ::= {nplPulseEntry 1}
nplPulseValid OBJECT-TYPE
      SYNTAX  INTEGER
      {
      notValid   (2),
      valid      (3)
            }
      MAX-ACCESS  read-write
      STATUS  current
      DESCRIPTION
      "Validity of the Pulse Type."
      ::= {nplPulseEntry 2}
nplPulseDurationType OBJECT-TYPE
      SYNTAX  Integer32  (0..31)
      MAX-ACCESS  read-write
      STATUS  current
      DESCRIPTION
      "Pulse Duration Type.
       - If meteringPulse1 and meteringPulse2 are both 'valid', the value of this 
         object must be different for them.
       - If initRinging1 and initRinging2 are both 'valid', the value of this 
         object must be different for them."
      ::= {nplPulseEntry 3}
nplPulseOnTime OBJECT-TYPE
      SYNTAX  Integer32  (0..990)
      MAX-ACCESS  read-write
      STATUS  current
      DESCRIPTION
      "How much time the pulse is ON, in msec.
       0 is a valid value only when nplPulseValid=notValid."
      ::= {nplPulseEntry 4}
nplPulseOffTime OBJECT-TYPE
      SYNTAX  Integer32  (0..990)
      MAX-ACCESS  read-write
      STATUS  current
      DESCRIPTION
      "How much time the pulse is OFF, in msec."
      ::= {nplPulseEntry 5}
--Variant tables
--
--Variant table - Configuration and Status at Variant Level
--
--Only ONE variant exists per link in the Temporary Configuration
v51VarTable  OBJECT-TYPE
     SYNTAX SEQUENCE OF V51VarEntry
     MAX-ACCESS not-accessible
     STATUS  current
     DESCRIPTION
      "The write operation into the Table Objects is valid only
       to the TmpCnfg entry."
     ::= { v51Variant 1}
v51VarEntry OBJECT-TYPE
      SYNTAX V51VarEntry
      MAX-ACCESS not-accessible
      STATUS current
	  DESCRIPTION
	  "An entry in table v51VarTable."
      INDEX {v51VarCnfgIdx, v51VarSltIdx, v51VarPrtIdx, v51VarIdx }
      ::= { v51VarTable 1}
V51VarEntry ::=
      SEQUENCE {
      v51VarCnfgIdx      Integer32,
      v51VarSltIdx       INTEGER,
      v51VarPrtIdx       Integer32,
      v51VarIdx          Integer32,
	  v51VarPstnCch      INTEGER,
	  v51VarIsdnSTypeCch INTEGER,
	  v51VarDescription  DisplayString,
	  v51VarStatus       INTEGER,
	  v51VarRowStatus    INTEGER
      }
v51VarCnfgIdx OBJECT-TYPE
      SYNTAX  Integer32 (1..255)
      MAX-ACCESS  read-only
      STATUS  current
      DESCRIPTION
      "This attribute indicates the Idx of the Cnfg being accessed.
       255 = TmpCnfg.
       1   = Current Cnfg. 
       Write is allowed only to TmpCnfg."
      ::= {v51VarEntry 1}
v51VarSltIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index.
       For V5.2, this index will be the Slot of the V5.2 Master ML."
      ::= {v51VarEntry 2}
v51VarPrtIdx OBJECT-TYPE
      SYNTAX  Integer32
      MAX-ACCESS  read-only
      STATUS  current
      DESCRIPTION
      "This attribute indicates a unique  port number of the ML having 
       V5 interface.
       Valid values: exPrt1 (1)..exPrt4 (4), inPrt1(101)..inPrt4(104),
       notApplicable(255) - for V5.2 only."
      ::= {v51VarEntry 3}
v51VarIdx OBJECT-TYPE
     SYNTAX  Integer32 (0..255)
     MAX-ACCESS   read-only
     STATUS   current
     DESCRIPTION
     "Variant Id.
      Valid values: 
      - for Current Cnfg: 0..127
      - for Tmp Cnfg: until MP R9 : 255 only.
                      from  MP R10: 0..127."
     ::= {v51VarEntry 4}
v51VarPstnCch OBJECT-TYPE
      SYNTAX  INTEGER 
      { 
      notApplicable (1),
      ts15          (2), 
      ts16          (3),
	  ts31          (4)
      }
      MAX-ACCESS   read-write
      STATUS   current
      DESCRIPTION
      "This object indicates which TS will be used for PSTN C channel.
       For V5.2 - notApplicable."
      ::= {v51VarEntry 5}
v51VarIsdnSTypeCch OBJECT-TYPE
      SYNTAX  INTEGER 
      { 
      notApplicable (1),
      ts15          (2), 
      ts16          (3),
	  ts31          (4)
      }
      MAX-ACCESS   read-write
      STATUS   current
      DESCRIPTION
      "This object indicates which TS will be used for S-Type C channel.
       For V5.2 - notApplicable."
      ::= {v51VarEntry 6}
v51VarDescription OBJECT-TYPE
      SYNTAX  DisplayString 
      MAX-ACCESS  read-write
      STATUS  current
      DESCRIPTION
      "This object describes the Variant."
      ::= {v51VarEntry 7}
v51VarStatus OBJECT-TYPE
      SYNTAX  INTEGER 
      { 
      notApplicable (1), 
      notActive  (2), 
      active     (3),
      activeReq  (4) 
      }
      MAX-ACCESS read-only
      STATUS current
      DESCRIPTION
      "This object reports the status of an existing Variant of a link.
       notActive - the variant exists on this link but is not active
       active    - the variant exists on this link AND is active
       activeReq - the variant exists on this link and it was requested to
                   be active, but the request is still in negotiation
                   (it can be either accepted as active, or not).
       This object is not applicable for v51VarCnfgIdx=255=TmpCnfg."
      ::= {v51VarEntry 8}
v51VarRowStatus OBJECT-TYPE
      SYNTAX  INTEGER 
      { 
      notApplicable(1),
      notValid     (2),
      valid        (3)
      }
      MAX-ACCESS   read-write
      STATUS   current
      DESCRIPTION
      "This object enables to create new entries and delete existing entries
       from the table. It is applicable only from MP R10."
      ::= {v51VarEntry 9}
--Variant Configuration and Status table - TS/Address Level
v51VarCfgTable  OBJECT-TYPE
     SYNTAX SEQUENCE OF V51VarCfgEntry
     MAX-ACCESS not-accessible
     STATUS  current
     DESCRIPTION
      "The write operation into the Table Objects is valid only
       to the TmpCnfg entry."
     ::= { v51Variant 2}
v51VarCfgEntry OBJECT-TYPE
      SYNTAX V51VarCfgEntry
      MAX-ACCESS not-accessible
      STATUS current
	  DESCRIPTION
	  "An entry in table v51VarCfgTable."
      INDEX {v51VarCfgIndex, v51VarCfgSltIdx, v51VarCfgPrtIdx, v51VarCfgIdx, 
             v51VarCfgTsIdx}
      ::= { v51VarCfgTable 1}
V51VarCfgEntry ::=
      SEQUENCE {
      v51VarCfgIndex       Integer32,
      v51VarCfgSltIdx      INTEGER,
      v51VarCfgPrtIdx      Integer32,
      v51VarCfgIdx         Integer32,
      v51VarCfgTsIdx       Integer32,
	  v51VarCfgTsType      INTEGER,
	  v51VarCfgPrtId       Integer32,
	  v51VarCfgEfL3Addr    Integer32,
      v51VarCfgFTypeCch    Integer32,
      v51VarCfgPTypeCch    Integer32,
      v51VarCfgConSlt      INTEGER,
      v51VarCfgConPrt      Integer32,
      v51VarCfgIoState     INTEGER,
	  v51VarCfgBlock       INTEGER,
	  v51VarCfgExtDch      INTEGER,
	  v51VarCfgExtDchSlot  INTEGER,
	  v51VarCfgExtDchPort  Integer32,
	  v51VarCfgExtDchTs    Integer32,
	  v51VarCfgExtDchCmpr     INTEGER,
	  v51VarCfgExtDchRate     INTEGER,
	  v51VarCfgExtDchStartBit Integer32,
      v51VarCfgSTypeCch    Integer32,
	  v51VarCfgStatus      INTEGER,
	  v51VarCfgV52MasterTsa   Integer32
      }
v51VarCfgIndex OBJECT-TYPE
      SYNTAX  Integer32 (1..255)
      MAX-ACCESS  read-only
      STATUS  current
      DESCRIPTION
      "This attribute indicates the Idx of the Cnfg being accessed.
       255 = TmpCnfg.
       1   = Current Cnfg. "
      ::= {v51VarCfgEntry 1}
v51VarCfgSltIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index.
       For V5.2, this index will be the Slot of the V5.2 Master ML."
      ::= {v51VarCfgEntry 2}
v51VarCfgPrtIdx OBJECT-TYPE
      SYNTAX  Integer32
      MAX-ACCESS  read-only
      STATUS  current
      DESCRIPTION
      "This attribute indicates a unique  port number of the ML having 
       V5 interface.
       Valid values: exPrt1 (1)..exPrt4 (4), inPrt1(101)..inPrt4(104)
       notApplicable(255) - for V5.2 only."
      ::= {v51VarCfgEntry 3}
v51VarCfgIdx OBJECT-TYPE
     SYNTAX  Integer32 (0..255)
     MAX-ACCESS   read-only
     STATUS   current
     DESCRIPTION
     "Variant Id.
      Valid values: 
      - for Current Cnfg: 0..127
      - for Tmp Cnfg: until MP R9 : 255 only.
                      from  MP R10: 0..127."
     ::= {v51VarCfgEntry 4}
v51VarCfgTsIdx OBJECT-TYPE
      SYNTAX  Integer32 
      MAX-ACCESS   read-only
      STATUS   current
      DESCRIPTION
      "For V5.1: Time Slot index (1..31).
       For V5.2: Running Index (1..1320) for Address Table."
      ::= {v51VarCfgEntry 5}
v51VarCfgTsType OBJECT-TYPE
      SYNTAX  INTEGER 
      { 
      nc              (1),
      pstn            (2), 
      isdnB1          (3),
	  isdnB2          (4),
	  cChannel        (5),
	  permanentB1     (6),
	  permanentB2     (7),
	  semiPermanentB1 (8),
	  semiPermanentB2 (9)
      }
      MAX-ACCESS   read-write
      STATUS   current
      DESCRIPTION
      "Time Slot Type."
      ::= {v51VarCfgEntry 6}
v51VarCfgPrtId OBJECT-TYPE
      SYNTAX  Integer32 (0..16777215)
      MAX-ACCESS   read-write
      STATUS   current
      DESCRIPTION
      "This object indicates the IO Port Id this TS is connected to.
       For V5.2, the Port Id is a concatenation of SS:PP:TS of the port 
       connected to V5.2 Master.
       SS=IO Slot (1..12)
       PP=Port   (01..04)
       TS = TS   (00 for ports that don't have TSs ..31).
       Example:  50327  means IO-5, port-3, TS27."
      ::= {v51VarCfgEntry 7}
v51VarCfgEfL3Addr OBJECT-TYPE
      SYNTAX  Integer32 (0..65535)
      MAX-ACCESS   read-write
      STATUS   current
      DESCRIPTION
      "This object indicates the Address of the IO port this TS is connected to.
       The IO port is identified according to its Address:
       - for ISDN ports: EF Address. Valid values: 0..8175 
       - for PSTN ports: L3 Address. Valid values: 0..32767
       65535=notApplicable (FFFF)."
      ::= {v51VarCfgEntry 8}
v51VarCfgFTypeCch OBJECT-TYPE
      SYNTAX  Integer32 
      MAX-ACCESS   read-write
      STATUS   current
      DESCRIPTION
      "For V5.1 - this object indicates which TS will be used for F-Type C channel.
           notApplicable (1),
           ts15          (2), 
           ts16          (3),
	       ts31          (4)
	   For V5.2 - this object indicates the Logical C Channel F Type (0..65535).
	              65536=not applicable in this case."
      ::= {v51VarCfgEntry 9}
v51VarCfgPTypeCch OBJECT-TYPE
      SYNTAX  Integer32 
      MAX-ACCESS   read-write
      STATUS   current
      DESCRIPTION
      "For V5.1 - This object indicates which TS will be used for P-Type C channel.
           notApplicable (1),
           ts15          (2), 
           ts16          (3),
	       ts31          (4)
	   For V5.2 - this object indicates the Logical C Channel P Type (0..65535).
	              65536=not applicable in this case."
      ::= {v51VarCfgEntry 10}
v51VarCfgConSlt OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "The Slot containing the IO port this TS is connected to.
       For V5.2 this object is notApplicable."
      ::= {v51VarCfgEntry 11}
v51VarCfgConPrt OBJECT-TYPE
      SYNTAX  Integer32
      MAX-ACCESS  read-only
      STATUS  current
      DESCRIPTION
      "The IO Port this TS is connected to.
       Valid values: exPrt1 (1)..exPrt12 (12), inPrt1(101)..inPrt4(104).
       100=noConnect
       For V5.2 this object is notApplicable=255."
      ::= {v51VarCfgEntry 12}
v51VarCfgIoState OBJECT-TYPE
      SYNTAX  INTEGER
      {
      notUsed         (1),
	  normal          (2),
	  blockReqDenied  (3),
	  remoteBlocked   (4),
      localBlocked    (5),
      unblockReqDenied(6),
      duringBlock     (7),
      duringUnblock   (8),
      localLoop       (9),
      remoteLoop     (10),
	  localUnblock   (11),
	  remoteUnblock  (12)
             }
      MAX-ACCESS  read-only
      STATUS  current
      DESCRIPTION
      "The State of the IO port this TS is connected to.
       This object is not applicable for v51VarCfgIndex=255=TmpCnfg.
       normal(2) - will be used for operating normally (operate)
       localBlocked(5) - will be used for general Block state"
      ::= {v51VarCfgEntry 13}
v51VarCfgBlock OBJECT-TYPE
      SYNTAX  INTEGER 
      { 
	  notApplicable (1),
      unBlock       (2), 
      block         (3),
	  blockRequest  (4)
      }
      MAX-ACCESS   read-write
      STATUS   current
      DESCRIPTION
      "This object indicates if this TS will be Blocked or not and how:
       block - done locally
       blockRequest - according to external request of the telephone exchange."
      ::= {v51VarCfgEntry 14}
v51VarCfgExtDch OBJECT-TYPE
      SYNTAX  INTEGER 
      { 
	  notApplicable(1),
      no  (2),
      yes (3)
      }
      MAX-ACCESS   read-write
      STATUS   current
      DESCRIPTION
      "For V5.1: This object indicates if this TS is an ISDN D channel that 
                 comes via Bypass from a non-V5.1 ML.
       For V5.2: this object will be notApplicable (not supported)."
      ::= {v51VarCfgEntry 15}
v51VarCfgExtDchSlot OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-write
      STATUS  current
      DESCRIPTION
      "This object is applicable only if v51VarCfgExtDch=yes(3).
       It indicates the Slot of the non-V5.1 ML on which the External D channel
       TS is defined (and is transferred via Bypass between the V5.1 ML and
       the non-V5.1 ML.)
       Not Applicable for V5.2 (it is part of Port Id)."
      ::= {v51VarCfgEntry 16}
v51VarCfgExtDchPort OBJECT-TYPE
      SYNTAX  Integer32
      MAX-ACCESS  read-write
      STATUS  current
      DESCRIPTION
      "This object is applicable only if v51VarCfgExtDch=yes(3).
       It indicates the Port on the Slot of 'v51VarCfgExtDchSlot' of the 
       non-V5.1 ML on which the External D channel TS is defined (and is 
       transferred via Bypass between the V5.1 ML and the non-V5.1 ML.)
	   Valid values: exPrt1 (1)..exPrt4 (4), inPrt1(101)..inPrt4(104).
       100=noConnect.
       Not Applicable for V5.2 (255; it is part of Port Id)."
      ::= {v51VarCfgEntry 17}
v51VarCfgExtDchTs OBJECT-TYPE
      SYNTAX  Integer32 (0..32)
      MAX-ACCESS  read-write
      STATUS  current
      DESCRIPTION
      "This object is applicable only if v51VarCfgExtDch=yes(3).
       It indicates the TS on the non-V5 ML on which the External 
       D channel TS is defined (and is transferred via Bypass between 
       the V5 ML and the non-V5 ML.)
       For V5.1: 0=notApplicable
       For V5.2: 0=None, 32=notApplicable."
      ::= {v51VarCfgEntry 18}
v51VarCfgExtDchCmpr OBJECT-TYPE
      SYNTAX  INTEGER 
      { 
      notApplicable(1),
      no  (2),
      yes (3)
      }
      MAX-ACCESS   read-write
      STATUS   current
      DESCRIPTION
      "For V5.1 - this object is applicable only if v51VarCfgExtDch=yes(3).
       It indicates if this ISDN D channel TS is Compressed or not."
      ::= {v51VarCfgEntry 19}
v51VarCfgExtDchRate OBJECT-TYPE
      SYNTAX  INTEGER 
      { 
      notApplicable(1),
      twoBits      (2),
      fourBits     (3),
	  eightBits    (4)
      }
      MAX-ACCESS   read-write
      STATUS   current
      DESCRIPTION
      "For V5.1 - this object is applicable only if v51VarCfgExtDch=yes(3).
       It indicates the Rate of the ISDN D channel."
      ::= {v51VarCfgEntry 20}
v51VarCfgExtDchStartBit OBJECT-TYPE
      SYNTAX  Integer32 (0..7)
      MAX-ACCESS  read-write
      STATUS  current
      DESCRIPTION
      "For V5.1 - this object is applicable only if v51VarCfgExtDch=yes(3).
       It indicates the Start Bit of the ISDN D channel on the TS of 
       the non-V5.1 ML on which it is defined.
	   Valid values:
	   - for v51VarCfgExtDchRate=twoBits(2):   1, 3, 5, 7
	   - for v51VarCfgExtDchRate=fourBits(3):  1, 5
	   - for v51VarCfgExtDchRate=eightBits(4): 1 
       - 0=notApplicable "
      ::= {v51VarCfgEntry 21}
v51VarCfgSTypeCch OBJECT-TYPE
      SYNTAX  Integer32 
      MAX-ACCESS   read-write 
      STATUS   current
      DESCRIPTION
      "This object is supported only by V5.2. It indicates the Logical 
       C Channel S Type (0..65535). 
	   65536=not applicable."
      ::= {v51VarCfgEntry 22}
v51VarCfgStatus OBJECT-TYPE
      SYNTAX  INTEGER 
      { 
      notApplicable(1),
      notValid     (2),
      valid        (3)
      }
      MAX-ACCESS   read-write
      STATUS   current
      DESCRIPTION
      "This object is supported only by V5.2.
       It enables to create new entries and delete existing entries
       from the table."
      ::= {v51VarCfgEntry 23}
v51VarCfgV52MasterTsa OBJECT-TYPE
      SYNTAX  Integer32 
      MAX-ACCESS   read-only
      STATUS   current
      DESCRIPTION
      "This object is supported only by V5.2.
       This will be the V5.2 Master, Switch Allocated Location. It is
       a concatenation of SS:PP:TS of the V5.2 Master.
	   It indicates which is the exact port and TS allocated by the Local
	   Exchange on the V5.2 Link.
       SS=IO Slot (1..12)
       PP=Port   (01..04)
       TS = TS    (1..31).
       Example: 50323  means IO-5, port-3, TS23."
      ::= {v51VarCfgEntry 24}
--Variant Configuration and Status table - C CH Level (V5.2 only)
v5VarCchTable  OBJECT-TYPE
     SYNTAX SEQUENCE OF V5VarCchEntry
     MAX-ACCESS not-accessible
     STATUS  current
     DESCRIPTION
      "The write operation into the Table Objects is valid only
       to the TmpCnfg entry."
     ::= { v51Variant 3}
v5VarCchEntry OBJECT-TYPE
      SYNTAX V5VarCchEntry
      MAX-ACCESS not-accessible
      STATUS current
	  DESCRIPTION
	  "An entry in table v5VarCchTable."
      INDEX {v5VarCchCfgIndex, v5VarCchVarIdx, v5VarCchIdx}
      ::= { v5VarCchTable 1}
V5VarCchEntry ::=
      SEQUENCE {
      v5VarCchCfgIndex     Integer32,
      v5VarCchVarIdx       Integer32,
      v5VarCchIdx          Integer32,
	  v5VarCchType         INTEGER,
	  v5VarCchPhyLinkNo    Integer32,
	  v5VarCchLogicalId    Integer32,
	  v5VarCchTs           Integer32,
	  v5VarCchPstn         INTEGER,
	  v5VarCchIsdnTypes    Integer32
	  } 
v5VarCchCfgIndex OBJECT-TYPE
      SYNTAX  Integer32 (1..255)
      MAX-ACCESS  read-only
      STATUS  current
      DESCRIPTION
      "This attribute indicates the Idx of the Cnfg being accessed.
       255 = TmpCnfg.
       1   = Current Cnfg. "
      ::= {v5VarCchEntry 1}
v5VarCchVarIdx OBJECT-TYPE
     SYNTAX  Integer32 (0..127)
     MAX-ACCESS   read-only
     STATUS   current
     DESCRIPTION
     "Variant Id.
      Valid values: 0..127."
     ::= {v5VarCchEntry 2}
v5VarCchIdx OBJECT-TYPE
     SYNTAX  Integer32 (1..8)
     MAX-ACCESS   read-only
     STATUS   current
     DESCRIPTION
     "C-CH Id.
      There are only 8 possible C-CHs per Variant."
     ::= {v5VarCchEntry 3}
v5VarCchType OBJECT-TYPE
      SYNTAX  INTEGER 
      { 
      none         (2),
      primary      (3),
	  secondary    (4),
	  regular      (5),
	  standby      (6)
      }
      MAX-ACCESS   read-write
      STATUS   current
      DESCRIPTION
      "C-CH Type."
      ::= {v5VarCchEntry 4}
v5VarCchPhyLinkNo OBJECT-TYPE
     SYNTAX  Integer32 
     MAX-ACCESS   read-write
     STATUS   current
     DESCRIPTION
     "The Physical Link Number of the card (1..4).
      This object is applicable only if v51VarCchType is not 'none'.
      notApplicable=255."
     ::= {v5VarCchEntry 5}
v5VarCchLogicalId OBJECT-TYPE
     SYNTAX  Integer32 (0..65535)
     MAX-ACCESS   read-write
     STATUS   current
     DESCRIPTION
     "The Logical C-CH Id. (0..65535)
      When v51VarCchType is 'none', this object is irrelevant."
     ::= {v5VarCchEntry 6}
v5VarCchTs OBJECT-TYPE
     SYNTAX  Integer32 
     MAX-ACCESS   read-write
     STATUS   current
     DESCRIPTION
     "The C-CH TS. Valid values: 16, 15, 31.
	  If  v51VarCchType=primary or secondary, the value must be 16 (RO).
      This object is applicable only if v51VarCchType is not 'none'.
      notApplicable=0."
     ::= {v5VarCchEntry 7}
v5VarCchPstn OBJECT-TYPE
      SYNTAX  INTEGER 
      { 
	  notApplicable(1),
      no           (2),
      yes          (3)
      }
      MAX-ACCESS   read-write
      STATUS   current
      DESCRIPTION
      "PSTN C-CH.
       Only one entry can have the value 'yes'.
       notApplicable - when v51VarCchType is none, secondary or standby."
      ::= {v5VarCchEntry 8}
v5VarCchIsdnTypes OBJECT-TYPE
     SYNTAX  Integer32 
     MAX-ACCESS   read-write
     STATUS   current
     DESCRIPTION
     "ISDN Types of C-CH.
      This object is a sum of 2**n, where n=Bit No. and Bit is '1':
		   Bit No.     ISDN Type
		      0          P
			  1          F
			  2          S
	  Bit value '1'= Yes
	  Bit value '0'= No
	  Example: P=No, F=Yes, S=Yes  (110H) will have the value 6. 
      Each Type is NA (notApplicable) when v51VarCchType is none, secondary 
      or standby. There is no special value for it, since each type can have
      only 2 values (1 or 0). When this object is NA, Agent will not refer its value
      (don't care)."
     ::= {v5VarCchEntry 9}
--Active Variant - Active Addresses Status table (V5.2 only)
v5VarStatTable  OBJECT-TYPE
     SYNTAX SEQUENCE OF V5VarStatEntry
     MAX-ACCESS not-accessible
     STATUS  current
     DESCRIPTION
      "This is a RO table. It includes only the Active Addresses of
       the Active Variant, their minimal Config data and Status."
     ::= { v51Variant 4}
v5VarStatEntry OBJECT-TYPE
     SYNTAX V5VarStatEntry
     MAX-ACCESS not-accessible
     STATUS current
	 DESCRIPTION
	 "An entry in table v5VarStatTable."
     INDEX {v5VarStatIdx}
     ::= { v5VarStatTable 1}
V5VarStatEntry ::=
      SEQUENCE {
      v5VarStatIdx        Integer32,
	  v5VarStatPrtId      Integer32,
	  v5VarStatPortType   INTEGER,
	  v5VarStatEfL3Addr   Integer32,
      v5VarStatPortState  INTEGER,
	  v5VarStatMasterTsa  Integer32,
	  v5VarStatCallState  INTEGER
      }
v5VarStatIdx OBJECT-TYPE
     SYNTAX  Integer32 
     MAX-ACCESS   not-accessible
     STATUS   current
     DESCRIPTION
     "Running Index (1..120). Up to 120 calls can be active at the same time
      on the Active Variant."
     ::= {v5VarStatEntry 1}
v5VarStatPrtId OBJECT-TYPE
     SYNTAX  Integer32 
     MAX-ACCESS   read-only
     STATUS   current
     DESCRIPTION
     "This object indicates the IO Port Id, the Address is connected to.
      The Port Id is a concatenation of SS:PP:TS of the port connected 
      to an Address of the Active Variant running on the V5.2 Master card.
      SS=IO Slot (1..12)
      PP=Port   (01..04)
      TS = TS   (00 for ports that don't have TSs ..31).
      Example:  50327  means IO-5, port-3, TS27."
     ::= {v5VarStatEntry 2}
v5VarStatPortType OBJECT-TYPE
      SYNTAX  INTEGER 
      { 
      nc              (1),
      pstn            (2), 
      isdnB1          (3),
	  isdnB2          (4),
	  cChannel        (5),
	  permanentB1     (6),
	  permanentB2     (7),
	  semiPermanentB1 (8),
	  semiPermanentB2 (9)
      }
      MAX-ACCESS   read-only
      STATUS   current
      DESCRIPTION
      "Address Port Type."
      ::= {v5VarStatEntry 3}
v5VarStatEfL3Addr OBJECT-TYPE
     SYNTAX  Integer32 (0..65535)
     MAX-ACCESS   read-only
     STATUS   current
     DESCRIPTION
     "This object indicates the EF/L3 Address of the IO port this entry 
      is connected to.
      The IO port is identified according to its EF/L3 Address:
      - for ISDN ports: EF Address. Valid values: 0..8175 
      - for PSTN ports: L3 Address. Valid values: 0..32767
      65535=notApplicable (FFFF)."
     ::= {v5VarStatEntry 4}
v5VarStatPortState OBJECT-TYPE
     SYNTAX  INTEGER
     {
     notUsed         (1),
	 normalOperation (2),
	 block           (5),
	 localUnblock    (11),
	 remoteUnblock   (12)
            }
     MAX-ACCESS  read-only
     STATUS  current
     DESCRIPTION
     "The State of the IO port this Address entry is connected to.
      The values were designed to match the relevant values of v51VarCfgIoState."
     ::= {v5VarStatEntry 5}
v5VarStatMasterTsa OBJECT-TYPE
     SYNTAX  Integer32 
     MAX-ACCESS   read-only
     STATUS   current
     DESCRIPTION
     "This will be the V5.2 Master Switch Allocated TSA Location. It is
      a concatenation of SS:PP:TS of the V5.2 Master card.
	  It indicates which is the exact port and TS allocated by the Local
	  Exchange on the V5.2 Link.
      SS=IO Slot (1..12)
      PP=Port   (01..04)
      TS = TS    (1..31).
      Example: 50323  means IO-5, port-3, TS23."
     ::= {v5VarStatEntry 6}
v5VarStatCallState OBJECT-TYPE
     SYNTAX  INTEGER 
     { 
     empty           (1),
     outOfService    (2), 
     deactive        (3),
	 actInit         (4),
	 accessAct       (5),
	 plActInit       (6),
	 plAct           (7),
	 loopback2       (8),
	 loopback1       (9),
	 loopback1A     (10),
	 null           (11),
	 pathInit       (12),
	 pathAbortReq   (13),
	 lineInfo       (14),
	 pathActive     (15),
	 blocked        (16),
	 disconnectReq  (17)  
     }
     MAX-ACCESS   read-only
     STATUS   current
     DESCRIPTION
     "Call State of the Address."
     ::= {v5VarStatEntry 7}
--V5.1 ML tables
v51MlCmdAndStatus OBJECT IDENTIFIER ::= {v51Ml 1}
v51MlCnfg   OBJECT IDENTIFIER ::= {v51Ml 2}
--ML command/status table
v51MlTable  OBJECT-TYPE
     SYNTAX SEQUENCE OF V51MlEntry
     MAX-ACCESS not-accessible
     STATUS  current
     DESCRIPTION
      "Variant Command and Status table."
     ::= { v51MlCmdAndStatus 1}
v51MlEntry OBJECT-TYPE
      SYNTAX V51MlEntry
      MAX-ACCESS not-accessible
      STATUS current
	  DESCRIPTION
	  "An entry in table v51MlTable."
      INDEX {v51MlSltIdx, v51MlPrtIdx}
      ::= { v51MlTable 1}
V51MlEntry ::=
      SEQUENCE {
      v51MlSltIdx           INTEGER,
      v51MlPrtIdx           Integer32,
      v51MlCurrActiveVar    Integer32,
      v51MlLeActiveReqVar   Integer32,
	  v51MlProtocolState    INTEGER,
	  v51MlUserActiveVarReq Integer32,
	  v51MlDeleteVarReq     Integer32,
	  v51MlSaveVariant      Integer32,
	  v51MlReadVariant      Integer32,
	  v51MlDeactivateVar    Integer32
	  }
v51MlSltIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index.
       For V5.2 this index is notApplicable."
      ::= {v51MlEntry 1}
v51MlPrtIdx OBJECT-TYPE
      SYNTAX  Integer32
      MAX-ACCESS  read-only
      STATUS  current
      DESCRIPTION
      "This attribute indicates a unique  port number of the ML having 
       V5 interface.
       Valid values: exPrt1 (1)..exPrt4 (4), inPrt1(101)..inPrt4(104),
       notApplicable(255) - for V5.2 only."
      ::= {v51MlEntry 2}
v51MlCurrActiveVar OBJECT-TYPE
      SYNTAX  Integer32  (0..128)
      MAX-ACCESS read-only
      STATUS current
      DESCRIPTION
      "For V5.1: the currently Active Variant Id. on this ML.
	   For V5.2: the currently Active Variant Id.
       128=none."
      ::= {v51MlEntry 3}
v51MlLeActiveReqVar OBJECT-TYPE
      SYNTAX  Integer32  (0..128)
      MAX-ACCESS read-only
      STATUS current
      DESCRIPTION
      "For V5.1: the Variant Id. that the Local Exchange (LE) 
                 requested to be Active on this ML.
       For V5.2: the Variant Id. that the Local Exchange (LE) 
                 requested to be Active.       
       128=none."
      ::= {v51MlEntry 4}
v51MlProtocolState OBJECT-TYPE
      SYNTAX  INTEGER  
      {
	  sysStartUp        (1),
  	  waitForVarId      (2),
  	  activatePstn      (3),
  	  restart1          (4),
 	  inService         (5),
 	  restart2          (6),
 	  restart3          (7),
 	  waitV5Init        (8),
 	  switchOver        (9),
 	  ctrlDataLinkRel1 (10),
 	  ctrlDataLinkRel2 (11),
 	  ctrlDataLinkRel3 (12),
 	  outOfService     (13),
 	  waitE1Reports    (14),
 	  waitL2StartUp    (15),
 	  waitLinkId       (16),
 	  waitRestart      (17),
	  notDefined       (18)
	  }
      MAX-ACCESS read-only
      STATUS current
      DESCRIPTION
      "Protocol State of the ML Active Variant.
       - sysStartUp   - an Establish request arrived to the V5.1 interface.
       - waitForVarId - the variant and the Interface Id were requested 
                        during the system start-up procedure.
       - activatePstn - activation of the PSTN Data Link was requested
                        during the system start-up procedure.
       - restart1     - the PSTN restart procedure is in process.
       - inService    - the V5.1 interface is IN SERVICE.
       - restart2     - the V5.1 is in AN5 state (sends restart complete
                        to all PSTN protocols and changes status to In-Service).
       - restart3     - the V5.1 is in AN6 state (sends restart complete
                        to all PSTN protocols and changes status to In-Service).
       - waitV5Init   - this state is entered when the system's management is in 
                        In-Service state, Switch to a new Variant is received 
                         and V5.1 interface will not be restarted.
       - switchOver   - this state is entered when the system's management is in 
                        In-Service state, Switch to a new Variant is received 
                        and V5.1 interface will be restarted.
       - ctrlDataLinkRel1 - this state is entered when the system's management is in 
                        In-Service state and Release Indication is received.
                        Timer TC1 is running in this state.
       - ctrlDataLinkRel2 - this state is entered on reception of Release-Indication
                        in 'restart3' state.
       - outOfService - the V5.1 interface is Out-of-Service.
       - notDefined   - V5.1 is not defined for this interface."
      ::= {v51MlEntry 5}
v51MlUserActiveVarReq OBJECT-TYPE
      SYNTAX  Integer32 (0..127)
      MAX-ACCESS read-write
      STATUS current
      DESCRIPTION
      "User Request to turn a certain Variant of the ML, to Active.
       This object specifies the Variant Id. requested by user to be Active.
       User's request is not always accepted."
      ::= {v51MlEntry 6}
v51MlDeleteVarReq OBJECT-TYPE
      SYNTAX  Integer32 (0..127)
      MAX-ACCESS read-write
      STATUS current
      DESCRIPTION
      "For V5.1: User Request to Delete a certain Variant of the ML.
	   For V5.2: User Request to Delete a certain Variant
       This object specifies the Variant Id. requested by user to be Delete.
       User's request will not be accepted if the required Variant Id is Active
       or during Reprovision process.
       This object is supported only up to MP R9."
      ::= {v51MlEntry 7}
v51MlSaveVariant OBJECT-TYPE
      SYNTAX  Integer32 (0..127)
      MAX-ACCESS read-write
      STATUS current
      DESCRIPTION
      "User Command to Save the TmpCnfg Variant data to a certain Variant Id of 
       the selected ML, in Current Cnfg. The value of this object specifies
	   the target Variant Id. 
       The data transferred should be: 
       - for V5.1: v51VarTable and v51VarCnfgTable parameters.
       - for V5.2: v51VarTable, v51VarCnfgTable and v51VarCchTable parameters.
       Upon Set command, the MUX will initiate a Sanity-Check process first: 
       - If	successful, the actual transfer will be performed. 
       - If warnings are detected, the user will have to perform the command 
         again to confirm the operation.
       - If errors are detected, transfer will NOT be performed.
       This object is supported only up to MP R9."
      ::= {v51MlEntry 8}
v51MlReadVariant OBJECT-TYPE
      SYNTAX  Integer32 (0..127)
      MAX-ACCESS read-write
      STATUS current
      DESCRIPTION
      "User Command to Read data from a certain Variant Id of the selected ML, 
       (in Current Cnfg) to the TmpCnfg. The value of this object specifies
	   the source Variant Id.
       The data transferred should be: 
       - for V5.1: v51VarTable and v51VarCnfgTable parameters.
       - for V5.2: v51VarTable, v51VarCnfgTable and v51VarCchTable parameters.
       The operation is valid only on existing Variants of the ML.
       This object is supported only up to MP R9."
      ::= {v51MlEntry 9}
v51MlDeactivateVar OBJECT-TYPE
      SYNTAX  Integer32 (0..127)
      MAX-ACCESS read-write
      STATUS current
      DESCRIPTION
      "User Request to Deactivate a certain Variant of the ML.
       This object specifies the Variant Id. requested by user to be Deactivated.
       User can deactivate a variant having Active Request status or Active
       status. Deactivating the variant having Active Status wil stop the V5.1
       operations on this link (for V5.2 it will stop completely the V5 activity)."
      ::= {v51MlEntry 10} 
--ML Cnfg Table
v51MlCnfgTable  OBJECT-TYPE
     SYNTAX SEQUENCE OF V51MlCnfgEntry
     MAX-ACCESS not-accessible
     STATUS  current
     DESCRIPTION
      "The write operation into the Table Objects is valid only
       to the TmpCnfg entry."
     ::= { v51MlCnfg 1}
v51MlCnfgEntry OBJECT-TYPE
      SYNTAX V51MlCnfgEntry
      MAX-ACCESS not-accessible
      STATUS current
	  DESCRIPTION
	  "An entry in table v51MlCnfgTable."
      INDEX {v51MlCnfgIdx, v51MlCnfgSltIdx, v51MlCnfgPrtIdx}
      ::= { v51MlCnfgTable 1}
V51MlCnfgEntry ::=
      SEQUENCE {
      v51MlCnfgIdx             Integer32,
      v51MlCnfgSltIdx          INTEGER,
      v51MlCnfgPrtIdx          Integer32,
      v51MlCnfgIfId            Integer32,
      v51MlCnfgStartupMode     INTEGER,
	  v51MlCnfgReprovision     INTEGER,
	  v51MlCnfgUnblockIoPorts  INTEGER,
	  v51MlCnfgRestartComplete INTEGER,
	  v51MlCnfgV52Application  INTEGER	  
      }
v51MlCnfgIdx OBJECT-TYPE
      SYNTAX  Integer32 (1..255)
      MAX-ACCESS  read-only
      STATUS  current
      DESCRIPTION
      "This attribute indicates the Idx of the Cnfg being accessed.
	   1..10 = Current Cnfg (data will be the same for all Current 
	           Configurations)
       255 = TmpCnfg."
      ::= {v51MlCnfgEntry 1}
v51MlCnfgSltIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index.
       For V5.2 this index will be notApplicable(255)."
      ::= {v51MlCnfgEntry 2}
v51MlCnfgPrtIdx OBJECT-TYPE
      SYNTAX  Integer32
      MAX-ACCESS  read-only
      STATUS  current
      DESCRIPTION
      "This attribute indicates a unique  port number of the ML having 
       V5 interface.
       Valid values: exPrt1 (1)..exPrt4 (4), inPrt1(101)..inPrt4(104)
       NA=255 (for V5.2 only)."
      ::= {v51MlCnfgEntry 3}
v51MlCnfgIfId OBJECT-TYPE
     SYNTAX  Integer32 (0..99999999)
     MAX-ACCESS   read-write
     STATUS   current
     DESCRIPTION
     "V5.1 Interface Id."
     ::= {v51MlCnfgEntry 4}
v51MlCnfgStartupMode OBJECT-TYPE
      SYNTAX  INTEGER 
      { 
      sync  (2),
      async (3)
      }
      MAX-ACCESS   read-write
      STATUS   current
      DESCRIPTION
      "Startup Mode."
      ::= {v51MlCnfgEntry 5}
v51MlCnfgReprovision OBJECT-TYPE
      SYNTAX  INTEGER 
      { 
      no  (2),
      yes (3)
      }
      MAX-ACCESS   read-write
      STATUS   current
      DESCRIPTION
      "Reprovision Support.
       - no : no reprovision support (=default)
       - yes: reprovision is supported."
      ::= {v51MlCnfgEntry 6}
v51MlCnfgUnblockIoPorts OBJECT-TYPE
      SYNTAX  INTEGER 
      { 
      disabled  (2),
      enabled   (3)
      }
      MAX-ACCESS   read-write
      STATUS   current
      DESCRIPTION
      "Unblock IO Ports on Startup.
       - disabled - disable sending Unblock request on restart
       - enabled  - request unblock of all IO ports ON RESTART (=default)."
      ::= {v51MlCnfgEntry 7}
v51MlCnfgRestartComplete OBJECT-TYPE
      SYNTAX  INTEGER 
      { 
      uponLeRestart       (2),
      uponPstnProtocolAck (3)
      }
      MAX-ACCESS   read-write
      STATUS   current
      DESCRIPTION
      "Send Restart Complete.
       - uponLeRestart - after receiving restart from the other side.
       - uponPstnProtocolAck - after receiving restart ack from PSTN 
         protocol (=default)."
      ::= {v51MlCnfgEntry 8}
v51MlCnfgV52Application OBJECT-TYPE
      SYNTAX  INTEGER 
      { 
      notApplicable (1),
      none          (2),
      endPoint      (3),
	  exchangePoint (4)
      }
      MAX-ACCESS   read-write
      STATUS   current
      DESCRIPTION
      "The V5.2 Application of the Mux.
       notApplicable - for Agents that don't support this object.
       none          - V5.2 is not used in the Mux.
       endPoint      - this V5.2 Application transfers voice of Analog Voice 
                       and ISDN cards of the Mux, to/from V5.2 Local Exchange.
       exchangePoint - this V5.2 Application exchanges voice of ML cards (coming
                       from other devices) to/from V5.2 Local Exchange."
      ::= {v51MlCnfgEntry 9}
--V5.1 Access port tables
v51IoCnfgTable  OBJECT-TYPE
     SYNTAX SEQUENCE OF V51IoCnfgEntry
     MAX-ACCESS not-accessible
     STATUS  current
     DESCRIPTION
      "The write operation into the Table Objects is valid only
       to the TmpCnfg entry."
     ::= { v51AccessPort 1}
v51IoCnfgEntry OBJECT-TYPE
      SYNTAX V51IoCnfgEntry
      MAX-ACCESS not-accessible
      STATUS current
	  DESCRIPTION
	  "An entry in table v51IoCnfgTable."
      INDEX {v51IoCnfgIdx, v51IoCnfgSltIdx, v51IoCnfgPrtIdx}
      ::= { v51IoCnfgTable 1}
V51IoCnfgEntry ::=
      SEQUENCE {
      v51IoCnfgIdx         Integer32,
      v51IoCnfgSltIdx      INTEGER,
      v51IoCnfgPrtIdx      Integer32,
      v51IoCnfgSType       INTEGER,
      v51IoCnfgFType       INTEGER,
      v51IoCnfgPType       INTEGER
      }
v51IoCnfgIdx OBJECT-TYPE
      SYNTAX  Integer32 (1..255)
      MAX-ACCESS  read-only
      STATUS  current
      DESCRIPTION
      "This attribute indicates the Idx of the Cnfg being accessed.
	   1..10 = Current Cnfg (data will be the same for all Current 
	           Configurations)
       255 = TmpCnfg."
      ::= {v51IoCnfgEntry 1}
v51IoCnfgSltIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index"
      ::= {v51IoCnfgEntry 2}
v51IoCnfgPrtIdx OBJECT-TYPE
      SYNTAX  Integer32
      MAX-ACCESS  read-only
      STATUS  current
      DESCRIPTION
      "This attribute indicates a unique  port number of the Io having 
       V5 interface.
       Valid values: exPrt1 (1)..exPrt16 (16)"
      ::= {v51IoCnfgEntry 3}
v51IoCnfgSType OBJECT-TYPE
      SYNTAX  INTEGER 
      { 
      notApplicable (1),
      no  (2),
      yes (3)
      }
      MAX-ACCESS   read-write
      STATUS   current
      DESCRIPTION
      "This object indicates if S Type Signaling will be used by this ISDN port
       (yes/no).
       notApplicable - for PSTN ports."
      ::= {v51IoCnfgEntry 4}
v51IoCnfgFType OBJECT-TYPE
      SYNTAX  INTEGER 
      { 
      notApplicable (1),
      no  (2),
      yes (3)
      }
      MAX-ACCESS   read-write
      STATUS   current
      DESCRIPTION
      "This object indicates if F Type Signaling will be used by this ISDN port
       (yes/no).
       notApplicable - for PSTN ports."
      ::= {v51IoCnfgEntry 5}
v51IoCnfgPType OBJECT-TYPE
      SYNTAX  INTEGER 
      { 
      notApplicable (1),
      no  (2),
      yes (3)
      }
      MAX-ACCESS   read-write
      STATUS   current
      DESCRIPTION
      "This object indicates if P Type Signaling will be used by this ISDN port
       (yes/no).
       notApplicable - for PSTN ports."
      ::= {v51IoCnfgEntry 6}
-- Traps
--NOTIFICATIONS
v51IfEvents OBJECT-IDENTITY
   STATUS  current
   DESCRIPTION
   "The events for the WAN V5.1."
    ::= { v51If 0 }
activeVariantTrap  NOTIFICATION-TYPE
   OBJECTS       { v51MlCurrActiveVar }
   STATUS  current
   DESCRIPTION
   "This trap is sent when the Active Variant of a Link is changed (that
    includes the case when a user performs Save to the Variant that is Active)."
   ::= { v51IfEvents 1 }
-- 
-- file :v:\doc\rdv\mib\ver485\voip\voip.txt
-- 
-- --------------------------------------------------------------------------------------
--Title:  RAD's Voice Over IP MIB
--By:     Liora Gafni
--Date :  28-Sep-99
--Description: This MIB contains parameters that were not defined in the ITU H.341 MIB
--             and are required for RAD products.
--
--Last Update:  28/05/02
--By:  			Liora Gafni
--File:  v:\doc\rdv\mib\ver485\voip\voip.txt
-- --------------------------------------------------------------------------------------
--IMPORTS
--      enterprises                            FROM SNMPv2-SMI
--      DisplayString                          FROM SNMPv2-TC
--      IpAddress                              FROM SNMPv2-SMI
--      OCTET STRING                           FROM SNMPv2-TC
--      OBJECT-TYPE                            FROM RFC-1212
--      TAddress                               FROM	SNMPv2-TC
--      MmTAddressTag,MmEndpointID,
--      MmAliasAddress,MmH323EndpointType,
--      MmGatekeeperID,MmGlobalIdentifier      FROM MULTI-MEDIA-MIB-TC;
--wanGen   OBJECT IDENTIFIER ::= {radWan 1} (see mpmx.txt)
voipWanGen OBJECT IDENTIFIER ::= {wanGen 7} --(see mpmx.txt)
-- VOIP Card Configuration
voipCardConfig OBJECT-TYPE   
      SYNTAX  Integer32 
      MAX-ACCESS  read-only    
      STATUS  current
      DESCRIPTION
      "The value of this object determines the VOIP card configuration.
       Bit 0 (LSB): if 1 - a GK exists. If 0 - no GK exists in this card.
       The other bits may be used in the future."
      ::= { voipWanGen 1 }
-- GK General Parameters table
gkGenTable  OBJECT-TYPE
     SYNTAX SEQUENCE OF GkGenEntry
     MAX-ACCESS not-accessible
     STATUS  current
     DESCRIPTION
      "General parameters for the VOIP GateKeeper."
     ::= { voipWanGen 2 }
gkGenEntry OBJECT-TYPE
      SYNTAX GkGenEntry
      MAX-ACCESS not-accessible
      STATUS current
	  DESCRIPTION
	  "An entry in table gkGenTable."
      INDEX {ifIndex}
      ::= { gkGenTable 1}
GkGenEntry ::=
      SEQUENCE {
      gkGenCallMode         INTEGER,
      gkGenMaxConnections   Integer32,
	  gkGenDefaultDistance  Integer32,
	  gkGenOutOfZoneDist    Integer32,
	  gkGenCallAcceptPolicy	INTEGER,
	  gkGenIrqInterval      Integer32,
	  gkGenQ931Port         Integer32,
	  gkGenRasPort          Integer32,
      gkGenRegPolicy        INTEGER,
      gkGenZoneId           OCTET STRING      
	  }
gkGenCallMode OBJECT-TYPE
      SYNTAX  INTEGER
      {
      direct           (2),
      routed           (3),
      notApplicable    (255)
            }
      MAX-ACCESS  read-write
      STATUS  current
      DESCRIPTION
      "This parameters shows whether the calls will go through the GK (routed) or
       whether the calls will be direct from Endpoint to Endpoint without involving
       the GK (direct)."
      ::= {gkGenEntry 1}
gkGenMaxConnections OBJECT-TYPE
      SYNTAX  Integer32  
      MAX-ACCESS  read-write
      STATUS  current
      DESCRIPTION
      "MAX no. of connections enabled by the GK to take place simultaneously.
       If the MAX no. of calls is exceeded, a busy signal will be returned."
      ::= {gkGenEntry 2}
gkGenDefaultDistance   OBJECT-TYPE
      SYNTAX  Integer32  
      MAX-ACCESS  read-write
      STATUS  current
      DESCRIPTION
      "The Distance allowed for endpoints that are registered dynamically."
      ::= {gkGenEntry 3}
gkGenOutOfZoneDist   OBJECT-TYPE
      SYNTAX  Integer32  
      MAX-ACCESS  read-write
      STATUS  current
      DESCRIPTION
      "The Distance allowed for an out of zone endpoint that is making a call
       through the gatekeeper."
      ::= {gkGenEntry 4}
gkGenCallAcceptPolicy OBJECT-TYPE
      SYNTAX  INTEGER
      {
      acceptAll      (2),
      registeredOnly (3),
	  predefinedOnly (4)
                  }
      MAX-ACCESS  read-write
      STATUS  current
      DESCRIPTION
      "Defines the policy concerning the incoming phone calls.
       The importance of this parameter is for bidding and security matters.
       Accept All - all the incoming calls are accepted.
       Registered Only - the calls are accepted from the predefined endpoints only,
       which are endpoints that have previously registered with the gatekeeper.
       Predefined Only - with this policy only the calls from the statically
       registered endpoints can be accepted."
      ::= {gkGenEntry 5}
gkGenIrqInterval   OBJECT-TYPE
      SYNTAX  Integer32  
      MAX-ACCESS  read-write
      STATUS  current
      DESCRIPTION
      "In order for the Gatekeeper to determine if an endpoint is turned off,
       or has otherwise entered a failure mode, the Gatekeeper may use the Information
       Request (IRQ) to poll the endpoints at the certain interval (in seconds).
       THE IRQ INTERVAL controls the frequency the gk sends IRQ messages.
       This message is sent to all on-line endpoints registered as dynamic in order
       to verify they are really on-line. This is done to detect terminals that
       shut off without sending the required URQ message that notifies the gk that
       they are no longer on-line.
       Endpoints failing to respond too many times have their dynamic properties
       unregistered. Choosing the desired interval should take into account the
       following factors : 
       IRQ messages add to the traffic already present over the network and the
       shorter the interval the more IRQ messages will be sent. On the other hand the
       longer the delay the longer it will take for the gk to detect dynamic
       registrations that have ceased to actually be on-line. Note that the
       IRQ interval relates to each endpoint and the actual number of the IRQ messages
       the gk will create should be multiplied by the number of endpoints
       registered dynamically."
      ::= {gkGenEntry 6}
gkGenQ931Port OBJECT-TYPE
      SYNTAX  Integer32
      MAX-ACCESS  read-write
      STATUS  current
      DESCRIPTION
      "Q.931 Port no."
      ::= {gkGenEntry 7}
gkGenRasPort OBJECT-TYPE
      SYNTAX  Integer32
      MAX-ACCESS  read-write
      STATUS  current
      DESCRIPTION
      "RAS Port no."
      ::= {gkGenEntry 8}
gkGenRegPolicy OBJECT-TYPE
      SYNTAX  INTEGER
      {
      acceptAll          (2),
      predefinedOnly     (3),
	  registrationReject (4)
                  }
      MAX-ACCESS  read-write
      STATUS  current
      DESCRIPTION
      "Policy of dynamic registrations in the Gatekeeper.
	   The GK will act according to the following policies:
       Accept All      - The GK will enable all requesting endpoints to register dynamically.
       Predefined Only - The GK will enable registration of endpoints that were registered
                         previously via static registration.
       Registration Reject - No endpoint may register dynamically."
      ::= {gkGenEntry 9}
gkGenZoneId OBJECT-TYPE
      SYNTAX  OCTET STRING
      MAX-ACCESS  read-write
      STATUS  current
      DESCRIPTION
      "Zone Identifier: 1 or 2 digits, (0-9)(1-9)."  
      ::= {gkGenEntry 10}
-- GK Endpoints Table
gkEndpTable  OBJECT-TYPE
     SYNTAX SEQUENCE OF GkEndpEntry
     MAX-ACCESS not-accessible
     STATUS  current
     DESCRIPTION
      "Table containing the Endpoints that are registered (statically & Dynamically)
       with the current GK."
     ::= { voipWanGen 3 }
gkEndpEntry OBJECT-TYPE
      SYNTAX GkEndpEntry
      MAX-ACCESS not-accessible
      STATUS current
	  DESCRIPTION
	  "An entry in table gkEndpTable."
      INDEX {ifIndex,
             gkEndpAliasTag,
             gkEndpAlias}
      ::= { gkEndpTable 1}
GkEndpEntry ::=
      SEQUENCE {
	  gkEndpAliasTag  MmAliasTag,
	  gkEndpAlias     MmAliasAddress,
	  gkEndpRowStatus RowStatus,
      gkEndpAddressTag MmTAddressTag,
	  gkEndpAddress   TAddress,
      gkEndpID        MmEndpointID,
      gkEndpType      MmH323EndpointType,
	  gkEndpQ931Port  Integer32,
	  gkEndpDistance  Integer32,
      gkEndpRegMode   INTEGER,
	  gkEndpSetOnline INTEGER,
	  gkEndpStatus    INTEGER
      }
gkEndpAliasTag OBJECT-TYPE
      SYNTAX   MmAliasTag
      MAX-ACCESS  read-only
      STATUS  current
      DESCRIPTION
      "Alias Tag of the Endpoint."
      ::= {gkEndpEntry 1}
gkEndpAlias OBJECT-TYPE
      SYNTAX   MmAliasAddress
      MAX-ACCESS  read-only
      STATUS  current
      DESCRIPTION
      "Alias of the Endpoint."
      ::= {gkEndpEntry 2}
gkEndpRowStatus OBJECT-TYPE
      SYNTAX  RowStatus
      MAX-ACCESS  read-create
      STATUS  current
      DESCRIPTION
      "The row status of the entry. This object is required to create
       or delete rows remotely by a manager. "
      ::= {gkEndpEntry 3}
gkEndpAddressTag  OBJECT-TYPE
      SYNTAX  MmTAddressTag         
      MAX-ACCESS  read-create
      STATUS  current
      DESCRIPTION
      "Address Tag of Endpoint."
      ::= {gkEndpEntry 4}
gkEndpAddress OBJECT-TYPE
      SYNTAX  TAddress
      MAX-ACCESS  read-create
      STATUS  current
      DESCRIPTION
      "Address of Endpoint."
      ::= {gkEndpEntry 5}
gkEndpID OBJECT-TYPE
      SYNTAX   MmEndpointID
      MAX-ACCESS  read-create
      STATUS  current
      DESCRIPTION
      "Endpoint Identifier."
      ::= {gkEndpEntry 6}
gkEndpType OBJECT-TYPE
      SYNTAX  MmH323EndpointType
      MAX-ACCESS  read-create
      STATUS  current
      DESCRIPTION
      "This parameter shows whether the current endpoint is a GW or Terminal or
       any other type of H.323 endpoint."
      ::= {gkEndpEntry 7}
gkEndpQ931Port OBJECT-TYPE
      SYNTAX  Integer32
      MAX-ACCESS  read-create
      STATUS  current
      DESCRIPTION
      "Q.931 Port no."
      ::= {gkEndpEntry 8}
gkEndpDistance OBJECT-TYPE
      SYNTAX  Integer32
      MAX-ACCESS  read-create
      STATUS  current
      DESCRIPTION
      "Distance from the current endpoint to the GateKeeper with which it is
       Registered."
      ::= {gkEndpEntry 9}
gkEndpRegMode OBJECT-TYPE
      SYNTAX  INTEGER
	  {
	  dynamic (2),
	  static  (3)
	  }
      MAX-ACCESS  read-only
      STATUS  current
      DESCRIPTION
      "This parameter shows whether the Endpoint Registered Dynamically or Statically."
      ::= {gkEndpEntry 10}
gkEndpSetOnline OBJECT-TYPE
      SYNTAX  INTEGER
	  {
	  uponDynamicReg (2),
	  always (3)
	  }
      MAX-ACCESS  read-create
      STATUS  current
      DESCRIPTION
      "This parameter shows whether the endpoint will always be online or whether it
       will be on line upon Dynamic Registration only."
      ::= {gkEndpEntry 11}
gkEndpStatus OBJECT-TYPE
      SYNTAX  INTEGER
	  {
	  online (2),
	  offline (3)
	  }
      MAX-ACCESS  read-only
      STATUS  current
      DESCRIPTION
      "This parameter shows whether the endpoint is currently online."
      ::= {gkEndpEntry 12}
-- GK Neighbors table
gkNeighbTable  OBJECT-TYPE
     SYNTAX SEQUENCE OF GkNeighbEntry
     MAX-ACCESS not-accessible
     STATUS  current
     DESCRIPTION
      "Table of GateKeepers that are Neighbors of the current Gatekeeper."
     ::= { voipWanGen 4 }
gkNeighbEntry OBJECT-TYPE
      SYNTAX GkNeighbEntry
      MAX-ACCESS not-accessible
      STATUS current
	  DESCRIPTION
	  "An entry in table gkNeighbTable."
      INDEX {ifIndex,
             gkNeighbAddressTag,
             gkNeighbAddress}
      ::= { gkNeighbTable 1}
GkNeighbEntry ::=
      SEQUENCE {
      gkNeighbAddressTag        MmTAddressTag,
	  gkNeighbAddress           TAddress,
	  gkNeighbRowStatus         RowStatus,
      gkNeighbLeadingAlias      MmAliasAddress,
      gkNeighbDistance          Integer32,
	  gkNeighbDescription       MmGatekeeperID
      }
gkNeighbAddressTag  OBJECT-TYPE
      SYNTAX  MmTAddressTag            
      MAX-ACCESS  read-only
      STATUS  current
      DESCRIPTION
      "Tag of GK or GW address."
      ::= {gkNeighbEntry 1}
gkNeighbAddress OBJECT-TYPE
      SYNTAX  TAddress
      MAX-ACCESS  read-only
      STATUS  current
      DESCRIPTION
      "Address of GK or GW."
      ::= {gkNeighbEntry 2}
gkNeighbRowStatus OBJECT-TYPE
      SYNTAX  RowStatus
      MAX-ACCESS  read-create
      STATUS  current
      DESCRIPTION
      "The row status of the entry. This object is required to create
       or delete rows remotely by a manager. "
      ::= {gkNeighbEntry 3}
gkNeighbLeadingAlias  OBJECT-TYPE
      SYNTAX  MmAliasAddress
      MAX-ACCESS  read-create
      STATUS  current
      DESCRIPTION
      "This is the Leading Alias Address (Zone Prefix) that will be dialed in order to reach 
       the specific neighbor."
      ::= {gkNeighbEntry 4}
gkNeighbDistance OBJECT-TYPE
      SYNTAX  Integer32  
      MAX-ACCESS  read-create
      STATUS  current
      DESCRIPTION
      "Distance between the local GateKeeper and the Neighbor GateKeeper."       
      ::= {gkNeighbEntry 5}
gkNeighbDescription OBJECT-TYPE
      SYNTAX  MmGatekeeperID
      MAX-ACCESS  read-create
      STATUS  current
      DESCRIPTION
      "ASCII String Description for identifying the Neighbor."       
      ::= {gkNeighbEntry 6}
-- GW General Parameters table
gwGenTable  OBJECT-TYPE
     SYNTAX SEQUENCE OF GwGenEntry
     MAX-ACCESS not-accessible
     STATUS  current
     DESCRIPTION
      "General parameters for the VOIP GateWay."
     ::= { voipWanGen 5 }
gwGenEntry OBJECT-TYPE
      SYNTAX GwGenEntry
      MAX-ACCESS not-accessible
      STATUS current
	  DESCRIPTION
	  "An entry in table gwGenTable."
      INDEX {ifIndex}
      ::= { gwGenTable 1}
GwGenEntry ::=
      SEQUENCE {
	  gwGenGwId           MmEndpointID,
	  gwGenQ931Port       Integer32,
	  gwGenRasPort        Integer32,
      gwGenMode           INTEGER,
	  gwGenVoipExtension  Integer32,
	  gwGenRemGwAddress   TAddress,
      gwGenMaxConnections Integer32,
	  gwGenTOS            OCTET STRING,
	  gwGenBackupGkAddr   TAddress,
	  gwGenTimeToRegister Integer32        
	  }
gwGenGwId OBJECT-TYPE
      SYNTAX  MmEndpointID
      MAX-ACCESS  read-write
      STATUS  current
      DESCRIPTION
      "A character string of up to 20 characters identifying the gateway."       
      ::= {gwGenEntry 1}
gwGenQ931Port OBJECT-TYPE
      SYNTAX  Integer32
      MAX-ACCESS  read-write
      STATUS  current
      DESCRIPTION
      "The Q.931 port no. of the Gateway."       
      ::= {gwGenEntry 2}
gwGenRasPort OBJECT-TYPE
      SYNTAX  Integer32
      MAX-ACCESS  read-write
      STATUS  current
      DESCRIPTION
      "The RAS port no. of the Gateway."       
      ::= {gwGenEntry 3}
gwGenMode OBJECT-TYPE
      SYNTAX  INTEGER
      {
      disable       (2),
      cvsIp         (3),
	  standard      (4),
      notApplicable (255)
            }
      MAX-ACCESS  read-write
      STATUS  current
      DESCRIPTION
      "GW Mode:
       disable - The GW is not activated.
       cvsIp   - CVS is a Compressed Voice System.
                 The GW will compress voice calls at a ratio of
                 16 to 1. 16 time slots of E1/T1 will be compressed into
                 1 E1/T1 time slot. When this mode is used the Gateway can
                 communicate directly with another Gateway without a Gatekeeper.
       standard - This mode includes a Gateway & a Gatekeeper."
     ::= {gwGenEntry 4}
gwGenVoipExtension OBJECT-TYPE
       SYNTAX  Integer32
       MAX-ACCESS  read-write
       STATUS  current
       DESCRIPTION
      "This is the extension number of the VOIP protocol.
	   It is used for the Voice card to identify the calls made through the VoIP card.
	   The user may choose an arbitrary value for this field, the only restriction is that
	   there must be no other entity registered with the same extension number."
	   ::= {gwGenEntry 5}
gwGenRemGwAddress OBJECT-TYPE
      SYNTAX  TAddress
      MAX-ACCESS  read-write
      STATUS  current
      DESCRIPTION
      "Defines the remote gateway address (IP + port). It is important for gateway
       to gateway connection."       
      ::= {gwGenEntry 6}
gwGenMaxConnections OBJECT-TYPE
      SYNTAX  Integer32  
      MAX-ACCESS  read-write
      STATUS  current
      DESCRIPTION
      "MAX no. of connections enabled by the GW."
      ::= {gwGenEntry 7}
gwGenTOS OBJECT-TYPE
      SYNTAX  OCTET STRING  
      MAX-ACCESS  read-write
      STATUS  current
      DESCRIPTION
      "Type of Service.
       The BIT Format is consistent with the IP standard:
       +-----+-----+-----+-----+-----+-----+-----+-----+
       |                 |                       |     |
       |   PRECEDENCE    |    TYPE OF SERVICE    |  0  |
       |                 |                       |     |
       +-----+-----+-----+-----+-----+-----+-----+-----+
       	  0	   1	  2	    3	  4	    5	  6		7
	   At present, only 1 BYTE will be used, bits 0 (MSB) - 7 (LSB).
	   The precedence consists of 3 BITS (0-2):
       111 - Network Control
       110 - Internetwork Control
       101 - CRITIC/ECP
       100 - Flash Override
       011 - Flash
       010 - Immediate
       001 - Priority
       000 - Routine
       The TOS values BITS (3-5):
       Bit 3 is the Delay:       0 = Normal Delay,       1 = Low Delay.
       Bit 4 is the Throughput:  0 = Normal Throughput,  1 = High Throughput.
       Bit 5:is the Reliability: 0 = Normal Reliability, 1 = High Reliability.
       Bits 6 & 7 are for future use and their current value is 0."
      ::= {gwGenEntry 8}
gwGenBackupGkAddr OBJECT-TYPE
      SYNTAX  TAddress
      MAX-ACCESS  read-write
      STATUS  current
      DESCRIPTION
      "Defines the backup gatekeeper address (IP + port).
       When the backup GK is active, all the calls will be routed to it and it
       will be responsible for their address translation.
       The first GK address is defined in the standard H.341 MIB."
     ::= {gwGenEntry 9}
gwGenTimeToRegister OBJECT-TYPE
      SYNTAX  Integer32  
      MAX-ACCESS  read-write
      STATUS  current
      DESCRIPTION
      "The GW should register every 'Time to Register' seconds with the GK.
       The 'Time to Register' range is from 0 to 900 seconds in intervals of 60 seconds.
	   0 means Never.
       When the GK becomes active the Gateways that are up can register so that
       the GK has an updated list of active Registered Gateways."
     ::= {gwGenEntry 10}
-- RAD's addition to h245ConfigurationTable         
radH245ConfigTable OBJECT-TYPE
      SYNTAX SEQUENCE OF RadH245ConfigEntry
      MAX-ACCESS not-accessible
      STATUS current
      DESCRIPTION
      "This table contains information about H.245 configuration parameters.
       It is a list of configuration parameter entries.
       The number of entries equals to the number of H.245 stacks in a system."
      ::= { voipWanGen 6 }
radH245ConfigEntry OBJECT-TYPE
      SYNTAX RadH245ConfigEntry
      MAX-ACCESS not-accessible
      STATUS current
      DESCRIPTION 
      "It contains objects that describe the H.245 configuration parameters."
      INDEX { ifIndex }
      ::= { radH245ConfigTable 1 }
RadH245ConfigEntry ::=
      SEQUENCE {
      h245MaxJitter   Integer32,
	  h245Tunneling   INTEGER
	  } 
h245MaxJitter OBJECT-TYPE
      SYNTAX  Integer32
      MAX-ACCESS  read-write
      STATUS  current
      DESCRIPTION
      "Maximum peak to peak delivery (in miliseconds) of audio packets
       to the transport layer that the transmitter shall cause."
      ::= {radH245ConfigEntry 1}
h245Tunneling OBJECT-TYPE
      SYNTAX  INTEGER
      {
      disable		(2),
      enable	    (3)
 	  }                  
      MAX-ACCESS  read-write
      STATUS  current
      DESCRIPTION
      "This variable enables or disables the usage of Tunneling."
      ::= {radH245ConfigEntry 2}
-- RTP Multiplexing
rtpMultiplexTable  OBJECT-TYPE
     SYNTAX SEQUENCE OF RtpMultiplexEntry
     MAX-ACCESS not-accessible
     STATUS  current
     DESCRIPTION
      "RTP Multiplexing table.
      RTP Multiplexing: In IP telephony system, the addition of packet headers,
      including IP, UDP and RTP headers, increases the header overhead, decreasing
      efficient transmission. Also, because of large numbers of short voice
      packets flowing into the network, Internet load increases, eventually
      resulting in large delay and packet loss. RTP Multiplexing is a way to send
      multiple RTP packets between a pair of Gateways, with a single
      IP frame. This will reduces the header overhead and decreases delay by
      enabling voice transmission with fewer packets."
     ::= { voipWanGen 7 }
rtpMultiplexEntry OBJECT-TYPE
      SYNTAX RtpMultiplexEntry
      MAX-ACCESS not-accessible
      STATUS current
	  DESCRIPTION
	  "An entry in table rtpMultiplexTable."
      INDEX {ifIndex}
      ::= { rtpMultiplexTable 1}
RtpMultiplexEntry ::=
      SEQUENCE {
      rtpMultiplexedRtp     INTEGER,
      rtpMultiplexFrameSize Integer32,
	  rtpMultiplexInterval  Integer32
      }
rtpMultiplexedRtp  OBJECT-TYPE
      SYNTAX  INTEGER {
	  disable         (2),
	  multiplexType1  (3),
	  multiplexType2  (4)
	  }                  
      MAX-ACCESS  read-write
      STATUS  current
      DESCRIPTION
      "RTP Multiplexing is a way to send multiple RTP packets with a single IP frame.
       This will reduce the header overhead and decrease the delay by enabling
       voice transmission with fewer packets.
       The option of this field are:
       Disable - No RTP Multiplexing.
	   multiplexType1 - medium level  of compression for RTP multiplexing.
   	   multiplexType2 - high level of compression for RTP multiplexing.
       Using the High Compression algorithm is more efficient
       but will cause the loss of some RTP header information.
       If RTP statistics are important, the medium compression must be selected."
      ::= {rtpMultiplexEntry 1}
rtpMultiplexFrameSize  OBJECT-TYPE
      SYNTAX  Integer32 
      MAX-ACCESS  read-write
      STATUS  current
      DESCRIPTION
      "Defines the maximum size in Bytes of the multiplexed frame.
       In some cases this must be limited to avoid IP fragmentation,
       which makes the multiplexing useless, and can also decrease
       the damage in case of the frame loss.
       At present the size is 1500."
      ::= {rtpMultiplexEntry 2}
rtpMultiplexInterval  OBJECT-TYPE
      SYNTAX  Integer32                   
      MAX-ACCESS  read-write
      STATUS  current
      DESCRIPTION
      "Defines the maximum amout of time (msec.) between multiplexed frames 
       that are sent.
       Legal values: 10-90 msec."
       ::= {rtpMultiplexEntry 3}
                                                                                                                                                                                                                                                                                                                                                                                                                                                                                                                                                                                                                                               -- 
-- file :v:\doc\rdv\mib\ver510\ipmux.txt
-- 
--Title:     RAD's IP-MUX PRODUCT MIB
--Version:   1.0
--Date:      27.05.99
--By:        Ilana Schvetz
--File:      ipmux.txt
--
--Last update: 26-Oct-04 by Liora Gafni
ip2If OBJECT IDENTIFIER ::= { diverseIfWanGen 7 }
-- ip2If Configuration table  
ip2IfTable OBJECT-TYPE
       SYNTAX  SEQUENCE OF Ip2IfEntry
       MAX-ACCESS  not-accessible
       STATUS  current
       DESCRIPTION
       "Channels Configuration Table."
       ::= { ip2If 1 }
ip2IfEntry OBJECT-TYPE
       SYNTAX Ip2IfEntry
       MAX-ACCESS not-accessible
       STATUS current
       DESCRIPTION
          "Application layer configuration per link"
       INDEX   { ip2IfChannelIndex }
       ::= { ip2IfTable 1 }
Ip2IfEntry ::=
         SEQUENCE {
         ip2IfChannelIndex	    Integer32,
         ip2IfRowStatus	        RowStatus,
         ip2IfOperStatus	    INTEGER,
         ip2IfAdminStatus	    INTEGER,
         ip2IfDestAddr		    IpAddress,
         ip2IfNextHop		    IpAddress,
         ip2IfDestPort		    Integer32,
         ip2IfMacAddr		    MacAddress,
         ip2IfJitterBuffer	    Integer32,
		 ip2IfTos			    Integer32,
		 ip2IfTDMBytesInFrame   Integer32,
		 ip2IfVlanSupport       INTEGER,
		 ip2IfVlanIdentifier    Integer32,
		 ip2IfVlanFramePriority Integer32,
		 ip2IfExitPort          INTEGER,
		 ip2IfVoiceOos			OCTET STRING,
		 ip2IfDataOos			OCTET STRING,
		 ip2IfBundleUsage 		Integer32,
		 ip2IfOAM				OCTET STRING,
		 ip2IfTDMoIpMode		INTEGER,
		 ip2IfTimeElapsed		Integer32,
		 ip2IfValidIntervals    Integer32,
		 ip2IfFarEndType        INTEGER,
		 ip2IfRdnState			INTEGER,
		 ip2IfSourceAddr		IpAddress,
		 ip2IfBandWidth 		Integer32,
		 ip2IfMeasuredSilence   Integer32,
		 ip2IfPayloadType		INTEGER,
		 ip2IfProtocolVersion	INTEGER,
         ip2IfTdmBackUpNextHop  IpAddress,	
		 ip2IfOosTxEnable		INTEGER,		 
		 ip2IfConnCheckPktFrequency Integer32,
         ip2IfConnPktTimeOutCycles  Integer32,
		 ip2IfMfRelay			    INTEGER,
		 ip2IfTxGain			    Integer32,
		 ip2IfSuperTandem			INTEGER,
		 ip2IfSrcPort				Integer32,
     	 ip2IfModemCalls            INTEGER,
         ip2IfMinPulseWidth         Integer32,
		 ip2IfMinPowerLevel         Integer32,
		 ip2IfEchoCanceler          INTEGER,
		 ip2IfCodingLaw             INTEGER,
		 ip2IfCustomToneDetect      INTEGER,
		 ip2IfCallerIdDelay	        Integer32,
		 ip2IfConnectivityMode      INTEGER,
		 ip2IfMfcSpoofing           INTEGER,
		 ip2IfToneAckInterval       Integer32 ,
 		 ip2IfNoiseLevelForVAD      INTEGER
	}
ip2IfChannelIndex OBJECT-TYPE
    SYNTAX  Integer32 
    MAX-ACCESS  read-only
    STATUS  current
    DESCRIPTION
    "The channel index, which is actualy the bundle ID."
    ::= { ip2IfEntry 1 }
ip2IfRowStatus OBJECT-TYPE
    SYNTAX  RowStatus
    MAX-ACCESS  read-create
    STATUS  current
    DESCRIPTION
    "This parameter allows NMS to create/delete entries of this table."
    ::= { ip2IfEntry 2 }
ip2IfOperStatus OBJECT-TYPE
    SYNTAX       INTEGER {
    down		(2),
    up	        (3),
    disabled    (4),
    remoteFail  (5),
    localFail	(6),
	unavailable (7),
	validationFail  (8),
	standby		(9),
	tdmFail	   (10),
	hwMismatch (11)
    }
    MAX-ACCESS    read-only
    STATUS        current
    DESCRIPTION
    "The actual link status.
    remoteFail - No Rx.
    localFail  - No Tx.
    unavailable - No echo replay or replay with invalid code or when connection is in Test state.
    valiodationFail - Connection is in not valid state.
    standby - offline (can be in pre-sync mode).
    tdmFail - oper status is down cause of failure in the tdm.
    hwMismatch - the bundle exists on a card that is not installed or has a different
                 type than the programmed card."
    ::= { ip2IfEntry 3 }
ip2IfAdminStatus OBJECT-TYPE
    SYNTAX       INTEGER {
    down		(2),
    up	    (3)
    }
    MAX-ACCESS    read-create
    STATUS        current
    DESCRIPTION
    "The desired state of the link."
    ::= { ip2IfEntry 4 }
ip2IfDestAddr OBJECT-TYPE
    SYNTAX  IpAddress 
    MAX-ACCESS  read-create
    STATUS  current
    DESCRIPTION
    "The destination IP address."
    ::= { ip2IfEntry 5 }
ip2IfNextHop OBJECT-TYPE
    SYNTAX  IpAddress 
    MAX-ACCESS  read-create
    STATUS  current
    DESCRIPTION
    "The next hop to which the frame should be sent.
     Default value - 0.0.0.0. 
     Upon setting the default value the frame is sent 
     to the default Gateway."
    ::= { ip2IfEntry 6 }
ip2IfDestPort OBJECT-TYPE
    SYNTAX  Integer32 
    MAX-ACCESS  read-create
    STATUS  current
    DESCRIPTION
    "The destination Bundle at the far-end device."
    ::= { ip2IfEntry 7 }
ip2IfMacAddr OBJECT-TYPE
    SYNTAX  MacAddress
    MAX-ACCESS  read-only
    STATUS  current
    DESCRIPTION
    "The Destination MAC address of the next hop or 
     destination station."
    ::= { ip2IfEntry 8 }
ip2IfJitterBuffer OBJECT-TYPE
    SYNTAX  Integer32 
    MAX-ACCESS  read-create
    STATUS  current
    DESCRIPTION
    "The maximum cell arrival jitter in 10 usec that the 
     reassembly process will tolerate in the cell stream, 
     without producing errors on the CBR service interface.
     Default value - 100.
     For KM2100:
     KML.11 - The range that will be used is 3...300 msec
     in steps of 1 msec.
     For Vmux:
     The range that will be used is 20...300 msec
     in steps of 10 msec."
    ::= { ip2IfEntry 9 }
ip2IfTos OBJECT-TYPE
    SYNTAX  Integer32 
    MAX-ACCESS  read-create
    STATUS  current
    DESCRIPTION
    "The TOS (Type of Service) value: 0..255."
    ::= { ip2IfEntry 10 }
ip2IfTDMBytesInFrame OBJECT-TYPE
    SYNTAX  Integer32 
    MAX-ACCESS  read-create
    STATUS  current
    DESCRIPTION
    "The number of TDM bytes to be placed in a single IP 
     frame payload."
    ::= { ip2IfEntry 11 }
ip2IfVlanSupport OBJECT-TYPE
    SYNTAX       INTEGER {
    no		(2),
    yes	    (3)
    }
    MAX-ACCESS  read-create
    STATUS  current
    DESCRIPTION
    "VLAN support (Tagging).
     no - No support to VLAN.
     yes - 4 VLAN bytes will be added to the frame."
    ::= { ip2IfEntry 12}
ip2IfVlanIdentifier OBJECT-TYPE
     SYNTAX  Integer32 
     MAX-ACCESS  read-create
     STATUS  current
     DESCRIPTION
     "VLAN ID."
     ::= { ip2IfEntry 13 }
ip2IfVlanFramePriority OBJECT-TYPE
     SYNTAX  Integer32 
     MAX-ACCESS  read-create
     STATUS  current
     DESCRIPTION
     "VLAN Frame priority."
     ::= { ip2IfEntry 14 }
ip2IfExitPort  OBJECT-TYPE
     SYNTAX  INTEGER
      {
       notApplicable (1),
       ext1          (2), 
       ext2          (3),
       auto          (4),
	   card2Ext1	 (5),
	   card2Ext2	 (6),
       ext5          (7),
       ext7          (8) 
      }
     MAX-ACCESS  read-create
     STATUS  current
     DESCRIPTION
     "This object determines to which external port the traffic
      will be sent.
      auto - the device will decide automatically the exit port.
      If there is an option for Tx via more than one ETH card then use ext1 (1) and ext2(2) for ETH card #1
      (ex. LAN1 or Ggabit-ETH1) and use card2Ext1(5) and card2Ext2(6) for card #2 (ex. LAN1 or Ggabit-ETH1).
      In Vmux-110 ext5 is used for ETH-NET, ext7 is used for Serial Link."
      ::= { ip2IfEntry 15 }
ip2IfVoiceOos  OBJECT-TYPE
     SYNTAX  OCTET STRING 
     MAX-ACCESS  read-create
     STATUS  current
     DESCRIPTION
     "Voice Out-Of-Service code. Valid range: (0 - FF HEX).
      For agents that do not support this feature, the value will 
      always be 0."
     ::= { ip2IfEntry 16 }
ip2IfDataOos  OBJECT-TYPE
     SYNTAX  OCTET STRING 
     MAX-ACCESS  read-create
     STATUS  current
     DESCRIPTION
     "Data Out-Of-Service code. Valid range: (0 - FF HEX).
      For agents that do not support this feature, the value will
      always be 0."
     ::= { ip2IfEntry 17 }
ip2IfBundleUsage OBJECT-TYPE
    SYNTAX  Integer32 
    MAX-ACCESS  read-only
    STATUS  current
    DESCRIPTION
    "The Bundle Resource usage in Kbps."
    ::= { ip2IfEntry 18 }
ip2IfOAM  OBJECT-TYPE
     SYNTAX  OCTET STRING 
     MAX-ACCESS  read-create
     STATUS  current
     DESCRIPTION
     "This parameter determine the OAM configuration.
      The LSB (Bit 0 the most right one) is used for OAM connectivity. 
      Values: 0 = disable, 1= enable."
    ::= { ip2IfEntry 19 }
ip2IfTDMoIpMode OBJECT-TYPE
    SYNTAX  INTEGER {
    notApplicable(1),
    static		 (2),
	dynamicLES   (3),
	dynamicCAS   (4),
	cesOverIp	 (5),
	voiceOverMpls(6)	
    }
    MAX-ACCESS    read-create
    STATUS        current
    DESCRIPTION
    "The TDMoIP Mode configuration. Static- means TS can Tx any time.
     dynamicLES - means TS can Tx only when line is enabled according to LES protocol.
     dynamicCAS - means TS can Tx only when line is enabled according to CAS protocol.
     cesOverIp - use for information that this bundle is used for CES Over IP.
     voiceOverMpls - Voice over Multi Protocol Label Switching."
    ::= { ip2IfEntry 20 }
ip2IfTimeElapsed OBJECT-TYPE
     SYNTAX  Integer32 (0..899)
     MAX-ACCESS  read-only
     STATUS  current
     DESCRIPTION
     "The number of seconds that have elapsed since
      the beginning of the  current error-measurement period.
      If, for some reason, such as an adjustment in the 
      system's time-of-day clock, the current interval exceeds
      the maximum	value, the agent will return the maximum value."
     ::= {ip2IfEntry 21 }
ip2IfValidIntervals OBJECT-TYPE
     SYNTAX  Integer32 (0..96)
     MAX-ACCESS  read-only
     STATUS  current
     DESCRIPTION
     "The number of previous intervals for which data was collected.  
      The value will be	96 unless the interface was brought online within
      the last 24 hours, in which case the value will be
      the number of complete 15 minute intervals since the
      interface has been online. "
     ::= {ip2IfEntry 22 }
ip2IfFarEndType  OBJECT-TYPE
     SYNTAX  INTEGER
      {
       notApplicable (1),
       e1            (2),
       t1Esf         (3),
       t1D4          (4),
       fxs           (5)
      }
     MAX-ACCESS  read-create
     STATUS  current
     DESCRIPTION
     "This object defines the type of the Far-End device.
      This data is important for signaling."
     ::= { ip2IfEntry 23 }
ip2IfRdnState  OBJECT-TYPE
     SYNTAX  INTEGER
      {
       notApplicable (1),
       none          (2),
       primary       (3),
       secondary     (4)
      }
     MAX-ACCESS  read-only
     STATUS  current
     DESCRIPTION
     "This object defines the role this bundle plays in the redundancy scheme:
     none(2) - means this bundle is not part of redundancy pair.
     primary/ secondary - means this bundle is not part of redundancy pair,
     and that is the primary bundle or the secondary bunle. "
     ::= { ip2IfEntry 24 }
ip2IfSourceAddr OBJECT-TYPE
     SYNTAX  IpAddress 
     MAX-ACCESS  read-create
     STATUS  current
     DESCRIPTION
     "Source IP Address of the bundle."     	  
	  ::= {ip2IfEntry 25 }
ip2IfBandWidth OBJECT-TYPE
    SYNTAX  Integer32 
    MAX-ACCESS  read-create
    STATUS  current
    DESCRIPTION
    "Number of Time Slots  in The Bundle.
     For T1 the value will be: 1..24
     For E1 the value will be: 1..31
     For T3 the value will be: 1..84
     For E3 the value will be: 1..63
     This parameter is required for devices like Emux where the bandwidth of
     the bundles is unknown. The bundles that are received should be transmitted
     without any change in the bandwidth. It is the user's responsibility to
     enter the correct bandwidth."
     ::= {ip2IfEntry 26 }
ip2IfMeasuredSilence  OBJECT-TYPE
     SYNTAX  Integer32     
     MAX-ACCESS  read-only
     STATUS  current
     DESCRIPTION
     "This object shows the percentage of Silence that was measured by the device
      for the current bundle.
      Relevant values: 0..100, 255.
      Default value is 50.
      0 means that there is no silence on the line.
      100 means that there is only silence. In this case, there might be no traffic.
      255 - value for not applicable or unknown."      
     ::= { ip2IfEntry 27 }
ip2IfPayloadType  OBJECT-TYPE
     SYNTAX  INTEGER
      {
       notApplicable (1),
       data          (2),
       voice         (3),
       voiceAndCas   (4)
      }
     MAX-ACCESS  read-create
     STATUS  current
     DESCRIPTION
     "This object defines the TDMoIP payload type."
     ::= { ip2IfEntry 28 }
ip2IfProtocolVersion  OBJECT-TYPE
     SYNTAX  INTEGER
      {
       notApplicable (1),
       v1   (2),
       v2   (3)
      }
     MAX-ACCESS  read-create
     STATUS  current
     DESCRIPTION
     "This object defines the TDMoIP protocol Version."
     ::= { ip2IfEntry 29 }
ip2IfTdmBackUpNextHop OBJECT-TYPE
    SYNTAX  IpAddress 
    MAX-ACCESS  read-create
    STATUS  current
    DESCRIPTION
    "Defines the TDM bundle default router in case there was a switch from the Primary Link
     (for example an ETH port) to a TDM backup Link like E1, T1 or Serial Link.
     This parameter is relevant only when a Backup Link is configured.
     When a Backup Link is not configured the value will be: 0.0.0.0"
    ::= { ip2IfEntry 30 }
ip2IfOosTxEnable  OBJECT-TYPE
     SYNTAX  INTEGER
      {
       notApplicable 	(1),
       disable  		(2),
       enable    		(3)
             }
     MAX-ACCESS  read-create
     STATUS  current
     DESCRIPTION
     "This object defines whether OOS will be Transmitted.
	 Note that for IPmux1000 the Lbit is always sent, 
	 but the OOS will be sent according to user selection in this parameter."
     ::= { ip2IfEntry 31 }
ip2IfConnCheckPktFrequency   OBJECT-TYPE
     SYNTAX  Integer32     
     MAX-ACCESS  read-create
     STATUS  current
     DESCRIPTION
     "Time in sec. between 2 Bundle Connectivity Check packets.
      Valid values: 0..60. 0 = Not Applicable."      
      ::= { ip2IfEntry 32 }
ip2IfConnPktTimeOutCycles      OBJECT-TYPE
     SYNTAX  Integer32     
     MAX-ACCESS  read-create
     STATUS  current
     DESCRIPTION
    "No. of cycles the agent will send Bundle Connectivity packets without receiving
     a response from the remote device before declaring that the bundle connection
     to the remote side is down - Time Out.
     Valid values: 0..5. 0 = Not Applicable."    
     ::= { ip2IfEntry 33 }
ip2IfMfRelay                  OBJECT-TYPE
     SYNTAX  INTEGER
      {
       notApplicable (1),
       disable       (2),
       enable        (3)
      }
     MAX-ACCESS  read-create
     STATUS  current
     DESCRIPTION
    "Multi Frequency Signaling Detection."    
     ::= { ip2IfEntry 34 }
ip2IfTxGain                  OBJECT-TYPE
     SYNTAX  Integer32
     MAX-ACCESS  read-create
     STATUS  current
     DESCRIPTION
    "Transmit gain in dBm."    
     ::= { ip2IfEntry 35 }
ip2IfSuperTandem             OBJECT-TYPE
     SYNTAX  INTEGER
      {
       notApplicable (1),
       disable       (2),
       enable        (3)
      }
     MAX-ACCESS  read-create
     STATUS  current
     DESCRIPTION
    "The Super Tandem feature provides end to end compression over multiple hops,
     solving the double compression problem detected in Voice compressing systems.
     The Super Tandem allows transmission of compressed voice between a few
     Vmux 2100 hubs, and eliminates the need to decompress an recompress it over
     each voice card and PBX, thus improving voice quality and reducing delay."    
     ::= { ip2IfEntry 36 }
ip2IfSrcPort OBJECT-TYPE
    SYNTAX  Integer32 
    MAX-ACCESS  read-create
    STATUS  current
    DESCRIPTION
    "The source Bundle at the local device, 
    this parameter used for cases where there is no match 
    between ip2IfChannelIndex and the Source Bundle ID."
    ::= { ip2IfEntry 37 }
   ip2IfModemCalls             OBJECT-TYPE
     SYNTAX  INTEGER
      {
       disable       (2),
       enable        (3),
	   relay         (4)
      }
     MAX-ACCESS  read-create
     STATUS  current
     DESCRIPTION
     "This MIB object shows whether Modem Calls are enabled via the bundle.
      relay option (3) means that the bundle will send to the network only
      modulated data."
     ::= { ip2IfEntry 38 }
   ip2IfMinPulseWidth  OBJECT-TYPE
      SYNTAX  Integer32                   
      MAX-ACCESS  read-create
      STATUS  current
      DESCRIPTION
      "Indicates the minimum width in milliseconds of the MF (Multi Frequency)
       tone transmitted by the switch.
       Valid values: 45-300 msec.
       notApplicable=0."
       ::= { ip2IfEntry 39 } 
   ip2IfMinPowerLevel  OBJECT-TYPE
      SYNTAX  Integer32                   
      MAX-ACCESS  read-create
      STATUS  current
      DESCRIPTION
       "Indicates the minimum power level in dBm of the MF (Multi Frequency)
        tone transmitted by the switch.
        Valid values: -1...-35 dBm."
        ::= { ip2IfEntry 40 }
ip2IfEchoCanceler             OBJECT-TYPE
     SYNTAX  INTEGER
        {
          off    (2),
          on     (3)
       }
      MAX-ACCESS  read-create
      STATUS  current
      DESCRIPTION
      "Echo canceler activation."
     ::= { ip2IfEntry 41 }
ip2IfCodingLaw OBJECT-TYPE
      SYNTAX  INTEGER
       {
          aLAW    (1),
          uLAW    (2)
       }
      MAX-ACCESS  read-create
      STATUS  current
      DESCRIPTION
      "This attribute indicates the Method/Law for decoding/encoding the voice
       information.
       aLaw(1) is the standard Law for E1 links.
       uLaw(2) is the standard Law for T1 links."
       ::= { ip2IfEntry 42 }
ip2IfCustomToneDetect             OBJECT-TYPE
     SYNTAX  INTEGER
      {
       disable       (2),
       enable        (3)
      }
     MAX-ACCESS  read-create
     STATUS  current
     DESCRIPTION
     "Custom Tone Detection (COT) is a Control operation of a 2Khz tone detector.
	  This tone is sent between PBX devices in order to check that the line status
	  is OK. When the COT is enabled the device will not compress/decompress the tone.
	  In this case, if the tone is initiated by the local PBX, the Device runs
	  a 2Khz detector tone and once detected by the Remote Device, if the COT is enabled
	  in the Remote Device, the Remote Device will generate a 2khz tone to the remote PBX."
	  ::= { ip2IfEntry 43 }
 ip2IfCallerIdDelay      OBJECT-TYPE
     SYNTAX  Integer32
     MAX-ACCESS  read-create
     STATUS  current
     DESCRIPTION
     "Time in msec between CLID (Caller ID) signal detection on the line and CLID
      signal transmission. The CLID must be sent between ringing signals and the value
      of the delay is used for synchronizing the CLID transmission with the ringing
      signals transmission.
      Valid values: 0 - 3000 msec."
	  ::= { ip2IfEntry 44 }
 ip2IfConnectivityMode    OBJECT-TYPE
     SYNTAX  INTEGER
      {
       ping       (2),
       oam        (3)
       }
     MAX-ACCESS  read-create
     STATUS  current
     DESCRIPTION
     "This MIB object shows whether to send Pings or OAM frames over the bundle."
      ::= { ip2IfEntry 45 }
 -- Objects in leafs 46-52 are reserved for future versions.
ip2IfMfcSpoofing		 OBJECT-TYPE
      SYNTAX   INTEGER
    {
     notApplicable 	(1),
     disable  		(2),
     enable    		(3)
     }
   MAX-ACCESS  read-create
   STATUS  current
   DESCRIPTION
   "This MIB object defines whether the MFC (Multi Frequency Compelled) protocol
    spoofing will exist in the bundle. When the MFC Spoofing is used, the Local
    and Remote PBXs will send MFC Signaling to each other. The Vmuxes between
    the PBXs will send proprietary signaling to each other. They will however
    create and send MFC tones to their local PBX. The PBXs will not know that
    the actual signaling was not sent from a PBX but from a Vmux."
    ::= { ip2IfEntry 53}
ip2IfToneAckInterval  OBJECT-TYPE
   SYNTAX         Integer32 
   MAX-ACCESS     read-create
   STATUS         current
   DESCRIPTION
   "Time Interval in milli seconds from the time a Vmux sends tone/s to a local PBX until
    it receives an acknowledgement from this PBX.
    Valid values: 60...400 in steps of 20.
    Default: 80."
    ::= { ip2IfEntry 54}
-- Object in leaf 55 is reserved for future versions.
 ip2IfNoiseLevelForVAD   OBJECT-TYPE
   SYNTAX  INTEGER
   {       
    low          (2),
    high         (3)
   }
   MAX-ACCESS  read-create
   STATUS  current
   DESCRIPTION
   "This object defines the Level of Noise on the line,
    the Voice Activation Detector (VAD) will have to handle."
   ::= { ip2IfEntry 56}
ip2IfTDMFrameBytes OBJECT-TYPE
       SYNTAX  Integer32 
       MAX-ACCESS  read-write
       STATUS  current
       DESCRIPTION
       "The number of TDM bytes to be placed in a single IP 
       frame payload."
       ::= { ip2If 2 }
ip2IfTosValue OBJECT-TYPE
       SYNTAX  Integer32 
       MAX-ACCESS  read-write
       STATUS  current
       DESCRIPTION
       "The TOS value to write in the IP frame."
       ::= { ip2If 3 }
ip2IfVlanTagging OBJECT-TYPE
       SYNTAX INTEGER {
       no		(1),
       yes	    (2)
       }
       MAX-ACCESS  read-write
       STATUS  current
       DESCRIPTION
       "VLAN support.
       no - No support to VLAN.
       yes - 4 VLAN bytes will be added to the frame."
       ::= { ip2If 4 }
ip2IfVlanID OBJECT-TYPE
       SYNTAX  Integer32 
       MAX-ACCESS  read-write
       STATUS  current
       DESCRIPTION
       "VLAN ID."
       ::= { ip2If 5 }
ip2IfVlanPriority OBJECT-TYPE
       SYNTAX  Integer32 
       MAX-ACCESS  read-write
       STATUS  current
       DESCRIPTION
       "Frame priority."
       ::= { ip2If 6 }
-- ip2If Statistics table  
ip2IfStatTable OBJECT-TYPE
       SYNTAX  SEQUENCE OF Ip2IfStatEntry
       MAX-ACCESS  not-accessible
       STATUS  current
       DESCRIPTION
       "Channels (Bundles) Statistics Table."
       ::= { ip2If 7 }
ip2IfStatEntry OBJECT-TYPE
       SYNTAX Ip2IfStatEntry
       MAX-ACCESS not-accessible
       STATUS current
       DESCRIPTION
       "IP Statistics per bundle"
       INDEX   { ip2IfStatChIndex }
       ::= { ip2IfStatTable 1 }
Ip2IfStatEntry ::=
         SEQUENCE {
         ip2IfStatChIndex	       Integer32,
         ip2IfStatSeqErrors        Integer32,
         ip2IfStatBufUnderflows    Integer32,
         ip2IfStatBufOverflows     Integer32,
		 ip2IfStatTxOnTimeInterval Counter32,
		 ip2IfStatTxOnMaxSize      Counter32,
		 ip2IfStatRxSignaling      Counter32,
		 ip2IfStatRxVoice          Counter32,
		 ip2IfStatRxHdlc           Counter32,
		 ip2IfStatTxSignaling      Counter32,
		 ip2IfStatTxVoice          Counter32,
		 ip2IfStatTxHdlc           Counter32,
		 ip2IfStatRdnFlip		   Counter32
	             }
ip2IfStatChIndex OBJECT-TYPE
    SYNTAX  		Integer32 
    MAX-ACCESS  read-only
    STATUS  current
    DESCRIPTION
    "The channel index, which is actualy the bundle ID."
    ::= { ip2IfStatEntry 1 }
ip2IfStatSeqErrors      OBJECT-TYPE
    SYNTAX        Integer32
    MAX-ACCESS        read-only
    STATUS        current
    DESCRIPTION
    "Number of times that the sequence number of an incoming Frame
     causes a transition from the 'sync' state to
     the 'out of sequence' state."
     ::= { ip2IfStatEntry 2 }
ip2IfStatBufUnderflows      OBJECT-TYPE
    SYNTAX        Integer32
    MAX-ACCESS    read-only
    STATUS        current
    DESCRIPTION
    "Number of buffer underflows. This records the count of the
     number of times the Receive (Eth to TDM) buffer underflows. In the
     case of a continuous underflow caused by a loss of Frame
     flow, a single buffer underflow should be counted."
    ::= { ip2IfStatEntry 3 }
ip2IfStatBufOverflows      OBJECT-TYPE
    SYNTAX        Integer32
    MAX-ACCESS        read-only
    STATUS        current
    DESCRIPTION
    "Number of buffer overflows. This records the count of the
     number of times the Receive (Eth to TDM) buffer overflows."
    ::= { ip2IfStatEntry 4 }
ip2IfStatTxOnTimeInterval      OBJECT-TYPE
    SYNTAX        Counter32
    MAX-ACCESS    read-only
    STATUS        current
    DESCRIPTION
    "Number of frames that were transmitted due to time interval elapse.
     The user can choose to Tx the Frame when it reaches the Max size
     or when the packetizing time interval elapses.
     The packetizing time interval is the interval in msec that it takes
     to build a Max. size frame."
    ::= { ip2IfStatEntry 5 }
ip2IfStatTxOnMaxSize      OBJECT-TYPE
    SYNTAX        Counter32
    MAX-ACCESS    read-only
    STATUS        current		
    DESCRIPTION
    "Number of frames that were transmitted due to reaching max.
     frame size. The user can choose to Tx the Frame when it reaches the
     Max size or when the packetizing time interval elapses."
    ::= { ip2IfStatEntry 6 }
ip2IfStatRxSignaling      OBJECT-TYPE
    SYNTAX        Counter32
    MAX-ACCESS    read-only
    STATUS        current		
    DESCRIPTION
    "Number of signaling frames that were received."
    ::= { ip2IfStatEntry 7 }
ip2IfStatRxVoice          OBJECT-TYPE
    SYNTAX        Counter32
    MAX-ACCESS    read-only
    STATUS        current		
    DESCRIPTION
    "Number of voice frames that were received."
    ::= { ip2IfStatEntry 8 }
ip2IfStatRxHdlc           OBJECT-TYPE
    SYNTAX        Counter32
    MAX-ACCESS    read-only
    STATUS        current		
    DESCRIPTION
    "Number of HDLC frames that were received."
    ::= { ip2IfStatEntry 9 }
ip2IfStatTxSignaling      OBJECT-TYPE
    SYNTAX        Counter32
    MAX-ACCESS    read-only
    STATUS        current		
    DESCRIPTION
    "Number of signaling frames that were transmitted."
    ::= { ip2IfStatEntry 10 }
ip2IfStatTxVoice          OBJECT-TYPE
    SYNTAX        Counter32
    MAX-ACCESS    read-only
    STATUS        current		
    DESCRIPTION
    "Number of voice frames that were transmitted."
    ::= { ip2IfStatEntry 11 }
ip2IfStatTxHdlc           OBJECT-TYPE
    SYNTAX        Counter32
    MAX-ACCESS    read-only
    STATUS        current		
    DESCRIPTION
    "Number of HDLC frames that were transmitted."
    ::= { ip2IfStatEntry 12 }
ip2IfStatRdnFlip          OBJECT-TYPE
    SYNTAX        Counter32
    MAX-ACCESS    read-only
    STATUS        current		
    DESCRIPTION
    "Number of redundancy flips occured.
    This parameter counts only flips from this bundle to the other bundle
    in the redundancy couple."
    ::= { ip2IfStatEntry 13 }
ip2IfRateLimit OBJECT-TYPE
       SYNTAX  Integer32 
       MAX-ACCESS  read-write
       STATUS  current
       DESCRIPTION
       "The maximum rate permitted to transfer via the network portin Mbps."
       ::= { ip2If 8 }
-- ip2If Port table  
ip2IfPortTable OBJECT-TYPE
       SYNTAX  SEQUENCE OF Ip2IfPortEntry
       MAX-ACCESS  not-accessible
       STATUS  current
       DESCRIPTION
               "Port  Table."
       ::= { ip2If 9 }
ip2IfPortEntry OBJECT-TYPE
       SYNTAX Ip2IfPortEntry
       MAX-ACCESS not-accessible
       STATUS current
       DESCRIPTION
          "Application layer configuration per Port"
       INDEX   { ip2IfPortIndex }
       ::= { ip2IfPortTable 1 }
Ip2IfPortEntry ::=
         SEQUENCE {
         ip2IfPortIndex	    		Integer32,
         ip2IfPortUsage		    	Integer32,
		 ip2IfPortMask				INTEGER,
		 ip2IfPortTotalThroughput	Integer32
         	}
ip2IfPortIndex OBJECT-TYPE
    SYNTAX  Integer32 
    MAX-ACCESS  read-only
    STATUS  current
    DESCRIPTION
    "The Port index, which is actualy the ifIndex."
    ::= { ip2IfPortEntry 1 }
ip2IfPortUsage OBJECT-TYPE
    SYNTAX  Integer32 
    MAX-ACCESS  read-only
    STATUS  current
    DESCRIPTION
    "This parameter indicates the usage of the port (percents)."
    ::= { ip2IfPortEntry 2 }
ip2IfPortMask OBJECT-TYPE
       SYNTAX INTEGER {
       notApplicable	(1),
       dontMask  	    (2),
	   mask 			(3)
       }
       MAX-ACCESS  read-write
       STATUS  current
       DESCRIPTION
       "This parameter defines whether Agent will mask port's alarms and statistics or not."
	 ::= {  ip2IfPortEntry 3 }
ip2IfPortTotalThroughput OBJECT-TYPE
    SYNTAX  Integer32 
    MAX-ACCESS  read-only
    STATUS  current
    DESCRIPTION
    "This parameter indicates the total Throughput of the port in bps."
    ::= { ip2IfPortEntry 4 }
-- ip2If Current Statistics table  
ip2IfCurrentStatTable OBJECT-TYPE
       SYNTAX  SEQUENCE OF Ip2IfCurrentStatEntry
       MAX-ACCESS  not-accessible
       STATUS  current
       DESCRIPTION
       "Channels (Bundles) Current Statistics Table."
       ::= { ip2If 10 }
ip2IfCurrentStatEntry OBJECT-TYPE
       SYNTAX Ip2IfCurrentStatEntry
       MAX-ACCESS not-accessible
       STATUS current
       DESCRIPTION
       "IP Current Statistics per bundle"
       INDEX   { ip2IfChannelIndex }
       ::= { ip2IfCurrentStatTable 1 }
Ip2IfCurrentStatEntry ::=
         SEQUENCE {
         ip2IfCurrentStatSeqErrors        Counter32,
         ip2IfCurrentStatBufUnderflows    Counter32,
         ip2IfCurrentStatBufOverflows     Counter32,
		 ip2IfCurrentStatMaxDelayVar      Integer32
		 		 		 }
ip2IfCurrentStatSeqErrors      OBJECT-TYPE
    SYNTAX        Counter32
    MAX-ACCESS        read-only
    STATUS        current
    DESCRIPTION
    "Number of times that the sequence number of an incoming Frame
     causes a transition from the 'sync' state to
     the 'out of sequence' state in the current interval."
     ::= { ip2IfCurrentStatEntry 1 }
ip2IfCurrentStatBufUnderflows      OBJECT-TYPE
    SYNTAX        Counter32
    MAX-ACCESS    read-only
    STATUS        current
    DESCRIPTION
    "Number of buffer underflows in the current interval. 
     This records the count of the number of times the Receive 
     (Eth to TDM) buffer underflows in the current interval. In the
     case of a continuous underflow caused by a loss of Frame
     flow, a single buffer underflow should be counted."
    ::= { ip2IfCurrentStatEntry 2 }
ip2IfCurrentStatBufOverflows      OBJECT-TYPE
    SYNTAX        Counter32
    MAX-ACCESS        read-only
    STATUS        current
    DESCRIPTION
    "Number of buffer overflows in the current interval. 
     This records the count of the number of times the Receive 
     (Eth to TDM) buffer overflows in the current interval."
    ::= { ip2IfCurrentStatEntry 3 }
ip2IfCurrentStatMaxDelayVar      OBJECT-TYPE
    SYNTAX        Integer32
    MAX-ACCESS        read-only
    STATUS        current
    DESCRIPTION
    "The maximum size of the buffer (in 10's of usec) for the current interval."
    ::= { ip2IfCurrentStatEntry 4 }
-- ip2If Interval Statistics table  
ip2IfIntervalStatTable OBJECT-TYPE
       SYNTAX  SEQUENCE OF Ip2IfIntervalStatEntry
       MAX-ACCESS  not-accessible
       STATUS  current
       DESCRIPTION
       "Channels (Bundles) Interval Statistics Table."
       ::= { ip2If 11 }
ip2IfIntervalStatEntry OBJECT-TYPE
       SYNTAX Ip2IfIntervalStatEntry
       MAX-ACCESS not-accessible
       STATUS current
       DESCRIPTION
       "IP Interval Statistics per bundle"
       INDEX   { ip2IfChannelIndex, ip2IfIntervalStatIndex }
       ::= { ip2IfIntervalStatTable 1 }
Ip2IfIntervalStatEntry ::=
         SEQUENCE {
         ip2IfIntervalStatIndex	       	   Integer32,
         ip2IfIntervalStatSeqErrors        Counter32,
         ip2IfIntervalStatBufUnderflows    Counter32,
         ip2IfIntervalStatBufOverflows     Counter32,
		 ip2IfIntervalStatMaxDelayVar      Integer32
		 }
ip2IfIntervalStatIndex OBJECT-TYPE
    SYNTAX  		Integer32 
    MAX-ACCESS  read-only
    STATUS  current
    DESCRIPTION
    "The Interval index, which is actualy the Interval number."
    ::= { ip2IfIntervalStatEntry 1 }
ip2IfIntervalStatSeqErrors      OBJECT-TYPE
    SYNTAX        Counter32
    MAX-ACCESS        read-only
    STATUS        current
    DESCRIPTION
    "Number of times that the sequence number of an incoming Frame
     causes a transition from the 'sync' state to
     the 'out of sequence' state in the selected interval."
     ::= { ip2IfIntervalStatEntry 2 }
ip2IfIntervalStatBufUnderflows      OBJECT-TYPE
    SYNTAX        Counter32
    MAX-ACCESS    read-only
    STATUS        current
    DESCRIPTION
    "Number of buffer underflows in the selected interval. 
     This records the count of the number of times the Receive 
     (Eth to TDM) buffer underflows in the selected interval. In the
     case of a continuous underflow caused by a loss of Frame
     flow, a single buffer underflow should be counted."
    ::= { ip2IfIntervalStatEntry 3 }
ip2IfIntervalStatBufOverflows      OBJECT-TYPE
    SYNTAX        Counter32
    MAX-ACCESS        read-only
    STATUS        current
    DESCRIPTION
    "Number of buffer overflows in the selected interval. 
     This records the count of the number of times the Receive 
     (Eth to TDM) buffer overflows in the selected interval."
    ::= { ip2IfIntervalStatEntry 4 }
ip2IfIntervalStatMaxDelayVar      OBJECT-TYPE
    SYNTAX        Integer32
    MAX-ACCESS        read-only
    STATUS        current
    DESCRIPTION
    "The maximum size of the buffer (in 10's of usec) in the selected interval."
    ::= { ip2IfIntervalStatEntry 5 }
ip2IfLogEvents			OBJECT-TYPE
     SYNTAX INTEGER {
       notApplicable	(1),
       all		  	    (2),
       oneMinStep		(3)
     }
     MAX-ACCESS  read-write
     STATUS  current
     DESCRIPTION
     "This parameter defines whether all Jitter Buffer and Sequence Number events
      will enter to Log File,
      or enter those events to Log file in one minute steps."
     ::= {  ip2If 12}
ip2IfEthSwitchMode			OBJECT-TYPE
     SYNTAX INTEGER {
       notApplicable	(1),
       unTagged	  	    (2),
       tagged			(3)
     }
     MAX-ACCESS  read-write
     STATUS  current
     DESCRIPTION
     "This parameter defines whether Eth Switch is in VLAN Tagged mode."
     ::= {  ip2If 13}
--Traps 
--The numbers 1-4 are used by imx.txt
alarmStatusTrap NOTIFICATION-TYPE
      OBJECTS  {atmInterfaceAlarmStatus}
      STATUS  current
      DESCRIPTION
	  "The trap is sent whenever there is a transition from a no alarm
	   state to a state with at least one active alarm."
      ::= { radSysWanEvents 5 }
systemTrap NOTIFICATION-TYPE
      OBJECTS  { /*atmNteEventType,*/ agnLed, alarmSeverity }  
      STATUS  current
      DESCRIPTION
	  "This trap alerts of major problems in the device."
      ::= { radSysWanEvents 6 }
alarmLOS NOTIFICATION-TYPE
      OBJECTS  { alarmSeverity, alarmState, ifAlias }  
      STATUS  current
      DESCRIPTION
	  "This trap indicates Loss Of Signal."
      ::= { radSysWanEvents 7 }
alarmLOF NOTIFICATION-TYPE
      OBJECTS  { alarmSeverity, alarmState, ifAlias }  
      STATUS  current
      DESCRIPTION
	  "This trap indicates Loss Of Frame."
      ::= { radSysWanEvents 8 }
channelOperStatusTrap NOTIFICATION-TYPE
      OBJECTS  { ip2IfOperStatus }  
      STATUS  current
      DESCRIPTION
	  "This trap is sent upon any change in one or more channels."
      ::= { radSysWanEvents 9 }
alarmAIS NOTIFICATION-TYPE
      OBJECTS  { alarmSeverity, alarmState, ifAlias }  
      STATUS  current
      DESCRIPTION
	  "This trap indicates AIS."
      ::= { radSysWanEvents 10 }
alarmRDI NOTIFICATION-TYPE
      OBJECTS  { alarmSeverity, alarmState, ifAlias }  
      STATUS  current
      DESCRIPTION
	  "This trap indicates RDI."
      ::= { radSysWanEvents 11 }
alarmFEBE NOTIFICATION-TYPE
      OBJECTS  { alarmSeverity, alarmState, ifAlias }  
      STATUS  current
      DESCRIPTION
	  "This trap indicates FEBE."
      ::= { radSysWanEvents 12 }
localConnStatusTrap NOTIFICATION-TYPE
      OBJECTS  { alarmSeverity, alarmState, ifAlias }  
      STATUS  current
      DESCRIPTION
	  "This trap is sent upon a change in Local connectivity
	   of Bundle connection."
      ::= { radSysWanEvents 13 }
remoteConnStatusTrap NOTIFICATION-TYPE
      OBJECTS  { alarmSeverity, alarmState, ifAlias }  
      STATUS  current
      DESCRIPTION
	  "This trap is sent upon a change in Remote connectivity
	   of Bundle connection."
      ::= { radSysWanEvents 14 }
bundleConnectionStatusTrap NOTIFICATION-TYPE
      OBJECTS  { ifAlias, ip2IfOperStatus }  
      STATUS  current
      DESCRIPTION
	  "This trap is sent upon any change in the connectivity status 
	   of a Bundle (ip2IfOperStatus).
	   The ifAlias index is the ifIndex of the bundle that its status has been changed."
      ::= { radSysWanEvents 15 }
END
