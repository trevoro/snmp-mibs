Nortel-Magellan-Passport-HdlcTransparentMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      PassportCounter64,
      InterfaceIndex,
      Gauge32,
      Integer32,
      Unsigned32
   FROM Nortel-Magellan-Passport-StandardTextualConventionsMIB

      AsciiString,
      NonReplicated,
      EnterpriseDateAndTime,
      Link
   FROM Nortel-Magellan-Passport-TextualConventionsMIB;




-- LAST-UPDATED   "9607010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     HdlcTransparent Enterprise MIB."

hdlcTransparentMIB OBJECT IDENTIFIER ::= { passportMIBs 47 }










-- HTDS/<n>
-- The HDLC Transparent Data Service (HTDS) component defines 
-- the characteristics of an instance of the HDLC transparent data 
-- service.
-- One instance of this component is required by each DS1, E1, V35 
-- or V11 channel which is offering HDLC transparent traffic.
-- The instance number is arbitrary.

htds OBJECT IDENTIFIER ::= { components 82 }



htdsRowStatusTable OBJECT-TYPE
   SYNTAX     SEQUENCE OF HtdsRowStatusEntry
   ACCESS     not-accessible
   STATUS     mandatory
   DESCRIPTION
     "This entry controls the addition and deletion of 
      htds components."
::= { htds 1 }

htdsRowStatusEntry OBJECT-TYPE
   SYNTAX     HtdsRowStatusEntry
   ACCESS     not-accessible
   STATUS     mandatory
   DESCRIPTION
     "A single entry in the table represents a single 
      htds component."
   INDEX {
      htdsIndex }
::= { htdsRowStatusTable 1 }

HtdsRowStatusEntry ::= SEQUENCE {
   htdsRowStatus
      RowStatus,
   htdsComponentName
      DisplayString,
   htdsStorageType
      StorageType,
   htdsIndex
      Integer32 }

htdsRowStatus OBJECT-TYPE
   SYNTAX     RowStatus 
   ACCESS     read-write
   STATUS     mandatory
   DESCRIPTION
     "This variable is used as the basis for SNMP naming of
      htds components.
      These components can be added and deleted."
::= { htdsRowStatusEntry 1 }

htdsComponentName OBJECT-TYPE
   SYNTAX     DisplayString 
   ACCESS     read-only
   STATUS     mandatory
   DESCRIPTION
     "This variable provides the component's string name for
      use with the ASCII Console Interface"
::= { htdsRowStatusEntry 2 }

htdsStorageType OBJECT-TYPE
   SYNTAX     StorageType 
   ACCESS     read-only
   STATUS     mandatory
   DESCRIPTION
     "This variable represents the storage type value for the
      htds tables."
::= { htdsRowStatusEntry 4 }

htdsIndex OBJECT-TYPE
   SYNTAX     Integer32 (1..65535)
   ACCESS     not-accessible
   STATUS     mandatory
   DESCRIPTION
     "This variable represents the index for the htds tables."
::= { htdsRowStatusEntry 10 }

htdsCidDataTable OBJECT-TYPE
   SYNTAX     SEQUENCE OF HtdsCidDataEntry
   ACCESS     not-accessible
   STATUS     mandatory
   DESCRIPTION
     "This group contains the attribute for a component's Customer 
      Identifier (CID). Refer to the attribute description for a detailed 
      explanation of CIDs."
::= { htds 10 }

htdsCidDataEntry OBJECT-TYPE
   SYNTAX     HtdsCidDataEntry
   ACCESS     not-accessible
   STATUS     mandatory
   DESCRIPTION
     "An entry in the htdsCidDataTable."
   INDEX {
      htdsIndex }
::= { htdsCidDataTable 1 }

HtdsCidDataEntry ::= SEQUENCE {
   htdsCustomerIdentifier
      Unsigned32 }

htdsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { htdsCidDataEntry 1 }

htdsIfEntryTable OBJECT-TYPE
   SYNTAX     SEQUENCE OF HtdsIfEntryEntry
   ACCESS     not-accessible
   STATUS     mandatory
   DESCRIPTION
     "This group contains the provisionable attributes for the ifEntry."
::= { htds 11 }

htdsIfEntryEntry OBJECT-TYPE
   SYNTAX     HtdsIfEntryEntry
   ACCESS     not-accessible
   STATUS     mandatory
   DESCRIPTION
     "An entry in the htdsIfEntryTable."
   INDEX {
      htdsIndex }
::= { htdsIfEntryTable 1 }

HtdsIfEntryEntry ::= SEQUENCE {
   htdsIfAdminStatus
      INTEGER,
   htdsIfIndex
      InterfaceIndex }

htdsIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { htdsIfEntryEntry 1 }

htdsIfIndex OBJECT-TYPE
   SYNTAX     InterfaceIndex (1..65535)
   ACCESS     read-only
   STATUS     mandatory
   DESCRIPTION
     "This is the index for the IfEntry. Its value is automatically initialized 
      during the provisioning process."
::= { htdsIfEntryEntry 2 }

htdsOperStatusTable OBJECT-TYPE
   SYNTAX     SEQUENCE OF HtdsOperStatusEntry
   ACCESS     not-accessible
   STATUS     mandatory
   DESCRIPTION
     "This group includes the Operational Status attribute. This attribute 
      defines the current operational state of this component."
::= { htds 12 }

htdsOperStatusEntry OBJECT-TYPE
   SYNTAX     HtdsOperStatusEntry
   ACCESS     not-accessible
   STATUS     mandatory
   DESCRIPTION
     "An entry in the htdsOperStatusTable."
   INDEX {
      htdsIndex }
::= { htdsOperStatusTable 1 }

HtdsOperStatusEntry ::= SEQUENCE {
   htdsSnmpOperStatus
      INTEGER }

htdsSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { htdsOperStatusEntry 1 }

htdsStateTable OBJECT-TYPE
   SYNTAX     SEQUENCE OF HtdsStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { htds 13 }

htdsStateEntry OBJECT-TYPE
   SYNTAX     HtdsStateEntry
   ACCESS     not-accessible
   STATUS     mandatory
   DESCRIPTION
     "An entry in the htdsStateTable."
   INDEX {
      htdsIndex }
::= { htdsStateTable 1 }

HtdsStateEntry ::= SEQUENCE {
   htdsAdminState
      INTEGER,
   htdsOperationalState
      INTEGER,
   htdsUsageState
      INTEGER,
   htdsAvailabilityStatus
      OCTET STRING,
   htdsProceduralStatus
      OCTET STRING,
   htdsControlStatus
      OCTET STRING,
   htdsAlarmStatus
      OCTET STRING,
   htdsStandbyStatus
      INTEGER,
   htdsUnknownStatus
      INTEGER }

htdsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { htdsStateEntry 1 }

htdsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { htdsStateEntry 2 }

htdsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { htdsStateEntry 3 }

htdsAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { htdsStateEntry 4 }

htdsProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { htdsStateEntry 5 }

htdsControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { htdsStateEntry 6 }

htdsAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { htdsStateEntry 7 }

htdsStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { htdsStateEntry 8 }

htdsUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { htdsStateEntry 9 }


-- 
-- Htds/n Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

htdsFramer OBJECT IDENTIFIER ::= { htds 2 }



htdsFramerRowStatusTable OBJECT-TYPE
   SYNTAX     SEQUENCE OF HtdsFramerRowStatusEntry
   ACCESS     not-accessible
   STATUS     mandatory
   DESCRIPTION
     "This entry controls the addition and deletion of 
      htdsFramer components."
::= { htdsFramer 1 }

htdsFramerRowStatusEntry OBJECT-TYPE
   SYNTAX     HtdsFramerRowStatusEntry
   ACCESS     not-accessible
   STATUS     mandatory
   DESCRIPTION
     "A single entry in the table represents a single 
      htdsFramer component."
   INDEX {
      htdsIndex,
      htdsFramerIndex }
::= { htdsFramerRowStatusTable 1 }

HtdsFramerRowStatusEntry ::= SEQUENCE {
   htdsFramerRowStatus
      RowStatus,
   htdsFramerComponentName
      DisplayString,
   htdsFramerStorageType
      StorageType,
   htdsFramerIndex
      NonReplicated }

htdsFramerRowStatus OBJECT-TYPE
   SYNTAX     RowStatus 
   ACCESS     read-only
   STATUS     mandatory
   DESCRIPTION
     "This variable is used as the basis for SNMP naming of
      htdsFramer components.
      These components cannot be added nor deleted."
::= { htdsFramerRowStatusEntry 1 }

htdsFramerComponentName OBJECT-TYPE
   SYNTAX     DisplayString 
   ACCESS     read-only
   STATUS     mandatory
   DESCRIPTION
     "This variable provides the component's string name for
      use with the ASCII Console Interface"
::= { htdsFramerRowStatusEntry 2 }

htdsFramerStorageType OBJECT-TYPE
   SYNTAX     StorageType 
   ACCESS     read-only
   STATUS     mandatory
   DESCRIPTION
     "This variable represents the storage type value for the
      htdsFramer tables."
::= { htdsFramerRowStatusEntry 4 }

htdsFramerIndex OBJECT-TYPE
   SYNTAX     NonReplicated 
   ACCESS     not-accessible
   STATUS     mandatory
   DESCRIPTION
     "This variable represents the index for the htdsFramer tables."
::= { htdsFramerRowStatusEntry 10 }

htdsFramerProvTable OBJECT-TYPE
   SYNTAX     SEQUENCE OF HtdsFramerProvEntry
   ACCESS     not-accessible
   STATUS     mandatory
   DESCRIPTION
     "This group contains the base provisioning data for the Framer 
      component. Application or hardware interface specific provisioning 
      data is contained in other provisionable Framer groups."
::= { htdsFramer 10 }

htdsFramerProvEntry OBJECT-TYPE
   SYNTAX     HtdsFramerProvEntry
   ACCESS     not-accessible
   STATUS     mandatory
   DESCRIPTION
     "An entry in the htdsFramerProvTable."
   INDEX {
      htdsIndex,
      htdsFramerIndex }
::= { htdsFramerProvTable 1 }

HtdsFramerProvEntry ::= SEQUENCE {
   htdsFramerInterfaceName
      Link }

htdsFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { htdsFramerProvEntry 1 }

htdsFramerLinkTable OBJECT-TYPE
   SYNTAX     SEQUENCE OF HtdsFramerLinkEntry
   ACCESS     not-accessible
   STATUS     mandatory
   DESCRIPTION
     "This group contains attributes defining the framing of data on the 
      link interface."
::= { htdsFramer 11 }

htdsFramerLinkEntry OBJECT-TYPE
   SYNTAX     HtdsFramerLinkEntry
   ACCESS     not-accessible
   STATUS     mandatory
   DESCRIPTION
     "An entry in the htdsFramerLinkTable."
   INDEX {
      htdsIndex,
      htdsFramerIndex }
::= { htdsFramerLinkTable 1 }

HtdsFramerLinkEntry ::= SEQUENCE {
   htdsFramerDataInversion
      INTEGER,
   htdsFramerNonOctetData
      INTEGER,
   htdsFramerFrameCrcType
      INTEGER,
   htdsFramerFlagsBetweenFrames
      Unsigned32,
   htdsFramerLineSignalTransport
      INTEGER }

htdsFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted."
   DEFVAL     { off }
::= { htdsFramerLinkEntry 2 }

htdsFramerNonOctetData OBJECT-TYPE
   SYNTAX     INTEGER  {
                 no(0),
                 yes(1) }
   ACCESS     read-write
   STATUS     mandatory
   DESCRIPTION
     "This attribute determines whether the data being received has the 
      potential to be non-octet aligned. If it is set to yes, then neither crc 
      checking and generation or abort detection will be functional."
   DEFVAL     { no }
::= { htdsFramerLinkEntry 3 }

htdsFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used."
   DEFVAL     { crc16 }
::= { htdsFramerLinkEntry 4 }

htdsFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { htdsFramerLinkEntry 5 }

htdsFramerLineSignalTransport OBJECT-TYPE
   SYNTAX     INTEGER  {
                 off(0),
                 on(1) }
   ACCESS     read-write
   STATUS     mandatory
   DESCRIPTION
     "This attribute determines how modem status lead information on a 
      V35 or V11 port is handled. When the value of the attribute is set to 
      on, line signal changes are passed transparently through the 
      network to the remote end of the connection, where they are passed 
      out on that end's outgoing leads. When the value of the attribute is 
      set to off, line signal changes are not transparently passed through 
      the network. Both ends must be provisioned to support this function 
      for line signal transport to work. It is highly recommended that line 
      signal interpretation is set to 'don't care' on the associated vport 
      component (ie. vport attributes readyLineState and 
      dataTransferLineState)."
   DEFVAL     { off }
::= { htdsFramerLinkEntry 8 }

htdsFramerStateTable OBJECT-TYPE
   SYNTAX     SEQUENCE OF HtdsFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { htdsFramer 12 }

htdsFramerStateEntry OBJECT-TYPE
   SYNTAX     HtdsFramerStateEntry
   ACCESS     not-accessible
   STATUS     mandatory
   DESCRIPTION
     "An entry in the htdsFramerStateTable."
   INDEX {
      htdsIndex,
      htdsFramerIndex }
::= { htdsFramerStateTable 1 }

HtdsFramerStateEntry ::= SEQUENCE {
   htdsFramerAdminState
      INTEGER,
   htdsFramerOperationalState
      INTEGER,
   htdsFramerUsageState
      INTEGER }

htdsFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { htdsFramerStateEntry 1 }

htdsFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { htdsFramerStateEntry 2 }

htdsFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { htdsFramerStateEntry 3 }

htdsFramerStatsTable OBJECT-TYPE
   SYNTAX     SEQUENCE OF HtdsFramerStatsEntry
   ACCESS     not-accessible
   STATUS     mandatory
   DESCRIPTION
     "This group contains the operational statistics data for a Framer 
      component."
::= { htdsFramer 13 }

htdsFramerStatsEntry OBJECT-TYPE
   SYNTAX     HtdsFramerStatsEntry
   ACCESS     not-accessible
   STATUS     mandatory
   DESCRIPTION
     "An entry in the htdsFramerStatsTable."
   INDEX {
      htdsIndex,
      htdsFramerIndex }
::= { htdsFramerStatsTable 1 }

HtdsFramerStatsEntry ::= SEQUENCE {
   htdsFramerFrmToIf
      Counter32,
   htdsFramerFrmFromIf
      Counter32,
   htdsFramerOctetFromIf
      Counter32,
   htdsFramerAborts
      Counter32,
   htdsFramerCrcErrors
      Counter32,
   htdsFramerLrcErrors
      Counter32,
   htdsFramerNonOctetErrors
      Counter32,
   htdsFramerOverruns
      Counter32,
   htdsFramerUnderruns
      Counter32,
   htdsFramerLargeFrmErrors
      Counter32 }

htdsFramerFrmToIf OBJECT-TYPE
   SYNTAX     Counter32 
   ACCESS     read-only
   STATUS     mandatory
   DESCRIPTION
     "This attribute counts the number of frames transmitted to the link 
      interface by Framer.
      This count wraps to zero after reaching its maximum value."
::= { htdsFramerStatsEntry 1 }

htdsFramerFrmFromIf OBJECT-TYPE
   SYNTAX     Counter32 
   ACCESS     read-only
   STATUS     mandatory
   DESCRIPTION
     "This attribute counts the number of frames received from the link 
      interface by Framer.
      This count wraps to zero after reaching its maximum value."
::= { htdsFramerStatsEntry 2 }

htdsFramerOctetFromIf OBJECT-TYPE
   SYNTAX     Counter32 
   ACCESS     read-only
   STATUS     mandatory
   DESCRIPTION
     "The number of bytes received from the link interface by Framer."
::= { htdsFramerStatsEntry 3 }

htdsFramerAborts OBJECT-TYPE
   SYNTAX     Counter32 
   ACCESS     read-only
   STATUS     mandatory
   DESCRIPTION
     "This attribute counts the total number of aborts received.
      This count wraps to zero after reaching its maximum value."
::= { htdsFramerStatsEntry 4 }

htdsFramerCrcErrors OBJECT-TYPE
   SYNTAX     Counter32 
   ACCESS     read-only
   STATUS     mandatory
   DESCRIPTION
     "This attribute counts the total number of frames with CRC errors.
      This count wraps to zero after reaching its maximum value."
::= { htdsFramerStatsEntry 5 }

htdsFramerLrcErrors OBJECT-TYPE
   SYNTAX     Counter32 
   ACCESS     read-only
   STATUS     mandatory
   DESCRIPTION
     "This attribute counts the total number of frames with LRC errors.
      This count wraps to zero after reaching its maximum value."
::= { htdsFramerStatsEntry 6 }

htdsFramerNonOctetErrors OBJECT-TYPE
   SYNTAX     Counter32 
   ACCESS     read-only
   STATUS     mandatory
   DESCRIPTION
     "This attribute counts the total number of frames that were non octet 
      aligned.
      This count wraps to zero after reaching its maximum value."
::= { htdsFramerStatsEntry 7 }

htdsFramerOverruns OBJECT-TYPE
   SYNTAX     Counter32 
   ACCESS     read-only
   STATUS     mandatory
   DESCRIPTION
     "This attribute counts the total number of frames received from the 
      link for which overruns occurred.
      This count wraps to zero after reaching its maximum value."
::= { htdsFramerStatsEntry 8 }

htdsFramerUnderruns OBJECT-TYPE
   SYNTAX     Counter32 
   ACCESS     read-only
   STATUS     mandatory
   DESCRIPTION
     "This attribute counts the total number of frames transmitted to the 
      link for which underruns occurred.
      This count wraps to zero after reaching its maximum value."
::= { htdsFramerStatsEntry 9 }

htdsFramerLargeFrmErrors OBJECT-TYPE
   SYNTAX     Counter32 
   ACCESS     read-only
   STATUS     mandatory
   DESCRIPTION
     "This attribute counts the total number of frames received which 
      were too large. The frame was longer than 8 kbytes or it contained 
      more than the 255 block hardware limit.
      This count wraps to zero after reaching its maximum value."
::= { htdsFramerStatsEntry 10 }

htdsFramerUtilTable OBJECT-TYPE
   SYNTAX     SEQUENCE OF HtdsFramerUtilEntry
   ACCESS     not-accessible
   STATUS     mandatory
   DESCRIPTION
     "This group contains the link utilization operational data for a 
      Framer component."
::= { htdsFramer 14 }

htdsFramerUtilEntry OBJECT-TYPE
   SYNTAX     HtdsFramerUtilEntry
   ACCESS     not-accessible
   STATUS     mandatory
   DESCRIPTION
     "An entry in the htdsFramerUtilTable."
   INDEX {
      htdsIndex,
      htdsFramerIndex }
::= { htdsFramerUtilTable 1 }

HtdsFramerUtilEntry ::= SEQUENCE {
   htdsFramerNormPrioLinkUtilToIf
      Gauge32,
   htdsFramerNormPrioLinkUtilFromIf
      Gauge32 }

htdsFramerNormPrioLinkUtilToIf OBJECT-TYPE
   SYNTAX     Gauge32 (0..100)
   ACCESS     read-only
   STATUS     mandatory
   DESCRIPTION
     "This attribute is the utilization of the normal priority data sent to the 
      link as a percentage of the available bandwidth allocated for the 
      service on the link. The utilization is the average for the last minute."
   DEFVAL     { 0 }
::= { htdsFramerUtilEntry 1 }

htdsFramerNormPrioLinkUtilFromIf OBJECT-TYPE
   SYNTAX     Gauge32 (0..100)
   ACCESS     read-only
   STATUS     mandatory
   DESCRIPTION
     "This attribute is the utilization of the normal priority data received 
      from the link as a percentage of the available bandwidth allocated 
      for the service on the link. The utilization is the average for the last 
      minute."
   DEFVAL     { 0 }
::= { htdsFramerUtilEntry 3 }


-- Htds/n PLC
-- This is the description of the PLC Component for the Htds service. 

htdsPlc OBJECT IDENTIFIER ::= { htds 3 }



htdsPlcRowStatusTable OBJECT-TYPE
   SYNTAX     SEQUENCE OF HtdsPlcRowStatusEntry
   ACCESS     not-accessible
   STATUS     mandatory
   DESCRIPTION
     "This entry controls the addition and deletion of 
      htdsPlc components."
::= { htdsPlc 1 }

htdsPlcRowStatusEntry OBJECT-TYPE
   SYNTAX     HtdsPlcRowStatusEntry
   ACCESS     not-accessible
   STATUS     mandatory
   DESCRIPTION
     "A single entry in the table represents a single 
      htdsPlc component."
   INDEX {
      htdsIndex,
      htdsPlcIndex }
::= { htdsPlcRowStatusTable 1 }

HtdsPlcRowStatusEntry ::= SEQUENCE {
   htdsPlcRowStatus
      RowStatus,
   htdsPlcComponentName
      DisplayString,
   htdsPlcStorageType
      StorageType,
   htdsPlcIndex
      NonReplicated }

htdsPlcRowStatus OBJECT-TYPE
   SYNTAX     RowStatus 
   ACCESS     read-only
   STATUS     mandatory
   DESCRIPTION
     "This variable is used as the basis for SNMP naming of
      htdsPlc components.
      These components cannot be added nor deleted."
::= { htdsPlcRowStatusEntry 1 }

htdsPlcComponentName OBJECT-TYPE
   SYNTAX     DisplayString 
   ACCESS     read-only
   STATUS     mandatory
   DESCRIPTION
     "This variable provides the component's string name for
      use with the ASCII Console Interface"
::= { htdsPlcRowStatusEntry 2 }

htdsPlcStorageType OBJECT-TYPE
   SYNTAX     StorageType 
   ACCESS     read-only
   STATUS     mandatory
   DESCRIPTION
     "This variable represents the storage type value for the
      htdsPlc tables."
::= { htdsPlcRowStatusEntry 4 }

htdsPlcIndex OBJECT-TYPE
   SYNTAX     NonReplicated 
   ACCESS     not-accessible
   STATUS     mandatory
   DESCRIPTION
     "This variable represents the index for the htdsPlc tables."
::= { htdsPlcRowStatusEntry 10 }

htdsPlcProvTable OBJECT-TYPE
   SYNTAX     SEQUENCE OF HtdsPlcProvEntry
   ACCESS     not-accessible
   STATUS     mandatory
   DESCRIPTION
     "This group contains all provisionable attributes for a permanent 
      logical connection. Note that all of the attributes are valid and 
      provisionable on both ends of a connection. However with the 
      exception of remoteName, all operational attributes are derived 
      from the originating end provisioning, which may be either end 
      unless remoteName is not provisioned on one end."
::= { htdsPlc 10 }

htdsPlcProvEntry OBJECT-TYPE
   SYNTAX     HtdsPlcProvEntry
   ACCESS     not-accessible
   STATUS     mandatory
   DESCRIPTION
     "An entry in the htdsPlcProvTable."
   INDEX {
      htdsIndex,
      htdsPlcIndex }
::= { htdsPlcProvTable 1 }

HtdsPlcProvEntry ::= SEQUENCE {
   htdsPlcRemoteName
      AsciiString,
   htdsPlcSetupPriority
      Unsigned32,
   htdsPlcHoldingPriority
      Unsigned32,
   htdsPlcRequiredTxBandwidth
      Unsigned32,
   htdsPlcRequiredRxBandwidth
      Unsigned32,
   htdsPlcRequiredTrafficType
      INTEGER,
   htdsPlcPermittedTrunkTypes
      OCTET STRING,
   htdsPlcRequiredSecurity
      Unsigned32,
   htdsPlcRequiredCustomerParm
      Unsigned32,
   htdsPlcPathAttributeToMinimize
      INTEGER,
   htdsPlcMaximumAcceptableCost
      Unsigned32,
   htdsPlcMaximumAcceptableDelay
      Unsigned32,
   htdsPlcEmissionPriority
      Unsigned32,
   htdsPlcDiscardPriority
      Unsigned32,
   htdsPlcPathType
      INTEGER,
   htdsPlcPathFailureAction
      INTEGER,
   htdsPlcBumpPreference
      INTEGER,
   htdsPlcOptimization
      INTEGER }

htdsPlcRemoteName OBJECT-TYPE
   SYNTAX     AsciiString (SIZE (0..40))
   ACCESS     read-write
   STATUS     mandatory
   DESCRIPTION
     "This attribute is the PLC's remote end point's address in the format 
      of a Passport component name The syntax of a component is:
      'em/node type/instance'. End points are identified using a node 
      name and a service name. As an example, the end point component 
      name for the third voice service on node MoonBase is:
      'EM/MoonBase VS/3'. If the remoteName is provisioned it must 
      match the remote name of the other end or the connection will not 
      be established even if the remote end is provisioned correctly. If no 
      remoteName is provisioned then this LC will accept connections 
      from any other remote LC and it will not originate calls. 
      Connections establish faster and are unique if both ends are 
      provisioned with the remoteName.
      These strings are case insensitive but the complete component name 
      must be input."
   DEFVAL     { ''H }  -- ""
::= { htdsPlcProvEntry 2 }

htdsPlcSetupPriority OBJECT-TYPE
   SYNTAX     Unsigned32 (0..4)
   ACCESS     read-write
   STATUS     mandatory
   DESCRIPTION
     "This attribute gives the priority at which a path is established. 
      Zero(0) is the highest priority and four(4) is the lowest. When 
      PORS establishes a path through the network, it uses the 
      setupPriority attribute to determine its potential for bumping 
      established paths to acquire their bandwidth. The holdingPriority, a 
      complementary attribute of this component, indicates the priority a 
      path maintains once it is established. A new path can bump an 
      existing path if the new path's setupPriority is higher (numerically 
      less) than the existing path's holdingPriority."
   DEFVAL     { 2 }
::= { htdsPlcProvEntry 3 }

htdsPlcHoldingPriority OBJECT-TYPE
   SYNTAX     Unsigned32 (0..4)
   ACCESS     read-write
   STATUS     mandatory
   DESCRIPTION
     "This attribute gives the priority that a path holds once it is 
      established. Zero(0) is the highest priority and four(4) is the lowest. 
      A path's holdingPriority determines its likelihood of being bumped 
      by a new path to acquire its bandwidth. The setupPriority, a 
      complementary attribute, indicates the priority of a path at 
      establishment time. A new path can bump an existing path if the 
      new path's setupPriority is higher (numerically less) than the 
      existing path's holdingPriority."
   DEFVAL     { 2 }
::= { htdsPlcProvEntry 4 }

htdsPlcRequiredTxBandwidth OBJECT-TYPE
   SYNTAX     Unsigned32 (0..4294967295)
   ACCESS     read-write
   STATUS     mandatory
   DESCRIPTION
     "This attribute gives the bandwidth (in bits per second) reserved by a 
      path on each of the trunks of its route. This attribute represents the 
      bandwidth for traffic outgoing to the remote end point. This value 
      should be chosen to achieve the amount of statistical bandwidth 
      sharing that is desired by the network administration. This 
      reservation is not enforced and is used to determine how many paths 
      can be supported on a trunk. Both ends should be provisioned with 
      the correct values allowing for the fact that Transmit at this end 
      represents Receive at the remote end. Note that when the values do 
      not correspond the originating end of the connection determines the 
      value."
   DEFVAL     { 64000 }
::= { htdsPlcProvEntry 5 }

htdsPlcRequiredRxBandwidth OBJECT-TYPE
   SYNTAX     Unsigned32 (0..4294967295)
   ACCESS     read-write
   STATUS     mandatory
   DESCRIPTION
     "This attribute gives the bandwidth (in bits per second) reserved by a 
      path on each of trunks of its route. This attribute represents the 
      bandwidth for traffic incoming from the remote end point. This 
      value should be chosen to achieve the amount of statistical 
      bandwidth sharing that is desired by the network administration. 
      This reservation is not enforced and is used to determine how many 
      paths can be supported on a trunk. Both ends should be provisioned 
      with the correct values allowing for the fact that Transmit at this end 
      represents Receive at the remote end. Note that when the values do 
      not correspond the originating end of the connection determines the 
      value."
   DEFVAL     { 64000 }
::= { htdsPlcProvEntry 6 }

htdsPlcRequiredTrafficType OBJECT-TYPE
   SYNTAX     INTEGER  {
                 voice(0),
                 data(1),
                 video(2),
                 trafficType1(3),
                 trafficType2(4),
                 trafficType3(5),
                 trafficType4(6),
                 trafficType5(7) }
   ACCESS     read-write
   STATUS     mandatory
   DESCRIPTION
     "This attribute indicates the type of traffic transmitted over the path. 
      There are eight(8) possible traffic types, and the path can transmit 
      only one of them. The originating end of the connection determines 
      the type. These are arbitrary designations for traffic type. The voice, 
      data and video traffic types are defined, and five(5) other arbitrary 
      traffic types can be defined by the network administration. This 
      attribute is used in the route selection process to restrict the route to 
      trunks that support this traffic type. The supportedTrafficType trunk 
      attribute lists all the types of traffic allowed on the trunk. For 
      example, if requiredTrafficType is specified as trafficType1 then 
      only trunks that include trafficType1 in supportedTrafficType, will 
      be candidates for this connection."
   DEFVAL     { data }
::= { htdsPlcProvEntry 7 }

htdsPlcPermittedTrunkTypes OBJECT-TYPE
   SYNTAX     OCTET STRING (SIZE (1))
   ACCESS     read-write
   STATUS     mandatory
   DESCRIPTION
     "This attribute lists up to eight(8) types of trunk that can be used on 
      the route. The terrestrial and satellite trunk types have been 
      defined, leaving six(6) remaining arbitrary types that can be defined 
      by the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
   DEFVAL     { 'f8'H }
::= { htdsPlcProvEntry 8 }

htdsPlcRequiredSecurity OBJECT-TYPE
   SYNTAX     Unsigned32 (0..7)
   ACCESS     read-write
   STATUS     mandatory
   DESCRIPTION
     "This attribute indicates the required minimum level of security of 
      the trunks on the route. Zero(0) represents the most secure and 
      seven(7) represents the least secure. The trunk's security is 
      indicated by the trunkSecurity attribute of the Trunk component, 
      and has values identical in range and meaning to the 
      requiredSecurity attribute. PORS ensures that any route selected 
      does not contain a trunk whose trunkSecurity attribute is 
      numerically greater than the requiredSecurity."
   DEFVAL     { 4 }
::= { htdsPlcProvEntry 9 }

htdsPlcRequiredCustomerParm OBJECT-TYPE
   SYNTAX     Unsigned32 (0..7)
   ACCESS     read-write
   STATUS     mandatory
   DESCRIPTION
     "This attribute indicates the allowed customer defined parameter of 
      the trunks on the route. Its value, a number from zero(0) to 
      seven(7), is chosen by a network administration to have a meaning 
      specific to their network, thus allowing them to customize the use of 
      their trunks. A complementary trunk attribute, customerParameter, 
      also has a value from zero(0) to seven(7). The route selection 
      process does not consider trunks whose customerParameter is 
      greater than the requiredCustomerParameter of the path."
   DEFVAL     { 4 }
::= { htdsPlcProvEntry 10 }

htdsPlcPathAttributeToMinimize OBJECT-TYPE
   SYNTAX     INTEGER  {
                 cost(0),
                 delay(1) }
   ACCESS     read-write
   STATUS     mandatory
   DESCRIPTION
     "This attribute indicates whether a route is selected on the basis of 
      minimizing the cost or the delay. Each trunk has a cost and a delay 
      metric associated with it. The cost or delay of a route is the sum of 
      the cost or delay metrics of all the trunks on the route. The route 
      selection algorithm uses this attribute as the minimization criteria. If 
      more than one route is found while using this attribute as the 
      minimization criteria, then the route with the smallest non-
      minimization metric is chosen amongst the equivalent routes."
   DEFVAL     { cost }
::= { htdsPlcProvEntry 11 }

htdsPlcMaximumAcceptableCost OBJECT-TYPE
   SYNTAX     Unsigned32 (0..65535)
   ACCESS     read-write
   STATUS     mandatory
   DESCRIPTION
     "This attribute indicates an upper bound on the cost metric of a route, 
      which is the sum of the cost metrics of all trunks on the route. The 
      cost metric is the trunkCost attribute of the Trunk component. This 
      attribute is used to accept or reject a path after the route selection 
      algorithm has been applied, regardless of the minimization criteria. 
      It is possible that there may not be a route with an acceptable cost."
   DEFVAL     { 1280 }
::= { htdsPlcProvEntry 12 }

htdsPlcMaximumAcceptableDelay OBJECT-TYPE
   SYNTAX     Unsigned32 (0..100000)
   ACCESS     read-write
   STATUS     mandatory
   DESCRIPTION
     "This attribute indicates an upper bound on the delay of a route, 
      which is the sum of the delay of all trunks on the route. It should be 
      provisioned with a reasonable maximum acceptable delay for the 
      end to end one way delay of a 512 byte packet.
      Note that the delay for a trunk can be a provisioned (with override) 
      or measured value on the trunk. PORs does not recommend using 
      override for the delay on a trunk since this has little added value for 
      PORs traffic.
      Remember, that the trunk measuredRoundTripDelay (ms) 
      discovered through the Trunk staging protocols, divided by two and 
      truncated, to provide the one way delay, is used to populate the 
      topological database. The value includes emission, propagation, and 
      queuing delays. A 512 byte data packet is used to perform the 
      measurement. This value is updated periodically by Trunks and 
      reflects the operating delay of the trunk. PORs uses this attribute to 
      accept or reject a path after the route selection algorithm has been 
      applied, regardless of the minimization criteria."
   DEFVAL     { 100000 }
::= { htdsPlcProvEntry 13 }

htdsPlcEmissionPriority OBJECT-TYPE
   SYNTAX     Unsigned32 (1..2)
   ACCESS     read-write
   STATUS     mandatory
   DESCRIPTION
     "This attribute indicates the urgency with which packets on the path 
      are emitted by the trunks on the route. EmissionPriority of Zero(0) 
      indicates the highest emission priority, while two (2) indicates the 
      lowest emission priority. Packets with a higher emissionPriority (or 
      numerically less) are serviced and sent out before the packets of 
      lower emissionPriority (or numerically higher)."
   DEFVAL     { 1 }
::= { htdsPlcProvEntry 14 }

htdsPlcDiscardPriority OBJECT-TYPE
   SYNTAX     Unsigned32 (1..3)
   ACCESS     read-write
   STATUS     mandatory
   DESCRIPTION
     "This attribute indicates the importance of the packets on the path. 
      One(1) is used for paths carrying the most important traffic, and 
      three(3) is used for paths carrying the least important traffic. 
      Packets with lower discardPriority(numerically higher) are 
      discarded after packets with a higher discardPriority(numerically 
      lower)."
   DEFVAL     { 2 }
::= { htdsPlcProvEntry 15 }

htdsPlcPathType OBJECT-TYPE
   SYNTAX     INTEGER  {
                 normal(0),
                 manual(1),
                 forced(2) }
   ACCESS     read-write
   STATUS     mandatory
   DESCRIPTION
     "This attribute specifies if the path for this PLC is determined 
      automatically or by static provisioning. The default (normal) is to 
      automatically choose a route with Route Selection. Normal 
      pathTypes require less provisioning and can dynamically handle 
      path failures. The other pathTypes are both manual pathTypes 
      where the operator must specify, through provisioning, a static route 
      termed the manualPath. A manual pathType connection is nearly 
      identical to a normal path type connection with the exception that 
      the route is pre-provisioned. For a manual pathType, bandwidth 
      reservations are respected along the path exactly as in a normal 
      path. The last type, the forced pathType, is also a manual path but 
      regardless of the bandwidth available the route is granted provided 
      the trunks are operational and there are sufficient Logical Channels 
      (LChs). 
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
   DEFVAL     { normal }
::= { htdsPlcProvEntry 16 }

htdsPlcPathFailureAction OBJECT-TYPE
   SYNTAX     INTEGER  {
                 disconnectConnection(0),
                 reRoutePath(1) }
   ACCESS     read-write
   STATUS     mandatory
   DESCRIPTION
     "This attribute is used to specify whether the application can tolerate 
      momentary interruption of a path while a new path is selected. If 
      disconnectConnection is chosen, the application is informed as 
      soon as possible about a failure by disconnection. If the attribute is 
      set to reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      All pathTypes respect this attribute. Also on a manualPath with 
      both ends provisioned with independent paths (at least with respect 
      to the failure) this option will have the desired effect that the path is 
      rerouted without complete disconnection at both ends."
   DEFVAL     { reRoutePath }
::= { htdsPlcProvEntry 17 }

htdsPlcBumpPreference OBJECT-TYPE
   SYNTAX     INTEGER  {
                 bumpWhenNecessary(0),
                 bumpToObtainBestRoute(1) }
   ACCESS     read-write
   STATUS     mandatory
   DESCRIPTION
     "This attribute controls when bumping occurs in the route selection 
      process. A connection with higher (numerically less) setupPriority 
      may bump a connection with lower (numerically higher) 
      holdingPriority in order to acquire its bandwidth and be established. 
      By default, bumping occurs only when it is necessary. That is, a 
      connection will bump another connection only if there is no other 
      way for the connection to be established. A connection may be set 
      to always bump in order to find the best route it may have."
   DEFVAL     { bumpWhenNecessary }
::= { htdsPlcProvEntry 18 }

htdsPlcOptimization OBJECT-TYPE
   SYNTAX     INTEGER  {
                 disabled(0),
                 enabled(1) }
   ACCESS     read-write
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
   DEFVAL     { enabled }
::= { htdsPlcProvEntry 19 }

htdsPlcMpathTable OBJECT-TYPE
   SYNTAX     SEQUENCE OF HtdsPlcMpathEntry
   ACCESS     not-accessible
   STATUS     mandatory
   DESCRIPTION
     "This attribute is optional and specifies the sequence of trunks to be 
      used as the route for the path, thus bypassing PORS' automatic 
      route selection. If the path fails the validation, no other path can be 
      selected1. This attribute should only be used in special cases since 
      the route selection algorithm is able to find and maintain the best 
      routes. A related path attribute, the pathType, determines if this 
      route will be used as a manual or forced path type. 
      As an example, the trunk component name for the third trunk on 
      node MoonBase is 'EM/MoonBase Trk/3'. Note that only the first 
      end of the trunk that the packet would encounter is provisioned. 
      These strings are case insensitive but the complete component name 
      must be input. 
      
      Note 1: the trunk designation must be a 3-letter form, e.g., 'trk'. 
      Note 2: only the outbound trunks component names are used to 
      provision the manualPath.
      
      Note 3: It is recommended to have two independent routes specified 
      for a manual path by specifying a different manualPath (non-
      symmetric) for each end. In this case, there is no way to select 
      which route will be used (first up wins) but if one path is torn down 
      due to a failure then the other manualPath may be used to reroute 
      the path."
::= { htdsPlc 265 }

htdsPlcMpathEntry OBJECT-TYPE
   SYNTAX     HtdsPlcMpathEntry
   ACCESS     not-accessible
   STATUS     mandatory
   DESCRIPTION
     "An entry in the htdsPlcMpathTable."
   INDEX {
      htdsIndex,
      htdsPlcIndex,
      htdsPlcMpathIndex }
::= { htdsPlcMpathTable 1 }

HtdsPlcMpathEntry ::= SEQUENCE {
   htdsPlcMpathIndex
      Integer32,
   htdsPlcMpathValue
      AsciiString }

htdsPlcMpathIndex OBJECT-TYPE
   SYNTAX     Integer32 (0..9)
   ACCESS     not-accessible
   STATUS     mandatory
   DESCRIPTION
     "This variable represents the htdsPlcMpathTable
      specific index for the htdsPlcMpathTable."
::= { htdsPlcMpathEntry 1 }

htdsPlcMpathValue OBJECT-TYPE
   SYNTAX     AsciiString (SIZE (0..40))
   ACCESS     read-write
   STATUS     mandatory
   DESCRIPTION
     "This variable represents an individual value for the
      htdsPlcMpathTable."
::= { htdsPlcMpathEntry 2 }


-- ...Lc
-- This component contains all of the operation attributes for a Path 
-- Oriented Logical Connection.

htdsLCo OBJECT IDENTIFIER ::= { htds 4 }



htdsLCoRowStatusTable OBJECT-TYPE
   SYNTAX     SEQUENCE OF HtdsLCoRowStatusEntry
   ACCESS     not-accessible
   STATUS     mandatory
   DESCRIPTION
     "This entry controls the addition and deletion of 
      htdsLCo components."
::= { htdsLCo 1 }

htdsLCoRowStatusEntry OBJECT-TYPE
   SYNTAX     HtdsLCoRowStatusEntry
   ACCESS     not-accessible
   STATUS     mandatory
   DESCRIPTION
     "A single entry in the table represents a single 
      htdsLCo component."
   INDEX {
      htdsIndex,
      htdsLCoIndex }
::= { htdsLCoRowStatusTable 1 }

HtdsLCoRowStatusEntry ::= SEQUENCE {
   htdsLCoRowStatus
      RowStatus,
   htdsLCoComponentName
      DisplayString,
   htdsLCoStorageType
      StorageType,
   htdsLCoIndex
      NonReplicated }

htdsLCoRowStatus OBJECT-TYPE
   SYNTAX     RowStatus 
   ACCESS     read-only
   STATUS     mandatory
   DESCRIPTION
     "This variable is used as the basis for SNMP naming of
      htdsLCo components.
      These components cannot be added nor deleted."
::= { htdsLCoRowStatusEntry 1 }

htdsLCoComponentName OBJECT-TYPE
   SYNTAX     DisplayString 
   ACCESS     read-only
   STATUS     mandatory
   DESCRIPTION
     "This variable provides the component's string name for
      use with the ASCII Console Interface"
::= { htdsLCoRowStatusEntry 2 }

htdsLCoStorageType OBJECT-TYPE
   SYNTAX     StorageType 
   ACCESS     read-only
   STATUS     mandatory
   DESCRIPTION
     "This variable represents the storage type value for the
      htdsLCo tables."
::= { htdsLCoRowStatusEntry 4 }

htdsLCoIndex OBJECT-TYPE
   SYNTAX     NonReplicated 
   ACCESS     not-accessible
   STATUS     mandatory
   DESCRIPTION
     "This variable represents the index for the htdsLCo tables."
::= { htdsLCoRowStatusEntry 10 }

htdsLCoPathDataTable OBJECT-TYPE
   SYNTAX     SEQUENCE OF HtdsLCoPathDataEntry
   ACCESS     not-accessible
   STATUS     mandatory
   DESCRIPTION
     "This group contains all operational attributes for the path oriented 
      LCo."
::= { htdsLCo 10 }

htdsLCoPathDataEntry OBJECT-TYPE
   SYNTAX     HtdsLCoPathDataEntry
   ACCESS     not-accessible
   STATUS     mandatory
   DESCRIPTION
     "An entry in the htdsLCoPathDataTable."
   INDEX {
      htdsIndex,
      htdsLCoIndex }
::= { htdsLCoPathDataTable 1 }

HtdsLCoPathDataEntry ::= SEQUENCE {
   htdsLCoState
      INTEGER,
   htdsLCoOverrideRemoteName
      AsciiString,
   htdsLCoEnd
      INTEGER,
   htdsLCoCostMetric
      Unsigned32,
   htdsLCoDelayMetric
      Unsigned32,
   htdsLCoRoundTripDelay
      Unsigned32,
   htdsLCoSetupPriority
      Unsigned32,
   htdsLCoHoldingPriority
      Unsigned32,
   htdsLCoRequiredTxBandwidth
      Gauge32,
   htdsLCoRequiredRxBandwidth
      Gauge32,
   htdsLCoRequiredTrafficType
      INTEGER,
   htdsLCoPermittedTrunkTypes
      OCTET STRING,
   htdsLCoRequiredSecurity
      Unsigned32,
   htdsLCoRequiredCustomerParameter
      Unsigned32,
   htdsLCoEmissionPriority
      Unsigned32,
   htdsLCoDiscardPriority
      Unsigned32,
   htdsLCoPathType
      INTEGER,
   htdsLCoRetryCount
      Unsigned32,
   htdsLCoPathFailureCount
      Unsigned32,
   htdsLCoReasonForNoRoute
      INTEGER,
   htdsLCoLastTearDownReason
      INTEGER,
   htdsLCoPathFailureAction
      INTEGER,
   htdsLCoBumpPreference
      INTEGER,
   htdsLCoOptimization
      INTEGER,
   htdsLCoPathUpDateTime
      EnterpriseDateAndTime }

htdsLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { htdsLCoPathDataEntry 1 }

htdsLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { htdsLCoPathDataEntry 2 }

htdsLCoEnd OBJECT-TYPE
   SYNTAX     INTEGER  {
                 calling(0),
                 called(1) }
   ACCESS     read-only
   STATUS     mandatory
   DESCRIPTION
     "This attribute identifies whether this is the calling or called end of 
      the path."
::= { htdsLCoPathDataEntry 3 }

htdsLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { htdsLCoPathDataEntry 4 }

htdsLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { htdsLCoPathDataEntry 5 }

htdsLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { htdsLCoPathDataEntry 6 }

htdsLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { htdsLCoPathDataEntry 7 }

htdsLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { htdsLCoPathDataEntry 8 }

htdsLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { htdsLCoPathDataEntry 9 }

htdsLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { htdsLCoPathDataEntry 10 }

htdsLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { htdsLCoPathDataEntry 11 }

htdsLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { htdsLCoPathDataEntry 12 }

htdsLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { htdsLCoPathDataEntry 13 }

htdsLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { htdsLCoPathDataEntry 14 }

htdsLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { htdsLCoPathDataEntry 15 }

htdsLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { htdsLCoPathDataEntry 16 }

htdsLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { htdsLCoPathDataEntry 17 }

htdsLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { htdsLCoPathDataEntry 18 }

htdsLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { htdsLCoPathDataEntry 19 }

htdsLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { htdsLCoPathDataEntry 20 }

htdsLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { htdsLCoPathDataEntry 21 }

htdsLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { htdsLCoPathDataEntry 22 }

htdsLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { htdsLCoPathDataEntry 23 }

htdsLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { htdsLCoPathDataEntry 24 }

htdsLCoPathUpDateTime OBJECT-TYPE
   SYNTAX     EnterpriseDateAndTime (SIZE (0 | 19))
   ACCESS     read-only
   STATUS     mandatory
   DESCRIPTION
     "This is the time stamp when the current path was established or 
      reestablished."
::= { htdsLCoPathDataEntry 25 }

htdsLCoStatsTable OBJECT-TYPE
   SYNTAX     SEQUENCE OF HtdsLCoStatsEntry
   ACCESS     not-accessible
   STATUS     mandatory
   DESCRIPTION
     "This group contains the operational statistics attributes for the path 
      oriented LCo."
::= { htdsLCo 11 }

htdsLCoStatsEntry OBJECT-TYPE
   SYNTAX     HtdsLCoStatsEntry
   ACCESS     not-accessible
   STATUS     mandatory
   DESCRIPTION
     "An entry in the htdsLCoStatsTable."
   INDEX {
      htdsIndex,
      htdsLCoIndex }
::= { htdsLCoStatsTable 1 }

HtdsLCoStatsEntry ::= SEQUENCE {
   htdsLCoPktsToNetwork
      PassportCounter64,
   htdsLCoBytesToNetwork
      PassportCounter64,
   htdsLCoPktsFromNetwork
      PassportCounter64,
   htdsLCoBytesFromNetwork
      PassportCounter64 }

htdsLCoPktsToNetwork OBJECT-TYPE
   SYNTAX     PassportCounter64 
   ACCESS     read-only
   STATUS     mandatory
   DESCRIPTION
     "This attribute counts the number of packets transmitted to the 
      network over this Logical Connection."
::= { htdsLCoStatsEntry 1 }

htdsLCoBytesToNetwork OBJECT-TYPE
   SYNTAX     PassportCounter64 
   ACCESS     read-only
   STATUS     mandatory
   DESCRIPTION
     "This attribute counts the number of bytes sent to the network over 
      this Logical Connection."
::= { htdsLCoStatsEntry 2 }

htdsLCoPktsFromNetwork OBJECT-TYPE
   SYNTAX     PassportCounter64 
   ACCESS     read-only
   STATUS     mandatory
   DESCRIPTION
     "This attribute counts the number of packets received from the 
      remote LCo via the network."
::= { htdsLCoStatsEntry 3 }

htdsLCoBytesFromNetwork OBJECT-TYPE
   SYNTAX     PassportCounter64 
   ACCESS     read-only
   STATUS     mandatory
   DESCRIPTION
     "This attribute counts the number of bytes received from the remote 
      LCo via the network."
::= { htdsLCoStatsEntry 4 }

htdsLCoPathTable OBJECT-TYPE
   SYNTAX     SEQUENCE OF HtdsLCoPathEntry
   ACCESS     not-accessible
   STATUS     mandatory
   DESCRIPTION
     "This attribute contains the trunk component names over which the 
      path has been instantiated and the remote end point name 
      terminating the path."
::= { htdsLCo 264 }

htdsLCoPathEntry OBJECT-TYPE
   SYNTAX     HtdsLCoPathEntry
   ACCESS     not-accessible
   STATUS     mandatory
   DESCRIPTION
     "An entry in the htdsLCoPathTable."
   INDEX {
      htdsIndex,
      htdsLCoIndex,
      htdsLCoPathValue }
::= { htdsLCoPathTable 1 }

HtdsLCoPathEntry ::= SEQUENCE {
   htdsLCoPathValue
      AsciiString }

htdsLCoPathValue OBJECT-TYPE
   SYNTAX     AsciiString (SIZE (0..40))
   ACCESS     read-only
   STATUS     mandatory
   DESCRIPTION
     "This variable represents both the value and the index for the
      htdsLCoPathTable."
::= { htdsLCoPathEntry 1 }




-- 
-- Version and Compliance statements
-- 



-- Object-Group Statement:
-- A list of all current accessible leaf objects.

-- OBJECTS { htdsLCoPathType,
--           htdsStandbyStatus,
--           htdsPlcStorageType,
--           htdsFramerOperationalState,
--           htdsLCoPathValue,
--           htdsLCoOverrideRemoteName,
--           htdsLCoRoundTripDelay,
--           htdsLCoDiscardPriority,
--           htdsOperationalState,
--           htdsPlcEmissionPriority,
--           htdsPlcRequiredSecurity,
--           htdsLCoReasonForNoRoute,
--           htdsPlcRemoteName,
--           htdsLCoOptimization,
--           htdsFramerLrcErrors,
--           htdsFramerCrcErrors,
--           htdsFramerStorageType,
--           htdsLCoLastTearDownReason,
--           htdsFramerAborts,
--           htdsFramerOctetFromIf,
--           htdsPlcPathFailureAction,
--           htdsLCoPermittedTrunkTypes,
--           htdsAvailabilityStatus,
--           htdsIfAdminStatus,
--           htdsPlcHoldingPriority,
--           htdsLCoRequiredTxBandwidth,
--           htdsPlcMaximumAcceptableDelay,
--           htdsPlcMaximumAcceptableCost,
--           htdsPlcSetupPriority,
--           htdsLCoPathFailureCount,
--           htdsLCoHoldingPriority,
--           htdsSnmpOperStatus,
--           htdsLCoRequiredSecurity,
--           htdsLCoState,
--           htdsIfIndex,
--           htdsFramerOverruns,
--           htdsFramerNormPrioLinkUtilToIf,
--           htdsPlcPermittedTrunkTypes,
--           htdsLCoEnd,
--           htdsFramerFrmFromIf,
--           htdsComponentName,
--           htdsUnknownStatus,
--           htdsFramerDataInversion,
--           htdsLCoDelayMetric,
--           htdsLCoBytesFromNetwork,
--           htdsLCoPathFailureAction,
--           htdsFramerFlagsBetweenFrames,
--           htdsStorageType,
--           htdsPlcPathType,
--           htdsLCoPktsToNetwork,
--           htdsPlcOptimization,
--           htdsLCoStorageType,
--           htdsPlcRequiredTxBandwidth,
--           htdsPlcRequiredRxBandwidth,
--           htdsLCoRequiredTrafficType,
--           htdsLCoRequiredRxBandwidth,
--           htdsProceduralStatus,
--           htdsPlcComponentName,
--           htdsFramerFrameCrcType,
--           htdsFramerAdminState,
--           htdsLCoSetupPriority,
--           htdsPlcMpathValue,
--           htdsPlcRowStatus,
--           htdsLCoPktsFromNetwork,
--           htdsControlStatus,
--           htdsAdminState,
--           htdsLCoBytesToNetwork,
--           htdsLCoPathUpDateTime,
--           htdsFramerRowStatus,
--           htdsPlcRequiredTrafficType,
--           htdsFramerNormPrioLinkUtilFromIf,
--           htdsAlarmStatus,
--           htdsLCoComponentName,
--           htdsLCoBumpPreference,
--           htdsRowStatus,
--           htdsFramerNonOctetData,
--           htdsFramerLineSignalTransport,
--           htdsCustomerIdentifier,
--           htdsLCoRowStatus,
--           htdsFramerNonOctetErrors,
--           htdsPlcPathAttributeToMinimize,
--           htdsFramerUsageState,
--           htdsLCoRetryCount,
--           htdsPlcRequiredCustomerParm,
--           htdsLCoEmissionPriority,
--           htdsLCoRequiredCustomerParameter,
--           htdsFramerComponentName,
--           htdsUsageState,
--           htdsPlcDiscardPriority,
--           htdsFramerLargeFrmErrors,
--           htdsLCoCostMetric,
--           htdsFramerInterfaceName,
--           htdsFramerFrmToIf,
--           htdsPlcBumpPreference,
--           htdsFramerUnderruns }
-- STATUS  mandatory
-- DESCRIPTION
--   "A list of all current accessible leaf objects."

hdlcTransparentGroup OBJECT IDENTIFIER ::= { hdlcTransparentMIB 1 }
hdlcTransparentGroupBC OBJECT IDENTIFIER ::= { hdlcTransparentGroup 3 }
hdlcTransparentGroupBC03 OBJECT IDENTIFIER ::= { hdlcTransparentGroupBC 4 }
hdlcTransparentGroupBC03A OBJECT IDENTIFIER ::= { hdlcTransparentGroupBC03 2 }



-- Agent-Capabilities Statement:

-- PRODUCT-RELEASE "Passport Release 7.0 HdlcTransparent."
-- STATUS          mandatory
-- DESCRIPTION     "HdlcTransparent MIB: MIB Version BC03A,
--                  Software Version BG00S4C."
-- SUPPORTS        Nortel-Magellan-Passport-HdlcTransparentMIB
--    INCLUDES     { hdlcTransparentGroupBC03A }

hdlcTransparentCapabilities OBJECT IDENTIFIER ::= { hdlcTransparentMIB 3 }
hdlcTransparentCapabilitiesBC OBJECT IDENTIFIER ::= { hdlcTransparentCapabilities 3 }
hdlcTransparentCapabilitiesBC03 OBJECT IDENTIFIER ::= { hdlcTransparentCapabilitiesBC 4 }
hdlcTransparentCapabilitiesBC03A OBJECT IDENTIFIER ::= { hdlcTransparentCapabilitiesBC03 2 }





END
