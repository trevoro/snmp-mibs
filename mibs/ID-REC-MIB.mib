ID-REC-MIB DEFINITIONS ::= BEGIN

    IMPORTS
        enterprises     FROM RFC1155-SMI;

    marconi     OBJECT IDENTIFIER ::= { enterprises 326 }
    systems     OBJECT IDENTIFIER ::= { marconi 2 }
    external    OBJECT IDENTIFIER ::= { systems 20 }
    dlink       OBJECT IDENTIFIER ::= { external 1 }

        dlinkcommon OBJECT IDENTIFIER ::= { dlink 1 }

        golf        OBJECT IDENTIFIER ::= { dlink 2 }
        golfproducts        OBJECT IDENTIFIER ::= { golf 1 }
        es2000              OBJECT IDENTIFIER ::= { golfproducts 3 }

        golfcommon          OBJECT IDENTIFIER ::= { golf 2 }
        marconi-products    OBJECT IDENTIFIER ::= { golfcommon 1 }
        marconi-es2000Prod  OBJECT IDENTIFIER ::= { marconi-products 28 }
        swProperty          OBJECT IDENTIFIER ::= { marconi-es2000Prod 1 }
        swModule            OBJECT IDENTIFIER ::= { swProperty 1 }

    es2000DevRegistration   OBJECT IDENTIFIER ::= { marconi-es2000Prod 2 }
        es2000Device        OBJECT IDENTIFIER ::= { es2000DevRegistration 1 }

    es2000UnitRegistration  OBJECT IDENTIFIER ::= { marconi-es2000Prod 3 }
        es2000Main          OBJECT IDENTIFIER ::= { es2000UnitRegistration 1 }

    es2000ModuleRegistration    OBJECT IDENTIFIER ::= { marconi-es2000Prod 4 }
        es2000ModuleTx          OBJECT IDENTIFIER ::= { es2000ModuleRegistration 1 }
        es2000ModuleFx          OBJECT IDENTIFIER ::= { es2000ModuleRegistration 2 }
        es2000ModuleGIGAMTRJSX  OBJECT IDENTIFIER ::= { es2000ModuleRegistration 3 }
        es2000ModuleGIGAMTRJLX  OBJECT IDENTIFIER ::= { es2000ModuleRegistration 4 }
        es2000ModuleGIGASCSX    OBJECT IDENTIFIER ::= { es2000ModuleRegistration 5 }
        es2000ModuleGIGASCLX    OBJECT IDENTIFIER ::= { es2000ModuleRegistration 6 }
        es2000ModuleCPUMaster   OBJECT IDENTIFIER ::= { es2000ModuleRegistration 7 }
        es2000ModuleCPUBackup   OBJECT IDENTIFIER ::= { es2000ModuleRegistration 8 }
        es2000ModuleNone        OBJECT IDENTIFIER ::= { es2000ModuleRegistration 9 }

    marconi-mgmt        OBJECT IDENTIFIER ::= { golfcommon 2 }
    es2000Mgmt          OBJECT IDENTIFIER ::= { marconi-mgmt 28 }

END
