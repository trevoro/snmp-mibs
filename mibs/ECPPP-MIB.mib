-- Documents: 285-524-1.

ECPPP-MIB DEFINITIONS ::= BEGIN

IMPORTS
	Counter, IpAddress, enterprises
		FROM RFC1155-SMI
	OBJECT-TYPE
		FROM RFC-1212
	DisplayString
		FROM RFC1213-MIB;

eicon           OBJECT IDENTIFIER  ::= { enterprises 434 }
management      OBJECT IDENTIFIER  ::= { eicon 2 }
mibv2           OBJECT IDENTIFIER  ::= { management 2 }
module          OBJECT IDENTIFIER  ::= { mibv2 4 }

PortRef ::= INTEGER (1..48)     -- Port reference on the server.

PppState ::= INTEGER {
		closed (1),
		opening (2),
		negotiating (3),
		opened (4),
		closing (5),
		other (6)
	}

NcpState ::= INTEGER {
		initial (1),
		starting (2),
		closed (3),
		stopped (4),
		closing (5),
		stopping (6),
		req-sent (7),
		ack-rcvd (8),
		ack-sent (9),
		opened (10),
		other (11)
	}

	ecppp  OBJECT IDENTIFIER ::= { module 23 }

--  ecppp MIB is composed of the  following tables:
  
	--  ecpppStatusTable      ppp link global status info table.
	--  ecpppStatsTable       ppp link global stats table.
	--  ecpppIPInfoTable      ppp link IP info table.
	--  ecpppIPStatsTable     ppp link IP stats table.
	--  ecpppIPXInfoTable     ppp link IPX info table.
	--  ecpppIPXStatsTable    ppp link IPX stats table.
	--  ecpppATInfoTable      ppp link AT info table.
	--  ecpppATStatsTable     ppp link AT stats table.

-- ******************************************
-- *       ecpppStatusTable                 *
-- ******************************************

ecpppStatusTable   OBJECT-TYPE
	SYNTAX    SEQUENCE OF EcpppStatusEntry
	ACCESS    not-accessible
	STATUS    mandatory
	DESCRIPTION
		  "A table containing PPP-link global info"
	::= { ecppp 1 }

ecpppStatusEntry   OBJECT-TYPE
	SYNTAX    EcpppStatusEntry
	ACCESS    not-accessible
	STATUS    mandatory
	DESCRIPTION
		  "Global information about a particular PPP
		   Link."
	INDEX     { ecpppStatusPortRef }
	::= { ecpppStatusTable 1 }

EcpppStatusEntry ::= SEQUENCE {
	ecpppStatusPortRef              
		PortRef,        
	ecpppStatusState        
		PppState,        
	ecpppStatusAuthentProtocol        
		INTEGER,        
	ecpppStatusQualityProtocol        
		INTEGER,        
	ecpppStatusNegotiatedPktSize        
		INTEGER,        
	ecpppStatusWindowSize        
		INTEGER,        
	ecpppStatusProtocolCompr        
		INTEGER,        
	ecpppStatusAddrCtrlCompr        
		INTEGER,        
	ecpppStatusRestartTimer        
		INTEGER,        
	ecpppStatusMaxPacketSize        
		INTEGER,        
	ecpppStatusMaxTerminate 
		INTEGER,        
	ecpppStatusMaxConfig    
		INTEGER,        
	ecpppStatusMaxFailure   
		INTEGER,
	ecpppStatusNcpMask
		INTEGER 
}       
	


ecpppStatusPortRef      OBJECT-TYPE
	SYNTAX  PortRef
	ACCESS  read-only 
	STATUS  mandatory
	DESCRIPTION    
		"The id of the port on which the parameters in the table are
		 configured"
	::= { ecpppStatusEntry 1 }      
			
ecpppStatusState                OBJECT-TYPE
	SYNTAX  PppState
	ACCESS  read-only 
	STATUS  mandatory
	DESCRIPTION    
		"The state of the ppp connection"
	::= { ecpppStatusEntry 2 }
	
ecpppStatusAuthentProtocol      OBJECT-TYPE                     
	SYNTAX  INTEGER {
		pap (1),
		chap (2),
		other (3)
	}
	ACCESS  read-only 
	STATUS  mandatory
	DESCRIPTION    
		"Authentication protocol used"
	::= { ecpppStatusEntry 3 }
	
ecpppStatusQualityProtocol      OBJECT-TYPE             
	SYNTAX  INTEGER {
		lqr (1),
		other (2)
	}
	ACCESS  read-only 
	STATUS  mandatory
	DESCRIPTION    
		"Link quality protocol used "
	::= { ecpppStatusEntry 4 }
	
ecpppStatusNegotiatedPktSize    OBJECT-TYPE             
	SYNTAX  INTEGER
	ACCESS  read-only 
	STATUS  mandatory
	DESCRIPTION    
		"Packet size negotiated."
	::= { ecpppStatusEntry 5 }
	
ecpppStatusWindowSize           OBJECT-TYPE     
	SYNTAX  INTEGER
	ACCESS  read-only 
	STATUS  mandatory
	DESCRIPTION    
		" "
	::= { ecpppStatusEntry 6 }
	
ecpppStatusProtocolCompr        OBJECT-TYPE             
	SYNTAX  INTEGER {
		enabled (1),
		disabled (2)
	}
	ACCESS  read-only 
	STATUS  mandatory
	DESCRIPTION    
		"Protocol Compression"
	::= { ecpppStatusEntry 7 }
	
ecpppStatusAddrCtrlCompr        OBJECT-TYPE             
	SYNTAX  INTEGER {
		enabled (1),
		disabled (2)
	}
	ACCESS  read-only 
	STATUS  mandatory
	DESCRIPTION    
		"Address and Control field Compression."
	::= { ecpppStatusEntry 8 }
	
ecpppStatusRestartTimer         OBJECT-TYPE             
	SYNTAX  INTEGER
	ACCESS  read-only 
	STATUS  mandatory
	DESCRIPTION    
		"Timeout retransmission"
	::= { ecpppStatusEntry 9 }
	
ecpppStatusMaxPacketSize        OBJECT-TYPE             
	SYNTAX  INTEGER
	ACCESS  read-only 
	STATUS  mandatory
	DESCRIPTION    
		"Maximum configured"
	::= { ecpppStatusEntry 10 }
	
ecpppStatusMaxTerminate         OBJECT-TYPE
	SYNTAX  INTEGER
	ACCESS  read-only 
	STATUS  mandatory
	DESCRIPTION    
		"Maximum Terminate Retransmission"
	::= { ecpppStatusEntry 11 }
	
ecpppStatusMaxConfig            OBJECT-TYPE
	SYNTAX  INTEGER
	ACCESS  read-only 
	STATUS  mandatory
	DESCRIPTION    
		"Maximum Configure Retransmission"
	::= { ecpppStatusEntry 12 }
	
ecpppStatusMaxFailure           OBJECT-TYPE
	SYNTAX  INTEGER
	ACCESS  read-only 
	STATUS  mandatory
	DESCRIPTION    
		" "
	::= { ecpppStatusEntry 13 }
	
ecpppStatusNcpMask             OBJECT-TYPE
	SYNTAX  INTEGER
	ACCESS  read-only 
	STATUS  mandatory
	DESCRIPTION    
		"The bitmask value, 1 = IP, 2 = IPX, 4 = AT."
	::= { ecpppStatusEntry 14 }
	
-- ******************************************
-- *       ecpppStatsTable                  *
-- ******************************************/

ecpppStatsTable   OBJECT-TYPE
	SYNTAX    SEQUENCE OF EcpppStatsEntry
	ACCESS    not-accessible
	STATUS    mandatory
	DESCRIPTION
		  "A table containing PPP-link specific variables
		   for this PPP implementation."
	::= { ecppp 2 }

ecpppStatsEntry   OBJECT-TYPE
	SYNTAX    EcpppStatsEntry
	ACCESS    not-accessible
	STATUS    mandatory
	DESCRIPTION
		  "Management information about a particular PPP
		   Link."
	INDEX     { ecpppStatsPortRef }
	::= { ecpppStatsTable 1 }

EcpppStatsEntry ::= SEQUENCE {
	ecpppStatsPortRef               
		PortRef,        
	ecpppStatsLcpReqTx
		Counter,
	ecpppStatsLcpReqRx
		Counter,
	ecpppStatsLcpAckTx
		Counter,
	ecpppStatsLcpAckRx
		Counter,
	ecpppStatsLcpNakTx
		Counter,
	ecpppStatsLcpNakRx
		Counter,
	ecpppStatsLcpRejTx
		Counter,
	ecpppStatsLcpRejRx
		Counter,
	ecpppStatsLcpCodeRejTx
		Counter,
	ecpppStatsLcpCodeRejRx
		Counter,
	ecpppStatsLcpProRejTx
		Counter,
	ecpppStatsLcpProRejRx
		Counter,
	ecpppStatsLcpEchoReqTx
		Counter,
	ecpppStatsLcpEchoReqRx
		Counter,
	ecpppStatsLcpEchoReplyTx
		Counter,
	ecpppStatsLcpEchoReplyRx
		Counter,
	ecpppStatsLcpRestartTimeout
		Counter,
	ecpppStatsLcpTermRetrans
		Counter,
	ecpppStatsLcpConfRetrans
		Counter,
	ecpppStatsFrameTx
		Counter,
	ecpppStatsFrameRx
		Counter,
	ecpppStatsCharTx
		Counter,
	ecpppStatsCharRx
		Counter
}


ecpppStatsPortRef               OBJECT-TYPE                     
	SYNTAX  PortRef
	ACCESS  read-only 
	STATUS  mandatory
	DESCRIPTION    
		"The id of the port on which the parameters in the table are
		 configured"
	::= { ecpppStatsEntry 1 }
	
ecpppStatsLcpReqTx              OBJECT-TYPE
	SYNTAX  Counter
	ACCESS  read-only 
	STATUS  mandatory
	DESCRIPTION    
		"Number of LCP Configure-Request sent"
	::= { ecpppStatsEntry 2 }
	
ecpppStatsLcpReqRx              OBJECT-TYPE
	SYNTAX  Counter
	ACCESS  read-only 
	STATUS  mandatory
	DESCRIPTION    
		"Number of LCP Configure-Request received"
	::= { ecpppStatsEntry 3 }
	
ecpppStatsLcpAckTx              OBJECT-TYPE
	SYNTAX  Counter
	ACCESS  read-only 
	STATUS  mandatory
	DESCRIPTION    
		"Number of LCP Configure-Ack sent "
	::= { ecpppStatsEntry 4 }
	
ecpppStatsLcpAckRx              OBJECT-TYPE
	SYNTAX  Counter
	ACCESS  read-only 
	STATUS  mandatory
	DESCRIPTION    
		"Number of LCP Configure-Ack received"
	::= { ecpppStatsEntry 5 }
	
ecpppStatsLcpNakTx              OBJECT-TYPE
	SYNTAX  Counter
	ACCESS  read-only 
	STATUS  mandatory
	DESCRIPTION    
		"Number of LCP Configure-Nak sent "
	::= { ecpppStatsEntry 6 }
	
ecpppStatsLcpNakRx              OBJECT-TYPE
	SYNTAX  Counter
	ACCESS  read-only 
	STATUS  mandatory
	DESCRIPTION    
		"Number of LCP Configure-Nak received "
	::= { ecpppStatsEntry 7 }
	
ecpppStatsLcpRejTx              OBJECT-TYPE
	SYNTAX  Counter
	ACCESS  read-only 
	STATUS  mandatory
	DESCRIPTION    
		"Number of LCP Configure-Reject sent"
	::= { ecpppStatsEntry 8 }
	
ecpppStatsLcpRejRx              OBJECT-TYPE
	SYNTAX  Counter
	ACCESS  read-only 
	STATUS  mandatory
	DESCRIPTION    
		"Number of LCP Configure-Reject received"
	::= { ecpppStatsEntry 9 }
	
ecpppStatsLcpCodeRejTx          OBJECT-TYPE
	SYNTAX  Counter
	ACCESS  read-only 
	STATUS  mandatory
	DESCRIPTION    
		"Number of LCP Code-Reject sent"
	::= { ecpppStatsEntry 10 }
	
ecpppStatsLcpCodeRejRx          OBJECT-TYPE
	SYNTAX  Counter
	ACCESS  read-only 
	STATUS  mandatory
	DESCRIPTION    
		"Number of LCP Code-Reject received"
	::= { ecpppStatsEntry 11 }
	
ecpppStatsLcpProRejTx           OBJECT-TYPE
	SYNTAX  Counter
	ACCESS  read-only 
	STATUS  mandatory
	DESCRIPTION    
		"Number of Protocol-Reject sent "
	::= { ecpppStatsEntry 12 }
	
ecpppStatsLcpProRejRx           OBJECT-TYPE
	SYNTAX  Counter
	ACCESS  read-only 
	STATUS  mandatory
	DESCRIPTION    
		"Number of Protocol-Reject received"
	::= { ecpppStatsEntry 13 }
	
ecpppStatsLcpEchoReqTx          OBJECT-TYPE
	SYNTAX  Counter
	ACCESS  read-only 
	STATUS  mandatory
	DESCRIPTION    
		"Number of Echo-Request sent "
	::= { ecpppStatsEntry 14 }
	
ecpppStatsLcpEchoReqRx          OBJECT-TYPE
	SYNTAX  Counter
	ACCESS  read-only 
	STATUS  mandatory
	DESCRIPTION    
		"Number of Echo-Request received"
	::= { ecpppStatsEntry 15 }
	
ecpppStatsLcpEchoReplyTx        OBJECT-TYPE
	SYNTAX  Counter
	ACCESS  read-only 
	STATUS  mandatory
	DESCRIPTION    
		"Number of Echo-Reply sent "
	::= { ecpppStatsEntry 16 }
	
ecpppStatsLcpEchoReplyRx        OBJECT-TYPE
	SYNTAX  Counter
	ACCESS  read-only 
	STATUS  mandatory
	DESCRIPTION    
		"Number of Echo-Reply received"
	::= { ecpppStatsEntry 17 }
	
ecpppStatsLcpRestartTimeout     OBJECT-TYPE
	SYNTAX  Counter
	ACCESS  read-only 
	STATUS  mandatory
	DESCRIPTION    
		"Number of restart timer time-out"
	::= { ecpppStatsEntry 18 }
	
ecpppStatsLcpTermRetrans        OBJECT-TYPE
	SYNTAX  Counter
	ACCESS  read-only 
	STATUS  mandatory
	DESCRIPTION    
		"Number of LCP terminate request retransmissions."
	::= { ecpppStatsEntry 19 }
	
ecpppStatsLcpConfRetrans                OBJECT-TYPE
	SYNTAX  Counter
	ACCESS  read-only 
	STATUS  mandatory
	DESCRIPTION    
		"Number of LCP configure request retransmissions."
	::= { ecpppStatsEntry 20 }
	
ecpppStatsFrameTx               OBJECT-TYPE
	SYNTAX  Counter
	ACCESS  read-only 
	STATUS  mandatory
	DESCRIPTION    
		" Number of information frames sent"
	::= { ecpppStatsEntry 21 }
	
ecpppStatsFrameRx               OBJECT-TYPE
	SYNTAX  Counter
	ACCESS  read-only 
	STATUS  mandatory
	DESCRIPTION    
		" Number of information frames received"
	::= { ecpppStatsEntry 22 }
	
ecpppStatsCharTx                OBJECT-TYPE
	SYNTAX  Counter
	ACCESS  read-only 
	STATUS  mandatory
	DESCRIPTION    
		"Number of information characters sent"
	::= { ecpppStatsEntry 23 }
	
ecpppStatsCharRx                OBJECT-TYPE
	SYNTAX  Counter
	ACCESS  read-only 
	STATUS  mandatory
	DESCRIPTION    
		"Number of information characters received "
	::= { ecpppStatsEntry 24 }
	

-- ******************************************
-- *       ecpppIPInfoTable                 *
-- ******************************************

ecpppIPInfoTable   OBJECT-TYPE
	SYNTAX    SEQUENCE OF EcpppIPInfoEntry
	ACCESS    not-accessible
	STATUS    mandatory
	DESCRIPTION
		  "A table for PPP IP Protocol Info"
	::= { ecppp 3 }

ecpppIPInfoEntry   OBJECT-TYPE
	SYNTAX    EcpppIPInfoEntry
	ACCESS    not-accessible
	STATUS    mandatory
	DESCRIPTION
		  "Management information about a particular PPP
		   Link."
	INDEX     { ecpppIPInfoPortRef }
	::= { ecpppIPInfoTable 1 }

EcpppIPInfoEntry ::= SEQUENCE {
	ecpppIPInfoPortRef              
		PortRef,        
	ecpppIPInfoNcpState             
		NcpState,       
	ecpppIPInfoIPComprProtocol              
		INTEGER,        
	ecpppIPInfoIPAddr               
		IpAddress,
	ecpppIPInfoIPcpMaxTerm          
		INTEGER,        
	ecpppIPInfoIPcpMaxConfig        
		INTEGER,        
	ecpppIPInfoIPcpMaxFailure               
		INTEGER 
}


ecpppIPInfoPortRef                OBJECT-TYPE           
	SYNTAX  PortRef
	ACCESS  read-only 
	STATUS  mandatory
	DESCRIPTION    
		"The id of the port on which the parameters in the table are
		 configured"
	::= { ecpppIPInfoEntry 1 }
	
ecpppIPInfoNcpState               OBJECT-TYPE           
	SYNTAX  NcpState
	ACCESS  read-only 
	STATUS  mandatory
	DESCRIPTION    
		"State during NCP phase"
	::= { ecpppIPInfoEntry 2 }
	
ecpppIPInfoIPComprProtocol        OBJECT-TYPE           
	SYNTAX  INTEGER {
		none (1),
		vj-tcp (2)
	}
	ACCESS  read-only 
	STATUS  mandatory
	DESCRIPTION    
		"Compression protocol "
	::= { ecpppIPInfoEntry 3 }
	
ecpppIPInfoIPAddr                 OBJECT-TYPE           
	SYNTAX  IpAddress
	ACCESS  read-only 
	STATUS  mandatory
	DESCRIPTION    
		"IP Address "
	::= { ecpppIPInfoEntry 4 }
	
ecpppIPInfoIPcpMaxTerm            OBJECT-TYPE           
	SYNTAX  INTEGER
	ACCESS  read-only 
	STATUS  mandatory
	DESCRIPTION    
		"Max. terminate retransmission "
	::= { ecpppIPInfoEntry 5 }
	
ecpppIPInfoIPcpMaxConfig             OBJECT-TYPE                
	SYNTAX  INTEGER
	ACCESS  read-only 
	STATUS  mandatory
	DESCRIPTION    
		"Max. configure retransmission"
	::= { ecpppIPInfoEntry 6 }
	
ecpppIPInfoIPcpMaxFailure         OBJECT-TYPE           
	SYNTAX  INTEGER
	ACCESS  read-only 
	STATUS  mandatory
	DESCRIPTION    
		"max config_nak retransmission "
	::= { ecpppIPInfoEntry 7 }
	

-- ******************************************
-- *       ecpppIPStatsTable                *
-- ******************************************

ecpppIPStatsTable   OBJECT-TYPE
	SYNTAX    SEQUENCE OF EcpppIPStatsEntry
	ACCESS    not-accessible
	STATUS    mandatory
	DESCRIPTION
		  "A table for PPP IP Protocol Stats"
	::= { ecppp 4 }

ecpppIPStatsEntry   OBJECT-TYPE
	SYNTAX    EcpppIPStatsEntry
	ACCESS    not-accessible
	STATUS    mandatory
	DESCRIPTION
		  "Management information about a particular PPP
		   Link."
	INDEX     { ecpppIPStatsPortRef }
	::= { ecpppIPStatsTable 1 }

EcpppIPStatsEntry ::= SEQUENCE {
	ecpppIPStatsPortRef             
		PortRef,        
	ecpppIPStatsDatagramsTx         
		Counter,        
	ecpppIPStatsDatagramsRx         
		Counter,        
	ecpppIPStatsCharTx              
		Counter,        
	ecpppIPStatsCharRx              
		Counter,        
	ecpppIPStatsNcpRestartTimeout           
		Counter,        
	ecpppIPStatsNcpTermRetrans              
		Counter,        
	ecpppIPStatsNcpReqRetrans               
		Counter
}       

ecpppIPStatsPortRef             OBJECT-TYPE                     
	SYNTAX  PortRef
	ACCESS  read-only 
	STATUS  mandatory
	DESCRIPTION    
		"The id of the port on which the parameters in the table are
		 configured"
	::= { ecpppIPStatsEntry 1 }
	
ecpppIPStatsDatagramsTx         OBJECT-TYPE             
	SYNTAX  Counter
	ACCESS  read-only 
	STATUS  mandatory
	DESCRIPTION    
		"Number of datagrams sent "
	::= { ecpppIPStatsEntry 2 }
	
ecpppIPStatsDatagramsRx         OBJECT-TYPE             
	SYNTAX  Counter
	ACCESS  read-only 
	STATUS  mandatory
	DESCRIPTION    
		"Number of datagrams received"
	::= { ecpppIPStatsEntry 3 }
	
ecpppIPStatsCharTx              OBJECT-TYPE             
	SYNTAX  Counter
	ACCESS  read-only 
	STATUS  mandatory
	DESCRIPTION    
		" Number of characters sent "
	::= { ecpppIPStatsEntry 4 }
	
ecpppIPStatsCharRx              OBJECT-TYPE             
	SYNTAX  Counter
	ACCESS  read-only 
	STATUS  mandatory
	DESCRIPTION    
		"Number of characters received "
	::= { ecpppIPStatsEntry 5 }
	
ecpppIPStatsNcpRestartTimeout   OBJECT-TYPE             
	SYNTAX  Counter
	ACCESS  read-only 
	STATUS  mandatory
	DESCRIPTION    
		"Number of NCP restart timer time-out"
	::= { ecpppIPStatsEntry 6 }
	
ecpppIPStatsNcpTermRetrans      OBJECT-TYPE             
	SYNTAX  Counter
	ACCESS  read-only 
	STATUS  mandatory
	DESCRIPTION    
		"Number of NCP terminate request retransmissions."
	::= { ecpppIPStatsEntry 7 }
	
ecpppIPStatsNcpReqRetrans       OBJECT-TYPE             
	SYNTAX  Counter
	ACCESS  read-only 
	STATUS  mandatory
	DESCRIPTION    
		"Number of NCP configure request retransmissions."
	::= { ecpppIPStatsEntry 8 }
	

-- ******************************************
-- *       ecpppIPXInfoTable                *
-- ******************************************

ecpppIPXInfoTable   OBJECT-TYPE
	SYNTAX    SEQUENCE OF EcpppIPXInfoEntry
	ACCESS    not-accessible
	STATUS    mandatory
	DESCRIPTION
		  "A table for PPP IPX Protocol Info."
	::= { ecppp 5 }

ecpppIPXInfoEntry   OBJECT-TYPE
	SYNTAX    EcpppIPXInfoEntry
	ACCESS    not-accessible
	STATUS    mandatory
	DESCRIPTION
		  "Management information about a particular PPP
		   Link."
	INDEX     { ecpppIPXInfoPortRef }
	::= { ecpppIPXInfoTable 1 }

EcpppIPXInfoEntry ::= SEQUENCE {
	ecpppIPXInfoPortRef             
		PortRef,        
	ecpppIPXInfoNcpState            
		NcpState,       
	ecpppIPXInfoIPXcpMaxTerm        
		INTEGER,        
	ecpppIPXInfoIPXcpMaxConfig              
		INTEGER,        
	ecpppIPXInfoIPXcpMaxFailure             
		INTEGER 
}


ecpppIPXInfoPortRef               OBJECT-TYPE           
	SYNTAX  PortRef
	ACCESS  read-only 
	STATUS  mandatory
	DESCRIPTION    
		"The id of the port on which the parameters in the table are
		 configured"
	::= { ecpppIPXInfoEntry 1 }
	
ecpppIPXInfoNcpState              OBJECT-TYPE           
	SYNTAX  NcpState
	ACCESS  read-only 
	STATUS  mandatory
	DESCRIPTION    
		"State during NCP phase "
	::= { ecpppIPXInfoEntry 2 }
	
ecpppIPXInfoIPXcpMaxTerm            OBJECT-TYPE         
	SYNTAX  INTEGER
	ACCESS  read-only 
	STATUS  mandatory
	DESCRIPTION    
		"Max. terminate retransmission "
	::= { ecpppIPXInfoEntry 3 }
	
ecpppIPXInfoIPXcpMaxConfig             OBJECT-TYPE              
	SYNTAX  INTEGER
	ACCESS  read-only 
	STATUS  mandatory
	DESCRIPTION    
		"Max. configure retransmission "
	::= { ecpppIPXInfoEntry 4 }
	
ecpppIPXInfoIPXcpMaxFailure         OBJECT-TYPE         
	SYNTAX  INTEGER
	ACCESS  read-only 
	STATUS  mandatory
	DESCRIPTION    
		"Max config_nak retransmission "
	::= { ecpppIPXInfoEntry 5 }
	

-- ******************************************
-- *       ecpppIPXStatsTable               *
-- ******************************************

ecpppIPXStatsTable   OBJECT-TYPE
	SYNTAX    SEQUENCE OF EcpppIPXStatsEntry
	ACCESS    not-accessible
	STATUS    mandatory
	DESCRIPTION
		  "A table for PPP IP Protocol Stats."
	::= { ecppp 6 }

ecpppIPXStatsEntry   OBJECT-TYPE
	SYNTAX    EcpppIPXStatsEntry
	ACCESS    not-accessible
	STATUS    mandatory
	DESCRIPTION
		  "Management information about a particular PPP
		   Link."
	INDEX     { ecpppIPXStatsPortRef }
	::= { ecpppIPXStatsTable 1 }

EcpppIPXStatsEntry ::= SEQUENCE {
	ecpppIPXStatsPortRef            
		PortRef,        
	ecpppIPXStatsDatagramsTx        
		Counter,        
	ecpppIPXStatsDatagramsRx        
		Counter,        
	ecpppIPXStatsCharTx             
		Counter,        
	ecpppIPXStatsCharRx             
		Counter,        
	ecpppIPXStatsNcpRestartTimeout          
		Counter,        
	ecpppIPXStatsNcpTermRetrans             
		Counter,        
	ecpppIPXStatsNcpReqRetrans              
		Counter
}       

ecpppIPXStatsPortRef            OBJECT-TYPE                     
	SYNTAX  PortRef
	ACCESS  read-only 
	STATUS  mandatory
	DESCRIPTION    
		"The id of the port on which the parameters in the table are
		 configured."
	::= { ecpppIPXStatsEntry 1 }
	
ecpppIPXStatsDatagramsTx         OBJECT-TYPE                    
	SYNTAX  Counter
	ACCESS  read-only 
	STATUS  mandatory
	DESCRIPTION    
		" Number of datagrams sent"
	::= { ecpppIPXStatsEntry 2 }
	
ecpppIPXStatsDatagramsRx        OBJECT-TYPE             
	SYNTAX  Counter
	ACCESS  read-only 
	STATUS  mandatory
	DESCRIPTION    
		" Number of datagrams received "
	::= { ecpppIPXStatsEntry 3 }
	
ecpppIPXStatsCharTx             OBJECT-TYPE             
	SYNTAX  Counter
	ACCESS  read-only 
	STATUS  mandatory
	DESCRIPTION    
		" Number of characters sent "
	::= { ecpppIPXStatsEntry 4 }
	
ecpppIPXStatsCharRx             OBJECT-TYPE             
	SYNTAX  Counter
	ACCESS  read-only 
	STATUS  mandatory
	DESCRIPTION    
		"Number of characters received"
	::= { ecpppIPXStatsEntry 5 }
	
ecpppIPXStatsNcpRestartTimeout   OBJECT-TYPE                    
	SYNTAX  Counter
	ACCESS  read-only 
	STATUS  mandatory
	DESCRIPTION    
		"Number of NCP restart timer time-out"
	::= { ecpppIPXStatsEntry 6 }
	
ecpppIPXStatsNcpTermRetrans      OBJECT-TYPE                    
	SYNTAX  Counter
	ACCESS  read-only 
	STATUS  mandatory
	DESCRIPTION    
		"Number of NCP terminate request retransmissions."
	::= { ecpppIPXStatsEntry 7 }
	
ecpppIPXStatsNcpReqRetrans       OBJECT-TYPE                    
	SYNTAX  Counter
	ACCESS  read-only 
	STATUS  mandatory
	DESCRIPTION    
		"Number of NCP configure request retransmissions."
	::= { ecpppIPXStatsEntry 8 }
	

-- ******************************************
-- *       ecpppATInfoTable                 *
-- ******************************************

ecpppATInfoTable   OBJECT-TYPE
	SYNTAX    SEQUENCE OF EcpppATInfoEntry
	ACCESS    not-accessible
	STATUS    mandatory
	DESCRIPTION
		  "A table for PPP AT Protocol Info"
	::= { ecppp 7 }

ecpppATInfoEntry   OBJECT-TYPE
	SYNTAX    EcpppATInfoEntry
	ACCESS    not-accessible
	STATUS    mandatory
	DESCRIPTION
		  "Management information about a particular PPP
		   Link."
	INDEX     { ecpppATInfoPortRef }
	::= { ecpppATInfoTable 1 }

EcpppATInfoEntry ::= SEQUENCE {
	ecpppATInfoPortRef              
		PortRef,        
	ecpppATInfoNcpState
		NcpState,
	ecpppATInfoRoutingProtocol              
		INTEGER,        
	ecpppATInfoComprConfig          
		INTEGER,        
	ecpppATInfoServerClass
		INTEGER,
	ecpppATInfoATAddr       
		INTEGER,        
	ecpppATInfoATNode               
		INTEGER,        
	ecpppATInfoATcpMaxTerm          
		INTEGER,        
	ecpppATInfoATcpMaxConfig        
		INTEGER,        
	ecpppATInfoATcpMaxFailure               
		INTEGER,        
	ecpppATInfoSrvName              
		DisplayString,
	ecpppATInfoZoneName             
		DisplayString
}

ecpppATInfoPortRef            OBJECT-TYPE               
	SYNTAX  PortRef
	ACCESS  read-only 
	STATUS  mandatory
	DESCRIPTION    
		"The id of the port on which the parameters in the table are
		 configured."
	::= { ecpppATInfoEntry 1 }
	
ecpppATInfoNcpState            OBJECT-TYPE              
	SYNTAX  NcpState
	ACCESS  read-only 
	STATUS  mandatory
	DESCRIPTION    
		"State during NCP phase"
	::= { ecpppATInfoEntry 2 }
	
ecpppATInfoRoutingProtocol    OBJECT-TYPE               
	SYNTAX  INTEGER {
		none (1),
		rtmp (2),
		aurp (3),
		abgp (4)
	}
	ACCESS  read-only 
	STATUS  mandatory
	DESCRIPTION    
		"Type of routing protocol"
	::= { ecpppATInfoEntry 3 }
	
ecpppATInfoComprConfig           OBJECT-TYPE            
	SYNTAX  INTEGER {
		no-compression (1),
		standard(2),
		prorietary (3)
	}
	ACCESS  read-only 
	STATUS  mandatory
	DESCRIPTION    
		"Compression configuration "
	::= { ecpppATInfoEntry 4 }
	
ecpppATInfoServerClass                OBJECT-TYPE       
	SYNTAX  INTEGER
	ACCESS  read-only 
	STATUS  mandatory
	DESCRIPTION    
		"Class of the remote server "
	::= { ecpppATInfoEntry 5 }
	
ecpppATInfoATAddr             OBJECT-TYPE       
	SYNTAX  INTEGER
	ACCESS  read-only 
	STATUS  mandatory
	DESCRIPTION    
		"Local address"
	::= { ecpppATInfoEntry 6 }
	
ecpppATInfoATNode             OBJECT-TYPE               
	SYNTAX  INTEGER
	ACCESS  read-only 
	STATUS  mandatory
	DESCRIPTION    
		"Local node id"
	::= { ecpppATInfoEntry 7 }
	
ecpppATInfoATcpMaxTerm        OBJECT-TYPE               
	SYNTAX  INTEGER
	ACCESS  read-only 
	STATUS  mandatory
	DESCRIPTION    
		"Max. terminate retransmission"
	::= { ecpppATInfoEntry 8 }
	
ecpppATInfoATcpMaxConfig         OBJECT-TYPE            
	SYNTAX  INTEGER
	ACCESS  read-only 
	STATUS  mandatory
	DESCRIPTION    
		"Max. configure retransmission"
	::= { ecpppATInfoEntry 9 }
	
ecpppATInfoATcpMaxFailure     OBJECT-TYPE               
	SYNTAX  INTEGER
	ACCESS  read-only 
	STATUS  mandatory
	DESCRIPTION    
		"Max config_nak retransmission"
	::= { ecpppATInfoEntry 10 }
	
ecpppATInfoSrvName        OBJECT-TYPE           
	SYNTAX  DisplayString (SIZE (0..32))
	ACCESS  read-only 
	STATUS  mandatory
	DESCRIPTION    
		"Length of the server name "
	::= { ecpppATInfoEntry 11 }
	
ecpppATInfoZoneName         OBJECT-TYPE         
	SYNTAX  DisplayString (SIZE (0..32))
	ACCESS  read-only 
	STATUS  mandatory
	DESCRIPTION    
		"AT ASCII name of the zone "
	::= { ecpppATInfoEntry 12 }
	

-- ******************************************
-- *       ecpppATStatsTable                *
-- ******************************************

ecpppATStatsTable   OBJECT-TYPE
	SYNTAX    SEQUENCE OF EcpppATStatsEntry
	ACCESS    not-accessible
	STATUS    mandatory
	DESCRIPTION
		  "A table for PPP IP Protocol Stats"
	::= { ecppp 8 }

ecpppATStatsEntry   OBJECT-TYPE
	SYNTAX    EcpppATStatsEntry
	ACCESS    not-accessible
	STATUS    mandatory
	DESCRIPTION
		  "Management information about a particular PPP
		   Link."
	INDEX     { ecpppATStatsPortRef }
	::= { ecpppATStatsTable 1 }

EcpppATStatsEntry ::= SEQUENCE {
	ecpppATStatsPortRef             
		PortRef,        
	ecpppATStatsDatagramsTx         
		Counter,        
	ecpppATStatsDatagramsRx         
		Counter,        
	ecpppATStatsCharTx              
		Counter,        
	ecpppATStatsCharRx              
		Counter,        
	ecpppATStatsNcpRestartTimeout           
		Counter,        
	ecpppATStatsNcpTermRetrans              
		Counter,        
	ecpppATStatsNcpReqRetrans               
		Counter
}       

ecpppATStatsPortRef             OBJECT-TYPE                     
	SYNTAX  PortRef
	ACCESS  read-only 
	STATUS  mandatory
	DESCRIPTION    
		"The id of the port on which the parameters in the table are
		 configured"
	::= { ecpppATStatsEntry 1 }
	
ecpppATStatsDatagramsTx         OBJECT-TYPE             
	SYNTAX  Counter
	ACCESS  read-only 
	STATUS  mandatory
	DESCRIPTION    
		"Number of datagrams sent "
	::= { ecpppATStatsEntry 2 }
	
ecpppATStatsDatagramsRx         OBJECT-TYPE             
	SYNTAX  Counter
	ACCESS  read-only 
	STATUS  mandatory
	DESCRIPTION    
		"Number of datagrams received "
	::= { ecpppATStatsEntry 3 }
	
ecpppATStatsCharTx              OBJECT-TYPE             
	SYNTAX  Counter
	ACCESS  read-only 
	STATUS  mandatory
	DESCRIPTION    
		"Number of characters sent"
	::= { ecpppATStatsEntry 4 }
	
ecpppATStatsCharRx              OBJECT-TYPE             
	SYNTAX  Counter
	ACCESS  read-only 
	STATUS  mandatory
	DESCRIPTION    
		"Number of characters sent"
	::= { ecpppATStatsEntry 5 }
	
ecpppATStatsNcpRestartTimeout   OBJECT-TYPE             
	SYNTAX  Counter
	ACCESS  read-only 
	STATUS  mandatory
	DESCRIPTION    
		"Number of NCP restart timer time-out"
	::= { ecpppATStatsEntry 6 }
	
ecpppATStatsNcpTermRetrans      OBJECT-TYPE             
	SYNTAX  Counter
	ACCESS  read-only 
	STATUS  mandatory
	DESCRIPTION    
		"Number of NCP terminate request retransmissions."
	::= { ecpppATStatsEntry 7 }
	
ecpppATStatsNcpReqRetrans       OBJECT-TYPE             
	SYNTAX  Counter
	ACCESS  read-only 
	STATUS  mandatory
	DESCRIPTION    
		"Number of NCP configure request retransmissions."
	::= { ecpppATStatsEntry 8 }
	
END
