--
-- GGSN MIB
--
-- Copyright (c) 2001-2003, Ericsson-Juniper Networks  MobileIP AB.
-- All rights reserved.
--
-- The contents of this document are subject to change
-- without notice.
--
GGSN-MIB DEFINITIONS ::= BEGIN
IMPORTS
    MODULE-IDENTITY, OBJECT-TYPE, NOTIFICATION-TYPE,
    Counter32, enterprises, Integer32, Unsigned32, Gauge32, Counter64, IpAddress
        FROM SNMPv2-SMI
    TEXTUAL-CONVENTION, DisplayString, TimeStamp
        FROM SNMPv2-TC
    MODULE-COMPLIANCE, OBJECT-GROUP, NOTIFICATION-GROUP
        FROM SNMPv2-CONF;

ggsnMIB MODULE-IDENTITY
    LAST-UPDATED "200407221546Z" -- date is 22 July 2004
    ORGANIZATION "Juniper Networks, Inc."
    CONTACT-INFO
            "        Juniper Technical Assistance Center
                     Juniper Networks, Inc.
                     1194 N. Mathilda Avenue
                     Sunnyvale, CA 94089
                     E-mail: support@juniper.net"

    DESCRIPTION
        "The MIB module for GPRS Gateway Support Node
         Application"
    ::= { ejnxMibs 1 }


--
-- Until we have the mechanism in place to "include" the
-- definition of juniperMIB, we replicate it here.
--

ejnmobileipABmib     OBJECT IDENTIFIER ::= { enterprises 10923 }
ejnxMibs             OBJECT IDENTIFIER ::= { ejnmobileipABmib 1 }


--
-- ggsnMIB tree structure
--

ggsnMibs       OBJECT IDENTIFIER ::= { ggsnMIB 1 }
ggsnTraps      OBJECT IDENTIFIER ::= { ggsnMIB 2 }
ggsnMIBObjects  OBJECT IDENTIFIER ::= { ggsnMibs 1 }


--
-- Top-level groups in ggsnMibs. For RADIUS group, standard
-- MIBs defined in RFC2618 and RFC2620 are supported.
--

ggsnGeneralInfo  OBJECT IDENTIFIER ::= { ggsnMIBObjects 1 }
ggsnGtpcInfo     OBJECT IDENTIFIER ::= { ggsnMIBObjects 2 }
ggsnChargingInfo OBJECT IDENTIFIER ::= { ggsnMIBObjects 3 }
ggsnDhcpInfo     OBJECT IDENTIFIER ::= { ggsnMIBObjects 4 }
ggsnAlarmInfo    OBJECT IDENTIFIER ::= { ggsnMIBObjects 5 }
ggsnGtpuInfo     OBJECT IDENTIFIER ::= { ggsnMIBObjects 6 }
ggsnFbcInfo	 OBJECT IDENTIFIER ::= { ggsnMIBObjects 7 }
ggsnMbmsInfo	 OBJECT IDENTIFIER ::= { ggsnMIBObjects 8 }
ggsnGtptInfo     OBJECT IDENTIFIER ::= { ggsnMIBObjects 9 }
ggsnRadiusInfo   OBJECT IDENTIFIER ::= { ggsnMIBObjects 10 }

--
--PGW Shared-ip-pool statistics
--
pgwSharedIpPoolStatsTable       OBJECT-TYPE
   SYNTAX        SEQUENCE OF SharedIpPoolStats
   MAX-ACCESS    not-accessible
   STATUS        current
   DESCRIPTION
         "A table listing the statistics for all shared IP pools which
          are served by the PGW."
   ::= { ggsnMIBObjects  11 }

pgwSharedIpPoolStatsEntry OBJECT-TYPE
   SYNTAX        SharedIpPoolStats
   MAX-ACCESS    not-accessible
   STATUS        current
   DESCRIPTION
         "A conceptual row listing the statistics for each
          shared IP pool which is served by the PGW."
   INDEX         { pgwSharedIpPoolIndex }
   ::= { pgwSharedIpPoolStatsTable 1 }

SharedIpPoolStats ::= SEQUENCE {
   pgwSharedIpPoolIndex                      Integer32,
   pgwSharedIpPoolName                       DisplayString,
   pgwAvailableAddressesInSharedIpPool       Gauge32,
   pgwAddressesInQuarantineInSharedIpPool    Gauge32
}

pgwSharedIpPoolIndex OBJECT-TYPE
   SYNTAX        Integer32 (1..2147483647)
   MAX-ACCESS    not-accessible
   STATUS        current
   DESCRIPTION
         "A number representing each shared IP pool whose statistics
          are generated."
   ::= { pgwSharedIpPoolStatsEntry 1 }

pgwSharedIpPoolName OBJECT-TYPE
   SYNTAX        DisplayString
   MAX-ACCESS    read-only
   STATUS        current
   DESCRIPTION
         "The identifier of a shared IP pool."
   ::= { pgwSharedIpPoolStatsEntry 2 }

pgwAvailableAddressesInSharedIpPool  OBJECT-TYPE
   SYNTAX        Gauge32
   MAX-ACCESS    read-only
   STATUS        current
   DESCRIPTION
         "The number of available IP addresses
          in a shared IP pool."
   ::= { pgwSharedIpPoolStatsEntry 3 }

pgwAddressesInQuarantineInSharedIpPool  OBJECT-TYPE
   SYNTAX        Gauge32
   MAX-ACCESS    read-only
   STATUS        current
   DESCRIPTION
         "The number of IP addresses that are in quarantine in a shared IP pool"
   ::= { pgwSharedIpPoolStatsEntry 4 }


--
-- GGSN service-based charging (FBC) statistics
--

ggsnFbcStats			OBJECT IDENTIFIER ::= { ggsnFbcInfo 1 }
ggsnFbcAuthorizationStats	OBJECT IDENTIFIER ::= { ggsnFbcInfo 2 }

ggsnFbcInitiatedDeactivation		OBJECT-TYPE
    SYNTAX				Counter64
    MAX-ACCESS				read-only
    STATUS				current
    DESCRIPTION
	"The number of bearer deactivations initiated by the SACC functionality."
    ::= { ggsnFbcStats 1 }

ggsnFbcApplicationTransactionPps	OBJECT-TYPE
    SYNTAX				Counter64
    MAX-ACCESS				read-only
    STATUS				deprecated
    DESCRIPTION
	"Number of transactions toward pre-paid server."
    ::= { ggsnFbcStats 2 }

ggsnFbcApplicationTransactionPrs	OBJECT-TYPE
    SYNTAX				Counter64
    MAX-ACCESS				read-only
    STATUS				deprecated
    DESCRIPTION
	"Number of transactions toward policy/rate server."
    ::= { ggsnFbcStats 3 }


--
-- GGSN system group
--

ggsnVersion OBJECT-TYPE
   SYNTAX        DisplayString (SIZE (0..255))
   MAX-ACCESS    read-only
   STATUS        current
   DESCRIPTION
         "The revision of this application, blank if unknown
          or unavailable."
   ::= { ggsnGeneralInfo 1 }

ggsnInstalled OBJECT-TYPE
   SYNTAX        TimeStamp
   MAX-ACCESS    read-only
   STATUS        current
   DESCRIPTION
         "The value of sysUpTime when the application was
          last restarted. Zero if unknown."
   ::= { ggsnGeneralInfo 2 }


--
-- GGSN Global statistics
--

ggsnGlobalStats OBJECT IDENTIFIER ::= { ggsnGeneralInfo 3 }

ggsnStatReportTime OBJECT-TYPE
   SYNTAX        TimeStamp
   MAX-ACCESS    read-only
   STATUS        current
   DESCRIPTION
         "The value of sysUpTime when the global statistics report is
          generated."
   ::= { ggsnGlobalStats 1 }

ggsnNbrOfActivePdpContexts OBJECT-TYPE
   SYNTAX        Gauge32
   MAX-ACCESS    read-only
   STATUS        current
   DESCRIPTION
         "The number of active PDP contexts on this GGSN.
         
          Incremented when a PDP context is activated and a
          GTP response has been sent to the SGSN. Decremented
          when a PDP context is deactivated."
   ::= { ggsnGlobalStats 2 }

ggsnNbrOfSubscribers OBJECT-TYPE
   SYNTAX        Gauge32
   MAX-ACCESS    read-only
   STATUS        current
   DESCRIPTION
         "The number of subscribers, uniquely identified by IMSI,
          currently serviced by this GGSN.
          Incremented on transmission of a PDP context response with
          request accepted for an IMSI (which previously did not have
          a PDP context active). Decremented when the last PDP context
          for that IMSI has been deleted.
          
          Note: This counter cannot be retrieved by CLI."
   ::= { ggsnGlobalStats 20 }

ggsnNbrOfSubscribersMean OBJECT-TYPE
   SYNTAX        Gauge32
   MAX-ACCESS    read-only
   STATUS        current
   DESCRIPTION
         "The mean number of subscribers serviced by this GGSN.
          Incremented on transmission of a PDP context response with
          request accepted for an IMSI (which previously did not have a
          PDP context active). Decremented when the last PDP context for
          that IMSI has been deleted.
          The mean number of subscribers is calculated over five samples
          taken over a 15 minute period.
          
          Note: This counter cannot be retrieved by CLI."
   ::= { ggsnGlobalStats 21 }

ggsnNbrOfTftFilters OBJECT-TYPE
   SYNTAX        Gauge32
   MAX-ACCESS    read-only
   STATUS        current
   DESCRIPTION
         "The number of Traffic Flow Template filters on this GGSN."
   ::= { ggsnGlobalStats 22 }

ggsnControlLoad OBJECT-TYPE
   SYNTAX        Gauge32
   MAX-ACCESS    read-only
   STATUS        current
   DESCRIPTION
         "Weighted PDP context load in control."
   ::= { ggsnGlobalStats 25 }

ggsnPayloadLoad OBJECT-TYPE
   SYNTAX        Gauge32
   MAX-ACCESS    read-only
   STATUS        current
   DESCRIPTION
         "This gauge keeps track of the weighted load on the node for the
          payload part. The gauge is used for the new load balancing scheme.
          
          Note: This counter cannot be retrieved by CLI."
   ::= { ggsnGlobalStats 26 }

ggsnNbrOfActivePdpContextsIpv6 OBJECT-TYPE
   SYNTAX        Gauge32
   MAX-ACCESS    read-only
   STATUS        current
   DESCRIPTION
         "The number of active IPv6 PDP contexts on this GGSN."
   ::= { ggsnGlobalStats 27 }

ggsnNeighborSolicitationRcv  OBJECT-TYPE
   SYNTAX        Counter64
   MAX-ACCESS    read-only
   STATUS        current
   DESCRIPTION
         "The number of neighbor solicitation requests
          received by GGSN.
          
          Note: This counter cannot be retrieved by CLI."
   ::= { ggsnGlobalStats 28 }

ggsnNeighborSolicitationRsp  OBJECT-TYPE
   SYNTAX        Counter64
   MAX-ACCESS    read-only
   STATUS        current
   DESCRIPTION
         "The number of neighbor solicitation responses
          from GGSN.
          
          Note: This counter cannot be retrieved by CLI."
   ::= { ggsnGlobalStats 29 }

ggsnRouterSolicitationRcv  OBJECT-TYPE
   SYNTAX        Counter64
   MAX-ACCESS    read-only
   STATUS        current
   DESCRIPTION
         "The number of router solicitation requests received by GGSN.
          
          Note: This counter cannot be retrieved by CLI."
   ::= { ggsnGlobalStats 30 }

ggsnRouterSolicitationRsp  OBJECT-TYPE
   SYNTAX        Counter64
   MAX-ACCESS    read-only
   STATUS        current
   DESCRIPTION
         "The number of router solicitation responses from GGSN.
          
          Note: This counter cannot be retrieved by CLI."
   ::= { ggsnGlobalStats 31 }

ggsnL2tpActiveTunnels OBJECT-TYPE
   SYNTAX	 Gauge32
   MAX-ACCESS	 read-only
   STATUS	 current
   DESCRIPTION
	 "The number of currently active L2TP tunnels."
   ::= { ggsnGlobalStats 32 }

ggsnL2tpMaxActiveTunnels OBJECT-TYPE
   SYNTAX	 Gauge32
   MAX-ACCESS	 read-only
   STATUS	 current
   DESCRIPTION
	 "The max number of active L2TP tunnels since last restart."
   ::= { ggsnGlobalStats 33 }

ggsnL2tpActiveSessions OBJECT-TYPE
   SYNTAX	 Gauge32
   MAX-ACCESS	 read-only
   STATUS	 current
   DESCRIPTION
	 "The number of currently active L2TP sessions."
   ::= { ggsnGlobalStats 34 }

ggsnL2tpMaxActiveSessions OBJECT-TYPE
   SYNTAX	 Gauge32
   MAX-ACCESS	 read-only
   STATUS	 current
   DESCRIPTION
	 "The max number of active L2TP sessions since last restart."
   ::= { ggsnGlobalStats 35 }

ggsnChgEncodedCdrs OBJECT-TYPE
   SYNTAX	 Counter64
   MAX-ACCESS	 read-only
   STATUS	 current
   DESCRIPTION
	 "The number of successfully encoded CDRs on this GGSN."
   ::= { ggsnGlobalStats 36 }

ggsnChgFailedEncodedCdrs OBJECT-TYPE
   SYNTAX	 Counter64
   MAX-ACCESS	 read-only
   STATUS	 current
   DESCRIPTION
	 "The number of unsuccessfully encoded CDRs on this GGSN."
   ::= { ggsnGlobalStats 37 }

ggsnChgGeneratedFtpCdrs OBJECT-TYPE
   SYNTAX	 Counter64
   MAX-ACCESS	 read-only
   STATUS	 current
   DESCRIPTION
	 "The number of CDRs generated for FTP."
   ::= { ggsnGlobalStats 38 }

ggsnChgGeneratedGtppCdrs OBJECT-TYPE
   SYNTAX	 Counter64
   MAX-ACCESS	 read-only
   STATUS	 current
   DESCRIPTION
	 "The number of CDRs generated for GTP prime."
   ::= { ggsnGlobalStats 39 }

ggsnChgGtppLogCdrs OBJECT-TYPE
   SYNTAX	 Counter64
   MAX-ACCESS	 read-only
   STATUS	 current
   DESCRIPTION
	 "The number of GTP prime CDRs stored in the charging log."
   ::= { ggsnGlobalStats 40 }

ggsnChgGtppAttemptedCdrsSend OBJECT-TYPE
   SYNTAX	 Counter64
   MAX-ACCESS	 read-only
   STATUS	 current
   DESCRIPTION
	 "The number sending attempts of CDRs generated for GTP prime."
   ::= { ggsnGlobalStats 41 }

ggsnChgGtppCdrsSendFailure OBJECT-TYPE
   SYNTAX	 Counter64
   MAX-ACCESS	 read-only
   STATUS	 current
   DESCRIPTION
	 "The number sending failures of CDRs generated for GTP prime."
   ::= { ggsnGlobalStats 42 }

ggsnNbActivePdpPerTrafficClassConversational OBJECT-TYPE
   SYNTAX	 Gauge32
   MAX-ACCESS	 read-only
   STATUS	 current
   DESCRIPTION
	 "The number of active PDP contexts per Traffic Class, conversational."
   ::= { ggsnGlobalStats 43 }

ggsnNbActivePdpPerTrafficClassStreaming   OBJECT-TYPE
   SYNTAX	 Gauge32
   MAX-ACCESS	 read-only
   STATUS	 current
   DESCRIPTION
	 "The number of active PDP contexts per Traffic Class, streaming."
   ::= { ggsnGlobalStats 44 }

ggsnNbActivePdpPerTrafficClassInteractive   OBJECT-TYPE
   SYNTAX	 Gauge32
   MAX-ACCESS	 read-only
   STATUS	 current
   DESCRIPTION
	 "The number of active PDP contexts per Traffic Class, interactive."
   ::= { ggsnGlobalStats 45 }

ggsnNbActivePdpPerTrafficClassBackground   OBJECT-TYPE
   SYNTAX	 Gauge32
   MAX-ACCESS	 read-only
   STATUS	 current
   DESCRIPTION
	 "The number of active PDP contexts per Traffic Class, background."
   ::= { ggsnGlobalStats 46 }

ggsnRadiusAuthenticationFailure   OBJECT-TYPE
   SYNTAX	 Counter64
   MAX-ACCESS	 read-only
   STATUS	 current
   DESCRIPTION
	 "The number of failed RADIUS Authentication procedures."
   ::= { ggsnGlobalStats 47 }

ggsnRadiusAccountingFailure   OBJECT-TYPE
   SYNTAX	 Counter64
   MAX-ACCESS	 read-only
   STATUS	 current
   DESCRIPTION
	 "The number of failed RADIUS Accounting procedures."
   ::= { ggsnGlobalStats 48 }

ggsnNbrOfActivePdpContextsWlan   OBJECT-TYPE
   SYNTAX	 Gauge32
   MAX-ACCESS	 read-only
   STATUS	 current
   DESCRIPTION
     "The number of active WLAN PDP contexts on this GGSN.
      
      Note: This counter cannot be retrieved by CLI."
   ::= { ggsnGlobalStats 49 }

ggsn3gdtActiveContexts   OBJECT-TYPE
   SYNTAX     Gauge32
   MAX-ACCESS     read-only
   STATUS     current
   DESCRIPTION
     "The number of active 3GDT PDP contexts on this GGSN."
   ::= { ggsnGlobalStats 50 }

ggsn3gdtTotalCompletedEstablishment   OBJECT-TYPE
   SYNTAX     Gauge32
   MAX-ACCESS     read-only
   STATUS     deprecated
   DESCRIPTION
     "The number of total completed 3GDT PDP context establishments on this GGSN."
   ::= { ggsnGlobalStats 51 }

ggsn3gdtTotalAttemptedEstablishment   OBJECT-TYPE
   SYNTAX     Gauge32
   MAX-ACCESS     read-only
   STATUS     deprecated
   DESCRIPTION
     "The number of total attempted 3GDT PDP context establishments on this GGSN."
   ::= { ggsnGlobalStats 52 }

ggsn3gdtErrorHandling   OBJECT-TYPE
   SYNTAX     Gauge32
   MAX-ACCESS     read-only
   STATUS     deprecated
   DESCRIPTION
     "The number error indications from RNC."
   ::= { ggsnGlobalStats 53 }

gn3gdtTotalCompletedEstablishment   OBJECT-TYPE
   SYNTAX     Counter32
   MAX-ACCESS     read-only
   STATUS     current
   DESCRIPTION
     "The number of total completed 3GDT PDP context establishments on this GGSN."
   ::= { ggsnGlobalStats 54 }

gn3gdtTotalAttemptedEstablishment   OBJECT-TYPE
   SYNTAX     Counter32
   MAX-ACCESS     read-only
   STATUS     current
   DESCRIPTION
     "The number of total attempted 3GDT PDP context establishments on this GGSN."
   ::= { ggsnGlobalStats 55 }

gn3gdtErrorHandling   OBJECT-TYPE
   SYNTAX     Counter32
   MAX-ACCESS     read-only
   STATUS     current
   DESCRIPTION
     "The number error indications from RNC."
   ::= { ggsnGlobalStats 56 }

ggsnNbrOfActivePdpContextsIpv4v6 OBJECT-TYPE
   SYNTAX        Gauge32
   MAX-ACCESS    read-only
   STATUS        current
   DESCRIPTION
         "The number of active IPv4v6 PDP contexts on this GGSN."
   ::= { ggsnGlobalStats 57 }


ggsnPdpContextsStatsAttempted
   OBJECT IDENTIFIER ::= { ggsnGlobalStats 3 }
ggsnPdpContextsStatsCompleted
   OBJECT IDENTIFIER ::= { ggsnGlobalStats 4 }
ggsnPdpContextsStatsFailed
   OBJECT IDENTIFIER ::= { ggsnGlobalStats 5 }
ggsnGtpStats
   OBJECT IDENTIFIER ::= { ggsnGlobalStats 6 }
ggsnGtpErrorStats
   OBJECT IDENTIFIER ::= { ggsnGlobalStats 7 }
ggsnGtpPrStats
   OBJECT IDENTIFIER ::= { ggsnGlobalStats 8 }
ggsnGtpPrErrorStats
   OBJECT IDENTIFIER ::= { ggsnGlobalStats 9 }

ggsnAttemptedActivation OBJECT-TYPE
   SYNTAX        Counter64
   MAX-ACCESS    read-only
   STATUS        current
   DESCRIPTION
         "The number of PDP context activation procedures
          initiated by the MS on this GGSN.
          
          Incremented each time a Create PDP Context Request
          that is not silently discarded is received by the GGSN.
          This means the SNMP counter incremented each time a
          Create PDP Context Response is sent back to the SGSN with
          cause value Request Accepted or Request Rejected.
          
          Note: This counter cannot be retrieved by CLI."
   ::= { ggsnPdpContextsStatsAttempted 1 }

ggsnAttemptedDeactivation OBJECT-TYPE
   SYNTAX        Counter64
   MAX-ACCESS    read-only
   STATUS        current
   DESCRIPTION
         "The number of PDP context deactivation procedures
          initiated by the MS on this GGSN.
          
          Incremented each time a Delete PDP Context Request
          is received at this GGSN.
          
          Note: This counter cannot be retrieved by CLI."
   ::= { ggsnPdpContextsStatsAttempted 2 }

ggsnAttemptedSelfDeactivation OBJECT-TYPE
   SYNTAX        Counter64
   MAX-ACCESS    read-only
   STATUS        current
   DESCRIPTION
         "The number of PDP context deactivation procedures
          initiated by this GGSN.
          
          Incremented each time this GGSN attempts to delete a context.
          Increases for all types of internal deletes.
          
          Note: This counter cannot be retrieved by CLI."
   ::= { ggsnPdpContextsStatsAttempted 3 }

ggsnAttemptedUpdate OBJECT-TYPE
   SYNTAX        Counter64
   MAX-ACCESS    read-only
   STATUS        current
   DESCRIPTION
         "The number of PDP context updates attempted on
          this GGSN.
          
          Incremented each time an Update PDP Context Request
          is received at this GGSN.
          
          Note: This counter cannot be retrieved by CLI."
   ::= { ggsnPdpContextsStatsAttempted 4 }

ggsnAttemptedTimeDeactivation OBJECT-TYPE
   SYNTAX        Counter64
   MAX-ACCESS    read-only
   STATUS        deprecated
   DESCRIPTION
         "The number of PDP context deactivation procedures
          initiated by this GGSN due to the idle supervision
          function."
   ::= { ggsnPdpContextsStatsAttempted 5 }

ggsnAttemptedManualDeactivation OBJECT-TYPE
   SYNTAX	 Counter64
   MAX-ACCESS	 read-only
   STATUS	 current
   DESCRIPTION
         "The number of PDP context deactivation procedures
          initiated by this GGSN due to manual user command.
          
          Note: This counter cannot be retrieved by CLI."
   ::= { ggsnPdpContextsStatsAttempted 6 }

ggsnAttemptedSecondaryActivation OBJECT-TYPE
   SYNTAX	 Counter64
   MAX-ACCESS	 read-only
   STATUS	 current
   DESCRIPTION
         "The number of secondary PDP context activation
          procedures initiated by the MS on this GGSN.
          
          All GPRS session management statistics except
          ggsnAttemptedSecondaryActivation, ggsnCompletedSecondaryActivation,
          ggsnAttemptedSecondaryActivationIpv6, and ggsnCompletedSecondaryActivationIpv6
          will accumulate all pdp contexts, that is both secondary and
          primary. 
          
          Note: This counter cannot be retrieved by CLI."
   ::= { ggsnPdpContextsStatsAttempted 7 }

ggsnAttemptedActivationIpv6 OBJECT-TYPE
   SYNTAX        Counter64
   MAX-ACCESS    read-only
   STATUS        current
   DESCRIPTION
         "The number of IPv6 PDP context activation procedures
          initiated by the MS on this GGSN.
          
          Note: This counter cannot be retrieved by CLI."
   ::= { ggsnPdpContextsStatsAttempted 8 }

ggsnAttemptedSecondaryActivationIpv6 OBJECT-TYPE
   SYNTAX        Counter64
   MAX-ACCESS    read-only
   STATUS        current
   DESCRIPTION
         "The number of secondary IPv6 PDP context activation procedures
          initiated by the MS on this GGSN.
          
          All GPRS session management statistics except
          ggsnAttemptedSecondaryActivation, ggsnCompletedSecondaryActivation,
          ggsnAttemptedSecondaryActivationIpv6, and
          ggsnCompletedSecondaryActivationIpv6 will accumulate all 
          pdp contexts, that is both secondary and primary.
          
          Note: This counter cannot be retrieved by CLI."
   ::= { ggsnPdpContextsStatsAttempted 9 }

ggsnAttemptedActivationWlan OBJECT-TYPE
   SYNTAX        Counter64
   MAX-ACCESS    read-only
   STATUS        current
   DESCRIPTION
         "The number of WLAN PDP context activation procedures
          initiated by the MS on this GGSN.
          
          Note: This counter cannot be retrieved by CLI."
   ::= { ggsnPdpContextsStatsAttempted 10 }

ggsnAttemptedActivationConversational OBJECT-TYPE
   SYNTAX        Counter64
   MAX-ACCESS    read-only
   STATUS        current
   DESCRIPTION
         "The total number of attempted primary and secondary PDP context activation procedures 
          with traffic class conversational on this GGSN.

          Note: This counter cannot be retrieved by CLI."
   ::= { ggsnPdpContextsStatsAttempted 11 }

ggsnAttemptedActivationStreaming OBJECT-TYPE
   SYNTAX        Counter64
   MAX-ACCESS    read-only
   STATUS        current
   DESCRIPTION
         "The total number of attempted primary and secondary PDP context activation procedures 
          with traffic class streaming on this GGSN.

          Note: This counter cannot be retrieved by CLI."
   ::= { ggsnPdpContextsStatsAttempted 12 }

ggsnAttemptedActivationInteractive OBJECT-TYPE
   SYNTAX        Counter64
   MAX-ACCESS    read-only
   STATUS        current
   DESCRIPTION
         "The total number of attempted primary and secondary PDP context activation procedures 
          with traffic class interactive on this GGSN.

          Note: This counter cannot be retrieved by CLI."
   ::= { ggsnPdpContextsStatsAttempted 13 }

ggsnAttemptedActivationBackground OBJECT-TYPE
   SYNTAX        Counter64
   MAX-ACCESS    read-only
   STATUS        current
   DESCRIPTION
         "The total number of attempted primary and secondary PDP context activation procedures 
          with traffic class background on this GGSN.

          Note: This counter cannot be retrieved by CLI."
   ::= { ggsnPdpContextsStatsAttempted 14 }

ggsnAttemptedActivationDiscarded OBJECT-TYPE
   SYNTAX        Counter64
   MAX-ACCESS    read-only
   STATUS        current
   DESCRIPTION
         "The total number of attempted primary and secondary PDP context activations
          that are discarded on this GGSN.

          Note: This counter cannot be retrieved by CLI."
   ::= { ggsnPdpContextsStatsAttempted 15 }

ggsnAttemptedActivationIpv4v6 OBJECT-TYPE
   SYNTAX        Counter64
   MAX-ACCESS    read-only
   STATUS        current
   DESCRIPTION
         "The number of IPv4v6 PDP context activation procedures
          initiated by the MS on this GGSN.
          
          Note: This counter cannot be retrieved by CLI."
   ::= { ggsnPdpContextsStatsAttempted 16 }

ggsnCompletedActivation OBJECT-TYPE
   SYNTAX        Counter64
   MAX-ACCESS    read-only
   STATUS        current
   DESCRIPTION
         "The number of successfully completed
          PDP context activation procedures initiated by an MS.
          
          Incremented each time a Create PDP Context Response is sent back
          to an SGSN with cause value Request Accepted."
   ::= { ggsnPdpContextsStatsCompleted 1 }

ggsnCompletedDeactivation OBJECT-TYPE
   SYNTAX        Counter64
   MAX-ACCESS    read-only
   STATUS        current
   DESCRIPTION
         "The number of successfully completed
          PDP context deactivation procedures initiated by an MS. 
          
          Note: This counter can not be retrieved by CLI. "
   ::= { ggsnPdpContextsStatsCompleted 2 }

ggsnCompletedSelfDeactivation OBJECT-TYPE
   SYNTAX        Counter64
   MAX-ACCESS    read-only
   STATUS        current
   DESCRIPTION
         "The number of successfully completed
          PDP context deactivation procedures initiated by the GGSN.
          
          Note: This counter can not be retrieved by CLI."
   ::= { ggsnPdpContextsStatsCompleted 3 }

ggsnCompletedUpdate OBJECT-TYPE
   SYNTAX        Counter64
   MAX-ACCESS    read-only
   STATUS        current
   DESCRIPTION
         "The number of successfully completed
          PDP context update procedures initiated by an MS.
          
          Incremented each time an Update PDP Context Response is sent back
          to an SGSN with cause value Request Accepted."
   ::= { ggsnPdpContextsStatsCompleted 4 }

ggsnIdleTimeoutDeactivation OBJECT-TYPE
   SYNTAX	 Counter64
   MAX-ACCESS	 read-only
   STATUS	 current
   DESCRIPTION
         "The number of successfully completed
          PDP context deactivation procedures initiated by the GGSN 
          due to the idle supervision function.
          
          Note: The PDP context is supervised for the time it has been idle,
          without actual payload." 
   ::= { ggsnPdpContextsStatsCompleted 5 }

ggsnCompletedManualDeactivation OBJECT-TYPE
   SYNTAX	 Counter64
   MAX-ACCESS	 read-only
   STATUS	 current
   DESCRIPTION
         "The number of successfully completed
          PDP context deactivation procedures initiated by the GGSN 
          due to manual user command."
   ::= { ggsnPdpContextsStatsCompleted 6 }

ggsnCompletedSecondaryActivation OBJECT-TYPE
   SYNTAX	 Counter64
   MAX-ACCESS	 read-only
   STATUS	 current
   DESCRIPTION
         "The number of successfully completed
          secondary PDP context activation procedures initiated by an MS.
          
          Note: All GPRS session management statistics except
          ggsnAttemptedSecondaryActivation, ggsnCompletedSecondaryActivation,
          ggsnAttemptedSecondaryActivationIpv6, and
          ggsnCompletedSecondaryActivationIpv6 count all PDP
          contexts, both secondary and primary." 
   ::= { ggsnPdpContextsStatsCompleted 7 }

ggsnSessionTimeoutDeactivation OBJECT-TYPE
   SYNTAX	 Counter64
   MAX-ACCESS	 read-only
   STATUS	 current
   DESCRIPTION
     "The number of successfully completed
      PDP context deactivation procedures initiated by the GGSN
      due to the duration supervision function.
      
      Note: The PDP context is supervised for the time it has been active,
      irrespective of the actual payload."
   ::= { ggsnPdpContextsStatsCompleted 8 }

ggsnCompletedActivationIpv6 OBJECT-TYPE
   SYNTAX        Counter64
   MAX-ACCESS    read-only
   STATUS        current
   DESCRIPTION
         "The number of successfully completed
          IPv6 PDP context activation procedures initiated by an MS."
   ::= { ggsnPdpContextsStatsCompleted 9 }

ggsnCompletedSecondaryActivationIpv6 OBJECT-TYPE
   SYNTAX        Counter64
   MAX-ACCESS    read-only
   STATUS        current
   DESCRIPTION
         "The number of successfully completed secondary IPv6 PDP context
         activation procedures initiated by an MS.
         
         Note: All GPRS session management statistics except
         ggsnAttemptedSecondaryActivation, ggsnCompletedSecondaryActivation,
         ggsnAttemptedSecondaryActivationIpv6, and
         ggsnCompletedSecondaryActivationIpv6 count all
         PDP contexts, both secondary and primary."
   ::= { ggsnPdpContextsStatsCompleted 10 }

ggsnCompletedActivationWlan OBJECT-TYPE
   SYNTAX        Counter64
   MAX-ACCESS    read-only
   STATUS        current
   DESCRIPTION
         "The number of successfully completed WLAN PDP context activation
          procedures initiated by an MS.
          
          Note: This counter can not be retrieved by CLI."
   ::= { ggsnPdpContextsStatsCompleted 11 }

ggsnCompletedActivationConversational OBJECT-TYPE
   SYNTAX        Counter64
   MAX-ACCESS    read-only
   STATUS        current
   DESCRIPTION
         "The number of successfully completed primary and secondary PDP context 
          activation procedures with traffic class conversational.

          Note: This counter can not be retrieved by CLI."
   ::= { ggsnPdpContextsStatsCompleted 12 }

ggsnCompletedActivationStreaming OBJECT-TYPE
   SYNTAX        Counter64
   MAX-ACCESS    read-only
   STATUS        current
   DESCRIPTION
         "The number of successfully completed primary and secondary PDP context 
          activation procedures with traffic class streaming.

          Note: This counter can not be retrieved by CLI."
   ::= { ggsnPdpContextsStatsCompleted 13 }

ggsnCompletedActivationInteractive OBJECT-TYPE
   SYNTAX        Counter64
   MAX-ACCESS    read-only
   STATUS        current
   DESCRIPTION
         "The number of successfully completed primary and secondary PDP context 
          activation procedures with traffic class interactive.

          Note: This counter can not be retrieved by CLI."
   ::= { ggsnPdpContextsStatsCompleted 14 }

ggsnCompletedActivationBackground OBJECT-TYPE
   SYNTAX        Counter64
   MAX-ACCESS    read-only
   STATUS        current
   DESCRIPTION
         "The number of successfully completed primary and secondary PDP context 
          activation procedures with traffic class background.

          Note: This counter can not be retrieved by CLI."
   ::= { ggsnPdpContextsStatsCompleted 15 }

ggsnCompletedActivationIpv4v6 OBJECT-TYPE
   SYNTAX        Counter64
   MAX-ACCESS    read-only
   STATUS        current
   DESCRIPTION
         "The number of successfully completed
          IPv4v6 PDP context activation procedures initiated by an MS.
          
          Note: This counter can not be retrieved by CLI."
   ::= { ggsnPdpContextsStatsCompleted 16 }

ggsnFailedActivation OBJECT-TYPE
   SYNTAX        Counter64
   MAX-ACCESS    read-only
   STATUS        current
   DESCRIPTION
         "The number of failed PDP context activation
          procedures initiated by an MS.
          
          Incremented each time a Create PDP Context Response is sent back
          to an SGSN with cause value Request Rejected."         
   ::= { ggsnPdpContextsStatsFailed 1 }



--
-- GGSN GTP statistics
--

ggsnGtpUplinkPackets	OBJECT-TYPE
    SYNTAX 		Counter64
    MAX-ACCESS		read-only
    STATUS		current
    DESCRIPTION
    "Total number of uplink control plane GTP packets processed by the GGSN or PGW.
     Incremented when an uplink GTP packet is received over the Gn control plane."
    
    ::= { ggsnGtpStats 1 }


ggsnGtpUplinkBytes	OBJECT-TYPE
    SYNTAX 		Counter64
    MAX-ACCESS		read-only
    STATUS		current
    DESCRIPTION
    "Total number of bytes for the uplink control plane GTP packets processed by the GGSN or PGW.
     Incremented when an uplink GTP packet is received over the Gn control plane."

    ::= { ggsnGtpStats 2 }


ggsnGtpDownlinkPackets	OBJECT-TYPE
    SYNTAX 		Counter64
    MAX-ACCESS		read-only
    STATUS		current
    DESCRIPTION
    "Total number of downlink control plane GTP packets processed by the GGSN or PGW.
     Incremented when a downlink packet is sent over the Gn control plane."

    ::= { ggsnGtpStats 3 }


ggsnGtpDownlinkBytes	OBJECT-TYPE
    SYNTAX 		Counter64
    MAX-ACCESS		read-only
    STATUS		current
    DESCRIPTION
    "Total number of bytes for the downlink control plane GTP packets processed by the GGSN or PGW.
     Incremented when a downlink packet is sent over the Gn control plane."

    ::= { ggsnGtpStats 4 }


ggsnGtpControlPacketDrops	OBJECT-TYPE
    SYNTAX 		Counter64
    MAX-ACCESS		read-only
    STATUS		current
    DESCRIPTION
	"The total number of GTP-C control packets that have been
	 dropped by the node."
    ::= { ggsnGtpStats 5 }


ggsnGtpVerUnsupPacketsReceived		OBJECT-TYPE
    SYNTAX 		Counter64
    MAX-ACCESS		read-only
    STATUS		current
    DESCRIPTION
	"The number of Version Unsupported responses received by the GGSN."
    ::= { ggsnGtpStats 6 }


ggsnGtpVerUnsupPacketsSent	OBJECT-TYPE
    SYNTAX 		Counter64
    MAX-ACCESS		read-only
    STATUS		current
    DESCRIPTION
	"The number of Version Unsupported responses sent by the GGSN."
    ::= { ggsnGtpStats 7 }


ggsnGtpEchoReqReceived	OBJECT-TYPE
    SYNTAX 		Counter64
    MAX-ACCESS		read-only
    STATUS		current
    DESCRIPTION
	"The number of GTP echo requests received by the GGSN."
    ::= { ggsnGtpStats 8 }


ggsnGtpEchoReqSent	OBJECT-TYPE
    SYNTAX 		Counter64
    MAX-ACCESS		read-only
    STATUS		current
    DESCRIPTION
	"The number of GTP echo requests sent by the GGSN."
    ::= { ggsnGtpStats 9 }


ggsnGtpEchoRespReceived	OBJECT-TYPE
    SYNTAX 		Counter64
    MAX-ACCESS		read-only
    STATUS		current
    DESCRIPTION
	"The number of GTP echo responses received by the GGSN."
    ::= { ggsnGtpStats 10 }


ggsnGtpEchoRespSent	OBJECT-TYPE
    SYNTAX 		Counter64
    MAX-ACCESS		read-only
    STATUS		current
    DESCRIPTION
	"The number of GTP echo responses sent by the GGSN."
    ::= { ggsnGtpStats 11 }


ggsnGtpPdpCreateReqReceived	OBJECT-TYPE
    SYNTAX 		Counter64
    MAX-ACCESS		read-only
    STATUS		current
    DESCRIPTION
	"The number of PDP Create requests received by the GGSN."
    ::= { ggsnGtpStats 12 }

ggsnGtpPdpCreateRespSent	OBJECT-TYPE
    SYNTAX 		Counter64
    MAX-ACCESS		read-only
    STATUS		current
    DESCRIPTION
	"The number of PDP Create responses sent by the GGSN."
    ::= { ggsnGtpStats 13 }


ggsnGtpPdpUpdateReqReceived	OBJECT-TYPE
    SYNTAX 		Counter64
    MAX-ACCESS		read-only
    STATUS		current
    DESCRIPTION
	"The number of PDP update requests received by the GGSN."
    ::= { ggsnGtpStats 14 }


ggsnGtpPdpUpdateReqSent	OBJECT-TYPE
    SYNTAX 		Counter64
    MAX-ACCESS		read-only
    STATUS		current
    DESCRIPTION
	"The number of PDP update requests sent by the GGSN."
    ::= { ggsnGtpStats 15 }


ggsnGtpPdpUpdateRespReceived	OBJECT-TYPE
    SYNTAX 		Counter64
    MAX-ACCESS		read-only
    STATUS		current
    DESCRIPTION
	"The number of PDP update responses received by the GGSN."
    ::= { ggsnGtpStats 16 }


ggsnGtpPdpUpdateRespSent	OBJECT-TYPE
    SYNTAX 		Counter64
    MAX-ACCESS		read-only
    STATUS		current
    DESCRIPTION
	"The number of PDP update responses sent by the GGSN."
    ::= { ggsnGtpStats 17 }


ggsnGtpPdpDeleteReqReceived	OBJECT-TYPE
    SYNTAX 		Counter64
    MAX-ACCESS		read-only
    STATUS		current
    DESCRIPTION
	"The number of PDP delete requests received by the GGSN."
    ::= { ggsnGtpStats 18 }


ggsnGtpPdpDeleteReqSent	OBJECT-TYPE
    SYNTAX 		Counter64
    MAX-ACCESS		read-only
    STATUS		current
    DESCRIPTION
	"The number of PDP delete requests sent by the GGSN."
    ::= { ggsnGtpStats 19 }


ggsnGtpPdpDeleteRespReceived	OBJECT-TYPE
    SYNTAX 		Counter64
    MAX-ACCESS		read-only
    STATUS		current
    DESCRIPTION
	"The number of PDP delete responses received by the GGSN."
    ::= { ggsnGtpStats 20 }


ggsnGtpPdpDeleteRespSent	OBJECT-TYPE
    SYNTAX 		Counter64
    MAX-ACCESS		read-only
    STATUS		current
    DESCRIPTION
	"The number of PDP delete responses sent by the GGSN."
    ::= { ggsnGtpStats 21 }


ggsnGtpRequestsAccepted	OBJECT-TYPE
    SYNTAX 		Counter64
    MAX-ACCESS		read-only
    STATUS		current
    DESCRIPTION
	"The number of GTP requests accepted by the GGSN.

         Incremented each time a Create PDP Context Response,
         Update PDP Context Response or Delete PDP Context Response
         is sent back to an SGSN with cause value Request Accepted."
    ::= { ggsnGtpStats 22 }

ggsnGtpNbrOfTunnels OBJECT-TYPE
    SYNTAX              Gauge32
    MAX-ACCESS          read-only
    STATUS              current
    DESCRIPTION
        "The number of currently active GTP tunnels on the GGSN.
         Each primary PDP context is counted twice for
         signaling tunnel and payload tunnel,
         and each secondary PDP context is counted once for
         payload tunnel only,
         as they share signaling tunnels with their primary PDP contexts."         
    ::= { ggsnGtpStats 23 }

ggsnGtpNbrOfCreatedTunnels OBJECT-TYPE
    SYNTAX              Counter64
    MAX-ACCESS          read-only
    STATUS              current
    DESCRIPTION
        "The total number of GTP tunnels that have been created on the GGSN.
         Each primary PDP context is counted twice for
         signaling tunnel and payload tunnel,
         and each secondary PDP context is counted once for
         payload tunnel only,
         as they share signaling tunnels with their primary PDP contexts."         
    ::= { ggsnGtpStats 24 }

ggsnGtpPdpInitiateContextActivationRespReceived	OBJECT-TYPE
    SYNTAX 		Counter64
    MAX-ACCESS		read-only
    STATUS		current
    DESCRIPTION
	"The number of Initiate PDP Context Activation Responses received by the GGSN from an SGSN."
    ::= { ggsnGtpStats 25 }
    
ggsnGtpPdpInitiateContextActivationReqSent	OBJECT-TYPE
    SYNTAX 		Counter64
    MAX-ACCESS		read-only
    STATUS		current
    DESCRIPTION
	"The number of Initiate PDP Context Activation Requests sent by the GGSN to an SGSN."
    ::= { ggsnGtpStats 26 }

ggsnGtpv0PdpCreateReqReceived	OBJECT-TYPE
    SYNTAX 		Counter64
    MAX-ACCESS		read-only
    STATUS		current
    DESCRIPTION
	"The number of GtpV0 PDP Create requests received by the GGSN."
    ::= { ggsnGtpStats 27 }
--
-- GGSN GTP error statistics
--


ggsnGtpErrorIndicationReceived		OBJECT-TYPE
    SYNTAX		Counter64
    MAX-ACCESS		read-only
    STATUS		current
    DESCRIPTION
	"The number of Error Indications received by the
	 node (aggregate of error indications received by the GTP-U)."
    ::= { ggsnGtpErrorStats 1 }

ggsnGtpErrorIndicationSent		OBJECT-TYPE
    SYNTAX		Counter64
    MAX-ACCESS		read-only
    STATUS		current
    DESCRIPTION
	"The number of Error Indications sent by the
	 node (aggregate of error indications sent by the GTP-U).
	 The GGSN may send an Error Indication to the SGSN or RNC 
	 if no PDP context exists or the PDP context is inactive 
	 for a received GTP Packet Data Unit (G-PDU)."
    ::= { ggsnGtpErrorStats 2 }

ggsnGtpErrorInvalidRequestFormat	OBJECT-TYPE
    SYNTAX		Counter64
    MAX-ACCESS		read-only
    STATUS		current
    DESCRIPTION
	"The number of GTP invalid request format errors sent by the GGSN."
    ::= { ggsnGtpErrorStats 3 }

ggsnGtpErrorResourcesUnavailable	OBJECT-TYPE
    SYNTAX		Counter64
    MAX-ACCESS		read-only
    STATUS		current
    DESCRIPTION
	"The number of GTP resources unavailable errors sent by the GGSN."
    ::= { ggsnGtpErrorStats 4 }

ggsnGtpErrorDynAddrUnavailable		OBJECT-TYPE
    SYNTAX		Counter64
    MAX-ACCESS		read-only
    STATUS		current
    DESCRIPTION
	"The number of GTP dynamic address unavailable errors
	 sent by the GGSN."
    ::= { ggsnGtpErrorStats 5 }

ggsnGtpErrorMemoryUnavailable		OBJECT-TYPE
    SYNTAX		Counter64
    MAX-ACCESS		read-only
    STATUS		current
    DESCRIPTION
	"The number of GTP memory not available errors sent by the GGSN."
    ::= { ggsnGtpErrorStats 6 }

ggsnGtpErrorApnUnknown			OBJECT-TYPE
    SYNTAX		Counter64
    MAX-ACCESS		read-only
    STATUS		current
    DESCRIPTION
    "The number of GTP APN invalid errors sent by the GGSN."
    ::= { ggsnGtpErrorStats 7 }

ggsnGtpErrorPdpAddrUnknown		OBJECT-TYPE
    SYNTAX		Counter64
    MAX-ACCESS		read-only
    STATUS		current
    DESCRIPTION
	"The number of GTP PDP address unknown errors sent by the GGSN."
    ::= { ggsnGtpErrorStats 8 }

ggsnGtpErrorAuthenticationFailed	OBJECT-TYPE
    SYNTAX		Counter64
    MAX-ACCESS		read-only
    STATUS		current
    DESCRIPTION
	"The number of GTP authentication failed errors sent by the GGSN."
    ::= { ggsnGtpErrorStats 9 }

ggsnGtpErrorSystemFailure		OBJECT-TYPE
    SYNTAX		Counter64
    MAX-ACCESS		read-only
    STATUS		current
    DESCRIPTION
	"The number of GTP system failure errors sent by the GGSN."
    ::= { ggsnGtpErrorStats 10 }

ggsnGtpErrorTftSemanticError		OBJECT-TYPE
    SYNTAX		Counter64
    MAX-ACCESS		read-only
    STATUS		current
    DESCRIPTION
	"The number of GTP TFT semantic errors sent by the GGSN."
    ::= { ggsnGtpErrorStats 11 }

ggsnGtpErrorTftSyntaxError		OBJECT-TYPE
    SYNTAX		Counter64
    MAX-ACCESS		read-only
    STATUS		current
    DESCRIPTION
	"The number of GTP TFT syntax errors sent by the GGSN."
    ::= { ggsnGtpErrorStats 12 }

ggsnGtpErrorPackFiltSemantError		OBJECT-TYPE
    SYNTAX		Counter64
    MAX-ACCESS		read-only
    STATUS		current
    DESCRIPTION
	"The number of semantic packet filter errors sent by the GGSN."
    ::= { ggsnGtpErrorStats 13 }

ggsnGtpErrorPackFiltSyntaxError		OBJECT-TYPE
    SYNTAX		Counter64
    MAX-ACCESS		read-only
    STATUS		current
    DESCRIPTION
	"The number of packet filter syntax errors sent by the GGSN."
    ::= { ggsnGtpErrorStats 14 }

ggsnGtpErrorMandatoryIEMissing		OBJECT-TYPE
    SYNTAX		Counter64
    MAX-ACCESS		read-only
    STATUS		current
    DESCRIPTION
	"The number of errors sent by the GGSN indicating that
	 a mandatory information element was missing."
    ::= { ggsnGtpErrorStats 15 }

ggsnGtpErrorMandatoryIEInvalid		OBJECT-TYPE
    SYNTAX		Counter64
    MAX-ACCESS		read-only
    STATUS		current
    DESCRIPTION
	"The number of errors sent by the GGSN indicating that a mandatory information element was invalid."
    ::= { ggsnGtpErrorStats 16 }

ggsnGtpErrorOptionalIEInvalid		OBJECT-TYPE
    SYNTAX		Counter64
    MAX-ACCESS		read-only
    STATUS		current
    DESCRIPTION
	"The number of errors sent by the GGSN indicating that an optional information element was invalid."
    ::= { ggsnGtpErrorStats 17 }

ggsnGtpErrorReferenceInexistent		OBJECT-TYPE
    SYNTAX		Counter64
    MAX-ACCESS		read-only
    STATUS		current
    DESCRIPTION
    "The number of cause codes 'Context Not Found' and 'Non Existent' sent
     as response to the following operations:
     -Create PDP context
     -Update PDP context
     -Delete PDP context"
    ::= { ggsnGtpErrorStats 18 }

ggsnGtpErrorServiceUnsupported		OBJECT-TYPE
    SYNTAX		Counter64
    MAX-ACCESS		read-only
    STATUS		current
    DESCRIPTION
	"The number of service unsupported errors sent by the GGSN."
    ::= { ggsnGtpErrorStats 19 }

ggsnGtpErrorInvalidRequestFormatUpd	OBJECT-TYPE
    SYNTAX		Counter64
    MAX-ACCESS		read-only
    STATUS		current
    DESCRIPTION
	"The number of GTP invalid update request format errors
         sent by the GGSN."
    ::= { ggsnGtpErrorStats 20 }

ggsnGtpErrorInvalidRequestFormatDel	OBJECT-TYPE
    SYNTAX		Counter64
    MAX-ACCESS		read-only
    STATUS		current
    DESCRIPTION
	"The number of GTP invalid delete request format errors
         sent by the GGSN."
    ::= { ggsnGtpErrorStats 21 }

ggsnGtpErrorSystemFailureUpd		OBJECT-TYPE
    SYNTAX		Counter64
    MAX-ACCESS		read-only
    STATUS		current
    DESCRIPTION
	"The number of GTP system update failure errors sent by the GGSN."
    ::= { ggsnGtpErrorStats 22 }

ggsnGtpErrorTftSemanticErrorUpd		OBJECT-TYPE
    SYNTAX		Counter64
    MAX-ACCESS		read-only
    STATUS		current
    DESCRIPTION
	"The number of GTP TFT update semantic errors sent by the GGSN."
    ::= { ggsnGtpErrorStats 23 }

ggsnGtpErrorTftSyntaxErrorUpd		OBJECT-TYPE
    SYNTAX		Counter64
    MAX-ACCESS		read-only
    STATUS		current
    DESCRIPTION
	"The number of GTP TFT update syntax errors sent by the GGSN."
    ::= { ggsnGtpErrorStats 24 }

ggsnGtpErrorPackFiltSemantErrorUpd		OBJECT-TYPE
    SYNTAX		Counter64
    MAX-ACCESS		read-only
    STATUS		current
    DESCRIPTION
	"The number of semantic update packet filter errors sent by the GGSN."
    ::= { ggsnGtpErrorStats 25 }

ggsnGtpErrorPackFiltSyntaxErrorUpd		OBJECT-TYPE
    SYNTAX		Counter64
    MAX-ACCESS		read-only
    STATUS		current
    DESCRIPTION
	"The number of packet update filter syntax errors sent by the GGSN."
    ::= { ggsnGtpErrorStats 26 }

ggsnGtpErrorMandatoryIEMissingUpd		OBJECT-TYPE
    SYNTAX		Counter64
    MAX-ACCESS		read-only
    STATUS		current
    DESCRIPTION
    "The number of errors sent by the GGSN indicating that
     a mandatory information element was missing in an update request."
    ::= { ggsnGtpErrorStats 27 }

ggsnGtpErrorMandatoryIEMissingDel		OBJECT-TYPE
    SYNTAX		Counter64
    MAX-ACCESS		read-only
    STATUS		current
    DESCRIPTION
    "The number of errors sent by the GGSN indicating that
     a mandatory information element was missing in a delete request."
    ::= { ggsnGtpErrorStats 28 }

ggsnGtpErrorMandatoryIEInvalidUpd		OBJECT-TYPE
    SYNTAX		Counter64
    MAX-ACCESS		read-only
    STATUS		current
    DESCRIPTION
    "The number of errors sent by the GGSN indicating that
     a mandatory information element was invalid in an update request."
    ::= { ggsnGtpErrorStats 29 }

ggsnGtpErrorMandatoryIEInvalidDel		OBJECT-TYPE
    SYNTAX		Counter64
    MAX-ACCESS		read-only
    STATUS		current
    DESCRIPTION
    "The number of errors sent by the GGSN indicating that
     a mandatory information element was invalid in a delete request."
    ::= { ggsnGtpErrorStats 30 }

ggsnGtpErrorOptionalIEInvalidUpd		OBJECT-TYPE
    SYNTAX		Counter64
    MAX-ACCESS		read-only
    STATUS		current
    DESCRIPTION
    "The number of errors sent by the GGSN indicating that an optional information element was invalid in an update request."
    ::= { ggsnGtpErrorStats 31 }

ggsnGtpErrorOptionalIEInvalidDel		OBJECT-TYPE
    SYNTAX		Counter64
    MAX-ACCESS		read-only
    STATUS		current
    DESCRIPTION
    "The number of errors sent by the GGSN indicating that an optional information element was invalid in a delete request."
    ::= { ggsnGtpErrorStats 32 }

ggsnGtpErrorReferenceInexistentUpd		OBJECT-TYPE
    SYNTAX		Counter64
    MAX-ACCESS		read-only
    STATUS		current
    DESCRIPTION
    "The number of cause codes 'Context Not Found' and 'Non Existent' sent
     as response to update PDP context requests"
    ::= { ggsnGtpErrorStats 33 }

ggsnGtpErrorReferenceInexistentDel		OBJECT-TYPE
    SYNTAX		Counter64
    MAX-ACCESS		read-only
    STATUS		current
    DESCRIPTION
    "The number of cause codes 'Context Not Found' and 'Non Existent' sent
     as response to delete PDP context requests"
    ::= { ggsnGtpErrorStats 34 }

ggsnGtpErrorPdpWithoutTft			OBJECT-TYPE
    SYNTAX		Counter64
    MAX-ACCESS		read-only
    STATUS		current
    DESCRIPTION
	"The number of pdp context errors without TFT already activated."
    ::= { ggsnGtpErrorStats 35 }

ggsnGtpErrorApnAccessDenied			OBJECT-TYPE
    SYNTAX		Counter64
    MAX-ACCESS		read-only
    STATUS		current
    DESCRIPTION
	"The number of GTP apn access denied errors with no subscription."
    ::= { ggsnGtpErrorStats 36 }

ggsnGtpNewPdpTypeNwPreference         OBJECT-TYPE
    SYNTAX      Counter64
    MAX-ACCESS      read-only
    STATUS      current
    DESCRIPTION
    "The number of new PDP type due to network preference sent by the GGSN."
    ::= { ggsnGtpErrorStats 37 }

ggsnGtpNewPdpTypeSingleAddressBearerOnly         OBJECT-TYPE
    SYNTAX      Counter64
    MAX-ACCESS      read-only
    STATUS      current
    DESCRIPTION
    "The number of new PDP type due to single address bearer only sent by the GGSN."
    ::= { ggsnGtpErrorStats 38 }

--
-- GGSN GTP Prime statistics
--


ggsnGtpPrEchoReqReceived		OBJECT-TYPE
    SYNTAX		Counter64
    MAX-ACCESS		read-only
    STATUS		current
    DESCRIPTION
	"The number of GTP Prime echo requests received by the GGSN."
    ::= { ggsnGtpPrStats 1 }

ggsnGtpPrEchoRequestsSent		OBJECT-TYPE
    SYNTAX		Counter64
    MAX-ACCESS		read-only
    STATUS		current
    DESCRIPTION
	"The number of GTP Prime echo requests sent by the GGSN."
    ::= { ggsnGtpPrStats 2 }

ggsnGtpPrEchoRespReceived		OBJECT-TYPE
    SYNTAX		Counter64
    MAX-ACCESS		read-only
    STATUS		current
    DESCRIPTION
	"The number of GTP Prime echo responses received by the GGSN."
    ::= { ggsnGtpPrStats 3 }

ggsnGtpPrEchoRespSent		OBJECT-TYPE
    SYNTAX		Counter64
    MAX-ACCESS		read-only
    STATUS		current
    DESCRIPTION
	"The number of GTP Prime echo responses sent by the GGSN."
    ::= { ggsnGtpPrStats 4 }

ggsnGtpPrVerUnsupPacketsReceived	OBJECT-TYPE
    SYNTAX		Counter64
    MAX-ACCESS		read-only
    STATUS		current
    DESCRIPTION
	"The number of GTP Prime version unsupported packets received by the GGSN."
    ::= { ggsnGtpPrStats 5 }

ggsnGtpPrVerUnsupPacketsSent		OBJECT-TYPE
    SYNTAX		Counter64
    MAX-ACCESS		read-only
    STATUS		current
    DESCRIPTION
	"The number of GTP Prime version unsupported packets sent by the GGSN."
    ::= { ggsnGtpPrStats 6 }

ggsnGtpPrNodeAliveReqReceived		OBJECT-TYPE
    SYNTAX		Counter64
    MAX-ACCESS		read-only
    STATUS		current
    DESCRIPTION
	"The number of GTP Prime Node Alive request packets received by the GGSN."
    ::= { ggsnGtpPrStats 7 }

ggsnGtpPrNodeAliveReqSent		OBJECT-TYPE
    SYNTAX		Counter64
    MAX-ACCESS		read-only
    STATUS		current
    DESCRIPTION
	"The number of GTP Prime Node Alive request packets sent by the GGSN."
    ::= { ggsnGtpPrStats 8 }

ggsnGtpPrNodeAliveRespReceived		OBJECT-TYPE
    SYNTAX		Counter64
    MAX-ACCESS		read-only
    STATUS		current
    DESCRIPTION
	"The number of GTP Prime Node Alive response packets received by the GGSN."
    ::= { ggsnGtpPrStats 9 }

ggsnGtpPrNodeAliveRespSent		OBJECT-TYPE
    SYNTAX		Counter64
    MAX-ACCESS		read-only
    STATUS		current
    DESCRIPTION
	"The number of GTP Prime Node Alive response packets sent by the GGSN."
    ::= { ggsnGtpPrStats 10 }

ggsnGtpPrRedirectReqReceived		OBJECT-TYPE
    SYNTAX		Counter64
    MAX-ACCESS		read-only
    STATUS		current
    DESCRIPTION
	"The number of GTP Prime redirect requests received by the GGSN."
    ::= { ggsnGtpPrStats 11 }

ggsnGtpPrRedirectReqSent		OBJECT-TYPE
    SYNTAX		Counter64
    MAX-ACCESS		read-only
    STATUS		current
    DESCRIPTION
	"The number of GTP Prime redirect requests sent by the GGSN."
    ::= { ggsnGtpPrStats 12 }

ggsnGtpPrRedirectRespReceived		OBJECT-TYPE
    SYNTAX		Counter64
    MAX-ACCESS		read-only
    STATUS		current
    DESCRIPTION
	"The number of GTP Prime redirect responses received by the GGSN."
    ::= { ggsnGtpPrStats 13 }

ggsnGtpPrRedirectRespSent		OBJECT-TYPE
    SYNTAX		Counter64
    MAX-ACCESS		read-only
    STATUS		current
    DESCRIPTION
	"The number of GTP Prime redirect responses sent by the GGSN."
    ::= { ggsnGtpPrStats 14 }

ggsnGtpPrDataRecTransferReceived	OBJECT-TYPE
    SYNTAX		Counter64
    MAX-ACCESS		read-only
    STATUS		current
    DESCRIPTION
	"The number of GTP Prime data record transfer responses received
	 by the GGSN."
    ::= { ggsnGtpPrStats 15 }

ggsnGtpPrDataRecTransferSent		OBJECT-TYPE
    SYNTAX		Counter64
    MAX-ACCESS		read-only
    STATUS		current
    DESCRIPTION
	"The number of GTP Prime data record transfers sent by the GGSN."
    ::= { ggsnGtpPrStats 16 }

ggsnGtpPrSndDataRecordPackets		OBJECT-TYPE
    SYNTAX              Counter64
    MAX-ACCESS          read-only
    STATUS              current
    DESCRIPTION
        "The number of GTP Prime data record transfer request Send
	 Data Record packets sent by the GGSN."
    ::= { ggsnGtpPrStats 17 }

-- { ggsnGtpPrStats 18-20 } are not assigned

ggsnGtpPrRequestAccepted		OBJECT-TYPE
    SYNTAX              Counter64
    MAX-ACCESS          read-only
    STATUS              current
    DESCRIPTION
        "The number of GTP Prime data record transfer response
	 Request Accepted received by the GGSN."
    ::= { ggsnGtpPrStats 21 }

ggsnGtpPrNoResource			OBJECT-TYPE
    SYNTAX              Counter64
    MAX-ACCESS          read-only
    STATUS              current
    DESCRIPTION
        "The number of GTP Prime data record transfer response
         No Resource received by the GGSN."
    ::= { ggsnGtpPrStats 22 }

ggsnGtpPrServiceUnsupported		OBJECT-TYPE
    SYNTAX              Counter64
    MAX-ACCESS          read-only
    STATUS              current
    DESCRIPTION
        "The number of GTP Prime data record transfer response
         Service Unsupported received by the GGSN."
    ::= { ggsnGtpPrStats 23 }

ggsnGtpPrSystemFailure			OBJECT-TYPE
    SYNTAX              Counter64
    MAX-ACCESS          read-only
    STATUS              current
    DESCRIPTION
        "The number of GTP Prime data record transfer response
         System Failure received by the GGSN."
    ::= { ggsnGtpPrStats 24 }

ggsnGtpPrInvalidMessageFormat		OBJECT-TYPE
    SYNTAX              Counter64
    MAX-ACCESS          read-only
    STATUS              current
    DESCRIPTION
        "The number of GTP Prime data record transfer response
         Invalid Message Format received by the GGSN."
    ::= { ggsnGtpPrStats 25 }

ggsnGtpPrVersionUnsupported		OBJECT-TYPE
    SYNTAX              Counter64
    MAX-ACCESS          read-only
    STATUS              current
    DESCRIPTION
        "The number of GTP Prime data record transfer response
         Version Unsupported received by the GGSN."
    ::= { ggsnGtpPrStats 26 }

ggsnGtpPrRequestUnfulfilled		OBJECT-TYPE
    SYNTAX              Counter64
    MAX-ACCESS          read-only
    STATUS              current
    DESCRIPTION
        "The number of GTP Prime data record transfer response
         Request Unfulfilled received by the GGSN."
    ::= { ggsnGtpPrStats 27 }

ggsnGtpPrDecodingError			OBJECT-TYPE
    SYNTAX              Counter64
    MAX-ACCESS          read-only
    STATUS              current
    DESCRIPTION
        "The number of GTP Prime data record transfer response
         Decoding Error received by the GGSN."
    ::= { ggsnGtpPrStats 28 }

ggsnGtpPrAlreadyFulfilled		OBJECT-TYPE
    SYNTAX              Counter64
    MAX-ACCESS          read-only
    STATUS              current
    DESCRIPTION
        "The number of GTP Prime data record transfer response
         Request Already Fulfilled received by the GGSN."
    ::= { ggsnGtpPrStats 29 }

ggsnGtpPrDupPacketFulfilled		OBJECT-TYPE
    SYNTAX              Counter64
    MAX-ACCESS          read-only
    STATUS              current
    DESCRIPTION
        "The number of GTP Prime data record transfer response
         Request Duplicate Packet Fulfilled received by the GGSN."
    ::= { ggsnGtpPrStats 30 }


--
-- GGSN GTP Prime Error statistics
--


ggsnGtpPrErrorMandatoryIEMissing	OBJECT-TYPE
    SYNTAX		Counter64
    MAX-ACCESS		read-only
    STATUS		current
    DESCRIPTION
	"The number of GTP Prime mandatory information element
	 missing errors received by the GGSN."
    ::= { ggsnGtpPrErrorStats 1 }

ggsnGtpPrErrorMandatoryIEInvalid	OBJECT-TYPE
    SYNTAX		Counter64
    MAX-ACCESS		read-only
    STATUS		current
    DESCRIPTION
	"The number of GTP Prime mandatory information element invalid
	 errors received by the GGSN."
    ::= { ggsnGtpPrErrorStats 2 }

ggsnGtpPrErrorOptionalIEInvalid		OBJECT-TYPE
    SYNTAX		Counter64
    MAX-ACCESS		read-only
    STATUS		current
    DESCRIPTION
	"The number of GTP Prime optional information element invalid
	 errors received by the GGSN."
    ::= { ggsnGtpPrErrorStats 3 }

ggsnGtpPrErrorRefInexistent		OBJECT-TYPE
    SYNTAX		Counter64
    MAX-ACCESS		read-only
    STATUS		current
    DESCRIPTION
	"The number of GTP Prime reference inexistent errors
	 received by the GGSN."
    ::= { ggsnGtpPrErrorStats 4 }


--
-- Link traffic information
--


ggsnUplinkTrafficInfo
   OBJECT IDENTIFIER ::= { ggsnGlobalStats 11 }
ggsnDownlinkTrafficInfo
   OBJECT IDENTIFIER ::= { ggsnGlobalStats 12 }
pdnConnectionsGgsn
   OBJECT IDENTIFIER ::= { ggsnGlobalStats 13 }

ggsnUplinkPackets OBJECT-TYPE
   SYNTAX        Counter64
   MAX-ACCESS    read-only
   STATUS        current
   DESCRIPTION
       "Total number of uplink Gn and S5 user plane IPv4 and IPv6 packets processed by the GGSN or PGW. Incremented when an uplink packet, received over the Gn or S5 user plane interface, is sent over Gi or SGi interface."   
   ::= { ggsnUplinkTrafficInfo 1 }

ggsnUplinkBytes OBJECT-TYPE
   SYNTAX        Counter64
   MAX-ACCESS    read-only
   STATUS        current
   DESCRIPTION
       "Total number of uplink Gn and S5 user plane IPv4 and IPv6 bytes processed by the GGSN or PGW. Incremented when an uplink packet, received over the Gn or S5 user plane interface, is sent over Gi or SGi interface."
   ::= { ggsnUplinkTrafficInfo 2 }

ggsnUplinkDrops OBJECT-TYPE
   SYNTAX        Counter64
   MAX-ACCESS    read-only
   STATUS        current
   DESCRIPTION
       "Total number of uplink Gn and S5 user plane IPv4 and IPv6 packets dropped by this GGSN or PGW. Incremented when an uplink packet, received over the Gn or S5 user plane interface, is dropped."
   ::= { ggsnUplinkTrafficInfo 3 }

ggsnUplinkDropsBytes OBJECT-TYPE
   SYNTAX        Counter64
   MAX-ACCESS    read-only
   STATUS        current
   DESCRIPTION
       "Total number of uplink Gn and S5 user plane IPv4 and IPv6 bytes dropped by this GGSN or PGW. Incremented when an uplink packet received over the Gn or S5 user plane interface is dropped."
   ::= { ggsnUplinkTrafficInfo 4 }

ggsnUplinkPacketsIpv6 OBJECT-TYPE
   SYNTAX        Counter64
   MAX-ACCESS    read-only
   STATUS        current
   DESCRIPTION
       "Total number of uplink Gn and S5 user plane IPv6 packets processed by the GGSN or PGW. Incremented when an uplink IPv6 packet, received over the Gn or S5 user plane interface is sent over Gi or SGi interface."
   ::= { ggsnUplinkTrafficInfo 5 }

ggsnUplinkBytesIpv6 OBJECT-TYPE
   SYNTAX        Counter64
   MAX-ACCESS    read-only
   STATUS        current
   DESCRIPTION
       "Total number of uplink Gn and S5 user plane IPv6 bytes processed by the GGSN or PGW. Incremented when an uplink IPv6 packet received over the Gn or S5 user plane interface is sent over Gi or SGi interface."
   ::= { ggsnUplinkTrafficInfo 6 }

ggsnUplinkDropsIpv6 OBJECT-TYPE
   SYNTAX        Counter64
   MAX-ACCESS    read-only
   STATUS        current
   DESCRIPTION
       "Total number of uplink Gn and S5 user plane IPv6 packets dropped by this GGSN or PGW. Incremented when an uplink IPv6 packet received over the Gn or S5 user plane interface is dropped."
   ::= { ggsnUplinkTrafficInfo 7 }

ggsnUplinkBytesWlan OBJECT-TYPE
   SYNTAX        Counter64
   MAX-ACCESS    read-only
   STATUS        obsolete
   DESCRIPTION
         "Total bytes for all processed uplink WLAN packets via this GGSN."
   ::= { ggsnUplinkTrafficInfo 8 }

ggsnUplinkDropsWlan OBJECT-TYPE
   SYNTAX        Counter64
   MAX-ACCESS    read-only
   STATUS        obsolete
   DESCRIPTION
         "The number of uplink WLAN packets dropped by this GGSN."
   ::= { ggsnUplinkTrafficInfo 9 }

ggsnUplinkPacketsWlan OBJECT-TYPE
   SYNTAX        Counter64
   MAX-ACCESS    read-only
   STATUS        obsolete
   DESCRIPTION
         "Total uplink WLAN packets processed by this GGSN."
   ::= { ggsnUplinkTrafficInfo 10 }

ggsnDownlinkPackets OBJECT-TYPE
   SYNTAX        Counter64
   MAX-ACCESS    read-only
   STATUS        current
   DESCRIPTION
       "Total number of downlink Gn and S5 user plane IPv4 and IPv6 packets processed by the GGSN or PGW. Incremented when a downlink packet is sent over the Gn or S5 user plane interface."
   ::= { ggsnDownlinkTrafficInfo 1 }

ggsnDownlinkBytes OBJECT-TYPE
   SYNTAX        Counter64
   MAX-ACCESS    read-only
   STATUS        current
   DESCRIPTION
       "Total number of downlink Gn and S5 user plane IPv4 and IPv6 bytes processed by the GGSN or PGW. Incremented when a downlink packet is sent over the Gn or S5 user plane interface."
   ::= { ggsnDownlinkTrafficInfo 2 }

ggsnDownlinkDrops OBJECT-TYPE
   SYNTAX        Counter64
   MAX-ACCESS    read-only
   STATUS        current
   DESCRIPTION
       "Total number of downlink Gn and S5 user plane IPv4 and IPv6 packets dropped by the GGSN or PGW. Incremented when a downlink packet received over the Gi or SGi user plane interface is dropped."
   ::= { ggsnDownlinkTrafficInfo 3 }

ggsnDownlinkDropsBytes OBJECT-TYPE
   SYNTAX        Counter64
   MAX-ACCESS    read-only
   STATUS        current
   DESCRIPTION
       "Total number of downlink Gn and S5 user plane IPv4 and IPv6 bytes dropped by the GGSN or PGW. Incremented when a downlink packet received over the Gi or SGi user plane interface is dropped."
   ::= { ggsnDownlinkTrafficInfo 4 }

ggsnDownlinkPacketsIpv6 OBJECT-TYPE
   SYNTAX        Counter64
   MAX-ACCESS    read-only
   STATUS        current
   DESCRIPTION
       "Total number of downlink Gn and S5 user plane IPv6 packets processed by the GGSN or PGW. Incremented when a downlink IPv6 packet is sent over the Gn or S5 user plane interface."
   ::= { ggsnDownlinkTrafficInfo 5 }

ggsnDownlinkBytesIpv6 OBJECT-TYPE
   SYNTAX        Counter64
   MAX-ACCESS    read-only
   STATUS        current
   DESCRIPTION
       "Total number of downlink Gn and S5 user plane IPv6 bytes processed by the GGSN or PGW. Incremented when a downlink IPv6 packet is sent over the Gn or S5 user plane interface."
   ::= { ggsnDownlinkTrafficInfo 6 }

ggsnDownlinkDropsIpv6 OBJECT-TYPE
   SYNTAX        Counter64
   MAX-ACCESS    read-only
   STATUS        current
   DESCRIPTION
       "Total number of downlink Gn and S5 user plane IPv6 bytes dropped by the GGSN or PGW. Incremented when a downlink IPv6 packet received over the Gi or SGi user plane interface is dropped."

   ::= { ggsnDownlinkTrafficInfo 7 }

ggsnDownlinkBytesWlan OBJECT-TYPE
   SYNTAX        Counter64
   MAX-ACCESS    read-only
   STATUS        obsolete
   DESCRIPTION
         "Total bytes for all processed downlink WLAN packets via this GGSN."
   ::= { ggsnDownlinkTrafficInfo 8 }

ggsnDownlinkDropsWlan OBJECT-TYPE
   SYNTAX        Counter64
   MAX-ACCESS    read-only
   STATUS        obsolete
   DESCRIPTION
         "The number of downlink WLAN packets dropped by this GGSN."
   ::= { ggsnDownlinkTrafficInfo 9 }

ggsnDownlinkPacketsWlan OBJECT-TYPE
   SYNTAX        Counter64
   MAX-ACCESS    read-only
   STATUS        obsolete
   DESCRIPTION
         "Total downlink WLAN packets processed by this GGSN."
   ::= { ggsnDownlinkTrafficInfo 10 }

--
-- PDN Connections GGSN
--

nbrOfGgsnPdnConnections OBJECT-TYPE
   SYNTAX        Counter32
   MAX-ACCESS    read-only
   STATUS        current
   DESCRIPTION
         "Number of PDN connections to a non-PGW-enabled APN."
   ::= { pdnConnectionsGgsn 1 }

--
-- GGSN Pic statistics
--


ggsnPicStatsTable OBJECT-TYPE
   SYNTAX        SEQUENCE OF GgsnPicStatsEntry
   MAX-ACCESS    not-accessible
   STATUS        deprecated
   DESCRIPTION
         "A table listing the statistics for all GTP PICs."
   ::= { ggsnGeneralInfo 4 }

ggsnPicStatsEntry OBJECT-TYPE
   SYNTAX        GgsnPicStatsEntry
   MAX-ACCESS    not-accessible
   STATUS        deprecated
   DESCRIPTION
         "A conceptual row listing the statistics for each
          GTP PICs on this GGSN."
   INDEX         { ggsnPicIndex }
   ::= { ggsnPicStatsTable 1 }


GgsnPicStatsEntry ::= SEQUENCE {
   ggsnPicIndex                  Integer32,
   ggsnPicAddress                IpAddress,
   ggsnPicNbrOfActivePdpContexts Gauge32
}

ggsnPicIndex OBJECT-TYPE
   SYNTAX        Integer32 (1..2147483647)
   MAX-ACCESS    not-accessible
   STATUS        deprecated
   DESCRIPTION
         "A number representing each GTP PIC whose statistics
          is being generated."
   ::= { ggsnPicStatsEntry 1 }

ggsnPicAddress OBJECT-TYPE
   SYNTAX        IpAddress
   MAX-ACCESS    read-only
   STATUS        deprecated
   DESCRIPTION
         "The IP address of this GTP PIC."
   ::= { ggsnPicStatsEntry 2 }

ggsnPicNbrOfActivePdpContexts OBJECT-TYPE
   SYNTAX        Gauge32
   MAX-ACCESS    read-only
   STATUS        deprecated
   DESCRIPTION
         "The number of active PDP contexts on a per PIC
          of this GGSN."
   ::= { ggsnPicStatsEntry 3 }



--
-- GGSN APN statistics
--


ggsnApnStatsTable OBJECT-TYPE
   SYNTAX        SEQUENCE OF ApnStats
   MAX-ACCESS    not-accessible
   STATUS        current
   DESCRIPTION
         "A table listing the statistics for all APNs which
          are served by this GGSN."
   ::= { ggsnGeneralInfo 5 }

ggsnApnStatsEntry OBJECT-TYPE
   SYNTAX        ApnStats
   MAX-ACCESS    not-accessible
   STATUS        current
   DESCRIPTION
         "A conceptual row listing the statistics for each
          APN which is served by this GGSN."
   INDEX         { ggsnApnIndex }
   ::= { ggsnApnStatsTable 1 }

ApnStats ::= SEQUENCE {
   ggsnApnIndex                     Integer32,
   ggsnApnName                      DisplayString,
   ggsnApnActivePdpContextCount     Gauge32,
   ggsnApnAttemptedActivation	    Counter64,
   ggsnApnAttemptedDynActivation    Counter64,
   ggsnApnAttemptedDeactivation     Counter64,
   ggsnApnAttemptedSelfDeactivation Counter64,
   ggsnApnCompletedActivation	    Counter64,
   ggsnApnCompletedDynActivation    Counter64,
   ggsnApnCompletedDeactivation     Counter64,
   ggsnApnCompletedSelfDeactivation Counter64,
   ggsnApnUplinkPackets             Counter64,
   ggsnApnUplinkBytes               Counter64,
   ggsnApnUplinkDrops               Counter64,
   ggsnApnDownlinkPackets           Counter64,
   ggsnApnDownlinkBytes             Counter64,
   ggsnApnDownlinkDrops             Counter64,
   ggsnApnAttemptedMSActivation     Counter64,
   ggsnApnCompletedMSActivation     Counter64,
   ggsnApnAttemptedMSDeactivation   Counter64,
   ggsnApnCompletedMSDeactivation   Counter64,
   ggsnApnActivePdpContextMax	    Gauge32,
   ggsnApnActivePdpContextMean	    Gauge32,
   ggsnApnAttemptedAuthActivation   Counter64,
   ggsnApnFailedAuthActivation      Counter64,
   ggsnApnAttemptedUpdateMsAndSgsn  Counter64,
   ggsnApnCompletedUpdateMsAndSgsn  Counter64,
   ggsnApnNbrOfTftFilters	        Gauge32,
   ggsnApnSessTimeoutDeactivation   Counter64,
   ggsnApnIdleTimeoutDeactivation   Counter64,
   ggsnApnGiSignalingInPackets      Counter64,
   ggsnApnGiSignalingInBytes        Counter64,
   ggsnApnGiSignalingOutPackets     Counter64,
   ggsnApnGiSignalingOutBytes       Counter64,
   ggsnApnActivePdpContextCountIpv6 Gauge32,
   ggsnApnAttemptedActivationIpv6   Counter64,
   ggsnApnCompletedActivationIpv6   Counter64,
   ggsnApnAvailableIpAddressesInInternalPool Gauge32,
   ggsnApnIpAddressesInQuarantineInInternalPool Gauge32,
   ggsnApnUplinkPacketsIpv6         Counter64,
   ggsnApnUplinkBytesIpv6           Counter64,
   ggsnApnUplinkDropsIpv6           Counter64,
   ggsnApnDownlinkPacketsIpv6       Counter64,
   ggsnApnDownlinkBytesIpv6         Counter64,
   ggsnApnDownlinkDropsIpv6         Counter64,
   ggsnApnNeighborSolicitationRcv   Counter64,
   ggsnApnNeighborSolicitationRsp   Counter64,
   ggsnApnRouterSolicitationRcv     Counter64,
   ggsnApnRouterSolicitationRsp     Counter64,
   ggsnNbApnActivePdpPerTrafficClassConversational  Gauge32,
   ggsnNbApnActivePdpPerTrafficClassStreaming       Gauge32,
   ggsnNbApnActivePdpPerTrafficClassInteractive     Gauge32,
   ggsnNbApnActivePdpPerTrafficClassBackground      Gauge32,
   ggsnApnImsDedicatedCompletedActivation           Counter64,
   ggsnApnImsDedicatedNotConfiguredActivationFailed Counter64,
   ggsnApnImsGeneralPurposeCompletedActivation      Counter64,
   ggsnApnImsGeneralNotConfiguredActivationFailed   Counter64,
   ggsnApnActivationFailedDuetoGeneralPurposeNotConfigured Counter64,
   ggsnApnUnauthorizedImsPackets                           Counter64,
   ggsnApnRadiusAccountingFailure                          Counter64,
   ggsnApnRadiusAuthenticationFailure                      Counter64,
   ggsnApnSaccRsInstalledDynRules                          Gauge32,
   ggsnApnSaccRsActivePredefinedChargingRules              Gauge32,
   ggsnApnSaccRsActivePredefinedChargingRuleBases          Gauge32,
   ggsnApn3gdtActiveContexts                               Gauge32,
   ggsnApn3gdtTotalCompletedEstablishment                  Gauge32,
   ggsnApn3gdtTotalAttemptedEstablishment                  Gauge32,
   ggsnApn3gdtErrorHandling                                Gauge32,
   ggsnApnAttemptedUpdateGgsn                              Counter64,
   ggsnApnCompletedUpdateGgsn                              Counter64,
   ggsnApnAttemptedActivationNonDuplicated                 Counter64,
   ggsnApnActivePdpContextMaxDuringLastPeriod              Gauge32,
   pgwApnActiveEpsBearer                                   Gauge32,
   pgwApnActiveIpv6EpsBearer                               Gauge32,
   pgwApnAttemptedEpsBearerActivation                      Counter64,
   pgwApnCompletedEpsBearerActivation                      Counter64,
   pgwApnAttemptedIpv6EpsBearerActivation                  Counter64,
   pgwApnCompletedIpv6EpsBearerActivation                  Counter64,
   pgwApnAttemptedEpsBearerDeactivation                    Counter64,
   pgwApnCompletedEpsBearerDeactivation                    Counter64,
   pgwApnAttemptedS5NetworkDeactivation                    Counter64,
   pgwApnCompletedS5NetworkDeactivation                    Counter64,
   pgwApnAttemptedS5UeSgwModification                      Counter64,
   pgwApnCompletedS5UeSgwModification                      Counter64,
   pgwApnAttemptedS5SgwSgsnModification                    Counter64,
   pgwApnCompletedS5SgwSgsnModification                    Counter64,
   pgwApnAttemptedS5SgsnSgwModification                    Counter64,
   pgwApnCompletedS5SgsnSgwModification                    Counter64,
   pgwApnAttemptedS5NetworkModification                    Counter64,
   pgwApnCompletedS5NetworkModification                    Counter64,
   pgwApnAttemptedS5UeSgwDeactivation                      Counter64,
   pgwApnCompletedS5UeSgwDeactivation                      Counter64,
   gnApnUplinkPackets                                      Counter64,
   gnApnUplinkBytes                                        Counter64,
   gnApnUplinkPacketsIpv6                                  Counter64,
   gnApnUplinkBytesIpv6                                    Counter64,
   gnApnDownlinkPackets                                    Counter64,
   gnApnDownlinkBytes                                      Counter64,
   gnApnDownlinkPacketsIpv6                                Counter64,
   gnApnDownlinkBytesIpv6                                  Counter64,
   s5ApnUplinkPackets                                      Counter64,
   s5ApnUplinkBytes                                        Counter64,
   s5ApnUplinkPacketsIpv6                                  Counter64,
   s5ApnUplinkBytesIpv6                                    Counter64,
   s5ApnDownlinkPackets                                    Counter64,
   s5ApnDownlinkBytes                                      Counter64,
   s5ApnDownlinkPacketsIpv6                                Counter64,
   s5ApnDownlinkBytesIpv6                                  Counter64,
   s2aApnUplinkPackets                                     Counter64,  
   s2aApnUplinkBytes                                       Counter64,
   s2aApnUplinkPacketsIpv6                                 Counter64,
   s2aApnUplinkBytesIpv6                                   Counter64,
   s2aApnDownlinkPackets                                   Counter64,
   s2aApnDownlinkBytes                                     Counter64,
   s2aApnDownlinkPacketsIpv6                               Counter64,
   s2aApnDownlinkBytesIpv6                                 Counter64,
   pgwApnActiveDedicatedEpsBearer                          Gauge32,
   pgwApnAttemptedDedicatedEpsBearerActivation	           Counter64,
   pgwApnCompletedDedicatedEpsBearerActivation  	       Counter64,
   pgwApnAttemptedIpv6DedicatedEpsBearerActivation  	   Counter64,
   pgwApnCompletedIpv6DedicatedEpsBearerActivation  	   Counter64,
   pgwApnAttemptedS5NetworkDedicatedEpsBearerDeactivation  Counter64,
   pgwApnCompletedS5NetworkDedicatedEpsBearerDeactivation  Counter64,
   pgwApnAttemptedS5NetworkDedicatedEpsBearerModification  Counter64,
   pgwApnCompletedS5NetworkDedicatedEpsBearerModification  Counter64,
   pgwApnAttemptedS5UeSgwDedicatedEpsBearerDeactivation    Counter64,
   pgwApnCompletedS5UeSgwDedicatedEpsBearerDeactivation	   Counter64,
   gnApn3gdtUplinkBytes                                    Counter64,
   gnApn3gdtUplinkBytesIpv6                                Counter64,
   gnApn3gdtUplinkPackets                                  Counter64,
   gnApn3gdtUplinkPacketsIpv6                              Counter64,
   gnApn3gdtDownlinkBytes                                  Counter64,
   gnApn3gdtDownlinkBytesIpv6                              Counter64,
   gnApn3gdtDownlinkPackets                                Counter64,
   gnApn3gdtDownlinkPacketsIpv6                            Counter64,
   gnApn3gdtDownlinkDropsErrorHandling                     Counter64,
   ggsnApn3gdtGtpError                                     Counter64,
   gnApn3gdtTotalCompletedEstablishment                    Counter32,
   gnApn3gdtTotalAttemptedEstablishment                    Counter32,
   gnApn3gdtErrorHandling                                  Counter32,
   ggsnApnActivePdpContextCountIpv4v6                      Gauge32,
   pgwApnActiveIpv4v6EpsBearer                             Gauge32,
   ggsnApnAttemptedActivationIpv4v6                        Counter64,
   ggsnApnCompletedActivationIpv4v6                        Counter64,
   pgwApnAttemptedIpv4v6EpsBearerActivation                Counter64,
   pgwApnCompletedIpv4v6EpsBearerActivation                Counter64,
   pgwApnActiveWlanEpsBearer                               Gauge32 
}

ggsnApnIndex OBJECT-TYPE
   SYNTAX        Integer32 (1..2147483647)
   MAX-ACCESS    not-accessible
   STATUS        current
   DESCRIPTION
         "A number representing each APN whose statistics
          is being generated."
   ::= { ggsnApnStatsEntry 1 }

ggsnApnName OBJECT-TYPE
   SYNTAX        DisplayString
   MAX-ACCESS    read-only
   STATUS        current
   DESCRIPTION
         "The identifier of the subject APN."
   ::= { ggsnApnStatsEntry 2 }

ggsnApnActivePdpContextCount  OBJECT-TYPE
   SYNTAX        Gauge32
   MAX-ACCESS    read-only
   STATUS        current
   DESCRIPTION
         "The number of active PDP contexts associated with
          the APN."
   ::= { ggsnApnStatsEntry 3 }

ggsnApnAttemptedActivation OBJECT-TYPE
   SYNTAX        Counter64
   MAX-ACCESS    read-only
   STATUS        current
   DESCRIPTION
         "The total number of attempted PDP context activations for this APN.
          Opposite to ggsnAttemptedActivation, the ggsnApnAttemptedActivation is incremented
          even when a Create PDP Context Request is silently discarded.
          
          Note1: If logical APN selection or RADIUS Assisted APN Selection (RAAS), or both are used, 
          the counter is incremented on the chosen physical APN. 
          If RAAS is used, and the RADIUS server does not reply or replies with an incorrect answer, 
          the counter is incremented on the APN, using RAAS.
                    
          Note2: When the SGSN resends the activation request, it is counted as two attempts
          on APN level but as only one attempt on node level. (This happens when the
          primary RADIUS server is unavailable.)"
   ::= { ggsnApnStatsEntry 4 }

ggsnApnAttemptedDynActivation OBJECT-TYPE
   SYNTAX        Counter64
   MAX-ACCESS    read-only
   STATUS        current
   DESCRIPTION
         "The number of dynamic PDP context activation
          procedures initiated by the MS where a dynamic
          PDP address is requested on a per APN basis of the GGSN."
   ::= { ggsnApnStatsEntry 5 }

ggsnApnAttemptedDeactivation OBJECT-TYPE
   SYNTAX        Counter64
   MAX-ACCESS    read-only
   STATUS        current
   DESCRIPTION
         "The total number of attempted PDP context
          deactivations on a per APN basis.

          Note: When the SGSN resends the deactivation request, 
          it is counted as two attempts on APN level but as 
          only one attempt on node level. (This happens when 
          the primary RADIUS server is unavailable.)"
   ::= { ggsnApnStatsEntry 6 }

ggsnApnAttemptedSelfDeactivation OBJECT-TYPE
   SYNTAX        Counter64
   MAX-ACCESS    read-only
   STATUS        current
   DESCRIPTION
         "The number of PDP context deactivation procedures
          initiated by the GGSN on a per APN basis.
           
           Note: This counter cannot be retrieved by CLI."
   ::= { ggsnApnStatsEntry 7 }

ggsnApnCompletedActivation OBJECT-TYPE
   SYNTAX        Counter64
   MAX-ACCESS    read-only
   STATUS        current
   DESCRIPTION
         "The total number of completed PDP context
          activations per APN. Number of completed activations doesn't
          necessarily match the number of attempts for the same APN.
          The APN may have changed after the attempt was made due to logical APN
          or RADIUS-assisted APN selection. The sum of all ggsnApnAttemptedActivation
          should match the sum of ggsnApnCompletedActivation (and failed) over all APNs."
   ::= { ggsnApnStatsEntry 8 }

ggsnApnCompletedDynActivation OBJECT-TYPE
   SYNTAX        Counter64
   MAX-ACCESS    read-only
   STATUS        current
   DESCRIPTION
         "The number of successfully attempted dynamic PDP
          context activation procedures initiated by the MS
          where a dynamic PDP address is requested on a per
          APN basis of the GGSN."
   ::= { ggsnApnStatsEntry 9 }

ggsnApnCompletedDeactivation OBJECT-TYPE
   SYNTAX        Counter64
   MAX-ACCESS    read-only
   STATUS        current
   DESCRIPTION
         "The total number of completed PDP context
          deactivations on a per APN basis."
   ::= { ggsnApnStatsEntry 10 }

ggsnApnCompletedSelfDeactivation OBJECT-TYPE
   SYNTAX        Counter64
   MAX-ACCESS    read-only
   STATUS        current
   DESCRIPTION
         "The number of successfully completed deactivation
          PDP context procedures initiated by the GGSN on a
          per APN basis.
          
          Note: This counter cannot be retrieved by CLI."
   ::= { ggsnApnStatsEntry 11 }

ggsnApnUplinkPackets OBJECT-TYPE
   SYNTAX        Counter64
   MAX-ACCESS    read-only
   STATUS        current
   DESCRIPTION
       "Total number of uplink Gn and S5 user plane packets processed on a per APN basis by the GGSN or PGW. Incremented when an uplink packet received over the Gn or S5 user plane interface is sent over the Gi or SGi interface."
   ::= { ggsnApnStatsEntry 12 }

ggsnApnUplinkBytes OBJECT-TYPE
   SYNTAX        Counter64
   MAX-ACCESS    read-only
   STATUS        current
   DESCRIPTION
       "Total number of uplink Gn and S5 user plane bytes processed on a per APN basis by the GGSN or PGW. Incremented when an uplink packet received over the Gn or S5 user plane interface is sent over the Gi or SGi interface."
   ::= { ggsnApnStatsEntry 13 }

ggsnApnUplinkDrops OBJECT-TYPE
   SYNTAX        Counter64
   MAX-ACCESS    read-only
   STATUS        current
   DESCRIPTION
       "Total number of uplink Gn and S5 user plane packets dropped on a per APN basis by the GGSN or PGW. Incremented when an uplink packet received over the Gn or S5 user plane interface is dropped."
   ::= { ggsnApnStatsEntry 14 }

ggsnApnDownlinkPackets OBJECT-TYPE
   SYNTAX        Counter64
   MAX-ACCESS    read-only
   STATUS        current
   DESCRIPTION
       "Total number of downlink Gn and S5 user plane packets processed on a per APN basis by the GGSN or PGW. Incremented when a downlink packet is sent over the Gn or S5 user plane interface."
   ::= { ggsnApnStatsEntry 15 }

ggsnApnDownlinkBytes OBJECT-TYPE
   SYNTAX        Counter64
   MAX-ACCESS    read-only
   STATUS        current
   DESCRIPTION
       "Total number of downlink Gn and S5 user plane bytes processed on a per APN basis by the GGSN or PGW. Incremented when a downlink packet is sent over the Gn or S5 user plane interface."
   ::= { ggsnApnStatsEntry 16 }

ggsnApnDownlinkDrops OBJECT-TYPE
   SYNTAX        Counter64
   MAX-ACCESS    read-only
   STATUS        current
   DESCRIPTION
       "Total number of downlink Gn and S5 user plane packets dropped on a per APN basis by the GGSN or PGW. Incremented when a downlink packet received over the Gi or SGi user plane interface is dropped."
   ::= { ggsnApnStatsEntry 17 }

ggsnApnAttemptedMSActivation OBJECT-TYPE
   SYNTAX        Counter64
   MAX-ACCESS    read-only
   STATUS        deprecated
   DESCRIPTION
         "The number of PDP context activation procedures
          initiated by the MS on a per APN basis of the GGSN.

          Note: When the SGSN resends the activation request, 
          it is counted as two attempts on APN level but as 
          only one attempt on node level. (This happens when 
          the primary RADIUS server is unavailable.)"
   ::= { ggsnApnStatsEntry 18 }

ggsnApnCompletedMSActivation OBJECT-TYPE
   SYNTAX        Counter64
   MAX-ACCESS    read-only
   STATUS        deprecated
   DESCRIPTION
         "The number of successfully completed activation
          PDP context procedures initiated by the MS on a
          per APN basis of the GGSN."
   ::= { ggsnApnStatsEntry 19 }

ggsnApnAttemptedMSDeactivation OBJECT-TYPE
   SYNTAX        Counter64
   MAX-ACCESS    read-only
   STATUS        current
   DESCRIPTION
         "The number of PDP context deactivation procedures
          initiated by the MS on a per APN basis of the GGSN.
          
          Note: When the SGSN resends the deactivation request, 
          it is counted as two attempts on APN level but as 
          only one attempt on node level. (This happens when 
          the primary RADIUS server is unavailable.)"
   ::= { ggsnApnStatsEntry 20 }

ggsnApnCompletedMSDeactivation OBJECT-TYPE
   SYNTAX        Counter64
   MAX-ACCESS    read-only
   STATUS        current
   DESCRIPTION
         "The number of successfully completed deactivation
          PDP context procedures initiated by the MS on a
          per APN basis of the GGSN."
   ::= { ggsnApnStatsEntry 21 }

ggsnApnActivePdpContextMax  OBJECT-TYPE
   SYNTAX        Gauge32
   MAX-ACCESS    read-only
   STATUS        current
   DESCRIPTION
         "The maximum number of PDP contexts that has been active at
          the same time for the APN."
   ::= { ggsnApnStatsEntry 22 }

ggsnApnActivePdpContextMean  OBJECT-TYPE
   SYNTAX        Gauge32
   MAX-ACCESS    read-only
   STATUS        current
   DESCRIPTION
         "The mean number of active PDP contexts active for the APN.
          The mean number is calculated with five samples taken over a 15 minute period."
   ::= { ggsnApnStatsEntry 23 }

ggsnApnAttemptedAuthActivation  OBJECT-TYPE
   SYNTAX        Counter64
   MAX-ACCESS    read-only
   STATUS        current
   DESCRIPTION
         "The total number of attempted session establishment with
	  user authentication required per APN of this GGSN."
   ::= { ggsnApnStatsEntry 24 }

ggsnApnFailedAuthActivation  OBJECT-TYPE
   SYNTAX        Counter64
   MAX-ACCESS    read-only
   STATUS        current
   DESCRIPTION
         "The total number of failed session establishment due to
	  user authentication failure, per APN of this GGSN."
   ::= { ggsnApnStatsEntry 25 }

ggsnApnAttemptedUpdateMsAndSgsn  OBJECT-TYPE
   SYNTAX        Counter64
   MAX-ACCESS    read-only
   STATUS        current
   DESCRIPTION
         "The total number of attempted PDP context updates, 
          initiated by a Mobile Station or an SGSN, per APN of this GGSN.
          
          Note: In some cases the information in the GTP message is not
          enough (missing or incorrect IE) to detect which APN the
          update is related to. If so, this update will fail and
          ggsnApnAttemptedUpdateMsAndSgsn will not be updated."
   ::= { ggsnApnStatsEntry 26 }

ggsnApnCompletedUpdateMsAndSgsn  OBJECT-TYPE
   SYNTAX        Counter64
   MAX-ACCESS    read-only
   STATUS        current
   DESCRIPTION
         "The total number of successfully completed PDP context
	  update initiated by MS or SGSN per APN of this GGSN."
   ::= { ggsnApnStatsEntry 27 }

ggsnApnNbrOfTftFilters  OBJECT-TYPE
    SYNTAX        Gauge32
   MAX-ACCESS    read-only
   STATUS        current
   DESCRIPTION
         "The current number of TFT filters in use per APN of this GGSN.
         
          Note: This counter cannot be retrieved by CLI."
   ::= { ggsnApnStatsEntry 28 }

ggsnApnSessTimeoutDeactivation  OBJECT-TYPE
   SYNTAX        Counter64
   MAX-ACCESS    read-only
   STATUS        current
   DESCRIPTION
         "The total number of PDP contexts deactivated per APN due to
          duration limit."
   ::= { ggsnApnStatsEntry 29 }

ggsnApnIdleTimeoutDeactivation  OBJECT-TYPE
   SYNTAX        Counter64
   MAX-ACCESS    read-only
   STATUS        current
   DESCRIPTION
         "The total number of PDP contexts deactivated per APN due to
          continuous idle time limit."
   ::= { ggsnApnStatsEntry 30 }

ggsnApnGiSignalingInPackets  OBJECT-TYPE
   SYNTAX        Counter64
   MAX-ACCESS    read-only
   STATUS        current
   DESCRIPTION
         "The number of incoming packets used for signaling purpose
	  on the Gi interface per APN of this GGSN."
   ::= { ggsnApnStatsEntry 31 }

ggsnApnGiSignalingInBytes  OBJECT-TYPE
   SYNTAX        Counter64
   MAX-ACCESS    read-only
   STATUS        current
   DESCRIPTION
         "The total number of bytes for incoming signaling packets
	  on the Gi interface per APN of this GGSN."
   ::= { ggsnApnStatsEntry 32 }

ggsnApnGiSignalingOutPackets  OBJECT-TYPE
   SYNTAX        Counter64
   MAX-ACCESS    read-only
   STATUS        current
   DESCRIPTION
         "The number of outgoing packets used for signaling purpose
	  on the Gi interface per APN of this GGSN."
   ::= { ggsnApnStatsEntry 33 }

ggsnApnGiSignalingOutBytes  OBJECT-TYPE
   SYNTAX        Counter64
   MAX-ACCESS    read-only
   STATUS        current
   DESCRIPTION
         "The total number of bytes for outgoing signaling packets
          on the Gi interface per APN of this GGSN."
   ::= { ggsnApnStatsEntry 34 }

ggsnApnActivePdpContextCountIpv6  OBJECT-TYPE
   SYNTAX        Gauge32
   MAX-ACCESS    read-only
   STATUS        current
   DESCRIPTION
         "The number of active IPv6 PDP contexts associated with
          the APN."
   ::= { ggsnApnStatsEntry 35 }

ggsnApnAttemptedActivationIpv6 OBJECT-TYPE
   SYNTAX        Counter64
   MAX-ACCESS    read-only
   STATUS        current
   DESCRIPTION
         "The total number of attempted IPv6 PDP context
          activations on a per APN basis."
   ::= { ggsnApnStatsEntry 36 }

ggsnApnCompletedActivationIpv6 OBJECT-TYPE
   SYNTAX        Counter64
   MAX-ACCESS    read-only
   STATUS        current
   DESCRIPTION
         "The total number of completed IPv6 PDP context
          activations on a per APN basis."
   ::= { ggsnApnStatsEntry 37 }

ggsnApnUplinkPacketsIpv6 OBJECT-TYPE
   SYNTAX        Counter64
   MAX-ACCESS    read-only
   STATUS        current
   DESCRIPTION
       "Total number of uplink Gn and S5 user plane IPv6 packets processed on a per APN basis processed by the GGSN or PGW. Incremented when an uplink IPv6 packet received over the Gn or S5 user plane interface is sent over Gi or SGi interface."
   ::= { ggsnApnStatsEntry 38 }

ggsnApnUplinkBytesIpv6 OBJECT-TYPE
   SYNTAX        Counter64
   MAX-ACCESS    read-only
   STATUS        current
   DESCRIPTION
       "Total number of uplink Gn and S5 user plane IPv6 bytes processed on a per APN basis by the GGSN or PGW. Incremented when an uplink IPv6 packet received over the Gn or S5 user plane interface is sent over Gi or SGi interface."
   ::= { ggsnApnStatsEntry 39 }

ggsnApnUplinkDropsIpv6 OBJECT-TYPE
   SYNTAX        Counter64
   MAX-ACCESS    read-only
   STATUS        current
   DESCRIPTION
       "Total number of uplink Gn and S5 user plane IPv6 packets dropped on a per APN basis by the GGSN or PGW. Incremented when an uplink packet received over the Gn or S5 user plane interface is dropped."
   ::= { ggsnApnStatsEntry 40 }

ggsnApnDownlinkPacketsIpv6 OBJECT-TYPE
   SYNTAX        Counter64
   MAX-ACCESS    read-only
   STATUS        current
   DESCRIPTION
       "Total number of downlink Gn and S5 user plane IPv6 bytes processed on a per APN basis by the GGSN or PGW. Incremented when a downlink IPv6 packet is sent over the Gn or S5 user plane interface."
   ::= { ggsnApnStatsEntry 41 }

ggsnApnDownlinkBytesIpv6 OBJECT-TYPE
   SYNTAX        Counter64
   MAX-ACCESS    read-only
   STATUS        current
   DESCRIPTION
       "Total number of downlink Gn and S5 user plane IPv6 bytes dropped on a per APN basis by the GGSN or PGW. Incremented when a downlink IPv6 packet is sent over the Gn or S5 user plane interface."
   ::= { ggsnApnStatsEntry 42 }

ggsnApnDownlinkDropsIpv6 OBJECT-TYPE
   SYNTAX        Counter64
   MAX-ACCESS    read-only
   STATUS        current
   DESCRIPTION
       "Total number of downlink Gn and S5 user plane IPv6 bytes dropped on a per APN basis by the GGSN or PGW. Incremented when a downlink IPv6 packet received over the Gi or SGi user plane interface is dropped."
   ::= { ggsnApnStatsEntry 43 }

ggsnApnNeighborSolicitationRcv  OBJECT-TYPE
   SYNTAX        Counter64
   MAX-ACCESS    read-only
   STATUS        current
   DESCRIPTION
         "The number of neighbor solicitation requests
          received by GGSN, per APN."
   ::= { ggsnApnStatsEntry 44 }

ggsnApnNeighborSolicitationRsp  OBJECT-TYPE
   SYNTAX        Counter64
   MAX-ACCESS    read-only
   STATUS        current
   DESCRIPTION
         "The number of neighbor solicitation responses
          from GGSN, per APN."
   ::= { ggsnApnStatsEntry 45 }

ggsnApnRouterSolicitationRcv  OBJECT-TYPE
   SYNTAX        Counter64
   MAX-ACCESS    read-only
   STATUS        current
   DESCRIPTION
         "The number of router solicitation requests
          received by GGSN, per APN."
   ::= { ggsnApnStatsEntry 46 }

ggsnApnRouterSolicitationRsp  OBJECT-TYPE
   SYNTAX        Counter64
   MAX-ACCESS    read-only
   STATUS        current
   DESCRIPTION
         "The number of router solicitation responses
          from GGSN, per APN."
   ::= { ggsnApnStatsEntry 47 }

ggsnNbApnActivePdpPerTrafficClassConversational  OBJECT-TYPE
   SYNTAX        Gauge32
   MAX-ACCESS    read-only
   STATUS        current
   DESCRIPTION
         "The number of active PDP contexts using traffic class conversational, per APN."
   ::= { ggsnApnStatsEntry 48 }

ggsnNbApnActivePdpPerTrafficClassStreaming  OBJECT-TYPE
   SYNTAX        Gauge32
   MAX-ACCESS    read-only
   STATUS        current
   DESCRIPTION
         "The number of active PDP contexts using traffic class streaming, per APN."
   ::= { ggsnApnStatsEntry 49 }

ggsnNbApnActivePdpPerTrafficClassInteractive  OBJECT-TYPE
   SYNTAX        Gauge32
   MAX-ACCESS    read-only
   STATUS        current
   DESCRIPTION
         "The number of active PDP contexts using traffic class interactive, per APN."
   ::= { ggsnApnStatsEntry 50 }

ggsnNbApnActivePdpPerTrafficClassBackground  OBJECT-TYPE
   SYNTAX        Gauge32
   MAX-ACCESS    read-only
   STATUS        current
   DESCRIPTION
         "The number of active PDP contexts using traffic class background, per APN."
   ::= { ggsnApnStatsEntry 51 }

ggsnApnImsDedicatedCompletedActivation  OBJECT-TYPE
   SYNTAX        Counter64
   MAX-ACCESS    read-only
   STATUS        current
   DESCRIPTION
         "The number of successful dedicated Signaling PDP-Context Activation requests per APN.
         
          Note: This counter cannot be retrieved by CLI."
   ::= { ggsnApnStatsEntry 52 }

ggsnApnImsDedicatedNotConfiguredActivationFailed  OBJECT-TYPE
   SYNTAX        Counter64
   MAX-ACCESS    read-only
   STATUS        current
   DESCRIPTION
         "The number of failed dedicated signaling PDP-Context Activation requests,
          due to the APN is turned OFF for Signaling PDP context Activation, per APN.
         
          Note: This counter cannot be retrieved by CLI."
   ::= { ggsnApnStatsEntry 53 }

 ggsnApnImsGeneralPurposeCompletedActivation  OBJECT-TYPE
   SYNTAX        Counter64
   MAX-ACCESS    read-only
   STATUS        current
   DESCRIPTION
         "The number of successful general purpose PDP-Context Activation requests per APN.
         
          Note: This counter cannot be retrieved by CLI."
   ::= { ggsnApnStatsEntry 54 }

ggsnApnImsGeneralNotConfiguredActivationFailed  OBJECT-TYPE
   SYNTAX        Counter64
   MAX-ACCESS    read-only
   STATUS        current
   DESCRIPTION
         "The number of failed general purpose PDP-Context Activation requests,
          due to the APN is turned OFF for general purpose PDP context Activation, per APN.
          
          Note: This counter cannot be retrieved by CLI."
   ::= { ggsnApnStatsEntry 55 }


ggsnApnActivationFailedDuetoGeneralPurposeNotConfigured  OBJECT-TYPE
   SYNTAX        Counter64
   MAX-ACCESS    read-only
   STATUS        current
   DESCRIPTION
         "The number of failed general purpose PDP-Context Activation requests where a normal PDP-Context is created, due to the APN is turned OFF for general purpose PDP context Activation."
   ::= { ggsnApnStatsEntry 56 }

ggsnApnUnauthorizedImsPackets  OBJECT-TYPE
   SYNTAX        Counter64
   MAX-ACCESS    read-only
   STATUS        current
   DESCRIPTION
         "The number of dropped unauthorized IMS signaling packets per APN."
   ::= { ggsnApnStatsEntry 57 }

ggsnApnRadiusAccountingFailure  OBJECT-TYPE
   SYNTAX        Counter64
   MAX-ACCESS    read-only
   STATUS        current
   DESCRIPTION
         "The number of failed RADIUS Accounting procedures per APN."
   ::= { ggsnApnStatsEntry 58 }

ggsnApnRadiusAuthenticationFailure  OBJECT-TYPE
   SYNTAX        Counter64
   MAX-ACCESS    read-only
   STATUS        current
   DESCRIPTION
         "The number of failed RADIUS Authentication procedures per APN."
   ::= { ggsnApnStatsEntry 59 }

ggsnApnSaccRsInstalledDynRules  OBJECT-TYPE
    SYNTAX       Gauge32
    MAX-ACCESS   read-only
    STATUS       current
    DESCRIPTION
		"Simultaneously installed dynamic charging rules."
    ::= { ggsnApnStatsEntry 60 }

ggsnApnSaccRsActivePredefinedChargingRules  OBJECT-TYPE
    SYNTAX       Gauge32
    MAX-ACCESS   read-only
    STATUS       current
    DESCRIPTION
		"Number of active pre-defined charging rules per APN."
    ::= { ggsnApnStatsEntry 61 }

ggsnApnSaccRsActivePredefinedChargingRuleBases  OBJECT-TYPE
    SYNTAX       Gauge32
    MAX-ACCESS   read-only
    STATUS       current
    DESCRIPTION
		"Number of active predefined charging rule bases per APN."
    ::= { ggsnApnStatsEntry 62 }

ggsnApnAvailableIpAddressesInInternalPool OBJECT-TYPE
    SYNTAX        Gauge32
    MAX-ACCESS    read-only
    STATUS        deprecated
    DESCRIPTION
        "Available IP-addresses in the Internal GGSN IP-address pool."
    ::= { ggsnApnStatsEntry 63 }

ggsnApnIpAddressesInQuarantineInInternalPool OBJECT-TYPE
    SYNTAX        Gauge32
    MAX-ACCESS    read-only
    STATUS        deprecated
    DESCRIPTION
        "IP-addresses in quarantine in Internal GGSN IP-address pool."
    ::= { ggsnApnStatsEntry 64 }

ggsnApn3gdtActiveContexts OBJECT-TYPE
    SYNTAX        Gauge32
    MAX-ACCESS    read-only
    STATUS        current
    DESCRIPTION
        "The current active 3GDT PDP contexts active in APN."
    ::= { ggsnApnStatsEntry 65}

ggsnApn3gdtTotalCompletedEstablishment OBJECT-TYPE
    SYNTAX        Gauge32
    MAX-ACCESS    read-only
    STATUS        deprecated
    DESCRIPTION
        "The total completed 3GDT active PDP contexts requests in APN."
    ::= { ggsnApnStatsEntry 66}

ggsnApn3gdtTotalAttemptedEstablishment OBJECT-TYPE
    SYNTAX        Gauge32
    MAX-ACCESS    read-only
    STATUS        deprecated
    DESCRIPTION
        "The total attempted 3GDT active PDP contexts requests in APN."
    ::= { ggsnApnStatsEntry 67}

ggsnApn3gdtErrorHandling OBJECT-TYPE
    SYNTAX        Gauge32
    MAX-ACCESS    read-only
    STATUS        deprecated
    DESCRIPTION
        "The number of error indications from RNC."
    ::= { ggsnApnStatsEntry 68}

ggsnApnAttemptedUpdateGgsn OBJECT-TYPE
    SYNTAX        Counter64
    MAX-ACCESS    read-only
    STATUS        current
    DESCRIPTION
        "The total number of attempted PDP context updates initiated by this GGSN on a per APN basis."
    ::= { ggsnApnStatsEntry 69}

ggsnApnCompletedUpdateGgsn OBJECT-TYPE
    SYNTAX        Counter64
    MAX-ACCESS    read-only
    STATUS        current
    DESCRIPTION
        "The total number of successful PDP context updates initiated by this GGSN on a per APN basis."
    ::= { ggsnApnStatsEntry 70}

ggsnApnAttemptedActivationNonDuplicated OBJECT-TYPE
   SYNTAX        Counter64
   MAX-ACCESS    read-only
   STATUS        current
   DESCRIPTION
         "The total number of non-duplicated PDP context activations on a per APN basis.
          
          Note: This counter cannot be retrieved by CLI."
   ::= { ggsnApnStatsEntry 71}

ggsnApnActivePdpContextMaxDuringLastPeriod OBJECT-TYPE
   SYNTAX        Gauge32
   MAX-ACCESS    read-only
   STATUS        current
   DESCRIPTION
         "The maximum number of PDP contexts that has been active at
          the same time for the APN during the last measurement period.
          
          Note: This counter cannot be retrieved by CLI."
   ::= { ggsnApnStatsEntry 72}

pgwApnActiveEpsBearer  OBJECT-TYPE
    SYNTAX      Gauge32
    MAX-ACCESS  read-only
    STATUS      current
    DESCRIPTION 
        "Total number of IPv4 and IPv6 EPS bearers associated with the APN by the PGW. Incremented when an EPS bearer is activated on this APN and a GTP response has been sent to the SGW. Decremented when entering the delete sequence."
    ::= { ggsnApnStatsEntry 73 }

pgwApnActiveIpv6EpsBearer  OBJECT-TYPE
    SYNTAX     Gauge32
    MAX-ACCESS read-only
    STATUS     current
    DESCRIPTION 
        "Total number of IPv6 EPS bearers associated with the APN by the PGW. Incremented when an EPS bearer is activated on this APN and a GTP response has been sent to the SGW. Decremented when entering the delete sequence."
    ::= { ggsnApnStatsEntry 74 }

pgwApnAttemptedEpsBearerActivation  OBJECT-TYPE
    SYNTAX     Counter64
    MAX-ACCESS read-only
    STATUS     current
    DESCRIPTION 
        "Total number of attempted IPv4 and IPv6 EPS Bearer activations for this APN. Incremented each time a Create EPS Bearer request is received by the PGW, even when the request is silently discarded."
    ::= { ggsnApnStatsEntry 75 }

pgwApnCompletedEpsBearerActivation  OBJECT-TYPE
    SYNTAX     Counter64
    MAX-ACCESS read-only
    STATUS     current
    DESCRIPTION 
        "Total number of completed IPv4 and IPv6 EPS Bearer activations for this APN. Incremented when an EPS bearer is successfully activated."
    ::= { ggsnApnStatsEntry 76 }

pgwApnAttemptedIpv6EpsBearerActivation  OBJECT-TYPE
    SYNTAX     Counter64
    MAX-ACCESS read-only
    STATUS     current
    DESCRIPTION 
        "Total number of EPS bearer activation attempts with the APN by the PGW. Incremented each time a Create EPS Bearer request that is not silently discarded is received by the PGW. This means the counter is incremented each time a create EPS Bearer response is sent back to the SGW with cause value Request Accepted or with a reject value."
    ::= { ggsnApnStatsEntry 77 }

pgwApnCompletedIpv6EpsBearerActivation  OBJECT-TYPE
    SYNTAX     Counter64
    MAX-ACCESS read-only
    STATUS     current
    DESCRIPTION 
        "Total number of IPv6 EPS bearers associated with the APN by the PGW.  Incremented when an EPS bearer is successfully activated."
    ::= { ggsnApnStatsEntry 78 }

pgwApnAttemptedEpsBearerDeactivation  OBJECT-TYPE
    SYNTAX     Counter64
    MAX-ACCESS read-only
    STATUS     current
    DESCRIPTION 
        "Total number of attempted IPv4 and IPv6 EPS Bearer deactivations for this APN. Incremented when a deactivation is triggered by the PGW, triggered by the UE/SGW, rejected deactivation requests and silently discarded deactivation requests."
    ::= { ggsnApnStatsEntry 79 }

pgwApnCompletedEpsBearerDeactivation  OBJECT-TYPE
    SYNTAX     Counter64
    MAX-ACCESS read-only
    STATUS     current
    DESCRIPTION 
        "Total number of IPv4 and IPv6 EPS bearer deactivations associated with the APN by the PGW. Incremented both for successful PGW triggered deactivations and successful UE/SGW triggered deactivations."
    ::= { ggsnApnStatsEntry 80 }

pgwApnAttemptedS5NetworkDeactivation  OBJECT-TYPE
    SYNTAX     Counter64
    MAX-ACCESS read-only
    STATUS     current
    DESCRIPTION 
        "Total number of attempted IPv4 and IPv6 EPS bearer deactivations for this APN. Incremented when a deactivation is triggered by the PGW."
    ::= { ggsnApnStatsEntry 81 }

pgwApnCompletedS5NetworkDeactivation  OBJECT-TYPE
    SYNTAX     Counter64
    MAX-ACCESS read-only
    STATUS     current
    DESCRIPTION 
        "Total number of completed IPv4 and IPv6 EPS bearer deactivations for this APN. Incremented for successful PGW triggered deactivations over the S5 interface"
    ::= { ggsnApnStatsEntry 82 }

pgwApnAttemptedS5UeSgwModification  OBJECT-TYPE
    SYNTAX     Counter64
    MAX-ACCESS read-only
    STATUS     current
    DESCRIPTION 
        "Total number of attempted UE/SGW initiated EPS bearer modifications (excluding modifications due to IRAT mobility from GERAN/UTRAN via SGSN using Gn/Gp to E-UTRAN)  including IPv6 EPS bearers. Attempted EPS bearer modifications include silently discarded modifications and retries of attempted modifications. Incremented at attempted UE/SGW initiated EPS bearer modifications including silently discarded modifications and retries of modifications."
    ::= { ggsnApnStatsEntry 83 }

pgwApnCompletedS5UeSgwModification  OBJECT-TYPE
    SYNTAX     Counter64
    MAX-ACCESS read-only
    STATUS     current
    DESCRIPTION 
        "Total number of successful UE/SGW initiated EPS bearer modifications (excluding modifications due to IRAT mobility from GERAN/UTRAN via SGSN using Gn/Gp to E-UTRAN) including IPv6 EPS bearers. Incremented when an UE/SGW initiated EPS bearer modification is successful."
    ::= { ggsnApnStatsEntry 84 }

pgwApnAttemptedS5SgwSgsnModification  OBJECT-TYPE
    SYNTAX     Counter64
    MAX-ACCESS read-only
    STATUS     current
    DESCRIPTION 
        "Total number of attempted SGW to SGSN initiated EPS bearer modifications including IPv6 EPS bearers. Attempted EPS bearer modifications include silently discarded modifications and retries of attempted modifications. Incremented at attempted SGW to SGSN initiated EPS bearer modifications including silently discarded modifications and retries of modifications."
    ::= { ggsnApnStatsEntry 85 }

pgwApnCompletedS5SgwSgsnModification  OBJECT-TYPE
    SYNTAX     Counter64
    MAX-ACCESS read-only
    STATUS     current
    DESCRIPTION 
        "Total number of successful SGW to SGSN initiated EPS bearer modifications including IPv6 EPS bearers. Incremented when an SGW to SGSN initiated EPS bearer modification is successful."
    ::= { ggsnApnStatsEntry 86 }

pgwApnAttemptedS5SgsnSgwModification  OBJECT-TYPE
    SYNTAX     Counter64
    MAX-ACCESS read-only
    STATUS     current
    DESCRIPTION 
        "Total number of attempted SGSN to SGW initiated EPS bearer modifications including IPv6 EPS bearers. Incremented at attempted SGSN to SGW initiated EPS bearer modifications including silently discarded modifications and retries of modifications."
    ::= { ggsnApnStatsEntry 87 }

pgwApnCompletedS5SgsnSgwModification  OBJECT-TYPE
    SYNTAX     Counter64
    MAX-ACCESS read-only
    STATUS     current
    DESCRIPTION 
        "Total number of successful SGSN to SGW initiated EPS bearer modifications including IPv6 EPS bearers. Incremented when an SGSN to SGW initiated EPS bearer modification is successful."
    ::= { ggsnApnStatsEntry 88 }

pgwApnAttemptedS5NetworkModification  OBJECT-TYPE
    SYNTAX     Counter64
    MAX-ACCESS read-only
    STATUS     current
    DESCRIPTION 
        "Total number of attempted network initiated EPS bearer modifications over the S5 interface including IPv6 EPS bearers. Incremented at attempted network initiated EPS bearer modifications over the S5 interface including silently discarded modifications and retries of modifications."
    ::= { ggsnApnStatsEntry 89 }

pgwApnCompletedS5NetworkModification  OBJECT-TYPE
    SYNTAX     Counter64
    MAX-ACCESS read-only
    STATUS     current
    DESCRIPTION 
        "Total number of successful network initiated EPS bearer modifications over the S5 interface including IPv6 EPS bearers. Incremented when a network initiated EPS bearer modification over the S5 interface is successful."
    ::= { ggsnApnStatsEntry 90 }

pgwApnAttemptedS5UeSgwDeactivation  OBJECT-TYPE
    SYNTAX     Counter64
    MAX-ACCESS read-only
    STATUS     current
    DESCRIPTION 
        "Total number of attempted UE/SGW triggered EPS bearer deactivations including IPv6 EPS bearers over the S5 interface associated with this APN. Incremented when an UE/SGW triggered EPS bearer is deactivated over the S5 interface."
    ::= { ggsnApnStatsEntry 91 }

pgwApnCompletedS5UeSgwDeactivation  OBJECT-TYPE
    SYNTAX     Counter64
    MAX-ACCESS read-only
    STATUS     current
    DESCRIPTION 
        "Total number of successful UE/SGW triggered EPS bearer deactivations including IPv6 EPS bearers over the S5 interface associated with this APN. Incremented when an UE/SGW triggered EPS bearer is successfully deactivated over the S5 interface."
    ::= { ggsnApnStatsEntry 92 }

gnApnUplinkPackets  OBJECT-TYPE
    SYNTAX     Counter64
    MAX-ACCESS read-only
    STATUS     current
    DESCRIPTION 
        "Total number of uplink Gn user plane packets processed on a per APN basis by the GGSN or PGW. Incremented when an uplink packet received over the Gn user plane interface is sent over Gi or SGi interface."
    ::= { ggsnApnStatsEntry 93 }

gnApnUplinkBytes  OBJECT-TYPE
    SYNTAX     Counter64
    MAX-ACCESS read-only
    STATUS     current
    DESCRIPTION 
        "Total number of uplink Gn user plane bytes processed on a per APN basis by the GGSN or PGW. Incremented when an uplink packet received over the Gn user plane interface is sent over Gi or SGi interface."
    ::= { ggsnApnStatsEntry 94 }

gnApnUplinkPacketsIpv6   OBJECT-TYPE
    SYNTAX     Counter64
    MAX-ACCESS read-only
    STATUS     current
    DESCRIPTION 
        "Total number of uplink Gn user plane IPv6 packets processed on a per APN basis by the GGSN or PGW. Incremented when an uplink IPv6 packet received over the Gn user plane interface is sent over Gi or SGi interface."
    ::= { ggsnApnStatsEntry 95 }

gnApnUplinkBytesIpv6  OBJECT-TYPE
    SYNTAX     Counter64
    MAX-ACCESS read-only
    STATUS     current
    DESCRIPTION 
        "Total number of uplink Gn user plane IPv6 bytes processed on a per APN basis by the GGSN or PGW. Incremented when an uplink IPv6 packet received over the Gn user plane interface is sent over Gi or SGi interface."
    ::= { ggsnApnStatsEntry 96 }

gnApnDownlinkPackets  OBJECT-TYPE
    SYNTAX     Counter64
    MAX-ACCESS read-only
    STATUS     current
    DESCRIPTION 
        "Total number of downlink Gn user plane packets processed on a per APN basis by the GGSN or PGW. Incremented when a downlink packet is sent over the Gn user plane interface."
    ::= { ggsnApnStatsEntry 97 }

gnApnDownlinkBytes  OBJECT-TYPE
    SYNTAX     Counter64
    MAX-ACCESS read-only
    STATUS     current
    DESCRIPTION 
        "Total number of downlink Gn user plane bytes processed on a per APN basis by the GGSN or PGW. Incremented when a downlink packet is sent over the Gn user plane interface."
    ::= { ggsnApnStatsEntry 98 }

gnApnDownlinkPacketsIpv6  OBJECT-TYPE
    SYNTAX     Counter64
    MAX-ACCESS read-only
    STATUS     current
    DESCRIPTION 
        "Total number of downlink Gn user plane IPv6 packets processed on a per APN basis by the GGSN or PGW. Incremented when a downlink IPv6 packet is sent over the Gn user plane interface."
    ::= { ggsnApnStatsEntry 99 }

gnApnDownlinkBytesIpv6  OBJECT-TYPE
    SYNTAX     Counter64
    MAX-ACCESS read-only
    STATUS     current
    DESCRIPTION 
        "Total number of downlink Gn user plane IPv6 bytes processed on a per APN basis by the GGSN or PGW. Incremented when a downlink IPv6 packet is sent over the Gn user plane interface."
    ::= { ggsnApnStatsEntry 100 }

s5ApnUplinkPackets  OBJECT-TYPE
    SYNTAX     Counter64
    MAX-ACCESS read-only
    STATUS     current
    DESCRIPTION 
        "Total number of uplink S5 user plane packets processed on a per APN basis by the GGSN or PGW. Incremented when an uplink packet, received over the S5 user plane interface, is sent over Gi or SGi interface."
    ::= { ggsnApnStatsEntry 101 }

s5ApnUplinkBytes  OBJECT-TYPE
    SYNTAX     Counter64
    MAX-ACCESS read-only
    STATUS     current
    DESCRIPTION 
        "Total number of uplink S5 user plane bytes processed on a per APN basis by the GGSN or PGW. Incremented when an uplink packet, received over the S5 user plane interface, is sent over Gi or SGi interface."
    ::= { ggsnApnStatsEntry 102 }

s5ApnUplinkPacketsIpv6  OBJECT-TYPE
    SYNTAX     Counter64
    MAX-ACCESS read-only
    STATUS     current
    DESCRIPTION 
        "Total number of uplink S5 user plane IPv6 packets processed on a per APN basis by the GGSN or PGW. Incremented when an uplink IPv6 packet received over the S5 user plane interface is sent over Gi or SGi interface."
    ::= { ggsnApnStatsEntry 103 }

s5ApnUplinkBytesIpv6  OBJECT-TYPE
    SYNTAX     Counter64
    MAX-ACCESS read-only
    STATUS     current
    DESCRIPTION 
        "Total number of uplink S5 user plane IPv6 bytes processed on a per APN basis by the GGSN or PGW. Incremented when an uplink IPv6 packet received over the S5 user plane interface is sent over Gi or SGi interface."
    ::= { ggsnApnStatsEntry 104 }

s5ApnDownlinkPackets  OBJECT-TYPE
    SYNTAX     Counter64
    MAX-ACCESS read-only
    STATUS     current
    DESCRIPTION 
        "Total number of downlink S5 user plane packets processed on a per APN basis by the GGSN or PGW. Incremented when a downlink packet is sent over the S5 user plane interface."
    ::= { ggsnApnStatsEntry 105 }

s5ApnDownlinkBytes  OBJECT-TYPE
    SYNTAX     Counter64
    MAX-ACCESS read-only
    STATUS     current
    DESCRIPTION 
        "Total number of downlink S5 user plane bytes processed on a per APN basis by the GGSN or PGW. Incremented when a downlink packet is sent over the S5 user plane interface."
    ::= { ggsnApnStatsEntry 106 }

s5ApnDownlinkPacketsIpv6  OBJECT-TYPE
    SYNTAX     Counter64
    MAX-ACCESS read-only
    STATUS     current
    DESCRIPTION 
        "Total number of downlink S5 user plane IPv6 packets processed on a per APN basis by the GGSN or PGW. Incremented when a downlink IPv6 packet is sent over the S5 user plane interface."
    ::= { ggsnApnStatsEntry 107 }

s5ApnDownlinkBytesIpv6  OBJECT-TYPE
    SYNTAX     Counter64
    MAX-ACCESS read-only
    STATUS     current
    DESCRIPTION 
        "Total number of downlink S5 user plane IPv6 bytes processed on a per APN basis by the GGSN or PGW. Incremented when a downlink IPv6 packet is sent over the S5 user plane interface."
    ::= { ggsnApnStatsEntry 108 }

gnApn3gdtUplinkBytes  OBJECT-TYPE
    SYNTAX     Counter64
    MAX-ACCESS read-only
    STATUS     current
    DESCRIPTION 
        "Total number of uplink Gn user plane IPv4 and IPv6 bytes that are contained in packets which are associated with 3GDT contexts. Incremented by the GGSN or PGW per APN when these packets are received from the RNC."
    ::= { ggsnApnStatsEntry 109 }

gnApn3gdtUplinkBytesIpv6  OBJECT-TYPE
    SYNTAX     Counter64
    MAX-ACCESS read-only
    STATUS     current
    DESCRIPTION 
        "Total number of uplink Gn user plane IPv6 bytes that are contained in packets which are associated with 3GDT contexts. Incremented by the GGSN or PGW per APN when these packets are received from the RNC."
    ::= { ggsnApnStatsEntry 110 }

gnApn3gdtUplinkPackets  OBJECT-TYPE
    SYNTAX     Counter64
    MAX-ACCESS read-only
    STATUS     current
    DESCRIPTION 
        "Total number of uplink Gn user plane IPv4 and IPv6 packets that are associated with 3GDT contexts. Incremented by 1 by the GGSN or PGW per APN when each of these packets is received from the RNC."
    ::= { ggsnApnStatsEntry 111 }

gnApn3gdtUplinkPacketsIpv6  OBJECT-TYPE
    SYNTAX     Counter64
    MAX-ACCESS read-only
    STATUS     current
    DESCRIPTION 
        "Total number of uplink Gn user plane IPv6 packets that are associated with 3GDT contexts. Incremented by 1 by the GGSN or PGW per APN when each of these packets is received from the RNC."
    ::= { ggsnApnStatsEntry 112 }

gnApn3gdtDownlinkBytes  OBJECT-TYPE
    SYNTAX     Counter64
    MAX-ACCESS read-only
    STATUS     current
    DESCRIPTION 
        "Total number of downlink Gn user plane IPv4 and IPv6 bytes that are contained in packets which are associated with 3GDT contexts. Incremented by the GGSN or PGW per APN when these packets are received from the PDN."
    ::= { ggsnApnStatsEntry 113 }

gnApn3gdtDownlinkBytesIpv6  OBJECT-TYPE
    SYNTAX     Counter64
    MAX-ACCESS read-only
    STATUS     current
    DESCRIPTION 
        "Total number of downlink Gn user plane IPv6 bytes that are contained in packets which are associated with 3GDT contexts. Incremented by the GGSN or PGW per APN when these packets are received from the PDN."
    ::= { ggsnApnStatsEntry 114 }

gnApn3gdtDownlinkPackets  OBJECT-TYPE
    SYNTAX     Counter64
    MAX-ACCESS read-only
    STATUS     current
    DESCRIPTION 
        "Total number of downlink Gn user plane IPv4 and IPv6 packets that are associated with 3GDT contexts. Incremented by 1 by the GGSN or PGW per APN when each of these packets is received from the PDN."
    ::= { ggsnApnStatsEntry 115 }

gnApn3gdtDownlinkPacketsIpv6  OBJECT-TYPE
    SYNTAX     Counter64
    MAX-ACCESS read-only
    STATUS     current
    DESCRIPTION 
        "Total number of downlink Gn user plane IPv6 packets that are associated with 3GDT contexts. Incremented by 1 by the GGSN or PGW per APN when each of these packets is received from the PDN."
    ::= { ggsnApnStatsEntry 116 }

gnApn3gdtDownlinkDropsErrorHandling  OBJECT-TYPE
    SYNTAX     Counter64
    MAX-ACCESS read-only
    STATUS     current
    DESCRIPTION 
        "The total number of downlink Gn user plane IPv4 and IPv6 packets that are dropped after the RNC sends to the GGSN an error indication message that is associated with a 3GDT tunnel. Incremented by 1 when each of these packets is dropped."
    ::= { ggsnApnStatsEntry 117 }

ggsnApn3gdtGtpError  OBJECT-TYPE
    SYNTAX     Counter64
    MAX-ACCESS read-only
    STATUS     current
    DESCRIPTION 
        "The number of occurrences when Update PDP Context Request/Response messages contain missing or incorrect IE values during a change of tunnel type from GTP to DT or vice versa. Specifically, the values for the SGSN-U or the TEID IEs."
    ::= { ggsnApnStatsEntry 118 }

gnApn3gdtTotalCompletedEstablishment OBJECT-TYPE
    SYNTAX        Counter32
    MAX-ACCESS    read-only
    STATUS        current
    DESCRIPTION
        "The total completed 3GDT active PDP contexts requests in APN."
    ::= { ggsnApnStatsEntry 119}

gnApn3gdtTotalAttemptedEstablishment OBJECT-TYPE
    SYNTAX        Counter32
    MAX-ACCESS    read-only
    STATUS        current
    DESCRIPTION
        "The total attempted 3GDT active PDP contexts requests in APN."
    ::= { ggsnApnStatsEntry 120}

gnApn3gdtErrorHandling OBJECT-TYPE
    SYNTAX        Counter32
    MAX-ACCESS    read-only
    STATUS        current
    DESCRIPTION
        "The number of error indications from RNC."
    ::= { ggsnApnStatsEntry 121}

pgwApnActiveDedicatedEpsBearer  OBJECT-TYPE
    SYNTAX     Gauge32
    MAX-ACCESS read-only
    STATUS     current
    DESCRIPTION 
        "Total number of IPv4 and IPv6 dedicated EPS bearers associated with the APN by the PGW. Incremented when a dedicated EPS bearer is activated on this APN and a GTP response has been sent to the SGW. Decremented when entering the delete sequence."
    ::= { ggsnApnStatsEntry 122 }

pgwApnAttemptedDedicatedEpsBearerActivation  OBJECT-TYPE
    SYNTAX     Counter64
    MAX-ACCESS read-only
    STATUS     current
    DESCRIPTION 
        "Total number of attempted IPv4 and IPv6 dedicated EPS Bearer activations for this APN. Incremented each time a Create dedicated EPS Bearer request is received by the PGW, even when the request is silently discarded."
    ::= { ggsnApnStatsEntry 123 }

pgwApnCompletedDedicatedEpsBearerActivation  OBJECT-TYPE
    SYNTAX     Counter64
    MAX-ACCESS read-only
    STATUS     current
    DESCRIPTION 
        "Total number of completed IPv4 and IPv6 dedicated EPS Bearer activations for this APN. Incremented when a dedicated EPS bearer is successfully activated."
    ::= { ggsnApnStatsEntry 124 }

pgwApnAttemptedIpv6DedicatedEpsBearerActivation  OBJECT-TYPE
    SYNTAX     Counter64
    MAX-ACCESS read-only
    STATUS     current
    DESCRIPTION 
        "Total number of dedicated EPS bearer activation attempts with the APN by the PGW. Incremented each time a Create dedicated EPS Bearer request that is not silently discarded is received by the PGW. This means the counter is incremented each time a create dedicated EPS Bearer response is sent back to the SGW with cause value Request Accepted or with a reject value."
    ::= { ggsnApnStatsEntry 125 }

pgwApnCompletedIpv6DedicatedEpsBearerActivation  OBJECT-TYPE
    SYNTAX     Counter64
    MAX-ACCESS read-only
    STATUS     current
    DESCRIPTION 
        "Total number of IPv6 dedicated EPS bearers associated with the APN by the PGW. Incremented when a dedicated EPS bearer is successfully activated."
    ::= { ggsnApnStatsEntry 126 }

pgwApnAttemptedS5NetworkDedicatedEpsBearerDeactivation  OBJECT-TYPE
    SYNTAX     Counter64
    MAX-ACCESS read-only
    STATUS     current
    DESCRIPTION 
        "Total number of attempted IPv4 and IPv6 EPS dedicated bearer deactivations for this APN. Incremented when a dedicated EPS bearer is deactivated over the S5 interface."
    ::= { ggsnApnStatsEntry 127 }

pgwApnCompletedS5NetworkDedicatedEpsBearerDeactivation  OBJECT-TYPE
    SYNTAX     Counter64
    MAX-ACCESS read-only
    STATUS     current
    DESCRIPTION 
        "Total number of completed IPv4 and IPv6 dedicated EPS bearer deactivations for this APN. Incremented when a dedicated EPS bearer is successfully deactivated over the S5 interface."
    ::= { ggsnApnStatsEntry 128 }

pgwApnAttemptedS5NetworkDedicatedEpsBearerModification  OBJECT-TYPE
    SYNTAX     Counter64
    MAX-ACCESS read-only
    STATUS     current
    DESCRIPTION 
        "Total number of attempted network initiated dedicated EPS bearer modifications over the S5 interface including IPv6 EPS bearers. Incremented at attempted network initiated dedicated EPS bearer modifications over the S5 interface including silently discarded modifications and retries of modifications."
    ::= { ggsnApnStatsEntry 129 }

pgwApnCompletedS5NetworkDedicatedEpsBearerModification  OBJECT-TYPE
    SYNTAX     Counter64
    MAX-ACCESS read-only
    STATUS     current
    DESCRIPTION 
        "Total number of successful network initiated dedicated EPS bearer modifications over the S5 interface including IPv6 EPS bearers. Incremented when a network initiated dedicated EPS bearer modification over the S5 interface is successful."
    ::= { ggsnApnStatsEntry 130 }

pgwApnAttemptedS5UeSgwDedicatedEpsBearerDeactivation  OBJECT-TYPE
    SYNTAX     Counter64
    MAX-ACCESS read-only
    STATUS     current
    DESCRIPTION 
        "Total number of attempted UE/SGW triggered dedicated EPS bearer deactivations including IPv6 EPS bearers over the S5 interface associated with this APN. Incremented when an UE/SGW triggered dedicated EPS bearer is deactivated over the S5 interface."
    ::= { ggsnApnStatsEntry 131 }

pgwApnCompletedS5UeSgwDedicatedEpsBearerDeactivation  OBJECT-TYPE
    SYNTAX     Counter64
    MAX-ACCESS read-only
    STATUS     current
    DESCRIPTION 
        "Total number of successful UE/SGW triggered dedicated EPS bearer deactivations including IPv6 EPS bearers over the S5 interface associated with this APN. Incremented when an UE/SGW triggered dedicated EPS bearer is successfully deactivated over the S5 interface."
    ::= { ggsnApnStatsEntry 132 }

ggsnApnActivePdpContextCountIpv4v6  OBJECT-TYPE
   SYNTAX        Gauge32
   MAX-ACCESS    read-only
   STATUS        current
   DESCRIPTION
         "The number of active IPv4v6 PDP contexts associated with
          the APN."
   ::= { ggsnApnStatsEntry 133 }

pgwApnActiveIpv4v6EpsBearer  OBJECT-TYPE
    SYNTAX     Gauge32
    MAX-ACCESS read-only
    STATUS     current
    DESCRIPTION 
        "Total number of IPv4v6 EPS bearers associated with the APN by the PGW. Incremented when an EPS bearer is activated on this APN and a GTP response has been sent to the SGW. Decremented when entering the delete sequence."
    ::= { ggsnApnStatsEntry 134 }

ggsnApnAttemptedActivationIpv4v6  OBJECT-TYPE
   SYNTAX        Counter64
   MAX-ACCESS    read-only
   STATUS        current
   DESCRIPTION
         "The total number of attempted IPv4v6 PDP context
          activations on a per APN basis."
   ::= { ggsnApnStatsEntry 135 }

ggsnApnCompletedActivationIpv4v6  OBJECT-TYPE
   SYNTAX        Counter64
   MAX-ACCESS    read-only
   STATUS        current
   DESCRIPTION
         "The total number of completed IPv4v6 PDP context
          activations on a per APN basis."
   ::= { ggsnApnStatsEntry 136 }

pgwApnAttemptedIpv4v6EpsBearerActivation  OBJECT-TYPE
    SYNTAX     Counter64
    MAX-ACCESS read-only
    STATUS     current
    DESCRIPTION
        "Total number of attempted IPv4v6 EPS Bearer activations for this APN. Incremented each time a Create EPS Bearer request is received by the PGW, even when the request is silently discarded."

    ::= { ggsnApnStatsEntry 137 }

pgwApnCompletedIpv4v6EpsBearerActivation  OBJECT-TYPE
    SYNTAX     Counter64
    MAX-ACCESS read-only
    STATUS     current
    DESCRIPTION
        "Total number of completed IPv4v6 EPS Bearer activations for this APN. Incremented when an EPS bearer is successfully activated."
    ::= { ggsnApnStatsEntry 138 }

pgwApnActiveWlanEpsBearer OBJECT-TYPE
    SYNTAX     Gauge32
    MAX-ACCESS read-only
    STATUS     current
    DESCRIPTION
        "Total number of EPS bearers for WLAN associated with this APN on this PGW."
    ::= { ggsnApnStatsEntry 139 }

s2aApnUplinkPackets OBJECT-TYPE
    SYNTAX     Counter64 
    MAX-ACCESS read-only
    STATUS     current
    DESCRIPTION
        "Total number of uplink user plane packets processed by PGW over S2a interface on the APN."
    ::= { ggsnApnStatsEntry 140 }    
                 
s2aApnUplinkBytes OBJECT-TYPE
    SYNTAX     Counter64
    MAX-ACCESS read-only
    STATUS     current
    DESCRIPTION
        "Total number of uplink user plane bytes processed by PGW over S2a interface on the APN."
    ::= { ggsnApnStatsEntry 141 }  
                                      
s2aApnDownlinkPackets OBJECT-TYPE
    SYNTAX     Counter64
    MAX-ACCESS read-only
    STATUS     current
    DESCRIPTION
        "Total number of downlink user plane packets processed by PGW over S2a interface on the APN."
    ::= { ggsnApnStatsEntry 142 }  
                                  
s2aApnDownlinkBytes OBJECT-TYPE
    SYNTAX     Counter64
    MAX-ACCESS read-only
    STATUS     current
    DESCRIPTION
        "Total number of downlink user plane bytes processed by PGW over S2a interface on the APN."
    ::= { ggsnApnStatsEntry 143 }  

s2aApnUplinkPacketsIpv6 OBJECT-TYPE
    SYNTAX     Counter64 
    MAX-ACCESS read-only
    STATUS     deprecated
    DESCRIPTION
        "Total number of uplink user plane packets processed by PGW over S2a interface on the APN."
    ::= { ggsnApnStatsEntry 144 }    
                 
s2aApnUplinkBytesIpv6 OBJECT-TYPE
    SYNTAX     Counter64
    MAX-ACCESS read-only
    STATUS     deprecated
    DESCRIPTION
        "Total number of uplink user plane bytes processed by PGW over S2a interface on the APN."
    ::= { ggsnApnStatsEntry 145 }  
                                      
s2aApnDownlinkPacketsIpv6 OBJECT-TYPE
    SYNTAX     Counter64
    MAX-ACCESS read-only
    STATUS     deprecated
    DESCRIPTION
        "Total number of downlink user plane packets processed by PGW over S2a interface on the APN."
    ::= { ggsnApnStatsEntry 146 }  
                                  
s2aApnDownlinkBytesIpv6 OBJECT-TYPE
    SYNTAX     Counter64
    MAX-ACCESS read-only
    STATUS     deprecated
    DESCRIPTION
        "Total number of downlink user plane bytes processed by PGW over S2a interface on the APN."
    ::= { ggsnApnStatsEntry 147 }  

--
-- GGSN APN RADIUS AUTH SERVER Statistics
--

ggsnApnRadiusAuthServersStatsTable OBJECT-TYPE
   SYNTAX        SEQUENCE OF GgsnApnRadiusAuthServersStatsEntry
   MAX-ACCESS    not-accessible
   STATUS        current
   DESCRIPTION
         "A table listing the statistics for all RADIUS servers for this APN."
   ::= { ggsnRadiusInfo 1 }

ggsnApnRadiusAuthServersStatsEntry OBJECT-TYPE
   SYNTAX        GgsnApnRadiusAuthServersStatsEntry
   MAX-ACCESS    not-accessible
   STATUS        current
   DESCRIPTION
         "A conceptual row listing the statistics for each
          APN which is served by this GGSN."
   INDEX         { ggsnApnIndex, ggsnApnRadiusAuthServerIndex }
   ::= { ggsnApnRadiusAuthServersStatsTable 1 }

GgsnApnRadiusAuthServersStatsEntry ::= SEQUENCE {
   ggsnApnRadiusAuthServerIndex                         Integer32,
   ggsnApnRadiusAuthServerIpAddress                     IpAddress,
   ggsnApnRadiusAuthServerAccessRequests                Counter64,
   ggsnApnRadiusAuthServerAccessAccepts                 Counter64,
   ggsnApnRadiusAuthServerAccessRejects                 Counter64,
   ggsnApnRadiusAuthServerAccessRequestTimeouts         Counter64,
   ggsnApnRadiusAuthServerAccessRequestRetransmits      Counter64,
   ggsnApnRadiusAuthServerInvalidAuthenticators         Counter64
}

ggsnApnRadiusAuthServerIndex OBJECT-TYPE
   SYNTAX        Integer32 (1..2147483647)
   MAX-ACCESS    not-accessible
   STATUS        current
   DESCRIPTION
         "A number representing each RADIUS authentication server."
   ::= { ggsnApnRadiusAuthServersStatsEntry 1 }

ggsnApnRadiusAuthServerIpAddress OBJECT-TYPE
   SYNTAX        IpAddress
   MAX-ACCESS    read-only
   STATUS        current
   DESCRIPTION   "RADIUS authentication server IP-address."
   ::= { ggsnApnRadiusAuthServersStatsEntry 2 }

ggsnApnRadiusAuthServerAccessRequests OBJECT-TYPE
   SYNTAX        Counter64
   MAX-ACCESS    read-only
   STATUS        current
   DESCRIPTION   "Number of ACCESS REQUESTS sent to the RADIUS authentication server for this APN."
   ::= { ggsnApnRadiusAuthServersStatsEntry 3 }

ggsnApnRadiusAuthServerAccessAccepts OBJECT-TYPE
   SYNTAX        Counter64
   MAX-ACCESS    read-only
   STATUS        current
   DESCRIPTION   "Number of ACCESS ACCEPTS received from the RADIUS authentication server for this APN."
   ::= { ggsnApnRadiusAuthServersStatsEntry 4 }

ggsnApnRadiusAuthServerAccessRejects OBJECT-TYPE
   SYNTAX        Counter64
   MAX-ACCESS    read-only
   STATUS        current
   DESCRIPTION   "Number of ACCESS REJECTS received from the RADIUS authentication server for this APN."
   ::= { ggsnApnRadiusAuthServersStatsEntry 5 }

ggsnApnRadiusAuthServerAccessRequestTimeouts OBJECT-TYPE
   SYNTAX        Counter64
   MAX-ACCESS    read-only
   STATUS        current
   DESCRIPTION   "Number of timed out ACCESS REQUESTS sent to the RADIUS authentication server for this APN."
   ::= { ggsnApnRadiusAuthServersStatsEntry 6 }

ggsnApnRadiusAuthServerAccessRequestRetransmits OBJECT-TYPE
   SYNTAX        Counter64
   MAX-ACCESS    read-only
   STATUS        current
   DESCRIPTION   "Number of ACCESS REQUESTS retransmitted to the RADIUS authentication server for this APN."
   ::= { ggsnApnRadiusAuthServersStatsEntry 7 }

ggsnApnRadiusAuthServerInvalidAuthenticators OBJECT-TYPE
   SYNTAX        Counter64
   MAX-ACCESS    read-only
   STATUS        current
   DESCRIPTION   "Number of invalid authenticators received from the RADIUS authentication server for this APN."
   ::= { ggsnApnRadiusAuthServersStatsEntry 8 }

--
-- GGSN APN RADIUS ACCT SERVER Statistics
--

ggsnApnRadiusAcctServersStatsTable OBJECT-TYPE
   SYNTAX        SEQUENCE OF GgsnApnRadiusAcctServersStatsEntry
   MAX-ACCESS    not-accessible
   STATUS        current
   DESCRIPTION
         "A table listing the statistics for all RADIUS servers for this APN."
   ::= { ggsnRadiusInfo 2 }

ggsnApnRadiusAcctServersStatsEntry OBJECT-TYPE
   SYNTAX        GgsnApnRadiusAcctServersStatsEntry
   MAX-ACCESS    not-accessible
   STATUS        current
   DESCRIPTION
         "A conceptual row listing the statistics for each
          APN which is served by this GGSN."
   INDEX         { ggsnApnIndex, ggsnApnRadiusAcctServerIndex }
   ::= { ggsnApnRadiusAcctServersStatsTable 1 }

GgsnApnRadiusAcctServersStatsEntry ::= SEQUENCE {
   ggsnApnRadiusAcctServerIndex                         Integer32,
   ggsnApnRadiusAcctServerIpAddress                     IpAddress,
   ggsnApnRadiusAcctServerAccountingRequests            Counter64,
   ggsnApnRadiusAcctServerAccountingResponses           Counter64,
   ggsnApnRadiusAcctServerAccountingRequestTimeouts     Counter64,
   ggsnApnRadiusAcctServerAccountingRequestRetransmits  Counter64,
   ggsnApnRadiusAcctServerInvalidAuthenticators         Counter64
}

ggsnApnRadiusAcctServerIndex OBJECT-TYPE
   SYNTAX        Integer32 (1..2147483647)
   MAX-ACCESS    not-accessible
   STATUS        current
   DESCRIPTION
         "A number representing each RADIUS accounting server."
   ::= { ggsnApnRadiusAcctServersStatsEntry 1 }

ggsnApnRadiusAcctServerIpAddress OBJECT-TYPE
   SYNTAX        IpAddress
   MAX-ACCESS    read-only
   STATUS        current
   DESCRIPTION   "RADIUS accounting server IP-address."
   ::= { ggsnApnRadiusAcctServersStatsEntry 2 }

ggsnApnRadiusAcctServerAccountingRequests OBJECT-TYPE
   SYNTAX        Counter64
   MAX-ACCESS    read-only
   STATUS        current
   DESCRIPTION   "Number of ACCOUNTING REQUESTS sent to the RADIUS accounting server for this APN."
   ::= { ggsnApnRadiusAcctServersStatsEntry 3 }

ggsnApnRadiusAcctServerAccountingResponses OBJECT-TYPE
   SYNTAX        Counter64
   MAX-ACCESS    read-only
   STATUS        current
   DESCRIPTION   "Number of ACCOUNTING RESPONSES received from the RADIUS accounting server for this APN."
   ::= { ggsnApnRadiusAcctServersStatsEntry 4 }

ggsnApnRadiusAcctServerAccountingRequestTimeouts OBJECT-TYPE
   SYNTAX        Counter64
   MAX-ACCESS    read-only
   STATUS        current
   DESCRIPTION   "Number of timed out ACCOUNTING REQUESTS sent to the RADIUS accounting server for this APN."
   ::= { ggsnApnRadiusAcctServersStatsEntry 5 }

ggsnApnRadiusAcctServerAccountingRequestRetransmits OBJECT-TYPE
   SYNTAX        Counter64
   MAX-ACCESS    read-only
   STATUS        current
   DESCRIPTION   "Number of ACCOUNTING REQUESTS retransmitted to the RADIUS accounting server for this APN."
   ::= { ggsnApnRadiusAcctServersStatsEntry 6 }

ggsnApnRadiusAcctServerInvalidAuthenticators OBJECT-TYPE
   SYNTAX        Counter64
   MAX-ACCESS    read-only
   STATUS        current
   DESCRIPTION   "Number of invalid authenticators received from the RADIUS accounting server for this APN."
   ::= { ggsnApnRadiusAcctServersStatsEntry 7 }

--
-- GGSN SGSN statistics
--


ggsnSgsnStatsTable OBJECT-TYPE
   SYNTAX        SEQUENCE OF SgsnStats
   MAX-ACCESS    not-accessible
   STATUS        obsolete
   DESCRIPTION
         "A table listing the statistics for all SGSNs with
          which this GGSN communicates."
   ::= { ggsnGeneralInfo 6 }

ggsnSgsnStatsEntry OBJECT-TYPE
   SYNTAX        SgsnStats
   MAX-ACCESS    not-accessible
   STATUS        obsolete
   DESCRIPTION
         "A conceptual row listing the statistics for each
          SGSN with which this GGSN communicates."
   INDEX        { ggsnSgsnIndex }
   ::= { ggsnSgsnStatsTable 1 }

SgsnStats ::= SEQUENCE {
    ggsnSgsnIndex		Integer32,
    ggsnSgsnAddress		IpAddress,
    ggsnSgsnUplinkPackets	Counter64,
    ggsnSgsnUplinkBytes		Counter64,
    ggsnSgsnUplinkDrops		Counter64,
    ggsnSgsnDownlinkPackets	Counter64,
    ggsnSgsnDownlinkBytes	Counter64,
    ggsnSgsnDownlinkDrops	Counter64
}

ggsnSgsnIndex OBJECT-TYPE
   SYNTAX        Integer32 (1..2147483647)
   MAX-ACCESS    not-accessible
   STATUS        obsolete
   DESCRIPTION
         "A number representing each SGSN whose statistics
          is being generated."
   ::= { ggsnSgsnStatsEntry 1 }

ggsnSgsnAddress OBJECT-TYPE
   SYNTAX        IpAddress
   MAX-ACCESS    read-only
   STATUS        obsolete
   DESCRIPTION
         "The IP address of the SGSN whose statistics
          is being generated."
   ::= { ggsnSgsnStatsEntry 2 }

ggsnSgsnUplinkPackets OBJECT-TYPE
   SYNTAX        Counter64
   MAX-ACCESS    read-only
   STATUS        obsolete
   DESCRIPTION
         "Total uplink packets processed on a per SGSN basis."
   ::= { ggsnSgsnStatsEntry 3 }

ggsnSgsnUplinkBytes OBJECT-TYPE
   SYNTAX        Counter64
   MAX-ACCESS    read-only
   STATUS        obsolete
   DESCRIPTION
         "Total bytes for all processed uplink packets
          on a per SGSN basis."
   ::= { ggsnSgsnStatsEntry 4 }

ggsnSgsnUplinkDrops OBJECT-TYPE
   SYNTAX        Counter64
   MAX-ACCESS    read-only
   STATUS        obsolete
   DESCRIPTION
         "Number of uplink GTP-U packets dropped in the GGSN for 
          this specific SGSN, that is, the number of packets dropped
          in this GGSN that were sent from this SGSN."
   ::= { ggsnSgsnStatsEntry 5 }

ggsnSgsnDownlinkPackets OBJECT-TYPE
   SYNTAX        Counter64
   MAX-ACCESS    read-only
   STATUS        obsolete
   DESCRIPTION
         "Total downlink packets processed on a per SGSN basis."
   ::= { ggsnSgsnStatsEntry 6 }

ggsnSgsnDownlinkBytes OBJECT-TYPE
   SYNTAX        Counter64
   MAX-ACCESS    read-only
   STATUS        obsolete
   DESCRIPTION
         "Total bytes for all processed downlink packets
          on a per SGSN basis."
   ::= { ggsnSgsnStatsEntry 7 }

ggsnSgsnDownlinkDrops OBJECT-TYPE
   SYNTAX        Counter64
   MAX-ACCESS    read-only
   STATUS        obsolete
   DESCRIPTION
         "Number of downlink GTP-U packets dropped in this GGSN
          for this specific SGSN, that is, the number of packets dropped
          by this GGSN before they were sent to this specific SGSN)."
   ::= { ggsnSgsnStatsEntry 8 }


--
-- GGSN L2TP statistics
--


ggsnL2tpTunnelStatsTable OBJECT-TYPE
   SYNTAX        SEQUENCE OF L2tpTunnelStats
   MAX-ACCESS    not-accessible
   STATUS        current
   DESCRIPTION
         "A table listing the statistics for all L2TP tunnels which
          are served by this GGSN."
   ::= { ggsnGeneralInfo 7 }

ggsnL2tpTunnelStatsEntry OBJECT-TYPE
   SYNTAX        L2tpTunnelStats
   MAX-ACCESS    not-accessible
   STATUS        current
   DESCRIPTION
         "A conceptual row listing the statistics for each
          L2TP tunnel which is served by this GGSN."
   INDEX         { ggsnL2tpTunnelIndex }
   ::= { ggsnL2tpTunnelStatsTable 1 }

L2tpTunnelStats ::= SEQUENCE {
   ggsnL2tpTunnelIndex              Integer32,
   ggsnL2tpTunnelLocalTID           Integer32,
   ggsnL2tpTunnelRemoteTID          Integer32,
   ggsnL2tpTunnelLocalIp            IpAddress,
   ggsnL2tpTunnelRemoteIp           IpAddress,
   ggsnL2tpTunnelActiveSessions     Gauge32,
   ggsnL2tpTunnelControlTxPackets   Counter64,
   ggsnL2tpTunnelControlRxPackets   Counter64,
   ggsnL2tpTunnelDataTxPackets      Counter64,
   ggsnL2tpTunnelDataRxPackets      Counter64,
   ggsnL2tpTunnelDiscardedTxPackets Counter64,
   ggsnL2tpTunnelDiscardedRxPackets Counter64
}

ggsnL2tpTunnelIndex OBJECT-TYPE
   SYNTAX        Integer32
   MAX-ACCESS    not-accessible
   STATUS        current
   DESCRIPTION
         "A number representing each tunnel whose statistics
          is being generated."
   ::= { ggsnL2tpTunnelStatsEntry 1 }

ggsnL2tpTunnelLocalTID OBJECT-TYPE
   SYNTAX        Integer32
   MAX-ACCESS    read-only
   STATUS        current
   DESCRIPTION
	 "The local tunnel identifier."
   ::= { ggsnL2tpTunnelStatsEntry 2 }

ggsnL2tpTunnelRemoteTID OBJECT-TYPE
   SYNTAX        Integer32
   MAX-ACCESS    read-only
   STATUS        current
   DESCRIPTION
	 "The remote tunnel identifier."
   ::= { ggsnL2tpTunnelStatsEntry 3 }

ggsnL2tpTunnelLocalIp OBJECT-TYPE
   SYNTAX        IpAddress
   MAX-ACCESS    read-only
   STATUS        current
   DESCRIPTION
	 "The local IP this tunnel is bound to."
   ::= { ggsnL2tpTunnelStatsEntry 4 }

ggsnL2tpTunnelRemoteIp OBJECT-TYPE
   SYNTAX        IpAddress
   MAX-ACCESS    read-only
   STATUS        current
   DESCRIPTION
	 "The remote IP this tunnel is bound to."
   ::= { ggsnL2tpTunnelStatsEntry 5 }

 ggsnL2tpTunnelActiveSessions OBJECT-TYPE
   SYNTAX        Gauge32
   MAX-ACCESS    read-only
   STATUS        current
   DESCRIPTION
	 "The number of sessions that are currently active for this tunnel."
   ::= { ggsnL2tpTunnelStatsEntry 6 }

 ggsnL2tpTunnelControlTxPackets OBJECT-TYPE
   SYNTAX        Counter64
   MAX-ACCESS    read-only
   STATUS        current
   DESCRIPTION
	 "The number of control packets transmitted for this tunnel."
   ::= { ggsnL2tpTunnelStatsEntry 7 }

 ggsnL2tpTunnelControlRxPackets OBJECT-TYPE
   SYNTAX        Counter64
   MAX-ACCESS    read-only
   STATUS        current
   DESCRIPTION
	 "The number of control packets received for this tunnel."
   ::= { ggsnL2tpTunnelStatsEntry 8 }

 ggsnL2tpTunnelDataTxPackets OBJECT-TYPE
   SYNTAX        Counter64
   MAX-ACCESS    read-only
   STATUS        current
   DESCRIPTION
	 "The number of data packets transmitted for this tunnel."
   ::= { ggsnL2tpTunnelStatsEntry 9 }

 ggsnL2tpTunnelDataRxPackets OBJECT-TYPE
   SYNTAX        Counter64
   MAX-ACCESS    read-only
   STATUS        current
   DESCRIPTION
	 "The number of data packets received for this tunnel."
   ::= { ggsnL2tpTunnelStatsEntry 10 }

 ggsnL2tpTunnelDiscardedTxPackets OBJECT-TYPE
   SYNTAX        Counter64
   MAX-ACCESS    read-only
   STATUS        current
   DESCRIPTION
	 "The number of (attempted) transmitted packets that were discarded by this tunnel."
   ::= { ggsnL2tpTunnelStatsEntry 11 }

 ggsnL2tpTunnelDiscardedRxPackets OBJECT-TYPE
   SYNTAX        Counter64
   MAX-ACCESS    read-only
   STATUS        current
   DESCRIPTION
	 "The number of received packets that were discarded by this tunnel."
   ::= { ggsnL2tpTunnelStatsEntry 12 }

--
-- PGW Global
--
pgwGlobalStats OBJECT IDENTIFIER ::= { ggsnGeneralInfo 8 }

pgwAttemptedEpsBearerStats
   OBJECT IDENTIFIER ::= { pgwGlobalStats 1 }
pgwCompletedEpsBearerStats
   OBJECT IDENTIFIER ::= { pgwGlobalStats 2 }

pgwNbrOfActiveEpsBearer  OBJECT-TYPE
	SYNTAX     Gauge32
	MAX-ACCESS read-only
	STATUS     current
	DESCRIPTION 
		"Total number of active IPv4 and IPv6 EPS bearers on this PGW. Incremented when successful create response has been sent to SGW. Decremented when entering the delete sequence."
	::= { pgwGlobalStats 3 }

pgwNbrOfActiveIpv6EpsBearer  OBJECT-TYPE
	SYNTAX     Gauge32
	MAX-ACCESS read-only
	STATUS     current
	DESCRIPTION 
		"Total number of active IPv6 EPS bearer on this PGW. Incremented when successful create response has been sent to SGW. Decremented when entering the delete sequence."
	::= { pgwGlobalStats 4 }

pgwNbrOfActiveIpv4v6EpsBearer  OBJECT-TYPE
	SYNTAX     Gauge32
	MAX-ACCESS read-only
	STATUS     current
	DESCRIPTION 
		"Total number of active IPv4v6 EPS bearer on this PGW. Incremented when successful create response has been sent to SGW. Decremented when entering the delete sequence."
	::= { pgwGlobalStats 5 }

pgwWlanNbrOfActiveEpsBearer  OBJECT-TYPE
	SYNTAX     Gauge32
	MAX-ACCESS read-only
	STATUS     current
	DESCRIPTION 
		"Total number of active EPS bearers for WLAN on this PGW"
	::= { pgwGlobalStats 6 }

s6bInterface
   OBJECT IDENTIFIER ::= { pgwGlobalStats 7 }

--
-- PDN Connections PGW
--
	
pdnConnectionsPgw
   OBJECT IDENTIFIER ::= { pgwGlobalStats 50 }	
   
nbrOfPgwPdnConnections  OBJECT-TYPE
	SYNTAX     Gauge32
	MAX-ACCESS read-only
	STATUS     current
	DESCRIPTION 
		"Number of PDN connections to a PGW-enabled APN."
	::= { pdnConnectionsPgw 1 }

nbrOfPiscPdnConnections  OBJECT-TYPE
	SYNTAX     Gauge32
	MAX-ACCESS read-only
	STATUS     current
	DESCRIPTION 
		"Number of PDN connections using PISC."
	::= { pdnConnectionsPgw 2 }

nbrOfOnlineChargingPdnConnections  OBJECT-TYPE
	SYNTAX     Gauge32
	MAX-ACCESS read-only
	STATUS     current
	DESCRIPTION 
		"Number of PDN connections using online charging."
	::= { pdnConnectionsPgw 3 }

nbrOfDynamicPolicyControlPdnConnections  OBJECT-TYPE
	SYNTAX     Gauge32
	MAX-ACCESS read-only
	STATUS     current
	DESCRIPTION 
		"Number of PDN connections using dynamic policy control."
	::= { pdnConnectionsPgw 4 }

nbrOfWlanPdnConnections  OBJECT-TYPE
	SYNTAX     Gauge32
	MAX-ACCESS read-only
	STATUS     current
	DESCRIPTION 
		"Number of PDN connections with RAT type WLAN."
	::= { pdnConnectionsPgw 5 }

nbrOfGeranPdnConnections  OBJECT-TYPE
	SYNTAX     Gauge32
	MAX-ACCESS read-only
	STATUS     current
	DESCRIPTION 
		"Number of PDN connections with RAT type GERAN."
	::= { pdnConnectionsPgw 6 }

nbrOfUtranPdnConnections  OBJECT-TYPE
	SYNTAX     Gauge32
	MAX-ACCESS read-only
	STATUS     current
	DESCRIPTION 
		"Number of PDN connections with RAT type UTRAN."
	::= { pdnConnectionsPgw 7 }

nbrOfHspaEvolutionPdnConnections  OBJECT-TYPE
	SYNTAX     Gauge32
	MAX-ACCESS read-only
	STATUS     current
	DESCRIPTION 
		"Number of PDN connections with RAT type HSPA Evolution."
	::= { pdnConnectionsPgw 8 }

nbrOfEutranPdnConnections  OBJECT-TYPE
	SYNTAX     Gauge32
	MAX-ACCESS read-only
	STATUS     current
	DESCRIPTION 
		"Number of PDN connections with RAT type EUTRAN."
	::= { pdnConnectionsPgw 9 }
 
ggsnNodeName OBJECT-TYPE
   SYNTAX        DisplayString 
   MAX-ACCESS    read-only
   STATUS        current
   DESCRIPTION
         "The node name of this ggsn."
   ::= { ggsnGeneralInfo 9 }

pgwRRreroutedStatsTable OBJECT-TYPE
   SYNTAX        SEQUENCE OF PgwRRreroutedStatsEntry
   MAX-ACCESS    not-accessible
   STATUS        current
   DESCRIPTION
         "A table listing the Scalable Gi Routing Redundancy statistics for each routing instance."
   ::= { ggsnGeneralInfo  11 }

pgwRRreroutedStatsEntry OBJECT-TYPE
   SYNTAX        PgwRRreroutedStatsEntry
   MAX-ACCESS    not-accessible
   STATUS        current
   DESCRIPTION
         "A conceptual row listing the GIRR statistics for each Routing Instance on this GGSN."
   INDEX     { pgwRoutingInstanceId }
   ::= { pgwRRreroutedStatsTable 1 }


PgwRRreroutedStatsEntry ::= SEQUENCE {
   pgwRoutingInstanceId Integer32,
   pgwRoutingInstanceName DisplayString,
   pgwRRreroutedDataDownlinkPkts Counter64,
   pgwRRreroutedDataRxPkts Counter64,
   pgwRRreroutedDataTxPkts Counter64,
   pgwRRreroutedDataIpv6DownlinkPkts Counter64,
   pgwRRreroutedDataIpv6RxPkts Counter64,
   pgwRRreroutedDataIpv6TxPkts Counter64
}

pgwRoutingInstanceId OBJECT-TYPE
   SYNTAX        Integer32
   MAX-ACCESS    not-accessible
   STATUS        current
   DESCRIPTION
         "Id of Routing Instance configured as GiRR instance."
   ::= { pgwRRreroutedStatsEntry 1 }

pgwRoutingInstanceName OBJECT-TYPE
   SYNTAX        DisplayString
   MAX-ACCESS    read-only
   STATUS        current
   DESCRIPTION
         "Name of Routing Instance configured as GiRR instance."
   ::= { pgwRRreroutedStatsEntry 2 }

pgwRRreroutedDataDownlinkPkts OBJECT-TYPE
   SYNTAX        Counter64
   MAX-ACCESS    read-only
   STATUS        current
   DESCRIPTION
         "Number of packets sent downlink"
   ::= { pgwRRreroutedStatsEntry 3 }

pgwRRreroutedDataRxPkts OBJECT-TYPE
   SYNTAX        Counter64
   MAX-ACCESS    read-only
   STATUS        current
   DESCRIPTION
         "The number of packets rerouted to peer by the GGSN."
   ::= { pgwRRreroutedStatsEntry 4 }
pgwRRreroutedDataTxPkts OBJECT-TYPE
   SYNTAX        Counter64
   MAX-ACCESS    read-only
   STATUS        current
   DESCRIPTION
         "The number of packets rerouted to the peer."
   ::= { pgwRRreroutedStatsEntry 5 }

pgwRRreroutedDataIpv6DownlinkPkts OBJECT-TYPE
   SYNTAX        Counter64
   MAX-ACCESS    read-only
   STATUS        current
   DESCRIPTION
         "Number of Ipv6 packets sent downlink"
   ::= { pgwRRreroutedStatsEntry 6 }

pgwRRreroutedDataIpv6RxPkts OBJECT-TYPE
   SYNTAX        Counter64
   MAX-ACCESS    read-only
   STATUS        current
   DESCRIPTION
         "The number of Ipv6 packets rerouted to peer by the GGSN."
   ::= { pgwRRreroutedStatsEntry 7 }

pgwRRreroutedDataIpv6TxPkts OBJECT-TYPE
   SYNTAX        Counter64
   MAX-ACCESS    read-only
   STATUS        current
   DESCRIPTION
         "The number of Ipv6 packets rerouted to the peer."
   ::= { pgwRRreroutedStatsEntry 8 }

pgwAttemptedEpsBearerActivation  OBJECT-TYPE
    SYNTAX     Counter64
    MAX-ACCESS read-only
    STATUS     current
    DESCRIPTION 
        "Total number of Active IPv4 and IPv6 EPS bearer creation attempts. Incremented each time a Create EPS Bearer request that is not silently discarded is received by the PGW. This means the counter is incremented each time a create EPS Bearer response is sent back to the SGW with cause value Request Accepted or with a reject value."
    ::= { pgwAttemptedEpsBearerStats 1 }

pgwAttemptedEpsBearerIpv6Activation  OBJECT-TYPE
    SYNTAX     Counter64
    MAX-ACCESS read-only
    STATUS     current
    DESCRIPTION 
        "Total number of Ipv6 EPS bearer creation attempts. Incremented each time a Create EPS Bearer request that is not silently discarded is received by the PGW. This means the counter is incremented each time a create EPS Bearer response is sent back to the SGW with cause value Request Accepted or with a reject value. Note: Counter not updated for bearers having the possibility to use either IPv4 or IPv6. Which address type that will be used is not known at this early stage."
    ::= { pgwAttemptedEpsBearerStats 2 }

pgwAttemptedEpsBearerModification  OBJECT-TYPE
    SYNTAX     Counter64
    MAX-ACCESS read-only
    STATUS     current
    DESCRIPTION
        "Total number of attempted IPv4 and IPv6 EPS bearer modifications. Incremented at attempted EPS bearer modifications including retries of modifications."
    ::= { pgwAttemptedEpsBearerStats 3 }

pgwAttemptedEpsBearerDeactivation  OBJECT-TYPE
    SYNTAX     Counter64
    MAX-ACCESS read-only
    STATUS     current
    DESCRIPTION 
        "Total number of IPv4 and IPv6 EPS bearer deactivation attempts. Incremented when a deactivation is triggered by the PGW, triggered by the UE/SGW, rejected deactivation requests and silently discarded deactivation requests."
    ::= { pgwAttemptedEpsBearerStats 4 }

pgwAttemptedDedicatedEpsBearerActivation  OBJECT-TYPE
    SYNTAX     Counter64
    MAX-ACCESS read-only
    STATUS     current
    DESCRIPTION 
        "Total number of Active IPv4 and IPv6 EPS bearer creation attempts. Incremented each time a Create EPS Bearer request that is not silently discarded is received by the PGW. This means the counter is incremented each time a create EPS Bearer response is sent back to the SGW with cause value Request Accepted or with a reject value."
    ::= { pgwAttemptedEpsBearerStats 5 }

pgwAttemptedDedicatedEpsBearerIpv6Activation  OBJECT-TYPE
    SYNTAX     Counter64
    MAX-ACCESS read-only
    STATUS     current
    DESCRIPTION 
        "Total number of Ipv6 dedicated EPS bearer creation attempts. Incremented each time a Create dedicated EPS Bearer request that is not silently discarded is received by the PGW. This means the counter is incremented each time a create dedicated EPS Bearer response is sent back to the SGW with cause value Request Accepted or with a reject value. Note: Counter not updated for bearers having the possibility to use either IPv4 or IPv6. Which address type that will be used is not known at this early stage."
    ::= { pgwAttemptedEpsBearerStats 6 }

pgwAttemptedEpsBearerIpv4v6Activation  OBJECT-TYPE
    SYNTAX     Counter64
    MAX-ACCESS read-only
    STATUS     current
    DESCRIPTION
        "Total number of Ipv4v6 EPS bearer creation attempts. Incremented each time a Create EPS Bearer request that is not silently discarded is received by the PGW. This means the counter is incremented each time a create EPS Bearer response is sent back to the SGW with cause value Request Accepted or with a reject value. Note: Counter not updated for bearers having the possibility to use either IPv4 or IPv6. Which address type that will be used is not known at this early stage."
    ::= { pgwAttemptedEpsBearerStats 7 }

pgwAttempteds2aEpsBearerActivation  OBJECT-TYPE
    SYNTAX     Counter64
    MAX-ACCESS read-only
    STATUS     current
    DESCRIPTION
        "Total number of attempted EPS bearer activations over the S2a interface, silently-discarded activations and activation retries also included."
    ::= { pgwAttemptedEpsBearerStats 8 }

pgwCompletedEpsBearerActivation  OBJECT-TYPE
    SYNTAX     Counter64
    MAX-ACCESS read-only
    STATUS     current
    DESCRIPTION 
        "Total number of IPv4 and IPv6 EPS bearer creations completed. Incremented when an EPS bearer is successfully activated."
    ::= { pgwCompletedEpsBearerStats 1 }

pgwCompletedEpsBearerIpv6Activation  OBJECT-TYPE
    SYNTAX     Counter64
    MAX-ACCESS read-only
    STATUS     current
    DESCRIPTION 
        "Total number of Ipv6 EPS bearer creations completed. Incremented when an EPS bearer is successfully activated."
    ::= { pgwCompletedEpsBearerStats 2 }

pgwCompletedEpsBearerModification  OBJECT-TYPE
    SYNTAX     Counter64
    MAX-ACCESS read-only
    STATUS     current
    DESCRIPTION 
        "Total number of IPv4 and IPv6 EPS bearer modifications completed. Incremented both for successful network and SGW initiated updates."
    ::= { pgwCompletedEpsBearerStats 3 }

pgwCompletedEpsBearerDeactivation  OBJECT-TYPE
    SYNTAX     Counter64
    MAX-ACCESS read-only
    STATUS     current
    DESCRIPTION 
        "Total number of IPv4 and IPv6 EPS bearer deactivations completed. Incremented both for successful PGW triggered deactivations and successful UE/SGW triggered deactivations."
    ::= { pgwCompletedEpsBearerStats 4 }

pgwCompletedDedicatedEpsBearerActivation  OBJECT-TYPE
    SYNTAX     Counter64
    MAX-ACCESS read-only
    STATUS     current
    DESCRIPTION 
        "Total number of IPv4 and IPv6 dedicated EPS bearer creations completed. Incremented when a dedicated EPS bearer is successfully activated."
    ::= { pgwCompletedEpsBearerStats 5 }

pgwCompletedDedicatedEpsBearerIpv6Activation  OBJECT-TYPE
    SYNTAX     Counter64
    MAX-ACCESS read-only
    STATUS     current
    DESCRIPTION 
        "Total number of Ipv6 dedicated EPS bearer creations completed. Incremented when a dedicated EPS bearer is successfully activated."
    ::= { pgwCompletedEpsBearerStats 6 }

pgwCompletedEpsBearerIpv4v6Activation  OBJECT-TYPE
    SYNTAX     Counter64
    MAX-ACCESS read-only
    STATUS     current
    DESCRIPTION
        "Total number of Ipv4v6 EPS bearer creations completed. Incremented when an EPS bearer is successfully activated."
    ::= { pgwCompletedEpsBearerStats 7 }

pgwCompleteds2aEpsBearerActivation  OBJECT-TYPE
    SYNTAX     Counter64
    MAX-ACCESS read-only
    STATUS     current
    DESCRIPTION
        "Total number of EPS bearer creations over the S2a interface completed."
    ::= { pgwCompletedEpsBearerStats 8 }

s6bAarSent  OBJECT-TYPE
    SYNTAX     Counter64
    MAX-ACCESS read-only
    STATUS     current
    DESCRIPTION
        "Total number of Authentication and Authorization Request (AAR) messages sent by the PGW over the S6b interface."
    ::= { s6bInterface 1 }

s6bAaaSuccRcvd  OBJECT-TYPE
    SYNTAX     Counter64
    MAX-ACCESS read-only
    STATUS     current
    DESCRIPTION
        "Total number of AAA messages with acceptance response cause values received by the PGW over the S6b interface."
    ::= { s6bInterface 2 }

s6bAaaFailRcvd  OBJECT-TYPE
    SYNTAX     Counter64
    MAX-ACCESS read-only
    STATUS     current
    DESCRIPTION
        "Total number of Authentication and Authorization Answer (AAA) messages with rejection response cause values received by the PGW over the S6b interface."
    ::= { s6bInterface 3 }

s6bAaaInvalidRcvd  OBJECT-TYPE
    SYNTAX     Counter64
    MAX-ACCESS read-only
    STATUS     current
    DESCRIPTION
        "Total number of AAA messages with invalid content received by the PGW over the S6b interface."
    ::= { s6bInterface 4 }

s6bStrSent  OBJECT-TYPE
    SYNTAX     Counter64
    MAX-ACCESS read-only
    STATUS     current
    DESCRIPTION
        "Total number of Session Termination Request (STR) messages sent by the PGW over the S6b interface."
    ::= { s6bInterface 5 }

s6bStaSuccRcvd  OBJECT-TYPE
    SYNTAX     Counter64
    MAX-ACCESS read-only
    STATUS     current
    DESCRIPTION
        "Total number of STA messages with acceptance response cause values received by the PGW over the S6b interface."
    ::= { s6bInterface 6 }

s6bStaFailRcvd  OBJECT-TYPE
    SYNTAX     Counter64
    MAX-ACCESS read-only
    STATUS     current
    DESCRIPTION
        "Total number of Session Termination Answer (STA) messages with rejection response cause values received by the PGW over the S6b interface."
    ::= { s6bInterface 7 }
--
-- GTP-C group
--


ggsnGtpcTable OBJECT-TYPE
   SYNTAX        SEQUENCE OF GtpcEntry
   MAX-ACCESS    not-accessible
   STATUS        current
   DESCRIPTION
         "The table listing GGSN-C PICs (also known as GTP-C PICs)"
   ::= { ggsnGtpcInfo 1 }

ggsnGtpcEntry OBJECT-TYPE
   SYNTAX        GtpcEntry
   MAX-ACCESS    not-accessible
   STATUS        current
   DESCRIPTION
         "An entry representing a GGSN-C (GTP-C) PIC."
   INDEX         { ggsnGtpcIndex }
   ::= { ggsnGtpcTable 1 }

GtpcEntry ::= SEQUENCE {
   ggsnGtpcIndex       Integer32,
   ggsnGtpcVersion     DisplayString,
   ggsnGtpcAddress     IpAddress,
   ggsnGtpcPdpCapacity Integer32,
   ggsnGtpcRole        INTEGER,
   ggsnGtpcStatus      DisplayString,
   ggsnGtpcControlPacketDrops Counter64,
   ggsnGtpcNbrOfActivePdpContexts Gauge32,
   ggsnGtpcMemory	Integer32,
   ggsnGtpcMemoryUsed	Integer32,
   ggsnGtpcCpuUsage	Gauge32,
   ggsnGtpcTftFilterDepthMax Gauge32,
   ggsnGtpcTftFilterDepthMean Gauge32,
   ggsnGtpcControlLoad  Gauge32,
   ggsnGtpcNbrOfActivePdpContextsIpv6 Gauge32,
   ggsnGtpcPeakCpuUsage  Gauge32,
   ggsnGtpcNbrOfActivePdpContextsIpv4v6 Gauge32
}

ggsnGtpcIndex OBJECT-TYPE
   SYNTAX        Integer32 (1..2147483647)
   MAX-ACCESS    not-accessible
   STATUS        current
   DESCRIPTION
         "A number uniquely identifying each GGSN-C (GTP-C) PIC
          in the GGSN."
   ::= { ggsnGtpcEntry 1 }

ggsnGtpcVersion OBJECT-TYPE
   SYNTAX        DisplayString
   MAX-ACCESS    read-only
   STATUS        current
   DESCRIPTION
         "Software version running on the GGSN-C (GTP-C) PIC."
   ::= { ggsnGtpcEntry 2 }

ggsnGtpcAddress OBJECT-TYPE
   SYNTAX        IpAddress
   MAX-ACCESS    read-only
   STATUS        current
   DESCRIPTION
         "The external IP address of the GGSN-C (GTP-C) PIC."
   ::= { ggsnGtpcEntry 3 }

ggsnGtpcPdpCapacity OBJECT-TYPE
   SYNTAX        Integer32
   MAX-ACCESS    read-only
   STATUS        current
   DESCRIPTION
         "The capacity of the GGSN-C (GTP-C) PIC."
   ::= { ggsnGtpcEntry 4 }

ggsnGtpcRole OBJECT-TYPE
   SYNTAX        INTEGER {
                     unknown(1),
                     master(2),
                     slave(3),
                     standby(4)
                 }
   MAX-ACCESS    read-only
   STATUS        current
   DESCRIPTION
         "The current role of the GGSN-C (GTP-C) PIC. 
         1. unknown 
         2. master = node controller 
         3. slave = session controller 
         4. standby"
   ::= { ggsnGtpcEntry 5 }

ggsnGtpcStatus OBJECT-TYPE
   SYNTAX        DisplayString
   MAX-ACCESS    read-only
   STATUS        current
   DESCRIPTION
         "The current status of the GGSN-C (GTP-C) PIC, 
         for example BLOCK, READY, STANDBY or NOT READY."
   ::= { ggsnGtpcEntry 6 }

ggsnGtpcControlPacketDrops OBJECT-TYPE
   SYNTAX        Counter64
   MAX-ACCESS    read-only
   STATUS        current
   DESCRIPTION
         "The number of control packets that have
          been dropped by this GGSN-C (GTP-C) PIC. 
          
          Note: This counter cannot be retrieved by CLI."
   ::= { ggsnGtpcEntry 7 }

ggsnGtpcNbrOfActivePdpContexts OBJECT-TYPE
   SYNTAX        Gauge32
   MAX-ACCESS    read-only
   STATUS        current
   DESCRIPTION
         "The number of active bearers on this C-PIC."
   ::= { ggsnGtpcEntry 8 }

ggsnGtpcMemory OBJECT-TYPE
   SYNTAX        Integer32
   MAX-ACCESS    read-only
   STATUS        current
   DESCRIPTION
         "The amount of memory on the GGSN-C PIC, in kilobytes."
   ::= { ggsnGtpcEntry 9 }

ggsnGtpcMemoryUsed OBJECT-TYPE
   SYNTAX        Integer32
   MAX-ACCESS    read-only
   STATUS        current
   DESCRIPTION
         "The amount of used memory on the GGSN-C PIC, in kilobytes."
   ::= { ggsnGtpcEntry 10 }

ggsnGtpcCpuUsage OBJECT-TYPE
   SYNTAX        Gauge32
   MAX-ACCESS    read-only
   STATUS        current
   DESCRIPTION
        "This counter shows the average CPU utilization percentage
         over all cores sampled every 5 seconds 
         in case of a Node Controller C-PIC,
         or shows the highest value from the Proxy CPU's utilization
         and the average Slave CPU's utilization sampled every 5 seconds
         in case of a Session Controller C-PIC." 
   ::= { ggsnGtpcEntry 11 }

ggsnGtpcTftFilterDepthMax OBJECT-TYPE
   SYNTAX        Gauge32
   MAX-ACCESS    read-only
   STATUS        current
   DESCRIPTION
         "The maximum number of TFT filters per user on this GGSN-C PIC,
          in the last statistics update period."
   ::= { ggsnGtpcEntry 12 }

ggsnGtpcTftFilterDepthMean OBJECT-TYPE
   SYNTAX        Gauge32
   MAX-ACCESS    read-only
   STATUS        current
   DESCRIPTION
         "The mean number of TFT filters per user on this GGSN-C PIC,
          in the last statistics update period."
   ::= { ggsnGtpcEntry 13 }

ggsnGtpcControlLoad OBJECT-TYPE
   SYNTAX        Gauge32
   MAX-ACCESS    read-only
   STATUS        current
   DESCRIPTION
         "Weighted PDP context load in control of the GGSN-C PIC."
   ::= { ggsnGtpcEntry 14 }

ggsnGtpcNbrOfActivePdpContextsIpv6 OBJECT-TYPE
   SYNTAX        Gauge32
   MAX-ACCESS    read-only
   STATUS        current
   DESCRIPTION
         "The number of active IPv6 bearers on this C-PIC. 
         
         Note: This counter cannot be retrieved by CLI."
   ::= { ggsnGtpcEntry 15 }

ggsnGtpcPeakCpuUsage OBJECT-TYPE
   SYNTAX        Gauge32
   MAX-ACCESS    read-only
   STATUS        current
   DESCRIPTION
         "This counter shows the highest CPU utilization percentage
          over all cores of the C-PIC sampled every 5 seconds."
   ::= { ggsnGtpcEntry 16 }

ggsnGtpcNbrOfActivePdpContextsIpv4v6 OBJECT-TYPE
   SYNTAX        Gauge32
   MAX-ACCESS    read-only
   STATUS        current
   DESCRIPTION
         "The number of active IPv4v6 bearers on this C-PIC.

         Note: This counter cannot be retrieved by CLI."
   ::= { ggsnGtpcEntry 17 }

--
-- GTP-U group
--

ggsnGtpuTable OBJECT-TYPE
   SYNTAX        SEQUENCE OF GtpuEntry
   MAX-ACCESS    not-accessible
   STATUS        current
   DESCRIPTION
         "The table listing GGSN-U PICs."
   ::= { ggsnGtpuInfo 1 }

ggsnGtpuEntry OBJECT-TYPE
   SYNTAX        GtpuEntry
   MAX-ACCESS    not-accessible
   STATUS        current
   DESCRIPTION
         "An entry representing a GGSN-U PIC."
   INDEX         { ggsnGtpuIndex }
   ::= { ggsnGtpuTable 1 }

GtpuEntry ::= SEQUENCE {
   ggsnGtpuIndex       Integer32,
   ggsnGtpuVersion     DisplayString,
   ggsnGtpuAddress     IpAddress,
   ggsnGtpuPdpCapacity Integer32,
   ggsnGtpuRole        INTEGER,
   ggsnGtpuStatus      DisplayString,
   ggsnGtpuUserUplinkDrops Counter64,
   ggsnGtpuUserDownlinkDrops Counter64,
   ggsnGtpuNbrOfActivePdpContexts Gauge32,
   ggsnGtpuMemory	Integer32,
   ggsnGtpuMemoryUsed	Integer32,
   ggsnGtpuCpuUsage	Gauge32,
   ggsnGtpuPayloadLoad  Gauge32,
   ggsnGtpuNbrOfActivePdpContextsIpv6 Gauge32,
   ggsnGtpuPeakCpuUsage	Gauge32,
   ggsnGtpuUplinkPackets Counter64,
   ggsnGtpuDownlinkPackets Counter64,
   ggsnGtpuNbrOfActivePdpContextsIpv4v6 Gauge32
}

ggsnGtpuIndex OBJECT-TYPE
   SYNTAX        Integer32 (0..2147483647)
   MAX-ACCESS    not-accessible
   STATUS        current
   DESCRIPTION
         "A number uniquely identifying each GGSN-U PIC. Its value
	  is calculated using formula 16 * (1 + FPC) + PIC."
   ::= { ggsnGtpuEntry 1 }

ggsnGtpuVersion OBJECT-TYPE
   SYNTAX        DisplayString
   MAX-ACCESS    read-only
   STATUS        current
   DESCRIPTION
         "Software version running on the GGSN-U PIC."
   ::= { ggsnGtpuEntry 2 }

ggsnGtpuAddress OBJECT-TYPE
   SYNTAX        IpAddress
   MAX-ACCESS    read-only
   STATUS        current
   DESCRIPTION
         "The Gn network IP address of the GGSN-U PIC."
   ::= { ggsnGtpuEntry 3 }

ggsnGtpuPdpCapacity OBJECT-TYPE
   SYNTAX        Integer32
   MAX-ACCESS    read-only
   STATUS        current
   DESCRIPTION
         "The capacity of the GGSN-U PIC."
   ::= { ggsnGtpuEntry 4 }

ggsnGtpuRole OBJECT-TYPE
   SYNTAX        INTEGER {
                     unknown(1),
                     active(2),
                     standby(4)
                 }
   MAX-ACCESS    read-only
   STATUS        current
   DESCRIPTION
         "The current role of the GGSN-U PIC.
          1. unknown
          2. active
          4. standby"
   ::= { ggsnGtpuEntry 5 }

ggsnGtpuStatus OBJECT-TYPE
   SYNTAX        DisplayString
   MAX-ACCESS    read-only
   STATUS        current
   DESCRIPTION
         "The current status of the GGSN-U PIC,
          for example BLOCK, READY, STANDBY or NOT READY."
   ::= { ggsnGtpuEntry 6 }

ggsnGtpuUserUplinkDrops OBJECT-TYPE
   SYNTAX        Counter64
   MAX-ACCESS    read-only
   STATUS        current
   DESCRIPTION
         "The number of uplink (GTP-U) packets dropped by this GGSN-U PIC. Note: This counter cannot be retrieved by CLI.
          Packets can be dropped for a number of reasons, including the following:
          The packet is classified as unauthorized after packet inspection
          The packet is an IPv6 link-local packet
          There are errors in the GTP header
          There is no PDP context
          There are general IP header faults
          No SGSN entry is found
          IP-in-IP encapsulation is missing for packet inspection
          IP-in-IP encapsulation provides wrong packet length
          The IP version is other than IPv4 or IPv6
          No GGSN-U/I application is available
          The packet cannot be forwarded to an GGSN-U/I application for classification
          The packet cannot be sent
          A certain type of IP traffic (IPv4/IPv6) is not allowed
          A bandwidth limitation is defined for the APN, and the limit is exceeded
          The packet is a broadcast message from an MS
          The IP packet source address does not match the IP address assigned to the MS by the GGSN 
          There is no free memory left in U-PIC"
   ::= { ggsnGtpuEntry 7 }

ggsnGtpuUserDownlinkDrops OBJECT-TYPE
   SYNTAX        Counter64
   MAX-ACCESS    read-only
   STATUS        current
   DESCRIPTION
         "The number of downlink (GTP-U) packets dropped by
          this GGSN-U PIC.
          
          Note: This counter cannot be retrieved by CLI."
   ::= { ggsnGtpuEntry 8 }

ggsnGtpuNbrOfActivePdpContexts OBJECT-TYPE
   SYNTAX        Gauge32
   MAX-ACCESS    read-only
   STATUS        current
   DESCRIPTION
         "The number of active bearers on this U-PIC."
   ::= { ggsnGtpuEntry 9 }

ggsnGtpuMemory OBJECT-TYPE
   SYNTAX        Integer32
   MAX-ACCESS    read-only
   STATUS        current
   DESCRIPTION
         "The amount of memory on the GGSN-U PIC, in kilobytes."
   ::= { ggsnGtpuEntry 10 }

ggsnGtpuMemoryUsed OBJECT-TYPE
   SYNTAX        Integer32
   MAX-ACCESS    read-only
   STATUS        current
   DESCRIPTION
         "The amount of used memory on the GGSN-U PIC, in kilobytes."
   ::= { ggsnGtpuEntry 11 }

ggsnGtpuCpuUsage OBJECT-TYPE
   SYNTAX        Gauge32
   MAX-ACCESS    read-only
   STATUS        current
   DESCRIPTION
         "This counter shows the average CPU utilization percentage
          over all Slave CPUs of the U-PIC sampled every 5 seconds."
   ::= { ggsnGtpuEntry 12 }

ggsnGtpuPayloadLoad OBJECT-TYPE
   SYNTAX        Gauge32
   MAX-ACCESS    read-only
   STATUS        current
   DESCRIPTION
         "Weighted PDP context load in payload of the GGSN-U PIC."
   ::= { ggsnGtpuEntry 13 }

ggsnGtpuNbrOfActivePdpContextsIpv6 OBJECT-TYPE
   SYNTAX        Gauge32
   MAX-ACCESS    read-only
   STATUS        current
   DESCRIPTION
         "The number of active IPv6 bearers on this U-PIC.
          
          Note: This counter cannot be retrieved by CLI."
   ::= { ggsnGtpuEntry 14 }

ggsnGtpuPeakCpuUsage OBJECT-TYPE
   SYNTAX        Gauge32
   MAX-ACCESS    read-only
   STATUS        current
   DESCRIPTION
         "This counter shows the highest CPU utilization percentage
          over all cores of the U-PIC sampled every 5 seconds."
   ::= { ggsnGtpuEntry 15 }

ggsnGtpuUplinkPackets OBJECT-TYPE
   SYNTAX        Counter64
   MAX-ACCESS    read-only
   STATUS        current
   DESCRIPTION
         "The number of uplink (GTP-U) packets processed by
          this GGSN-U PIC.
          
          Note: This counter cannot be retrieved by CLI."
   ::= { ggsnGtpuEntry 16 }

ggsnGtpuDownlinkPackets OBJECT-TYPE
   SYNTAX        Counter64
   MAX-ACCESS    read-only
   STATUS        current
   DESCRIPTION
         "The number of downlink (GTP-U) packets processed by
          this GGSN-U PIC.
          
          Note: This counter cannot be retrieved by CLI."
   ::= { ggsnGtpuEntry 17 }

ggsnGtpuNbrOfActivePdpContextsIpv4v6 OBJECT-TYPE
   SYNTAX        Gauge32
   MAX-ACCESS    read-only
   STATUS        current
   DESCRIPTION
         "The number of active IPv4v6 bearers on this U-PIC.

          Note: This counter cannot be retrieved by CLI."
   ::= { ggsnGtpuEntry 18 }

--
-- T-PIC group
--

ggsnGtptTable OBJECT-TYPE
   SYNTAX        SEQUENCE OF GtptEntry
   MAX-ACCESS    not-accessible
   STATUS        deprecated
   DESCRIPTION
         "The table listing GGSN-T PICs."
   ::= { ggsnGtptInfo 1 }

ggsnGtptEntry OBJECT-TYPE
   SYNTAX        GtptEntry
   MAX-ACCESS    not-accessible
   STATUS        deprecated
   DESCRIPTION
         "An entry representing a GGSN-T PIC."
   INDEX         { ggsnGtptIndex }
   ::= { ggsnGtptTable 1 }

GtptEntry ::= SEQUENCE {
   ggsnGtptIndex       Integer32,
   ggsnGtptVersion     DisplayString,
   ggsnGtptAddress     IpAddress,
   ggsnGtptCapacity	   Integer32,
   ggsnGtptRole        INTEGER,
   ggsnGtptStatus      DisplayString,
   ggsnGtptMemory	   Integer32,
   ggsnGtptMemoryUsed  Integer32,
   ggsnGtptCpuUsage	   Gauge32,
   ggsnGtptPeakCpuUsage	   Gauge32
}

ggsnGtptIndex OBJECT-TYPE
   SYNTAX        Integer32 (0..2147483647)
   MAX-ACCESS    not-accessible
   STATUS        deprecated 
   DESCRIPTION
         "A number uniquely identifying each GGSN-T PIC. Its value
	  is calculated using formula 16 * (1 + FPC) + PIC."
   ::= { ggsnGtptEntry 1 }

ggsnGtptVersion OBJECT-TYPE
   SYNTAX        DisplayString
   MAX-ACCESS    read-only
   STATUS        deprecated 
   DESCRIPTION
         "Software version running on the GGSN-T PIC."
   ::= { ggsnGtptEntry 2 }

ggsnGtptAddress OBJECT-TYPE
   SYNTAX        IpAddress
   MAX-ACCESS    read-only
   STATUS        deprecated
   DESCRIPTION
         "The Gn network IP address of the GGSN-T PIC."
   ::= { ggsnGtptEntry 3 }

ggsnGtptCapacity OBJECT-TYPE
   SYNTAX        Integer32
   MAX-ACCESS    read-only
   STATUS        deprecated
   DESCRIPTION
         "The capacity of the GGSN-T PIC."
   ::= { ggsnGtptEntry 4 }

ggsnGtptRole OBJECT-TYPE
   SYNTAX        INTEGER {
                     unknown(1),
                     active(2),
                     standby(4)
                 }
   MAX-ACCESS    read-only
   STATUS        deprecated
   DESCRIPTION
         "The current role of the GGSN-T PIC."
   ::= { ggsnGtptEntry 5 }

ggsnGtptStatus OBJECT-TYPE
   SYNTAX        DisplayString
   MAX-ACCESS    read-only
   STATUS        deprecated 
   DESCRIPTION
         "The current status of the GGSN-T PIC, example BLOCK."
   ::= { ggsnGtptEntry 6 }

ggsnGtptMemory OBJECT-TYPE
   SYNTAX        Integer32
   MAX-ACCESS    read-only
   STATUS        deprecated
   DESCRIPTION
         "The amount of memory on the GGSN-T PIC, in kilobytes."
   ::= { ggsnGtptEntry 7 }

ggsnGtptMemoryUsed OBJECT-TYPE
   SYNTAX        Integer32
   MAX-ACCESS    read-only
   STATUS        deprecated
   DESCRIPTION
         "The amount of used memory on the GGSN-T PIC, in kilobytes."
   ::= { ggsnGtptEntry 8 }

ggsnGtptCpuUsage OBJECT-TYPE
   SYNTAX        Gauge32
   MAX-ACCESS    read-only
   STATUS        deprecated
   DESCRIPTION
         "This counter describes the average CPU utilization in 
         percentage of the GGSN-T PIC calculated over 5 seconds. 
         The GGSN-T PIC contains multiple CPUs. The counter is 
         calculated as the max of(proxy, average of all the 
         slave CPUs load) of the GGSN-T PIC."
   ::= { ggsnGtptEntry 9 }

ggsnGtptPeakCpuUsage OBJECT-TYPE
   SYNTAX        Gauge32
   MAX-ACCESS    read-only
   STATUS        deprecated
   DESCRIPTION
         "The counter describes the maximum CPU load of a GGSN-T PIC
          in percentage. A GGSN-T PIC contains multiple CPUs. The 
          counter is the CPU utilization of the CPU with the highest 
          value calculated over a 5 second average of a GGSN-T PIC."
   ::= { ggsnGtptEntry 10 }
--
-- Charging group
--


ggsnAcctPartialRecordGenerated OBJECT-TYPE
   SYNTAX        Counter64
   MAX-ACCESS    read-only
   STATUS        current
   DESCRIPTION
         "The number of partial Call Data Records
          generated."
   ::= { ggsnChargingInfo 1 }

ggsnAcctBillingGatewayTable OBJECT-TYPE
   SYNTAX        SEQUENCE OF BillingGatewayEntry
   MAX-ACCESS    not-accessible
   STATUS        current
   DESCRIPTION
         "The table listing the Charging Gateway Functions with
          which the GGSN communicates."
   ::= { ggsnChargingInfo 2 }

ggsnAcctBillingGatewayEntry OBJECT-TYPE
   SYNTAX        BillingGatewayEntry
   MAX-ACCESS    not-accessible
   STATUS        current
   DESCRIPTION
         "An entry representing a Charging Gateway Functions."
   INDEX         { ggsnAcctBillingGatewayIndex }
   ::= { ggsnAcctBillingGatewayTable 1 }

BillingGatewayEntry ::= SEQUENCE {
   ggsnAcctBillingGatewayIndex       Integer32,
   ggsnAcctBillingGatewayAddress     IpAddress,
   ggsnAcctDataRecTransReqSent       Counter64,
   ggsnAcctDataRecTransReqSentDup    Counter64,
   ggsnAcctDataRecTransReqCancelled  Counter64,
   ggsnAcctDataRecTransRespReceived  Counter64,
   ggsnAcctRedirectionReqReceived    Counter64,
   ggsnAcctRedirectionRespSent       Counter64
}

ggsnAcctBillingGatewayIndex OBJECT-TYPE
   SYNTAX        Integer32 (1..2147483647)
   MAX-ACCESS    not-accessible
   STATUS        current
   DESCRIPTION
         "A number uniquely identifying each Charging Gateway Functions
          with which the GGSN communicates."
   ::= { ggsnAcctBillingGatewayEntry 1 }

ggsnAcctBillingGatewayAddress OBJECT-TYPE
   SYNTAX        IpAddress
   MAX-ACCESS    read-only
   STATUS        current
   DESCRIPTION
         "The address of the Charging Gateway Functions referred to
          in this table entry."
   ::= { ggsnAcctBillingGatewayEntry 2 }

ggsnAcctDataRecTransReqSent OBJECT-TYPE
   SYNTAX        Counter64
   MAX-ACCESS    read-only
   STATUS        current
   DESCRIPTION
         "The number of Data Record Transfer Request
         messages that are sent from the GGSN to 
         the Charging Gateway Function."   
   ::= { ggsnAcctBillingGatewayEntry 3 }

ggsnAcctDataRecTransReqSentDup OBJECT-TYPE
   SYNTAX        Counter64
   MAX-ACCESS    read-only
   STATUS        current
   DESCRIPTION
         "The number of Data Record Transfer Request
          messages that are sent from the GGSN to 
          the Charging Gateway Function when the 
          Packet Transfer Command IE has the 
          'Send possibly duplicated Data Record Packet'
          value.
          
          Note: This counter is applicable 
          only when using GTP Prime version 2." 
   ::= { ggsnAcctBillingGatewayEntry 4 }

ggsnAcctDataRecTransReqCancelled OBJECT-TYPE
   SYNTAX        Counter64
   MAX-ACCESS    read-only
   STATUS        deprecated
   DESCRIPTION
         "The number of Data Record Transfer Requests
          sent with indication to cancel CDR packets
          related to previously unacknowledged sequence
          number."
   ::= { ggsnAcctBillingGatewayEntry 5 }

ggsnAcctDataRecTransRespReceived OBJECT-TYPE
   SYNTAX        Counter64
   MAX-ACCESS    read-only
   STATUS        current
   DESCRIPTION
         "The number of Data Record Transfer Response
         messages that are received from the
         Charging Gateway Function." 
   ::= { ggsnAcctBillingGatewayEntry 6 }

ggsnAcctRedirectionReqReceived OBJECT-TYPE
   SYNTAX        Counter64
   MAX-ACCESS    read-only
   STATUS        current
   DESCRIPTION
         "The number of Redirection Request
         messages that are received from the
         Charging Gateway Function."
   ::= { ggsnAcctBillingGatewayEntry 7 }

ggsnAcctRedirectionRespSent OBJECT-TYPE
   SYNTAX        Counter64
   MAX-ACCESS    read-only
   STATUS        current
   DESCRIPTION
         "The number of Redirection Response
         messages that are sent from the GGSN
         to the Charging Gateway Function."
   ::= { ggsnAcctBillingGatewayEntry 8 }


--
-- DHCP group
--


ggsnDhcpClientAddress OBJECT-TYPE
   SYNTAX        IpAddress
   MAX-ACCESS    read-only
   STATUS        current
   DESCRIPTION
         "The Address of the DHCP client of the GGSN."
   ::= { ggsnDhcpInfo 1 }

ggsnDhcpServerTable OBJECT-TYPE
   SYNTAX        SEQUENCE OF DhcpServerEntry
   MAX-ACCESS    not-accessible
   STATUS        current
   DESCRIPTION
         "The table listing the DHCP servers with
          which the GGSN communicates."
   ::= { ggsnDhcpInfo 2 }

ggsnDhcpServerEntry OBJECT-TYPE
   SYNTAX        DhcpServerEntry
   MAX-ACCESS    not-accessible
   STATUS        current
   DESCRIPTION
         "An entry representing a GGSN DHCP server."
   INDEX         { ggsnDhcpServerIndex }
   ::= { ggsnDhcpServerTable 1 }

DhcpServerEntry ::= SEQUENCE {
   ggsnDhcpServerIndex            Integer32,
   ggsnDhcpServerAddress          IpAddress,
   ggsnDhcpServerName             DisplayString,
   ggsnDhcpClientYiaddr           IpAddress,
   ggsnDhcpClientState            DisplayString,
   ggsnDhcpClientRequestsSent     Counter64,
   ggsnDhcpClientRepliesReceived  Counter64,
   ggsnDhcpClientRepliesDiscarded Counter64,
   ggsnDhcpClientDiscoversSent    Counter64,
   ggsnDhcpClientDeclinesSent     Counter64,
   ggsnDhcpClientReleasesSent     Counter64,
   ggsnDhcpClientOffersReceived   Counter64,
   ggsnDhcpClientAcksReceived     Counter64,
   ggsnDhcpClientNaksReceived     Counter64,
   ggsnDhcpClientSendErrors       Counter64,
   ggsnDhcpServerRoutingInstance  DisplayString
}

ggsnDhcpServerIndex OBJECT-TYPE
   SYNTAX        Integer32 (1..2147483647)
   MAX-ACCESS    not-accessible
   STATUS        current
   DESCRIPTION
         "A number uniquely identifying each DHCP server with
          which this client communicates."
   ::= { ggsnDhcpServerEntry 1 }

ggsnDhcpServerAddress OBJECT-TYPE
   SYNTAX        IpAddress
   MAX-ACCESS    read-only
   STATUS        current
   DESCRIPTION
         "The IP address of the DHCP server (siaddr)
          referred to in this table entry."
   ::= { ggsnDhcpServerEntry 2 }

ggsnDhcpServerName OBJECT-TYPE
   SYNTAX        DisplayString
   MAX-ACCESS    read-only
   STATUS        current
   DESCRIPTION
         "The host name of the DHCP server (sname)."
   ::= { ggsnDhcpServerEntry 3 }

ggsnDhcpClientYiaddr OBJECT-TYPE
   SYNTAX        IpAddress
   MAX-ACCESS    read-only
   STATUS        current
   DESCRIPTION
         "The IP address of the 'your' client (yiaddr)."
   ::= { ggsnDhcpServerEntry 4 }

ggsnDhcpClientState OBJECT-TYPE
   SYNTAX        DisplayString
   MAX-ACCESS    read-only
   STATUS        current
   DESCRIPTION
         "The state of the DHCP client such as RENEWING."
   ::= { ggsnDhcpServerEntry 5 }

ggsnDhcpClientRequestsSent     OBJECT-TYPE
   SYNTAX        Counter64
   MAX-ACCESS    read-only
   STATUS        current
   DESCRIPTION
         "The number of requests sent by the GGSN to this DHCP server. "
   ::= { ggsnDhcpServerEntry 6 }

ggsnDhcpClientRepliesReceived  OBJECT-TYPE
   SYNTAX        Counter64
   MAX-ACCESS    read-only
   STATUS        current
   DESCRIPTION
         "The number of replies received by the GGSN from this DHCP server."
   ::= { ggsnDhcpServerEntry 7 }

ggsnDhcpClientRepliesDiscarded OBJECT-TYPE
   SYNTAX        Counter64
   MAX-ACCESS    read-only
   STATUS        current
   DESCRIPTION
         "The number of replies received and dropped by the GGSN from this DHCP server."
   ::= { ggsnDhcpServerEntry 8 }

ggsnDhcpClientDiscoversSent OBJECT-TYPE
   SYNTAX        Counter64
   MAX-ACCESS    read-only
   STATUS        current
   DESCRIPTION
         "Specifies the number of DHCPDISCOVER messages sent by the GGSN to a DHCP server."
   ::= { ggsnDhcpServerEntry 9 }

ggsnDhcpClientDeclinesSent OBJECT-TYPE
   SYNTAX        Counter64
   MAX-ACCESS    read-only
   STATUS        current
   DESCRIPTION
         "The number of DHCPRELEASE messages sent by GGSN to this DHCP server.
          This counter is only incremented when a duplicate ip-address has been
          received from a DHCP server."
   ::= { ggsnDhcpServerEntry 10 }

ggsnDhcpClientReleasesSent OBJECT-TYPE
   SYNTAX        Counter64
   MAX-ACCESS    read-only
   STATUS        current
   DESCRIPTION
         "The number of releases sent to this server."
   ::= { ggsnDhcpServerEntry 11 }

ggsnDhcpClientOffersReceived OBJECT-TYPE
   SYNTAX        Counter64
   MAX-ACCESS    read-only
   STATUS        current
   DESCRIPTION
         "The number of offers received from this server."
   ::= { ggsnDhcpServerEntry 12 }

ggsnDhcpClientAcksReceived OBJECT-TYPE
   SYNTAX        Counter64
   MAX-ACCESS    read-only
   STATUS        current
   DESCRIPTION
         "The number of acks received from this server."
   ::= { ggsnDhcpServerEntry 13 }

ggsnDhcpClientNaksReceived OBJECT-TYPE
   SYNTAX        Counter64
   MAX-ACCESS    read-only
   STATUS        current
   DESCRIPTION
         "The number of naks received from this server."
   ::= { ggsnDhcpServerEntry 14 }

ggsnDhcpClientSendErrors OBJECT-TYPE
   SYNTAX        Counter64
   MAX-ACCESS    read-only
   STATUS        current
   DESCRIPTION
         "The number of client send errors."
   ::= { ggsnDhcpServerEntry 15 }

ggsnDhcpServerRoutingInstance OBJECT-TYPE
   SYNTAX        DisplayString
   MAX-ACCESS    read-only
   STATUS        current
   DESCRIPTION
         "The routing instance of the DHCP server."
   ::= { ggsnDhcpServerEntry 16 }

--
-- GGSN APN service-based charging (FBC) statistics
--
-- Per U PIC, per APN service-based charging (FBC) statistics
--

ggsnApnFbcStatsTable 		OBJECT-TYPE
    SYNTAX        		SEQUENCE OF ApnFbcStats
    MAX-ACCESS    		not-accessible
    STATUS        		current
    DESCRIPTION
    "SACC statistics per APN."
    ::= { ggsnFbcStats 4 }

ggsnApnFbcStatsEntry 		OBJECT-TYPE
    SYNTAX			ApnFbcStats
    MAX-ACCESS			not-accessible
    STATUS			current
    DESCRIPTION
	"SACC statistics per APN."
    INDEX         		{ ggsnGtpuIndex, ggsnApnIndex }
    ::= { ggsnApnFbcStatsTable 1 }

ApnFbcStats ::= SEQUENCE {
    ggsnApnFbcNbrOfPpsUsers		Gauge32,
    ggsnApnFbcNbrOfPpsPdpContexts	Gauge32,
    ggsnApnFbcPpsCreate			Counter64,
    ggsnApnFbcPpsReject			Counter64,
    ggsnApnFbcInitiatedDeactivation	Counter64,
    ggsnApnFbcInitialPrsReq		Counter64,
    ggsnApnFbcInitialPrsReqFailed	Counter64,
    ggsnApnFbcUpdPrsReq			Counter64,
    ggsnApnFbcUpdPrsReqFailed		Counter64,
    ggsnApnFbcStartCredReq		Counter64,
    ggsnApnFbcStartCredReqFailed	Counter64,
    ggsnApnFbcUpdCredReq		Counter64,
    ggsnApnFbcUpdCredReqFailed		Counter64,
    ggsnApnFbcStopCredReq		Counter64,
    ggsnApnFbcStopCredReqFailed		Counter64,
    ggsnApnFbcExtPrsUpd			Counter64,
    ggsnApnFbcExtCreditUpd		Counter64,
    ggsnApnFbcDurationTime		Counter64,
    ggsnApnFbcActivationBearerCtrlAccept		Counter64,
    ggsnApnFbcActivationBearerCtrlReject		Counter64,
    ggsnApnFbcActivationBearerCtrlUpgrade		Counter64,
    ggsnApnFbcActivationBearerCtrlDowngrade		Counter64,
    ggsnApnFbcModificationBearerCtrlAccept		Counter64,
    ggsnApnFbcModificationBearerCtrlDeactivate		Counter64,
    ggsnApnFbcModificationBearerCtrlUpgrade		Counter64,
    ggsnApnFbcModificationBearerCtrlDowngrade		Counter64,
    ggsnApnFbcActivationNoBearerCtrlAccept		Counter64,
    ggsnApnFbcActivationNoBearerCtrlReject		Counter64,
    ggsnApnFbcActivationNoBearerCtrlDowngrade		Counter64,
    ggsnApnFbcModificationNoBearerCtrlAccept		Counter64,
    ggsnApnFbcModificationNoBearerCtrlDeactivate	Counter64,
    ggsnApnFbcModificationNoBearerCtrlDowngrade	Counter64,
    ggsnApnSaccAttemptedServiceInitiatedQoSModification	Counter64
}

ggsnApnFbcNbrOfPpsUsers		OBJECT-TYPE
    SYNTAX			Gauge32
    MAX-ACCESS			read-only
    STATUS			current
    DESCRIPTION
    "The number of user sessions with online charging per APN."
    ::= { ggsnApnFbcStatsEntry 2 }

ggsnApnFbcNbrOfPpsPdpContexts		OBJECT-TYPE
    SYNTAX			Gauge32
    MAX-ACCESS			read-only
    STATUS			deprecated
    DESCRIPTION
    "The number of user sessions with online charging per APN."
    ::= { ggsnApnFbcStatsEntry 3 }

ggsnApnFbcPpsCreate		OBJECT-TYPE
    SYNTAX			Counter64
    MAX-ACCESS			read-only
    STATUS			current
    DESCRIPTION
    "The number of user session activations with online charging per APN."
    ::= { ggsnApnFbcStatsEntry 4 }

ggsnApnFbcPpsReject		OBJECT-TYPE
    SYNTAX			Counter64
    MAX-ACCESS			read-only
    STATUS			current
    DESCRIPTION
    "The number of user session activations with online charging rejected per APN."
    ::= { ggsnApnFbcStatsEntry 5 }

ggsnApnFbcInitiatedDeactivation	OBJECT-TYPE
    SYNTAX			Counter64
    MAX-ACCESS			read-only
    STATUS			current
    DESCRIPTION
    "The number of bearer deactivations initiated by the SACC functionality per APN."
    ::= { ggsnApnFbcStatsEntry 6 }

ggsnApnFbcInitialPrsReq		OBJECT-TYPE
    SYNTAX			Counter64
    MAX-ACCESS			read-only
    STATUS			deprecated
    DESCRIPTION
	"Number of service-based charging (FBC) initial policy/rate requests."
    ::= { ggsnApnFbcStatsEntry 7 }

ggsnApnFbcInitialPrsReqFailed	OBJECT-TYPE
    SYNTAX			Counter64
    MAX-ACCESS			read-only
    STATUS			deprecated
    DESCRIPTION
	"Number of failed service-based charging (FBC) initial
	 policy/rate requests."
    ::= { ggsnApnFbcStatsEntry 8 }

ggsnApnFbcUpdPrsReq		OBJECT-TYPE
    SYNTAX			Counter64
    MAX-ACCESS			read-only
    STATUS			deprecated
    DESCRIPTION
	"Number of service-based charging (FBC) policy/rate
	 updates/interim requests."
    ::= { ggsnApnFbcStatsEntry 9 }

ggsnApnFbcUpdPrsReqFailed	OBJECT-TYPE
    SYNTAX			Counter64
    MAX-ACCESS			read-only
    STATUS			deprecated
    DESCRIPTION
	"Number of failed service-based charging (FBC) policy/rate
	 updates/interim requests."
    ::= { ggsnApnFbcStatsEntry 10 }

ggsnApnFbcStartCredReq		OBJECT-TYPE
    SYNTAX			Counter64
    MAX-ACCESS			read-only
    STATUS			deprecated
    DESCRIPTION
	"Number of service-based charging (FBC) start credit requests
	 to pre-paid server."
    ::= { ggsnApnFbcStatsEntry 11 }

ggsnApnFbcStartCredReqFailed	OBJECT-TYPE
    SYNTAX			Counter64
    MAX-ACCESS			read-only
    STATUS			deprecated
    DESCRIPTION
	"Number of failed service-based charging (FBC) start credit requests
	 to pre-paid server."
    ::= { ggsnApnFbcStatsEntry 12 }

ggsnApnFbcUpdCredReq		OBJECT-TYPE
    SYNTAX			Counter64
    MAX-ACCESS			read-only
    STATUS			deprecated
    DESCRIPTION
	"Number of service-based charging (FBC) interim credit requests
	 to pre-paid server."
    ::= { ggsnApnFbcStatsEntry 13 }

ggsnApnFbcUpdCredReqFailed	OBJECT-TYPE
    SYNTAX			Counter64
    MAX-ACCESS			read-only
    STATUS			deprecated
    DESCRIPTION
	"Number of failed service-based charging (FBC) interim credit requests to
	 pre-paid server."
    ::= { ggsnApnFbcStatsEntry 14 }

ggsnApnFbcStopCredReq		OBJECT-TYPE
    SYNTAX			Counter64
    MAX-ACCESS			read-only
    STATUS			deprecated
    DESCRIPTION
	"Number of stop credit requests (bucket request / renewals)."
    ::= { ggsnApnFbcStatsEntry 15 }

ggsnApnFbcStopCredReqFailed	OBJECT-TYPE
    SYNTAX			Counter64
    MAX-ACCESS			read-only
    STATUS			deprecated
    DESCRIPTION
	"Number of failed stop credit requests
	 (bucket request / renewals)."
    ::= { ggsnApnFbcStatsEntry 16 }

ggsnApnFbcExtPrsUpd		OBJECT-TYPE
    SYNTAX			Counter64
    MAX-ACCESS			read-only
    STATUS			current
    DESCRIPTION
    "The number of externally initiated updates due to RAR and ASR from the PCRF per APN."
    ::= { ggsnApnFbcStatsEntry 17 }

ggsnApnFbcExtCreditUpd		OBJECT-TYPE
    SYNTAX			Counter64
    MAX-ACCESS			read-only
    STATUS			current
    DESCRIPTION
    "The number of externally initiated updates due to RAR and ASR from the OCS per APN."
    ::= { ggsnApnFbcStatsEntry 18 }

ggsnApnFbcDurationTime		OBJECT-TYPE
    SYNTAX			Counter64
    MAX-ACCESS			read-only
    STATUS			deprecated
    DESCRIPTION
    "Number of seconds measured for duration time.
     
     Note: Only valid for SACC 2.0."
    ::= { ggsnApnFbcStatsEntry 19 }

ggsnApnFbcActivationBearerCtrlAccept		OBJECT-TYPE
    SYNTAX			Counter64
    MAX-ACCESS			read-only
    STATUS			current
    DESCRIPTION
	"Number of QoS accepts at PDP Context activation with SGSN bearer control support."
    ::= { ggsnApnFbcStatsEntry 20 }

ggsnApnFbcActivationBearerCtrlReject		OBJECT-TYPE
    SYNTAX			Counter64
    MAX-ACCESS			read-only
    STATUS			current
    DESCRIPTION
    "Number of PDP Context rejects at activation with SGSN bearer control support."
    ::= { ggsnApnFbcStatsEntry 21 }

ggsnApnFbcActivationBearerCtrlUpgrade		OBJECT-TYPE
    SYNTAX			Counter64
    MAX-ACCESS			read-only
    STATUS			current
    DESCRIPTION
	"Number of QoS upgrades at PDP Context activation with SGSN bearer control support."
    ::= { ggsnApnFbcStatsEntry 22 }

ggsnApnFbcActivationBearerCtrlDowngrade		OBJECT-TYPE
    SYNTAX			Counter64
    MAX-ACCESS			read-only
    STATUS			current
    DESCRIPTION
	"Number of QoS downgrades at PDP Context activation with SGSN bearer control support."
    ::= { ggsnApnFbcStatsEntry 23 }

ggsnApnFbcModificationBearerCtrlAccept		OBJECT-TYPE
    SYNTAX			Counter64
    MAX-ACCESS			read-only
    STATUS			current
    DESCRIPTION
	"Number of QoS accepts at PDP Context modification with SGSN bearer control support."
    ::= { ggsnApnFbcStatsEntry 24 }

ggsnApnFbcModificationBearerCtrlDeactivate		OBJECT-TYPE
    SYNTAX			Counter64
    MAX-ACCESS			read-only
    STATUS			current
    DESCRIPTION
	"Number of PDP Context deactivates at modification with SGSN bearer control support."
    ::= { ggsnApnFbcStatsEntry 25 }

ggsnApnFbcModificationBearerCtrlUpgrade		OBJECT-TYPE
    SYNTAX			Counter64
    MAX-ACCESS			read-only
    STATUS			current
    DESCRIPTION
	"Number of QoS upgrades at PDP Context modification with SGSN bearer control support."
    ::= { ggsnApnFbcStatsEntry 26 }

ggsnApnFbcModificationBearerCtrlDowngrade		OBJECT-TYPE
    SYNTAX			Counter64
    MAX-ACCESS			read-only
    STATUS			current
    DESCRIPTION
	"Number of QoS downgrades at PDP Context modification with SGSN bearer control support."
    ::= { ggsnApnFbcStatsEntry 27 }

ggsnApnFbcActivationNoBearerCtrlAccept		OBJECT-TYPE
    SYNTAX			Counter64
    MAX-ACCESS			read-only
    STATUS			current
    DESCRIPTION
	"Number of QoS accepts at PDP Context activation without SGSN bearer control support."
    ::= { ggsnApnFbcStatsEntry 28 }

ggsnApnFbcActivationNoBearerCtrlReject		OBJECT-TYPE
    SYNTAX			Counter64
    MAX-ACCESS			read-only
    STATUS			current
    DESCRIPTION
	"Number of PDP Context rejects at activation without SGSN bearer control support."
    ::= { ggsnApnFbcStatsEntry 29 }

ggsnApnFbcActivationNoBearerCtrlDowngrade		OBJECT-TYPE
    SYNTAX			Counter64
    MAX-ACCESS			read-only
    STATUS			current
    DESCRIPTION
	"Number of QoS downgrades at PDP Context activation without SGSN bearer control support."
    ::= { ggsnApnFbcStatsEntry 30 }

ggsnApnFbcModificationNoBearerCtrlAccept		OBJECT-TYPE
    SYNTAX			Counter64
    MAX-ACCESS			read-only
    STATUS			current
    DESCRIPTION
	"Number of QoS accepts at PDP Context modification without SGSN bearer control support."
    ::= { ggsnApnFbcStatsEntry 31 }

ggsnApnFbcModificationNoBearerCtrlDeactivate		OBJECT-TYPE
    SYNTAX			Counter64
    MAX-ACCESS			read-only
    STATUS			current
    DESCRIPTION
	"Number of PDP Context deactivates at modification without SGSN bearer control support."
    ::= { ggsnApnFbcStatsEntry 32 }

ggsnApnFbcModificationNoBearerCtrlDowngrade		OBJECT-TYPE
    SYNTAX			Counter64
    MAX-ACCESS			read-only
    STATUS			current
    DESCRIPTION
	"Number of QoS downgrades at PDP Context modification without SGSN bearer control support."
    ::= { ggsnApnFbcStatsEntry 33 }

ggsnApnSaccAttemptedServiceInitiatedQoSModification		OBJECT-TYPE
    SYNTAX			Counter64
    MAX-ACCESS			read-only
    STATUS			current
    DESCRIPTION
	"Number of attempted service initiated QoS modifications for default bearer."
    ::= { ggsnApnFbcStatsEntry 34 }

--
-- GGSN service-based charging (FBC) Authorization statistics
--
-- Per node
--

ggsnFbcAuthStats	OBJECT IDENTIFIER ::= { ggsnFbcAuthorizationStats 1 }

ggsnFbcUserAuthPacketsDropped		OBJECT-TYPE
    SYNTAX				Counter64
    MAX-ACCESS				read-only
    STATUS				deprecated
    DESCRIPTION
    "Number of packets discarded by authorization for
     service classes originating from the policy server list.
     Only dropped downlink packets result in incrementation of the counter.
     
     Note: Only valid for SACC 2.0."
    ::= { ggsnFbcAuthStats 2 }

ggsnFbcDefaultAuthPacketsDropped	OBJECT-TYPE
    SYNTAX				Counter64
    MAX-ACCESS				read-only
    STATUS				deprecated
    DESCRIPTION
    "Number of packets discarded by authorization for service
     classes originating from the policy server communication
     error fallback list (default list).
     Only dropped downlink packets result in incrementation of the counter.
     
     Note: Only valid for SACC 2.0."
    ::= { ggsnFbcAuthStats 3 }

ggsnFbcEmptyBucketPacketsDropped	OBJECT-TYPE
    SYNTAX				Counter64
    MAX-ACCESS				read-only
    STATUS				deprecated
    DESCRIPTION
    "Number of packets discarded by authorization for service
     classes originating from the empty-bucket based service
     class list. Only dropped downlink packets result in incrementation
     of the counter.
     
     Note: Only valid for SACC 2.0."
    ::= { ggsnFbcAuthStats 4 }

ggsnFbcComFailAuthPacketsDropped	OBJECT-TYPE
    SYNTAX				Counter64
    MAX-ACCESS				read-only
    STATUS				deprecated
    DESCRIPTION
    "Number of packets discarded by authorization for service
     classes originating from the prepaid server communication
     error fallback list (default list). Only dropped downlink 
     packets result in incrementation of the counter.
     
     Note: Only valid for SACC 2.0."
    ::= { ggsnFbcAuthStats 5 }

ggsnFbcIdentErrorPacketsDropped		OBJECT-TYPE
    SYNTAX				Counter64
    MAX-ACCESS				read-only
    STATUS				deprecated
    DESCRIPTION
    "Number of packets discarded by authorization due to a
     service identification error. Only dropped downlink packets
     result in incrementation of the counter.
     
     Note: Only valid for SACC 2.0."
    ::= { ggsnFbcAuthStats 6 }


--
-- GGSN APN service-based charging (FBC) SID statistics
--
-- Per U PIC, per APN, per SID
--

ggsnApnFbcServIdentStatsTable 	OBJECT-TYPE
    SYNTAX        		SEQUENCE OF ApnFbcServIdentStats
    MAX-ACCESS    		not-accessible
    STATUS        		current
    DESCRIPTION
    "Service data flow statistics per APN."
    ::= { ggsnFbcStats 5 }

ggsnApnFbcServIdentStatsEntry		OBJECT-TYPE
    SYNTAX			ApnFbcServIdentStats
    MAX-ACCESS			not-accessible
    STATUS			current
    DESCRIPTION
	"Service data flow statistics per APN."
    INDEX { ggsnGtpuIndex, ggsnApnIndex, ggsnServIdentIndex }
    ::= { ggsnApnFbcServIdentStatsTable 1 }

ApnFbcServIdentStats ::= SEQUENCE {
    ggsnServIdentIndex		Integer32,
    ggsnApnFbcServIdentUplinkBytes	Counter64,
    ggsnApnFbcServIdentDownlinkBytes	Counter64,
    ggsnApnFbcServIdentEventTrans	Counter64,
    ggsnApnFbcServIdentEventTransFail	Counter64,
    ggsnApnFbcServIdentEventStartTrans	Counter64,
    ggsnApnFbcServIdentEventSuccessTrans	Counter64
}

ggsnServIdentIndex		OBJECT-TYPE
   SYNTAX			Integer32 (1..4096)
   MAX-ACCESS			not-accessible
   STATUS			current
   DESCRIPTION
   "The service data flow identifier."
   ::= { ggsnApnFbcServIdentStatsEntry 1 }

ggsnApnFbcServIdentUplinkBytes		OBJECT-TYPE
    SYNTAX				Counter64
    MAX-ACCESS				read-only
    STATUS				current
    DESCRIPTION
    "The number of uplink bytes on service data flow per APN."
    ::= { ggsnApnFbcServIdentStatsEntry 2 }

ggsnApnFbcServIdentDownlinkBytes	OBJECT-TYPE
    SYNTAX				Counter64
    MAX-ACCESS				read-only
    STATUS				current
    DESCRIPTION
    "The number of downlink bytes on service data flow per APN."
    ::= { ggsnApnFbcServIdentStatsEntry 4 }

ggsnApnFbcServIdentEventTrans	OBJECT-TYPE
    SYNTAX				Counter64
    MAX-ACCESS				read-only
    STATUS				deprecated
    DESCRIPTION
	"Number of transactions per service identifier for which event charging applies."
    ::= { ggsnApnFbcServIdentStatsEntry 5 }

ggsnApnFbcServIdentEventTransFail	OBJECT-TYPE
    SYNTAX				Counter64
    MAX-ACCESS				read-only
    STATUS				deprecated
    DESCRIPTION
	"Number of failed transactions (error response or abnormal termination)
	 per service identifier for which event charging applies."
    ::= { ggsnApnFbcServIdentStatsEntry 6 }

ggsnApnFbcServIdentEventStartTrans	OBJECT-TYPE
    SYNTAX				Counter64
    MAX-ACCESS				read-only
    STATUS				deprecated
    DESCRIPTION
	"Number of start transaction events per service identifier for which event charging applies."
    ::= { ggsnApnFbcServIdentStatsEntry 7 }

ggsnApnFbcServIdentEventSuccessTrans	OBJECT-TYPE
    SYNTAX				Counter64
    MAX-ACCESS				read-only
    STATUS				deprecated
    DESCRIPTION
	"Number of successful transaction events per service identifier for which event charging applies."
    ::= { ggsnApnFbcServIdentStatsEntry 8 }

--
-- GGSN APN service-based charging (FBC) SCID statistics
--
-- Per U PIC, per APN, per SCID
--

ggsnApnFbcServClassStatsTable 	OBJECT-TYPE
    SYNTAX        		SEQUENCE OF ApnFbcServClassStats
    MAX-ACCESS    		not-accessible
    STATUS        		deprecated
    DESCRIPTION
         "Service-based charging (FBC) service ID statistics for an APN."
    ::= { ggsnFbcStats 6 }

ggsnApnFbcServClassStatsEntry		OBJECT-TYPE
    SYNTAX			ApnFbcServClassStats
    MAX-ACCESS			not-accessible
    STATUS			deprecated
    DESCRIPTION
	"A conceptual row listing the service-based charging (FBC) service ID
	 statistics for each APN."
    INDEX { ggsnGtpuIndex, ggsnApnIndex, ggsnServClassIndex }
    ::= { ggsnApnFbcServClassStatsTable 1 }

ApnFbcServClassStats ::= SEQUENCE {
    ggsnServClassIndex		Integer32,
    ggsnApnFbcServClassUplinkBytes	Counter64,
    ggsnApnFbcServClassDownlinkBytes	Counter64,
    ggsnApnFbcServClassActiveTime	Counter64
}

ggsnServClassIndex		OBJECT-TYPE
   SYNTAX			Integer32 (1..4096)
   MAX-ACCESS			not-accessible
   STATUS			deprecated
   DESCRIPTION
         "The service ID for the statistics."
   ::= { ggsnApnFbcServClassStatsEntry 1 }

ggsnApnFbcServClassUplinkBytes		OBJECT-TYPE
    SYNTAX				Counter64
    MAX-ACCESS				read-only
    STATUS				deprecated
    DESCRIPTION
    "Number of uplink bytes marked with rating group (RG)."
    ::= { ggsnApnFbcServClassStatsEntry 2 }

ggsnApnFbcServClassDownlinkBytes	OBJECT-TYPE
    SYNTAX				Counter64
    MAX-ACCESS				read-only
    STATUS				deprecated
    DESCRIPTION
    "Number of downlink bytes marked with rating group (RG)."
    ::= { ggsnApnFbcServClassStatsEntry 4 }

ggsnApnFbcServClassActiveTime	OBJECT-TYPE
    SYNTAX				Counter64
    MAX-ACCESS				read-only
    STATUS				deprecated
    DESCRIPTION
    "Number of seconds measured for active time for service class.
    
     Note: Only valid for SACC 2.0."
    ::= { ggsnApnFbcServClassStatsEntry 6 }

ggsnFbcExtPrsUpdReqNoMatch      OBJECT-TYPE
    SYNTAX			Counter64
    MAX-ACCESS			read-only
    STATUS			deprecated
    DESCRIPTION
         "Number of externally initiated URT updates for users
          without PDP context.
          
          Note: Only valid for SACC 2.0."
    ::= { ggsnFbcStats 7 }

ggsnFbcExtCreditUpdReqNoMatch   OBJECT-TYPE
    SYNTAX			Counter64
    MAX-ACCESS			read-only
    STATUS			deprecated
    DESCRIPTION
         "Number of externally initiated quota updates for users
          without PDP context.

          Note: Only valid for SACC 2.0."
    ::= { ggsnFbcStats 8 }

ggsnFbcExtUpdReqFailure         OBJECT-TYPE
    SYNTAX			Counter64
    MAX-ACCESS			read-only
    STATUS			deprecated
    DESCRIPTION
         "Number of unidentified messages including messages with
          authentication id failure.
          
          Note: Only valid for SACC 2.0."
    ::= { ggsnFbcStats 9 }



--
-- GGSN APN service-based charging (FBC) PR-AS statistics
--
-- Per APN, per PR-AS ID
--

ggsnApnFbcPrasStatsTable 	OBJECT-TYPE
    SYNTAX        		SEQUENCE OF ApnFbcPrasStats
    MAX-ACCESS    		not-accessible
    STATUS        		current
    DESCRIPTION
    "Policy control application system statistics per APN."
    ::= { ggsnFbcStats 10 }

ggsnApnFbcPrasStatsEntry		OBJECT-TYPE
    SYNTAX			ApnFbcPrasStats
    MAX-ACCESS			not-accessible
    STATUS			current
    DESCRIPTION
	"Policy control application system statistics per APN."
    INDEX { ggsnApnIndex, ggsnPrasIndex }
    ::= { ggsnApnFbcPrasStatsTable 1 }

ApnFbcPrasStats ::= SEQUENCE {
    ggsnPrasIndex		Integer32,
    ggsnApnFbcPrasName		DisplayString,
    ggsnApnFbcPrasStartReq	Counter64,
    ggsnApnFbcPrasStartReqFail	Counter64,
    ggsnApnFbcPrasUpdateReq	Counter64,
    ggsnApnFbcPrasUpdateReqFail	Counter64,
    ggsnApnFbcPrasStopReq	Counter64,
    ggsnApnFbcPrasStopReqFail	Counter64,
    ggsnApnFbcPrasUserServiceDenied	Counter64,
    ggsnApnFbcPrasUserUnknown	Counter64
}

ggsnPrasIndex		OBJECT-TYPE
   SYNTAX			Integer32
   MAX-ACCESS			not-accessible
   STATUS			current
   DESCRIPTION
   "The PCRF index."
   ::= { ggsnApnFbcPrasStatsEntry 1 }

ggsnApnFbcPrasName OBJECT-TYPE
   SYNTAX        DisplayString
   MAX-ACCESS    read-only
   STATUS        current
   DESCRIPTION
   "The PCRF identifier."
   ::= { ggsnApnFbcPrasStatsEntry 2 }

ggsnApnFbcPrasStartReq		OBJECT-TYPE
    SYNTAX				Counter64
    MAX-ACCESS				read-only
    STATUS				current
    DESCRIPTION
    "The number of initial requests towards the PCRF per APN."
    ::= { ggsnApnFbcPrasStatsEntry 3 }

ggsnApnFbcPrasStartReqFail		OBJECT-TYPE
    SYNTAX				Counter64
    MAX-ACCESS				read-only
    STATUS				current
    DESCRIPTION
    "The number of failed initial requests towards the PCRF per APN."
    ::= { ggsnApnFbcPrasStatsEntry 4 }

ggsnApnFbcPrasUpdateReq		OBJECT-TYPE
    SYNTAX				Counter64
    MAX-ACCESS				read-only
    STATUS				current
    DESCRIPTION
    "The number of update requests towards the PCRF per APN."
    ::= { ggsnApnFbcPrasStatsEntry 5 }

ggsnApnFbcPrasUpdateReqFail		OBJECT-TYPE
    SYNTAX				Counter64
    MAX-ACCESS				read-only
    STATUS				current
    DESCRIPTION
    "The number of failed update requests towards the PCRF per APN."
    ::= { ggsnApnFbcPrasStatsEntry 6 }

ggsnApnFbcPrasStopReq		OBJECT-TYPE
    SYNTAX				Counter64
    MAX-ACCESS				read-only
    STATUS				current
    DESCRIPTION
    "The number of termination requests towards the PCRF per APN."
    ::= { ggsnApnFbcPrasStatsEntry 7 }

ggsnApnFbcPrasStopReqFail		OBJECT-TYPE
    SYNTAX				Counter64
    MAX-ACCESS				read-only
    STATUS				current
    DESCRIPTION
    "The number of failed termination requests towards the PCRF per APN."
    ::= { ggsnApnFbcPrasStatsEntry 8 }

ggsnApnFbcPrasUserServiceDenied		OBJECT-TYPE
    SYNTAX				Counter64
    MAX-ACCESS				read-only
    STATUS				current
    DESCRIPTION
	"The number of requests towards the PCRF per APN that failed with result code User Service Denied."
    ::= { ggsnApnFbcPrasStatsEntry 9 }

ggsnApnFbcPrasUserUnknown		OBJECT-TYPE
    SYNTAX				Counter64
    MAX-ACCESS				read-only
    STATUS				current
    DESCRIPTION
	"The number of requests towards the PCRF per APN that failed with result code User Unknown."
    ::= { ggsnApnFbcPrasStatsEntry 10 }



--
-- GGSN APN service-based charging (FBC) CC-AS statistics
--
-- Per APN, per CC-AS ID
--

ggsnApnFbcCcasStatsTable 	OBJECT-TYPE
    SYNTAX        		SEQUENCE OF ApnFbcCcasStats
    MAX-ACCESS    		not-accessible
    STATUS        		current
    DESCRIPTION
    "Online charging application system statistics per APN."
    ::= { ggsnFbcStats 11 }

ggsnApnFbcCcasStatsEntry		OBJECT-TYPE
    SYNTAX			ApnFbcCcasStats
    MAX-ACCESS			not-accessible
    STATUS			current
    DESCRIPTION
    "Online charging application system statistics per APN."
    INDEX { ggsnApnIndex, ggsnCcasIndex }
    ::= { ggsnApnFbcCcasStatsTable 1 }

ApnFbcCcasStats ::= SEQUENCE {
    ggsnCcasIndex		Integer32,
    ggsnApnFbcCcasName		DisplayString,
    ggsnApnFbcCcasStartReq	Counter64,
    ggsnApnFbcCcasStartReqFail	Counter64,
    ggsnApnFbcCcasUpdateReq	Counter64,
    ggsnApnFbcCcasUpdateReqFail	Counter64,
    ggsnApnFbcCcasStopReq	Counter64,
    ggsnApnFbcCcasStopReqFail	Counter64,
    ggsnApnFbcCcasUserServiceDenied	Counter64,
    ggsnApnFbcCcasUserUnknown	Counter64,
    ggsnApnSaccCcasAuthReject	Counter64,
    ggsnApnSaccCcasCcNotApplicable	Counter64
}

ggsnCcasIndex		OBJECT-TYPE
    SYNTAX			Integer32
    MAX-ACCESS			not-accessible
    STATUS			current
    DESCRIPTION
    "The OCS index."
    ::= { ggsnApnFbcCcasStatsEntry 1 }

ggsnApnFbcCcasName OBJECT-TYPE
    SYNTAX        DisplayString
    MAX-ACCESS    read-only
    STATUS        current
    DESCRIPTION
    "The OCS identifier."
    ::= { ggsnApnFbcCcasStatsEntry 2 }

ggsnApnFbcCcasStartReq		OBJECT-TYPE
    SYNTAX				Counter64
    MAX-ACCESS				read-only
    STATUS				current
    DESCRIPTION
    "The number of initial requests towards the OCS per APN."
    ::= { ggsnApnFbcCcasStatsEntry 3 }

ggsnApnFbcCcasStartReqFail		OBJECT-TYPE
    SYNTAX				Counter64
    MAX-ACCESS				read-only
    STATUS				current
    DESCRIPTION
    "The number of failed initial requests towards the OCS per APN."
    ::= { ggsnApnFbcCcasStatsEntry 4 }

ggsnApnFbcCcasUpdateReq		OBJECT-TYPE
    SYNTAX				Counter64
    MAX-ACCESS				read-only
    STATUS				current
    DESCRIPTION
    "The number of update requests towards the OCS per APN."
    ::= { ggsnApnFbcCcasStatsEntry 5 }

ggsnApnFbcCcasUpdateReqFail		OBJECT-TYPE
    SYNTAX				Counter64
    MAX-ACCESS				read-only
    STATUS				current
    DESCRIPTION
    "The number of failed update requests towards the OCS per APN."
    ::= { ggsnApnFbcCcasStatsEntry 6 }

ggsnApnFbcCcasStopReq		OBJECT-TYPE
    SYNTAX				Counter64
    MAX-ACCESS				read-only
    STATUS				current
    DESCRIPTION
    "The number of termination requests towards the OCS per APN."
    ::= { ggsnApnFbcCcasStatsEntry 7 }

ggsnApnFbcCcasStopReqFail		OBJECT-TYPE
    SYNTAX				Counter64
    MAX-ACCESS				read-only
    STATUS				current
    DESCRIPTION
    "The number of failed termination requests towards the OCS per APN."
    ::= { ggsnApnFbcCcasStatsEntry 8 }

ggsnApnFbcCcasUserServiceDenied		OBJECT-TYPE
    SYNTAX				Counter64
    MAX-ACCESS				read-only
    STATUS				current
    DESCRIPTION
    "The number of requests towards the OCS per APN that failed with result code User Service Denied."
    ::= { ggsnApnFbcCcasStatsEntry 9 }

ggsnApnFbcCcasUserUnknown		OBJECT-TYPE
    SYNTAX				Counter64
    MAX-ACCESS				read-only
    STATUS				current
    DESCRIPTION
    "The number of requests towards the OCS per APN that failed with result code User Unknown."
    ::= { ggsnApnFbcCcasStatsEntry 10 }

ggsnApnSaccCcasAuthReject		OBJECT-TYPE
    SYNTAX				Counter64
    MAX-ACCESS				read-only
    STATUS				current
    DESCRIPTION
    "The number of requests towards the OCS per APN that failed with result code Authorization Rejected."
    ::= { ggsnApnFbcCcasStatsEntry 11 }

ggsnApnSaccCcasCcNotApplicable		OBJECT-TYPE
    SYNTAX				Counter64
    MAX-ACCESS				read-only
    STATUS				current
    DESCRIPTION
    "The number of requests towards the OCS per APN that failed with result code Credit Control Not Applicable."
    ::= { ggsnApnFbcCcasStatsEntry 12 }



--
-- GGSN service-based charging (FBC) DAS statistics
--
-- Per DAS ID
--

ggsnFbcDiamApplSysStatsTable 	OBJECT-TYPE
    SYNTAX        		SEQUENCE OF FbcDiamApplSysStats
    MAX-ACCESS    		not-accessible
    STATUS        		current
    DESCRIPTION
    "Diameter application system statistics."
    ::= { ggsnFbcStats 12 }

ggsnFbcDiamApplSysStatsEntry		OBJECT-TYPE
    SYNTAX			FbcDiamApplSysStats
    MAX-ACCESS			not-accessible
    STATUS			current
    DESCRIPTION
    "Diameter application system statistics."
    INDEX { ggsnDiamApplSysIndex }
    ::= { ggsnFbcDiamApplSysStatsTable 1 }

FbcDiamApplSysStats ::= SEQUENCE {
    ggsnDiamApplSysIndex		Integer32,
    ggsnFbcDiamApplSysName		DisplayString,
    ggsnFbcDiamApplSysReq	Counter64
}

ggsnDiamApplSysIndex		OBJECT-TYPE
    SYNTAX			Integer32
    MAX-ACCESS			not-accessible
    STATUS			current
    DESCRIPTION
    "The diamater application system index."
    ::= { ggsnFbcDiamApplSysStatsEntry 1 }

ggsnFbcDiamApplSysName OBJECT-TYPE
    SYNTAX        DisplayString
    MAX-ACCESS    read-only
    STATUS        current
    DESCRIPTION
    "The diameter application system identifier."
    ::= { ggsnFbcDiamApplSysStatsEntry 2 }

ggsnFbcDiamApplSysReq		OBJECT-TYPE
    SYNTAX				Counter64
    MAX-ACCESS				read-only
    STATUS				current
    DESCRIPTION
    "The number of requests towards the diameter application system."
    ::= { ggsnFbcDiamApplSysStatsEntry 3 }

--
-- GGSN APN service-based charging (FBC) Rate Group statistics
--
-- Per APN, per RG
--

ggsnApnFbcRateGroupStatsTable 	OBJECT-TYPE
    SYNTAX        		SEQUENCE OF ApnFbcRateGroupStats
    MAX-ACCESS    		not-accessible
    STATUS        		obsolete
    DESCRIPTION
         "Service-based charging (FBC) rate group statistics for an APN."
    ::= { ggsnFbcStats 13 }

ggsnApnFbcRateGroupStatsEntry		OBJECT-TYPE
    SYNTAX			ApnFbcRateGroupStats
    MAX-ACCESS			not-accessible
    STATUS			obsolete
    DESCRIPTION
	"A conceptual row listing the service-based charging (FBC) rate group statistics for each APN."
    INDEX { ggsnApnIndex, ggsnRateGroupIndex }
    ::= { ggsnApnFbcRateGroupStatsTable 1 }

ApnFbcRateGroupStats ::= SEQUENCE {
    ggsnRateGroupIndex		Integer32,
    ggsnApnFbcRateGroupEventStartTrans Counter64,
    ggsnApnFbcRateGroupEventSuccessTrans Counter64
}

ggsnRateGroupIndex		OBJECT-TYPE
   SYNTAX			Integer32 (1..65535)
   MAX-ACCESS			not-accessible
   STATUS			obsolete
   DESCRIPTION
         "The rate group for the statistics."
   ::= { ggsnApnFbcRateGroupStatsEntry 1 }

ggsnApnFbcRateGroupEventStartTrans 	OBJECT-TYPE
    SYNTAX				Counter64
    MAX-ACCESS				read-only
    STATUS				obsolete
    DESCRIPTION
	"Number of start transaction events per rate group."
    ::= { ggsnApnFbcRateGroupStatsEntry 2 }

ggsnApnFbcRateGroupEventSuccessTrans  OBJECT-TYPE
    SYNTAX				Counter64
    MAX-ACCESS				read-only
    STATUS				obsolete
    DESCRIPTION
	"Number of successful transaction events per rate group."
    ::= { ggsnApnFbcRateGroupStatsEntry 3 }


--
-- GGSN APN service-based charging PCRF statistics
--
-- Per APN, per PCRF
--

ggsnApnSaccPcrfStatsTable 	OBJECT-TYPE
    SYNTAX        		SEQUENCE OF ApnSaccPcrfStats
    MAX-ACCESS    		not-accessible
    STATUS        		current
    DESCRIPTION
    "PCRF statistics per APN."
    ::= { ggsnFbcStats 14 }

ggsnApnSaccPcrfStatsEntry	OBJECT-TYPE
    SYNTAX			ApnSaccPcrfStats
    MAX-ACCESS			not-accessible
    STATUS			current
    DESCRIPTION
    "PCRF statistics per APN."
    INDEX				{ ggsnApnIndex, ggsnPcrfIndex }
    ::= { ggsnApnSaccPcrfStatsTable 1 }

ApnSaccPcrfStats ::= SEQUENCE {
    ggsnPcrfIndex				Integer32,
    ggsnApnSaccPcrfName  			DisplayString,
    ggsnApnSaccPcrfAuthorFail			Counter64,
    ggsnApnSaccPcrfAuthenFail			Counter64,
    ggsnApnSaccPcrfUpdCcReqSessIdNoMatch	Counter64,
    ggsnApnSaccPcrfActivePdpContextUsageReporting  Gauge32,
    ggsnApnSaccPcrfActiveIPcanSessions		Gauge32,
    ggsnApnSaccPcrfActiveDedicatedIPcanBearers		Gauge32
}

ggsnPcrfIndex			OBJECT-TYPE
    SYNTAX			Integer32
    MAX-ACCESS			not-accessible
    STATUS			current
    DESCRIPTION
    "The PCRF index."
    ::= { ggsnApnSaccPcrfStatsEntry 1 }

ggsnApnSaccPcrfName 		OBJECT-TYPE
    SYNTAX        		DisplayString
    MAX-ACCESS    		read-only
    STATUS        		current
    DESCRIPTION
    "The PCRF identifier."
    ::= { ggsnApnSaccPcrfStatsEntry 2 }

ggsnApnSaccPcrfAuthorFail		OBJECT-TYPE
    SYNTAX				Counter64
    MAX-ACCESS				read-only
    STATUS				current
    DESCRIPTION
    "The number of requests towards the PCRF per APN that failed with result code Authorization Rejected."
    ::= { ggsnApnSaccPcrfStatsEntry 3 }

ggsnApnSaccPcrfAuthenFail		OBJECT-TYPE
    SYNTAX				Counter64
    MAX-ACCESS				read-only
    STATUS				current
    DESCRIPTION
    "The number of requests towards the OCS per APN that failed with result code Authentication Rejected."
    ::= { ggsnApnSaccPcrfStatsEntry 4 }

ggsnApnSaccPcrfUpdCcReqSessIdNoMatch	OBJECT-TYPE
    SYNTAX				Counter64
    MAX-ACCESS				read-only
    STATUS				current
    DESCRIPTION
    "The number of requests towards the OCS per APN that failed with result code Unknown Session ID."
    ::= { ggsnApnSaccPcrfStatsEntry 5 }

ggsnApnSaccPcrfActivePdpContextUsageReporting	OBJECT-TYPE
    SYNTAX				Gauge32
    MAX-ACCESS				read-only
    STATUS				current
    DESCRIPTION
    "The number of IP-CAN sessions with usage monitoring or usage reporting over Gx per APN."
    ::= { ggsnApnSaccPcrfStatsEntry 6 }

ggsnApnSaccPcrfActiveIPcanSessions	OBJECT-TYPE
    SYNTAX				Gauge32
    MAX-ACCESS				read-only
    STATUS				current
    DESCRIPTION
    "The number of active IP-CAN sessions with policy control over Gx per APN."
    ::= { ggsnApnSaccPcrfStatsEntry 7 }

ggsnApnSaccPcrfActiveDedicatedIPcanBearers	OBJECT-TYPE
    SYNTAX				Gauge32
    MAX-ACCESS				read-only
    STATUS				current
    DESCRIPTION
    "The number of active dedicated IP-CAN bearers with policy control over Gx per APN."
    ::= { ggsnApnSaccPcrfStatsEntry 8 }

--
-- GGSN APN service-based charging RS statistics
--
-- Per APN, per RS
--

ggsnApnSaccRsStatsTable 	OBJECT-TYPE
    SYNTAX        		SEQUENCE OF ApnSaccRsStats
    MAX-ACCESS    		not-accessible
    STATUS        		current
    DESCRIPTION
    "Rule space statistics per APN."
    ::= { ggsnFbcStats 15 }

ggsnApnSaccRsStatsEntry 	OBJECT-TYPE
    SYNTAX			ApnSaccRsStats
    MAX-ACCESS			not-accessible
    STATUS			current
    DESCRIPTION
    "Rule space statistics per APN."
    INDEX				{ ggsnApnIndex, ggsnRsIndex }
    ::= { ggsnApnSaccRsStatsTable 1 }

ApnSaccRsStats ::= SEQUENCE {
    ggsnRsIndex 				Integer32,
    ggsnApnSaccRsName				DisplayString,
    ggsnApnSaccRsUplinkBytes			Counter64,
    ggsnApnSaccRsDownlinkBytes			Counter64,
    ggsnApnSaccRsServiceInstances		Counter64,
    ggsnApnSaccRsAuthDownlinkPacketsDropped	Counter64,
    ggsnApnSaccRsAuthUplinkPacketsDropped	Counter64,
    ggsnApnSaccRsGateDownlinkPacketsDropped	Counter64,
    ggsnApnSaccRsGateUplinkPacketsDropped	Counter64
}

ggsnRsIndex			OBJECT-TYPE
    SYNTAX			Integer32
    MAX-ACCESS			not-accessible
    STATUS			current
    DESCRIPTION
    "The rule space index."
    ::= { ggsnApnSaccRsStatsEntry 1 }

ggsnApnSaccRsName 		OBJECT-TYPE
    SYNTAX        		DisplayString
    MAX-ACCESS    		read-only
    STATUS        		current
    DESCRIPTION
    "The rule space identifier."
    ::= { ggsnApnSaccRsStatsEntry 2 }

ggsnApnSaccRsUplinkBytes		OBJECT-TYPE
    SYNTAX				Counter64
    MAX-ACCESS				read-only
    STATUS				current
    DESCRIPTION
    "The number of uplink bytes on rule space per APN."
    ::= { ggsnApnSaccRsStatsEntry 3 }

ggsnApnSaccRsDownlinkBytes		OBJECT-TYPE
    SYNTAX				Counter64
    MAX-ACCESS				read-only
    STATUS				current
    DESCRIPTION
    "The number of downlink bytes on rule space per APN."
    ::= { ggsnApnSaccRsStatsEntry 4 }

ggsnApnSaccRsServiceInstances		OBJECT-TYPE
    SYNTAX				Counter64
    MAX-ACCESS				read-only
    STATUS				deprecated
    DESCRIPTION
    "Number of service instances identified per APN and Rule Space."
    ::= { ggsnApnSaccRsStatsEntry 5 }

ggsnApnSaccRsAuthDownlinkPacketsDropped 	OBJECT-TYPE
    SYNTAX					Counter64
    MAX-ACCESS					read-only
    STATUS					current
    DESCRIPTION
    "The number of discarded downlink packets due to authorization based on policy and credit control."
    ::= { ggsnApnSaccRsStatsEntry 6 }

ggsnApnSaccRsAuthUplinkPacketsDropped		OBJECT-TYPE
    SYNTAX					Counter64
    MAX-ACCESS					read-only
    STATUS					current
    DESCRIPTION
    "The number of discarded uplink packets due to authorization based on policy and credit control."
    ::= { ggsnApnSaccRsStatsEntry 7 }

ggsnApnSaccRsGateDownlinkPacketsDropped		OBJECT-TYPE
    SYNTAX					Counter64
    MAX-ACCESS				read-only
    STATUS					current
    DESCRIPTION
    "The number of discarded downlink packets due to closed gate."
    ::= { ggsnApnSaccRsStatsEntry 8 }

ggsnApnSaccRsGateUplinkPacketsDropped		OBJECT-TYPE
    SYNTAX					Counter64
    MAX-ACCESS				read-only
    STATUS					current
    DESCRIPTION
    "The number of discarded uplink packets due to closed gate."
    ::= { ggsnApnSaccRsStatsEntry 9 }

--
-- GGSN APN service-based charging (SACC 2) SID statistics
--
-- Per U PIC, per APN, per SID
--

ggsnApnSacc2ServIdentStatsTable	OBJECT-TYPE
    SYNTAX                      SEQUENCE OF ApnSacc2ServIdentStats
    MAX-ACCESS                  not-accessible
    STATUS                      deprecated
    DESCRIPTION
         "Service-based charging (SACC 2) service ID statistics for an APN."
    ::= { ggsnFbcStats 16 }

ggsnApnSacc2ServIdentStatsEntry OBJECT-TYPE
    SYNTAX                      ApnSacc2ServIdentStats
    MAX-ACCESS                  not-accessible
    STATUS                      deprecated
    DESCRIPTION
        "A conceptual row listing the service-based charging (SACC 2) service ID
         statistics for each APN."
    INDEX { ggsnGtpuIndex, ggsnApnIndex, ggsnSacc2ServIdentIndex }
    ::= { ggsnApnSacc2ServIdentStatsTable 1 }

ApnSacc2ServIdentStats ::= SEQUENCE {
    ggsnSacc2ServIdentIndex			Unsigned32,
    ggsnApnSacc2ServIdentUplinkBytes    	Counter64,
    ggsnApnSacc2ServIdentDownlinkBytes  	Counter64,
    ggsnApnSacc2ServIdentEventTrans     	Counter64,
    ggsnApnSacc2ServIdentEventTransFail 	Counter64,
    ggsnApnSacc2ServIdentEventStartTrans	Counter64,
    ggsnApnSacc2ServIdentEventSuccessTrans	Counter64
}

ggsnSacc2ServIdentIndex		OBJECT-TYPE
   SYNTAX                       Unsigned32
   MAX-ACCESS                   not-accessible
   STATUS                       deprecated
   DESCRIPTION
         "The service ID for the statistics."
   ::= { ggsnApnSacc2ServIdentStatsEntry 1 }

ggsnApnSacc2ServIdentUplinkBytes        OBJECT-TYPE
    SYNTAX                              Counter64
    MAX-ACCESS                          read-only
    STATUS                              deprecated
    DESCRIPTION
        "Number of uplink bytes marked with service identifier."
    ::= { ggsnApnSacc2ServIdentStatsEntry 2 }

ggsnApnSacc2ServIdentDownlinkBytes      OBJECT-TYPE
    SYNTAX                              Counter64
    MAX-ACCESS                          read-only
    STATUS                              deprecated
    DESCRIPTION
        "Number of downlink bytes marked with service identifier."
    ::= { ggsnApnSacc2ServIdentStatsEntry 4 }

ggsnApnSacc2ServIdentEventTrans	   	OBJECT-TYPE
    SYNTAX                              Counter64
    MAX-ACCESS                          read-only
    STATUS                              deprecated
    DESCRIPTION
        "Number of transactions per service identifier for which event charging applies."
    ::= { ggsnApnSacc2ServIdentStatsEntry 5 }

ggsnApnSacc2ServIdentEventTransFail   	OBJECT-TYPE
    SYNTAX                              Counter64
    MAX-ACCESS                          read-only
    STATUS                              deprecated
    DESCRIPTION
        "Number of failed transactions (error response or abnormal termination)
         per service identifier for which event charging applies."
    ::= { ggsnApnSacc2ServIdentStatsEntry 6 }

ggsnApnSacc2ServIdentEventStartTrans    OBJECT-TYPE
    SYNTAX                              Counter64
    MAX-ACCESS                          read-only
    STATUS                              deprecated
    DESCRIPTION
        "Number of start transaction events per service identifier for which event charging applies."
    ::= { ggsnApnSacc2ServIdentStatsEntry 7 }

ggsnApnSacc2ServIdentEventSuccessTrans	OBJECT-TYPE
    SYNTAX                              Counter64
    MAX-ACCESS                          read-only
    STATUS                              deprecated
    DESCRIPTION
        "Number of successful transaction events per service identifier for which event charging applies."
    ::= { ggsnApnSacc2ServIdentStatsEntry 8 }

--
-- GGSN APN service-based charging (SACC 2) SCID statistics
--
-- Per U PIC, per APN, per SCID
--

ggsnApnSacc2ServClassStatsTable	OBJECT-TYPE
    SYNTAX                      SEQUENCE OF ApnSacc2ServClassStats
    MAX-ACCESS                  not-accessible
    STATUS                      deprecated
    DESCRIPTION
         "Service-based charging (SACC 2) service ID statistics for an APN."
    ::= { ggsnFbcStats 17 }

ggsnApnSacc2ServClassStatsEntry OBJECT-TYPE
    SYNTAX                      ApnSacc2ServClassStats
    MAX-ACCESS                  not-accessible
    STATUS                      deprecated
    DESCRIPTION
        "A conceptual row listing the service-based charging (SACC 2) service class ID
         statistics for each APN."
    INDEX { ggsnGtpuIndex, ggsnApnIndex, ggsnSacc2ServClassIndex }
    ::= { ggsnApnSacc2ServClassStatsTable 1 }

ApnSacc2ServClassStats ::= SEQUENCE {
    ggsnSacc2ServClassIndex		Unsigned32,
    ggsnApnSacc2ServClassUplinkBytes    Counter64,
    ggsnApnSacc2ServClassDownlinkBytes  Counter64,
    ggsnApnSacc2ServClassActiveTime     Counter64
}

ggsnSacc2ServClassIndex		OBJECT-TYPE
   SYNTAX                       Unsigned32
   MAX-ACCESS                   not-accessible
   STATUS                       deprecated
   DESCRIPTION
         "The service class ID for the statistics."
   ::= { ggsnApnSacc2ServClassStatsEntry 1 }

ggsnApnSacc2ServClassUplinkBytes        OBJECT-TYPE
    SYNTAX                              Counter64
    MAX-ACCESS                          read-only
    STATUS                              deprecated
    DESCRIPTION
        "Number of uplink bytes marked with service class."
    ::= { ggsnApnSacc2ServClassStatsEntry 2 }

ggsnApnSacc2ServClassDownlinkBytes	OBJECT-TYPE
    SYNTAX                              Counter64
    MAX-ACCESS                          read-only
    STATUS                              deprecated
    DESCRIPTION
        "Number of downlink bytes marked with service class."
    ::= { ggsnApnSacc2ServClassStatsEntry 4 }

ggsnApnSacc2ServClassActiveTime		OBJECT-TYPE
    SYNTAX                              Counter64
    MAX-ACCESS                          read-only
    STATUS                              deprecated
    DESCRIPTION
        "Number of seconds measured for active time for service class."
    ::= { ggsnApnSacc2ServClassStatsEntry 6 }

--
-- GGSN APN service-based charging (SACC 3) SID statistics
--
-- Per U PIC, per APN, per SID
--

ggsnApnSacc3ServIdentStatsTable 	OBJECT-TYPE
    SYNTAX        			SEQUENCE OF ApnSacc3ServIdentStats
    MAX-ACCESS    			not-accessible
    STATUS        			deprecated
    DESCRIPTION
         "Service-based charging (SACC 3) service ID statistics for an APN."
    ::= { ggsnFbcStats 18 }

ggsnApnSacc3ServIdentStatsEntry		OBJECT-TYPE
    SYNTAX				ApnSacc3ServIdentStats
    MAX-ACCESS				not-accessible
    STATUS				deprecated
    DESCRIPTION
	"A conceptual row listing the service-based charging (SACC 3) service ID
	 statistics for each APN."
    INDEX { ggsnGtpuIndex, ggsnApnIndex, ggsnSacc3ServIdentIndex }
    ::= { ggsnApnSacc3ServIdentStatsTable 1 }

ApnSacc3ServIdentStats ::= SEQUENCE {
    ggsnSacc3ServIdentIndex			Unsigned32,
    ggsnApnSacc3ServIdentUplinkBytes		Counter64,
    ggsnApnSacc3ServIdentDownlinkBytes		Counter64
}

ggsnSacc3ServIdentIndex		OBJECT-TYPE
   SYNTAX			Unsigned32
   MAX-ACCESS			not-accessible
   STATUS			deprecated
   DESCRIPTION
         "The service ID for SACC 3 statistics."
   ::= { ggsnApnSacc3ServIdentStatsEntry 1 }

ggsnApnSacc3ServIdentUplinkBytes	OBJECT-TYPE
    SYNTAX				Counter64
    MAX-ACCESS				read-only
    STATUS				deprecated
    DESCRIPTION
	"Number of uplink bytes marked with service data flow ID."
    ::= { ggsnApnSacc3ServIdentStatsEntry 2 }

ggsnApnSacc3ServIdentDownlinkBytes	OBJECT-TYPE
    SYNTAX				Counter64
    MAX-ACCESS				read-only
    STATUS				deprecated
    DESCRIPTION
	"Number of downlink bytes marked with service data flow ID."
    ::= { ggsnApnSacc3ServIdentStatsEntry 4 }

--
-- GGSN APN service-based charging (SACC 3) Rating Group statistics
--
-- Per APN, per RG
--

ggsnApnSacc3RatingGroupStatsTable 	OBJECT-TYPE
    SYNTAX        			SEQUENCE OF ApnSacc3RatingGroupStats
    MAX-ACCESS    			not-accessible
    STATUS        			deprecated
    DESCRIPTION
         "Service-based charging (SACC 3) rating group statistics for an APN."
    ::= { ggsnFbcStats 19 }

ggsnApnSacc3RatingGroupStatsEntry		OBJECT-TYPE
    SYNTAX					ApnSacc3RatingGroupStats
    MAX-ACCESS					not-accessible
    STATUS					deprecated
    DESCRIPTION
	"A conceptual row listing the service-based charging (SACC 3) rating group statistics for each APN."
    INDEX { ggsnApnIndex, ggsnRatingGroupIndex }
    ::= { ggsnApnSacc3RatingGroupStatsTable 1 }

ApnSacc3RatingGroupStats ::= SEQUENCE {
    ggsnRatingGroupIndex			Unsigned32,
    ggsnApnSacc3RatingGroupUplinkBytes		Counter64,
    ggsnApnSacc3RatingGroupDownlinkBytes	Counter64
}

ggsnRatingGroupIndex		OBJECT-TYPE
   SYNTAX			Unsigned32
   MAX-ACCESS			not-accessible
   STATUS			deprecated
   DESCRIPTION
         "The rating group for the statistics."
   ::= { ggsnApnSacc3RatingGroupStatsEntry 1 }

ggsnApnSacc3RatingGroupUplinkBytes	OBJECT-TYPE
    SYNTAX				Counter64
    MAX-ACCESS				read-only
    STATUS				deprecated
    DESCRIPTION
	"Number of uplink bytes marked with rating group."
    ::= { ggsnApnSacc3RatingGroupStatsEntry 2 }

ggsnApnSacc3RatingGroupDownlinkBytes	OBJECT-TYPE
    SYNTAX				Counter64
    MAX-ACCESS				read-only
    STATUS				deprecated
    DESCRIPTION
	"Number of downlink bytes marked with rating group."
    ::= { ggsnApnSacc3RatingGroupStatsEntry 3 }

--
-- GGSN APN service-based charging (SACC 3) Rating Group statistics
--
-- Per U PIC, APN, per RG
--

pgwApnSaccRatingGroupStatsTable 	OBJECT-TYPE
    SYNTAX        			SEQUENCE OF PgwApnSaccRatingGroupStats
    MAX-ACCESS    			not-accessible
    STATUS        			current
    DESCRIPTION
    "Rating group statistics per APN."
    ::= { ggsnFbcStats 20 }

pgwApnSaccRatingGroupStatsEntry		OBJECT-TYPE
    SYNTAX					PgwApnSaccRatingGroupStats
    MAX-ACCESS				not-accessible
    STATUS					current
    DESCRIPTION
    "Rating group statistics per APN."
    INDEX { ggsnGtpuIndex, ggsnApnIndex, pgwRatingGroupIndex }
    ::= { pgwApnSaccRatingGroupStatsTable 1 }
    
PgwApnSaccRatingGroupStats ::= SEQUENCE {
    pgwRatingGroupIndex			Unsigned32,
    pgwApnSaccRatingGroupUplinkBytes	Counter64,
    pgwApnSaccRatingGroupDownlinkBytes	Counter64
}

pgwRatingGroupIndex	OBJECT-TYPE
    SYNTAX			Unsigned32
    MAX-ACCESS		not-accessible
    STATUS			current
    DESCRIPTION
    "The rating group identifier."
    ::= { pgwApnSaccRatingGroupStatsEntry 1 }

pgwApnSaccRatingGroupUplinkBytes	OBJECT-TYPE
    SYNTAX				Counter64
    MAX-ACCESS			read-only
    STATUS				current
    DESCRIPTION
    "The number of uplink bytes on rating group per APN."
    ::= { pgwApnSaccRatingGroupStatsEntry 2 }

pgwApnSaccRatingGroupDownlinkBytes	OBJECT-TYPE
    SYNTAX				Counter64
    MAX-ACCESS			read-only
    STATUS				current
    DESCRIPTION
    "The number of downlink bytes on rating group per APN."
    ::= { pgwApnSaccRatingGroupStatsEntry 3 }

--
-- MBMS information group
--

ggsnMbmsGmbSessionStartAttempts  OBJECT-TYPE
   SYNTAX        Counter64
   MAX-ACCESS    read-only
   STATUS        current
   DESCRIPTION
         "The number of MBMS activation procedures initiated on this GGSN"
   ::= { ggsnMbmsInfo 1 }

ggsnMbmsGmbSessionStartFailures  OBJECT-TYPE
   SYNTAX        Counter64
   MAX-ACCESS    read-only
   STATUS        current
   DESCRIPTION
         "The number of failed MBMS activation procedures initiated on this GGSN."
   ::= { ggsnMbmsInfo 2 }

ggsnMbmsCurrentNbrOfSessions  OBJECT-TYPE
   SYNTAX        Gauge32
   MAX-ACCESS    read-only
   STATUS        current
   DESCRIPTION
         "The number of active MBMS sessions on this GGSN."
   ::= { ggsnMbmsInfo 3 }

ggsnMbmsCurrentAggregatedMbr  OBJECT-TYPE
   SYNTAX        Gauge32
   MAX-ACCESS    read-only
   STATUS        current
   DESCRIPTION
         "The aggregated maximum bitrate for MBMS sessions on this GGSN."
   ::= { ggsnMbmsInfo 4 }

ggsnMbmsGiIncomingPackets  OBJECT-TYPE
   SYNTAX        Counter64
   MAX-ACCESS    read-only
   STATUS        current
   DESCRIPTION
         "Total downlink MBMS packets processed by this GGSN."
   ::= { ggsnMbmsInfo 5 }

ggsnMbmsDiscardedPackets  OBJECT-TYPE
   SYNTAX        Counter64
   MAX-ACCESS    read-only
   STATUS        current
   DESCRIPTION
         "Total Downlink MBMS packets dropped by this GGSN"
   ::= { ggsnMbmsInfo 6 }

ggsnMbmsSgsnUserPlaneTable  OBJECT-TYPE
   SYNTAX        SEQUENCE OF MbmsSgsnUStats
   MAX-ACCESS    not-accessible
   STATUS        deprecated
   DESCRIPTION
         "A table listing MBMS payload statistics for all SGSNs with
          which this GGSN communicates."
   ::= { ggsnMbmsInfo 7 }

ggsnMbmsSgsnUserPlaneEntry OBJECT-TYPE
   SYNTAX        MbmsSgsnUStats
   MAX-ACCESS    not-accessible
   STATUS        deprecated
   DESCRIPTION
         "A conceptual row listing the MBMS payload statistics for each
          SGSN with which this GGSN communicates."
   INDEX        { ggsnMbmsSgsnUIndex }
   ::= { ggsnMbmsSgsnUserPlaneTable 1 }

MbmsSgsnUStats ::= SEQUENCE {
    ggsnMbmsSgsnUIndex		Integer32,
    ggsnMbmsSgsnUAddress		IpAddress,
    ggsnMbmsSgsnForwardedPackets	Counter64
}

ggsnMbmsSgsnUIndex OBJECT-TYPE
   SYNTAX        Integer32 (1..2147483647)
   MAX-ACCESS    not-accessible
   STATUS        deprecated
   DESCRIPTION
         "A number representing each SGSN whose statistics
          is being generated."
   ::= { ggsnMbmsSgsnUserPlaneEntry 1 }

ggsnMbmsSgsnUAddress OBJECT-TYPE
   SYNTAX        IpAddress
   MAX-ACCESS    read-only
   STATUS        deprecated
   DESCRIPTION
         "The IP address of the SGSN whose statistics
          is being generated."
   ::= { ggsnMbmsSgsnUserPlaneEntry 2 }

ggsnMbmsSgsnForwardedPackets  OBJECT-TYPE
   SYNTAX        Counter64
   MAX-ACCESS    read-only
   STATUS        deprecated
   DESCRIPTION
         "Total outgoing MBMS data packets processed on a per SGSN"
   ::= { ggsnMbmsSgsnUserPlaneEntry 3 }


ggsnMbmsSgsnControlPlaneTable  OBJECT-TYPE
   SYNTAX        SEQUENCE OF MbmsSgsnCStats
   MAX-ACCESS    not-accessible
   STATUS        current
   DESCRIPTION
         "A table listing MBMS signaling statistics for all SGSNs with
          which this GGSN communicates."
   ::= { ggsnMbmsInfo 8 }

ggsnMbmsSgsnControlPlaneEntry OBJECT-TYPE
   SYNTAX        MbmsSgsnCStats
   MAX-ACCESS    not-accessible
   STATUS        current
   DESCRIPTION
         "A conceptual row listing the MBMS signaling statistics for each
          SGSN with which this GGSN communicates."
   INDEX        { ggsnMbmsSgsnCIndex }
   ::= { ggsnMbmsSgsnControlPlaneTable 1 }

MbmsSgsnCStats ::= SEQUENCE {
    ggsnMbmsSgsnCIndex		Integer32,
    ggsnMbmsSgsnCAddress		IpAddress,
    ggsnMbmsGnSessionStartAttempts	Counter64,
    ggsnMbmsGnSessionStartFailures	Counter64
}

ggsnMbmsSgsnCIndex OBJECT-TYPE
   SYNTAX        Integer32 (1..2147483647)
   MAX-ACCESS    not-accessible
   STATUS        current
   DESCRIPTION
         "A number representing each SGSN whose statistics
          is being generated."
   ::= { ggsnMbmsSgsnControlPlaneEntry 1 }

ggsnMbmsSgsnCAddress OBJECT-TYPE
   SYNTAX        IpAddress
   MAX-ACCESS    read-only
   STATUS        current
   DESCRIPTION
         "The IP address of the SGSN whose statistics
          is being generated."
   ::= { ggsnMbmsSgsnControlPlaneEntry 2 }

ggsnMbmsGnSessionStartAttempts  OBJECT-TYPE
   SYNTAX        Counter64
   MAX-ACCESS    read-only
   STATUS        current
   DESCRIPTION
         "The number of MBMS activation procedures initiated per SGSN."
   ::= { ggsnMbmsSgsnControlPlaneEntry 3 }

ggsnMbmsGnSessionStartFailures  OBJECT-TYPE
   SYNTAX        Counter64
   MAX-ACCESS    read-only
   STATUS        current
   DESCRIPTION
         "The number of failed MBMS activation procedures initiated per SGSN."
   ::= { ggsnMbmsSgsnControlPlaneEntry 4 }

--
-- Alarm information group
--

PerceivedSeverity ::= TEXTUAL-CONVENTION
   STATUS      current
   DESCRIPTION
       "Perceived severity of an event or alarm."
   SYNTAX      INTEGER {
       unknown       (1),
       critical      (2),
       major         (3),
       minor         (4),
       warning       (5),
       cleared       (6),
       informational (7)
   }

ggsnAlarmNumber  OBJECT-TYPE
   SYNTAX        Gauge32
   MAX-ACCESS    read-only
   STATUS        current
   DESCRIPTION
         "Total number of active alarms, that is, the total number
          of entries in the alarm table"
   ::= { ggsnAlarmInfo 1 }

ggsnAlarmCriticalNumber OBJECT-TYPE
   SYNTAX       Gauge32
   MAX-ACCESS    read-only
   STATUS        current
   DESCRIPTION
         "Total number of critical alarms."
   ::= { ggsnAlarmInfo 2 }

ggsnAlarmMajorNumber OBJECT-TYPE
   SYNTAX        Gauge32
   MAX-ACCESS    read-only
   STATUS        current
   DESCRIPTION
         "Total number of major alarms."
   ::= { ggsnAlarmInfo 3 }

ggsnAlarmMinorNumber OBJECT-TYPE
   SYNTAX       Gauge32
   MAX-ACCESS    read-only
   STATUS        current
   DESCRIPTION
         "Total number of minor alarms."
   ::= { ggsnAlarmInfo 4 }

ggsnAlarmWarningNumber OBJECT-TYPE
   SYNTAX        Gauge32
   MAX-ACCESS    read-only
   STATUS        current
   DESCRIPTION
         "Total number of warnings."
   ::= { ggsnAlarmInfo 5 }

ggsnAlarmUnknownNumber OBJECT-TYPE
   SYNTAX        Gauge32
   MAX-ACCESS    read-only
   STATUS        current
   DESCRIPTION
         "Total number of unknown alarms."
   ::= { ggsnAlarmInfo 6 }

ggsnAlarmTable OBJECT-TYPE
   SYNTAX        SEQUENCE OF GgsnAlarm
   MAX-ACCESS    not-accessible
   STATUS        current
   DESCRIPTION
         "A table listing the current active alarms in the
          system."
   ::= { ggsnAlarmInfo 7 }

ggsnAlarmEntry OBJECT-TYPE
   SYNTAX        GgsnAlarm
   MAX-ACCESS    not-accessible
   STATUS        current
   DESCRIPTION
         "A table entry holding one current alarm."
   INDEX         { ggsnAlarmId }
   ::= { ggsnAlarmTable 1 }

GgsnAlarm ::= SEQUENCE {
   ggsnAlarmId             Integer32,
   ggsnAlarmName           DisplayString,
   ggsnAlarmTime           TimeStamp,
   ggsnAlarmSourceId       DisplayString,
   ggsnAlarmObjectClass    DisplayString,
   ggsnAlarmObjectInstance DisplayString,
   ggsnAlarmSeverity       PerceivedSeverity,
   ggsnAlarmDescription    DisplayString
}

ggsnAlarmId OBJECT-TYPE
   SYNTAX        Integer32 (1..2147483647)
   MAX-ACCESS    read-only
   STATUS        current
   DESCRIPTION
         "A number uniquely identifying each event or alarm
          in the Alarm Table."
   ::= { ggsnAlarmEntry 1 }

ggsnAlarmName OBJECT-TYPE
   SYNTAX        DisplayString
   MAX-ACCESS    read-only
   STATUS        current
   DESCRIPTION
         "The name of the event or alarm."
   ::= { ggsnAlarmEntry 2 }

ggsnAlarmTime OBJECT-TYPE
   SYNTAX        TimeStamp
   MAX-ACCESS    read-only
   STATUS        current
   DESCRIPTION
         "The value of sysUpTime when the event or alarm was sent."
   ::= { ggsnAlarmEntry 3 }

ggsnAlarmSourceId OBJECT-TYPE
   SYNTAX        DisplayString
   MAX-ACCESS    read-only
   STATUS        current
   DESCRIPTION
         "The name of the event or alarm's originator."
   ::= { ggsnAlarmEntry 4 }

ggsnAlarmObjectClass OBJECT-TYPE
   SYNTAX        DisplayString
   MAX-ACCESS    read-only
   STATUS        current
   DESCRIPTION
         "The class of the network resources associated
          with the event or alarm."
   ::= { ggsnAlarmEntry 5 }

ggsnAlarmObjectInstance OBJECT-TYPE
   SYNTAX        DisplayString
   MAX-ACCESS    read-only
   STATUS        current
   DESCRIPTION
         "The instance (of a class) of the network resource
          associated with the event or alarm."
   ::= { ggsnAlarmEntry 6 }

ggsnAlarmSeverity OBJECT-TYPE
   SYNTAX        PerceivedSeverity
   MAX-ACCESS    read-only
   STATUS        current
   DESCRIPTION
         "The perceived severity of the event. The value
          unknown (0) is not recommended to be used."
   ::= { ggsnAlarmEntry 7 }

ggsnAlarmDescription OBJECT-TYPE
   SYNTAX        DisplayString
   MAX-ACCESS     read-only
   STATUS        current
   DESCRIPTION
         "A short textual explanation of the event or
          alarm instance."
   ::= { ggsnAlarmEntry 8 }


--
-- Alarm History
--


AlarmEventCause ::= TEXTUAL-CONVENTION
    STATUS      	current
    DESCRIPTION
	"Cause for the alarm event appearing in the alarm history table."
    SYNTAX      INTEGER {
	new		(1),
	changed		(2),
	cleared		(3),
	notification	(4),
	mibcleared	(5),
	usercleared	(6)
    }

ggsnAlarmHistTable 			OBJECT-TYPE
    SYNTAX        			SEQUENCE OF GgsnAlarmHistEntry
    MAX-ACCESS    			not-accessible
    STATUS        			current
    DESCRIPTION
	"The alarm history table is a limited size table
	that contains recent alarms and alarm events.

	A number of events cause an entry to be added to the
	alarm history table:

	'new'          - a trap was sent and an alarm added to the alarm
	                 table
	'changed'      - an existing alarm was updated and a changed trap sent
	'cleared'      - an existing alarm was removed and a clear trap sent
	'notification' - only a trap was sent
	'mibcleared'   - the entire MIB statistics were cleared
	'usercleared'  - a user requested a clear of the alarm history table

	Only a fixed maximum of alarm events are stored in
	this table at once and events are aged out of this
	table over time. "
    ::= { ggsnAlarmInfo 8 }

ggsnAlarmHistEntry OBJECT-TYPE
    SYNTAX        			GgsnAlarmHistEntry
    MAX-ACCESS    			not-accessible
    STATUS        			current
    DESCRIPTION
	"A table entry holding one alarm history event."
    INDEX         		{ ggsnAlarmHistTime }
    ::= { ggsnAlarmHistTable 1 }

GgsnAlarmHistEntry ::= SEQUENCE {
    ggsnAlarmHistTime    		TimeStamp,
    ggsnAlarmHistEventCause 		AlarmEventCause,
    ggsnAlarmHistAlarmId    	   	Integer32,
    ggsnAlarmHistAlarmName          	DisplayString,
    ggsnAlarmHistAlarmTime          	TimeStamp,
    ggsnAlarmHistAlarmSourceId      	DisplayString,
    ggsnAlarmHistAlarmObjInstance	DisplayString,
    ggsnAlarmHistAlarmSeverity      	PerceivedSeverity,
    ggsnAlarmHistAlarmDescription   	DisplayString
}

ggsnAlarmHistTime			OBJECT-TYPE
    SYNTAX        			TimeStamp
    MAX-ACCESS    			read-only
    STATUS        			current
    DESCRIPTION
     "The value of sysUpTime when the alarm event occurred."
    ::= { ggsnAlarmHistEntry 1 }

ggsnAlarmHistEventCause			OBJECT-TYPE
    SYNTAX        			AlarmEventCause
    MAX-ACCESS    			read-only
    STATUS        			current
    DESCRIPTION
	"The event documented by this alarm history event entry."
    ::= { ggsnAlarmHistEntry 2 }

ggsnAlarmHistAlarmId 			OBJECT-TYPE
    SYNTAX        			Integer32 (1..2147483647)
    MAX-ACCESS    			read-only
    STATUS        			current
    DESCRIPTION
	"A number uniquely identifying each event or alarm
	in the Alarm Table."
    ::= { ggsnAlarmHistEntry 3 }

ggsnAlarmHistAlarmName 			OBJECT-TYPE
    SYNTAX        			DisplayString
    MAX-ACCESS    			read-only
    STATUS        			current
    DESCRIPTION
	"The name of the event or alarm."
    ::= { ggsnAlarmHistEntry 4 }

ggsnAlarmHistAlarmTime 			OBJECT-TYPE
    SYNTAX        			TimeStamp
    MAX-ACCESS    			read-only
    STATUS        			current
    DESCRIPTION
	"The value of sysUpTime when the event or alarm was sent."
    ::= { ggsnAlarmHistEntry 5 }

ggsnAlarmHistAlarmSourceId 		OBJECT-TYPE
    SYNTAX        			DisplayString
    MAX-ACCESS    			read-only
    STATUS        			current
    DESCRIPTION
	"The name of the event or alarm's originator."
    ::= { ggsnAlarmHistEntry 6 }

ggsnAlarmHistAlarmObjInstance 		OBJECT-TYPE
    SYNTAX        			DisplayString
    MAX-ACCESS    			read-only
    STATUS        			current
    DESCRIPTION
	"The instance (of a class) of the network resource
	    associated with the event or alarm."
    ::= { ggsnAlarmHistEntry 7 }

ggsnAlarmHistAlarmSeverity 		OBJECT-TYPE
    SYNTAX        			PerceivedSeverity
    MAX-ACCESS    			read-only
    STATUS        			current
    DESCRIPTION
	"The perceived severity of the event. The value
	unknown (0) is not recommended to be used."
    ::= { ggsnAlarmHistEntry 8 }

ggsnAlarmHistAlarmDescription 		OBJECT-TYPE
    SYNTAX        			DisplayString
    MAX-ACCESS     			read-only
    STATUS        			current
    DESCRIPTION
	"A short textual explanation of the event or
	alarm instance."
    ::= { ggsnAlarmHistEntry 9 }



--
-- GGSN enterprise traps
--


ggsnTrapNew NOTIFICATION-TYPE
   OBJECTS { ggsnAlarmId,
             ggsnAlarmName,
             ggsnAlarmTime,
             ggsnAlarmSourceId,
             ggsnAlarmObjectClass,
             ggsnAlarmObjectInstance,
             ggsnAlarmSeverity,
             ggsnAlarmDescription }
   STATUS    current
   DESCRIPTION
         "A trap describing the newly generated event or
          alarm. The text in ggsnTrapDescription indicates
          the nature of the problem."
   ::= { ggsnTraps 1 }

ggsnTrapChanged NOTIFICATION-TYPE
   OBJECTS { ggsnAlarmId,
             ggsnAlarmName,
             ggsnAlarmTime,
             ggsnAlarmSourceId,
             ggsnAlarmObjectClass,
             ggsnAlarmObjectInstance,
             ggsnAlarmSeverity,
             ggsnAlarmDescription }
   STATUS    current
   DESCRIPTION
         "A trap indicating a change has occurred in the attributes of the alarm or event. 
          The text in ggsnTrapDescription indicates the nature of the change."
   ::= { ggsnTraps 2 }

ggsnTrapCleared NOTIFICATION-TYPE
   OBJECTS { ggsnAlarmId,
             ggsnAlarmName,
             ggsnAlarmTime,
             ggsnAlarmSourceId,
             ggsnAlarmObjectClass,
             ggsnAlarmObjectInstance,
             ggsnAlarmSeverity,
             ggsnAlarmDescription }
   STATUS    current
   DESCRIPTION
         "A trap indicating the clear of the event or alarm."
   ::= { ggsnTraps 3 }


--
-- Conformance information
--

ggsnMIBConformance
         OBJECT IDENTIFIER ::= { ggsnMibs 2 }
ggsnMIBCompliances
         OBJECT IDENTIFIER ::= { ggsnMIBConformance 1 }
ggsnMIBGroups
         OBJECT IDENTIFIER ::= { ggsnMIBConformance 2 }


-- Compliance statements

ggsnMIBCompliance MODULE-COMPLIANCE
   STATUS        current
   DESCRIPTION
         "The compliance statement for the box implementing
          the ggsn MIB."
   MODULE -- this module
   MANDATORY-GROUPS {
	ggsnSystemGroup,
	ggsnGlobalStatisticsGroup,
	ggsnApnStatisticsGroup,
	ggsnSgsnStatisticsGroup,
	ggsnAcctClientStatisticsGroup,
	ggsnDhcpStatisticsGroup,
	ggsnAlarmsGroup,
	ggsnAlarmsEntryGroup,
	ggsnNotificationsGroup,
	ggsnAlarmHistEntryGroup,
	ggsnApnFbcStatisticsGroup,
	ggsnFbcAuthStatisticsGroup,
	ggsnApnFbcServIdentStatsGroup,
	ggsnApnFbcServClassStatsGroup,
    ggsnApnSacc2ServIdentStatsGroup,
    ggsnApnSacc2ServClassStatsGroup,
    ggsnApnSacc3ServIdentStatsGroup,
	ggsnApnSacc3RatingGroupStatsGroup,
	ggsnFbcStatsGroup,
	pgwApnSaccRatingGroupStatsGroup
   }
   ::= { ggsnMIBCompliances 1 }


-- Unit of conformance

ggsnSystemGroup OBJECT-GROUP
   OBJECTS { ggsnVersion,
             ggsnInstalled,
             ggsnGtpcVersion,
             ggsnGtpcAddress,
             ggsnGtpcPdpCapacity,
             ggsnGtpcRole,
             ggsnGtpcStatus,
             ggsnGtpcControlPacketDrops,
             ggsnGtpcNbrOfActivePdpContexts,
             ggsnGtpcMemory,
             ggsnGtpcMemoryUsed,
             ggsnGtpcCpuUsage,
             ggsnGtpcTftFilterDepthMax,
             ggsnGtpcTftFilterDepthMean,
             ggsnGtpcControlLoad,
             ggsnGtpuVersion,
             ggsnGtpuAddress,
             ggsnGtpuPdpCapacity,
             ggsnGtpuRole,
             ggsnGtpuStatus,
             ggsnGtpuUserUplinkDrops,
             ggsnGtpuUserDownlinkDrops,
             ggsnGtpuNbrOfActivePdpContexts,
             ggsnGtpuMemory,
             ggsnGtpuMemoryUsed,
             ggsnGtpuCpuUsage,
             ggsnGtpuPayloadLoad,
             ggsnGtpuNbrOfActivePdpContextsIpv6,
             ggsnGtpuNbrOfActivePdpContextsIpv4v6,
             ggsnGtpcNbrOfActivePdpContextsIpv6,
             ggsnGtpcNbrOfActivePdpContextsIpv4v6,
			 ggsnGtpuUplinkPackets,
			 ggsnGtpuDownlinkPackets
   }
   STATUS current
   DESCRIPTION
         "The basic collection of objects providing system
          management of the ggsn application."
   ::= { ggsnMIBGroups 1 }

ggsnGlobalStatisticsGroup OBJECT-GROUP
   OBJECTS { 	ggsnStatReportTime,
		ggsnNbrOfActivePdpContexts,
		ggsnNbrOfSubscribers,
		ggsnNbrOfSubscribersMean,
		ggsnNbrOfTftFilters,
		ggsnControlLoad,
		ggsnPayloadLoad,
		ggsnAttemptedActivation,
		ggsnAttemptedDeactivation,
		ggsnAttemptedSelfDeactivation,
		ggsnAttemptedUpdate,
		ggsnAttemptedManualDeactivation,
		ggsnAttemptedSecondaryActivation,
		ggsnCompletedActivation,
		ggsnCompletedDeactivation,
		ggsnCompletedSelfDeactivation,
		ggsnCompletedUpdate,
		ggsnIdleTimeoutDeactivation,
		ggsnCompletedManualDeactivation,
		ggsnCompletedSecondaryActivation,
	        ggsnSessionTimeoutDeactivation,
		ggsnFailedActivation,
		ggsnGtpUplinkPackets,
		ggsnGtpUplinkBytes,
		ggsnGtpDownlinkPackets,
		ggsnGtpDownlinkBytes,
		ggsnGtpControlPacketDrops,
		ggsnGtpVerUnsupPacketsReceived,
		ggsnGtpVerUnsupPacketsSent,
		ggsnGtpEchoReqReceived,
		ggsnGtpEchoReqSent,
		ggsnGtpEchoRespReceived,
		ggsnGtpEchoRespSent,
		ggsnGtpPdpCreateReqReceived,
                ggsnGtpv0PdpCreateReqReceived,
		ggsnGtpPdpCreateRespSent,
		ggsnGtpPdpUpdateReqReceived,
		ggsnGtpPdpUpdateReqSent,
		ggsnGtpPdpUpdateRespReceived,
		ggsnGtpPdpUpdateRespSent,
		ggsnGtpPdpDeleteReqReceived,
		ggsnGtpPdpDeleteReqSent,
		ggsnGtpPdpDeleteRespReceived,
		ggsnGtpPdpDeleteRespSent,
		ggsnGtpPdpInitiateContextActivationRespReceived,
		ggsnGtpPdpInitiateContextActivationReqSent,
		ggsnGtpRequestsAccepted,
		ggsnGtpNbrOfTunnels,
		ggsnGtpNbrOfCreatedTunnels,
		ggsnGtpErrorIndicationReceived,
		ggsnGtpErrorIndicationSent,
		ggsnGtpErrorInvalidRequestFormat,
		ggsnGtpErrorResourcesUnavailable,
		ggsnGtpErrorDynAddrUnavailable,
		ggsnGtpErrorMemoryUnavailable,
		ggsnGtpErrorApnUnknown,
		ggsnGtpErrorPdpAddrUnknown,
		ggsnGtpErrorAuthenticationFailed,
		ggsnGtpErrorSystemFailure,
		ggsnGtpErrorTftSemanticError,
		ggsnGtpErrorTftSyntaxError,
		ggsnGtpErrorPackFiltSemantError,
		ggsnGtpErrorPackFiltSyntaxError,
		ggsnGtpErrorMandatoryIEMissing,
		ggsnGtpErrorMandatoryIEInvalid,
		ggsnGtpErrorOptionalIEInvalid,
		ggsnGtpErrorReferenceInexistent,
		ggsnGtpErrorServiceUnsupported,
		ggsnGtpPrEchoReqReceived,
		ggsnGtpPrEchoRequestsSent,
		ggsnGtpPrEchoRespReceived,
		ggsnGtpPrEchoRespSent,
		ggsnGtpPrVerUnsupPacketsReceived,
		ggsnGtpPrVerUnsupPacketsSent,
		ggsnGtpPrNodeAliveReqReceived,
		ggsnGtpPrNodeAliveReqSent,
		ggsnGtpPrNodeAliveRespReceived,
		ggsnGtpPrNodeAliveRespSent,
		ggsnGtpPrRedirectReqReceived,
		ggsnGtpPrRedirectReqSent,
		ggsnGtpPrRedirectRespReceived,
		ggsnGtpPrRedirectRespSent,
		ggsnGtpPrDataRecTransferReceived,
		ggsnGtpPrDataRecTransferSent,
		ggsnGtpPrSndDataRecordPackets,
		ggsnGtpPrRequestAccepted,
		ggsnGtpPrNoResource,
		ggsnGtpPrServiceUnsupported,
		ggsnGtpPrSystemFailure,
		ggsnGtpPrInvalidMessageFormat,
		ggsnGtpPrVersionUnsupported,
		ggsnGtpPrRequestUnfulfilled,
		ggsnGtpPrDecodingError,
		ggsnGtpPrAlreadyFulfilled,
		ggsnGtpPrDupPacketFulfilled,
		ggsnGtpPrErrorMandatoryIEMissing,
		ggsnGtpPrErrorMandatoryIEInvalid,
		ggsnGtpPrErrorOptionalIEInvalid,
		ggsnGtpPrErrorRefInexistent,
		ggsnUplinkPackets,
		ggsnUplinkBytes,
		ggsnUplinkDrops,
		ggsnUplinkDropsBytes,
		ggsnDownlinkPackets,
		ggsnDownlinkBytes,
		ggsnDownlinkDrops,
		ggsnDownlinkDropsBytes,
		ggsnNbrOfActivePdpContextsIpv6,
		ggsnAttemptedActivationIpv6,
		ggsnAttemptedSecondaryActivationIpv6,
		ggsnCompletedActivationIpv6,
		ggsnCompletedSecondaryActivationIpv6,
		ggsnUplinkPacketsIpv6,
		ggsnUplinkBytesIpv6,
		ggsnUplinkDropsIpv6,
		ggsnDownlinkPacketsIpv6,
		ggsnDownlinkBytesIpv6,
		ggsnDownlinkDropsIpv6,
		ggsnNbrOfActivePdpContextsWlan,
		ggsnAttemptedActivationWlan,
		ggsnCompletedActivationWlan,
		ggsnAttemptedActivationConversational,
		ggsnAttemptedActivationStreaming,
 		ggsnAttemptedActivationInteractive,
		ggsnAttemptedActivationBackground,
		ggsnAttemptedActivationDiscarded,
		ggsnCompletedActivationConversational,
		ggsnCompletedActivationStreaming,
		ggsnCompletedActivationInteractive,
		ggsnCompletedActivationBackground,
		ggsnAttemptedActivationIpv4v6,
		ggsnCompletedActivationIpv4v6,
		ggsnUplinkBytesWlan,
		ggsnUplinkDropsWlan,
		ggsnUplinkPacketsWlan,
		ggsnDownlinkBytesWlan,
		ggsnDownlinkDropsWlan,
		ggsnDownlinkPacketsWlan,
		ggsnNeighborSolicitationRcv,
		ggsnNeighborSolicitationRsp,
		ggsnRouterSolicitationRcv,
		ggsnRouterSolicitationRsp,
		ggsnL2tpActiveTunnels,
		ggsnL2tpMaxActiveTunnels,
		ggsnL2tpActiveSessions,
		ggsnL2tpMaxActiveSessions,
		ggsnChgEncodedCdrs,
		ggsnChgFailedEncodedCdrs,
		ggsnChgGeneratedFtpCdrs,
		ggsnChgGeneratedGtppCdrs,
		ggsnChgGtppLogCdrs,
		ggsnChgGtppAttemptedCdrsSend,
		ggsnChgGtppCdrsSendFailure,
		ggsnNbActivePdpPerTrafficClassConversational,
		ggsnNbActivePdpPerTrafficClassStreaming,
		ggsnNbActivePdpPerTrafficClassInteractive,
		ggsnNbActivePdpPerTrafficClassBackground,
		ggsnRadiusAuthenticationFailure,
        ggsnRadiusAccountingFailure,
        ggsn3gdtActiveContexts,
        ggsn3gdtTotalCompletedEstablishment,
        ggsn3gdtTotalAttemptedEstablishment,
        ggsn3gdtErrorHandling,
        gn3gdtTotalCompletedEstablishment,
	    gn3gdtTotalAttemptedEstablishment,
	    gn3gdtErrorHandling,
        ggsnNbrOfActivePdpContextsIpv4v6
   }
   STATUS current
   DESCRIPTION
         "The basic collection of objects providing global
          measurements for the ggsn node."
   ::= { ggsnMIBGroups 2 }

ggsnApnStatisticsGroup OBJECT-GROUP
   OBJECTS { ggsnApnName,
             ggsnApnActivePdpContextCount,
             ggsnApnAttemptedActivation,
             ggsnApnAttemptedDynActivation,
             ggsnApnAttemptedDeactivation,
             ggsnApnAttemptedSelfDeactivation,
             ggsnApnCompletedActivation,
             ggsnApnCompletedDynActivation,
             ggsnApnCompletedDeactivation,
             ggsnApnCompletedSelfDeactivation,
             ggsnApnAvailableIpAddressesInInternalPool,
             ggsnApnIpAddressesInQuarantineInInternalPool,
             ggsnApnUplinkPackets,
             ggsnApnUplinkBytes,
             ggsnApnUplinkDrops,
             ggsnApnDownlinkPackets,
             ggsnApnDownlinkBytes,
             ggsnApnDownlinkDrops,
             ggsnApnAttemptedMSActivation,
             ggsnApnCompletedMSActivation,
             ggsnApnAttemptedMSDeactivation,
             ggsnApnCompletedMSDeactivation,
             ggsnApnActivePdpContextMax,
             ggsnApnActivePdpContextMean,
             ggsnApnAttemptedAuthActivation,
             ggsnApnFailedAuthActivation,
             ggsnApnAttemptedUpdateMsAndSgsn,
             ggsnApnCompletedUpdateMsAndSgsn,
             ggsnApnNbrOfTftFilters,
             ggsnApnSessTimeoutDeactivation,
             ggsnApnIdleTimeoutDeactivation,
             ggsnApnGiSignalingInPackets,
             ggsnApnGiSignalingInBytes,
             ggsnApnGiSignalingOutPackets,
             ggsnApnGiSignalingOutBytes,
	         ggsnApnActivePdpContextCountIpv6,
	         ggsnApnAttemptedActivationIpv6,
	         ggsnApnCompletedActivationIpv6,
	         ggsnApnUplinkPacketsIpv6,
             ggsnApnUplinkBytesIpv6,
             ggsnApnUplinkDropsIpv6,
	         ggsnApnDownlinkPacketsIpv6,
             ggsnApnDownlinkBytesIpv6,
             ggsnApnDownlinkDropsIpv6,
	         ggsnApnNeighborSolicitationRcv,
             ggsnApnNeighborSolicitationRsp,
	         ggsnApnRouterSolicitationRcv,
             ggsnApnRouterSolicitationRsp,
             ggsnNbApnActivePdpPerTrafficClassConversational,
             ggsnNbApnActivePdpPerTrafficClassStreaming,
             ggsnNbApnActivePdpPerTrafficClassInteractive,
             ggsnNbApnActivePdpPerTrafficClassBackground,
             ggsnApnImsDedicatedCompletedActivation,
             ggsnApnImsDedicatedNotConfiguredActivationFailed,
             ggsnApnImsGeneralPurposeCompletedActivation,
             ggsnApnImsGeneralNotConfiguredActivationFailed,
             ggsnApnActivationFailedDuetoGeneralPurposeNotConfigured,
             ggsnApnUnauthorizedImsPackets,
             ggsnApnRadiusAccountingFailure,
             ggsnApnRadiusAuthenticationFailure,
             ggsnApnSaccRsInstalledDynRules,
             ggsnApnSaccRsActivePredefinedChargingRules,
             ggsnApnSaccRsActivePredefinedChargingRuleBases,
             ggsnApn3gdtActiveContexts,
             ggsnApn3gdtTotalCompletedEstablishment,
             ggsnApn3gdtTotalAttemptedEstablishment,
             ggsnApn3gdtErrorHandling,
             ggsnApnAttemptedUpdateGgsn,
             ggsnApnCompletedUpdateGgsn,
             ggsnApnAttemptedActivationNonDuplicated,
             ggsnApnActivePdpContextMaxDuringLastPeriod,
             pgwApnActiveEpsBearer,
             pgwApnActiveIpv6EpsBearer,
             pgwApnAttemptedEpsBearerActivation,
             pgwApnCompletedEpsBearerActivation,
             pgwApnAttemptedIpv6EpsBearerActivation,
             pgwApnCompletedIpv6EpsBearerActivation,
             pgwApnAttemptedEpsBearerDeactivation,
             pgwApnCompletedEpsBearerDeactivation,
             pgwApnAttemptedS5NetworkDeactivation,
             pgwApnCompletedS5NetworkDeactivation,
             pgwApnAttemptedS5UeSgwModification,
             pgwApnCompletedS5UeSgwModification,
             pgwApnAttemptedS5SgwSgsnModification,
             pgwApnCompletedS5SgwSgsnModification,
             pgwApnAttemptedS5SgsnSgwModification,
             pgwApnCompletedS5SgsnSgwModification,
             pgwApnAttemptedS5NetworkModification,
             pgwApnCompletedS5NetworkModification,
             pgwApnAttemptedS5UeSgwDeactivation,
             pgwApnCompletedS5UeSgwDeactivation,
             gnApnUplinkPackets,
             gnApnUplinkBytes,
             gnApnUplinkPacketsIpv6,
             gnApnUplinkBytesIpv6,
             gnApnDownlinkPackets,
             gnApnDownlinkBytes,
             gnApnDownlinkPacketsIpv6,
             gnApnDownlinkBytesIpv6,
             s5ApnUplinkPackets,
             s5ApnUplinkBytes,
             s5ApnUplinkPacketsIpv6,
             s5ApnUplinkBytesIpv6,
             s5ApnDownlinkPackets,
             s5ApnDownlinkBytes,
             s5ApnDownlinkPacketsIpv6,
             s5ApnDownlinkBytesIpv6,
             gnApn3gdtUplinkBytes,
             gnApn3gdtUplinkBytesIpv6,
             gnApn3gdtUplinkPackets,
             gnApn3gdtUplinkPacketsIpv6,
             gnApn3gdtDownlinkBytes,
             gnApn3gdtDownlinkBytesIpv6,
             gnApn3gdtDownlinkPackets,
             gnApn3gdtDownlinkPacketsIpv6,
             gnApn3gdtDownlinkDropsErrorHandling,
             ggsnApn3gdtGtpError,
             pgwApnActiveDedicatedEpsBearer,
	         pgwApnAttemptedDedicatedEpsBearerActivation,  
		     pgwApnCompletedDedicatedEpsBearerActivation,  
		     pgwApnAttemptedIpv6DedicatedEpsBearerActivation,  
		     pgwApnCompletedIpv6DedicatedEpsBearerActivation,  
		     pgwApnAttemptedS5NetworkDedicatedEpsBearerDeactivation, 
		     pgwApnCompletedS5NetworkDedicatedEpsBearerDeactivation,  
		     pgwApnAttemptedS5NetworkDedicatedEpsBearerModification,  
		     pgwApnCompletedS5NetworkDedicatedEpsBearerModification,  
		     pgwApnAttemptedS5UeSgwDedicatedEpsBearerDeactivation,  
		     pgwApnCompletedS5UeSgwDedicatedEpsBearerDeactivation,
             ggsnApnActivePdpContextCountIpv4v6,
             pgwApnActiveIpv4v6EpsBearer,
             ggsnApnAttemptedActivationIpv4v6,
             ggsnApnCompletedActivationIpv4v6,
             pgwApnAttemptedIpv4v6EpsBearerActivation,
             pgwApnCompletedIpv4v6EpsBearerActivation,
             pgwApnActiveWlanEpsBearer,
             s2aApnUplinkPackets,
             s2aApnUplinkBytes,
             s2aApnDownlinkPackets,
             s2aApnDownlinkBytes,
             s2aApnUplinkPacketsIpv6,
             s2aApnUplinkBytesIpv6,
             s2aApnDownlinkPacketsIpv6,
             s2aApnDownlinkBytesIpv6
   }
   STATUS current
   DESCRIPTION
         "The basic collection of objects providing
          measurements on a per APN of the ggsn node."
   ::= { ggsnMIBGroups 3 }

ggsnSgsnStatisticsGroup OBJECT-GROUP
   OBJECTS { ggsnSgsnAddress,
             ggsnSgsnUplinkPackets,
             ggsnSgsnUplinkBytes,
             ggsnSgsnUplinkDrops,
             ggsnSgsnDownlinkPackets,
             ggsnSgsnDownlinkBytes,
             ggsnSgsnDownlinkDrops
   }
   STATUS current
   DESCRIPTION
         "The basic collection of objects providing
          measurements on a per SGSN of the ggsn node."
   ::= { ggsnMIBGroups 4 }

ggsnAcctClientStatisticsGroup OBJECT-GROUP
   OBJECTS { ggsnAcctPartialRecordGenerated,
       	     ggsnAcctBillingGatewayIndex,
             ggsnAcctBillingGatewayAddress,
             ggsnAcctDataRecTransReqSent,
             ggsnAcctDataRecTransReqSentDup,
             ggsnAcctDataRecTransReqCancelled,
             ggsnAcctDataRecTransRespReceived,
             ggsnAcctRedirectionReqReceived,
             ggsnAcctRedirectionRespSent
   }
   STATUS current
   DESCRIPTION
         "The basic collection of objects providing
          measurements on a per Billing Gateway with
          which the ggsn node communicates."
   ::= { ggsnMIBGroups 5 }

ggsnDhcpStatisticsGroup OBJECT-GROUP
   OBJECTS { ggsnDhcpClientAddress,
             ggsnDhcpServerAddress,
             ggsnDhcpServerName,
             ggsnDhcpClientYiaddr,
             ggsnDhcpClientState,
             ggsnDhcpClientRequestsSent,
             ggsnDhcpClientRepliesReceived,
             ggsnDhcpClientRepliesDiscarded,
             ggsnDhcpClientDiscoversSent,
             ggsnDhcpClientDeclinesSent,
             ggsnDhcpClientReleasesSent,
             ggsnDhcpClientOffersReceived,
             ggsnDhcpClientAcksReceived,
             ggsnDhcpClientNaksReceived,
             ggsnDhcpClientSendErrors,
             ggsnDhcpServerRoutingInstance
   }
   STATUS current
   DESCRIPTION
         "The basic collection of objects providing
          measurements on a per DHCP server with
          which the ggsn node communicates."
   ::= { ggsnMIBGroups 6 }

ggsnAlarmsGroup OBJECT-GROUP
   OBJECTS { ggsnAlarmNumber,
             ggsnAlarmCriticalNumber,
             ggsnAlarmMajorNumber,
             ggsnAlarmMinorNumber,
             ggsnAlarmWarningNumber,
             ggsnAlarmUnknownNumber
   }
   STATUS current
   DESCRIPTION
         "The alarms objects implemented for the GGSN node."
   ::= {ggsnMIBGroups 7}

ggsnAlarmsEntryGroup OBJECT-GROUP
   OBJECTS { ggsnAlarmId,
             ggsnAlarmName,
             ggsnAlarmTime,
             ggsnAlarmSourceId,
             ggsnAlarmObjectClass,
             ggsnAlarmObjectInstance,
             ggsnAlarmSeverity,
             ggsnAlarmDescription
   }
   STATUS current
   DESCRIPTION
         "The alarm entry objects implemented for the GGSN node."
   ::= {ggsnMIBGroups 8}


ggsnNotificationsGroup NOTIFICATION-GROUP
   NOTIFICATIONS { ggsnTrapNew,
                   ggsnTrapChanged,
                   ggsnTrapCleared
   }
   STATUS current
   DESCRIPTION
         "The notifications which are implemented by the
          GGSN node."
   ::= {ggsnMIBGroups 9}


ggsnAlarmHistEntryGroup OBJECT-GROUP
   OBJECTS {
	ggsnAlarmHistTime,
	ggsnAlarmHistEventCause,
	ggsnAlarmHistAlarmId,
	ggsnAlarmHistAlarmName,
	ggsnAlarmHistAlarmTime,
	ggsnAlarmHistAlarmSourceId,
	ggsnAlarmHistAlarmObjInstance,
	ggsnAlarmHistAlarmSeverity,
	ggsnAlarmHistAlarmDescription
   }
   STATUS current
   DESCRIPTION
   	"The alarm history objects implemented for the GGSN node."
   ::= { ggsnMIBGroups 10 }


-- { ggsnMIBGroups 11 } is not assigned

ggsnOldObjectsGroup    OBJECT-GROUP
    OBJECTS {
	ggsnPicAddress,
        ggsnPicNbrOfActivePdpContexts,
	ggsnAttemptedTimeDeactivation,
	ggsnFbcApplicationTransactionPps,
	ggsnFbcApplicationTransactionPrs,
	ggsnApnFbcInitialPrsReq,
	ggsnApnFbcInitialPrsReqFailed,
	ggsnApnFbcUpdPrsReq,
	ggsnApnFbcUpdPrsReqFailed,
	ggsnApnFbcStartCredReq,
	ggsnApnFbcStartCredReqFailed,
	ggsnApnFbcUpdCredReq,
	ggsnApnFbcUpdCredReqFailed,
	ggsnApnFbcStopCredReq,
	ggsnApnFbcStopCredReqFailed
    }
    STATUS  deprecated
    DESCRIPTION
            "The collection of objects deprecated from
             the original GGSN MIB."
    ::= { ggsnMIBGroups 12 }

ggsnApnFbcStatisticsGroup	OBJECT-GROUP
   OBJECTS {
	ggsnApnFbcNbrOfPpsUsers,
	ggsnApnFbcNbrOfPpsPdpContexts,
	ggsnApnFbcPpsCreate,
	ggsnApnFbcPpsReject,
	ggsnApnFbcInitiatedDeactivation,
        ggsnApnFbcExtPrsUpd,
	ggsnApnFbcExtCreditUpd,
	ggsnApnFbcDurationTime,
	ggsnApnFbcActivationBearerCtrlAccept,
	ggsnApnFbcActivationBearerCtrlReject,
	ggsnApnFbcActivationBearerCtrlUpgrade,
	ggsnApnFbcActivationBearerCtrlDowngrade,
	ggsnApnFbcModificationBearerCtrlAccept,
	ggsnApnFbcModificationBearerCtrlDeactivate,
	ggsnApnFbcModificationBearerCtrlUpgrade,
	ggsnApnFbcModificationBearerCtrlDowngrade,
	ggsnApnFbcActivationNoBearerCtrlAccept,
	ggsnApnFbcActivationNoBearerCtrlReject,
	ggsnApnFbcActivationNoBearerCtrlDowngrade,
	ggsnApnFbcModificationNoBearerCtrlAccept,
	ggsnApnFbcModificationNoBearerCtrlDeactivate,
	ggsnApnFbcModificationNoBearerCtrlDowngrade,
	ggsnApnSaccAttemptedServiceInitiatedQoSModification
   }
   STATUS current
   DESCRIPTION
   "SACC statistics per APN."
   ::= { ggsnMIBGroups 13 }

ggsnFbcAuthStatisticsGroup	OBJECT-GROUP
   OBJECTS {
	ggsnFbcUserAuthPacketsDropped,
	ggsnFbcDefaultAuthPacketsDropped,
	ggsnFbcEmptyBucketPacketsDropped,
	ggsnFbcComFailAuthPacketsDropped,
	ggsnFbcIdentErrorPacketsDropped
   }
   STATUS deprecated
   DESCRIPTION
         "Service-based charging (FBC) authorization statistics per node."
   ::= { ggsnMIBGroups 14 }

ggsnApnFbcServIdentStatsGroup	OBJECT-GROUP
    OBJECTS {
	ggsnApnFbcServIdentUplinkBytes,
	ggsnApnFbcServIdentDownlinkBytes,
	ggsnApnFbcServIdentEventTrans,
	ggsnApnFbcServIdentEventTransFail,
	ggsnApnFbcServIdentEventStartTrans,
	ggsnApnFbcServIdentEventSuccessTrans
    }
    STATUS current
    DESCRIPTION
    "Service data flow statistics per APN."
    ::= { ggsnMIBGroups 15 }

ggsnApnFbcServClassStatsGroup	OBJECT-GROUP
    OBJECTS {
	ggsnApnFbcServClassUplinkBytes,
	ggsnApnFbcServClassDownlinkBytes,
	ggsnApnFbcServClassActiveTime
    }
    STATUS deprecated
    DESCRIPTION
	"Service-based charging (FBC) service class statistics per APN."
    ::= { ggsnMIBGroups 16 }

ggsnFbcStatsGroup		OBJECT-GROUP
    OBJECTS {
	ggsnFbcInitiatedDeactivation,
        ggsnFbcExtPrsUpdReqNoMatch,
        ggsnFbcExtCreditUpdReqNoMatch,
        ggsnFbcExtUpdReqFailure
    }
    STATUS current
    DESCRIPTION
	"SACC statistics."
    ::= { ggsnMIBGroups 17 }

ggsnApnFbcPrasStatsGroup	OBJECT-GROUP
    OBJECTS {
	ggsnApnFbcPrasName,
	ggsnApnFbcPrasStartReq,
	ggsnApnFbcPrasStartReqFail,
	ggsnApnFbcPrasUpdateReq,
	ggsnApnFbcPrasUpdateReqFail,
	ggsnApnFbcPrasStopReq,
	ggsnApnFbcPrasStopReqFail,
	ggsnApnFbcPrasUserServiceDenied,
	ggsnApnFbcPrasUserUnknown
    }
    STATUS current
    DESCRIPTION
    "Policy control application system statistics per APN."
    ::= { ggsnMIBGroups 18 }

ggsnApnFbcCcasStatsGroup	OBJECT-GROUP
    OBJECTS {
	ggsnApnFbcCcasName,
	ggsnApnFbcCcasStartReq,
	ggsnApnFbcCcasStartReqFail,
	ggsnApnFbcCcasUpdateReq,
	ggsnApnFbcCcasUpdateReqFail,
	ggsnApnFbcCcasStopReq,
	ggsnApnFbcCcasStopReqFail,
	ggsnApnFbcCcasUserServiceDenied,
	ggsnApnFbcCcasUserUnknown,
	ggsnApnSaccCcasAuthReject,
	ggsnApnSaccCcasCcNotApplicable
    }
    STATUS current
    DESCRIPTION
    "Online charging application system statistics per APN."
    ::= { ggsnMIBGroups 19 }

ggsnFbcDiamApplSysStatsGroup	OBJECT-GROUP
    OBJECTS {
	ggsnFbcDiamApplSysName,
	ggsnFbcDiamApplSysReq
    }
    STATUS current
    DESCRIPTION
    "Diameter application system statistics."
    ::= { ggsnMIBGroups 20 }

ggsnApnFbcRateGroupStatsGroup	OBJECT-GROUP
    OBJECTS {
	ggsnApnFbcRateGroupEventStartTrans,
	ggsnApnFbcRateGroupEventSuccessTrans
    }
    STATUS obsolete
    DESCRIPTION
	"Service-based charging (FBC) rate group statistics per APN."
    ::= { ggsnMIBGroups 21 }

ggsnL2tpTunnelStatsGroup OBJECT-GROUP
   OBJECTS { ggsnL2tpTunnelLocalTID,
             ggsnL2tpTunnelRemoteTID,
             ggsnL2tpTunnelLocalIp,
             ggsnL2tpTunnelRemoteIp,
             ggsnL2tpTunnelActiveSessions,
             ggsnL2tpTunnelControlTxPackets,
             ggsnL2tpTunnelControlRxPackets,
             ggsnL2tpTunnelDataTxPackets,
             ggsnL2tpTunnelDataRxPackets,
             ggsnL2tpTunnelDiscardedTxPackets,
             ggsnL2tpTunnelDiscardedRxPackets
   }
   STATUS current
   DESCRIPTION
         "The basic collection of objects providing
          measurements on a per L2TP tunnel of the ggsn node."
   ::= { ggsnMIBGroups 22 }

ggsnApnSaccPcrfStatsGroup	OBJECT-GROUP
    OBJECTS {
	ggsnApnSaccPcrfName,
	ggsnApnSaccPcrfAuthorFail,
	ggsnApnSaccPcrfAuthenFail,
	ggsnApnSaccPcrfUpdCcReqSessIdNoMatch,
	ggsnApnSaccPcrfActivePdpContextUsageReporting,
	ggsnApnSaccPcrfActiveIPcanSessions,
	ggsnApnSaccPcrfActiveDedicatedIPcanBearers
    }
    STATUS current
    DESCRIPTION
    "PCRF statistics per APN."
    ::= { ggsnMIBGroups 23 }

ggsnApnSaccRsStatsGroup	OBJECT-GROUP
    OBJECTS {
	ggsnApnSaccRsName,
	ggsnApnSaccRsUplinkBytes,
	ggsnApnSaccRsDownlinkBytes,
	ggsnApnSaccRsServiceInstances,
	ggsnApnSaccRsAuthDownlinkPacketsDropped,
	ggsnApnSaccRsAuthUplinkPacketsDropped,
	ggsnApnSaccRsGateDownlinkPacketsDropped,
	ggsnApnSaccRsGateUplinkPacketsDropped
    }
    STATUS current
    DESCRIPTION
    "Rule space statistics per APN."
    ::= { ggsnMIBGroups 24 }

ggsnApnSacc2ServIdentStatsGroup   OBJECT-GROUP
    OBJECTS {
        ggsnApnSacc2ServIdentUplinkBytes,
        ggsnApnSacc2ServIdentDownlinkBytes,
        ggsnApnSacc2ServIdentEventTrans,
        ggsnApnSacc2ServIdentEventTransFail,
        ggsnApnSacc2ServIdentEventStartTrans,
        ggsnApnSacc2ServIdentEventSuccessTrans
    }
    STATUS deprecated
    DESCRIPTION
        "Service-based charging (SACC 2) service identifier statistics per APN."
    ::= { ggsnMIBGroups 25 }

ggsnApnSacc2ServClassStatsGroup   OBJECT-GROUP
    OBJECTS {
        ggsnApnSacc2ServClassUplinkBytes,
        ggsnApnSacc2ServClassDownlinkBytes,
        ggsnApnSacc2ServClassActiveTime
    }
    STATUS deprecated
    DESCRIPTION
        "Service-based charging (SACC 2) service class statistics per APN."
    ::= { ggsnMIBGroups 26 }

ggsnApnSacc3ServIdentStatsGroup   OBJECT-GROUP
    OBJECTS {
        ggsnApnFbcServIdentUplinkBytes,
        ggsnApnFbcServIdentDownlinkBytes
    }
    STATUS deprecated
    DESCRIPTION
        "Service-based charging (SACC 3) service identifier statistics per APN."
    ::= { ggsnMIBGroups 27 }

ggsnApnSacc3RatingGroupStatsGroup   OBJECT-GROUP
    OBJECTS {
        ggsnApnSacc3RatingGroupUplinkBytes,
        ggsnApnSacc3RatingGroupDownlinkBytes
    }
    STATUS deprecated
    DESCRIPTION
        "Service-based charging (SACC 3) rating group statistics per APN."
    ::= { ggsnMIBGroups 28 }

pgwGlobalStatisticsGroup   OBJECT-GROUP
    OBJECTS {
        pgwNbrOfActiveEpsBearer,
        pgwNbrOfActiveIpv6EpsBearer,
        pgwNbrOfActiveIpv4v6EpsBearer,
        pgwWlanNbrOfActiveEpsBearer
    }
    STATUS current
    DESCRIPTION
        "Global statistics for EPS bearers"
    ::= { ggsnMIBGroups 29 }

pgwAttemptedEpsBearerStatsGroup   OBJECT-GROUP
    OBJECTS {
        pgwAttemptedEpsBearerActivation,
        pgwAttemptedEpsBearerIpv6Activation,
        pgwAttemptedEpsBearerModification,
        pgwAttemptedEpsBearerDeactivation,       
        pgwAttemptedDedicatedEpsBearerActivation,
        pgwAttemptedDedicatedEpsBearerIpv6Activation,
        pgwAttemptedEpsBearerIpv4v6Activation,
        pgwAttempteds2aEpsBearerActivation 
    }
    STATUS current
    DESCRIPTION
        "Global statistics for EPS bearer attempts"
    ::= { ggsnMIBGroups 30 }

pgwCompletedEpsBearerStatsGroup   OBJECT-GROUP
    OBJECTS {
        pgwCompletedEpsBearerActivation,
        pgwCompletedEpsBearerIpv6Activation,
        pgwCompletedEpsBearerModification,
        pgwCompletedEpsBearerDeactivation,
        pgwCompletedDedicatedEpsBearerActivation,
		pgwCompletedDedicatedEpsBearerIpv6Activation,
        pgwCompletedEpsBearerIpv4v6Activation,
        pgwCompleteds2aEpsBearerActivation
    }
    STATUS current
    DESCRIPTION
        "Global statistics for EPS bearer completions"
    ::= { ggsnMIBGroups 31 }
    
pgwApnSaccRatingGroupStatsGroup   OBJECT-GROUP
    OBJECTS {
        pgwApnSaccRatingGroupUplinkBytes,
        pgwApnSaccRatingGroupDownlinkBytes
    }
    STATUS current
    DESCRIPTION
    "Rating group statistics per APN."
    ::= { ggsnMIBGroups 32 }

s6bInterfaceGroup   OBJECT-GROUP
    OBJECTS {
        s6bAarSent,
        s6bAaaSuccRcvd,
        s6bAaaFailRcvd,
        s6bAaaInvalidRcvd,
        s6bStrSent,
	s6bStaSuccRcvd,
        s6bStaFailRcvd
    }
    STATUS current
    DESCRIPTION
        "S6b statistics."
    ::= { ggsnMIBGroups 33 }


END
