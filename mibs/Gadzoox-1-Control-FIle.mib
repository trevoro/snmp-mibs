Gadzoox-1-Control-FIle

--        FORCE-INCLUDE <envoy/h/snmp.h>
--        FORCE-INCLUDE "pnamib.h"

        
DEFINITIONS ::= BEGIN

	IMPORTS 
	enterprises
		FROM RFC1155-SMI
	OBJECT-TYPE
		FROM RFC-1212;

       gadzoox               OBJECT IDENTIFIER ::= { enterprises 1754 }
--      netMgmt              OBJECT IDENTIFIER ::= { gadzoox 1 }

netMgmt	OBJECT-TYPE
--	DEFAULT get-function-async get-%n
--	DEFAULT set-function-async set-%n
--	DEFAULT test-function-async test-%n
--	DEFAULT next-function-async std-next-async
--	DEFAULT cookie (char *) 0
	SYNTAX INTEGER
	ACCESS read-only
	STATUS mandatory
	::= { gadzoox 1 }

         common              OBJECT IDENTIFIER ::= { netMgmt 1 }
          system             OBJECT IDENTIFIER ::= { common 1 }
           zoning            OBJECT IDENTIFIER ::= { system 3 }
          download           OBJECT IDENTIFIER ::= { common 3 }
          security           OBJECT IDENTIFIER ::= { common 4 }
          discovery          OBJECT IDENTIFIER ::= { common 5 }
          monitor            OBJECT IDENTIFIER ::= { common 6 }
          proxy              OBJECT IDENTIFIER ::= { common 7 }
           policy            OBJECT IDENTIFIER ::= { proxy 11 }
          gbic               OBJECT IDENTIFIER ::= { common 8 }
         hub                 OBJECT IDENTIFIER ::= { netMgmt 2 }
         areaSwitch          OBJECT IDENTIFIER ::= { netMgmt 3 }
         channelAgent        OBJECT IDENTIFIER ::= { netMgmt 4 }
         traps               OBJECT IDENTIFIER ::= { netMgmt 5 }
         switch              OBJECT IDENTIFIER ::= { netMgmt 6 }
          capChas             OBJECT IDENTIFIER ::= { switch 1 }
          capPim              OBJECT IDENTIFIER ::= { switch 2 }


nlPendingZoneTable OBJECT-TYPE
--	DEFAULT next-function-async nlPendingZone-next
	SYNTAX INTEGER
	ACCESS read-only
	STATUS mandatory
	::= { zoning 7 }

nlPendingZoneMemberTable OBJECT-TYPE
--	DEFAULT next-function-async nlPendingZoneMember-next
	SYNTAX INTEGER
	ACCESS read-only
	STATUS mandatory
	::= { zoning 9 }


nlActiveZoneTable OBJECT-TYPE
--	DEFAULT next-function-async nlActiveZone-next
	SYNTAX INTEGER
	ACCESS read-only
	STATUS mandatory
	::= { zoning 11 }

nlActiveZoneMemberTable OBJECT-TYPE
--	DEFAULT next-function-async nlActiveZoneMember-next
	SYNTAX INTEGER
	ACCESS read-only
	STATUS mandatory
	::= { zoning 13 }

deviceTable OBJECT-TYPE
--	DEFAULT next-function-async dev-next
	SYNTAX INTEGER
	ACCESS read-only
	STATUS mandatory
	::= { proxy 9 }

gbicTable OBJECT-TYPE
--	DEFAULT next-function-async gbic-next
	SYNTAX INTEGER
	ACCESS read-only
	STATUS mandatory
	::= { gbic 1 }

trapIPaddrTable	OBJECT-TYPE
--	DEFAULT next-function-async trap-next
	SYNTAX INTEGER
	ACCESS read-only
	STATUS mandatory
	::= { traps 1}	 	 

capChasTable	OBJECT-TYPE
--	DEFAULT next-function-async capChas-next
	SYNTAX INTEGER
	ACCESS read-only
	STATUS mandatory
	::= { capChas 1}	 	 

capChasSlotTable	OBJECT-TYPE
--	DEFAULT next-function-async capChasSlot-next
	SYNTAX INTEGER
	ACCESS read-only
	STATUS mandatory
	::= { capChas 2}	 	 

capPimTable	OBJECT-TYPE
--	DEFAULT next-function-async capPim-next
	SYNTAX INTEGER
	ACCESS read-only
	STATUS mandatory
	::= { capPim 1}	 	 

capPortTable OBJECT-TYPE
--	DEFAULT next-function-async capPort-next
	SYNTAX INTEGER
	ACCESS read-only
	STATUS mandatory
	::= { capPim 2}	 	 

END
