--			Ascend mibikespd MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIKESPD-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfIkeSpd  OBJECT IDENTIFIER ::= { configuration 166}

	-- The mibmibProfIkeSpd table
	--
	-- This table contains parameters for the mibmibProfIkeSpd profile
	--

    mibmibProfIkeSpdTable	OBJECT-TYPE
	SYNTAX		SEQUENCE OF MibmibProfIkeSpdEntry
	ACCESS		not-accessible
	STATUS		mandatory
	DESCRIPTION	"A list of mibmibProfIkeSpd profile entries."
	::= { mibmibProfIkeSpd 1 }

    mibmibProfIkeSpdEntry	OBJECT-TYPE
	SYNTAX		MibmibProfIkeSpdEntry
	ACCESS		not-accessible
	STATUS		mandatory
	DESCRIPTION	"A mibmibProfIkeSpd entry containing objects that
			 maps to the parameters of mibmibProfIkeSpd profile."
	INDEX		{ mibProfIkeSpd-Index-o }
	::= { mibmibProfIkeSpdTable 1 }

    MibmibProfIkeSpdEntry ::=
	SEQUENCE {
	    mibProfIkeSpd-Index-o
		INTEGER,
	    mibProfIkeSpd-Action-o
		INTEGER
	}

    mibProfIkeSpd-Index-o	OBJECT-TYPE
	SYNTAX	INTEGER
	ACCESS	read-only
	STATUS	mandatory
	DESCRIPTION	""
	::= { mibmibProfIkeSpdEntry 1 }

    mibProfIkeSpd-Action-o	OBJECT-TYPE
	SYNTAX	INTEGER {
		    noAction (1),
		    createProfile (2),
		    deleteProfile (3)
		}
	ACCESS	read-write
	STATUS	mandatory
	DESCRIPTION	""
	::= { mibmibProfIkeSpdEntry 2 }


	-- The mibmibProfIkeSpd__ike_policy table
	--
	-- This table contains parameters for the mibmibProfIkeSpd__ike_policy profile
	--

    mibmibProfIkeSpd-IkePolicyTable	OBJECT-TYPE
	SYNTAX		SEQUENCE OF MibmibProfIkeSpd-IkePolicyEntry
	ACCESS		not-accessible
	STATUS		mandatory
	DESCRIPTION	"A list of mibmibProfIkeSpd__ike_policy profile entries."
	::= { mibmibProfIkeSpd 2 }

    mibmibProfIkeSpd-IkePolicyEntry	OBJECT-TYPE
	SYNTAX		MibmibProfIkeSpd-IkePolicyEntry
	ACCESS		not-accessible
	STATUS		mandatory
	DESCRIPTION	"A mibmibProfIkeSpd__ike_policy entry containing objects that
			 maps to the parameters of mibmibProfIkeSpd__ike_policy profile."
	INDEX		{ mibProfIkeSpd-IkePolicy-Index-o, mibProfIkeSpd-IkePolicy-Index1-o }
	::= { mibmibProfIkeSpd-IkePolicyTable 1 }

    MibmibProfIkeSpd-IkePolicyEntry ::=
	SEQUENCE {
	    mibProfIkeSpd-IkePolicy-Index-o
		INTEGER,
	    mibProfIkeSpd-IkePolicy-Index1-o
		INTEGER,
	    mibProfIkeSpd-IkePolicy-ValidEntry
		INTEGER,
	    mibProfIkeSpd-IkePolicy-Address-IpAddress
		IpAddress,
	    mibProfIkeSpd-IkePolicy-Address-Netmask
		IpAddress,
	    mibProfIkeSpd-IkePolicy-IkeProposals
		DisplayString,
	    mibProfIkeSpd-IkePolicy-PresharedKey
		DisplayString
	}

    mibProfIkeSpd-IkePolicy-Index-o	OBJECT-TYPE
	SYNTAX	INTEGER
	ACCESS	read-only
	STATUS	mandatory
	DESCRIPTION	""
	::= { mibmibProfIkeSpd-IkePolicyEntry 1 }

    mibProfIkeSpd-IkePolicy-Index1-o	OBJECT-TYPE
	SYNTAX	INTEGER
	ACCESS	read-only
	STATUS	mandatory
	DESCRIPTION	""
	::= { mibmibProfIkeSpd-IkePolicyEntry 2 }

    mibProfIkeSpd-IkePolicy-ValidEntry	OBJECT-TYPE
	SYNTAX	INTEGER {
		    no (1),
		    yes (2)
		}
	ACCESS	read-write
	STATUS	mandatory
	DESCRIPTION	"This policy can be disabled by setting this field to no."
	::= { mibmibProfIkeSpd-IkePolicyEntry 3 }

    mibProfIkeSpd-IkePolicy-Address-IpAddress	OBJECT-TYPE
	SYNTAX	IpAddress
	ACCESS	read-write
	STATUS	mandatory
	DESCRIPTION	"An IP address."
	::= { mibmibProfIkeSpd-IkePolicyEntry 4 }

    mibProfIkeSpd-IkePolicy-Address-Netmask	OBJECT-TYPE
	SYNTAX	IpAddress
	ACCESS	read-write
	STATUS	mandatory
	DESCRIPTION	"The netmask"
	::= { mibmibProfIkeSpd-IkePolicyEntry 5 }

    mibProfIkeSpd-IkePolicy-IkeProposals	OBJECT-TYPE
	SYNTAX	DisplayString
	ACCESS	read-write
	STATUS	mandatory
	DESCRIPTION	"The name of the IKE Protection Suite profile to be used for IKE SAs negotiation with peers encompassed by this policy. This may be a unique proposal or the first element of a list of proposals."
	::= { mibmibProfIkeSpd-IkePolicyEntry 6 }

    mibProfIkeSpd-IkePolicy-PresharedKey	OBJECT-TYPE
	SYNTAX	DisplayString
	ACCESS	read-write
	STATUS	mandatory
	DESCRIPTION	"Preshared Key for IKE authentication."
	::= { mibmibProfIkeSpd-IkePolicyEntry 7 }

END
