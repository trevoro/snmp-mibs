RIVERSTONE-CAPACITY-MIB DEFINITIONS ::= BEGIN

IMPORTS
   MODULE-IDENTITY,OBJECT-IDENTITY, OBJECT-TYPE, Unsigned32
       FROM SNMPv2-SMI
   MODULE-COMPLIANCE, OBJECT-GROUP
      FROM SNMPv2-CONF
   riverstoneMibs
       FROM RIVERSTONE-SMI-MIB;

rsCapacityMIB MODULE-IDENTITY
   LAST-UPDATED "200304041300Z"  -- April 4th 2003
  
        ORGANIZATION "Riverstone Networks, Inc"
        CONTACT-INFO
            "Riverstone Networks, Inc
             5200 Great America Parkway
             Santa Clara CA USA 95054
             PHONE:+1 408.878.6500
             EMAIL: nms-eng@riverstonenet.com
             WEB: http://www.riverstonenet.com"
    DESCRIPTION
     "This module defines a schema to access RS system resource 
      capacity statistics."
  
    REVISION     "200304041300Z"
    DESCRIPTION
         "First Version which only has objects for CPU utilization."
      ::= {  riverstoneMibs 270 }   




-- Capacity metrics are broken down by these functional areas 

    rsCpu  OBJECT-IDENTITY
    STATUS current
    DESCRIPTION
	   "cpu group"
    ::= { rsCapacityMIB 5 }

  
    rsCapConformance OBJECT-IDENTITY
    STATUS current
    DESCRIPTION
	   "capacity conformance group "
    ::= { rsCapacityMIB 35 }



-- cpu group : capacity stats for CPU main memory

   rsCapCPUTable OBJECT-TYPE
       SYNTAX      SEQUENCE OF RsCapCPUEntry
       MAX-ACCESS  not-accessible
       STATUS      current
       DESCRIPTION
        "Summary of CPU statistics.  It is assumed that there is only 
         one CPU per line card."
       ::= { rsCpu 1 }
 
   rsCapCPUEntry OBJECT-TYPE
       SYNTAX      RsCapCPUEntry
       MAX-ACCESS  not-accessible
       STATUS      current
       DESCRIPTION
        "An entry containing CPU utilization information."
       INDEX   { rsCapCPUModuleIndex }
       ::= { rsCapCPUTable 1 }
 
   RsCapCPUEntry ::=
       SEQUENCE {
           rsCapCPUModuleIndex               Unsigned32,
           rsCapCPUCurrentUtilization5Sec    Unsigned32,
           rsCapCPUCurrentUtilization60Sec   Unsigned32,
           rsCapCPUCurrentUtilization5Min    Unsigned32

       
       }
 

   rsCapCPUModuleIndex OBJECT-TYPE
       SYNTAX      Unsigned32 
       MAX-ACCESS  not-accessible
       STATUS      current
       DESCRIPTION
               "The Slot index in which the current CPU is residing."
       ::= { rsCapCPUEntry 1 }

   rsCapCPUCurrentUtilization5Sec OBJECT-TYPE
       SYNTAX      Unsigned32 (0..100)
       MAX-ACCESS  read-only
       STATUS      current
       DESCRIPTION
               "The CPU utilization expressed as an integer percentage.
                This is calculated over the last 5 seconds at a 0.1 second
                interval as a simple average."

       ::= { rsCapCPUEntry 2 }
 rsCapCPUCurrentUtilization60Sec OBJECT-TYPE
       SYNTAX      Unsigned32 (0..100)
       MAX-ACCESS  read-only
       STATUS      current
       DESCRIPTION
               "The CPU utilization expressed as an integer percentage.
                This is calculated over the last 60 seconds at a 0.1 second
                interval as a simple average."

       ::= { rsCapCPUEntry 3 }

 rsCapCPUCurrentUtilization5Min OBJECT-TYPE
       SYNTAX      Unsigned32 (0..100)
       MAX-ACCESS  read-only
       STATUS      current
       DESCRIPTION
               "The CPU utilization expressed as an integer percentage.
                This is calculated over the last  5 minutes at a 0.1 second
                interval as a simple average."

       ::= { rsCapCPUEntry 4 }

 
-- ### Compliance ###

rsCapCompliances OBJECT IDENTIFIER ::= { rsCapConformance 1 }
rsCapGroups      OBJECT IDENTIFIER ::= { rsCapConformance 2 }
 
rsCapComplianceV1  MODULE-COMPLIANCE
    STATUS current
    DESCRIPTION
            "The compliance statement for the RIVERSTONE-CAPACITY-MIB."
    MODULE  -- this module
    MANDATORY-GROUPS { rsCapConfGroupV1 }
    ::= { rsCapCompliances 1 }


rsCapConfGroupV1  OBJECT-GROUP 
   OBJECTS {
     rsCapCPUCurrentUtilization5Sec,
     rsCapCPUCurrentUtilization60Sec,
     rsCapCPUCurrentUtilization5Min
}
  STATUS current
  DESCRIPTION
  "A set of managed objects that make up version 1.0 of the Riverstone Capacity mib."
   ::= { rsCapGroups 1 } 
 
END
