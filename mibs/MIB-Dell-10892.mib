-------------------------------------------------------------------------------
--
-- Server Administrator MIB : 10892.mib
--
-- Copyright (c) 2000-2002 Dell Computer Corporation.
-- All Rights Reserved.
--
-- The information and functionality described by this MIB file,
-- like many MIB files, is subject to change without notice. Please
-- examine the version number of this MIB and compare it to the version
-- number you are expecting.
--
-- MIB Version 1.55                     06 March 2002
--
-------------------------------------------------------------------------------

MIB-Dell-10892 DEFINITIONS ::= BEGIN

IMPORTS
    enterprises, IpAddress
        FROM RFC1155-SMI
    OBJECT-TYPE
        FROM RFC-1212
    TRAP-TYPE
        FROM RFC-1215
    DisplayString
        FROM RFC1213-MIB;

-- Dell enterprises ID
dell                          OBJECT IDENTIFIER ::= { enterprises    674   }
-- Server Administrator
server3                       OBJECT IDENTIFIER ::= { dell           10892 }
-- Server Administrator Groups
baseboardGroup                OBJECT IDENTIFIER ::= { server3        1     }
drsOutOfBandGroup             OBJECT IDENTIFIER ::= { server3        2     }
mIBVersionGroup               OBJECT IDENTIFIER ::= { baseboardGroup 1     }
systemManagementSoftwareGroup OBJECT IDENTIFIER ::= { baseboardGroup 100   }
systemStateGroup              OBJECT IDENTIFIER ::= { baseboardGroup 200   }
chassisInformationGroup       OBJECT IDENTIFIER ::= { baseboardGroup 300   }
operatingSystemGroup          OBJECT IDENTIFIER ::= { baseboardGroup 400   }
systemResourceGroup           OBJECT IDENTIFIER ::= { baseboardGroup 500   }
powerGroup                    OBJECT IDENTIFIER ::= { baseboardGroup 600   }
thermalGroup                  OBJECT IDENTIFIER ::= { baseboardGroup 700   }
userSecurityGroup             OBJECT IDENTIFIER ::= { baseboardGroup 800   }
remoteFlashBIOSGroup          OBJECT IDENTIFIER ::= { baseboardGroup 900   }
portGroup                     OBJECT IDENTIFIER ::= { baseboardGroup 1000  }
deviceGroup                   OBJECT IDENTIFIER ::= { baseboardGroup 1100  }
slotGroup                     OBJECT IDENTIFIER ::= { baseboardGroup 1200  }
memoryGroup                   OBJECT IDENTIFIER ::= { baseboardGroup 1300  }
biosSetUpControlGroup         OBJECT IDENTIFIER ::= { baseboardGroup 1400  }
lraGroup                      OBJECT IDENTIFIER ::= { baseboardGroup 1500  }
cooGroup                      OBJECT IDENTIFIER ::= { baseboardGroup 1600  }
remoteAccessGroup             OBJECT IDENTIFIER ::= { baseboardGroup 1700  }
alertGroup                    OBJECT IDENTIFIER ::= { baseboardGroup 5000  }

--
-- Textual Conventions
--
DellString                  ::= DisplayString (SIZE (0..64))
DellSecurityString          ::= DisplayString (SIZE (0..255))
DellCostofOwnershipString   ::= DisplayString (SIZE (0..64))
DellObjectRange             ::= INTEGER (1..128)
DellUnsigned8BitRange       ::= INTEGER (0..255)
DellUnsigned16BitRange      ::= INTEGER (0..65535)
DellUnsigned32BitRange      ::= INTEGER (0..4294967295)
DellSigned32BitRange        ::= INTEGER (-2147483647..2147483647)
DellBoolean                 ::= INTEGER (0..1) -- FALSE = 0, TRUE = 1

-- Please Note:
-- Variables with definitions of xxxCapabilities or xxxCapabilitiesUnique
-- are integers representing a series of bit definitions. They are NOT enumerations
-- and should be treated as bit fields. The value is passed as a decimal value;
-- it should be converted to hex, and the appropriate bits should be parsed from
-- that. Some of the more common bit combinations are defined in some variables,
-- but not all combinations are or will be defined.

DellStateCapabilities             ::= INTEGER {
    -- If set to 0 (zero) the object has no capabilities
    unknownCapabilities(1),       -- The objects capabilities are unknown
    -- The objects capabilities allow it to be set to:
    enableCapable(2),             -- be disabled (offline) or be enabled (online)
    notReadyCapable(4),           -- not ready
    enableAndNotReadyCapable(6)   -- enable and not ready Capable
}

DellProbeCapabilities                           ::= INTEGER {
    -- If set to 0 (zero) the object has no capabilities
    -- The objects capabilities allow it to be set to:
    upperNonCriticalThresholdSetCapable(1),     -- upper noncritical threshold can be set
    lowerNonCriticalThresholdSetCapable(2),     -- lower noncritical threshold can be set
    upperNonCriticalThresholdDefaultCapable(4), -- upper noncritical threshold can be set to default
    lowerNonCriticalThresholdDefaultCapable(8)  -- lower noncritical threshold can be set to default
}

-- Please Note:
-- Variables with definitions of xxxSettings or xxxSettingsUnique
-- are integers representing a series of bit definitions. They are NOT enumerations
-- and should be treated as bit fields. The value is passed as a decimal value;
-- it should be converted to hex, and the appropriate bits should be parsed from
-- that.  Some of the more common bit combinations are defined in some variables,
-- but not all combinations are or will be defined.

DellStateSettings           ::= INTEGER {
    -- If set to 0 (zero) the object has no settings capabilities, and it's state is disabled
    unknown(1),             -- The objects state is unknown
    enabled(2),             -- The objects state is disabled (offline) 0, or enabled (online) 1
    notReady(4),            -- The objects state is not ready
    enabledAndNotReady(6)   -- enabled and not ready
}

DellStatus                  ::= INTEGER {
    other(1),               -- the status of the object is not one of the following:
    unknown(2),             -- the status of the object is unknown
                            --  (not known or monitored)
    ok(3),                  -- the status of the object is ok
    nonCritical(4),         -- the status of the object is warning, non-critical
    critical(5),            -- the status of the object is critical (failure)
    nonRecoverable(6)       -- the status of the object is non-recoverable (dead)
}

DellStatusRedundancy        ::= INTEGER {
    other(1),               -- the status is not one of following:
    unknown(2),             -- the status of the redundancy object is unknown
    full(3),                -- the object is fully redundant
    degraded(4),            -- the object's redundancy has been degraded
    lost(5),                -- the object's redundancy has been lost
    notRedundant(6),        -- redundancy does not apply or it is not redundant
    redundancyOffline(7)    -- the status of the object is that its' redundancy is offline
}

DellStatusProbe             ::= INTEGER {
    other(1),               -- the status of the object is not one of following:
    unknown(2),             -- the status of the object is unknown
                            -- (not known or monitored)
    ok(3),                  -- the status of the object is ok
    nonCriticalUpper(4),    -- the object is at the non-critical upper limit
    criticalUpper(5),       -- the object is at the critical upper limit
    nonRecoverableUpper(6), -- the object is at the non-recoverable upper limit
    nonCriticalLower(7),    -- the object is at the non-critical lower limit
    criticalLower(8),       -- the object is at the critical lower limit
    nonRecoverableLower(9), -- the object is at the non-recoverable lower limit
    failed(10)              -- the status of the object is failed
}

-- This definition is required because SNMP V1 does not support 64 bit
-- ranges. The information sent back by this subagent will have the
-- most significant byte of the information as the first byte.
-- E.G. A hex address 0x1029384754657687
-- will be sent as hex:
-- 0001 0000 0010 1001 0011 1000 0100 0111 ...
-- Byte 1    Byte 2    Byte 3    Byte 4    ...
DellUnsigned64BitRange  ::=  OCTET STRING (SIZE(8))

-- DellDateName dates are defined in the displayable format
--   yyyymmddHHMMSS.uuuuuu+ooo
-- where yyyy is the year, mm is the month number, dd is the day of the month,
-- HHMMSS are the hours, minutes and seconds, respectively, uuuuuu is the
-- number of microseconds, and +ooo is the offset from UTC in minutes. If east
-- of UTC, the number is preceded by a plus (+) sign, and if west of UTC, the
-- number is preceded by a minus (-) sign.
--
-- For example, Wednesday, May 25, 1994, at 1:30:15 PM EDT
--   would be represented as: 19940525133015.000000-300
--
-- Values must be zero-padded if necessary, like "05" in the example above.
-- If a value is not supplied for a field, each character in the field
-- must be replaced with asterisk ('*') characters.
DellDateName           ::= DisplayString (SIZE (25))


-------------------------------------------------------------------------------
--
-- MIB Version Group
--
-------------------------------------------------------------------------------

mIBMajorVersionNumber           OBJECT-TYPE
    SYNTAX      DellUnsigned8BitRange
    ACCESS      read-only
    STATUS      mandatory
    DESCRIPTION
"0001.0001 This attribute defines the major version number of this MIB
supported by the systems management software."
    ::= { mIBVersionGroup 1 }
mIBMinorVersionNumber           OBJECT-TYPE
    SYNTAX      DellUnsigned8BitRange
    ACCESS      read-only
    STATUS      mandatory
    DESCRIPTION
"0001.0002 This attribute defines the minor version number of this MIB
supported by the systems management software."
    ::= { mIBVersionGroup 2 }


-------------------------------------------------------------------------------
--
-- System Management Software Group
--
-------------------------------------------------------------------------------

SMSSupportedTypes                 ::= INTEGER {
    supportsSNMP(1),              -- SNMP is supported
    supportsDMI(2),               -- DMI  is supported
    supportsSNMPandDMI(3),        -- Supports SNMP and DMI
    supportsCIMOM(4),             -- CIM  is supported
    supportsSNMPandCIMOM(5),      -- Supports SNMP and CIM
    supportsSNMPandDMIandCIMOM(7) -- Supports SNMP, DMI and CIM
}

systemManagementSoftwareName                    OBJECT-TYPE
    SYNTAX      DellString
    ACCESS      read-only
    STATUS      mandatory
    DESCRIPTION
"0100.0001 This attribute defines the product name of the
systems management software."
    ::= { systemManagementSoftwareGroup 1 }
systemManagementSoftwareVersionNumberName       OBJECT-TYPE
    SYNTAX      DellString
    ACCESS      read-only
    STATUS      mandatory
    DESCRIPTION
"0100.0002 This attribute defines the version number of the
instrumentation component of the systems management software."
    ::= { systemManagementSoftwareGroup 2 }
systemManagementSoftwareBuildNumber             OBJECT-TYPE
    SYNTAX      DellUnsigned16BitRange
    ACCESS      read-only
    STATUS      mandatory
    DESCRIPTION
"0100.0003 This attribute defines the build number of the
instrumentation component of the systems management software."
    ::= { systemManagementSoftwareGroup 3 }
systemManagementSoftwareDescriptionName         OBJECT-TYPE
    SYNTAX      DellString
    ACCESS      read-only
    STATUS      mandatory
    DESCRIPTION
"0100.0004 This attribute defines the description of the
systems management software."
    ::= { systemManagementSoftwareGroup 4 }
systemManagementSoftwareSupportedProtocol       OBJECT-TYPE
    SYNTAX      SMSSupportedTypes
    ACCESS      read-only
    STATUS      mandatory
    DESCRIPTION
"0100.0005 This attribute defines the protocols supported by the
systems management software."
    ::= { systemManagementSoftwareGroup 5 }
systemManagementSoftwarePreferredProtocol       OBJECT-TYPE
    SYNTAX      SMSSupportedTypes
    ACCESS      read-only
    STATUS      mandatory
    DESCRIPTION
"0100.0006 This attribute defines the protocol preferred by the
systems management software."
    ::= { systemManagementSoftwareGroup 6 }
systemManagementSoftwareUpdateLevelName         OBJECT-TYPE
    SYNTAX      DellString
    ACCESS      read-only
    STATUS      mandatory
    DESCRIPTION
"0100.0007 This attribute defines the update level of the
instrumentation component of the systems management software."
    ::= { systemManagementSoftwareGroup 7 }
systemManagementSoftwareURLName                 OBJECT-TYPE
    SYNTAX      DisplayString (SIZE (0..255))
    ACCESS      read-only
    STATUS      mandatory
    DESCRIPTION
"0100.0008 This attribute defines the Universal Resource Locator (URL) of the
systems management software."
    ::= { systemManagementSoftwareGroup 8 }
systemManagementSoftwareLanguageName            OBJECT-TYPE
    SYNTAX      DisplayString (SIZE (0..255))
    ACCESS      read-only
    STATUS      mandatory
    DESCRIPTION
"0100.0009 This attribute defines the language of the
systems management software."
    ::= { systemManagementSoftwareGroup 9 }
systemManagementSoftwareGlobalVersionName       OBJECT-TYPE
    SYNTAX      DellString
    ACCESS      read-only
    STATUS      mandatory
    DESCRIPTION
"0100.0010 This attribute defines the global version of the
systems management software."
    ::= { systemManagementSoftwareGroup 10 }


-------------------------------------------------------------------------------
--
-- System State Group
--
-------------------------------------------------------------------------------

-------------------------------------------------------------------------------
-- System State Table
-------------------------------------------------------------------------------

SystemStateTableEntry                           ::= SEQUENCE {
    systemStatechassisIndex                     DellObjectRange,
    systemStateGlobalSystemStatus               DellStatus,
    systemStateChassisState                     DellStateSettings,
    systemStateChassisStatus                    DellStatus,
    systemStatePowerUnitStateDetails            OCTET STRING (SIZE(1..128)),
    systemStatePowerUnitStatusRedundancy        DellStatusRedundancy,
    systemStatePowerUnitStatusDetails           OCTET STRING (SIZE(1..128)),
    systemStatePowerSupplyStateDetails          OCTET STRING (SIZE(1..128)),
    systemStatePowerSupplyStatusCombined        DellStatus,
    systemStatePowerSupplyStatusDetails         OCTET STRING (SIZE(1..128)),
    systemStateVoltageStateDetails              OCTET STRING (SIZE(1..128)),
    systemStateVoltageStatusCombined            DellStatus,
    systemStateVoltageStatusDetails             OCTET STRING (SIZE(1..128)),
    systemStateAmperageStateDetails             OCTET STRING (SIZE(1..128)),
    systemStateAmperageStatusCombined           DellStatus,
    systemStateAmperageStatusDetails            OCTET STRING (SIZE(1..128)),
    systemStateCoolingUnitStateDetails          OCTET STRING (SIZE(1..128)),
    systemStateCoolingUnitStatusRedundancy      DellStatusRedundancy,
    systemStateCoolingUnitStatusDetails         OCTET STRING (SIZE(1..128)),
    systemStateCoolingDeviceStateDetails        OCTET STRING (SIZE(1..128)),
    systemStateCoolingDeviceStatusCombined      DellStatus,
    systemStateCoolingDeviceStatusDetails       OCTET STRING (SIZE(1..128)),
    systemStateTemperatureStateDetails          OCTET STRING (SIZE(1..128)),
    systemStateTemperatureStatusCombined        DellStatus,
    systemStateTemperatureStatusDetails         OCTET STRING (SIZE(1..128)),
    systemStateMemoryDeviceStateDetails         OCTET STRING (SIZE(1..128)),
    systemStateMemoryDeviceStatusCombined       DellStatus,
    systemStateMemoryDeviceStatusDetails        OCTET STRING (SIZE(1..128)),
    systemStateChassisIntrusionStateDetails     OCTET STRING (SIZE(1..128)),
    systemStateChassisIntrusionStatusCombined   DellStatus,
    systemStateChassisIntrusionStatusDetails    OCTET STRING (SIZE(1..128)),
    systemStateACPowerSwitchStateDetails        OCTET STRING (SIZE(1..128)),
    systemStateACPowerSwitchStatusRedundancy    DellStatusRedundancy,
    systemStateACPowerSwitchStatusDetails       OCTET STRING (SIZE(1..128)),
    systemStateACPowerCordStateDetails          OCTET STRING (SIZE(1..128)),
    systemStateACPowerCordStatusCombined        DellStatus,
    systemStateACPowerCordStatusDetails         OCTET STRING (SIZE(1..128)),
    systemStateRedundantMemoryUnitStateDetails  OCTET STRING (SIZE(1..128)),
    systemStateRedundantMemoryUnitStatusRedundancy DellStatusRedundancy,
    systemStateRedundantMemoryUnitStatusDetails OCTET STRING (SIZE(1..128)),
    systemStateEventLogStatus                   DellStatus
}

systemStateTable                                OBJECT-TYPE
    SYNTAX      SEQUENCE OF SystemStateTableEntry
    ACCESS      not-accessible
    STATUS      mandatory
    DESCRIPTION
"0200.0010 This object defines the System State Table."
    ::= { systemStateGroup 10 }
systemStateTableEntry                           OBJECT-TYPE
    SYNTAX      SystemStateTableEntry
    ACCESS      not-accessible
    STATUS      mandatory
    DESCRIPTION
"0200.0010.0001 This object defines the System State Table Entry."
    INDEX       { systemStatechassisIndex }
    ::= { systemStateTable 1 }
systemStatechassisIndex                         OBJECT-TYPE
    SYNTAX      DellObjectRange
    ACCESS      read-only
    STATUS      mandatory
    DESCRIPTION
"0200.0010.0001.0001 This attribute defines the index (one based) of this
chassis."
    ::= { systemStateTableEntry 1 }
systemStateGlobalSystemStatus                   OBJECT-TYPE
    SYNTAX      DellStatus
    ACCESS      read-only
    STATUS      mandatory
    DESCRIPTION
"0200.0010.0001.0002 This attribute defines the global system status
of all chassis being monitored by the systems management software."
    ::= { systemStateTableEntry 2 }
systemStateChassisState                         OBJECT-TYPE
    SYNTAX      DellStateSettings
    ACCESS      read-only
    STATUS      mandatory
    DESCRIPTION
"0200.0010.0001.0003 This attribute defines the system state of this
chassis."
    ::= { systemStateTableEntry 3 }
systemStateChassisStatus                        OBJECT-TYPE
    SYNTAX      DellStatus
    ACCESS      read-only
    STATUS      mandatory
    DESCRIPTION
"0200.0010.0001.0004 This attribute defines the system status of this
chassis."
    ::= { systemStateTableEntry 4 }
systemStatePowerUnitStateDetails                OBJECT-TYPE
    SYNTAX      OCTET STRING (SIZE(1..128))
    ACCESS      read-only
    STATUS      mandatory
    DESCRIPTION
"0200.0010.0001.0005 This attribute defines the power unit state of all
power units in this chassis. The results are returned as a binary
octet string, each byte of the octet string represents the state of
the specific object. The first byte returned represents the state of
the first object, etc. The bytes have the same definition type as
DellStateSettings."
    ::= { systemStateTableEntry 5 }
systemStatePowerUnitStatusRedundancy            OBJECT-TYPE
    SYNTAX      DellStatusRedundancy
    ACCESS      read-only
    STATUS      mandatory
    DESCRIPTION
"0200.0010.0001.0006 This attribute defines the system status of the
power unit(s) of this chassis."
    ::= { systemStateTableEntry 6 }
systemStatePowerUnitStatusDetails               OBJECT-TYPE
    SYNTAX      OCTET STRING (SIZE(1..128))
    ACCESS      read-only
    STATUS      mandatory
    DESCRIPTION
"0200.0010.0001.0007 This attribute defines the power unit status of all
power units in this chassis. The results are returned as a binary
octet string, each byte of the octet string represents the status of
the specific object. The first byte returned represents the status of
the first object, etc. The bytes have the same definition type as
DellStatusRedundancy."
    ::= { systemStateTableEntry 7 }
systemStatePowerSupplyStateDetails              OBJECT-TYPE
    SYNTAX      OCTET STRING (SIZE(1..128))
    ACCESS      read-only
    STATUS      mandatory
    DESCRIPTION
"0200.0010.0001.0008 This attribute defines the power supply state of all
power supplies in this chassis. The results are returned as a binary
octet string, each byte of the octet string represents the state of the
specific object. The first byte returned represents the state of the first
object, etc. The bytes have the same definition type as DellStateSettings."
    ::= { systemStateTableEntry 8 }
systemStatePowerSupplyStatusCombined            OBJECT-TYPE
    SYNTAX      DellStatus
    ACCESS      read-only
    STATUS      mandatory
    DESCRIPTION
"0200.0010.0001.0009 This attribute defines the power supply status of all
power supplies in this chassis. The result is returned as a combined status
value. The value has the same definition type as DellStatus."
    ::= { systemStateTableEntry 9 }
systemStatePowerSupplyStatusDetails             OBJECT-TYPE
    SYNTAX      OCTET STRING (SIZE(1..128))
    ACCESS      read-only
    STATUS      mandatory
    DESCRIPTION
"0200.0010.0001.0010 This attribute defines the power supply status of all
power supplies in this chassis. The results are returned as a binary
octet string, each byte of the octet string represents the status of the
specific object. The first byte returned represents the status of the first
object, etc. The bytes have the same definition type as DellStatus."
    ::= { systemStateTableEntry 10 }
systemStateVoltageStateDetails                  OBJECT-TYPE
    SYNTAX      OCTET STRING (SIZE(1..128))
    ACCESS      read-only
    STATUS      mandatory
    DESCRIPTION
"0200.0010.0001.0011 This attribute defines the voltage state of all voltage
probes in this chassis. The results are returned as a binary octet
string, each byte of the octet string represents the state of the specific
object. The first byte returned represents the state of the first object,
etc. The bytes have the same definition type as DellStateSettings."
    ::= { systemStateTableEntry 11 }
systemStateVoltageStatusCombined                OBJECT-TYPE
    SYNTAX      DellStatus
    ACCESS      read-only
    STATUS      mandatory
    DESCRIPTION
"0200.0010.0001.0012 This attribute defines the voltage status of all
voltage probes in this chassis. The result is returned as a combined
status value. The value has the same definition type as DellStatus."
    ::= { systemStateTableEntry 12 }
systemStateVoltageStatusDetails                 OBJECT-TYPE
    SYNTAX      OCTET STRING (SIZE(1..128))
    ACCESS      read-only
    STATUS      mandatory
    DESCRIPTION
"0200.0010.0001.0013 This attribute defines the voltage status of all voltage
probes in this chassis. The results are returned as a binary octet
string, each byte of the octet string represents the status of the specific
object. The first byte returned represents the status of the first object,
etc. The bytes have the same definition type as DellStatus."
    ::= { systemStateTableEntry 13 }
systemStateAmperageStateDetails                 OBJECT-TYPE
    SYNTAX      OCTET STRING (SIZE(1..128))
    ACCESS      read-only
    STATUS      mandatory
    DESCRIPTION
"0200.0010.0001.0014 This attribute defines the state of all current
probes in this chassis. The results are returned as a binary octet
string, each byte of the octet string represents the state of the
specific object. The first byte returned represents the state of the
first object, etc. The bytes have the same definition type as
DellStateSettings."
    ::= { systemStateTableEntry 14 }
systemStateAmperageStatusCombined               OBJECT-TYPE
    SYNTAX      DellStatus
    ACCESS      read-only
    STATUS      mandatory
    DESCRIPTION
"0200.0010.0001.0015 This attribute defines the amperage status of all
amperage probes in this chassis. The result is returned as a combined
status value. The value has the same definition type as DellStatus."
    ::= { systemStateTableEntry 15 }
systemStateAmperageStatusDetails                OBJECT-TYPE
    SYNTAX      OCTET STRING (SIZE(1..128))
    ACCESS      read-only
    STATUS      mandatory
    DESCRIPTION
"0200.0010.0001.0016 This attribute defines the status of all current
probes in this chassis. The results are returned as a binary octet
string, each byte of the octet string represents the status of the
specific object. The first byte returned represents the status of the
first object, etc. The bytes have the same definition type as DellStatus."
    ::= { systemStateTableEntry 16 }
systemStateCoolingUnitStateDetails              OBJECT-TYPE
    SYNTAX      OCTET STRING (SIZE(1..128))
    ACCESS      read-only
    STATUS      mandatory
    DESCRIPTION
"0200.0010.0001.0017 This attribute defines the cooling unit state of all
cooling units in this chassis. The results are returned as a binary
octet string, each byte of the octet string represents the state of
the specific object. The first byte returned represents the state of
the first object, etc. The bytes have the same definition type as
DellStateSettings."
    ::= { systemStateTableEntry 17 }
systemStateCoolingUnitStatusRedundancy          OBJECT-TYPE
    SYNTAX      DellStatusRedundancy
    ACCESS      read-only
    STATUS      mandatory
    DESCRIPTION
"0200.0010.0001.0018 This attribute defines the system status of the
cooling units in this chassis. The returned value has the same
definition type as DellStatusRedundancy."
    ::= { systemStateTableEntry 18 }
systemStateCoolingUnitStatusDetails             OBJECT-TYPE
    SYNTAX      OCTET STRING (SIZE(1..128))
    ACCESS      read-only    STATUS      mandatory
    DESCRIPTION
"0200.0010.0001.0019 This attribute defines the cooling unit status of
all cooling units in this chassis. The results are returned as a
binary octet string, each byte of the octet string represents the status
of the specific object. The first byte returned represents the status of
the first object, etc. The bytes have the same definition type as
DellStatusRedundancy."
    ::= { systemStateTableEntry 19 }
systemStateCoolingDeviceStateDetails            OBJECT-TYPE
    SYNTAX      OCTET STRING (SIZE(1..128))
    ACCESS      read-only
    STATUS      mandatory
    DESCRIPTION
"0200.0010.0001.0020 This attribute defines the cooling device state of
all cooling devices in this chassis. The results are returned as a
binary octet string, each byte of the octet string represents the state
of the specific object. The first byte returned represents the state of
the first object, etc. The bytes have the same definition type as
DellStateSettings."
    ::= { systemStateTableEntry 20 }
systemStateCoolingDeviceStatusCombined          OBJECT-TYPE
    SYNTAX      DellStatus
    ACCESS      read-only
    STATUS      mandatory
    DESCRIPTION
"0200.0010.0001.0021 This attribute defines the cooling device status of all
cooling devices in this chassis. The result is returned as a combined
status value. The value has the same definition type as DellStatus."
    ::= { systemStateTableEntry 21 }
systemStateCoolingDeviceStatusDetails           OBJECT-TYPE
    SYNTAX      OCTET STRING (SIZE(1..128))
    ACCESS      read-only
    STATUS      mandatory
    DESCRIPTION
"0200.0010.0001.0022 This attribute defines the cooling device status of
all cooling devices in this chassis. The results are returned as a
binary octet string, each byte of the octet string represents the status
of the specific object. The first byte returned represents the status of
the first object, etc. The bytes have the same definition type as
DellStatus."
    ::= { systemStateTableEntry 22 }
systemStateTemperatureStateDetails              OBJECT-TYPE
    SYNTAX      OCTET STRING (SIZE(1..128))
    ACCESS      read-only
    STATUS      mandatory
    DESCRIPTION
"0200.0010.0001.0023 This attribute defines the temperature probe state of
all temperature probes in this chassis. The results are returned as a
binary octet string, each byte of the octet string represents the state of
the specific object. The first byte returned represents the state of the
first object, etc. The bytes have the same definition type as
DellStateSettings."
    ::= { systemStateTableEntry 23 }
systemStateTemperatureStatusCombined            OBJECT-TYPE
    SYNTAX      DellStatus
    ACCESS      read-only
    STATUS      mandatory
    DESCRIPTION
"0200.0010.0001.0024 This attribute defines the temperature status of all
temperature probes in this chassis. The result is returned as a
combined status value. The value has the same definition type as
DellStatus."
    ::= { systemStateTableEntry 24 }
systemStateTemperatureStatusDetails             OBJECT-TYPE
    SYNTAX      OCTET STRING (SIZE(1..128))
    ACCESS      read-only
    STATUS      mandatory
    DESCRIPTION
"0200.0010.0001.0025 This attribute defines the temperature probe status of
all temperature probes in this chassis. The results are returned as a
binary octet string, each byte of the octet string represents the status of
the specific object. The first byte returned represents the status of the
first object, etc. The bytes have the same definition type as DellStatus."
    ::= { systemStateTableEntry 25 }
systemStateMemoryDeviceStateDetails             OBJECT-TYPE
    SYNTAX      OCTET STRING (SIZE(1..128))
    ACCESS      read-only
    STATUS      mandatory
    DESCRIPTION
"0200.0010.0001.0026 This attribute defines the memory device
state of all memory devices in this chassis. The results are
returned as a binary octet string, each byte of the octet string represents
the state of the specific object. The first byte returned represents the
state of the first object, etc. The bytes have the same definition type
as DellStateSettings."
    ::= { systemStateTableEntry 26 }
systemStateMemoryDeviceStatusCombined           OBJECT-TYPE
    SYNTAX      DellStatus
    ACCESS      read-only
    STATUS      mandatory
    DESCRIPTION
"0200.0010.0001.0027 This attribute defines the memory device status of all
memory devices in this chassis. The result is returned as a combined
status value. The value has the same definition type as DellStatus."
    ::= { systemStateTableEntry 27 }
systemStateMemoryDeviceStatusDetails            OBJECT-TYPE
    SYNTAX      OCTET STRING (SIZE(1..128))
    ACCESS      read-only
    STATUS      mandatory
    DESCRIPTION
"0200.0010.0001.0028 This attribute defines the memory device status
of all memory devices in this chassis. The results are returned
as a binary octet string, each byte of the octet string represents the status
of the specific object. The first byte returned represents the status of the
first object, etc. The bytes have the same definition type as DellStatus."
    ::= { systemStateTableEntry 28 }
systemStateChassisIntrusionStateDetails         OBJECT-TYPE
    SYNTAX      OCTET STRING (SIZE(1..128))
    ACCESS      read-only
    STATUS      mandatory
    DESCRIPTION
"0200.0010.0001.0029 This attribute defines the intrusion state of all
intrusion detection devices in this chassis. The results are
returned as a binary octet string, each byte of the octet string represents
the state of the specific object. The first byte returned represents the
state of the first object, etc. The bytes have the same definition type
as DellStateSettings."
    ::= { systemStateTableEntry 29 }
systemStateChassisIntrusionStatusCombined       OBJECT-TYPE
    SYNTAX      DellStatus
    ACCESS      read-only
    STATUS      mandatory
    DESCRIPTION
"0200.0010.0001.0030 This attribute defines the intrusion reading of all
intrusion detection devices in this chassis.  The result is returned
as a combined status value. The value has the same definition type as
DellStatus."
    ::= { systemStateTableEntry 30 }
systemStateChassisIntrusionStatusDetails        OBJECT-TYPE
    SYNTAX      OCTET STRING (SIZE(1..128))
    ACCESS      read-only
    STATUS      mandatory
    DESCRIPTION
"0200.0010.0001.0031 This attribute defines the intrusion status of all
intrustion detection devices in this chassis. The results are returned
as a binary octet string, each byte of the octet string represents the value
of the specific object. The first byte returned represents the value of the
first object, etc. The bytes have the same definition type as DellStatus."
    ::= { systemStateTableEntry 31 }
systemStateACPowerSwitchStateDetails            OBJECT-TYPE
    SYNTAX      OCTET STRING (SIZE(1..128))
    ACCESS      read-only
    STATUS      mandatory
    DESCRIPTION
"0200.0010.0001.00032 This attribute defines the individual state of all
AC power switches in this chassis. The results are returned as a binary
octet string, each byte of the octet string represents the state of the
specific object. The first byte returned represents the state of the first
object, etc. The bytes have the same definition type as DellStateSettings."
    ::= { systemStateTableEntry 32 }
systemStateACPowerSwitchStatusRedundancy        OBJECT-TYPE
    SYNTAX      DellStatusRedundancy
    ACCESS      read-only
    STATUS      mandatory
    DESCRIPTION
"0200.0010.0001.0033 This attribute defines the overall redundancy status
of the AC power switch(es) in this chassis."
    ::= { systemStateTableEntry 33 }
systemStateACPowerSwitchStatusDetails           OBJECT-TYPE
    SYNTAX      OCTET STRING (SIZE(1..128))
    ACCESS      read-only
    STATUS      mandatory
    DESCRIPTION
"0200.0010.0001.0034 This attribute defines the individual status of all
AC power switches in this chassis. The results are returned as a binary
octet string, each byte of the octet string represents the status of the
specific object. The first byte returned represents the status of the first
object, etc. The bytes have the same definition type as DellStatusRedundancy."
    ::= { systemStateTableEntry 34 }
systemStateACPowerCordStateDetails              OBJECT-TYPE
    SYNTAX      OCTET STRING (SIZE(1..128))
    ACCESS      read-only
    STATUS      mandatory
    DESCRIPTION
"0200.0010.0001.0035 This attribute defines the individual state of all
AC power cords for any AC power switches in this chassis. The results
are returned as a binary octet string, each byte of the octet string
represents the state of the specific object. The first byte returned
represents the state of the first object, etc. The bytes have the same
definition type as DellStateSettings."
    ::= { systemStateTableEntry 35 }
systemStateACPowerCordStatusCombined            OBJECT-TYPE
    SYNTAX      DellStatus
    ACCESS      read-only
    STATUS      mandatory
    DESCRIPTION
"0200.0010.0001.0036 This attribute defines the overall status of all
AC power cords for any AC power switches in this chassis. The result
is returned as a combined status value. The value has the same definition
type as DellStatus."
    ::= { systemStateTableEntry 36 }
systemStateACPowerCordStatusDetails             OBJECT-TYPE
    SYNTAX      OCTET STRING (SIZE(1..128))
    ACCESS      read-only
    STATUS      mandatory
    DESCRIPTION
"0200.0010.0001.0037 This attribute defines the individual status of all
AC power cords for any AC power switches in this chassis. The results
are returned as a binary octet string, each byte of the octet string
represents the status of the specific object. The first byte returned
represents the status of the first object, etc. The bytes have the same
definition type as DellStatus."
    ::= { systemStateTableEntry 37 }
systemStateRedundantMemoryUnitStateDetails      OBJECT-TYPE
    SYNTAX      OCTET STRING (SIZE(1..128))
    ACCESS      read-only
    STATUS      mandatory
    DESCRIPTION
"0200.0010.0001.0038 This attribute defines the state of all redundant
memory units in this chassis. The results are returned as a binary
octet string, each byte of the octet string represents the state of
the specific object. The first byte returned represents the state of
the first object, etc. The bytes have the same definition type as
DellStateSettings."
    ::= { systemStateTableEntry 38 }
systemStateRedundantMemoryUnitStatusRedundancy  OBJECT-TYPE
    SYNTAX      DellStatusRedundancy
    ACCESS      read-only
    STATUS      mandatory
    DESCRIPTION
"0200.0010.0001.0039 This attribute defines the overall redundancy status
of the redundant memory unit(s) of this chassis."
    ::= { systemStateTableEntry 39 }
systemStateRedundantMemoryUnitStatusDetails     OBJECT-TYPE
    SYNTAX      OCTET STRING (SIZE(1..128))
    ACCESS      read-only
    STATUS      mandatory
    DESCRIPTION
"0200.0010.0001.0040 This attribute defines the status of all redundant
memory units in this chassis. The results are returned as a binary
octet string, each byte of the octet string represents the status of
the specific object. The first byte returned represents the status of
the first object, etc. The bytes have the same definition type as
DellStatusRedundancy."
    ::= { systemStateTableEntry 40 }
systemStateEventLogStatus                       OBJECT-TYPE
    SYNTAX      DellStatus
    ACCESS      read-only
    STATUS      mandatory
    DESCRIPTION
"0200.0010.0001.0041 This attribute defines the overall status of the
(ESM) event log of this chassis."
    ::= { systemStateTableEntry 41 }


-------------------------------------------------------------------------------
--
-- Chassis Information Group
--
-------------------------------------------------------------------------------

DellStateCapabilitiesLogUnique          ::= INTEGER {
    unknown(1),                         -- The objects capabilities are unknown
    -- The objects capabilities allow it to be set to:
    onlineCapable(2),                   -- be disabled (offline) or be enabled (online)
    notReadyCapable(4),                 -- not ready
    resetCapable(8)                     -- reset
}
DellStateSettingsLogUnique              ::= INTEGER {
    unknown(1),                         -- The objects settings are unknown
    -- The objects settings are:
    online(2),                          -- disabled (offline) or enabled (online)
    notReady(4),                        -- not ready
    reset(8)                            -- reset
}
DellLogFormat                           ::= INTEGER {
    raw(1),                             -- post Log written in RAW format
    ascii(2),                           -- post Log written in ASCII format
    uniCode(3)                          -- post Log written in UniCode format
}

-------------------------------------------------------------------------------
-- Chassis Information Table
-------------------------------------------------------------------------------

DellChassisType                 ::= INTEGER {
    other(1),                   -- the type of the chassis is not one of the object's listed
    unknown(2),                 -- the type of the chassis is unknown
    desktop(3),                 -- the type of the chassis is a desktop
    lowProfileDesktop(4),       -- the type of the chassis is a low profile desktop
    pizzaBox(5),                -- the type of the chassis is a pizza box
    miniTower(6),               -- the type of the chassis is a minitower
    tower(7),                   -- the type of the chassis is a tower
    portable(8),                -- the type of the chassis is a portable
    lapTop(9),                  -- the type of the chassis is a laptop
    noteBook(10),               -- the type of the chassis is a notebook
    handHeld(11),               -- the type of the chassis is a handheld
    dockingStation(12),         -- the type of the chassis is a docking station
    allInOne(13),               -- the type of the chassis is an all in one
    subNoteBook(14),            -- the type of the chassis is a subNotebook
    spaceSaving(15),            -- the type of the chassis is a spacesaver
    lunchBox(16),               -- the type of the chassis is a lunchbox
    mainSystemChassis(17),      -- the type of the chassis is the main system chassis
    expansionChassis(18),       -- the type of the chassis is an expansion chassis
    subChassis(19),             -- the type of the chassis is a subChassis
    busExpansionChassis(20),    -- the type of the chassis is a bus expansion chassis
    peripheralChassis(21),      -- the type of the chassis is a peripheral chassis
    raidChassis(22),            -- the type of the chassis is a disk RAID chassis
    rackMountChassis(23),       -- the type of the chassis is a rackmounted chassis
    sealedCasePC(24),           -- the type of the chassis is a sealed-case PC
    multiSystemChassis(25)      -- the type of the chassis is a multi-system chassis
}
DellConnectionStatus            ::= INTEGER {
    unknown(2),                 -- the status of the chassis connection is unknown
    ok(3),                      -- the status of the chassis connection is OK
    failure(4)                  -- the status of the chassis connection is failure
}
DellFanControlCapabilities      ::= INTEGER {
    unknown(1),                 -- The objects capabilities are unknown
    lowSpeedCapable(2),         -- the fan can be set to low speed
    highSpeedCapable(4),        -- the fan can be set to high speed
    lowOrHighSpeedCapable(6)    -- the fan can be set to low or high speed
}
DellFanControlSettings          ::= INTEGER {
    unknown(1),                 -- The objects setting is unknown
    lowSpeed(2),                -- set fan to low speed
    highSpeed(4)                -- set fan to high speed
}
DellLEDControlCapabilities             ::= INTEGER {
    unknown(1),                        -- The objects capabilities are unknown
    alertOnErrorCapable(2),            -- LED control can be set to alert on an error condition
    alertOnWarningAndErrorCapable(4),  -- LED control can be set to alert on an error or a warning condition
    alertOnWarningOrErrorCapable(6)    -- LED control can be set to alert on an error or a warning condition
}
DellLEDControlSettings          ::= INTEGER {
    unknown(1),                 -- The objects setting is unknown
    alertOnError(2),            -- set the LED control to alert on an error condition
    alertOnWarningAndError(4)   -- set the LED control to alert on an error or a warning condition
}
DellHDFaultLEDControlCapabilities ::= INTEGER {
    -- If set to 0 (zero) the object has no capabilities
    unknownCapabilities(1),       -- The objects capabilities are unknown
    -- The objects capabilities allow it to be set to:
    enableCapable(2),             -- be disabled (offline) or be enabled (online)
    notReadyCapable(4),           -- not ready
    resetCapable(8)               -- Hard Disk Fault LED can be reset
}
DellHDFaultLEDControlSettings     ::= INTEGER {
    -- If set to 0 (zero) the object has no settings capabilities
    unknown(1),             -- The objects state is unknown
    enabled(2),             -- The objects state is disabled (offline) 0, or enabled (online) 1
    notReady(4),            -- The objects state is not ready
    reset(8),               -- Reset the Hard Disk Fault LED
    resetAndEnable(10)      -- Reset and enable the Hard Disk Fault LED
}
DellChassisIdentifyControlCapabilities ::= INTEGER {
    -- If set to 0 (zero) the object has no capabilities
    unknownCapabilities(1),       -- The objects capabilities are unknown
    -- The objects capabilities allow it to be set to:
    enableCapable(2),             -- be disabled (offline) or be enabled (online)
    notReadyCapable(4),           -- not ready
    identifyCapable(8)            -- Chassis LED can be made to identify the chassis
}
DellChassisIdentifyControlSettings     ::= INTEGER {
    -- If set to 0 (zero) the object has no settings capabilities
    unknown(1),             -- The objects state is unknown
    enabled(2),             -- The objects state is disabled (offline) 0, or enabled (online) 1
    notReady(4),            -- The objects state is not ready
    identifyChassis(8),     -- The objects LED's may be returned to normal 0, or identify chassis 1
    identifyChassisAndEnable(10)  -- The objects LED's may be returned to normal 0, or identify chassis 1 and enabled
}
DellHostControlCapabilities                           ::= INTEGER {
    manualRebootCapable(1),                           -- Reboot Capable host
    manualPowerOFFCapable(2),                         -- Power OFF Capable host
    manualPowerCycleCapable(4),                       -- Power cycleable Capable host
    manualAllExceptOperatingSystemShutdownCapable(7), -- Reboot AND Power OFF AND Power cycleable Capable host
    manualOperatingSystemShutdownCapable(8),          -- Operating System shutdown Capable host
    manualFullyCapable(15)                            -- Reboot AND Power OFF AND Power cycleable AND Operating System shutdown Capable host
}
DellHostControlSettings                               ::= INTEGER {
    manualReboot(1),                                  -- Reboot the host
    manualPowerOFF(2),                                -- Power OFF the host
    manualPowerCycle(4),                              -- Power cycle the host
    manualOperatingSystemShutdown(8),                 -- Shutdown the Operating System on the host
    manualOperatingSystemShutdownThenReboot(9),       -- Shutdown the Operating System on the host then reboot
    manualOperatingSystemShutdownThenPowerOFF(10),    -- Shutdown the Operating System on the host then power off machine
    manualOperatingSystemShutdownThenPowerCycle(12)   -- Shutdown the Operating System on the host then power cycle machine
}
DellWatchDogControlCapabilities                ::= INTEGER {
    automaticRebootCapable(1),                 -- Reboot Capable host
    automaticPowerCycleCapable(2),             -- Power cycleable Capable host
    automaticNotificationCapable(4),           -- Notification Capable host
    automaticWatchDogTimerCapable(8),          -- WatchDog timer capable
    automaticAllExceptNotificationCapable(11), -- All functions except Notification capable
    automaticFullyCapable(15)                  -- All watchdog capabilities
}
DelllWatchControlSettings                      ::= INTEGER {
    automaticRebootEnabled(1),                 -- Automatic Reboot Enabled for this host
    automaticPowerCycleEnabled(2),             -- Automatic Power cycleable Enabled for this host
    automaticNotificationEnabled(4)            -- Automatic Notification Enabled for this host
}
DellWatchDogTimerCapabilities                  ::= INTEGER {
    type1Capable(1),                           -- can time in range of 20-480 seconds
    type2Capable(2),                           -- can time in 30, 60, 120 and 480 second intervals
    type3Capable(4)                            -- can time in 60 second intervals
}
DellPowerButtonControlCapabilities             ::= INTEGER {
    -- If set to 0 (zero) the object has no capabilities
    unknownCapabilities(1),                    -- The objects capabilities are unknown
    -- The objects capabilities allow it to be set to:
    enableCapable(2)                           -- be disabled (offline) or be enabled (online)
}
DellPowerButtonControlSettings                 ::= INTEGER {
    -- If set to 0 (zero) the object has no settings capabilities
    unknown(1),                                -- The objects state is unknown
    enabled(2),                                -- The objects state is enabled (online)
    disabled(4)                                -- The objects state is disabled (offline)
}
DellChassisSystemClass                         ::= INTEGER {
    other(1),                                  -- the chassis system class is not one of the following
    unknown(2),                                -- the chassis system class is unknown
    workstationClass(3),                       -- the chassis system class is a workstation
    serverClass(4),                            -- the chassis system class is a server
    desktopClass(5),                           -- the chassis system class is a desktop
    portableClass(6),                          -- the chassis system class is a portable
    netPCClass(7),                             -- the chassis system class is a NET PC
    storageClass(8)                            -- the chassis system class is storage
}

ChassisInformationTableEntry                        ::= SEQUENCE {
    chassisIndexChassisInformation                  DellObjectRange,
    chassisStateCapabilities                        DellStateCapabilities,
    chassisStateSettings                            DellStateSettings,
    chassisStatus                                   DellStatus,
    chassisparentIndexReference                     DellObjectRange,
    chassisType                                     DellChassisType,
    chassisName                                     DellString,
    chassisManufacturerName                         DellString,
    chassisModelName                                DellString,
    chassisAssetTagName                             DisplayString (SIZE (0..10)),
    chassisServiceTagName                           DisplayString (SIZE (0..7)),
    chassisID                                       DellUnsigned8BitRange,
    chassisIDExtension                              DellUnsigned16BitRange,
    chassisSystemClass                              DellChassisSystemClass,
    chassisSystemName                               DellString,
    chassisSystemBootDateName                       DellDateName,
    chassisSystemDateName                           DellDateName,
    chassisSystemLocationName                       DellString,
    chassisSystemPrimaryUserName                    DellString,
    chassisSystemUserPhoneNumberName                DellString,
    chassisConnectionStatusUnique                   DellConnectionStatus,
    chassisFanControlCapabilitiesUnique             DellFanControlCapabilities,
    chassisFanControlSettingsUnique                 DellFanControlSettings,
    chassisLEDControlCapabilitiesUnique             DellLEDControlCapabilities,
    chassisLEDControlSettingsUnique                 DellLEDControlSettings,
    chassisHDFaultClearControlCapabilities          DellHDFaultLEDControlCapabilities,
    chassisHDFaultClearControlSettings              DellHDFaultLEDControlSettings,
    chassisIdentifyFlashControlCapabilities         DellChassisIdentifyControlCapabilities,
    chassisIdentifyFlashControlSettings             DellChassisIdentifyControlSettings,
    chassisLockPresent                              DellBoolean,
    chassishostControlCapabilitiesUnique            DellHostControlCapabilities,
    chassishostControlSettingsUnique                DellHostControlSettings,
    chassiswatchDogControlCapabilitiesUnique        DellWatchDogControlCapabilities,
    chassiswatchDogControlSettingsUnique            DelllWatchControlSettings,
    chassiswatchDogControlExpiryTimeCapabilitiesUnique  DellWatchDogTimerCapabilities,
    chassiswatchDogControlExpiryTime                    DellUnsigned16BitRange,
    chassisallowSETCommandsfromSNMP                 DellBoolean,
    chassisPowerButtonControlCapabilitiesUnique     DellPowerButtonControlCapabilities,
    chassisPowerButtonControlSettingsUnique         DellPowerButtonControlSettings,
    chassisResellerName                             DisplayString (SIZE (0..128)),
    chassisResellerContactInformationName           DisplayString (SIZE (0..128)),
    chassisResellerProductName                      DisplayString (SIZE (0..128)),
    chassisResellerSystemID                         DellUnsigned16BitRange
}

chassisInformationTable                         OBJECT-TYPE
    SYNTAX      SEQUENCE OF ChassisInformationTableEntry
    ACCESS      not-accessible
    STATUS      mandatory
    DESCRIPTION
"0300.0010 This Group defines the Dell Chassis Table."
    ::= { chassisInformationGroup 10 }
chassisInformationTableEntry                    OBJECT-TYPE
    SYNTAX      ChassisInformationTableEntry
    ACCESS      not-accessible
    STATUS      mandatory
    DESCRIPTION
"0300.0010.0001 This Group defines the Dell Chassis Table Entry."
    INDEX       { chassisIndexChassisInformation }
    ::= { chassisInformationTable 1 }
chassisIndexChassisInformation                  OBJECT-TYPE
    SYNTAX      DellObjectRange
    ACCESS      read-only
    STATUS      mandatory
    DESCRIPTION
"0300.0010.0001.0001 This attribute defines the index (one based) of
this Dell chassis."
    ::= { chassisInformationTableEntry 1 }
chassisStateCapabilities                        OBJECT-TYPE
    SYNTAX      DellStateCapabilities
    ACCESS      read-only
    STATUS      mandatory
    DESCRIPTION
"0300.0010.0001.0002 This attribute defines the capabilities of the
Dell chassis."
    ::= { chassisInformationTableEntry 2 }
chassisStateSettings                            OBJECT-TYPE
    SYNTAX      DellStateSettings
    ACCESS      read-write
    STATUS      mandatory
    DESCRIPTION
"0300.0010.0001.0003 This attribute defines the state of this Dell
chassis."
    ::= { chassisInformationTableEntry 3 }
chassisStatus                                   OBJECT-TYPE
    SYNTAX      DellStatus
    ACCESS      read-only
    STATUS      mandatory
    DESCRIPTION
"0300.0010.0001.0004 This attribute defines the status of the
Dell chassis."
    ::= { chassisInformationTableEntry 4 }
chassisparentIndexReference                     OBJECT-TYPE
    SYNTAX      DellObjectRange
    ACCESS      read-only
    STATUS      mandatory
    DESCRIPTION
"0300.0010.0001.0005 This attribute defines the index (one based) to the
parent Dell chassis of this chassis, if any."
    ::= { chassisInformationTableEntry 5 }
chassisType                                     OBJECT-TYPE
    SYNTAX      DellChassisType
    ACCESS      read-only
    STATUS      mandatory
    DESCRIPTION
"0300.0010.0001.0006 This attribute defines the chassis type of the
Dell chassis."
    ::= { chassisInformationTableEntry 6 }
chassisName                                     OBJECT-TYPE
    SYNTAX      DellString
    ACCESS      read-write
    STATUS      mandatory
    DESCRIPTION
"0300.0010.0001.0007 This attribute defines the user assigned chassis
name of the Dell chassis."
    ::= { chassisInformationTableEntry 7 }
chassisManufacturerName                         OBJECT-TYPE
    SYNTAX      DellString
    ACCESS      read-only
    STATUS      mandatory
    DESCRIPTION
"0300.0010.0001.0008 This attribute defines the manufacturer's name
of the Dell chassis."
    ::= { chassisInformationTableEntry 8 }
chassisModelName                                OBJECT-TYPE
    SYNTAX      DellString
    ACCESS      read-only
    STATUS      mandatory
    DESCRIPTION
"0300.0010.0001.0009 This attribute defines the system model type
of the Dell chassis."
    ::= { chassisInformationTableEntry 9 }
chassisAssetTagName                             OBJECT-TYPE
    SYNTAX      DisplayString (SIZE (0..10))
    ACCESS      read-write
    STATUS      mandatory
    DESCRIPTION
"0300.0010.0001.0010 This attribute defines the asset tag name of the
Dell chassis."
    ::= { chassisInformationTableEntry 10 }
chassisServiceTagName                           OBJECT-TYPE
    SYNTAX      DisplayString (SIZE (0..7))
    ACCESS      read-only
    STATUS      mandatory
    DESCRIPTION
"0300.0010.0001.0011 This attribute defines the service tag name of the
Dell chassis."
    ::= { chassisInformationTableEntry 11 }
chassisID                                       OBJECT-TYPE
    SYNTAX      DellUnsigned8BitRange
    ACCESS      read-only
    STATUS      mandatory
    DESCRIPTION
"0300.0010.0001.0012 This attribute defines the BIOS Machine ID of the
Dell chassis."
    ::= { chassisInformationTableEntry 12 }
chassisIDExtension                              OBJECT-TYPE
    SYNTAX      DellUnsigned16BitRange
    ACCESS      read-only
    STATUS      mandatory
    DESCRIPTION
"0300.0010.0001.0013 This attribute defines the SMBIOS Machine ID of the
Dell chassis."
    ::= { chassisInformationTableEntry 13 }
chassisSystemClass                              OBJECT-TYPE
    SYNTAX      DellChassisSystemClass
    ACCESS      read-only
    STATUS      mandatory
    DESCRIPTION
"0300.0010.0001.0014 This attribute defines the chassis class of the
Dell chassis."
    ::= { chassisInformationTableEntry 14 }
chassisSystemName                               OBJECT-TYPE
    SYNTAX      DellString
    ACCESS      read-only
    STATUS      mandatory
    DESCRIPTION
"0300.0010.0001.0015 This attribute defines system name of the Dell System."
    ::= { chassisInformationTableEntry 15 }
chassisSystemBootDateName                       OBJECT-TYPE
    SYNTAX      DellDateName
    ACCESS      read-only
    STATUS      mandatory
    DESCRIPTION
"0300.0010.0001.0016 This attribute defines boot time of the Dell System.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { chassisInformationTableEntry 16 }
chassisSystemDateName                           OBJECT-TYPE
    SYNTAX      DellDateName
    ACCESS      read-only
    STATUS      mandatory
    DESCRIPTION
"0300.0010.0001.0017 This attribute defines the current time of the
Dell System.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { chassisInformationTableEntry 17 }
chassisSystemLocationName                       OBJECT-TYPE
    SYNTAX      DellString
    ACCESS      read-write
    STATUS      mandatory
    DESCRIPTION
"0300.0010.0001.0018 This attribute defines the location of the Dell System."
    ::= { chassisInformationTableEntry 18 }
chassisSystemPrimaryUserName                    OBJECT-TYPE
    SYNTAX      DellString
    ACCESS      read-write
    STATUS      mandatory
    DESCRIPTION
"0300.0010.0001.0019 This attribute defines the name of the primary user
of the Dell System."
    ::= { chassisInformationTableEntry 19 }
chassisSystemUserPhoneNumberName                OBJECT-TYPE
    SYNTAX      DellString
    ACCESS      read-write
    STATUS      mandatory
    DESCRIPTION
"0300.0010.0001.0020 This attribute defines the phone number of the primary
user of the Dell System."
    ::= { chassisInformationTableEntry 20 }
chassisConnectionStatusUnique                   OBJECT-TYPE
    SYNTAX      DellConnectionStatus
    ACCESS      read-only
    STATUS      mandatory
    DESCRIPTION
"0300.0010.0001.0021 This attribute defines the status of the connection
of the Dell chassis."
    ::= { chassisInformationTableEntry 21 }
chassisFanControlCapabilitiesUnique             OBJECT-TYPE
    SYNTAX      DellFanControlCapabilities
    ACCESS      read-only
    STATUS      mandatory
    DESCRIPTION
"0300.0010.0001.0022 This attribute defines the capabilities of the
fan control function in the Dell chassis."
    ::= { chassisInformationTableEntry 22 }
chassisFanControlSettingsUnique                 OBJECT-TYPE
    SYNTAX      DellFanControlSettings
    ACCESS      read-write
    STATUS      mandatory
    DESCRIPTION
"0300.0010.0001.0023 This attribute defines the reading and setting of
the fan control hardware in the Dell chassis."
    ::= { chassisInformationTableEntry 23 }
chassisLEDControlCapabilitiesUnique             OBJECT-TYPE
    SYNTAX      DellLEDControlCapabilities
    ACCESS      read-only
    STATUS      mandatory
    DESCRIPTION
"0300.0010.0001.0024 This attribute defines the capabilities of the
LED control function in the Dell chassis."
    ::= { chassisInformationTableEntry 24 }
chassisLEDControlSettingsUnique                 OBJECT-TYPE
    SYNTAX      DellLEDControlSettings
    ACCESS      read-write
    STATUS      mandatory
    DESCRIPTION

"0300.0010.0001.0025 This attribute defines the reading and setting of
the LED control hardware in the Dell chassis."
    ::= { chassisInformationTableEntry 25 }
chassisHDFaultClearControlCapabilities          OBJECT-TYPE
    SYNTAX      DellHDFaultLEDControlCapabilities
    ACCESS      read-only
    STATUS      mandatory
    DESCRIPTION
"0300.0010.0001.0026 This attribute defines if the chassis allows reset
of the chassis hard disk drive fault LED."
    ::= { chassisInformationTableEntry 26 }
chassisHDFaultClearControlSettings              OBJECT-TYPE
    SYNTAX      DellHDFaultLEDControlSettings
    ACCESS      read-write
    STATUS      mandatory
    DESCRIPTION
"0300.0010.0001.0027 This attribute allows reset of a chassis hard disk
drive fault LED."
    ::= { chassisInformationTableEntry 27 }
chassisIdentifyFlashControlCapabilities         OBJECT-TYPE
    SYNTAX      DellChassisIdentifyControlCapabilities
    ACCESS      read-only
    STATUS      mandatory
    DESCRIPTION
"0300.0010.0001.0028 This attribute defines if the chassis allows setting
of the chassis front panel LED's to flash."
    ::= { chassisInformationTableEntry 28 }
chassisIdentifyFlashControlSettings             OBJECT-TYPE
    SYNTAX      DellChassisIdentifyControlSettings
    ACCESS      read-write
    STATUS      mandatory
    DESCRIPTION
"0300.0010.0001.0029 This attribute setting causes the chassis front panel
LED's to flash."
    ::= { chassisInformationTableEntry 29 }
chassisLockPresent                              OBJECT-TYPE
    SYNTAX      DellBoolean
    ACCESS      read-only
    STATUS      mandatory
    DESCRIPTION
"0300.0010.0001.0030 If true, a chassis lock is present on the chassis."
    ::= { chassisInformationTableEntry 30 }
chassishostControlCapabilitiesUnique            OBJECT-TYPE
    SYNTAX      DellHostControlCapabilities
    ACCESS      read-only
    STATUS      mandatory
    DESCRIPTION
"0300.0010.0001.031 This attribute defines the capabilities of the Dell
Host Control object."
    ::= { chassisInformationTableEntry 31 }
chassishostControlSettingsUnique                OBJECT-TYPE
    SYNTAX      DellHostControlSettings
    ACCESS      read-write
    STATUS      mandatory
    DESCRIPTION
"0300.0010.0001.0032 This attribute defines the current settings of the
Dell Host Control object."
    ::= { chassisInformationTableEntry 32 }
chassiswatchDogControlCapabilitiesUnique        OBJECT-TYPE
    SYNTAX      DellWatchDogControlCapabilities
    ACCESS      read-only
    STATUS      mandatory
    DESCRIPTION
"0300.0010.0001.0033 This attribute defines the capabilities of the Dell
Watch Dog Timer object."
    ::= { chassisInformationTableEntry 33 }
chassiswatchDogControlSettingsUnique            OBJECT-TYPE
    SYNTAX      DelllWatchControlSettings
    ACCESS      read-write
    STATUS      mandatory
    DESCRIPTION
"0300.0010.0001.0034 This attribute defines the current settings of the
Dell Watch Dog Timer object."
    ::= { chassisInformationTableEntry 34 }
chassiswatchDogControlExpiryTimeCapabilitiesUnique   OBJECT-TYPE
    SYNTAX      DellWatchDogTimerCapabilities
    ACCESS      read-only
    STATUS      mandatory
    DESCRIPTION
"0300.0010.0001.0035 This attribute defines the capabilities of the Dell
Watch Dog Expiry Timer object."
    ::= { chassisInformationTableEntry 35 }
chassiswatchDogControlExpiryTime                OBJECT-TYPE
    SYNTAX      DellUnsigned16BitRange
    ACCESS      read-write
    STATUS      mandatory
    DESCRIPTION
"0300.0010.0001.0036 This attribute defines the current watchdog timer
value in seconds."
    ::= { chassisInformationTableEntry 36 }
chassisallowSETCommandsfromSNMP                 OBJECT-TYPE
    SYNTAX      DellBoolean
    ACCESS      read-only
    STATUS      mandatory
    DESCRIPTION
"0300.0010.0001.0037 This attribute defines if SNMP SET type commands
are allowed or not."
    ::= { chassisInformationTableEntry 37 }
chassisPowerButtonControlCapabilitiesUnique     OBJECT-TYPE
    SYNTAX      DellPowerButtonControlCapabilities
    ACCESS      read-only
    STATUS      mandatory
    DESCRIPTION
"0300.0010.0001.0038 This attribute defines the capabilities of the
power button control function in the Dell chassis."
    ::= { chassisInformationTableEntry 38 }
chassisPowerButtonControlSettingsUnique         OBJECT-TYPE
    SYNTAX      DellPowerButtonControlSettings
    ACCESS      read-write
    STATUS      mandatory
    DESCRIPTION
"0300.0010.0001.0039 This attribute defines the reading and setting of
the power button control hardware in the Dell chassis."
    ::= { chassisInformationTableEntry 39 }
chassisResellerName                             OBJECT-TYPE
    SYNTAX      DisplayString (SIZE (0..128))
    ACCESS      read-only
    STATUS      mandatory
    DESCRIPTION
"0300.0010.0001.0040 This attribute defines the name of the system reseller."
    ::= { chassisInformationTableEntry 40 }
chassisResellerContactInformationName           OBJECT-TYPE
    SYNTAX      DisplayString (SIZE (0..128))
    ACCESS      read-only
    STATUS      mandatory
    DESCRIPTION
"0300.0010.0001.0041 This attribute defines the contact information
for the system reseller."
    ::= { chassisInformationTableEntry 41 }
chassisResellerProductName                      OBJECT-TYPE
    SYNTAX      DisplayString (SIZE (0..128))
    ACCESS      read-only
    STATUS      mandatory
    DESCRIPTION
"0300.0010.0001.0042 This attribute defines the reseller's product name
for the system."
    ::= { chassisInformationTableEntry 42 }
chassisResellerSystemID                         OBJECT-TYPE
    SYNTAX      DellUnsigned16BitRange
    ACCESS      read-only
    STATUS      mandatory
    DESCRIPTION
"0300.0010.0001.0043 This attribute defines the reseller's system ID
for the system."
    ::= { chassisInformationTableEntry 43 }


-------------------------------------------------------------------------------
-- UUID (Universal Unique ID) Table
-------------------------------------------------------------------------------

DellUUIDType                        ::= INTEGER {
    other(1),                       -- UUID type is not one of the types listed
    unknown(2),                     -- UUID type is unknown
    motherBoard(3),                 -- UUID type is a Motherboard
    systemBackPlane(4),             -- UUID type is a System backplane
    powerSupplyParallelingBoard(5), -- UUID type is a Power supply paralleling board
    peripheralBayBackPlane(6),      -- UUID type is a Peripheral bay backplane
    secondaryBackPlane(7)           -- UUID type is a Secondary system backplane
}

UUIDTableEntry                      ::= SEQUENCE {
    uUIDchassisIndex                DellObjectRange,
    uUIDIndex                       DellObjectRange,
    uUIDType                        DellUUIDType,
    uUIDValue                       OCTET STRING (SIZE(16))
}

uUIDTable                           OBJECT-TYPE
    SYNTAX      SEQUENCE OF UUIDTableEntry
    ACCESS      not-accessible
    STATUS      mandatory
    DESCRIPTION
"0300.0020 This object defines the UUID (Universal Unique ID) Table."
    ::= { chassisInformationGroup 20 }
uUIDTableEntry                      OBJECT-TYPE
    SYNTAX      UUIDTableEntry
    ACCESS      not-accessible
    STATUS      mandatory
    DESCRIPTION
"0300.0020.0001 This object defines the UUID Table Entry."
    INDEX       { uUIDchassisIndex, uUIDIndex }
    ::= { uUIDTable 1 }
uUIDchassisIndex                    OBJECT-TYPE
    SYNTAX      DellObjectRange
    ACCESS      read-only
    STATUS      mandatory
    DESCRIPTION
"0300.0020.0001.0001 This attribute defines the index (one based) of the
associated chassis."
    ::= { uUIDTableEntry 1 }
uUIDIndex                           OBJECT-TYPE
    SYNTAX      DellObjectRange
    ACCESS      read-only
    STATUS      mandatory
    DESCRIPTION
"0300.0020.0001.0002 This attribute defines the index (one based) of the UUID."
    ::= { uUIDTableEntry 2 }
uUIDType                            OBJECT-TYPE
    SYNTAX      DellUUIDType
    ACCESS      read-only
    STATUS      mandatory
    DESCRIPTION
"0300.0020.0001.0003 This attribute defines the type of the UUID."
    ::= { uUIDTableEntry 3 }
uUIDValue                           OBJECT-TYPE
    SYNTAX      OCTET STRING (SIZE(16))
    ACCESS      read-only
    STATUS      mandatory
    DESCRIPTION
"0300.0020.0001.0004 This attribute defines the value of the UUID."
    ::= { uUIDTableEntry 4 }


-------------------------------------------------------------------------------
-- POST (Power On Self Test) Log Table
-------------------------------------------------------------------------------

PostLogTableEntry                   ::= SEQUENCE {
    postLogchassisIndex             DellObjectRange,
    postLogRecordIndex              DellUnsigned32BitRange,
    postLogStateCapabilitiesUnique  DellStateCapabilitiesLogUnique,
    postLogStateSettingsUnique      DellStateSettingsLogUnique,
    postLogRecord                   DisplayString (SIZE (0..1024)),
    postLogFormat                   DellLogFormat
}

postLogTable                        OBJECT-TYPE
    SYNTAX      SEQUENCE OF PostLogTableEntry
    ACCESS      not-accessible
    STATUS      mandatory
    DESCRIPTION
"0300.0030 This object defines the POST (Power On Self Test) Log Table."
    ::= { chassisInformationGroup 30 }
postLogTableEntry                   OBJECT-TYPE
    SYNTAX      PostLogTableEntry
    ACCESS      not-accessible
    STATUS      mandatory
    DESCRIPTION
"0300.0030.0001 This object defines the POST Log Table Entry."
    INDEX       { postLogchassisIndex, postLogRecordIndex }
    ::= { postLogTable 1 }
postLogchassisIndex                 OBJECT-TYPE
    SYNTAX      DellObjectRange
    ACCESS      read-only
    STATUS      mandatory
    DESCRIPTION
"0300.0030.0001.0001 This attribute defines the index (one based) of the
associated chassis."
    ::= { postLogTableEntry 1 }
postLogRecordIndex                  OBJECT-TYPE
    SYNTAX      DellUnsigned32BitRange
    ACCESS      read-only
    STATUS      mandatory
    DESCRIPTION
"0300.0030.0001.0002 This attribute defines the index (one based) of the
POST log record."
    ::= { postLogTableEntry 2 }
postLogStateCapabilitiesUnique      OBJECT-TYPE
    SYNTAX      DellStateCapabilitiesLogUnique
    ACCESS      read-only
    STATUS      mandatory
    DESCRIPTION
"0300.0030.0001.0003 This attribute defines the state capabilities of the
object that is writing the POST log."
    ::= { postLogTableEntry 3 }
postLogStateSettingsUnique          OBJECT-TYPE
    SYNTAX      DellStateSettingsLogUnique
    ACCESS      read-write
    STATUS      mandatory
    DESCRIPTION
"0300.0030.0001.0004 This attribute defines the state settings of the
object that is writing the POST log."
    ::= { postLogTableEntry 4 }
postLogRecord                       OBJECT-TYPE
    SYNTAX       DisplayString (SIZE (0..1024))
    ACCESS      read-only
    STATUS      mandatory
    DESCRIPTION
"0300.0030.0001.0005 This attribute defines the data of the POST log record."
    ::= { postLogTableEntry 5 }
postLogFormat                       OBJECT-TYPE
    SYNTAX      DellLogFormat
    ACCESS      read-only
    STATUS      mandatory
    DESCRIPTION
"0300.0030.0001.0006 This attribute defines the format of the POST log record."
    ::= { postLogTableEntry 6 }


-------------------------------------------------------------------------------
-- (ESM) Event Log Table
-------------------------------------------------------------------------------

EventLogTableEntry                  ::= SEQUENCE {
    eventLogchassisIndex            DellObjectRange,
    eventLogRecordIndex             DellUnsigned32BitRange,
    eventLogStateCapabilitiesUnique DellStateCapabilitiesLogUnique,
    eventLogStateSettingsUnique     DellStateSettingsLogUnique,
    eventLogRecord                  DisplayString (SIZE (0..1024)),
    eventLogFormat                  DellLogFormat,
    eventLogSeverityStatus          DellStatus,
    eventLogDateName                DellDateName
}

eventLogTable                       OBJECT-TYPE
    SYNTAX      SEQUENCE OF EventLogTableEntry
    ACCESS      not-accessible
    STATUS      mandatory
    DESCRIPTION
"0300.0040 This object defines the (ESM) Event Log Table."
    ::= { chassisInformationGroup 40 }
eventLogTableEntry                  OBJECT-TYPE
    SYNTAX      EventLogTableEntry
    ACCESS      not-accessible
    STATUS      mandatory
    DESCRIPTION
"0300.0040.0001 This object defines the (ESM) Event Log Table Entry."
    INDEX       { eventLogchassisIndex, eventLogRecordIndex }
    ::= { eventLogTable 1 }
eventLogchassisIndex                OBJECT-TYPE
    SYNTAX      DellObjectRange
    ACCESS      read-only
    STATUS      mandatory
    DESCRIPTION
"0300.0040.0001.0001 This attribute defines the index (one based) of the
associated chassis."
    ::= { eventLogTableEntry 1 }
eventLogRecordIndex                 OBJECT-TYPE
    SYNTAX      DellUnsigned32BitRange
    ACCESS      read-only
    STATUS      mandatory
    DESCRIPTION
"0300.0040.0001.0002 This attribute defines the index (one based) of the
event log record."
    ::= { eventLogTableEntry 2 }
eventLogStateCapabilitiesUnique     OBJECT-TYPE
    SYNTAX      DellStateCapabilitiesLogUnique
    ACCESS      read-only
    STATUS      mandatory
    DESCRIPTION
"0300.0040.0001.0003 This attribute defines the state capabilities of the
object that is writing the event log."
    ::= { eventLogTableEntry 3 }
eventLogStateSettingsUnique         OBJECT-TYPE
    SYNTAX      DellStateSettingsLogUnique
    ACCESS      read-write
    STATUS      mandatory
    DESCRIPTION
"0300.0040.0001.0004 This attribute defines the state settings of the
object that is writing the event log."
    ::= { eventLogTableEntry 4 }
eventLogRecord                      OBJECT-TYPE
    SYNTAX       DisplayString (SIZE (0..1024))
    ACCESS      read-only
    STATUS      mandatory
    DESCRIPTION
"0300.0040.0001.0005 This attribute defines the data of the event log record."
    ::= { eventLogTableEntry 5 }
eventLogFormat                      OBJECT-TYPE
    SYNTAX      DellLogFormat
    ACCESS      read-only
    STATUS      mandatory
    DESCRIPTION
"0300.0040.0001.0006 This attribute defines the format of the event log record."
    ::= { eventLogTableEntry 6 }
eventLogSeverityStatus              OBJECT-TYPE
    SYNTAX      DellStatus
    ACCESS      read-only
    STATUS      mandatory
    DESCRIPTION
"0300.0040.0001.0007 This attribute defines the severity of the
event log record."
    ::= { eventLogTableEntry 7 }
eventLogDateName                    OBJECT-TYPE
    SYNTAX      DellDateName
    ACCESS      read-only
    STATUS      mandatory
    DESCRIPTION
"0300.0040.0001.0008 This attribute defines the date and time of the
event log record."
    ::= { eventLogTableEntry 8 }


-------------------------------------------------------------------------------
-- System BIOS Table
-------------------------------------------------------------------------------

SystemBIOSTableEntry                ::= SEQUENCE {
    systemBIOSchassisIndex          DellObjectRange,
    systemBIOSIndex                 DellObjectRange,
    systemBIOSStateCapabilities     DellStateCapabilities,
    systemBIOSStateSettings         DellStateSettings,
    systemBIOSStatus                DellStatus,
    systemBIOSSize                  DellUnsigned32BitRange,
    systemBIOSReleaseDateName       DellDateName,
    systemBIOSVersionName           DellString,
    systemBIOSStartingAddress       DellUnsigned64BitRange,
    systemBIOSEndingAddress         DellUnsigned64BitRange,
    systemBIOSManufacturerName      DellString
}

systemBIOSTable                     OBJECT-TYPE
    SYNTAX          SEQUENCE OF SystemBIOSTableEntry
    ACCESS          not-accessible
    STATUS          mandatory
    DESCRIPTION
"0300.0050 This object defines the System BIOS Table."
    ::= { chassisInformationGroup 50 }
systemBIOSTableEntry                OBJECT-TYPE
    SYNTAX          SystemBIOSTableEntry
    ACCESS          not-accessible
    STATUS          mandatory
    DESCRIPTION
"0300.0050.0001 This object defines the System BIOS Table Entry."
    INDEX           { systemBIOSchassisIndex, systemBIOSIndex }
    ::= { systemBIOSTable 1 }
systemBIOSchassisIndex              OBJECT-TYPE
    SYNTAX      DellObjectRange
    ACCESS      read-only
    STATUS      mandatory
    DESCRIPTION
"0300.0050.0001.0001 This attribute defines the index (one based) of the
associated chassis."
    ::= { systemBIOSTableEntry 1 }
systemBIOSIndex                     OBJECT-TYPE
    SYNTAX      DellObjectRange
    ACCESS      read-only
    STATUS      mandatory
    DESCRIPTION
"0300.0050.0001.0002 This attribute defines the index (one based) of the
system BIOS."
    ::= { systemBIOSTableEntry 2 }
systemBIOSStateCapabilities         OBJECT-TYPE
    SYNTAX      DellStateCapabilities
    ACCESS      read-only
    STATUS      mandatory
    DESCRIPTION
"0300.0050.0001.0003 This attribute defines the state capabilities of the
system BIOS."
    ::= { systemBIOSTableEntry 3 }
systemBIOSStateSettings             OBJECT-TYPE
    SYNTAX      DellStateSettings
    ACCESS      read-write
    STATUS      mandatory
    DESCRIPTION
"0300.0050.0001.0004 This attribute defines the state settings of the
system BIOS."
    ::= { systemBIOSTableEntry 4 }
systemBIOSStatus                    OBJECT-TYPE
    SYNTAX      DellStatus
    ACCESS      read-only
    STATUS      mandatory
    DESCRIPTION
"0300.0050.0001.0005 This attribute defines the status of the system BIOS."
    ::= { systemBIOSTableEntry 5 }
systemBIOSSize                      OBJECT-TYPE
    SYNTAX      DellUnsigned32BitRange
    ACCESS      read-only
    STATUS      mandatory
    DESCRIPTION
"0300.0050.0001.0006 This attribute defines the image size of the
system BIOS in Kbytes.  0 (zero) indicates size is unknown."
    ::= { systemBIOSTableEntry 6 }
systemBIOSReleaseDateName           OBJECT-TYPE
    SYNTAX      DellDateName
    ACCESS      read-only
    STATUS      mandatory
    DESCRIPTION
"0300.0050.0001.0007 This attribute defines the release date name of the
system BIOS."
    ::= { systemBIOSTableEntry 7 }
systemBIOSVersionName               OBJECT-TYPE
    SYNTAX      DellString
    ACCESS      read-only
    STATUS      mandatory
    DESCRIPTION
"0300.0050.0001.0008 This attribute defines the version name of the
system BIOS."
    ::= { systemBIOSTableEntry 8 }
systemBIOSStartingAddress           OBJECT-TYPE
    SYNTAX      DellUnsigned64BitRange
    ACCESS      read-only
    STATUS      mandatory
    DESCRIPTION
"0300.0050.0001.0009 This attribute defines the starting address of the
system BIOS.  0 (zero) indicates the starting address is unknown."
    ::= { systemBIOSTableEntry 9 }
systemBIOSEndingAddress             OBJECT-TYPE
    SYNTAX      DellUnsigned64BitRange
    ACCESS      read-only
    STATUS      mandatory
    DESCRIPTION
"0300.0050.0001.0010 This attribute defines the ending address of the
system BIOS.  0 (zero) indicates the starting address is unknown."
    ::= { systemBIOSTableEntry 10 }
systemBIOSManufacturerName          OBJECT-TYPE
    SYNTAX      DellString
    ACCESS      read-only
    STATUS      mandatory
    DESCRIPTION
"0300.0050.0001.0011 This attribute defines the manufacturer's name of the
system BIOS."
    ::= { systemBIOSTableEntry 11 }


-------------------------------------------------------------------------------
-- Firmware Table
-------------------------------------------------------------------------------

DellFirwareType                            ::= INTEGER {
    other(1),                              -- unspecified type
    unknown(2),                            -- unknown type
    systemBOIS(3),                         -- system bios
    embeddedSystemManagementController(4), -- Embedded system management controller
    powerSupplyParallelingBoard(5),        -- Power supply paralleling board
    systemBackPlane(6),                    -- Main System backplane
    hendrixKernel(7),                      -- Hendrix (PV20x) kernel
    hendrixApplication(8),                 -- Hendrix (PV20x) application
    frontPanel(9),                         -- Front panel controller
    baseboardManagementController(10),     -- Baseboard Management Controller
    hotPlugPCI(11),                        -- Hot Plug PCI Controller
    sensorData(12),                        -- Sensor Data Records
    peripheralBay(13),                     -- Peripheral bay backplane
    secondaryBackPlane(14)                 -- Secondary system backplane
}

FirmwareTableEntry                  ::= SEQUENCE {
    firmwarechassisIndex            DellObjectRange,
    firmwareIndex                   DellObjectRange,
    firmwareStateCapabilities       DellStateCapabilities,
    firmwareStateSettings           DellStateSettings,
    firmwareStatus                  DellStatus,
    firmwareSize                    DellUnsigned16BitRange,
    firmwareType                    DellFirwareType,
    firmwareTypeName                DellString,
    firmwareUpdateCapabilities      DellUnsigned16BitRange,
    firmwareDateName                OCTET STRING (SIZE(8)),
    firmwareVersionName             DellString
}

firmwareTable                       OBJECT-TYPE
    SYNTAX          SEQUENCE OF FirmwareTableEntry
    ACCESS          not-accessible
    STATUS          mandatory
    DESCRIPTION
"0300.0060 This object defines the Firmware Table."
    ::= { chassisInformationGroup 60 }
firmwareTableEntry                  OBJECT-TYPE
    SYNTAX          FirmwareTableEntry
    ACCESS          not-accessible
    STATUS          mandatory
    DESCRIPTION
"0300.0060.0001 This object defines the Firmware Table Entry."
    INDEX           { firmwarechassisIndex, firmwareIndex }
    ::= { firmwareTable 1 }
firmwarechassisIndex                OBJECT-TYPE
    SYNTAX      DellObjectRange
    ACCESS      read-only
    STATUS      mandatory
    DESCRIPTION
"0300.0060.0001.0001 This attribute defines the index (one based) of the
associated chassis."
    ::= { firmwareTableEntry 1 }
firmwareIndex                       OBJECT-TYPE
    SYNTAX      DellObjectRange
    ACCESS      read-only
    STATUS      mandatory
    DESCRIPTION
"0300.0060.0001.0002 This attribute defines the index (one based) of the
firmware."
    ::= { firmwareTableEntry 2 }
firmwareStateCapabilities           OBJECT-TYPE
    SYNTAX      DellStateCapabilities
    ACCESS      read-only
    STATUS      mandatory
    DESCRIPTION
"0300.0060.0001.0003 This attribute defines the state capabilities of the
firmware."
    ::= { firmwareTableEntry 3 }
firmwareStateSettings               OBJECT-TYPE
    SYNTAX      DellStateSettings
    ACCESS      read-write
    STATUS      mandatory
    DESCRIPTION
"0300.0060.0001.0004 This attribute defines the state settings of the
firmware."
    ::= { firmwareTableEntry 4 }
firmwareStatus                      OBJECT-TYPE
    SYNTAX      DellStatus
    ACCESS      read-only
    STATUS      mandatory
    DESCRIPTION
"0300.0060.0001.0005 This attribute defines the status of the firmware."
    ::= { firmwareTableEntry 5 }
firmwareSize                        OBJECT-TYPE
    SYNTAX      DellUnsigned16BitRange
    ACCESS      read-only
    STATUS      mandatory
    DESCRIPTION
"0300.0060.0001.0006 This attribute defines the image size of the firmware
in Kbytes.  0 (zero) indicates size unknown."
    ::= { firmwareTableEntry 6 }
firmwareType                        OBJECT-TYPE
    SYNTAX      DellFirwareType
    ACCESS      read-only
    STATUS      mandatory
    DESCRIPTION
"0300.0060.0001.0007 This attribute defines the type of firmware."
    ::= { firmwareTableEntry 7 }
firmwareTypeName                    OBJECT-TYPE
    SYNTAX      DellString
    ACCESS      read-only
    STATUS      mandatory
    DESCRIPTION
"0300.0060.0001.0008 This attribute defines the type name of the firmware."
    ::= { firmwareTableEntry 8 }
firmwareUpdateCapabilities          OBJECT-TYPE
    SYNTAX      DellUnsigned16BitRange
    ACCESS      read-only
    STATUS      mandatory
    DESCRIPTION
"0300.0060.0001.0009 This attribute defines the bitmap of supported methods
for firmware update."
    ::= { firmwareTableEntry 9 }
firmwareDateName                    OBJECT-TYPE
    SYNTAX      OCTET STRING (SIZE(8))
    ACCESS      read-only
    STATUS      mandatory
    DESCRIPTION
"0300.0060.0001.0010 This attribute defines the date name of the firmware."
    ::= { firmwareTableEntry 10 }
firmwareVersionName                 OBJECT-TYPE
    SYNTAX      DellString
    ACCESS      read-only
    STATUS      mandatory
    DESCRIPTION
"0300.0060.0001.0011 This attribute defines the version name of the firmware."
    ::= { firmwareTableEntry 11 }


-------------------------------------------------------------------------------
-- Intrusion Table
-------------------------------------------------------------------------------

DellIntrusionReading                ::= INTEGER {
    chassisNotBreached(1),          -- Chassis not breached and no uncleared breaches
    chassisBreached(2),             -- Chassis currently has a breach
    chassisBreachedPrior(3),        -- Chassis was breached prior to boot and has not been cleared
    chassisBreachSensorFailure(4)   -- Chassis inrusion sensor has failed
}
DellIntrusionType                           ::= INTEGER {
    chassisBreachDetectionWhenPowerON(1),   -- Detects intrusion while power on
    chassisBreachDetectionWhenPowerOFF(2)   -- Detects intrusion while power off
}

IntrusionTableEntry                 ::= SEQUENCE {
    intrusionchassisIndex           DellObjectRange,
    intrusionIndex                  DellObjectRange,
    intrusionStateCapabilities      DellStateCapabilities,
    intrusionStateSettings          DellStateSettings,
    intrusionStatus                 DellStatus,
    intrusionReading                DellIntrusionReading,
    intrusionType                   DellIntrusionType,
    intrusionLocationName           DellString
}

intrusionTable                      OBJECT-TYPE
    SYNTAX      SEQUENCE OF IntrusionTableEntry
    ACCESS      not-accessible
    STATUS      mandatory
    DESCRIPTION
"0300.0070 This object defines the Intrusion Table."
    ::= { chassisInformationGroup 70 }
intrusionTableEntry                 OBJECT-TYPE
    SYNTAX      IntrusionTableEntry
    ACCESS      not-accessible
    STATUS      mandatory
    DESCRIPTION
"0300.0070.0001 This object defines the Intrusion Table Entry."
    INDEX       { intrusionchassisIndex, intrusionIndex }
    ::= { intrusionTable 1 }
intrusionchassisIndex               OBJECT-TYPE
    SYNTAX      DellObjectRange
    ACCESS      read-only
    STATUS      mandatory
    DESCRIPTION
"0300.0070.0001.0001 This attribute defines the index (one based) of the
associated chassis."
    ::= { intrusionTableEntry 1 }
intrusionIndex                      OBJECT-TYPE
    SYNTAX      DellObjectRange
    ACCESS      read-only
    STATUS      mandatory
    DESCRIPTION
"0300.0070.0001.0002 This attribute defines the index (one based) of the
intrusion object."
    ::= { intrusionTableEntry 2 }
intrusionStateCapabilities          OBJECT-TYPE
    SYNTAX      DellStateCapabilities
    ACCESS      read-only
    STATUS      mandatory
    DESCRIPTION
"0300.0070.0001.0003 This attribute defines the state capabilities of the
intrusion object."
    ::= { intrusionTableEntry 3 }
intrusionStateSettings              OBJECT-TYPE
    SYNTAX      DellStateSettings
    ACCESS      read-write
    STATUS      mandatory
    DESCRIPTION
"0300.0070.0001.0004 This attribute defines the state settings of the
intrusion object."
    ::= { intrusionTableEntry 4 }
intrusionStatus                     OBJECT-TYPE
    SYNTAX      DellStatus
    ACCESS      read-only
    STATUS      mandatory
    DESCRIPTION
"0300.0070.0001.0005 This attribute defines the status of the
intrusion object."
    ::= { intrusionTableEntry 5 }
intrusionReading                    OBJECT-TYPE
    SYNTAX      DellIntrusionReading
    ACCESS      read-only
    STATUS      mandatory
    DESCRIPTION
"0300.0070.0001.0006 This attribute defines the reading of the
intrusion object."
    ::= { intrusionTableEntry 6 }
intrusionType                       OBJECT-TYPE
    SYNTAX      DellIntrusionType
    ACCESS      read-only
    STATUS      mandatory
    DESCRIPTION
"0300.0070.0001.0007 This attribute defines the type of the
intrusion object."
    ::= { intrusionTableEntry 7 }
intrusionLocationName               OBJECT-TYPE
    SYNTAX      DellString
    ACCESS      read-only
    STATUS      mandatory
    DESCRIPTION
"0300.0070.0001.0008 This attribute defines the location name of the
intrusion object."
    ::= { intrusionTableEntry 8 }


-------------------------------------------------------------------------------
-- Base Board Table
-------------------------------------------------------------------------------

DellBaseBoardType                   ::= INTEGER {
    unknown(1),                     -- board type is unknown
    other(2),                       -- board type is not one of the following types
    serverBlade(3),                 -- board type is Server Blade
    connectivitySwitch(4),          -- board type is Connectivity Switch
    systemManagementModule(5),      -- board type is System Management Module
    processorModule(6),             -- board type is Processor Module
    ioModule(7),                    -- board type is I/O Module
    memoryModule(8),                -- board type is Memory Module
    daughterBoard(9),               -- board type is Daughter Board
    motherboard(10),                -- board type is Motherboard
    processorMemoryModule(11),      -- board type is Processor/Memory Module
    processorIOModule(12),          -- board type is Processor/IO Module
    interconnectBoard(13)           -- board type is Interconnect Board
}
DellBaseBoardFeatureFlags           ::= INTEGER {
    -- If set to 0 (zero), the board has no features.
    -- Note: These values are bit fields, so combination values are possible.
    boardIsHostingBoard(1),         -- board is a hosting board
    boardRequiresDaughterBoard(2),  -- board requires at least one daughter board or auxiliary card
    boardIsRemovable(4),            -- board is removable
    boardIsReplaceable(8),          -- board is replaceable
    boardIsHotSwappable(16)         -- board is hot swappable
}

BaseBoardTableEntry                 ::= SEQUENCE {
    baseBoardChassisIndex           DellObjectRange,
    baseBoardIndex                  DellObjectRange,
    baseBoardStateCapabilities      DellStateCapabilities,
    baseBoardStateSettings          DellStateSettings,
    baseBoardStatus                 DellStatus,
    baseBoardFeatureFlags           DellBaseBoardFeatureFlags,
    baseBoardType                   DellBaseBoardType,
    baseBoardTypeName               DellString,
    baseBoardLocationName           DellString,
    baseBoardManufacturerName       DellString,
    baseBoardProductName            DellString,
    baseBoardVersionName            DellString,
    baseBoardServiceTagName         DellString,
    baseBoardPiecePartIDName        DellString,
    baseBoardAssetTagName           DellString
}

baseBoardTable                      OBJECT-TYPE
    SYNTAX      SEQUENCE OF BaseBoardTableEntry
    ACCESS      not-accessible
    STATUS      mandatory
    DESCRIPTION
"0300.0080 This object defines the Base Board Table."
    ::= { chassisInformationGroup 80 }
baseBoardTableEntry                 OBJECT-TYPE
    SYNTAX      BaseBoardTableEntry
    ACCESS      not-accessible
    STATUS      mandatory
    DESCRIPTION
"0300.0080.0001 This object defines the Base Board Table Entry."
    INDEX       { baseBoardChassisIndex, baseBoardIndex }
    ::= { baseBoardTable 1 }
baseBoardChassisIndex               OBJECT-TYPE
    SYNTAX      DellObjectRange
    ACCESS      read-only
    STATUS      mandatory
    DESCRIPTION
"0300.0080.0001.0001 This attribute defines the index (one based) of the
associated chassis."
    ::= { baseBoardTableEntry 1 }
baseBoardIndex                      OBJECT-TYPE
    SYNTAX      DellObjectRange
    ACCESS      read-only
    STATUS      mandatory
    DESCRIPTION
"0300.0080.0001.0002 This attribute defines the index (one based) of the
base board."
    ::= { baseBoardTableEntry 2 }
baseBoardStateCapabilities          OBJECT-TYPE
    SYNTAX      DellStateCapabilities
    ACCESS      read-only
    STATUS      mandatory
    DESCRIPTION
"0300.0080.0001.0003 This attribute defines the state capabilities of the
base board."
    ::= { baseBoardTableEntry 3 }
baseBoardStateSettings              OBJECT-TYPE
    SYNTAX      DellStateSettings
    ACCESS      read-write
    STATUS      mandatory
    DESCRIPTION
"0300.0080.0001.0004 This attribute defines the state settings of the
base board."
    ::= { baseBoardTableEntry 4 }
baseBoardStatus                     OBJECT-TYPE
    SYNTAX      DellStatus
    ACCESS      read-only
    STATUS      mandatory
    DESCRIPTION
"0300.0080.0001.0005 This attribute defines the status of the
base board."
    ::= { baseBoardTableEntry 5 }
baseBoardFeatureFlags               OBJECT-TYPE
    SYNTAX      DellBaseBoardFeatureFlags
    ACCESS      read-only
    STATUS      mandatory
    DESCRIPTION
"0300.0080.0001.0006 This attribute defines the features of the
base board."
    ::= { baseBoardTableEntry 6 }
baseBoardType                       OBJECT-TYPE
    SYNTAX      DellBaseBoardType
    ACCESS      read-only
    STATUS      mandatory
    DESCRIPTION
"0300.0080.0001.0007 This attribute defines the type of the
base board."
    ::= { baseBoardTableEntry 7 }
baseBoardTypeName                   OBJECT-TYPE
    SYNTAX      DellString
    ACCESS      read-only
    STATUS      mandatory
    DESCRIPTION
"0300.0080.0001.0008 This attribute defines the type name of the
base board."
    ::= { baseBoardTableEntry 8 }
baseBoardLocationName               OBJECT-TYPE
    SYNTAX      DellString
    ACCESS      read-only
    STATUS      mandatory
    DESCRIPTION
"0300.0080.0001.0009 This attribute defines the location name of the
base board."
    ::= { baseBoardTableEntry 9 }
baseBoardManufacturerName           OBJECT-TYPE
    SYNTAX      DellString
    ACCESS      read-only
    STATUS      mandatory
    DESCRIPTION
"0300.0080.0001.0010 This attribute defines the manufacturer's name of the
base board."
    ::= { baseBoardTableEntry 10 }
baseBoardProductName                OBJECT-TYPE
    SYNTAX      DellString
    ACCESS      read-only
    STATUS      mandatory
    DESCRIPTION
"0300.0080.0001.0011 This attribute defines the product name of the
base board."
    ::= { baseBoardTableEntry 11 }
baseBoardVersionName                OBJECT-TYPE
    SYNTAX      DellString
    ACCESS      read-only
    STATUS      mandatory
    DESCRIPTION
"0300.0080.0001.0012 This attribute defines the version name of the
base board."
    ::= { baseBoardTableEntry 12 }
baseBoardServiceTagName             OBJECT-TYPE
    SYNTAX      DellString
    ACCESS      read-only
    STATUS      mandatory
    DESCRIPTION
"0300.0080.0001.0013 This attribute defines the service tag name of the
base board."
    ::= { baseBoardTableEntry 13 }
baseBoardPiecePartIDName            OBJECT-TYPE
    SYNTAX      DellString
    ACCESS      read-only
    STATUS      mandatory
    DESCRIPTION
"0300.0080.0001.0014 This attribute defines the Piece Part ID (PPID) name of the
base board."
    ::= { baseBoardTableEntry 14 }
baseBoardAssetTagName               OBJECT-TYPE
    SYNTAX      DellString
    ACCESS      read-only
    STATUS      mandatory
    DESCRIPTION
"0300.0080.0001.0015 This attribute defines the asset tag name of the
base board."
    ::= { baseBoardTableEntry 15 }


-------------------------------------------------------------------------------
--
-- Operating System Group
--
-------------------------------------------------------------------------------

-------------------------------------------------------------------------------
-- Operating System Table
-------------------------------------------------------------------------------

OperatingSystemTableEntry                       ::= SEQUENCE {
    operatingSystemchassisIndex                 DellObjectRange,
    operatingSystemStateCapabilities            DellStateCapabilities,
    operatingSystemStateSettings                DellStateSettings,
    operatingSystemStatus                       DellStatus,
    operatingSystemIsPrimary                    DellBoolean,
    operatingSystemOperatingSystemName          DellString,
    operatingSystemOperatingSystemVersionName   DellString
}

operatingSystemTable                            OBJECT-TYPE
    SYNTAX      SEQUENCE OF OperatingSystemTableEntry
    ACCESS      not-accessible
    STATUS      mandatory
    DESCRIPTION
"0400.0010 This Group defines the Operating System Table."
    ::= { operatingSystemGroup 10 }
operatingSystemTableEntry                       OBJECT-TYPE
    SYNTAX      OperatingSystemTableEntry
    ACCESS      not-accessible
    STATUS      mandatory
    DESCRIPTION
"0400.0010.0001 This Group defines the Operating System Table Entry."
    INDEX       { operatingSystemchassisIndex }
    ::= { operatingSystemTable 1 }
operatingSystemchassisIndex                     OBJECT-TYPE
    SYNTAX      DellObjectRange
    ACCESS      read-only
    STATUS      mandatory
    DESCRIPTION
"0400.0010.0001.0001 This attribute defines the index (one based) of
this Dell chassis."
    ::= { operatingSystemTableEntry 1 }
operatingSystemStateCapabilities                OBJECT-TYPE
    SYNTAX      DellStateCapabilities
    ACCESS      read-only
    STATUS      mandatory
    DESCRIPTION
"0400.0010.0001.0002 This attribute defines the capabilities of the
Operating System."
    ::= { operatingSystemTableEntry 2 }
operatingSystemStateSettings                    OBJECT-TYPE
    SYNTAX      DellStateSettings
    ACCESS      read-write
    STATUS      mandatory
    DESCRIPTION
"0400.0010.0001.0003 This attribute defines the state of the Operating
System."
    ::= { operatingSystemTableEntry 3 }
operatingSystemStatus                           OBJECT-TYPE
    SYNTAX      DellStatus
    ACCESS      read-only
    STATUS      mandatory
    DESCRIPTION
"0400.0010.0001.0004 This attribute defines the status of the
Operating System."
    ::= { operatingSystemTableEntry 4 }
operatingSystemIsPrimary                        OBJECT-TYPE
    SYNTAX      DellBoolean
    ACCESS      read-only
    STATUS      mandatory
    DESCRIPTION
"0400.0010.0001.0005 This attribute defines if this operating system is the
primary operating system or not."
    ::= { operatingSystemTableEntry 5 }
operatingSystemOperatingSystemName              OBJECT-TYPE
    SYNTAX      DellString
    ACCESS      read-only
    STATUS      mandatory
    DESCRIPTION
"0400.0010.0001.0006 This attribute defines the name of the Operating
System."
    ::= { operatingSystemTableEntry 6 }
operatingSystemOperatingSystemVersionName       OBJECT-TYPE
    SYNTAX      DellString
    ACCESS      read-only
    STATUS      mandatory
    DESCRIPTION
"0400.0010.0001.0007 This attribute defines the version of the Operating
System."
    ::= { operatingSystemTableEntry 7 }


-------------------------------------------------------------------------------
-- Operating System Memory Table
-------------------------------------------------------------------------------

OperatingSystemMemoryTableEntry                     ::= SEQUENCE {
    operatingSystemMemorychassisIndex               DellObjectRange,
    operatingSystemMemoryStateCapabilities          DellStateCapabilities,
    operatingSystemMemoryStateSettings              DellStateSettings,
    operatingSystemMemoryStatus                     DellStatus,
    operatingSystemMemoryTotalPhysicalSize          DellUnsigned32BitRange,
    operatingSystemMemoryAvailablePhysicalSize      DellUnsigned32BitRange,
    operatingSystemMemoryTotalPageFileSize          DellUnsigned32BitRange,
    operatingSystemMemoryAvailablePageFileSize      DellUnsigned32BitRange,
    operatingSystemMemoryTotalVirtualSize           DellUnsigned32BitRange,
    operatingSystemMemoryAvailableVirtualSize       DellUnsigned32BitRange
}

operatingSystemMemoryTable                          OBJECT-TYPE
    SYNTAX      SEQUENCE OF OperatingSystemMemoryTableEntry
    ACCESS      not-accessible
    STATUS      mandatory
    DESCRIPTION
"0400.0020 This Group defines the Operating System Memory Table."
    ::= { operatingSystemGroup 20 }
operatingSystemMemoryTableEntry                     OBJECT-TYPE
    SYNTAX      OperatingSystemMemoryTableEntry
    ACCESS      not-accessible
    STATUS      mandatory
    DESCRIPTION
"0400.0020.0001 This Group defines the Operating System Memory
Table Entry."
    INDEX       { operatingSystemMemorychassisIndex }
    ::= { operatingSystemMemoryTable 1 }
operatingSystemMemorychassisIndex               OBJECT-TYPE
    SYNTAX      DellObjectRange
    ACCESS      read-only
    STATUS      mandatory
    DESCRIPTION
"0400.0020.0001.0001 This attribute defines the index (one based) of
this Dell chassis."
    ::= { operatingSystemMemoryTableEntry 1 }
operatingSystemMemoryStateCapabilities              OBJECT-TYPE
    SYNTAX      DellStateCapabilities
    ACCESS      read-only
    STATUS      mandatory
    DESCRIPTION
"0400.0020.0001.0002 This attribute defines the capabilities of the
Operating System Memory."
    ::= { operatingSystemMemoryTableEntry 2 }
operatingSystemMemoryStateSettings                  OBJECT-TYPE
    SYNTAX      DellStateSettings
    ACCESS      read-write
    STATUS      mandatory
    DESCRIPTION
"0400.0020.0001.0003 This attribute defines the state of the
Operating System Memory."
    ::= { operatingSystemMemoryTableEntry 3 }
operatingSystemMemoryStatus                         OBJECT-TYPE
    SYNTAX      DellStatus
    ACCESS      read-only
    STATUS      mandatory
    DESCRIPTION
"0400.0020.0001.0004 This attribute defines the status of the
Operating System Memory."
    ::= { operatingSystemMemoryTableEntry 4 }
operatingSystemMemoryTotalPhysicalSize              OBJECT-TYPE
    SYNTAX      DellUnsigned32BitRange
    ACCESS      read-only
    STATUS      mandatory
    DESCRIPTION
"0400.0020.0001.0005 This attribute defines the total physical memory
in the Operating System Memory in Kbytes."
    ::= { operatingSystemMemoryTableEntry 5 }
operatingSystemMemoryAvailablePhysicalSize          OBJECT-TYPE
    SYNTAX      DellUnsigned32BitRange
    ACCESS      read-only
    STATUS      mandatory
    DESCRIPTION
"0400.0020.0001.0006 This attribute defines the available physical
memory in the Operating System Memory in Kbytes."
    ::= { operatingSystemMemoryTableEntry 6 }
operatingSystemMemoryTotalPageFileSize              OBJECT-TYPE
    SYNTAX      DellUnsigned32BitRange
    ACCESS      read-only
    STATUS      mandatory
    DESCRIPTION
"0400.0020.0001.0007 This attribute defines the total page file memory
in the Operating System Memory in Kbytes."
    ::= { operatingSystemMemoryTableEntry 7 }
operatingSystemMemoryAvailablePageFileSize          OBJECT-TYPE
    SYNTAX      DellUnsigned32BitRange
    ACCESS      read-only
    STATUS      mandatory
    DESCRIPTION
"0400.0020.0001.0008 This attribute defines the available page file memory
in the Operating System Memory in Kbytes."
    ::= { operatingSystemMemoryTableEntry 8 }
operatingSystemMemoryTotalVirtualSize               OBJECT-TYPE
    SYNTAX      DellUnsigned32BitRange
    ACCESS      read-only
    STATUS      mandatory
    DESCRIPTION
"0400.0020.0001.0009 This attribute defines the total virtual memory in
the Operating System Memory in Kbytes."
    ::= { operatingSystemMemoryTableEntry 9 }
operatingSystemMemoryAvailableVirtualSize           OBJECT-TYPE
    SYNTAX      DellUnsigned32BitRange
    ACCESS      read-only
    STATUS      mandatory
    DESCRIPTION
"0400.0020.0001.0010 This attribute defines the available virtual memory
in the Operating System Memory in Kbytes."
    ::= { operatingSystemMemoryTableEntry 10 }


-------------------------------------------------------------------------------
--
-- System Resource Group
--
-------------------------------------------------------------------------------

-------------------------------------------------------------------------------
-- System Resource Map Table
-------------------------------------------------------------------------------

DellSystemResourceMapType ::= INTEGER {
    other(1),             -- the System resource map type is not one of the following:
    unknown(2),           -- the System resource map type is unknown (not known or monitored)
    typeOne(3)            -- the System resource map type is type 1 (one)
}

SystemResourceMapTableEntry             ::= SEQUENCE {
    systemResourceMapchassisIndex       DellObjectRange,
    systemResourceMapIndex              DellObjectRange,
    systemResourceMapStateCapabilities  DellStateCapabilities,
    systemResourceMapStateSettings      DellStateSettings,
    systemResourceMapStatus             DellStatus,
    systemResourceMapType               DellSystemResourceMapType
}

systemResourceMapTable          OBJECT-TYPE
    SYNTAX          SEQUENCE OF SystemResourceMapTableEntry
    ACCESS          not-accessible
    STATUS          mandatory
    DESCRIPTION
"0500.0010 This Group defines the Dell System Resource Map Table."
    ::= { systemResourceGroup 10 }
systemResourceMapTableEntry     OBJECT-TYPE
    SYNTAX          SystemResourceMapTableEntry
    ACCESS          not-accessible
    STATUS          mandatory
    DESCRIPTION
"0500.0010.0001 This Group defines the Dell System Resource Map Table Entry."
    INDEX           { systemResourceMapchassisIndex, systemResourceMapIndex }
    ::= { systemResourceMapTable 1 }
systemResourceMapchassisIndex           OBJECT-TYPE
    SYNTAX      DellObjectRange
    ACCESS      read-only
    STATUS      mandatory
    DESCRIPTION
"0500.0010.0001.0001 This attribute defines the index (one based) of
this Dell chassis."
    ::= { systemResourceMapTableEntry 1 }
systemResourceMapIndex                  OBJECT-TYPE
    SYNTAX      DellObjectRange
    ACCESS      read-only
    STATUS      mandatory
    DESCRIPTION
"0500.0010.0001.0002 This attribute defines the index of Dell System
Resource Maps in this chassis."
    ::= { systemResourceMapTableEntry 2 }
systemResourceMapStateCapabilities       OBJECT-TYPE
    SYNTAX      DellStateCapabilities
    ACCESS      read-only
    STATUS      mandatory
    DESCRIPTION
"0500.0010.0001.0003 This attribute defines the capabilities of this system map."
    ::= { systemResourceMapTableEntry 3 }
systemResourceMapStateSettings          OBJECT-TYPE
    SYNTAX      DellStateSettings
    ACCESS      read-write
    STATUS      mandatory
    DESCRIPTION
"0500.0010.0001.0004 This attribute defines the state of this system map."
    ::= { systemResourceMapTableEntry 4 }
systemResourceMapStatus                 OBJECT-TYPE
    SYNTAX      DellStatus
    ACCESS      read-only
    STATUS      mandatory
    DESCRIPTION
"0500.0010.0001.0005 This attribute defines the status of this system map."
    ::= { systemResourceMapTableEntry 5 }
systemResourceMapType                   OBJECT-TYPE
    SYNTAX      DellSystemResourceMapType
    ACCESS      read-only
    STATUS      mandatory
    DESCRIPTION
"0500.0010.0001.0006 This attribute defines the type of this system map."
    ::= { systemResourceMapTableEntry 6 }


-------------------------------------------------------------------------------
-- System Resource Owner Table
-------------------------------------------------------------------------------

DellResourceOwnerInterfaceType  ::= INTEGER {
    typeIsOther(1),        -- the interface type is not one of the following:
    typeIsUnknown(2),      -- the interface type is unknown (not known or monitored)
    typeIsInternal(3),     -- the interface type is internal
    typeIsISA(4),          -- the interface type is an ISA Bus
    typeIsEISA(5),         -- the interface type is an EISA Bus
    typeIsMCA(6),          -- the interface type is an MCA Bus
    typeIsTurboChannel(7), -- the interface type is a TurboChannel Bus
    typeIsPCI(8)           -- the interface type is a PCI Bus
}

SystemResourceOwnerTableEntry               ::= SEQUENCE {
    systemResourceOwnerchassisIndex         DellObjectRange,
    systemResourceOwnerIndex                DellObjectRange,
    systemResourceOwnerStateCapabilities    DellStateCapabilities,
    systemResourceOwnerStateSettings        DellStateSettings,
    systemResourceOwnerStatus               DellStatus,
    systemResourceOwnerInterfaceType        DellResourceOwnerInterfaceType,
    systemResourceMapIndexReference         DellObjectRange,
    systemResourceOwnerDescriptionName      DellString,
    systemResourceOwnerInterfaceInstance    DellObjectRange
}

systemResourceOwnerTable                    OBJECT-TYPE
    SYNTAX          SEQUENCE OF SystemResourceOwnerTableEntry
    ACCESS          not-accessible
    STATUS          mandatory
    DESCRIPTION
"0500.0020 This Group defines the Dell System Resource Owner Table.
The variables in this group reference the Dell System Resource Map index."
    ::= { systemResourceGroup 20 }
systemResourceOwnerTableEntry               OBJECT-TYPE
    SYNTAX          SystemResourceOwnerTableEntry
    ACCESS          not-accessible
    STATUS          mandatory
    DESCRIPTION
"0500.0020.0001 This Group defines the Dell System Resource Owner Table Entry."
    INDEX           { systemResourceOwnerchassisIndex, systemResourceOwnerIndex }
    ::= { systemResourceOwnerTable 1 }
systemResourceOwnerchassisIndex             OBJECT-TYPE
    SYNTAX      DellObjectRange
    ACCESS      read-only
    STATUS      mandatory
    DESCRIPTION
"0500.0020.0001.0001 This attribute defines the index (one based) of
this Dell chassis."
    ::= { systemResourceOwnerTableEntry 1 }
systemResourceOwnerIndex                    OBJECT-TYPE
    SYNTAX      DellObjectRange
    ACCESS      read-only
    STATUS      mandatory
    DESCRIPTION
"0500.0020.0001.0002 This attribute defines the index of Dell System
Resource Owners in this chassis."
    ::= { systemResourceOwnerTableEntry 2 }
systemResourceOwnerStateCapabilities        OBJECT-TYPE
    SYNTAX      DellStateCapabilities
    ACCESS      read-only
    STATUS      mandatory
    DESCRIPTION
"0500.0020.0001.0003 This attribute defines the capabilities of this system
resource owner."
    ::= { systemResourceOwnerTableEntry 3 }
systemResourceOwnerStateSettings           OBJECT-TYPE
    SYNTAX      DellStateSettings
    ACCESS      read-write
    STATUS      mandatory
    DESCRIPTION
"0500.0020.0001.0004 This attribute defines the state of this system
resource owner."
    ::= { systemResourceOwnerTableEntry 4 }
systemResourceOwnerStatus                  OBJECT-TYPE
    SYNTAX      DellStatus
    ACCESS      read-only
    STATUS      mandatory
    DESCRIPTION
"0500.0020.0001.0005 This attribute defines the status of this system
resource owner."
    ::= { systemResourceOwnerTableEntry 5 }
systemResourceOwnerInterfaceType            OBJECT-TYPE
    SYNTAX      DellResourceOwnerInterfaceType
    ACCESS      read-only
    STATUS      mandatory
    DESCRIPTION
"0500.0020.0001.0006 This attribute defines the interface type of this
system resource owner."
    ::= { systemResourceOwnerTableEntry 6 }
systemResourceMapIndexReference                     OBJECT-TYPE
    SYNTAX      DellObjectRange
    ACCESS      read-only
    STATUS      mandatory
    DESCRIPTION
"0500.0020.0001.0007 This attribute defines the index to the associated
Dell System Resource Map in this chassis."
    ::= { systemResourceOwnerTableEntry 7 }
systemResourceOwnerDescriptionName              OBJECT-TYPE
    SYNTAX      DellString
    ACCESS      read-only
    STATUS      mandatory
    DESCRIPTION
"0500.0020.0001.0008 This attribute defines the description name of
 the system resource owner."
    ::= { systemResourceOwnerTableEntry 8 }
systemResourceOwnerInterfaceInstance            OBJECT-TYPE
    SYNTAX      DellObjectRange
    ACCESS      read-only
    STATUS      mandatory
    DESCRIPTION
"0500.0020.0001.0009 This attribute defines the index to the associated
system resource owner interface type in this chassis."
    ::= { systemResourceOwnerTableEntry 9 }


-------------------------------------------------------------------------------
-- System Resource IO Port Table
-------------------------------------------------------------------------------

DellResourceShareDisposition    ::= INTEGER {
    shareIsOther(1),            -- the share disposition is not one of the following:
    shareIsUnknown(2),          -- the share disposition is unknown (not known or monitored)
    shareIsDeviceExclusive(3),  -- the share disposition is device exclusive
    shareIsDriverExclusive(4),  -- the share disposition is driver exclusive
    shareIsShared(5)            -- the share disposition is shared
}

SystemResourceIOPortTableEntry                  ::= SEQUENCE {
    systemResourceIOPortchassisIndex            DellObjectRange,
    systemResourceIOPortIndex                   DellObjectRange,
    systemResourceIOPortStateCapabilities       DellStateCapabilities,
    systemResourceIOPortStateSettings           DellStateSettings,
    systemResourceIOPortStatus                  DellStatus,
    systemResourceIOPortOwnerIndexReference     DellObjectRange,
    systemResourceIOPortShareDisposition        DellResourceShareDisposition,
    systemResourceIOPortStartingAddress         DellUnsigned64BitRange,
    systemResourceIOPortEndingAddress           DellUnsigned64BitRange
}

systemResourceIOPortTable                       OBJECT-TYPE
    SYNTAX          SEQUENCE OF SystemResourceIOPortTableEntry
    ACCESS          not-accessible
    STATUS          mandatory
    DESCRIPTION
"0500.0030 This Group defines the Dell System Resource IO Port Table."
    ::= { systemResourceGroup 30 }
systemResourceIOPortTableEntry                  OBJECT-TYPE
    SYNTAX          SystemResourceIOPortTableEntry
    ACCESS          not-accessible
    STATUS          mandatory
    DESCRIPTION
"0500.0030.0001 This Group defines the Dell System Resource IO Port
Table Entry."
    INDEX           { systemResourceIOPortchassisIndex, systemResourceIOPortIndex }
    ::= { systemResourceIOPortTable 1 }
systemResourceIOPortchassisIndex            OBJECT-TYPE
    SYNTAX      DellObjectRange
    ACCESS      read-only
    STATUS      mandatory
    DESCRIPTION
"0500.0030.0001.0001 This attribute defines the index (one based) of
this Dell chassis."
    ::= { systemResourceIOPortTableEntry 1 }
systemResourceIOPortIndex                       OBJECT-TYPE
    SYNTAX      DellObjectRange
    ACCESS      read-only
    STATUS      mandatory
    DESCRIPTION
"0500.0030.0001.0002 This attribute defines the index of Dell System
Resource IO Ports in this chassis."
    ::= { systemResourceIOPortTableEntry 2 }
systemResourceIOPortStateCapabilities           OBJECT-TYPE
    SYNTAX      DellStateCapabilities
    ACCESS      read-only
    STATUS      mandatory
    DESCRIPTION
"0500.0030.0001.0003 This attribute defines the capabilities of this System
Resource IO Port."
    ::= { systemResourceIOPortTableEntry 3 }
systemResourceIOPortStateSettings               OBJECT-TYPE
    SYNTAX      DellStateSettings
    ACCESS      read-write
    STATUS      mandatory
    DESCRIPTION
"0500.0030.0001.0004 This attribute defines the state of this System
Resource IO Port."
    ::= { systemResourceIOPortTableEntry 4 }
systemResourceIOPortStatus                      OBJECT-TYPE
    SYNTAX      DellStatus
    ACCESS      read-only
    STATUS      mandatory
    DESCRIPTION
"0500.0030.0001.0005 This attribute defines the status of this System
Resource IO Port."
    ::= { systemResourceIOPortTableEntry 5 }
systemResourceIOPortOwnerIndexReference         OBJECT-TYPE
    SYNTAX      DellObjectRange
    ACCESS      read-only
    STATUS      mandatory
    DESCRIPTION
"0500.0030.0001.0006 This attribute defines the index to the associated
Dell System Resource Owner in this chassis."
    ::= { systemResourceIOPortTableEntry 6 }
systemResourceIOPortShareDisposition            OBJECT-TYPE
    SYNTAX      DellResourceShareDisposition
    ACCESS      read-only
    STATUS      mandatory
    DESCRIPTION
"0500.0030.0001.0007 This attribute defines the share disposition of the
Dell System Resource IO Port."
    ::= { systemResourceIOPortTableEntry 7 }
systemResourceIOPortStartingAddress             OBJECT-TYPE
    SYNTAX      DellUnsigned64BitRange
    ACCESS      read-only
    STATUS      mandatory
    DESCRIPTION
"0500.0030.0001.0008 This attribute defines the sixty-four bits of
the starting address of the Dell System Resource IO Port."
    ::= { systemResourceIOPortTableEntry 8 }
systemResourceIOPortEndingAddress              OBJECT-TYPE
    SYNTAX      DellUnsigned64BitRange
    ACCESS      read-only
    STATUS      mandatory
    DESCRIPTION
"0500.0030.0001.0009 This attribute defines the sixty-four bits
of the ending address of the Dell System Resource IO Port."
    ::= { systemResourceIOPortTableEntry 9 }


-------------------------------------------------------------------------------
-- System Resource Memory Table
-------------------------------------------------------------------------------

DellResourceMemoryFlags          ::= INTEGER {
    memoryIsReadOnly(1),         -- the Resource Memory is read only
    memoryIsWriteOnly(2),        -- the Resource Memory is write only
    memoryIsReadAndWrite(3),     -- the Resource Memory is read and write
    memoryIsPreFetchable(4),     -- the Resource Memory is prefetchable
    memoryIsCombinedWritable(8), -- the Resource Memory is combined writable
    memoryIsF24(16)              -- the Resource Memory is 24
}

SystemResourceMemoryTableEntry                  ::= SEQUENCE {
    systemResourceMemorychassisIndex            DellObjectRange,
    systemResourceMemoryIndex                   DellObjectRange,
    systemResourceMemoryStateCapabilities       DellStateCapabilities,
    systemResourceMemoryStateSettings           DellStateSettings,
    systemResourceMemoryStatus                  DellStatus,
    systemResourceMemoryOwnerIndexReference     DellObjectRange,
    systemResourceMemoryShareDisposition        DellResourceShareDisposition,
    systemResourceMemoryStartingAddress         DellUnsigned64BitRange,
    systemResourceMemoryEndingAddress           DellUnsigned64BitRange,
    systemResourceMemoryFlags                   DellResourceMemoryFlags
}

systemResourceMemoryTable                       OBJECT-TYPE
    SYNTAX          SEQUENCE OF SystemResourceMemoryTableEntry
    ACCESS          not-accessible
    STATUS          mandatory
    DESCRIPTION
"0500.0040 This Group defines the Dell System Resource Memory Table."
    ::= { systemResourceGroup 40 }
systemResourceMemoryTableEntry                  OBJECT-TYPE
    SYNTAX          SystemResourceMemoryTableEntry
    ACCESS          not-accessible
    STATUS          mandatory
    DESCRIPTION
"0500.0040.0001 This Group defines the Dell System Resource Memory Table
Entry."
    INDEX           { systemResourceMemorychassisIndex, systemResourceMemoryIndex }
    ::= { systemResourceMemoryTable 1 }
systemResourceMemorychassisIndex            OBJECT-TYPE
    SYNTAX      DellObjectRange
    ACCESS      read-only
    STATUS      mandatory
    DESCRIPTION
"0500.0040.0001.0001 This attribute defines the index (one based) of
this Dell chassis."
    ::= { systemResourceMemoryTableEntry 1 }
systemResourceMemoryIndex                       OBJECT-TYPE
    SYNTAX      DellObjectRange
    ACCESS      read-only
    STATUS      mandatory
    DESCRIPTION
"0500.0040.0001.0002 This attribute defines the index of Dell System Resource
Memories in this chassis."
    ::= { systemResourceMemoryTableEntry 2 }
systemResourceMemoryStateCapabilities           OBJECT-TYPE
    SYNTAX      DellStateCapabilities
    ACCESS      read-only
    STATUS      mandatory
    DESCRIPTION
"0500.0040.0001.0003 This attribute defines the capabilities of this System
Resource Memory."
    ::= { systemResourceMemoryTableEntry 3 }
systemResourceMemoryStateSettings               OBJECT-TYPE
    SYNTAX      DellStateSettings
    ACCESS      read-write
    STATUS      mandatory
    DESCRIPTION
"0500.0040.0001.0004 This attribute defines the state of this System
Resource Memory."
    ::= { systemResourceMemoryTableEntry 4 }
systemResourceMemoryStatus                      OBJECT-TYPE
    SYNTAX      DellStatus
    ACCESS      read-only
    STATUS      mandatory
    DESCRIPTION
"0500.0040.0001.0005 This attribute defines the status of this System
Resource Memory."
    ::= { systemResourceMemoryTableEntry 5 }
systemResourceMemoryOwnerIndexReference         OBJECT-TYPE
    SYNTAX      DellObjectRange
    ACCESS      read-only
    STATUS      mandatory
    DESCRIPTION
"0500.0040.0001.0006 This attribute defines the index to the associated
Dell System Resource Owner in this chassis."
    ::= { systemResourceMemoryTableEntry 6 }
systemResourceMemoryShareDisposition            OBJECT-TYPE
    SYNTAX      DellResourceShareDisposition
    ACCESS      read-only
    STATUS      mandatory
    DESCRIPTION
"0500.0040.0001.0007 This attribute defines the share disposition of the
Dell System Resource Memory."
    ::= { systemResourceMemoryTableEntry 7 }
systemResourceMemoryStartingAddress             OBJECT-TYPE
    SYNTAX      DellUnsigned64BitRange
    ACCESS      read-only
    STATUS      mandatory
    DESCRIPTION
"0500.0040.0001.0008 This attribute defines the sixty-four bits of
the starting address of the Dell System Resource Memory."
    ::= { systemResourceMemoryTableEntry 8 }
systemResourceMemoryEndingAddress               OBJECT-TYPE
    SYNTAX      DellUnsigned64BitRange
    ACCESS      read-only
    STATUS      mandatory
    DESCRIPTION
"0500.0040.0001.0009 This attribute defines the sixty-four bits of
the ending address of the Dell System Resource Memory."
    ::= { systemResourceMemoryTableEntry 9 }
systemResourceMemoryFlags                       OBJECT-TYPE
    SYNTAX      DellResourceMemoryFlags
    ACCESS      read-only
    STATUS      mandatory
    DESCRIPTION
"0500.0040.0001.0010 This attribute defines the permission flags of
the Dell System Resource Memory."
    ::= { systemResourceMemoryTableEntry 10 }


-------------------------------------------------------------------------------
-- System Resource Interrupts Table
-------------------------------------------------------------------------------

DellResourceInterruptType         ::= INTEGER {
    interruptIsLevelSensitive(1), -- the Interrupt type is level sensitive
    interruptIsLatched(2)         -- the Interrupt type is latched
}
DellResourceInterruptTrigger      ::= INTEGER {
    interruptIsActiveWhenLow(1),  -- the Interrupt trigger is active on a low  signal
    interruptIsActiveWhenHigh(2)  -- the Interrupt trigger is active on a high signal
}

SystemResourceInterruptTableEntry               ::= SEQUENCE {
    systemResourceInterruptchassisIndex         DellObjectRange,
    systemResourceInterruptIndex                DellObjectRange,
    systemResourceInterruptStateCapabilities    DellStateCapabilities,
    systemResourceInterruptStateSettings        DellStateSettings,
    systemResourceInterruptStatus               DellStatus,
    systemResourceInterruptOwnerIndexReference  DellObjectRange,
    systemResourceInterruptShareDisposition     DellResourceShareDisposition,
    systemResourceInterruptLevel                DellUnsigned32BitRange,
    systemResourceInterruptType                 DellResourceInterruptType,
    systemResourceInterruptTrigger              DellResourceInterruptTrigger
}

systemResourceInterruptTable                    OBJECT-TYPE
    SYNTAX          SEQUENCE OF SystemResourceInterruptTableEntry
    ACCESS          not-accessible
    STATUS          mandatory
    DESCRIPTION
"0500.0050 This Group defines the Dell System Resource Interrupts Table."
    ::= { systemResourceGroup 50 }
systemResourceInterruptTableEntry               OBJECT-TYPE
    SYNTAX          SystemResourceInterruptTableEntry
    ACCESS          not-accessible
    STATUS          mandatory
    DESCRIPTION
"0500.0050.0001 This Group defines the Dell System Resource Interrupts
Table Entry."
    INDEX           { systemResourceInterruptchassisIndex, systemResourceInterruptIndex }
    ::= { systemResourceInterruptTable 1 }
systemResourceInterruptchassisIndex             OBJECT-TYPE
    SYNTAX      DellObjectRange
    ACCESS      read-only
    STATUS      mandatory
    DESCRIPTION
"0500.0050.0001.0001 This attribute defines the index (one based) of
this Dell chassis."
    ::= { systemResourceInterruptTableEntry 1 }
systemResourceInterruptIndex                    OBJECT-TYPE
    SYNTAX      DellObjectRange
    ACCESS      read-only
    STATUS      mandatory
    DESCRIPTION
"0500.0050.0001.0002 This attribute defines the index of Dell System
Resource Interrupts in this chassis."
    ::= { systemResourceInterruptTableEntry 2 }
systemResourceInterruptStateCapabilities        OBJECT-TYPE
    SYNTAX      DellStateCapabilities
    ACCESS      read-only
    STATUS      mandatory
    DESCRIPTION
"0500.0050.0001.0003 This attribute defines the capabilities of this System
Resource Interrupt."
    ::= { systemResourceInterruptTableEntry 3 }
systemResourceInterruptStateSettings           OBJECT-TYPE
    SYNTAX      DellStateSettings
    ACCESS      read-write
    STATUS      mandatory
    DESCRIPTION
"0500.0050.0001.0004 This attribute defines the state of this System
Resource Interrupt."
    ::= { systemResourceInterruptTableEntry 4 }
systemResourceInterruptStatus                   OBJECT-TYPE
    SYNTAX      DellStatus
    ACCESS      read-only
    STATUS      mandatory
    DESCRIPTION
"0500.0050.0001.0005 This attribute defines the status of this System
Resource Interrupt."
    ::= { systemResourceInterruptTableEntry 5 }
systemResourceInterruptOwnerIndexReference      OBJECT-TYPE
    SYNTAX      DellObjectRange
    ACCESS      read-only
    STATUS      mandatory
    DESCRIPTION
"0500.0050.0001.0006 This attribute defines the index to the associated
Dell System Resource Owner in this chassis."
    ::= { systemResourceInterruptTableEntry 6 }
systemResourceInterruptShareDisposition         OBJECT-TYPE
    SYNTAX      DellResourceShareDisposition
    ACCESS      read-only
    STATUS      mandatory
    DESCRIPTION
"0500.0050.0001.0007 This attribute defines the share disposition of the
Dell System Resource Interrupt."
    ::= { systemResourceInterruptTableEntry 7 }
systemResourceInterruptLevel                    OBJECT-TYPE
    SYNTAX      DellUnsigned32BitRange
    ACCESS      read-only
    STATUS      mandatory
    DESCRIPTION
"0500.0050.0001.0008 This attribute defines the interrupt request level
(IRQ) of the Dell System Resource Interrupt."
    ::= { systemResourceInterruptTableEntry 8 }
systemResourceInterruptType                     OBJECT-TYPE
    SYNTAX      DellResourceInterruptType
    ACCESS      read-only
    STATUS      mandatory
    DESCRIPTION
"0500.0050.0001.0009 This attribute defines the interrupt type of the
Dell System Resource Interrupt."
    ::= { systemResourceInterruptTableEntry 9 }
systemResourceInterruptTrigger                  OBJECT-TYPE
    SYNTAX      DellResourceInterruptTrigger
    ACCESS      read-only
    STATUS      mandatory
    DESCRIPTION
"0500.0050.0001.0010 This attribute defines the interrupt trigger of
the Dell System Resource Interrupt."
    ::= { systemResourceInterruptTableEntry 10 }


-------------------------------------------------------------------------------
-- System Resource DMA Table
-------------------------------------------------------------------------------

DellResourceDMATransferWidth      ::= INTEGER {
    dmaTransferWidthIsOther(1),   -- the DMA transfer width is not one of the following:
    dmaTransferWidthIsunknown(2), -- the DMA transfer width is unknown
    dmaTransferWidthIs8Bits(3),   -- the DMA transfer width is eight bits
    dmaTransferWidthIs16Bits(4),  -- the DMA transfer width is sixteen bits
    dmaTransferWidthIs32Bits(5),  -- the DMA transfer width is thirty two bits
    dmaTransferWidthIs64Bits(6),  -- the DMA transfer width is sixty four bits
    dmaTransferWidthIs128Bits(7)  -- the DMA transfer width is 128 bits
}
DellResourceDMABusMaster          ::= INTEGER {
    dmaIsOther(1),                -- the DMA bus master capability is not one of the following:
    dmaIsUnknown(2),              -- the DMA bus master capability is unknown
    dmaIsNotABusmaster(3),        -- the DMA has no bus master capability
    dmaIsABusmaster(4)            -- the DMA has bus master capability
}

SystemResourceDMATableEntry                 ::= SEQUENCE {
    systemResourceDMAchassisIndex           DellObjectRange,
    systemResourceDMAIndex                  DellObjectRange,
    systemResourceDMAStateCapabilities      DellStateCapabilities,
    systemResourceDMAStateSettings          DellStateSettings,
    systemResourceDMAStatus                 DellStatus,
    systemResourceDMAOwnerIndexReference    DellObjectRange,
    systemResourceDMAShareDisposition       DellResourceShareDisposition,
    systemResourceDMAMaximumTransferSize    DellUnsigned32BitRange,
    systemResourceDMATransferWidth          DellResourceDMATransferWidth,
    systemResourceDMABusMaster              DellResourceDMABusMaster
}

systemResourceDMATable                      OBJECT-TYPE
    SYNTAX          SEQUENCE OF SystemResourceDMATableEntry
    ACCESS          not-accessible
    STATUS          mandatory
    DESCRIPTION
"0500.0060 This Group defines the Dell System Resource DMA Table."
    ::= { systemResourceGroup 60 }
systemResourceDMATableEntry                 OBJECT-TYPE
    SYNTAX          SystemResourceDMATableEntry
    ACCESS          not-accessible
    STATUS          mandatory
    DESCRIPTION
"0500.0060.0001 This Group defines the Dell System Resource DMA Table Entry."
    INDEX           { systemResourceDMAchassisIndex, systemResourceDMAIndex }
    ::= { systemResourceDMATable 1 }
systemResourceDMAchassisIndex           OBJECT-TYPE
    SYNTAX      DellObjectRange
    ACCESS      read-only
    STATUS      mandatory
    DESCRIPTION
"0500.0060.0001.0001 This attribute defines the index (one based) of
this Dell chassis."
    ::= { systemResourceDMATableEntry 1 }
systemResourceDMAIndex                      OBJECT-TYPE
    SYNTAX      DellObjectRange
    ACCESS      read-only
    STATUS      mandatory
    DESCRIPTION
"0500.0060.0001.0002 This attribute defines the index of Dell System
Resource DMAs in this chassis."
    ::= { systemResourceDMATableEntry 2 }
systemResourceDMAStateCapabilities          OBJECT-TYPE
    SYNTAX      DellStateCapabilities
    ACCESS      read-only
    STATUS      mandatory
    DESCRIPTION
"0500.0060.0001.0003 This attribute defines the capabilities of this System
Resource DMA."
    ::= { systemResourceDMATableEntry 3 }
systemResourceDMAStateSettings             OBJECT-TYPE
    SYNTAX      DellStateSettings
    ACCESS      read-write
    STATUS      mandatory
    DESCRIPTION
"0500.0060.0001.0004 This attribute defines the state of this System
Resource DMA."
    ::= { systemResourceDMATableEntry 4 }
systemResourceDMAStatus                     OBJECT-TYPE
    SYNTAX      DellStatus
    ACCESS      read-only
    STATUS      mandatory
    DESCRIPTION
"0500.0060.0001.0005 This attribute defines the status of this System
Resource DMA."
    ::= { systemResourceDMATableEntry 5 }
systemResourceDMAOwnerIndexReference        OBJECT-TYPE
    SYNTAX      DellObjectRange
    ACCESS      read-only
    STATUS      mandatory
    DESCRIPTION
"0500.0060.0001.0006 This attribute defines the index to the associated
Dell System Resource Owner in this chassis."
    ::= { systemResourceDMATableEntry 6 }
systemResourceDMAShareDisposition           OBJECT-TYPE
    SYNTAX      DellResourceShareDisposition
    ACCESS      read-only
    STATUS      mandatory
    DESCRIPTION
"0500.0060.0001.0007 This attribute defines the share disposition of the
Dell System Resource DMA."
    ::= { systemResourceDMATableEntry 7 }
systemResourceDMAMaximumTransferSize        OBJECT-TYPE
    SYNTAX      DellUnsigned32BitRange
    ACCESS      read-only
    STATUS      mandatory
    DESCRIPTION
"0500.0060.0001.0008 This attribute defines the maximum size of a memory
transfer in bytes for the Dell System Resource DMA."
    ::= { systemResourceDMATableEntry 8 }
systemResourceDMATransferWidth              OBJECT-TYPE
    SYNTAX      DellResourceDMATransferWidth
    ACCESS      read-only
    STATUS      mandatory
    DESCRIPTION
"0500.0060.0001.0009 This attribute defines the tranfer width of the Dell
System Resource DMA."
    ::= { systemResourceDMATableEntry 9 }
systemResourceDMABusMaster                  OBJECT-TYPE
    SYNTAX      DellResourceDMABusMaster
    ACCESS      read-only
    STATUS      mandatory
    DESCRIPTION
"0500.0060.0001.0010 This attribute defines the bus mastering capabilities
of the Dell System Resource DMA."
    ::= { systemResourceDMATableEntry 10 }


-------------------------------------------------------------------------------
--
-- Power Group
--
-------------------------------------------------------------------------------

-------------------------------------------------------------------------------
-- Power Unit Table
-------------------------------------------------------------------------------

PowerUnitTableEntry                             ::= SEQUENCE {
    powerUnitchassisIndex                       DellObjectRange,
    powerUnitIndex                              DellObjectRange,
    powerUnitStateCapabilities                  DellStateCapabilities,
    powerUnitStateSettings                      DellStateSettings,
    powerUnitRedundancyStatus                   DellStatusRedundancy,
    powerSupplyCountForRedundancy               DellObjectRange,
    powerUnitName                               DellString
}

powerUnitTable                                  OBJECT-TYPE
    SYNTAX      SEQUENCE OF PowerUnitTableEntry
    ACCESS      not-accessible
    STATUS      mandatory
    DESCRIPTION
"0600.0010 This object defines the Power Unit Table."
    ::= { powerGroup 10 }
powerUnitTableEntry                             OBJECT-TYPE
    SYNTAX      PowerUnitTableEntry
    ACCESS      not-accessible
    STATUS      mandatory
    DESCRIPTION
"0600.0010.0001 This object defines the Power Unit Table Entry."
    INDEX       { powerUnitchassisIndex, powerUnitIndex }
    ::= { powerUnitTable 1 }
powerUnitchassisIndex                           OBJECT-TYPE
    SYNTAX      DellObjectRange
    ACCESS      read-only
    STATUS      mandatory
    DESCRIPTION
"0600.0010.0001.0001 This attribute defines the index (one based) of the
chassis."
    ::= { powerUnitTableEntry 1 }
powerUnitIndex                                  OBJECT-TYPE
    SYNTAX      DellObjectRange
    ACCESS      read-only
    STATUS      mandatory
    DESCRIPTION
"0600.0010.0001.0002 This attribute defines the index (one based) of the
power unit."
    ::= { powerUnitTableEntry 2 }
powerUnitStateCapabilities                      OBJECT-TYPE
    SYNTAX      DellStateCapabilities
    ACCESS      read-only
    STATUS      mandatory
    DESCRIPTION
"0600.0010.0001.0003 This attribute defines the state capabilities of the
power unit."
    ::= { powerUnitTableEntry 3 }
powerUnitStateSettings                          OBJECT-TYPE
    SYNTAX      DellStateSettings
    ACCESS      read-write
    STATUS      mandatory
    DESCRIPTION
"0600.0010.0001.0004 This attribute defines the state settings of the
power unit."
    ::= { powerUnitTableEntry 4 }
powerUnitRedundancyStatus                       OBJECT-TYPE
    SYNTAX      DellStatusRedundancy
    ACCESS      read-only
    STATUS      mandatory
    DESCRIPTION
"0600.0010.0001.0005 This attribute defines the redundancy status of the
power unit."
    ::= { powerUnitTableEntry 5 }
powerSupplyCountForRedundancy                   OBJECT-TYPE
    SYNTAX      DellObjectRange
    ACCESS      read-only
    STATUS      mandatory
    DESCRIPTION
"0600.0010.0001.0006 This attribute defines the total number of power supplies
required for this power unit to have redundancy."
    ::= { powerUnitTableEntry 6 }
powerUnitName                                   OBJECT-TYPE
    SYNTAX      DellString
    ACCESS      read-only
    STATUS      mandatory
    DESCRIPTION
"0600.0010.0001.0007 This attribute defines the name of the power unit."
    ::= { powerUnitTableEntry 7 }


-------------------------------------------------------------------------------
-- Power Supply Table
-------------------------------------------------------------------------------

DellPowerSupplyStateCapabilitiesUnique          ::= INTEGER {
    -- If set to 0 (zero) the object has no capabilities
    unknown(1),                                 -- The objects capabilities are unknown
    -- The objects capabilities allow it to be set to:
    onlineCapable(2),                           -- be disabled (offline) or be enabled (online)
    notReadyCapable(4)                          -- not ready
}
DellPowerSupplyStateSettingsUnique      ::= INTEGER {
    -- If set to 0 (zero) the object has no settings
    unknown(1),                                 -- The objects state is unknown
    onLine(2),                                  -- The objects state is disabled (offline) 0, or enabled (online) 1
    notReady(4),                                -- The objects state is not ready
    fanFailure(8),                              -- power supply fan has failed
    onlineAndFanFailure(10),
    powerSupplyIsON(16),                        -- power supply is supplying power
    powerSupplyIsOK(32),                        -- power supply is indicating it is OK
    acSwitchIsON(64),                           -- power supply is indicating the AC power switch is on
    onlineandAcSwitchIsON(66),
    acPowerIsON(128),                           -- power supply is indicating the AC power is on
    onlineAndAcPowerIsON(130),
    onlineAndPredictiveFailure(210),
    acPowerAndSwitchAreOnPowerSupplyIsOnIsOkAndOnline(242)
}
DellPowerSupplyType                             ::= INTEGER {
    powerSupplyTypeIsOther(1),                  -- type is not one of the following types:
    powerSupplyTypeIsUnknown(2),                -- type is unknown (not known or monitored)
    powerSupplyTypeIsLinear(3),                 -- type is a linear power supply
    powerSupplyTypeIsSwitching(4),              -- type is a switching power supply
    powerSupplyTypeIsBattery(5),                -- type is a battery
    powerSupplyTypeIsUPS(6),                    -- type is an uninterruptable power supply
    powerSupplyTypeIsConverter(7),              -- type is a power converter power supply
    powerSupplyTypeIsRegulator(8),              -- type is a regulator type of power supply
    powerSupplyTypeIsAC(9),                     -- type is a AC power supply
    powerSupplyTypeIsDC(10)                     -- type is a DC power supply
}

PowerSupplyTableEntry                           ::= SEQUENCE {
    powerSupplychassisIndex                     DellObjectRange,
    powerSupplyIndex                            DellObjectRange,
    powerSupplyStateCapabilitiesUnique          DellPowerSupplyStateCapabilitiesUnique,
    powerSupplyStateSettingsUnique              DellPowerSupplyStateSettingsUnique,
    powerSupplyStatus                           DellStatus,
    powerSupplyOutputWatts                      DellSigned32BitRange,
    powerSupplyType                             DellPowerSupplyType,
    powerSupplyLocationName                     DellString,
    powerSupplyInputVoltage                     DellSigned32BitRange,
    powerSupplypowerUnitIndexReference          DellObjectRange
}

powerSupplyTable                                OBJECT-TYPE
    SYNTAX      SEQUENCE OF PowerSupplyTableEntry
    ACCESS      not-accessible
    STATUS      mandatory
    DESCRIPTION
"0600.0012 This object defines the Power Supply Table."
    ::= { powerGroup 12 }
powerSupplyTableEntry                           OBJECT-TYPE
    SYNTAX      PowerSupplyTableEntry
    ACCESS      not-accessible
    STATUS      mandatory
    DESCRIPTION
"0600.0012.0001 This object defines the Power Supply Table Entry."
    INDEX       { powerSupplychassisIndex, powerSupplyIndex }
    ::= { powerSupplyTable 1 }
powerSupplychassisIndex                         OBJECT-TYPE
    SYNTAX      DellObjectRange
    ACCESS      read-only
    STATUS      mandatory
    DESCRIPTION
"0600.0012.0001.0001 This attribute defines the index (one based) of the
chassis."
    ::= { powerSupplyTableEntry 1 }
powerSupplyIndex                                OBJECT-TYPE
    SYNTAX      DellObjectRange
    ACCESS      read-only
    STATUS      mandatory
    DESCRIPTION
"0600.0012.0001.0002 This attribute defines the index (one based) of the
power supply."
    ::= { powerSupplyTableEntry 2 }
powerSupplyStateCapabilitiesUnique              OBJECT-TYPE
    SYNTAX      DellPowerSupplyStateCapabilitiesUnique
    ACCESS      read-only
    STATUS      mandatory
    DESCRIPTION
"0600.0012.0001.0003 This attribute defines the state capabilities of the
power supply."
    ::= { powerSupplyTableEntry 3 }
powerSupplyStateSettingsUnique                  OBJECT-TYPE
    SYNTAX      DellPowerSupplyStateSettingsUnique
    ACCESS      read-write
    STATUS      mandatory
    DESCRIPTION
"0600.0012.0001.0004 This attribute defines the state settings of the
power supply."
    ::= { powerSupplyTableEntry 4 }
powerSupplyStatus                               OBJECT-TYPE
    SYNTAX      DellStatus
    ACCESS      read-only
    STATUS      mandatory
    DESCRIPTION
"0600.0012.0001.0005 This attribute defines the status of the power supply."
    ::= { powerSupplyTableEntry 5 }
powerSupplyOutputWatts                          OBJECT-TYPE
    SYNTAX      DellSigned32BitRange
    ACCESS      read-only
    STATUS      mandatory
    DESCRIPTION
"0600.0012.0001.0006 This attribute defines the maximum sustained output
wattage of the power supply, in tenths of watts."
    ::= { powerSupplyTableEntry 6 }
powerSupplyType                                 OBJECT-TYPE
    SYNTAX      DellPowerSupplyType
    ACCESS      read-only
    STATUS      mandatory
    DESCRIPTION
"0600.0012.0001.0007 This attribute defines the type of the power supply."
    ::= { powerSupplyTableEntry 7 }
powerSupplyLocationName                         OBJECT-TYPE
    SYNTAX      DellString
    ACCESS      read-only
    STATUS      mandatory
    DESCRIPTION
"0600.0012.0001.0008 This attribute defines the location name of the power
supply."
    ::= { powerSupplyTableEntry 8 }
powerSupplyInputVoltage                         OBJECT-TYPE
    SYNTAX      DellSigned32BitRange
    ACCESS      read-only
    STATUS      mandatory
    DESCRIPTION
"0600.0012.0001.0009 This attribute defines the input voltage to the power
supply, in volts."
    ::= { powerSupplyTableEntry 9 }
powerSupplypowerUnitIndexReference              OBJECT-TYPE
    SYNTAX      DellObjectRange
    ACCESS      read-only
    STATUS      mandatory
    DESCRIPTION
"0600.0012.0001.0010 This attribute defines the index to the associated
Power Unit, if the power supply is part of a power unit."
    ::= { powerSupplyTableEntry 10 }


-------------------------------------------------------------------------------
-- Voltage Probe Table
-------------------------------------------------------------------------------

DellVoltageType ::= INTEGER {
    voltageProbeTypeIsOther(1),                 -- type is not one of the following types:
    voltageProbeTypeIsUnknown(2),               -- type is unknown (not known or monitored)
    voltageProbeTypeIs1Point5Volt(3),           -- type is a   1.5 Volt probe
    voltageProbeTypeIs3Point3Volt(4),           -- type is a   3.3 Volt probe
    voltageProbeTypeIs5Volt(5),                 -- type is a   5   Volt probe
    voltageProbeTypeIsMinus5Volt(6),            -- type is a  -5   Volt probe
    voltageProbeTypeIs12Volt(7),                -- type is a  12   Volt probe
    voltageProbeTypeIsMinus12Volt(8),           -- type is a -12   Volt probe
    voltageProbeTypeIsIO(9),                    -- type is an IO   Volt probe
    voltageProbeTypeIsCore(10),                 -- type is a core  Volt probe
    voltageProbeTypeIsFLEA(11),                 -- type is a FLEA (standby) Volt probe
    voltageProbeTypeIsBattery(12),              -- type is a battery Volt probe
    voltageProbeTypeIsTerminator(13),           -- type is a SCSI termination Volt probe
    voltageProbeTypeIs2Point5Volt(14),          -- type is a   2.5 Volt probe
    voltageProbeTypeIsGTL(15)                   -- type is a GTL (ground termination logic) probe
}

VoltageProbeTableEntry                          ::= SEQUENCE {
    voltageProbechassisIndex                    DellObjectRange,
    voltageProbeIndex                           DellObjectRange,
    voltageProbeStateCapabilities               DellStateCapabilities,
    voltageProbeStateSettings                   DellStateSettings,
    voltageProbeStatus                          DellStatusProbe,
    voltageProbeReading                         DellSigned32BitRange,
    voltageProbeType                            DellVoltageType,
    voltageProbeLocationName                    DellString,
    voltageProbeUpperNonRecoverableThreshold    DellSigned32BitRange,
    voltageProbeUpperCriticalThreshold          DellSigned32BitRange,
    voltageProbeUpperNonCriticalThreshold       DellSigned32BitRange,
    voltageProbeLowerNonCriticalThreshold       DellSigned32BitRange,
    voltageProbeLowerCriticalThreshold          DellSigned32BitRange,
    voltageProbeLowerNonRecoverableThreshold    DellSigned32BitRange,
    voltageProbeProbeCapabilities               DellProbeCapabilities
}

voltageProbeTable                               OBJECT-TYPE
    SYNTAX      SEQUENCE OF VoltageProbeTableEntry
    ACCESS      not-accessible
    STATUS      mandatory
    DESCRIPTION
"0600.0020 This object defines the Voltage Probe Table."
    ::= { powerGroup 20 }
voltageProbeTableEntry                          OBJECT-TYPE
    SYNTAX      VoltageProbeTableEntry
    ACCESS      not-accessible
    STATUS      mandatory
    DESCRIPTION
"0600.0020.001 This object defines the Voltage Probe Table Entry."
    INDEX       { voltageProbechassisIndex, voltageProbeIndex }
    ::= { voltageProbeTable 1 }
voltageProbechassisIndex                        OBJECT-TYPE
    SYNTAX      DellObjectRange
    ACCESS      read-only
    STATUS      mandatory
    DESCRIPTION
"0600.0020.0001.0001 This attribute defines the index (one based) of the
chassis."
    ::= { voltageProbeTableEntry 1 }
voltageProbeIndex                               OBJECT-TYPE
    SYNTAX      DellObjectRange
    ACCESS      read-only
    STATUS      mandatory
    DESCRIPTION
"0600.0020.0001.0002 This attribute defines the index (one based) of the
voltage probe."
    ::= { voltageProbeTableEntry 2 }
voltageProbeStateCapabilities                   OBJECT-TYPE
    SYNTAX      DellStateCapabilities
    ACCESS      read-only
    STATUS      mandatory
    DESCRIPTION
"0600.0020.0001.0003 This attribute defines the state capabilities of the
voltage probe."
    ::= { voltageProbeTableEntry 3 }
voltageProbeStateSettings                       OBJECT-TYPE
    SYNTAX      DellStateSettings
    ACCESS      read-write
    STATUS      mandatory
    DESCRIPTION
"0600.0020.0001.0004 This attribute defines the state settints of the
voltage probe."
    ::= { voltageProbeTableEntry 4 }
voltageProbeStatus                              OBJECT-TYPE
    SYNTAX      DellStatusProbe
    ACCESS      read-only
    STATUS      mandatory
    DESCRIPTION
"0600.0020.0001.0005 This attribute defines the probe status of the
voltage probe."
    ::= { voltageProbeTableEntry 5 }
voltageProbeReading                             OBJECT-TYPE
    SYNTAX      DellSigned32BitRange
    ACCESS      read-only
    STATUS      mandatory
    DESCRIPTION
"0600.0020.0001.0006 This attribute defines the reading of the voltage
probe.  The value is an integer representing the voltage the probe is reading
in millivolts."
    ::= { voltageProbeTableEntry 6 }
voltageProbeType                                OBJECT-TYPE
    SYNTAX      DellVoltageType
    ACCESS      read-only
    STATUS      mandatory
    DESCRIPTION
"0600.0020.0001.0007 This attribute defines the type of the voltage probe."
    ::= { voltageProbeTableEntry 7 }
voltageProbeLocationName                        OBJECT-TYPE
    SYNTAX      DellString
    ACCESS      read-only
    STATUS      mandatory
    DESCRIPTION
"0600.0020.0001.0008 This attribute defines the location name of the
voltage probe."
    ::= { voltageProbeTableEntry 8 }
voltageProbeUpperNonRecoverableThreshold        OBJECT-TYPE
    SYNTAX      DellSigned32BitRange
    ACCESS      read-only
    STATUS      mandatory
    DESCRIPTION
"0600.0020.0001.0009 This attribute defines the upper nonrecoverable threshold
of the voltage probe.  The value is an integer representing the voltage
of the threshold in millivolts."
    ::= { voltageProbeTableEntry 9 }
voltageProbeUpperCriticalThreshold              OBJECT-TYPE
    SYNTAX      DellSigned32BitRange
    ACCESS      read-only
    STATUS      mandatory
    DESCRIPTION
"0600.0020.0001.0010 This attribute defines the upper critical threshold
of the voltage probe.  The value is an integer representing the voltage
of the threshold in millivolts."
    ::= { voltageProbeTableEntry 10 }
voltageProbeUpperNonCriticalThreshold           OBJECT-TYPE
    SYNTAX      DellSigned32BitRange
    ACCESS      read-write
    STATUS      mandatory
    DESCRIPTION
"0600.0020.0001.0011 This attribute defines the upper noncritical threshold
of the voltage probe.  The value is an integer representing the voltage
of the threshold in millivolts."
    ::= { voltageProbeTableEntry 11 }
voltageProbeLowerNonCriticalThreshold           OBJECT-TYPE
    SYNTAX      DellSigned32BitRange
    ACCESS      read-write
    STATUS      mandatory
    DESCRIPTION
"0600.0020.0001.0012 This attribute defines the lower noncritical threshold
of the voltage probe.  The value is an integer representing the voltage
of the threshold in millivolts."
    ::= { voltageProbeTableEntry 12 }
voltageProbeLowerCriticalThreshold              OBJECT-TYPE
    SYNTAX      DellSigned32BitRange
    ACCESS      read-only
    STATUS      mandatory
    DESCRIPTION
"0600.0020.0001.0013 This attribute defines the lower critical threshold
of the voltage probe.  The value is an integer representing the voltage
of the threshold in millivolts."
    ::= { voltageProbeTableEntry 13 }
voltageProbeLowerNonRecoverableThreshold        OBJECT-TYPE
    SYNTAX      DellSigned32BitRange
    ACCESS      read-only
    STATUS      mandatory
    DESCRIPTION
"0600.0020.0001.0014 This attribute defines the lower nonrecoverable threshold
of the voltage probe.  The value is an integer representing the voltage
of the threshold in millivolts."
    ::= { voltageProbeTableEntry 14 }
voltageProbeProbeCapabilities                   OBJECT-TYPE
    SYNTAX      DellProbeCapabilities
    ACCESS      read-only
    STATUS      mandatory
    DESCRIPTION
"0600.0020.0001.0015 This attribute defines the probe capabilities of the
voltage probe."
    ::= { voltageProbeTableEntry 15 }


-------------------------------------------------------------------------------
-- Amperage Probe Table
-------------------------------------------------------------------------------

DellAmperageProbeType    ::= INTEGER {
    amperageProbeTypeIsOther(1),                -- type is not one of the following types:
    amperageProbeTypeIsUnknown(2),              -- type is unknown (not known or monitored)
    amperageProbeTypeIs1Point5Volt(3),          -- type is a   1.5 Amperage probe
    amperageProbeTypeIs3Point3volt(4),          -- type is a   3.3 Amperage probe
    amperageProbeTypeIs5Volt(5),                -- type is a   5   Amperage probe
    amperageProbeTypeIsMinus5Volt(6),           -- type is a  -5   Amperage probe
    amperageProbeTypeIs12Volt(7),               -- type is a  12   Amperage probe
    amperageProbeTypeIsMinus12Volt(8),          -- type is a -12   Amperage probe
    amperageProbeTypeIsIO(9),                   -- type is an IO   Amperage probe
    amperageProbeTypeIsCore(10),                -- type is a core  Amperage probe
    amperageProbeTypeIsFLEA(11),                -- type is a FLEA (standby) Amperage probe
    amperageProbeTypeIsBattery(12),             -- type is a battery Amperage probe
    amperageProbeTypeIsTerminator(13),          -- type is a SCSI termination Amperage probe
    amperageProbeTypeIs2Point5Volt(14),         -- type is a   2.5 Volt amperage probe
    amperageProbeTypeIsGTL(15)                  -- type is a GTL (ground termination logic) probe
}

AmperageProbeTableEntry                         ::= SEQUENCE {
    amperageProbechassisIndex                   DellObjectRange,
    amperageProbeIndex                          DellObjectRange,
    amperageProbeStateCapabilities              DellStateCapabilities,
    amperageProbeStateSettings                  DellStateSettings,
    amperageProbeStatus                         DellStatusProbe,
    amperageProbeReading                        DellSigned32BitRange,
    amperageProbeType                           DellAmperageProbeType,
    amperageProbeLocationName                   DellString,
    amperageProbeUpperNonRecoverableThreshold   DellSigned32BitRange,
    amperageProbeUpperCriticalThreshold         DellSigned32BitRange,
    amperageProbeUpperNonCriticalThreshold      DellSigned32BitRange,
    amperageProbeLowerNonCriticalThreshold      DellSigned32BitRange,
    amperageProbeLowerCriticalThreshold         DellSigned32BitRange,
    amperageProbeLowerNonRecoverableThreshold   DellSigned32BitRange,
	amperageProbeProbeCapabilities              DellProbeCapabilities
}

amperageProbeTable                              OBJECT-TYPE
    SYNTAX      SEQUENCE OF AmperageProbeTableEntry
    ACCESS      not-accessible
    STATUS      mandatory
    DESCRIPTION
"0600.0030 This object defines the Amperage Probe Table."
    ::= { powerGroup 30 }
amperageProbeTableEntry                         OBJECT-TYPE
    SYNTAX      AmperageProbeTableEntry
    ACCESS      not-accessible
    STATUS      mandatory
    DESCRIPTION
"0600.0030.0001 This object defines the Amperage Probe Table Entry."
    INDEX       { amperageProbechassisIndex, amperageProbeIndex }
    ::= { amperageProbeTable 1 }
amperageProbechassisIndex                       OBJECT-TYPE
    SYNTAX      DellObjectRange
    ACCESS      read-only
    STATUS      mandatory
    DESCRIPTION
"0600.0030.0001.0001 This attribute defines the index (one based) of the
chassis."
    ::= { amperageProbeTableEntry 1 }
amperageProbeIndex                              OBJECT-TYPE
    SYNTAX      DellObjectRange
    ACCESS      read-only
    STATUS      mandatory
    DESCRIPTION
"0600.0030.0001.0002 This attribute defines the index (one based) of the
amperage probe."
    ::= { amperageProbeTableEntry 2 }
amperageProbeStateCapabilities                  OBJECT-TYPE
    SYNTAX      DellStateCapabilities
    ACCESS      read-only
    STATUS      mandatory
    DESCRIPTION
"0600.0030.0001.0003 This attribute defines the state capabilities of the
amperage probe."
    ::= { amperageProbeTableEntry 3 }
amperageProbeStateSettings                      OBJECT-TYPE
    SYNTAX      DellStateSettings
    ACCESS      read-write
    STATUS      mandatory
    DESCRIPTION
"0600.0030.0001.0004 This attribute defines the state settings of the
amperage probe."
    ::= { amperageProbeTableEntry 4 }
amperageProbeStatus                             OBJECT-TYPE
    SYNTAX      DellStatusProbe
    ACCESS      read-only
    STATUS      mandatory
    DESCRIPTION
"0600.0030.0001.0005 This attribute defines the probe status of the
amperage probe."
    ::= { amperageProbeTableEntry 5 }
amperageProbeReading                            OBJECT-TYPE
    SYNTAX      DellSigned32BitRange
    ACCESS      read-only
    STATUS      mandatory
    DESCRIPTION
"0600.0030.0001.0006 This attribute defines the reading of the amperage
probe.  The value is an integer representing the amperage the probe is reading
in milliamps."
    ::= { amperageProbeTableEntry 6 }
amperageProbeType                               OBJECT-TYPE
    SYNTAX      DellAmperageProbeType
    ACCESS      read-only
    STATUS      mandatory
    DESCRIPTION
"0600.0030.0001.0007 This attribute defines the type of the amperage probe."
    ::= { amperageProbeTableEntry 7 }
amperageProbeLocationName                       OBJECT-TYPE
    SYNTAX      DellString
    ACCESS      read-only
    STATUS      mandatory
    DESCRIPTION
"0600.0030.0001.0008 This attribute defines the location name of the
amperage probe."
    ::= { amperageProbeTableEntry 8 }
amperageProbeUpperNonRecoverableThreshold       OBJECT-TYPE
    SYNTAX      DellSigned32BitRange
    ACCESS      read-only
    STATUS      mandatory
    DESCRIPTION
"0600.0030.0001.0009 This attribute defines the upper nonrecoverable threshold
of the amperage probe.  The value is an integer representing the amperage
of the threshold in milliamps."
    ::= { amperageProbeTableEntry 9 }
amperageProbeUpperCriticalThreshold             OBJECT-TYPE
    SYNTAX      DellSigned32BitRange
    ACCESS      read-only
    STATUS      mandatory
    DESCRIPTION
"0600.0030.0001.0010 This attribute defines the upper critical threshold
of the amperage probe.  The value is an integer representing the amperage
of the threshold in milliamps."
    ::= { amperageProbeTableEntry 10 }
amperageProbeUpperNonCriticalThreshold          OBJECT-TYPE
    SYNTAX      DellSigned32BitRange
    ACCESS      read-write
    STATUS      mandatory
    DESCRIPTION
"0600.0030.0001.0011 This attribute defines the upper noncritical threshold
of the amperage probe.  The value is an integer representing the amperage
of the threshold in milliamps."
    ::= { amperageProbeTableEntry 11 }
amperageProbeLowerNonCriticalThreshold          OBJECT-TYPE
    SYNTAX      DellSigned32BitRange
    ACCESS      read-write
    STATUS      mandatory
    DESCRIPTION
"0600.0030.0001.0012 This attribute defines the lower noncritical threshold
of the amperage probe.  The value is an integer representing the amperage
of the threshold in milliamps."
    ::= { amperageProbeTableEntry 12 }
amperageProbeLowerCriticalThreshold             OBJECT-TYPE
    SYNTAX      DellSigned32BitRange
    ACCESS      read-only
    STATUS      mandatory
    DESCRIPTION
"0600.0030.0001.0013 This attribute defines the lower critical threshold
of the amperage probe.  The value is an integer representing the amperage
of the threshold in milliamps."
    ::= { amperageProbeTableEntry 13 }
amperageProbeLowerNonRecoverableThreshold       OBJECT-TYPE
    SYNTAX      DellSigned32BitRange
    ACCESS      read-only
    STATUS      mandatory
    DESCRIPTION
"0600.0030.0001.0014 This attribute defines the lower nonrecoverable threshold
of the amperage probe.  The value is an integer representing the amperage
of the threshold in milliamps."
    ::= { amperageProbeTableEntry 14 }
amperageProbeProbeCapabilities                  OBJECT-TYPE
    SYNTAX      DellProbeCapabilities
    ACCESS      read-only
    STATUS      mandatory
    DESCRIPTION
"0600.0030.0001.0015 This attribute defines the probe capabilities of the
amperage probe."
    ::= { amperageProbeTableEntry 15 }


-------------------------------------------------------------------------------
-- AC Power Switch Table
-------------------------------------------------------------------------------

DellACPowerSwitchCapabilities           ::= INTEGER {
    -- If set to 0 (zero) the object has no capabilities
    unknownCapabilities(1),             -- The objects capabilities are unknown
    -- The objects capabilities allow it to be set to:
    inputSourceCord1NoReturnCapable(2), -- input source is cord 1, with no return
    inputSourceCord1ReturnCapable(4),   -- input source is cord 1, with return
    inputSourceCord2NoReturnCapable(8), -- input source is cord 2, with no return
    inputSourceCord1NoReturnCord1ReturnAndCord2NoReturnCapable(14),
    inputSourceCord2ReturnCapable(16),  -- input source is cord 2, with return
    inputSourceAllExceptSharedCapable(30),
    inputSourceSharedCapable(32),       -- input source is shared
    inputSourceAllCapable(62)
}
DellACPowerSwitchSettings               ::= INTEGER {
    -- If set to 0 (zero) the object has no settings
    unknown(1),                         -- The objects settings are unknown
	-- The input source settings are mutually-exclusive
    inputSourceCord1NoReturn(2),        -- input source is cord 1, with no return
    inputSourceCord1Return(4),          -- input source is cord 1, with return
    inputSourceCord2NoReturn(8),        -- input source is cord 2, with no return
    inputSourceCord2Return(16),         -- input source is cord 2, with return
    inputSourceShared(32)               -- input source is shared
}
DellACPowerSwitchRedundancyMode         ::= INTEGER {
    nonRedundant(1),                    -- AC power switch not expecting redundancy
    redundant(2)                        -- AC power switch is expecting redundancy
}

ACPowerSwitchTableEntry                 ::= SEQUENCE {
    aCPowerSwitchchassisIndex           DellObjectRange,
    aCPowerSwitchIndex                  DellObjectRange,
    aCPowerSwitchCapabilities           DellACPowerSwitchCapabilities,
    aCPowerSwitchSettings               DellACPowerSwitchSettings,
    aCPowerSwitchRedundancyStatus       DellStatusRedundancy,
    aCPowerCordCountForRedundancy       DellObjectRange,
    aCPowerSwitchName                   DellString,
    aCPowerSwitchRedundancyMode         DellACPowerSwitchRedundancyMode
}

aCPowerSwitchTable                      OBJECT-TYPE
    SYNTAX      SEQUENCE OF ACPowerSwitchTableEntry
    ACCESS      not-accessible
    STATUS      mandatory
    DESCRIPTION
"0600.0040 This Group defines the Dell AC Power Switch Table."
    ::= { powerGroup 40 }
aCPowerSwitchTableEntry                 OBJECT-TYPE
    SYNTAX      ACPowerSwitchTableEntry
    ACCESS      not-accessible
    STATUS      mandatory
    DESCRIPTION
"0600.0040.0001 This Group defines the Dell AC Power Switch Table Entry."
    INDEX       { aCPowerSwitchchassisIndex, aCPowerSwitchIndex }
    ::= { aCPowerSwitchTable 1 }
aCPowerSwitchchassisIndex               OBJECT-TYPE
    SYNTAX      DellObjectRange
    ACCESS      read-only
    STATUS      mandatory
    DESCRIPTION
"0600.0040.0001.0001 This attribute defines the index (one based) of the
chassis containing this Dell AC power switch."
    ::= { aCPowerSwitchTableEntry 1 }
aCPowerSwitchIndex                      OBJECT-TYPE
    SYNTAX      DellObjectRange
    ACCESS      read-only
    STATUS      mandatory
    DESCRIPTION
"0600.0040.0001.0002 This attribute defines the index (one based) of this
Dell AC power switch."
    ::= { aCPowerSwitchTableEntry 2 }
aCPowerSwitchCapabilities               OBJECT-TYPE
    SYNTAX      DellACPowerSwitchCapabilities
    ACCESS      read-only
    STATUS      mandatory
    DESCRIPTION
"0600.0040.0001.0003 This attribute defines the capabilities of this Dell
AC power switch."
    ::= { aCPowerSwitchTableEntry 3 }
aCPowerSwitchSettings                   OBJECT-TYPE
    SYNTAX      DellACPowerSwitchSettings
    ACCESS      read-write
    STATUS      mandatory
    DESCRIPTION
"0600.0040.0001.0004 This attribute defines the settings of this Dell
AC power switch."
    ::= { aCPowerSwitchTableEntry 4 }
aCPowerSwitchRedundancyStatus           OBJECT-TYPE
    SYNTAX      DellStatusRedundancy
    ACCESS      read-only
    STATUS      mandatory
    DESCRIPTION
"0600.0040.0001.0005 This attribute defines the redundancy status of this Dell
AC power switch."
    ::= { aCPowerSwitchTableEntry 5 }
aCPowerCordCountForRedundancy           OBJECT-TYPE
    SYNTAX      DellObjectRange
    ACCESS      read-only
    STATUS      mandatory
    DESCRIPTION
"0600.0040.0001.0006 This attribute defines the total number of Dell AC power
cords required for this Dell AC power switch to have redundancy."
    ::= { aCPowerSwitchTableEntry 6 }
aCPowerSwitchName                       OBJECT-TYPE
    SYNTAX      DellString
    ACCESS      read-only
    STATUS      mandatory
    DESCRIPTION
"0600.0040.0001.0007 This attribute defines the name of this Dell AC power
switch."
    ::= { aCPowerSwitchTableEntry 7 }
aCPowerSwitchRedundancyMode             OBJECT-TYPE
    SYNTAX      DellACPowerSwitchRedundancyMode
    ACCESS      read-write
    STATUS      mandatory
    DESCRIPTION
"0600.0040.0001.0008 This attribute defines the redundancy mode of this Dell
AC power switch."
    ::= { aCPowerSwitchTableEntry 8 }


-------------------------------------------------------------------------------
-- AC Power Cord Table
-------------------------------------------------------------------------------

DellACPowerCordStateCapabilities        ::= INTEGER {
    unknown(1),                         -- The objects capabilities are unknown
    -- The objects capabilities allow it to be set to:
    enableCapable(2),                   -- be disabled (offline) or be enabled (online)
    notReadyCapable(4)                  -- not ready
}
DellACPowerCordStateSettings            ::= INTEGER {
    unknown(1),                         -- The objects state is unknown
    enabled(2),                         -- The objects state is disabled (offline) 0, or enabled (online) 1
    notReady(4),                        -- The objects state is not ready
    acPowerCordHasPower(8),             -- AC power cord has power
    acPowerCordIsEnabledAndHasPower(10),
    acPowerCordIsActiveSource(16),      -- AC power cord is active source of AC power
    acPowerCordIsEnabledHasPowerAndIsActiveSource(26)
}

ACPowerCordTableEntry                   ::= SEQUENCE {
    aCPowerCordchassisIndex             DellObjectRange,
    aCPowerCordIndex                    DellObjectRange,
    aCPowerCordStateCapabilities        DellACPowerCordStateCapabilities,
    aCPowerCordStateSettings            DellACPowerCordStateSettings,
    aCPowerCordStatus                   DellStatus,
    aCPowerCordaCPowerSwitchIndexReference DellObjectRange,
    aCPowerCordLocationName             DellString
}

aCPowerCordTable                        OBJECT-TYPE
    SYNTAX      SEQUENCE OF ACPowerCordTableEntry
    ACCESS      not-accessible
    STATUS      mandatory
    DESCRIPTION
"0600.0042 This Group defines the Dell AC Power Cord Table."
    ::= { powerGroup 42 }
aCPowerCordTableEntry                   OBJECT-TYPE
    SYNTAX      ACPowerCordTableEntry
    ACCESS      not-accessible
    STATUS      mandatory
    DESCRIPTION
"0600.0042.0001 This Group defines the Dell AC Power Cord Table Entry."
    INDEX       { aCPowerCordchassisIndex, aCPowerCordIndex }
    ::= { aCPowerCordTable 1 }
aCPowerCordchassisIndex                 OBJECT-TYPE
    SYNTAX      DellObjectRange
    ACCESS      read-only
    STATUS      mandatory
    DESCRIPTION
"0600.0042.0001.0001 This attribute defines the index (one based) of the
chassis containing this Dell AC power cord."
    ::= { aCPowerCordTableEntry 1 }
aCPowerCordIndex                        OBJECT-TYPE
    SYNTAX      DellObjectRange
    ACCESS      read-only
    STATUS      mandatory
    DESCRIPTION
"0600.0042.0001.0002 This attribute defines the index (one based) of this
Dell AC power cord."
    ::= { aCPowerCordTableEntry 2 }
aCPowerCordStateCapabilities            OBJECT-TYPE
    SYNTAX      DellACPowerCordStateCapabilities
    ACCESS      read-only
    STATUS      mandatory
    DESCRIPTION
"0600.0042.0001.0003 This attribute defines the capabilities of this Dell
AC power cord."
    ::= { aCPowerCordTableEntry 3 }
aCPowerCordStateSettings                OBJECT-TYPE
    SYNTAX      DellACPowerCordStateSettings
    ACCESS      read-write
    STATUS      mandatory
    DESCRIPTION
"0600.0042.0001.0004 This attribute defines the state of this Dell AC power
cord."
    ::= { aCPowerCordTableEntry 4 }
aCPowerCordStatus                       OBJECT-TYPE
    SYNTAX      DellStatus
    ACCESS      read-only
    STATUS      mandatory
    DESCRIPTION
"0600.0042.0001.0005 This attribute defines the status of this Dell AC power
cord."
    ::= { aCPowerCordTableEntry 5 }
aCPowerCordaCPowerSwitchIndexReference  OBJECT-TYPE
    SYNTAX      DellObjectRange
    ACCESS      read-only
    STATUS      mandatory
    DESCRIPTION
"0600.0042.0001.0006 This attribute defines the index (one based) to the
associated Dell AC power switch for this Dell AC power cord."
    ::= { aCPowerCordTableEntry 6 }
aCPowerCordLocationName                 OBJECT-TYPE
    SYNTAX      DellString
    ACCESS      read-only
    STATUS      mandatory
    DESCRIPTION
"0600.0042.0001.0007 This attribute defines the location name of this Dell
AC power cord."
    ::= { aCPowerCordTableEntry 7 }


-------------------------------------------------------------------------------
--
-- Thermal Group
--
-------------------------------------------------------------------------------

-------------------------------------------------------------------------------
-- Cooling Unit Table
-------------------------------------------------------------------------------

CoolingUnitTableEntry                           ::= SEQUENCE {
    coolingUnitchassisIndex                     DellObjectRange,
    coolingUnitIndex                            DellObjectRange,
    coolingUnitStateCapabilties                 DellStateCapabilities,
    coolingUnitStateSettings                    DellStateSettings,
    coolingUnitRedundancyStatus                 DellStatusRedundancy,
    coolingDeviceCountForRedundancy             DellObjectRange,
    coolingUnitName                             DellString
}

coolingUnitTable                                OBJECT-TYPE
    SYNTAX      SEQUENCE OF CoolingUnitTableEntry
    ACCESS      not-accessible
    STATUS      mandatory
    DESCRIPTION
"0700.0010 This object defines the Cooling Unit Table."
    ::= { thermalGroup 10 }
coolingUnitTableEntry                           OBJECT-TYPE
    SYNTAX      CoolingUnitTableEntry
    ACCESS      not-accessible
    STATUS      mandatory
    DESCRIPTION
"0700.0010.0001 This object defines the Cooling Unit Table Entry."
    INDEX       { coolingUnitchassisIndex, coolingUnitIndex }
    ::= { coolingUnitTable 1 }
coolingUnitchassisIndex                         OBJECT-TYPE
    SYNTAX      DellObjectRange
    ACCESS      read-only
    STATUS      mandatory
    DESCRIPTION
"0700.0010.0001.0001 This attribute defines the index (one based) of the
chassis."
    ::= { coolingUnitTableEntry 1 }
coolingUnitIndex                                OBJECT-TYPE
    SYNTAX      DellObjectRange
    ACCESS      read-only
    STATUS      mandatory
    DESCRIPTION
"0700.0010.0001.0002 This attribute defines the index (one based) of the
cooling unit."
    ::= { coolingUnitTableEntry 2 }
coolingUnitStateCapabilties                     OBJECT-TYPE
    SYNTAX      DellStateCapabilities
    ACCESS      read-only
    STATUS      mandatory
    DESCRIPTION
"0700.0010.0001.0003 This attribute defines the state capabilities of the
cooling unit."
    ::= { coolingUnitTableEntry 3 }
coolingUnitStateSettings                        OBJECT-TYPE
    SYNTAX      DellStateSettings
    ACCESS      read-write
    STATUS      mandatory
    DESCRIPTION
"0700.0010.0001.0004 This attribute defines the state settings of the
cooling unit."
    ::= { coolingUnitTableEntry 4 }
coolingUnitRedundancyStatus                     OBJECT-TYPE
    SYNTAX      DellStatusRedundancy
    ACCESS      read-only
    STATUS      mandatory
    DESCRIPTION
"0700.0010.0001.0005 This attribute defines the redundancy status of the
cooling unit."
    ::= { coolingUnitTableEntry 5 }
coolingDeviceCountForRedundancy                 OBJECT-TYPE
    SYNTAX      DellObjectRange
    ACCESS      read-only
    STATUS      mandatory
    DESCRIPTION
"0700.0010.0001.0006 This attribute defines the total number of cooling devices
required for this cooling unit to have redundancy."
    ::= { coolingUnitTableEntry 6 }
coolingUnitName                                 OBJECT-TYPE
    SYNTAX      DellString
    ACCESS      read-only
    STATUS      mandatory
    DESCRIPTION
"0700.0010.0001.0007 This attribute defines the name of the cooling unit."
    ::= { coolingUnitTableEntry 7 }


-------------------------------------------------------------------------------
-- Cooling Device Table
-------------------------------------------------------------------------------

DellCoolingDeviceType                           ::= INTEGER {
    coolingDeviceTypeIsOther(1),                -- type is not one of the following types:
    coolingDeviceTypeIsUnknown(2),              -- type of the object is unknown (not known or monitored)
    coolingDeviceTypeIsAFan(3),                 -- type is a fan
    coolingDeviceTypeIsABlower(4),              -- type is a centrifugal blower
    coolingDeviceTypeIsAChipFan(5),             -- type is a fan on an integrated circuit
    coolingDeviceTypeIsACabinetFan(6),          -- type is a cabinet fan
    coolingDeviceTypeIsAPowerSupplyFan(7),      -- type is a power supply fan
    coolingDeviceTypeIsAHeatPipe(8),            -- type is a heat pipe
    coolingDeviceTypeIsRefrigeration(9),        -- type is an integrated refrigeration unit
    coolingDeviceTypeIsActiveCooling(10),       -- type is an active cooling device
    coolingDeviceTypeIsPassiveCooling(11)       -- type is a passive cooling device
}
DellCoolingDeviceSubType    ::= INTEGER {
    coolingDeviceSubTypeIsOther(1),                          -- the subtype is not one of the following types:
    coolingDeviceSubTypeIsUnknown(2),                        -- the subtype is unknown (not known or monitored)
    coolingDeviceSubTypeIsAFanThatReadsInRPM(3),             -- the fan reads in RPM
    coolingDeviceSubTypeIsAFanReadsONorOFF(4),               -- the fan reads 0/1 (off/on)
    coolingDeviceSubTypeIsAPowerSupplyFanThatReadsinRPM(5),  -- the power supply fan reads in RPM
    coolingDeviceSubTypeIsAPowerSupplyFanThatReadsONorOFF(6) -- the power supply fan reads 0/1 (off/on)
}

CoolingDeviceTableEntry                         ::= SEQUENCE {
    coolingDevicechassisIndex                   DellObjectRange,
    coolingDeviceIndex                          DellObjectRange,
    coolingDeviceStateCapabilities              DellStateCapabilities,
    coolingDeviceStateSettings                  DellStateSettings,
    coolingDeviceStatus                         DellStatusProbe,
    coolingDeviceReading                        DellSigned32BitRange,
    coolingDeviceType                           DellCoolingDeviceType,
    coolingDeviceLocationName                   DellString,
    coolingDeviceUpperNonRecoverableThreshold   DellSigned32BitRange,
    coolingDeviceUpperCriticalThreshold         DellSigned32BitRange,
    coolingDeviceUpperNonCriticalThreshold      DellSigned32BitRange,
    coolingDeviceLowerNonCriticalThreshold      DellSigned32BitRange,
    coolingDeviceLowerCriticalThreshold         DellSigned32BitRange,
    coolingDeviceLowerNonRecoverableThreshold   DellSigned32BitRange,
    coolingDevicecoolingUnitIndexReference      DellObjectRange,
    coolingDeviceSubType                        DellCoolingDeviceSubType,
	coolingDeviceProbeCapabilities              DellProbeCapabilities
}

coolingDeviceTable                              OBJECT-TYPE
    SYNTAX      SEQUENCE OF CoolingDeviceTableEntry
    ACCESS      not-accessible
    STATUS      mandatory
    DESCRIPTION
"0700.0012 This object defines the Cooling Device Table."
    ::= {  thermalGroup 12 }
coolingDeviceTableEntry                         OBJECT-TYPE
    SYNTAX      CoolingDeviceTableEntry
    ACCESS      not-accessible
    STATUS      mandatory
    DESCRIPTION
"0700.0012.0001 This object defines the Cooling Device Table Entry."
    INDEX       { coolingDevicechassisIndex, coolingDeviceIndex }
    ::= { coolingDeviceTable 1 }
coolingDevicechassisIndex                       OBJECT-TYPE
    SYNTAX      DellObjectRange
    ACCESS      read-only
    STATUS      mandatory
    DESCRIPTION
"0700.0012.0001.0001 This attribute defines the index (one based) of the
chassis."
    ::= { coolingDeviceTableEntry 1 }
coolingDeviceIndex                              OBJECT-TYPE
    SYNTAX      DellObjectRange
    ACCESS      read-only
    STATUS      mandatory
    DESCRIPTION
"0700.0012.0001.0002 This attribute defines the index (one based) of the
cooling device."
    ::= { coolingDeviceTableEntry 2 }
coolingDeviceStateCapabilities                  OBJECT-TYPE
    SYNTAX      DellStateCapabilities
    ACCESS      read-only
    STATUS      mandatory
    DESCRIPTION
"0700.0012.0001.0003 This attribute defines the state capabilities of the
cooling device."
    ::= { coolingDeviceTableEntry 3 }
coolingDeviceStateSettings                      OBJECT-TYPE
    SYNTAX      DellStateSettings
    ACCESS      read-write
    STATUS      mandatory
    DESCRIPTION
"0700.0012.0001.0004 This attribute defines the state settings of the
cooling device."
    ::= { coolingDeviceTableEntry 4 }
coolingDeviceStatus                             OBJECT-TYPE
    SYNTAX      DellStatusProbe
    ACCESS      read-only
    STATUS      mandatory
    DESCRIPTION
"0700.0012.0001.0005 This attribute defines the probe status of the
cooling device."
    ::= { coolingDeviceTableEntry 5 }
coolingDeviceReading                            OBJECT-TYPE
    SYNTAX      DellSigned32BitRange
    ACCESS      read-only
    STATUS      mandatory
    DESCRIPTION
"0700.0012.0001.0006 This attribute defines the speed in RPM or the
OFF/ON value of the cooling device."
    ::= { coolingDeviceTableEntry 6 }
coolingDeviceType                               OBJECT-TYPE
    SYNTAX      DellCoolingDeviceType
    ACCESS      read-only
    STATUS      mandatory
    DESCRIPTION
"0700.0012.0001.0007 This attribute defines the type of the cooling device."
    ::= { coolingDeviceTableEntry 7 }
coolingDeviceLocationName                       OBJECT-TYPE
    SYNTAX      DellString
    ACCESS      read-only
    STATUS      mandatory
    DESCRIPTION
"0700.0012.0001.0008 This attribute defines the location name of the
cooling device."
    ::= { coolingDeviceTableEntry 8 }
coolingDeviceUpperNonRecoverableThreshold       OBJECT-TYPE
    SYNTAX      DellSigned32BitRange
    ACCESS      read-only
    STATUS      mandatory
    DESCRIPTION
"0700.0012.0001.0009 This attribute defines the upper nonrecoverable threshold
of the cooling device.  The value is an integer representing fan speed
in revolutions per minute (RPM).  It is not applicable to OFF/ON type
cooling devices or non-cooling device types."
    ::= { coolingDeviceTableEntry 9 }
coolingDeviceUpperCriticalThreshold             OBJECT-TYPE
    SYNTAX      DellSigned32BitRange
    ACCESS      read-only
    STATUS      mandatory
    DESCRIPTION
"0700.0012.0001.0010 This attribute defines the upper critical threshold
of the cooling device.  The value is an integer representing fan speed
in revolutions per minute (RPM).  It is not applicable to OFF/ON type
cooling devices or non-cooling device types."
    ::= { coolingDeviceTableEntry 10 }
coolingDeviceUpperNonCriticalThreshold          OBJECT-TYPE
    SYNTAX      DellSigned32BitRange
    ACCESS      read-write
    STATUS      mandatory
    DESCRIPTION
"0700.0012.0001.0011 This attribute defines the upper noncritical threshold
of the cooling device.  The value is an integer representing fan speed
in revolutions per minute (RPM).  It is not applicable to OFF/ON type
cooling devices or non-cooling device types."
    ::= { coolingDeviceTableEntry 11 }
coolingDeviceLowerNonCriticalThreshold          OBJECT-TYPE
    SYNTAX      DellSigned32BitRange
    ACCESS      read-write
    STATUS      mandatory
    DESCRIPTION
"0700.0012.0001.0012 This attribute defines the lower noncritical threshold
of the cooling device.  The value is an integer representing fan speed
in revolutions per minute (RPM).  It is not applicable to OFF/ON type
cooling devices or non-cooling device types."
    ::= { coolingDeviceTableEntry 12 }
coolingDeviceLowerCriticalThreshold             OBJECT-TYPE
    SYNTAX      DellSigned32BitRange
    ACCESS      read-only
    STATUS      mandatory
    DESCRIPTION
"0700.0012.0001.0013 This attribute defines the lower critical threshold
of the cooling device.  The value is an integer representing fan speed
in revolutions per minute (RPM).  It is not applicable to OFF/ON type
cooling devices or non-cooling device types."
    ::= { coolingDeviceTableEntry 13 }
coolingDeviceLowerNonRecoverableThreshold       OBJECT-TYPE
    SYNTAX      DellSigned32BitRange
    ACCESS      read-only
    STATUS      mandatory
    DESCRIPTION
"0700.0012.0001.0014 This attribute defines the lower nonrecoverable threshold
of the cooling device.  The value is an integer representing fan speed
in revolutions per minute (RPM).  It is not applicable to OFF/ON type
cooling devices or non-cooling device types."
    ::= { coolingDeviceTableEntry 14 }
coolingDevicecoolingUnitIndexReference          OBJECT-TYPE
    SYNTAX      DellObjectRange
    ACCESS      read-only
    STATUS      mandatory
    DESCRIPTION
"0700.0012.0001.0015 This attribute defines the index to the associated
cooling unit."
    ::= { coolingDeviceTableEntry 15 }
coolingDeviceSubType                            OBJECT-TYPE
    SYNTAX      DellCoolingDeviceSubType
    ACCESS      read-only
    STATUS      mandatory
    DESCRIPTION
"0700.0012.0001.0016 This attribute defines the subtype of the cooling device."
    ::= { coolingDeviceTableEntry 16 }
coolingDeviceProbeCapabilities                  OBJECT-TYPE
    SYNTAX      DellProbeCapabilities
    ACCESS      read-only
    STATUS      mandatory
    DESCRIPTION
"0700.0012.0001.0017 This attribute defines the probe capabilities of the
cooling device."
    ::= { coolingDeviceTableEntry 17 }


-------------------------------------------------------------------------------
-- Temperature Probe Table
-------------------------------------------------------------------------------

DellTemperatureProbeType                        ::= INTEGER {
    temperatureProbeTypeIsOther(1),             -- type is not one of the following types:
    temperatureProbeTypeIsUnknown(2),           -- type is unknown (not known or monitored)
    temperatureProbeTypeIsAmbientESM(3)         -- type is Ambient Embedded Systems Management temperature probe
}

TemperatureProbeTableEntry                      ::= SEQUENCE {
    temperatureProbechassisIndex                DellObjectRange,
    temperatureProbeIndex                       DellObjectRange,
    temperatureProbeStateCapabilities           DellStateCapabilities,
    temperatureProbeStateSettings               DellStateSettings,
    temperatureProbeStatus                      DellStatusProbe,
    temperatureProbeReading                     DellSigned32BitRange,
    temperatureProbeType                        DellTemperatureProbeType,
    temperatureProbeLocationName                DellString,
    temperatureProbeUpperNonRecoverableThreshold DellSigned32BitRange,
    temperatureProbeUpperCriticalThreshold      DellSigned32BitRange,
    temperatureProbeUpperNonCriticalThreshold   DellSigned32BitRange,
    temperatureProbeLowerNonCriticalThreshold   DellSigned32BitRange,
    temperatureProbeLowerCriticalThreshold      DellSigned32BitRange,
    temperatureProbeLowerNonRecoverableThreshold DellSigned32BitRange,
	temperatureProbeProbeCapabilities           DellProbeCapabilities
}

temperatureProbeTable                           OBJECT-TYPE
    SYNTAX      SEQUENCE OF TemperatureProbeTableEntry
    ACCESS      not-accessible
    STATUS      mandatory
    DESCRIPTION
"0700.0020 This object defines the Temperature Probe Table."
    ::= { thermalGroup 20 }
temperatureProbeTableEntry                      OBJECT-TYPE
    SYNTAX      TemperatureProbeTableEntry
    ACCESS      not-accessible
    STATUS      mandatory
    DESCRIPTION
"0700.0020.0001 This object defines the Temperature Probe Table Entry."
    INDEX       { temperatureProbechassisIndex, temperatureProbeIndex }
    ::= { temperatureProbeTable 1 }
temperatureProbechassisIndex                    OBJECT-TYPE
    SYNTAX      DellObjectRange
    ACCESS      read-only
    STATUS      mandatory
    DESCRIPTION
"0700.0020.0001.0001 This attribute defines the index (one based) of the
chassis."
    ::= { temperatureProbeTableEntry 1 }
temperatureProbeIndex                           OBJECT-TYPE
    SYNTAX      DellObjectRange
    ACCESS      read-only
    STATUS      mandatory
    DESCRIPTION
"0700.0020.0001.0002 This attribute defines the index (one based) of the
temperature probe."
    ::= { temperatureProbeTableEntry 2 }
temperatureProbeStateCapabilities               OBJECT-TYPE
    SYNTAX      DellStateCapabilities
    ACCESS      read-only
    STATUS      mandatory
    DESCRIPTION
"0700.0020.0001.0003 This attribute defines the state capabilities of the
temperature probe."
    ::= { temperatureProbeTableEntry 3 }
temperatureProbeStateSettings                   OBJECT-TYPE
    SYNTAX      DellStateSettings
    ACCESS      read-write
    STATUS      mandatory
    DESCRIPTION
"0700.0020.0001.0004 This attribute defines the state settings of the
temperature probe."
    ::= { temperatureProbeTableEntry 4 }
temperatureProbeStatus                          OBJECT-TYPE
    SYNTAX      DellStatusProbe
    ACCESS      read-only
    STATUS      mandatory
    DESCRIPTION
"0700.0020.0001.0005 This attribute defines the probe status of the
temperature probe."
    ::= { temperatureProbeTableEntry 5 }
temperatureProbeReading                         OBJECT-TYPE
    SYNTAX      DellSigned32BitRange
    ACCESS      read-only
    STATUS      mandatory
    DESCRIPTION
"0700.0020.0001.0006 This attribute defines the reading of the temperature
probe.  The value is an integer representing temperature in tenths of
degrees Centigrade."
    ::= { temperatureProbeTableEntry 6 }
temperatureProbeType                            OBJECT-TYPE
    SYNTAX      DellTemperatureProbeType
    ACCESS      read-only
    STATUS      mandatory
    DESCRIPTION
"0700.0020.0001.0007 This attribute defines the type of the temperature probe."
    ::= { temperatureProbeTableEntry 7 }
temperatureProbeLocationName                    OBJECT-TYPE
    SYNTAX      DellString
    ACCESS      read-only
    STATUS      mandatory
    DESCRIPTION
"0700.0020.0001.0008 This attribute defines the location name of the
temperature probe."
    ::= { temperatureProbeTableEntry 8 }
temperatureProbeUpperNonRecoverableThreshold    OBJECT-TYPE
    SYNTAX      DellSigned32BitRange
    ACCESS      read-only
    STATUS      mandatory
    DESCRIPTION
"0700.0020.0001.0009 This attribute defines the upper nonrecoverable threshold
of the temperature probe.  The value is an integer representing the temperature
of the threshold in tenths of degrees Centigrade."
    ::= { temperatureProbeTableEntry 9 }
temperatureProbeUpperCriticalThreshold          OBJECT-TYPE
    SYNTAX      DellSigned32BitRange
    ACCESS      read-only
    STATUS      mandatory
    DESCRIPTION
"0700.0020.0001.0010 This attribute defines the upper critical threshold
of the temperature probe.  The value is an integer representing the temperature
of the threshold in tenths of degrees Centigrade."
    ::= { temperatureProbeTableEntry 10 }
temperatureProbeUpperNonCriticalThreshold       OBJECT-TYPE
    SYNTAX      DellSigned32BitRange
    ACCESS      read-write
    STATUS      mandatory
    DESCRIPTION
"0700.0020.0001.0011 This attribute defines the upper noncritical threshold
of the temperature probe.  The value is an integer representing the temperature
of the threshold in tenths of degrees Centigrade."
    ::= { temperatureProbeTableEntry 11 }
temperatureProbeLowerNonCriticalThreshold       OBJECT-TYPE
    SYNTAX      DellSigned32BitRange
    ACCESS      read-write
    STATUS      mandatory
    DESCRIPTION
"0700.0020.0001.0012 This attribute defines the lower noncritical threshold
of the temperature probe.  The value is an integer representing the temperature
of the threshold in tenths of degrees Centigrade."
    ::= { temperatureProbeTableEntry 12 }
temperatureProbeLowerCriticalThreshold          OBJECT-TYPE
    SYNTAX      DellSigned32BitRange
    ACCESS      read-only
    STATUS      mandatory
    DESCRIPTION
"0700.0020.0001.0013 This attribute defines the lower critical threshold
of the temperature probe.  The value is an integer representing the temperature
of the threshold in tenths of degrees Centigrade."
    ::= { temperatureProbeTableEntry 13 }
temperatureProbeLowerNonRecoverableThreshold    OBJECT-TYPE
    SYNTAX      DellSigned32BitRange
    ACCESS      read-only
    STATUS      mandatory
    DESCRIPTION
"0700.0020.0001.0014 This attribute defines the lower nonrecoverable threshold
of the temperature probe.  The value is an integer representing the temperature
of the threshold in tenths of degrees Centigrade."
    ::= { temperatureProbeTableEntry 14 }
temperatureProbeProbeCapabilities               OBJECT-TYPE
    SYNTAX      DellProbeCapabilities
    ACCESS      read-only
    STATUS      mandatory
    DESCRIPTION
"0700.0020.0001.0015 This attribute defines the probe capabilities of the
temperature probe."
    ::= { temperatureProbeTableEntry 15 }


-------------------------------------------------------------------------------
--
-- User Security Group
--
-------------------------------------------------------------------------------

-------------------------------------------------------------------------------
-- User Security Table
-------------------------------------------------------------------------------

UserSecurityTableEntry              ::= SEQUENCE {
    userSecuritychassisIndex        DellObjectRange,
    userSecurityIndex               DellObjectRange,
    userSecurityUserName            DellSecurityString,
    userSecurityControlName         DellSecurityString,
    userSecurityRequestName         DellSecurityString
}

userSecurityTable                   OBJECT-TYPE
    SYNTAX      SEQUENCE OF UserSecurityTableEntry
    ACCESS      not-accessible
    STATUS      mandatory
    DESCRIPTION
"0800.0010 This table contains the database of users that are authorized
to perform Set operations on a managed Dell system."
    ::= { userSecurityGroup 10 }
userSecurityTableEntry              OBJECT-TYPE
    SYNTAX      UserSecurityTableEntry
    ACCESS      not-accessible
    STATUS      mandatory
    DESCRIPTION
"0800.0010.0001 A row in the user table."
    INDEX       { userSecuritychassisIndex, userSecurityIndex }
    ::= { userSecurityTable 1 }
userSecuritychassisIndex            OBJECT-TYPE
    SYNTAX      DellObjectRange
    ACCESS      read-only
    STATUS      mandatory
    DESCRIPTION
"0800.0010.0001.0001 Chassis index."
    ::= { userSecurityTableEntry 1 }
userSecurityIndex                   OBJECT-TYPE
    SYNTAX      DellObjectRange
    ACCESS      read-only
    STATUS      mandatory
    DESCRIPTION
"0800.0010.0001.0002 User index."
    ::= { userSecurityTableEntry 2 }
userSecurityUserName                OBJECT-TYPE
    SYNTAX      DellSecurityString
    ACCESS      read-only
    STATUS      mandatory
    DESCRIPTION
"0800.0010.0001.0003 User name."
    ::= { userSecurityTableEntry 3 }
userSecurityControlName             OBJECT-TYPE
    SYNTAX      DellSecurityString
    ACCESS      read-write
    STATUS      mandatory
    DESCRIPTION
"0800.0010.0001.0004 User control.  Used for creating/deleting/editing users."
    ::= { userSecurityTableEntry 4 }
userSecurityRequestName             OBJECT-TYPE
    SYNTAX      DellSecurityString
    ACCESS      read-write
    STATUS      mandatory
    DESCRIPTION
"0800.0010.0001.0005 Set request control.  Used for Set operations."
    ::= { userSecurityTableEntry 5 }


-------------------------------------------------------------------------------
--
-- Remote Flash BIOS Group
--
-------------------------------------------------------------------------------

-------------------------------------------------------------------------------
-- Remote Flash BIOS Table
-------------------------------------------------------------------------------

DellRemoteFlashBIOSStateCapabilitiesUnique ::= INTEGER {
    unknown(1),                   -- The objects capabilities are unknown
    -- The objects capabilities allow it to be set to:
    enableCapable(2),             -- be disabled (offline) or be enabled (online)
    notReadyCapable(4),           -- not ready
    cancelCapable(8),             -- Flash of BIOS is canceled
    enableAndCancelCapable(10)    -- Flash of BIOS eanbled or canceled
}
DellRemoteFlashBIOSStateSettingsUnique ::= INTEGER {
    unknown(1),   -- The objects state is unknown
    enabled(2),   -- Flash BIOS update is disabled (0) or enabled (1)
    notReady(4),  -- The objects state is not ready
    canceled(8),  -- Flash of BIOS has been canceled
    pending(16),  -- This system remote flash BIOS update is pending
    other(32)     -- The state/setting of the object is not one of the previous
}
DellRemoteFlashBIOSCompletionCode          ::= INTEGER {
    completionCodeIsOther(1),              -- the status of the object is not one of the following:
    completionCodeIsUnknown(2),            -- the completion code is unknown (not known or monitored)
    completionCodeIsOK(3),                 -- This completion code is completed successfully
    completionCodeIsBadImage(4),           -- This completion code is bad flash BIOS image
    completionCodeIsNoFileAccess(5),       -- This completion code is flash bios could not be accessed
    completionCodeIsNotReady(6),           -- This completion code is flash bios memory not ready
    completionCodeIsDisabled(7),           -- This completion code is flash bios is currently disabled
    completionCodeIsNoBattery(8),          -- This completion code is a battery must be installed
    completionCodeIsNoChargedBattery(9),   -- This completion code is a fully charged battery must be installed
    completionCodeIsNoExternalPower(10),   -- This completion code is an external power adapter must be connected
    completionCodeIsNo12VoltSet(11),       -- This completion code is that 12 Volts could not be set
    completionCodeIsNo12VoltRemoval(12),   -- This completion code is that 12 Volts could not be removed
    completionCodeIsFlashMemoryFailed(13), -- This completion code is a flash memory failure occured
    completionCodeIsGeneralFailure(14),    -- This completion code is a general failure occurred
    completionCodeIsDataMiscompare(15),    -- This completion code is a data miscompare error occurred
    completionCodeIsNoImageFound(16),      -- This completion code is flash bios image could not be found in memory
    completionCodeIsNoUpdatePerformed(17)  -- This completion code is no update operation has been performed
}

RemoteFlashBIOSTableEntry                    ::= SEQUENCE {
    remoteFlashBIOSchassisIndex              DellObjectRange,
    remoteFlashBIOSIndex                     DellObjectRange,
    remoteFlashBIOSStateCapabilitiesUnique   DellRemoteFlashBIOSStateCapabilitiesUnique,
    remoteFlashBIOSStateSettingsUnique       DellRemoteFlashBIOSStateSettingsUnique,
    remoteFlashBIOSStatus                    DellStatus,
    remoteFlashBIOSLastBIOSDateName          DellDateName,
    remoteFlashBIOSCompletionCode            DellRemoteFlashBIOSCompletionCode,
    remoteFlashBIOSMinimumContiguousMemory   DellUnsigned32BitRange
}

remoteFlashBIOSTable               OBJECT-TYPE
    SYNTAX      SEQUENCE OF RemoteFlashBIOSTableEntry
    ACCESS      not-accessible
    STATUS      mandatory
    DESCRIPTION
"0900.0010 This Table defines the settings for Dell Remote BIOS updates."
    ::= { remoteFlashBIOSGroup 10 }
remoteFlashBIOSTableEntry          OBJECT-TYPE
    SYNTAX      RemoteFlashBIOSTableEntry
    ACCESS      not-accessible
    STATUS      mandatory
    DESCRIPTION
"0900.0010.0001 This Group defines the Dell Remote Flash BIOS Table Entry."
    INDEX       { remoteFlashBIOSchassisIndex, remoteFlashBIOSIndex }
    ::= { remoteFlashBIOSTable 1 }
remoteFlashBIOSchassisIndex                 OBJECT-TYPE
    SYNTAX      DellObjectRange
    ACCESS      read-only
    STATUS      mandatory
    DESCRIPTION
"0900.0010.0001.0001 This attribute defines the index (one based) of
this Dell chassis."
    ::= { remoteFlashBIOSTableEntry 1 }
remoteFlashBIOSIndex                         OBJECT-TYPE
    SYNTAX      DellObjectRange
    ACCESS      read-only
    STATUS      mandatory
    DESCRIPTION
"0900.0010.0001.0002 This attribute defines the index to the Dell Remote
BIOS update hardware on this Dell System."
    ::= { remoteFlashBIOSTableEntry 2 }
remoteFlashBIOSStateCapabilitiesUnique OBJECT-TYPE
    SYNTAX      DellRemoteFlashBIOSStateCapabilitiesUnique
    ACCESS      read-only
    STATUS      mandatory
    DESCRIPTION
"0900.0010.0001.0003 This attribute defines the capabilities of the Dell Remote
BIOS update on this Dell System."
    ::= { remoteFlashBIOSTableEntry 3 }
remoteFlashBIOSStateSettingsUnique OBJECT-TYPE
    SYNTAX      DellRemoteFlashBIOSStateSettingsUnique
    ACCESS      read-write
    STATUS      mandatory
    DESCRIPTION
"0900.0010.0001.0004 This attribute defines the state of the Dell Remote
BIOS update on this Dell System."
    ::= { remoteFlashBIOSTableEntry 4 }
remoteFlashBIOSStatus               OBJECT-TYPE
    SYNTAX      DellStatus
    ACCESS      read-only
    STATUS      mandatory
    DESCRIPTION
"0900.0010.0001.0005 This attribute defines the status of the Dell Remote
BIOS update on this Dell System."
    ::= { remoteFlashBIOSTableEntry 5 }
remoteFlashBIOSLastBIOSDateName    OBJECT-TYPE
    SYNTAX      DellDateName
    ACCESS      read-only
    STATUS      mandatory
    DESCRIPTION
"0900.0010.0001.0006 This attribute defines the date of last BIOS update.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { remoteFlashBIOSTableEntry 6 }
remoteFlashBIOSCompletionCode      OBJECT-TYPE
    SYNTAX      DellRemoteFlashBIOSCompletionCode
    ACCESS      read-only
    STATUS      mandatory
    DESCRIPTION
"0900.0010.0001.0007 This attribute defines the completion code of the
last BIOS update."
    ::= { remoteFlashBIOSTableEntry 7 }
remoteFlashBIOSMinimumContiguousMemory        OBJECT-TYPE
    SYNTAX      DellUnsigned32BitRange
    ACCESS      read-only
    STATUS      mandatory
    DESCRIPTION
"0900.0010.0001.0008 This attribute defines the minimum size of contiguous
memory required for remote BIOS update in kilobytes."
    ::= { remoteFlashBIOSTableEntry 8 }


-------------------------------------------------------------------------------
--
-- Port Group
--
-------------------------------------------------------------------------------

DellGenericPortConnectorType                 ::= INTEGER {
    portConnectorTypeIsOther(1),             -- there is not one of the following:
    portConnectorTypeIsNone(2),              -- there is no port connector
    portConnectorTypeIsCentronics(3),        -- the type of port connector is a Centronics,     IEEE1284-B Receptical
    portConnectorTypeIsMiniCentronics(4),    -- the type of port connector is a miniCentronics, IEEE1284-C Receptical
    portConnectorTypeIsProprietary(5),       -- the type of port connector is proprietary
    portConnectorTypeIsDB25Male(6),          -- the type of port connector is a male   DB-25,   IEEE1284-A Plug
    portConnectorTypeIsDB25Female(7),        -- the type of port connector is a female DB-25,   IEEE1284-A Receptical
    portConnectorTypeIsDB15Male(8),          -- the type of port connector is a male   DB-15
    portConnectorTypeIsDB15Female(9),        -- the type of port connector is a female DB-15
    portConnectorTypeIsDB9Male(10),          -- the type of port connector is a male   DB-9
    portConnectorTypeIsDB9Female(11),        -- the type of port connector is a female DB-9
    portConnectorTypeIsRJ11(12),             -- the type of port connector is an RJ-11
    portConnectorTypeIsRJ45(13),             -- the type of port connector is an RJ-45
    portConnectorTypeIsMiniSCSI50Pin(14),    -- the type of port connector is a 50 pin miniSCSI
    portConnectorTypeIsMiniDIN(15),          -- the type of port connector is a mini DIN
    portConnectorTypeIsMicroDIN(16),         -- the type of port connector is a micro DIN
    portConnectorTypeIsPS2(17),              -- the type of port connector is a PS/2
    portConnectorTypeIsInfrared(18),         -- the type of port connector is infrared
    portConnectorTypeIsHPHIL(19),            -- the type of port connector is HP-HIL
    portConnectorTypeIsAccessBussUSB(20),    -- the type of port connector is Access Bus USB
    portConnectorTypeISSASCSI(21),           -- the type of port connector is SSA SCSI
    portConnectorTypeIsCirdin8Male(22),      -- the type of port connector is a male   circular DIN-8
    portConnectorTypeIsCirdin8Female(23),    -- the type of port connector is a female circular DIN-8
    portConnectorTypeIsIDE(24),              -- the type of port connector is an IDE
    portConnectorTypeIsFloppy(25),           -- the type of port connector is floppy
    portConnectorTypeIsDIN9Pin(26),          -- the type of port connector is nine pin dual inline
    portConnectorTypeIsDIN25Pin(27),         -- the type of port connector is 25 pin dual inline
    portConnectorTypeIsDIN50Pin(28),         -- the type of port connector is 50 pin dual inline
    portConnectorTypeIsDIN68Pin(29),         -- the type of port connector is 68 pin dual inline
    portConnectorTypeIsCDROMLineOut(30),     -- the type of port connector is CDROM line output
    portConnectorTypeIsMiniCentronics14(31), -- the type of port connector is a miniCentronics 14
    portConnectorTypeIsMiniCentronics26(32), -- the type of port connector is a miniCentronics 26
    portConnectorTypeIsMiniJack(33),         -- the type of port connector is a minijack, headphones
    portConnectorTypeIsBNC(34),              -- the type of port connector is a BNC
    portConnectorTypeIs1394(35),             -- the type of port connector is a 1394, firewire
    portConnectorTypeIsPC98(36),             -- the type of port connector is a PC-98
    portConnectorTypeIsPC98Hireso(37),       -- the type of port connector is a PC-98 Hireso
    portConnectorTypeIsPCH98(38),            -- the type of port connector is a PCH98
    portConnectorTypeIsPC98Note(39),         -- the type of port connector is a PC-98 Note
    portConnectorTypeIsPC98Full(40)          -- the type of port connector is a PC-98 Full
}
DellPortSecurityState      ::= INTEGER {
    other(1),              -- the security settings are not one of following:
    unknown(2),            -- the security settings are unknown
    none(3),               -- the security settings are none
    externalIsDisabled(4), -- the security setting by an external interface is disabled
    externalIsEnabled(5),  -- the security setting by an external interface is enabled
    bootByPass(6)          -- the security setting is boot bypass
}

-------------------------------------------------------------------------------
-- Pointing Port Table
-------------------------------------------------------------------------------

DellPointingPortConnectorType            ::= INTEGER {
    connectorPortTypeIsOther(1),         -- there is not one of the following:
    connectorPortTypeIsUnknown(2),       -- the port connector type is unknown
    connectorPortTypeIsSerial(3),        -- the type of port connector is serial
    connectorPortTypeIsPS2(4),           -- the type of port connector is a PS/2
    connectorPortTypeIsInfrared(5),      -- the type of port connector is infrared
    connectorPortTypeIsHPHIL(6),         -- the type of port connector is HP-HIL
    connectorPortTypeIsBusMouse(7),      -- the type of port connector is bus mouse
    connectorPortTypeIsADB(8),           -- the type of port connector is ADB
    connectorPortTypeIsDB9(9),           -- the type of port connector is nine pin DB-9
    connectorPortTypeIsMicroDIN(10),     -- the type of port connector is micro DIN
    connectorPortTypeIsAccessBusUSB(11), -- the type of port connector is Access Bus USB
    connectorPortTypeIsPC98(12)          -- the type of port connector is a PC-98
}

PointingPortTableEntry              ::= SEQUENCE {
    pointingPortchassisIndex        DellObjectRange,
    pointingPortIndex               DellObjectRange,
    pointingPortStateCapabilities   DellStateCapabilities,
    pointingPortStateSettings       DellStateSettings,
    pointingPortStatus              DellStatus,
    pointingPortSecurityState       DellPortSecurityState,
    pointingPortConnectorType       DellPointingPortConnectorType,
    pointingPortName                DellString,
    pointingPortBIOSConnectorType   DellGenericPortConnectorType
}

pointingPortTable                   OBJECT-TYPE
    SYNTAX      SEQUENCE OF PointingPortTableEntry
    ACCESS      not-accessible
    STATUS      mandatory
    DESCRIPTION
"1000.0010 This Group defines the Dell Pointing Port Table."
    ::= { portGroup 10 }
pointingPortTableEntry              OBJECT-TYPE
    SYNTAX      PointingPortTableEntry
    ACCESS      not-accessible
    STATUS      mandatory
    DESCRIPTION
"1000.0010.0001 This Group defines the Dell Pointing Port Table Entry."
    INDEX       { pointingPortchassisIndex, pointingPortIndex }
    ::= { pointingPortTable 1 }
pointingPortchassisIndex                OBJECT-TYPE
    SYNTAX      DellObjectRange
    ACCESS      read-only
    STATUS      mandatory
    DESCRIPTION
"1000.0010.0001.0001 This attribute defines the index (one based) of
this Dell chassis."
    ::= { pointingPortTableEntry 1 }
pointingPortIndex                   OBJECT-TYPE
    SYNTAX      DellObjectRange
    ACCESS      read-only
    STATUS      mandatory
    DESCRIPTION
"1000.0010.0001.0002 This attribute defines the index of the Dell
Pointing Port in this chassis."
    ::= { pointingPortTableEntry 2 }
pointingPortStateCapabilities       OBJECT-TYPE
    SYNTAX      DellStateCapabilities
    ACCESS      read-only
    STATUS      mandatory
    DESCRIPTION
"1000.0010.0001.0003 This attribute defines the capabilities of the
Dell Pointing Port."
    ::= { pointingPortTableEntry 3 }
pointingPortStateSettings           OBJECT-TYPE
    SYNTAX      DellStateSettings
    ACCESS      read-write
    STATUS      mandatory
    DESCRIPTION
"1000.0010.0001.0004 This attribute defines the state of the Dell
Pointing Port."
    ::= { pointingPortTableEntry 4 }
pointingPortStatus                  OBJECT-TYPE
    SYNTAX      DellStatus
    ACCESS      read-only
    STATUS      mandatory
    DESCRIPTION
"1000.0010.0001.0005 This attribute defines the status of the Dell
Pointing Port."
    ::= { pointingPortTableEntry 5 }
pointingPortSecurityState        OBJECT-TYPE
    SYNTAX      DellPortSecurityState
    ACCESS      read-only
    STATUS      mandatory
    DESCRIPTION
"1000.0010.0001.0006 This attribute defines if security settings of the
Dell Pointing Port."
    ::= { pointingPortTableEntry 6 }
pointingPortConnectorType           OBJECT-TYPE
    SYNTAX      DellPointingPortConnectorType
    ACCESS      read-only
    STATUS      mandatory
    DESCRIPTION
"1000.0010.0001.0007 This attribute defines the connector type of the
Dell Pointing Port."
    ::= { pointingPortTableEntry 7 }
pointingPortName                    OBJECT-TYPE
    SYNTAX      DellString
    ACCESS      read-only
    STATUS      mandatory
    DESCRIPTION
"1000.0010.0001.0008 This attribute defines name of the Dell Pointing Port."
    ::= { pointingPortTableEntry 8 }
pointingPortBIOSConnectorType       OBJECT-TYPE
    SYNTAX      DellGenericPortConnectorType
    ACCESS      read-only
    STATUS      mandatory
    DESCRIPTION
"1000.0010.0001.0009 This attribute defines the BIOS connector type of the
Dell Pointing Port."
    ::= { pointingPortTableEntry 9 }


-------------------------------------------------------------------------------
-- Keyboard Port Table
-------------------------------------------------------------------------------

DellKeyboardPortConnectorType           ::= INTEGER {
    connectorPortTypeIsOther(1),        -- there is not one of the following:
    connectorPortTypeIsUnknown(2),      -- the port connector type is unknown
    connectorPortTypeIsMiniDIN(3),      -- the type of port connector is a mini DIN
    connectorPortTypeIsMicroDIN(4),     -- the type of port connector is a micro DIN
    connectorPortTypeIsPS2(5),          -- the type of port connector is a PS/2
    connectorPortTypeIsInfrared(6),     -- the type of port connector is infrared
    connectorPortTypeIsHPHIL(7),        -- the type of port connector is HP-HIL
    connectorPortTypeIsDB9(8),          -- the type of port connector is a DB-9
    connectorPortTypeIsAccessBusUSB(9), -- the type of port connector is Access Bus USB
    connectorPortTypeIsPC98(10)         -- the type of port connector is a PC-98
}

KeyboardPortTableEntry              ::= SEQUENCE {
    keyboardPortchassisIndex        DellObjectRange,
    keyboardPortIndex               DellObjectRange,
    keyboardPortStateCapabilities   DellStateCapabilities,
    keyboardPortStateSettings       DellStateSettings,
    keyboardPortStatus              DellStatus,
    keyboardPortSecurityState       DellPortSecurityState,
    keyboardPortConnectorType       DellKeyboardPortConnectorType,
    keyboardPortName                DellString,
    keyboardPortBIOSConnectorType   DellGenericPortConnectorType
}

keyboardPortTable                   OBJECT-TYPE
    SYNTAX      SEQUENCE OF KeyboardPortTableEntry
    ACCESS      not-accessible
    STATUS      mandatory
    DESCRIPTION
"1000.0020 This Group defines the Dell Keyboard Port Table."
    ::= { portGroup 20 }
keyboardPortTableEntry              OBJECT-TYPE
    SYNTAX      KeyboardPortTableEntry
    ACCESS      not-accessible
    STATUS      mandatory
    DESCRIPTION
"1000.0020.0001 This Group defines the Dell Keyboard Port Table Entry."
    INDEX       { keyboardPortchassisIndex, keyboardPortIndex }
    ::= { keyboardPortTable 1 }
keyboardPortchassisIndex                OBJECT-TYPE
    SYNTAX      DellObjectRange
    ACCESS      read-only
    STATUS      mandatory
    DESCRIPTION
"1000.0020.0001.0001 This attribute defines the index (one based) of
this Dell chassis."
    ::= { keyboardPortTableEntry 1 }
keyboardPortIndex                   OBJECT-TYPE
    SYNTAX      DellObjectRange
    ACCESS      read-only
    STATUS      mandatory
    DESCRIPTION
"1000.0020.0001.0002 This attribute defines the index of the Dell Keyboard
Port in this chassis."
    ::= { keyboardPortTableEntry 2 }
keyboardPortStateCapabilities        OBJECT-TYPE
    SYNTAX      DellStateCapabilities
    ACCESS      read-only
    STATUS      mandatory
    DESCRIPTION
"1000.0020.0001.0003 This attribute defines the capabilities of the Dell
Keyboard Port."
    ::= { keyboardPortTableEntry 3 }
keyboardPortStateSettings           OBJECT-TYPE
    SYNTAX      DellStateSettings
    ACCESS      read-only
    STATUS      mandatory
    DESCRIPTION
"1000.0020.0001.0004 This attribute defines the state of the Dell Keyboard
Port."
    ::= { keyboardPortTableEntry 4 }
keyboardPortStatus                  OBJECT-TYPE
    SYNTAX      DellStatus
    ACCESS      read-only
    STATUS      mandatory
    DESCRIPTION
"1000.0020.0001.0005 This attribute defines the status of the Dell Keyboard
Port."
    ::= { keyboardPortTableEntry 5 }
keyboardPortSecurityState        OBJECT-TYPE
    SYNTAX      DellPortSecurityState
    ACCESS      read-only
    STATUS      mandatory
    DESCRIPTION
"1000.0020.0001.0006 This attribute defines if security settings of
the Dell Keyboard Port."
    ::= { keyboardPortTableEntry 6 }
keyboardPortConnectorType           OBJECT-TYPE
    SYNTAX      DellKeyboardPortConnectorType
    ACCESS      read-only
    STATUS      mandatory
    DESCRIPTION
"1000.0020.0001.0007 This attribute defines the connector type of the Dell
Keyboard Port."
    ::= { keyboardPortTableEntry 7 }
keyboardPortName                    OBJECT-TYPE
    SYNTAX      DellString
    ACCESS      read-only
    STATUS      mandatory
    DESCRIPTION
"1000.0020.0001.0008 This attribute defines name of the Dell Keyboard Port."
    ::= { keyboardPortTableEntry 8 }
keyboardPortBIOSConnectorType       OBJECT-TYPE
    SYNTAX      DellGenericPortConnectorType
    ACCESS      read-only
    STATUS      mandatory
    DESCRIPTION
"1000.0020.0001.0009 This attribute defines the BIOS connector type of
the Dell Keyboard Port."
    ::= { keyboardPortTableEntry 9 }


-------------------------------------------------------------------------------
-- Processor Port Table
-------------------------------------------------------------------------------

DellProcessorPortConnectorType             ::= INTEGER {
    connectorPortTypeIsOther(1),           -- there is not one of the following:
    connectorPortTypeIsUnknown(2),         -- the port connector type is unknown
    connectorPortTypeIsDaughterdBoard(3),  -- the connector port is daughter board
    connectorPortTypeIsZIFSocket(4),       -- the connector port is a zero insertion force socket
    connectorPortTypeIsAPiggyBackBoard(5), -- the connector port is a replacement piggyback board
    connectorPortTypeIsNone(6),            -- the connector port is none, soldered in place
    connectorPortTypeIsLIFSocket(7),       -- the connector port is a low force insertion socket
    connectorPortTypeIsSlot1(8),           -- the connector port is a slot one type
    connectorPortTypeIsSlot2(9),           -- the connector port is a slot two type
    connectorPortTypeIsP370(10)            -- the connector port is a P370 type
}

ProcessorPortTableEntry             ::= SEQUENCE {
    processorPortchassisIndex       DellObjectRange,
    processorPortIndex              DellObjectRange,
    processorPortStateCapabilities  DellStateCapabilities,
    processorPortStateSettings      DellStateSettings,
    processorPortStatus             DellStatus,
    processorPortSecurityState      DellPortSecurityState,
    processorPortConnectorType      DellProcessorPortConnectorType,
    processorPortName               DellString,
    processorPortBIOSConnectorType  DellGenericPortConnectorType
}

processorPortTable                  OBJECT-TYPE
    SYNTAX      SEQUENCE OF ProcessorPortTableEntry
    ACCESS      not-accessible
    STATUS      mandatory
    DESCRIPTION
"1000.0030 This Group defines the Dell Processor Port Table."
    ::= { portGroup 30 }
processorPortTableEntry             OBJECT-TYPE
    SYNTAX      ProcessorPortTableEntry
    ACCESS      not-accessible
    STATUS      mandatory
    DESCRIPTION
"1000.0030.0001 This Group defines the Dell Processor Port Table Entry."
    INDEX       { processorPortchassisIndex, processorPortIndex }
    ::= { processorPortTable 1 }
processorPortchassisIndex               OBJECT-TYPE
    SYNTAX      DellObjectRange
    ACCESS      read-only
    STATUS      mandatory
    DESCRIPTION
"1000.0030.0001.0001 This attribute defines the index (one based) of
this Dell chassis."
    ::= { processorPortTableEntry 1 }
processorPortIndex                  OBJECT-TYPE
    SYNTAX      DellObjectRange
    ACCESS      read-only
    STATUS      mandatory
    DESCRIPTION
"1000.0030.0001.0002 This attribute defines the index of the Dell
Processor Port in this chassis."
    ::= { processorPortTableEntry 2 }
processorPortStateCapabilities      OBJECT-TYPE
    SYNTAX      DellStateCapabilities
    ACCESS      read-only
    STATUS      mandatory
    DESCRIPTION
"1000.0030.0001.0003 This attribute defines the capabilities of the Dell
Processor Port."
    ::= { processorPortTableEntry 3 }
processorPortStateSettings         OBJECT-TYPE
    SYNTAX      DellStateSettings
    ACCESS      read-write
    STATUS      mandatory
    DESCRIPTION
"1000.0030.0001.0004 This attribute defines the state of the Dell
Processor Port."
    ::= { processorPortTableEntry 4 }
processorPortStatus                 OBJECT-TYPE
    SYNTAX      DellStatus
    ACCESS      read-only
    STATUS      mandatory
    DESCRIPTION
"1000.0030.0001.0005 This attribute defines the status of the Dell
Processor Port."
    ::= { processorPortTableEntry 5 }
processorPortSecurityState       OBJECT-TYPE
    SYNTAX      DellPortSecurityState
    ACCESS      read-only
    STATUS      mandatory
    DESCRIPTION
"1000.0030.0001.0006 This attribute defines the security settings of the
Dell Processor Port."
    ::= { processorPortTableEntry 6 }
processorPortConnectorType          OBJECT-TYPE
    SYNTAX      DellProcessorPortConnectorType
    ACCESS      read-only
    STATUS      mandatory
    DESCRIPTION
"1000.0030.0001.0007 This attribute defines the connector type of the
Dell Processor Port."
    ::= { processorPortTableEntry 7 }
processorPortName                   OBJECT-TYPE
    SYNTAX      DellString
    ACCESS      read-only
    STATUS      mandatory
    DESCRIPTION
"1000.0030.0001.0008 This attribute defines name of the Dell Processor Port."
    ::= { processorPortTableEntry 8 }
processorPortBIOSConnectorType      OBJECT-TYPE
    SYNTAX      DellGenericPortConnectorType
    ACCESS      read-only
    STATUS      mandatory
    DESCRIPTION
"1000.0030.0001.0009 This attribute defines the BIOS connector type of the
Dell Processor Port."
    ::= { processorPortTableEntry 9 }


-------------------------------------------------------------------------------
-- Memory Device Port Table
-------------------------------------------------------------------------------

DellMemoryDevicePortConnectorType           ::= INTEGER {
    connectorPortTypeIsOther(1),            -- there is not one of the following:
    connectorPortTypeIsUnknown(2),          -- the port connector type is unknown
    connectorPortTypeIsSIMM(3),             -- the connector port is a simm
    connectorPortTypeIsSIP(4),              -- the connector port is a sip
    connectorPortTypeIsAChip(5),            -- the connector port is a chip
    connectorPortTypeIsDIP(6),              -- the connector port is a dip
    connectorPortTypeIsZIP(7),              -- the connector port is a zip
    connectorPortTypeIsAProprietaryCard(8), -- the connector port is a proprietary card
    connectorPortTypeIsDIMM(9),             -- the connector port is a dimm
    connectorPortTypeIsTSOP(10),            -- the connector port is a tsop
    connectorPortTypeIsARowOfChips(11),     -- the connector port is a row of chips
    connectorPortTypeIsRIMM(12),            -- the connector port is a rimm
    connectorPortTypeIsSODIMM(13),          -- the connector port is a sodimm
    connectorPortTypeIsSRIMM(14)            -- the connector port is a srimm
}

MemoryDevicePortTableEntry                            ::= SEQUENCE {
    memoryDevicePortchassisIndex                      DellObjectRange,
    memoryDevicePortIndex                             DellObjectRange,
    memoryDevicePortStateCapabilities                 DellStateCapabilities,
    memoryDevicePortStateSettings                     DellStateSettings,
    memoryDevicePortStatus                            DellStatus,
    memoryDevicePortSecurityState                     DellPortSecurityState,
    memoryDevicePortConnectorType                     DellMemoryDevicePortConnectorType,
    memoryDevicePortName                              DellString,
    memoryDevicePortBIOSConnectorType                 DellGenericPortConnectorType,
    memoryDevicePortPhysicalMemoryArrayIndexReference DellUnsigned32BitRange
}

memoryDevicePortTable                  OBJECT-TYPE
    SYNTAX      SEQUENCE OF MemoryDevicePortTableEntry
    ACCESS      not-accessible
    STATUS      mandatory
    DESCRIPTION
"1000.0040 This Group defines the Dell Memory Device Port Table."
    ::= { portGroup 40 }
memoryDevicePortTableEntry             OBJECT-TYPE
    SYNTAX      MemoryDevicePortTableEntry
    ACCESS      not-accessible
    STATUS      mandatory
    DESCRIPTION
"1000.0040.0001 This Group defines the Dell Memory Device Port Table Entry."
    INDEX       { memoryDevicePortchassisIndex, memoryDevicePortIndex }
    ::= { memoryDevicePortTable 1 }
memoryDevicePortchassisIndex               OBJECT-TYPE
    SYNTAX      DellObjectRange
    ACCESS      read-only
    STATUS      mandatory
    DESCRIPTION
"1000.0040.0001.0001 This attribute defines the index (one based) of
this Dell chassis."
    ::= { memoryDevicePortTableEntry 1 }
memoryDevicePortIndex                  OBJECT-TYPE
    SYNTAX      DellObjectRange
    ACCESS      read-only
    STATUS      mandatory
    DESCRIPTION
"1000.0040.0001.0002 This attribute defines the index of the Dell
Memory Device Port in this chassis."
    ::= { memoryDevicePortTableEntry 2 }
memoryDevicePortStateCapabilities      OBJECT-TYPE
    SYNTAX      DellStateCapabilities
    ACCESS      read-only
    STATUS      mandatory
    DESCRIPTION
"1000.0040.0001.0003 This attribute defines the capabilities of the Dell
Memory Device Port."
    ::= { memoryDevicePortTableEntry 3 }
memoryDevicePortStateSettings         OBJECT-TYPE
    SYNTAX      DellStateSettings
    ACCESS      read-write
    STATUS      mandatory
    DESCRIPTION
"1000.0040.0001.0004 This attribute defines the state of the Dell
Memory Device Port."
    ::= { memoryDevicePortTableEntry 4 }
memoryDevicePortStatus                 OBJECT-TYPE
    SYNTAX      DellStatus
    ACCESS      read-only
    STATUS      mandatory
    DESCRIPTION
"1000.0040.0001.0005 This attribute defines the status of the Dell
Memory Device Port."
    ::= { memoryDevicePortTableEntry 5 }
memoryDevicePortSecurityState       OBJECT-TYPE
    SYNTAX      DellPortSecurityState
    ACCESS      read-only
    STATUS      mandatory
    DESCRIPTION
"1000.0040.0001.0006 This attribute defines the security settings of the
Dell Memory Device Port."
    ::= { memoryDevicePortTableEntry 6 }
memoryDevicePortConnectorType          OBJECT-TYPE
    SYNTAX      DellMemoryDevicePortConnectorType
    ACCESS      read-only
    STATUS      mandatory
    DESCRIPTION
"1000.0040.0001.0007 This attribute defines the connector type of the
Dell Memory Device Port."
    ::= { memoryDevicePortTableEntry 7 }
memoryDevicePortName                   OBJECT-TYPE
    SYNTAX      DellString
    ACCESS      read-only
    STATUS      mandatory
    DESCRIPTION
"1000.0040.0001.0008 This attribute defines name of the Dell Memory Device Port."
    ::= { memoryDevicePortTableEntry 8 }
memoryDevicePortBIOSConnectorType      OBJECT-TYPE
    SYNTAX      DellGenericPortConnectorType
    ACCESS      read-only
    STATUS      mandatory
    DESCRIPTION
"1000.0040.0001.0009 This attribute defines the BIOS connector type of the
Dell Memory Device Port."
    ::= { memoryDevicePortTableEntry 9 }
memoryDevicePortPhysicalMemoryArrayIndexReference      OBJECT-TYPE
    SYNTAX      DellUnsigned32BitRange
    ACCESS      read-only
    STATUS      mandatory
    DESCRIPTION
"1000.0040.0001.0010 This attribute defines the index value of the Physical
Memory Array that this memory device is associated with."
    ::= { memoryDevicePortTableEntry 10 }


-------------------------------------------------------------------------------
-- Monitor Port Table
-------------------------------------------------------------------------------

DellMonitorPortConnectorType            ::= INTEGER {
    connectorPortTypeIsOther(1),        -- there is not one of the following:
    connectorPortTypeIsUnknown(2),      -- the port connector type is unknown
    connectorPortTypeIsDB15PinMale(3),  -- the type of port connector is a male  DB-15
    connectorPortTypeIsDB15PinFemale(4) -- the type of port connector is a female DB-15
}

MonitorPortTableEntry                   ::= SEQUENCE {
    monitorPortchassisIndex             DellObjectRange,
    monitorPortIndex                    DellObjectRange,
    monitorPortStateCapabilities        DellStateCapabilities,
    monitorPortStateSettings            DellStateSettings,
    monitorPortStatus                   DellStatus,
    monitorPortSecurityState            DellPortSecurityState,
    monitorPortConnectorType            DellMonitorPortConnectorType,
    monitorPortName                     DellString,
    monitorPortBIOSConnectorType        DellGenericPortConnectorType
}

monitorPortTable                        OBJECT-TYPE
    SYNTAX      SEQUENCE OF MonitorPortTableEntry
    ACCESS      not-accessible
    STATUS      mandatory
    DESCRIPTION
"1000.0050 This Group defines the Dell Monitor Port Table."
    ::= { portGroup 50 }
monitorPortTableEntry                   OBJECT-TYPE
    SYNTAX      MonitorPortTableEntry
    ACCESS      not-accessible
    STATUS      mandatory
    DESCRIPTION
"1000.0050.0001 This Group defines the Dell Monitor Port Table Entry."
    INDEX       { monitorPortchassisIndex, monitorPortIndex }
    ::= { monitorPortTable 1 }
monitorPortchassisIndex                 OBJECT-TYPE
    SYNTAX      DellObjectRange
    ACCESS      read-only
    STATUS      mandatory
    DESCRIPTION
"1000.0050.0001.0001 This attribute defines the index (one based) of
this Dell chassis."
    ::= { monitorPortTableEntry 1 }
monitorPortIndex                        OBJECT-TYPE
    SYNTAX      DellObjectRange
    ACCESS      read-only
    STATUS      mandatory
    DESCRIPTION
"1000.0050.0001.0002 This attribute defines the index of the Dell
Monitor Port in this chassis."
    ::= { monitorPortTableEntry 2 }
monitorPortStateCapabilities           OBJECT-TYPE
    SYNTAX      DellStateCapabilities
    ACCESS      read-only
    STATUS      mandatory
    DESCRIPTION
"1000.0050.0001.0003 This attribute defines the capabilities of the Dell
Monitor Port."
    ::= { monitorPortTableEntry 3 }
monitorPortStateSettings                OBJECT-TYPE
    SYNTAX      DellStateSettings
    ACCESS      read-write
    STATUS      mandatory
    DESCRIPTION
"1000.0050.0001.0004 This attribute defines the state of the Dell
Monitor Port."
    ::= { monitorPortTableEntry 4 }
monitorPortStatus                       OBJECT-TYPE
    SYNTAX      DellStatus
    ACCESS      read-only
    STATUS      mandatory
    DESCRIPTION
"1000.0050.0001.0005 This attribute defines the status of the Dell
Monitor Port."
    ::= { monitorPortTableEntry 5 }
monitorPortSecurityState             OBJECT-TYPE
    SYNTAX      DellPortSecurityState
    ACCESS      read-only
    STATUS      mandatory
    DESCRIPTION
"1000.0050.0001.0006 This attribute defines if security settings of the
Dell Monitor Port."
    ::= { monitorPortTableEntry 6 }
monitorPortConnectorType                OBJECT-TYPE
    SYNTAX      DellMonitorPortConnectorType
    ACCESS      read-only
    STATUS      mandatory
    DESCRIPTION
"1000.0050.0001.0007 This attribute defines the connector type of the
Dell Monitor Port."
    ::= { monitorPortTableEntry 7 }
monitorPortName                         OBJECT-TYPE
    SYNTAX      DellString
    ACCESS      read-only
    STATUS      mandatory
    DESCRIPTION
"1000.0050.0001.0008 This attribute defines name of the Dell Monitor Port."
    ::= { monitorPortTableEntry 8 }
monitorPortBIOSConnectorType            OBJECT-TYPE
    SYNTAX      DellGenericPortConnectorType
    ACCESS      read-only
    STATUS      mandatory
    DESCRIPTION
"1000.0050.0001.0009 This attribute defines the BIOS connector type of the
Dell Monitor Port."
    ::= { monitorPortTableEntry 9 }


-------------------------------------------------------------------------------
-- SCSI Port Table
-------------------------------------------------------------------------------

DellSCSIPortConnectorType           ::= INTEGER {
    connectorPortTypeIsOther(1),    -- there is not one of the following:
    connectorPortTypeIsUnknown(2),  -- the port connector type is unknown
    connectorPortTypeIsDIN25pin(3), -- the type of port connector is DIN 25 pin
    connectorPortTypeIsDIN50pin(4), -- the type of port connector is DIN 50 pin
    connectorPortTypeIsDIN68pin(5)  -- the type of port connector is DIN 68 pin
}

SCSIPortTableEntry                  ::= SEQUENCE {
    sCSIPortchassisIndex            DellObjectRange,
    sCSIPortIndex                   DellObjectRange,
    sCSIPortStateCapabilities       DellStateCapabilities,
    sCSIPortStateSettings           DellStateSettings,
    sCSIPortStatus                  DellStatus,
    sCSIPortSecurityState           DellPortSecurityState,
    sCSIPortConnectorType           DellSCSIPortConnectorType,
    sCSIPortName                    DellString,
    sCSIPortBIOSConnectorType       DellGenericPortConnectorType
}

sCSIPortTable                       OBJECT-TYPE
    SYNTAX      SEQUENCE OF SCSIPortTableEntry
    ACCESS      not-accessible
    STATUS      mandatory
    DESCRIPTION
"1000.0060 This Group defines the Dell SCSI Port Table."
    ::= { portGroup 60 }
sCSIPortTableEntry                  OBJECT-TYPE
    SYNTAX      SCSIPortTableEntry
    ACCESS      not-accessible
    STATUS      mandatory
    DESCRIPTION
"1000.0060.0001 This Group defines the Dell SCSI Port Table Entry."
    INDEX       { sCSIPortchassisIndex, sCSIPortIndex }
    ::= { sCSIPortTable 1 }
sCSIPortchassisIndex                OBJECT-TYPE
    SYNTAX      DellObjectRange
    ACCESS      read-only
    STATUS      mandatory
    DESCRIPTION
"1000.0060.0001.0001 This attribute defines the index (one based) of
this Dell chassis."
    ::= { sCSIPortTableEntry 1 }
sCSIPortIndex                       OBJECT-TYPE
    SYNTAX      DellObjectRange
    ACCESS      read-only
    STATUS      mandatory
    DESCRIPTION
"1000.0060.0001.0002 This attribute defines the index of the Dell SCSI
Port in this chassis."
    ::= { sCSIPortTableEntry 2 }
sCSIPortStateCapabilities           OBJECT-TYPE
    SYNTAX      DellStateCapabilities
    ACCESS      read-only
    STATUS      mandatory
    DESCRIPTION
"1000.0060.0001.0003 This attribute defines the capabilities of the Dell
SCSI Port."
    ::= { sCSIPortTableEntry 3 }
sCSIPortStateSettings               OBJECT-TYPE
    SYNTAX      DellStateSettings
    ACCESS      read-write
    STATUS      mandatory
    DESCRIPTION
"1000.0060.0001.0004 This attribute defines the state of the Dell
SCSI Port."
    ::= { sCSIPortTableEntry 4 }
sCSIPortStatus                      OBJECT-TYPE
    SYNTAX      DellStatus
    ACCESS      read-only
    STATUS      mandatory
    DESCRIPTION
"1000.0060.0001.0005 This attribute defines the status of the Dell
SCSI Port."
    ::= { sCSIPortTableEntry 5 }
sCSIPortSecurityState            OBJECT-TYPE
    SYNTAX      DellPortSecurityState
    ACCESS      read-only
    STATUS      mandatory
    DESCRIPTION
"1000.0060.0001.0006 This attribute defines if security settings of the
Dell SCSI Port."
    ::= { sCSIPortTableEntry 6 }
sCSIPortConnectorType               OBJECT-TYPE
    SYNTAX      DellSCSIPortConnectorType
    ACCESS      read-only
    STATUS      mandatory
    DESCRIPTION
"1000.0060.0001.0007 This attribute defines the connector type of the
Dell SCSI Port."
    ::= { sCSIPortTableEntry 7 }
sCSIPortName                        OBJECT-TYPE
    SYNTAX      DellString
    ACCESS      read-only
    STATUS      mandatory
    DESCRIPTION
"1000.0060.0001.0008 This attribute defines name of the Dell SCSI Port."
    ::= { sCSIPortTableEntry 8 }
sCSIPortBIOSConnectorType           OBJECT-TYPE
    SYNTAX      DellGenericPortConnectorType
    ACCESS      read-only
    STATUS      mandatory
    DESCRIPTION
"1000.0060.0001.0009 This attribute defines the BIOS connector type of the
Dell SCSI Port."
    ::= { sCSIPortTableEntry 9 }


-------------------------------------------------------------------------------
-- Parallel Port Table
-------------------------------------------------------------------------------

DellParallelPortConnectorType               ::= INTEGER {
    connectorPortTypeIsOther(1),            -- the type of port connector is not one of following:
    connectorPortTypeIsUnknown(2),          -- the type of port connector is unknown
    connectorPortTypeIsDB25PinFemale(3),    -- the type of port connector is a female DB-25,   IEEE1284-A Receptical
    connectorPortTypeIsDB25PinMale(4),      -- the type of port connector is a male   DB-25,   IEEE1284-A Plug
    connectorPortTypeIsCentronics(5),       -- the type of port connector is a Centronics,     IEEE1284-B Receptical
    connectorPortTypeIsMiniCentronics(6),   -- the type of port connector is a miniCentronics, IEEE1284-C Receptical
    connectorPortTypeIsProprietary(7),      -- the type of port connector is proprietary
    connectorPortTypeIsCentronics14(8),     -- the type of port connector is a Centronics 14
    connectorPortTypeIsDB36PinFemale(9),    -- the type of port connector is a female DB-36
    connectorPortTypeIsMiniCentronics20(10) -- the type of port connector is a miniCentronics 20
}
DellParallelPortConnectorPinout          ::= INTEGER {
    connectorPortPinoutIsOther(1),       -- the type of port connector pinout is not one of following:
    connectorPortPinoutIsUnknown(2),     -- the type of port connector pinout is unknown
    connectorPortPinoutIsXTorAT(3),      -- the type of port connector pinout is XT or AT pinout compatible
    connectorPortPinoutIsPS2(4),         -- the type of port connector pinout is PS/2 pinout compatible
    connectorPortPinoutIsIEEE1284(5),    -- the type of port connector pinout is IEEE 1284 pinout compatible
    connectorPortPinoutIsProprietary(6), -- the type of port connector pinout is proprietary
    connectorPortPinoutIsPC98(7),        -- the type of port connector pinout is PC-98 pinout compatible
    connectorPortPinoutIsPC98Hireso(8),  -- the type of port connector pinout is PC-98 Hireso pinout compatible
    connectorPortPinoutIsPC98Note(9),    -- the type of port connector pinout is PC-98 Note pinout compatible
    connectorPortPinoutIsPC98Full(10)    -- the type of port connector pinout is PC-98 Full pinout compatible
}
DellParallelPortCapabilitiesUnique  ::= INTEGER {
    unknown(1),                   -- The objects capabilities are unknown
    atCapable(2),                 -- The parallel port is AT mode Capable
    ps2Capable(4),                -- The parallel port is PS/2 mode Capable
    ecpCapable(8),                -- The parallel port is ECP mode Capable
    eppCapable(16),               -- The parallel port is EPP mode Capable
    atOrPS2OrECPOrEPPCapable(30), -- The parallel port is EPP mode Capable
    pc98Capable(32),              -- The parallel port is PC98 mode Capable
    pc98HiresoCapable(64),        -- The parallel port is PC98 Hireso mode Capable
    pc98HCapable(128)             -- The parallel port is PC98H mode Capable
}

ParallelPortTableEntry              ::= SEQUENCE {
    parallelPortchassisIndex        DellObjectRange,
    parallelPortIndex               DellObjectRange,
    parallelPortStateCapabilities   DellStateCapabilities,
    parallelPortStateSettings       DellStateSettings,
    parallelPortStatus              DellStatus,
    parallelPortSecurityState       DellPortSecurityState,
    parallelPortConnectorType       DellParallelPortConnectorType,
    parallelPortName                DellString,
    parallelPortConnectorPinOut     DellParallelPortConnectorPinout,
    parallelPortCapabilitiesUnique  DellParallelPortCapabilitiesUnique,
    parallelPortBaseIOAddress       DellUnsigned64BitRange,
    parallelPortIRQLevel            DellUnsigned8BitRange,
    parallelPortDMASupport          DellBoolean
}

parallelPortTable                   OBJECT-TYPE
    SYNTAX      SEQUENCE OF ParallelPortTableEntry
    ACCESS      not-accessible
    STATUS      mandatory
    DESCRIPTION
"1000.0070 This Group defines the Dell Parallel Port Table."
    ::= { portGroup 70 }
parallelPortTableEntry              OBJECT-TYPE
    SYNTAX      ParallelPortTableEntry
    ACCESS      not-accessible
    STATUS      mandatory
    DESCRIPTION
"1000.0070.0001 This Group defines the Dell Parallel Port Table Entry."
    INDEX       { parallelPortchassisIndex, parallelPortIndex }
    ::= { parallelPortTable 1 }
parallelPortchassisIndex                OBJECT-TYPE
    SYNTAX      DellObjectRange
    ACCESS      read-only
    STATUS      mandatory
    DESCRIPTION
"1000.0070.0001.0001 This attribute defines the index (one based) of
this Dell chassis."
    ::= { parallelPortTableEntry 1 }
parallelPortIndex                   OBJECT-TYPE
    SYNTAX      DellObjectRange
    ACCESS      read-only
    STATUS      mandatory
    DESCRIPTION
"1000.0070.0001.0002 This attribute defines the index of the Dell Parallel
Port in this chassis."
    ::= { parallelPortTableEntry 2 }
parallelPortStateCapabilities       OBJECT-TYPE
    SYNTAX      DellStateCapabilities
    ACCESS      read-only
    STATUS      mandatory
    DESCRIPTION
"1000.0070.0001.0003 This attribute defines the capabilities of the
Dell Parallel Port."
    ::= { parallelPortTableEntry 3 }
parallelPortStateSettings           OBJECT-TYPE
    SYNTAX      DellStateSettings
    ACCESS      read-write
    STATUS      mandatory
    DESCRIPTION
"1000.0070.0001.0004 This attribute defines the state of the
Dell Parallel Port."
    ::= { parallelPortTableEntry 4 }
parallelPortStatus                  OBJECT-TYPE
    SYNTAX      DellStatus
    ACCESS      read-only
    STATUS      mandatory
    DESCRIPTION
"1000.0070.0001.0005 This attribute defines the status of the
Dell Parallel Port."
    ::= { parallelPortTableEntry 5 }
parallelPortSecurityState        OBJECT-TYPE
    SYNTAX      DellPortSecurityState
    ACCESS      read-only
    STATUS      mandatory
    DESCRIPTION
"1000.0070.0001.0006 This attribute defines if security state of the
Dell Parallel Port."
    ::= { parallelPortTableEntry 6 }
parallelPortConnectorType           OBJECT-TYPE
    SYNTAX      DellParallelPortConnectorType
    ACCESS      read-only
    STATUS      mandatory
    DESCRIPTION
"1000.0070.0001.0007 This attribute defines the connector type of the
Dell Parallel Port."
    ::= { parallelPortTableEntry 7 }
parallelPortName                OBJECT-TYPE
    SYNTAX      DellString
    ACCESS      read-only
    STATUS      mandatory
    DESCRIPTION
"1000.0070.0001.0008 This attribute defines the name of the Dell Parallel
Port."
    ::= { parallelPortTableEntry 8 }
parallelPortConnectorPinOut         OBJECT-TYPE
    SYNTAX      DellParallelPortConnectorPinout
    ACCESS      read-only
    STATUS      mandatory
    DESCRIPTION
"1000.0070.0001.0009 This attribute defines the pinout of the Dell Parallel
Port."
    ::= { parallelPortTableEntry 9 }
parallelPortCapabilitiesUnique            OBJECT-TYPE
    SYNTAX      DellParallelPortCapabilitiesUnique
    ACCESS      read-only
    STATUS      mandatory
    DESCRIPTION
"1000.0070.0001.0010 This attribute defines the capabilities of the Dell
Parallel Port."
    ::= { parallelPortTableEntry 10 }
parallelPortBaseIOAddress           OBJECT-TYPE
    SYNTAX      DellUnsigned64BitRange
    ACCESS      read-only
    STATUS      mandatory
    DESCRIPTION
"1000.0070.0001.0011 This attribute defines the Base Input Output address of
the Dell Parallel Port."
    ::= { parallelPortTableEntry 11 }
parallelPortIRQLevel                OBJECT-TYPE
    SYNTAX      DellUnsigned8BitRange
    ACCESS      read-only
    STATUS      mandatory
    DESCRIPTION
"1000.0070.0001.0012 This attribute defines the Interrupt Request Level of
the Dell Parallel Port."
    ::= { parallelPortTableEntry 12 }
parallelPortDMASupport              OBJECT-TYPE
    SYNTAX      DellBoolean
    ACCESS      read-only
    STATUS      mandatory
    DESCRIPTION
"1000.0070.0001.0013 This attribute defines if DMA is supported by the
Dell Parallel Port."
    ::= { parallelPortTableEntry 13 }


-------------------------------------------------------------------------------
-- Serial Port Table
-------------------------------------------------------------------------------

DellSerialPortConnectorType                  ::= INTEGER {
    connectorPortTypeIsOther(1),             -- the type of port connector is not one of following:
    connectorPortTypeIsUnknown(2),           -- the type of port connector is unknown
    connectorPortTypeIsDB9PinMale(3),        -- the type of port connector is a male   DB-9
    connectorPortTypeIsDB9PinFemale(4),      -- the type of port connector is a female DB-9
    connectorPortTypeIsDB25PinMale(5),       -- the type of port connector is a male   DB-25
    connectorPortTypeIsDB25PinFemale(6),     -- the type of port connector is a female DB-25
    connectorPortTypeIsRJ11(7),              -- the type of port connector is an RJ-11
    connectorPortTypeIsRJ45(8),              -- the type of port connector is an RJ-45
    connectorPortTypeIsProprietary(9),       -- the type of port connector is proprietary
    connectorPortTypeIsCirdin8Male(10),      -- the type of port connector is a male   circular DIN-8
    connectorPortTypeIsCirdin8Female(11),    -- the type of port connector is a female circular DIN-8
    connectorPortTypeIsMiniCentronics14(12), -- the type of port connector is a miniCentronics 14
    connectorPortTypeIsMiniCentronics26(13)  -- the type of port connector is a miniCentronics 26
}
DellSerialPortCapabilitiesUnique ::= INTEGER {
    other(1),              -- The serial port capabilities are not one of following:
    unknown(2),            -- The serial port capabilities is unknown
    xtorATCapable(4),      -- The serial port is XT or AT mode Capable
    c16450Capable(8),      -- The serial port is 16450 Capable
    c16550Capable(16),     -- The serial port is 16550 Capable
    c16550aCapable(32),    -- The serial port is 16550A Capable
    c8251Capable(64),      -- The serial port is 8251 Capable
    c8251FIFOCapable(128)  -- The serial port is 8251 FIFO Capable
}

SerialPortTableEntry             ::= SEQUENCE {
    serialPortchassisIndex       DellObjectRange,
    serialPortIndex              DellObjectRange,
    serialPortStateCapabilities  DellStateCapabilities,
    serialPortStateSettings      DellStateSettings,
    serialPortStatus             DellStatus,
    serialPortSecurityState      DellPortSecurityState,
    serialPortConnectorType      DellSerialPortConnectorType,
    serialPortName               DellString,
    serialPortMaximumSpeed       DellUnsigned32BitRange,
    serialPortCapabilitiesUnique DellSerialPortCapabilitiesUnique,
    serialPortBaseIOAddress      DellUnsigned64BitRange,
    serialPortIRQLevel           DellUnsigned8BitRange
}

serialPortTable                 OBJECT-TYPE
    SYNTAX      SEQUENCE OF SerialPortTableEntry
    ACCESS      not-accessible
    STATUS      mandatory
    DESCRIPTION
"1000.0080 This Group defines the Dell Serial Port Table."
    ::= { portGroup 80 }
serialPortTableEntry            OBJECT-TYPE
    SYNTAX      SerialPortTableEntry
    ACCESS      not-accessible
    STATUS      mandatory
    DESCRIPTION
"1000.0080.0001 This Group defines the Dell Serial Port Table Entry."
    INDEX       { serialPortchassisIndex, serialPortIndex }
    ::= { serialPortTable 1 }
serialPortchassisIndex              OBJECT-TYPE
    SYNTAX      DellObjectRange
    ACCESS      read-only
    STATUS      mandatory
    DESCRIPTION
"1000.0080.0001.0001 This attribute defines the index (one based) of
this Dell chassis."
    ::= { serialPortTableEntry 1 }
serialPortIndex                 OBJECT-TYPE
    SYNTAX      DellObjectRange
    ACCESS      read-only
    STATUS      mandatory
    DESCRIPTION
"1000.0080.0001.0002 This attribute defines the index of the Dell
Serial Port in this chassis."
    ::= { serialPortTableEntry 2 }
serialPortStateCapabilities     OBJECT-TYPE
    SYNTAX      DellStateCapabilities
    ACCESS      read-only
    STATUS      mandatory
    DESCRIPTION
"1000.0080.0001.0003 This attribute defines the capabilities of the Dell
Serial Port."
    ::= { serialPortTableEntry 3 }
serialPortStateSettings         OBJECT-TYPE
    SYNTAX      DellStateSettings
    ACCESS      read-write
    STATUS      mandatory
    DESCRIPTION
"1000.0080.0001.0004 This attribute defines the state of the Dell
Serial Port."
    ::= { serialPortTableEntry 4 }
serialPortStatus                OBJECT-TYPE
    SYNTAX      DellStatus
    ACCESS      read-only
    STATUS      mandatory
    DESCRIPTION
"1000.0080.0001.0005 This attribute defines the status of the Dell
Serial Port."
    ::= { serialPortTableEntry 5 }
serialPortSecurityState      OBJECT-TYPE
    SYNTAX      DellPortSecurityState
    ACCESS      read-only
    STATUS      mandatory
    DESCRIPTION
"1000.0080.0001.0006 This attribute defines the security settings of the
Dell Serial Port."
    ::= { serialPortTableEntry 6 }
serialPortConnectorType         OBJECT-TYPE
    SYNTAX      DellSerialPortConnectorType
    ACCESS      read-only
    STATUS      mandatory
    DESCRIPTION
"1000.0080.0001.0007 This attribute defines the connector type of the
Dell Serial Port."
    ::= { serialPortTableEntry 7 }
serialPortName              OBJECT-TYPE
    SYNTAX      DellString
    ACCESS      read-only
    STATUS      mandatory
    DESCRIPTION
"1000.0080.0001.0008 This attribute defines the name of the
Dell Serial Port."
    ::= { serialPortTableEntry 8 }
serialPortMaximumSpeed          OBJECT-TYPE
    SYNTAX      DellUnsigned32BitRange
    ACCESS      read-only
    STATUS      mandatory
    DESCRIPTION
"1000.0080.0001.0009 This attribute defines the maximum speed the serial
interface can support in BPS (bits per second).
        0 (zero) indicated maximum port speed is unknown."
    ::= { serialPortTableEntry 9 }
serialPortCapabilitiesUnique   OBJECT-TYPE
    SYNTAX      DellSerialPortCapabilitiesUnique
    ACCESS      read-only
    STATUS      mandatory
    DESCRIPTION
"1000.0080.0001.0010 This attribute defines the capabilities of the
Dell Serial Port."
    ::= { serialPortTableEntry 10 }
serialPortBaseIOAddress         OBJECT-TYPE
    SYNTAX      DellUnsigned64BitRange
    ACCESS      read-only
    STATUS      mandatory
    DESCRIPTION
"1000.0080.0001.0011 This attribute defines the Base Input Output
address of the Dell Serial Port."
    ::= { serialPortTableEntry 11 }
serialPortIRQLevel              OBJECT-TYPE
    SYNTAX      DellUnsigned8BitRange
    ACCESS      read-only
    STATUS      mandatory
    DESCRIPTION
"1000.0080.0001.0012 This attribute defines the Interrupt Request Level
of the Dell Serial Port."
    ::= { serialPortTableEntry 12 }


-------------------------------------------------------------------------------
-- USB Port Table
-------------------------------------------------------------------------------

DellUSBPortConnectorType            ::= INTEGER {
    connectorPortTypeIsOther(1),    -- there is not one of the following:
    connectorPortTypeIsUnknown(2),  -- the port connector type is unknown
    connectorPortTypeIsUSB(3)       -- the type of port connector is a universal serial bus
}

USBPortTableEntry                   ::= SEQUENCE {
    uSBPortchassisIndex             DellObjectRange,
    uSBPortIndex                    DellObjectRange,
    uSBPortStateCapabilities        DellStateCapabilities,
    uSBPortStateSettings            DellStateSettings,
    uSBPortStatus                   DellStatus,
    uSBPortSecurityState            DellPortSecurityState,
    uSBPortConnectorType            DellUSBPortConnectorType,
    uSBPortName                     DellString,
    uSBPortBIOSConnectorType        DellGenericPortConnectorType
}

uSBPortTable                        OBJECT-TYPE
    SYNTAX      SEQUENCE OF USBPortTableEntry
    ACCESS      not-accessible
    STATUS      mandatory
    DESCRIPTION
"1000.0090 This Group defines the Dell USB Port Table."
    ::= { portGroup 90 }
uSBPortTableEntry                   OBJECT-TYPE
    SYNTAX      USBPortTableEntry
    ACCESS      not-accessible
    STATUS      mandatory
    DESCRIPTION
"1000.0090.0001 This Group defines the Dell USB Port Table Entry."
    INDEX       { uSBPortchassisIndex, uSBPortIndex }
    ::= { uSBPortTable 1 }
uSBPortchassisIndex                 OBJECT-TYPE
    SYNTAX      DellObjectRange
    ACCESS      read-only
    STATUS      mandatory
    DESCRIPTION
"1000.0090.0001.0001 This attribute defines the index (one based) of
this Dell chassis."
    ::= { uSBPortTableEntry 1 }
uSBPortIndex                        OBJECT-TYPE
    SYNTAX      DellObjectRange
    ACCESS      read-only
    STATUS      mandatory
    DESCRIPTION
"1000.0090.0001.0002 This attribute defines the index of the Dell USB
Port in this chassis."
    ::= { uSBPortTableEntry 2 }
uSBPortStateCapabilities             OBJECT-TYPE
    SYNTAX      DellStateCapabilities
    ACCESS      read-only
    STATUS      mandatory
    DESCRIPTION
"1000.0090.0001.0003 This attribute defines the capabilities the
Dell USB Port."
    ::= { uSBPortTableEntry 3 }
uSBPortStateSettings                OBJECT-TYPE
    SYNTAX      DellStateSettings
    ACCESS      read-write
    STATUS      mandatory
    DESCRIPTION
"1000.0090.0001.0004 This attribute defines the status of the
Dell USB Port."
    ::= { uSBPortTableEntry 4 }
uSBPortStatus                       OBJECT-TYPE
    SYNTAX      DellStatus
    ACCESS      read-only
    STATUS      mandatory
    DESCRIPTION
"1000.0090.0001.0005 This attribute defines the state of the Dell USB Port."
    ::= { uSBPortTableEntry 5 }
uSBPortSecurityState             OBJECT-TYPE
    SYNTAX      DellPortSecurityState
    ACCESS      read-only
    STATUS      mandatory
    DESCRIPTION
"1000.0090.0001.0006 This attribute defines the security settings of the
Dell USB Port."
    ::= { uSBPortTableEntry 6 }
uSBPortConnectorType                OBJECT-TYPE
    SYNTAX      DellUSBPortConnectorType
    ACCESS      read-only
    STATUS      mandatory
    DESCRIPTION
"1000.0090.0001.0007 This attribute defines the connector type of the
Dell USB Port."
    ::= { uSBPortTableEntry 7 }
uSBPortName                         OBJECT-TYPE
    SYNTAX      DellString
    ACCESS      read-only
    STATUS      mandatory
    DESCRIPTION
"1000.0090.0001.0008 This attribute defines name of the Dell USB Port."
    ::= { uSBPortTableEntry 8 }
uSBPortBIOSConnectorType            OBJECT-TYPE
    SYNTAX      DellGenericPortConnectorType
    ACCESS      read-only
    STATUS      mandatory
    DESCRIPTION
"1000.0090.0001.0009 This attribute defines the BIOS connector type of
the Dell USB Port."
    ::= { uSBPortTableEntry 9 }


-------------------------------------------------------------------------------
--
-- Device Group
--
-------------------------------------------------------------------------------

-------------------------------------------------------------------------------
-- Pointing Device Table
-------------------------------------------------------------------------------

DellPointingDeviceType          ::= INTEGER {
    deviceTypeIsOther(1),       -- there is not one of the following:
    deviceTypeIsUnknown(2),     -- the device type is unknown
    deviceTypeIsAMouse(3),      -- the type of device is a mouse
    deviceTypeIsATrackBall(4),  -- the type of device is a track ball
    deviceTypeIsATrackPoint(5), -- the type of device is a track point
    deviceTypeIsAGlidePoint(6), -- the type of device is a glide point
    deviceTypeIsATouchPad(7)    -- the type of device is a touch pad
}

PointingDeviceTableEntry            ::= SEQUENCE {
    pointingDevicechassisIndex      DellObjectRange,
    pointingDeviceIndex             DellObjectRange,
    pointingDeviceStateCapabilities DellStateCapabilities,
    pointingDeviceStateSettings     DellStateSettings,
    pointingDeviceStatus            DellStatus,
    pointingPortIndexReference      DellObjectRange,
    pointingDeviceType              DellPointingDeviceType,
    pointingDeviceNumberofButtons   DellUnsigned8BitRange
}

pointingDeviceTable                 OBJECT-TYPE
    SYNTAX      SEQUENCE OF PointingDeviceTableEntry
    ACCESS      not-accessible
    STATUS      mandatory
    DESCRIPTION
"1100.0010 This Group defines the Dell Pointing Device Table.
It references the Dell Pointing Port Index."
    ::= { deviceGroup 10 }
pointingDeviceTableEntry            OBJECT-TYPE
    SYNTAX      PointingDeviceTableEntry
    ACCESS      not-accessible
    STATUS      mandatory
    DESCRIPTION
"1100.0010.0001 This Group defines the Dell Pointing Device Table Entry."
    INDEX       { pointingDevicechassisIndex, pointingDeviceIndex }
    ::= { pointingDeviceTable 1 }
pointingDevicechassisIndex              OBJECT-TYPE
    SYNTAX      DellObjectRange
    ACCESS      read-only
    STATUS      mandatory
    DESCRIPTION
"1100.0010.0001.0001 This attribute defines the index (one based) of
this Dell chassis."
    ::= { pointingDeviceTableEntry 1 }
pointingDeviceIndex                 OBJECT-TYPE
    SYNTAX      DellObjectRange
    ACCESS      read-only
    STATUS      mandatory
    DESCRIPTION
"1100.0010.0001.0002 This attribute defines the index of the Dell
Pointing Device in this chassis."
    ::= { pointingDeviceTableEntry 2 }
pointingDeviceStateCapabilities      OBJECT-TYPE
    SYNTAX      DellStateCapabilities
    ACCESS      read-only
    STATUS      mandatory
    DESCRIPTION
"1100.0010.0001.0003 This attribute defines the capabilities of the
Dell Pointing Device."
    ::= { pointingDeviceTableEntry 3 }
pointingDeviceStateSettings         OBJECT-TYPE
    SYNTAX      DellStateSettings
    ACCESS      read-write
    STATUS      mandatory
    DESCRIPTION
"1100.0010.0001.0004 This attribute defines the state of the Dell Pointing
Device."
    ::= { pointingDeviceTableEntry 4 }
pointingDeviceStatus                OBJECT-TYPE
    SYNTAX      DellStatus
    ACCESS      read-only
    STATUS      mandatory
    DESCRIPTION
"1100.0010.0001.0005 This attribute defines the status of the Dell Pointing
Device."
    ::= { pointingDeviceTableEntry 5 }
pointingPortIndexReference              OBJECT-TYPE
    SYNTAX      DellObjectRange
    ACCESS      read-only
    STATUS      mandatory
    DESCRIPTION
"1100.0010.0001.0006 This attribute defines the index to the associated
Dell Pointing Port in this chassis."
    ::= { pointingDeviceTableEntry 6 }
pointingDeviceType                  OBJECT-TYPE
    SYNTAX      DellPointingDeviceType
    ACCESS      read-only
    STATUS      mandatory
    DESCRIPTION
"1100.0010.0001.0007 This attribute defines the type of the Dell
Pointing Device."
    ::= { pointingDeviceTableEntry 7 }
pointingDeviceNumberofButtons       OBJECT-TYPE
    SYNTAX      DellUnsigned8BitRange
    ACCESS      read-only
    STATUS      mandatory
    DESCRIPTION
"1100.0010.0001.0008 This attribute defines the number of buttons on the
Dell Pointing Device."
    ::= { pointingDeviceTableEntry 8 }


-------------------------------------------------------------------------------
-- Keyboard Device Table
-------------------------------------------------------------------------------

KeyboardDeviceTableEntry            ::= SEQUENCE {
    keyboardDevicechassisIndex      DellObjectRange,
    keyboardDeviceIndex             DellObjectRange,
    keyboardDeviceStateCapabilities DellStateCapabilities,
    keyboardDeviceStateSettings     DellStateSettings,
    keyboardDeviceStatus            DellStatus,
    keyboardPortIndexReference      DellObjectRange,
    keyboardDeviceTypeName          DellString,
    keyboardDeviceLayoutName        DellString
}

keyboardDeviceTable             OBJECT-TYPE
    SYNTAX      SEQUENCE OF KeyboardDeviceTableEntry
    ACCESS      not-accessible
    STATUS      mandatory
    DESCRIPTION
"1100.0020 This Group defines the Dell Keyboard Device Table.
It references the Dell Keyboard Port Index."
    ::= { deviceGroup 20 }
keyboardDeviceTableEntry        OBJECT-TYPE
    SYNTAX      KeyboardDeviceTableEntry
    ACCESS      not-accessible
    STATUS      mandatory
    DESCRIPTION
"1100.0020.0001 This Group defines the Dell Keyboard Device Table Entry."
    INDEX       { keyboardDevicechassisIndex, keyboardDeviceIndex }
    ::= { keyboardDeviceTable 1 }
keyboardDevicechassisIndex              OBJECT-TYPE
    SYNTAX      DellObjectRange
    ACCESS      read-only
    STATUS      mandatory
    DESCRIPTION
"1100.0020.0001.0001 This attribute defines the index (one based) of
this Dell chassis."
    ::= { keyboardDeviceTableEntry 1 }
keyboardDeviceIndex             OBJECT-TYPE
    SYNTAX      DellObjectRange
    ACCESS      read-only
    STATUS      mandatory
    DESCRIPTION
"1100.0020.0001.0002 This attribute defines the index of the Dell
Keyboard Device in this chassis."
    ::= { keyboardDeviceTableEntry 2 }
keyboardDeviceStateCapabilities  OBJECT-TYPE
    SYNTAX      DellStateCapabilities
    ACCESS      read-only
    STATUS      mandatory
    DESCRIPTION
"1100.0020.0001.0003 This attribute defines the capabilities of the Dell
Keyboard Device."
    ::= { keyboardDeviceTableEntry 3 }
keyboardDeviceStateSettings  OBJECT-TYPE
    SYNTAX      DellStateSettings
    ACCESS      read-write
    STATUS      mandatory
    DESCRIPTION
"1100.0020.0001.0004 This attribute defines the state of the Dell
Keyboard Device."
    ::= { keyboardDeviceTableEntry 4 }
keyboardDeviceStatus            OBJECT-TYPE
    SYNTAX      DellStatus
    ACCESS      read-only
    STATUS      mandatory
    DESCRIPTION
"1100.0020.0001.0005 This attribute defines the status of the Dell
Keyboard Device."
    ::= { keyboardDeviceTableEntry 5 }
keyboardPortIndexReference      OBJECT-TYPE
    SYNTAX      DellObjectRange
    ACCESS      read-only
    STATUS      mandatory
    DESCRIPTION
"1100.0020.0001.0006 This attribute defines the index to the associated
Dell Keyboard Port in this chassis."
    ::= { keyboardDeviceTableEntry 6 }
keyboardDeviceTypeName          OBJECT-TYPE
    SYNTAX      DellString
    ACCESS      read-only
    STATUS      mandatory
    DESCRIPTION
"1100.0020.0001.0007 This is the name of the Dell keyboard type."
    ::= { keyboardDeviceTableEntry 7 }
keyboardDeviceLayoutName        OBJECT-TYPE
    SYNTAX      DellString
    ACCESS      read-only
    STATUS      mandatory
    DESCRIPTION
"1100.0020.0001.0008 This is the name of the Dell keyboard layout."
    ::= { keyboardDeviceTableEntry 8 }


-------------------------------------------------------------------------------
-- Processor Device Table
-------------------------------------------------------------------------------

DellProcessorDeviceType              ::= INTEGER {
    deviceTypeIsOther(1),            -- there is not one of the following:
    deviceTypeIsUnknown(2),          -- the device type is unknown
    deviceTypeIsCPU(3),              -- the type of device is a central processing unit
    deviceTypeIsMathProcessor(4),    -- the type of device is a math processor
    deviceTypeIsDSP(5),              -- the type of device is a digital signal processor
    deviceTypeIsAVideoProcessor(6)   -- the type of device is a video processor
}
DellProcessorDeviceFamily            ::= INTEGER {
    deviceFamilyIsOther(1),          -- there is not one of the following:
    deviceFamilyIsUnknown(2),        -- the device family is unknown
    deviceFamilyIs8086(3),           -- the family of the device is an  8086
    deviceFamilyIs80286(4),          -- the family of the device is an 80286
    deviceFamilyIs80386(5),          -- the family of the device is an 80386
    deviceFamilyIs80486(6),          -- the family of the device is an 80486
    deviceFamilyIs8087(7),           -- the family of the device is an  8087
    deviceFamilyIs80287(8),          -- the family of the device is an 80287
    deviceFamilyIs80387(9),          -- the family of the device is an 80387
    deviceFamilyIs80487(10),         -- the family of the device is an 80487
    deviceFamilyIsPentium(11),       -- the family of the device is a  pentium
    deviceFamilyIsPentiumPro(12),    -- the family of the device is a  pentium pro
    deviceFamilyIsPentium2(13),      -- the family of the device is a  pentium II
    deviceFamilyIsPentiumMMX(14),    -- the family of the device is a  pentium mmx
    deviceFamilyIsCeleron(15),       -- the family of the device is a  celeron
    deviceFamilyIsXeon(16),          -- the family of the device is a  xeon
    deviceFamilyIsPentium3(17),      -- the family of the device is a  pentium III
    deviceFamilyIsPentium3Xeon(18),  -- the family of the device is a  pentium III xeon
    deviceFamilyIsPentium3Step(19),  -- the family of the device is a  pentium III Speed Step
    deviceFamilyIsPentiumItanium(20),-- the family of the device is a  pentium itanium
    deviceFamilyIsIntelXeon(21),     -- the family of the device is an Intel Xeon
    deviceFamilyIsPentium4(22),      -- the family of the device is a  pentium 4
    deviceFamilyIsIntelXeonMP(23)    -- the family of the device is an Intel Xeon MP
}
DellProcessorDeviceStatusState       ::= INTEGER {
    other(1),                        -- the status is not one of the following:
    unknown(2),                      -- the device type is unknown
    enabled(3),                      -- the device is enabled
    userDisabled(4),                 -- the device is disabled by the user
    biosDisabled(5),                 -- the device has it's BIOS disabled
    idle(6)                          -- the device is idle
}
DellProcessorUpgradeInformation           ::= INTEGER {
    processorUpgradeIsOther(1),           -- there is not one of the following:
    processorUpgradeIsUnknown(2),         -- the upgrade device type is unknown
    processorUpgradeIsByDaughterBoard(3), -- the upgrade device type is on a daughterboard
    processorUpgradeIsByZIFSocket(4),     -- the upgrade device type is in a ZIF socket
    processorUpgradeIsByReplacement(5),   -- the upgrade device type is a replacement
    processorUpgradeIsNone(6),            -- there is no upgrade device type
    processorUpgradeIsByLIFSocket(7),     -- the upgrade device type is in a LIF socket
    processorUpgradeIsBySlot1(8),         -- the upgrade device type is a SLOT 1 processor
    processorUpgradeIsBySlot2(9),         -- the upgrade device type is a SLOT 2 processor
    processorUpgradeIsByP370(10)          -- the upgrade device type is a pin 370 processor
}

ProcessorDeviceTableEntry                   ::= SEQUENCE {
    processorDevicechassisIndex             DellObjectRange,
    processorDeviceIndex                    DellObjectRange,
    processorDeviceStateCapabilities        DellStateCapabilities,
    processorDeviceStateSettings            DellStateSettings,
    processorDeviceStatus                   DellStatus,
    processorPortIndexReference             DellObjectRange,
    processorDeviceType                     DellProcessorDeviceType,
    processorDeviceManufacturerName         DellString,
    processorDeviceStatusState              DellProcessorDeviceStatusState,
    processorDeviceFamily                   DellProcessorDeviceFamily,
    processorDeviceMaximumSpeed             DellUnsigned32BitRange,
    processorDeviceCurrentSpeed             DellUnsigned32BitRange,
    processorDeviceExternalClockSpeed       DellUnsigned32BitRange,
    processorDeviceVoltage                  DellSigned32BitRange,
    processorDeviceUpgradeInformation       DellProcessorUpgradeInformation,
    processorDeviceVersionName              DellString
}

processorDeviceTable                    OBJECT-TYPE
    SYNTAX      SEQUENCE OF ProcessorDeviceTableEntry
    ACCESS      not-accessible
    STATUS      mandatory
    DESCRIPTION
"1100.0030 This Group defines the Dell Processor Device Table.
It references the Dell Processor Port Index."
    ::= { deviceGroup 30 }
processorDeviceTableEntry               OBJECT-TYPE
    SYNTAX      ProcessorDeviceTableEntry
    ACCESS      not-accessible
    STATUS      mandatory
    DESCRIPTION
"1100.0030.0001 This Group defines the Dell Processor Device Table Entry."
    INDEX       { processorDevicechassisIndex, processorDeviceIndex }
    ::= { processorDeviceTable 1 }
processorDevicechassisIndex                 OBJECT-TYPE
    SYNTAX      DellObjectRange
    ACCESS      read-only
    STATUS      mandatory
    DESCRIPTION
"1100.0030.0001.0001 This attribute defines the index (one based) of
this Dell chassis."
    ::= { processorDeviceTableEntry 1 }
processorDeviceIndex                    OBJECT-TYPE
    SYNTAX      DellObjectRange
    ACCESS      read-only
    STATUS      mandatory
    DESCRIPTION
"1100.0030.0001.0002 This attribute defines the index of the Dell Processor
Device in this chassis."
    ::= { processorDeviceTableEntry 2 }
processorDeviceStateCapabilities        OBJECT-TYPE
    SYNTAX      DellStateCapabilities
    ACCESS      read-only
    STATUS      mandatory
    DESCRIPTION
"1100.0030.0001.0003 This attribute defines the capabilities of the Dell
Processor Device."
    ::= { processorDeviceTableEntry 3 }
processorDeviceStateSettings           OBJECT-TYPE
    SYNTAX      DellStateSettings
    ACCESS      read-write
    STATUS      mandatory
    DESCRIPTION
"1100.0030.0001.0004 This attribute defines the state of the Dell
Processor Device."
    ::= { processorDeviceTableEntry 4 }
processorDeviceStatus                   OBJECT-TYPE
    SYNTAX      DellStatus
    ACCESS      read-only
    STATUS      mandatory
    DESCRIPTION
"1100.0030.0001.0005 This attribute defines the status of the Dell
Processor Device."
    ::= { processorDeviceTableEntry 5 }
processorPortIndexReference             OBJECT-TYPE
    SYNTAX      DellObjectRange
    ACCESS      read-only
    STATUS      mandatory
    DESCRIPTION
"1100.0030.0001.0006 This attribute defines the index to the associated
Dell Processor Port in this chassis."
    ::= { processorDeviceTableEntry 6 }
processorDeviceType                     OBJECT-TYPE
    SYNTAX      DellProcessorDeviceType
    ACCESS      read-only
    STATUS      mandatory
    DESCRIPTION
"1100.0030.0001.0007 This attribute defines the type of Dell Processor
Device."
    ::= { processorDeviceTableEntry 7 }
processorDeviceManufacturerName         OBJECT-TYPE
    SYNTAX      DellString
    ACCESS      read-only
    STATUS      mandatory
    DESCRIPTION
"1100.0030.0001.0008 This is the name of manufacturer of the
Dell processor."
    ::= { processorDeviceTableEntry 8 }
processorDeviceStatusState              OBJECT-TYPE
    SYNTAX      DellProcessorDeviceStatusState
    ACCESS      read-only
    STATUS      mandatory
    DESCRIPTION
"1100.0030.0001.0009 This attribute defines the status state of
the Dell Processor Device."
    ::= { processorDeviceTableEntry 9 }
processorDeviceFamily                   OBJECT-TYPE
    SYNTAX      DellProcessorDeviceFamily
    ACCESS      read-only
    STATUS      mandatory
    DESCRIPTION
"1100.0030.0001.0010 This attribute defines the family of the Dell
Processor Device."
    ::= { processorDeviceTableEntry 10 }
processorDeviceMaximumSpeed             OBJECT-TYPE
    SYNTAX      DellUnsigned32BitRange
    ACCESS      read-only
    STATUS      mandatory
    DESCRIPTION
"1100.0030.0001.0011 This attribute defines the maximum speed of the
Dell Processor Device in MHz, a 0 (zero) indicates the speed is unknown."
    ::= { processorDeviceTableEntry 11 }
processorDeviceCurrentSpeed             OBJECT-TYPE
    SYNTAX      DellUnsigned32BitRange
    ACCESS      read-only
    STATUS      mandatory
    DESCRIPTION
"1100.0030.0001.0012 This attribute defines the current speed of the
Dell Processor Device in MHz, a 0 (zero) indicates the speed is unknown."
    ::= { processorDeviceTableEntry 12 }
processorDeviceExternalClockSpeed       OBJECT-TYPE
    SYNTAX      DellUnsigned32BitRange
    ACCESS      read-only
    STATUS      mandatory
    DESCRIPTION
"1100.0030.0001.0013 This attribute defines the speed of the
external clock for the Dell Processor Device in MHz,  a 0 (zero) indicates
the speed is unknown."
    ::= { processorDeviceTableEntry 13 }
processorDeviceVoltage                  OBJECT-TYPE
    SYNTAX      DellSigned32BitRange
    ACCESS      read-only
    STATUS      mandatory
    DESCRIPTION
"1100.0030.0001.0014 This attribute defines the voltage powering the
Dell Processor Device in millivolts, a 0 (zero) indicates the speed is
unknown."
    ::= { processorDeviceTableEntry 14 }
processorDeviceUpgradeInformation       OBJECT-TYPE
    SYNTAX      DellProcessorUpgradeInformation
    ACCESS      read-only
    STATUS      mandatory
    DESCRIPTION
"1100.0030.0001.0015 This attribute defines the processor upgrade
information for the Dell Processor Device."
    ::= { processorDeviceTableEntry 15 }
processorDeviceVersionName              OBJECT-TYPE
    SYNTAX      DellString
    ACCESS      read-only
    STATUS      mandatory
    DESCRIPTION
"1100.0030.0001.0016 This is the name of the version of the
Dell processor."
    ::= { processorDeviceTableEntry 16 }


-------------------------------------------------------------------------------
-- Cache Device Table
-------------------------------------------------------------------------------

DellCacheDeviceType                     ::= INTEGER {
    deviceTypeIsOther(1),               -- there is not one of the following:
    deviceTypeIsUnknown(2),             -- the SystemCache type is unknown
    deviceTypeIsInstruction(3),         -- the System Cache type is instruction
    deviceTypeIsData(4),                -- the System Cache type is data
    deviceTypeIsUnified(5)              -- the System Cache type is both
}
DellCacheDeviceLevel                    ::= INTEGER {
    deviceLevelIsOther(1),              -- there is not one of the following:
    deviceLevelIsUnknown(2),            -- the device level is unknown
    deviceLevelIsPrimary(3),            -- the level of device is primary
    deviceLevelIsSecondary(4),          -- the level of device is secondary
    deviceLevelIsTertiary(5)            -- the level of device is tertiary
}
DellCacheDeviceWritePolicy                 ::= INTEGER {
    deviceWritePolicyIsOther(1),           -- there is not one of the following:
    deviceWritePolicyIsUnknown(2),         -- the device write policy is unknown
    deviceWritePolicyIsWriteBack(3),       -- the type of write policy is write back
    deviceWritePolicyIsWriteThrough(4),    -- the type of write policy is write through
    deviceWritePolicyIsVariesByAddress(5), -- the type of write policy varies by address
    deviceWritePolicyIsDeterminedByIO(6)   -- the type of write policy is determined by IO query
}
DellCacheDeviceStatusState              ::= INTEGER {
    other(1),                           -- there is not one of the following:
    unknown(2),                         -- the device status state is unknown
    enabled(3),                         -- the device is enabled
    userDisabled(4),                    -- the device is disabled by the user
    biosDisabled(5)                     -- the device has it's BIOS disabled
}
DellCacheDeviceECCType                  ::= INTEGER {
    deviceECCTypeIsOther(1),            -- there is not one of the following:
    deviceECCTypeIsUnknown(2),          -- the device error correction type is unknown
    deviceECCTypeIsNone(3),             -- the device error correction type is none
    deviceECCTypeIsParity(4),           -- the device error correction type is parity
    deviceECCTypeIsSingleBitECC(5),     -- the device error correction type is single bit ecc
    deviceECCTypeIsMultiBitECC(6),      -- the device error correction type is multibit ecc
    deviceECCTypeIsCRC(7)               -- the device error correction type is crc
}
DellCacheDeviceAssociativity                        ::= INTEGER {
    deviceAssociativityIsOther(1),                  -- there is not one of the following:
    deviceAssociativityIsUnknown(2),                -- the device associativity is unknown
    deviceAssociativityIsDirectMapped(3),           -- the device associativity is direct mapped
    deviceAssociativityIsTwoWaySetAssociative(4),   -- the device associativity is two way set associative
    deviceAssociativityIsFourWaySetAssociative(5),  -- the device associativity is four way set associative
    deviceAssociativityIsFullyAssociative(6),       -- the device associativity is fully associative
    deviceAssociativityIsEightWaySetAssociative(7), -- the device associativity is eight way set associative
    deviceAssociativityIsSixteenWaySetAssociative(8)-- the device associativity is sixteen way set associative
}
DellCacheDeviceLocation                 ::= INTEGER {
    deviceLocationIsOther(1),           -- there is not one of the following:
    deviceLocationIsUnknown(2),         -- the device location is unknown
    deviceLocationIsInternal(3),        -- the location of the device is internal
    deviceLocationIsExternal(4)         -- the location of the device is external
}
DellCacheDeviceSRAMType                 ::= INTEGER {
    deviceSRAMTypeIsOther(1),           -- there is not one of the following:
    deviceSRAMTypeIsUnknown(2),         -- the device SRAM type is unknown
    deviceSRAMTypeIsNonBurst(3),        -- the SRAM type of device is nonburst
    deviceSRAMTypeIsBurst(4),           -- the SRAM type of device is burst
    deviceSRAMTypeIsPipeBurst(5),       -- the SRAM type of device is pipeburst
    deviceSRAMTypeIsSynchronous(6),     -- the SRAM type of device is synchronous
    deviceSRAMTypeIsAsynchronous(7)     -- the SRAM type of device is asynchronous
}

CacheDeviceTableEntry                        ::= SEQUENCE {
    cacheDevicechassisIndex                  DellObjectRange,
    cacheDeviceIndex                         DellObjectRange,
    cacheDeviceStateCapabilities             DellStateCapabilities,
    cacheDeviceStateSettings                 DellStateSettings,
    cacheDeviceStatus                        DellStatus,
    cacheDeviceprocessorDeviceIndexReference DellObjectRange,
    cacheDeviceType                          DellCacheDeviceType,
    cacheDeviceLocation                      DellCacheDeviceLocation,
    cacheDeviceStatusState                   DellCacheDeviceStatusState,
    cacheDeviceExternalSocketName            DellString,
    cacheDeviceLevel                         DellCacheDeviceLevel,
    cacheDeviceMaximumSize                   DellUnsigned32BitRange,
    cacheDeviceCurrentSize                   DellUnsigned32BitRange,
    cacheDeviceSpeed                         DellUnsigned32BitRange,
    cacheDeviceWritePolicy                   DellCacheDeviceWritePolicy,
    cacheDeviceIsSocketed                    DellBoolean,
    cacheDeviceECCType                       DellCacheDeviceECCType,
    cacheDeviceAssociativity                 DellCacheDeviceAssociativity,
    cacheDeviceSupportedType                 DellCacheDeviceSRAMType,
    cacheDeviceCurrentType                   DellCacheDeviceSRAMType
}

cacheDeviceTable                    OBJECT-TYPE
    SYNTAX      SEQUENCE OF CacheDeviceTableEntry
    ACCESS      not-accessible
    STATUS      mandatory
    DESCRIPTION
"1100.0040 This Group defines the Dell Cache Device Table."
    ::= { deviceGroup 40 }
cacheDeviceTableEntry               OBJECT-TYPE
    SYNTAX      CacheDeviceTableEntry
    ACCESS      not-accessible
    STATUS      mandatory
    DESCRIPTION
"1100.0040.0001 This Group defines the Dell Cache Device Table Entry."
    INDEX       { cacheDevicechassisIndex, cacheDeviceIndex }
    ::= { cacheDeviceTable 1 }
cacheDevicechassisIndex                 OBJECT-TYPE
    SYNTAX      DellObjectRange
    ACCESS      read-only
    STATUS      mandatory
    DESCRIPTION
"1100.0040.0001.0001 This attribute defines the index (one based) of
this Dell chassis."
    ::= { cacheDeviceTableEntry 1 }
cacheDeviceIndex                    OBJECT-TYPE
    SYNTAX      DellObjectRange
    ACCESS      read-only
    STATUS      mandatory
    DESCRIPTION
"1100.0040.0001.0002 This attribute defines the index of the Dell
Cache Device in this chassis."
    ::= { cacheDeviceTableEntry 2 }
cacheDeviceStateCapabilities       OBJECT-TYPE
    SYNTAX      DellStateCapabilities
    ACCESS      read-only
    STATUS      mandatory
    DESCRIPTION
"1100.0040.0001.0003 This attribute defines the capabilities of the Dell
Cache Device."
    ::= { cacheDeviceTableEntry 3 }
cacheDeviceStateSettings            OBJECT-TYPE
    SYNTAX      DellStateSettings
    ACCESS      read-write
    STATUS      mandatory
    DESCRIPTION
"1100.0040.0001.0004 This attribute defines the state of the Dell
Cache Device."
    ::= { cacheDeviceTableEntry 4 }
cacheDeviceStatus                   OBJECT-TYPE
    SYNTAX      DellStatus
    ACCESS      read-only
    STATUS      mandatory
    DESCRIPTION
"1100.0040.0001.0005 This attribute defines the status of the Dell
Cache Device."
    ::= { cacheDeviceTableEntry 5 }
cacheDeviceprocessorDeviceIndexReference     OBJECT-TYPE
    SYNTAX      DellObjectRange
    ACCESS      read-only
    STATUS      mandatory
    DESCRIPTION
"1100.0040.0001.0006 This attribute defines the index number of the
processor device that this Dell cache Device is associated with."
    ::= { cacheDeviceTableEntry 6 }
cacheDeviceType                     OBJECT-TYPE
    SYNTAX      DellCacheDeviceType
    ACCESS      read-only
    STATUS      mandatory
    DESCRIPTION
"1100.0040.0001.0007 This attribute defines the type of Dell Cache Device."
    ::= { cacheDeviceTableEntry 7 }
cacheDeviceLocation                 OBJECT-TYPE
    SYNTAX      DellCacheDeviceLocation
    ACCESS      read-only
    STATUS      mandatory
    DESCRIPTION
"1100.0040.0001.0008 This is the location of the Dell cache."
    ::= { cacheDeviceTableEntry 8 }
cacheDeviceStatusState              OBJECT-TYPE
    SYNTAX      DellCacheDeviceStatusState
    ACCESS      read-only
    STATUS      mandatory
    DESCRIPTION
"1100.0040.0001.0009 This attribute defines the status state of the Dell
Cache Device."
    ::= { cacheDeviceTableEntry 9 }
cacheDeviceExternalSocketName       OBJECT-TYPE
    SYNTAX      DellString
    ACCESS      read-only
    STATUS      mandatory
    DESCRIPTION
"1100.0040.0001.0010 This is the name of the external socket name of the
Dell cache if the cache is socketed."
    ::= { cacheDeviceTableEntry 10 }
cacheDeviceLevel                    OBJECT-TYPE
    SYNTAX      DellCacheDeviceLevel
    ACCESS      read-only
    STATUS      mandatory
    DESCRIPTION
"1100.0040.0001.0011 This attribute defines the level of the Dell Cache
Device."
    ::= { cacheDeviceTableEntry 11 }
cacheDeviceMaximumSize              OBJECT-TYPE
    SYNTAX      DellUnsigned32BitRange
    ACCESS      read-only
    STATUS      mandatory
    DESCRIPTION
"1100.0040.0001.0012 This attribute defines the maximum size of the Dell
Cache Device in KBytes, a 0 (zero) indicates the size is unknown."
    ::= { cacheDeviceTableEntry 12 }
cacheDeviceCurrentSize              OBJECT-TYPE
    SYNTAX      DellUnsigned32BitRange
    ACCESS      read-only
    STATUS      mandatory
    DESCRIPTION
"1100.0040.0001.0013 This attribute defines the current size of the Dell
Cache Device in KBytes,
        a 0 (zero) indicates the size is unknown."
    ::= { cacheDeviceTableEntry 13 }
cacheDeviceSpeed                    OBJECT-TYPE
    SYNTAX      DellUnsigned32BitRange
    ACCESS      read-only
    STATUS      mandatory
    DESCRIPTION
"1100.0040.0001.0014 This attribute defines the speed of the Dell Cache
Device in nanoseconds,
        a 0 (zero) indicates the speed is unknown."
    ::= { cacheDeviceTableEntry 14 }
cacheDeviceWritePolicy              OBJECT-TYPE
    SYNTAX      DellCacheDeviceWritePolicy
    ACCESS      read-only
    STATUS      mandatory
    DESCRIPTION
"1100.0040.0001.0015 This attribute defines the write policy of the Dell
Cache Device."
    ::= { cacheDeviceTableEntry 15 }
cacheDeviceIsSocketed               OBJECT-TYPE
    SYNTAX      DellBoolean
    ACCESS      read-only
    STATUS      mandatory
    DESCRIPTION
"1100.0040.0001.0016 This is the attribute that defines if the Dell cache
is socketed or not."
    ::= { cacheDeviceTableEntry 16 }
cacheDeviceECCType                  OBJECT-TYPE
    SYNTAX      DellCacheDeviceECCType
    ACCESS      read-only
    STATUS      mandatory
    DESCRIPTION
"1100.0040.0001.0017 This is the type of error correction in use by the
Dell cache."
    ::= { cacheDeviceTableEntry 17 }
cacheDeviceAssociativity            OBJECT-TYPE
    SYNTAX      DellCacheDeviceAssociativity
    ACCESS      read-only
    STATUS      mandatory
    DESCRIPTION
"1100.0040.0001.0018 This is the type of associativity in use by the
Dell cache."
    ::= { cacheDeviceTableEntry 18 }
cacheDeviceSupportedType            OBJECT-TYPE
    SYNTAX      DellCacheDeviceSRAMType
    ACCESS      read-only
    STATUS      mandatory
    DESCRIPTION
"1100.0040.0001.0019 This is the type of SRAM the Dell cache can support."
    ::= { cacheDeviceTableEntry 19 }
cacheDeviceCurrentType              OBJECT-TYPE
    SYNTAX      DellCacheDeviceSRAMType
    ACCESS      read-only
    STATUS      mandatory
    DESCRIPTION
"1100.0040.0001.0020 This is the current type of SRAM for the Dell cache."
    ::= { cacheDeviceTableEntry 20 }


-------------------------------------------------------------------------------
-- Memory Device Table
-------------------------------------------------------------------------------

DellMemoryDeviceFormFactor                 ::= INTEGER {
    deviceFormFactorIsOther(1),            -- this device form factor is not one of the following:
    deviceFormFactorIsUnknown(2),          -- the device form factor is unknown
    deviceFormFactorIsSIMM(3),             -- the device form factor is SIMM
    deviceFormFactorIsSIP(4),              -- the device form factor is SIP
    deviceFormFactorIsAChip(5),            -- the device form factor is Chip
    deviceFormFactorIsDIP(6),              -- the device form factor is DIP
    deviceFormFactorIsZIP(7),              -- the device form factor is ZIP
    deviceFormFactorIsAProprietaryCard(8), -- the device form factor is a Proprietary Card
    deviceFormFactorIsDIMM(9),             -- the device form factor is DIMM
    deviceFormFactorIsTSOP(10),            -- the device form factor is TSOP
    deviceFormFactorIsARowOfChips(11),     -- the device form factor is a Row of chips
    deviceFormFactorIsRIMM(12),            -- the device form factor is RIMM
    deviceFormFactorIsSODIMM(13),          -- the device form factor is SODIMM
    deviceFormFactorIsSRIMM(14)            -- the device form factor is SRIMM
}
DellMemoryDeviceType                       ::= INTEGER {
    deviceTypeIsOther(1),                  -- this device type is not one of the following:
    deviceTypeIsUnknown(2),                -- the device type is unknown
    deviceTypeIsDRAM(3),                   -- the device type is DRAM
    deviceTypeIsEDRAM(4),                  -- the device type is EDRAM
    deviceTypeIsVRAM(5),                   -- the device type is VRAM
    deviceTypeIsSRAM(6),                   -- the device type is SRAM
    deviceTypeIsRAM(7),                    -- the device type is RAM
    deviceTypeIsROM(8),                    -- the device type is ROM
    deviceTypeIsFLASH(9),                  -- the device type is FLASH
    deviceTypeIsEEPROM(10),                -- the device type is EEPROM
    deviceTypeIsFEPROM(11),                -- the device type is FEPROM
    deviceTypeIsEPROM(12),                 -- the device type is EPROM
    deviceTypeIsCDRAM(13),                 -- the device type is CDRAM
    deviceTypeIs3DRAM(14),                 -- the device type is 3DRAM
    deviceTypeIsSDRAM(15),                 -- the device type is SDRAM
    deviceTypeIsSGRAM(16),                 -- the device type is SGRAM
    deviceTypeIsRDRAM(17),                 -- the device type is RDRAM
    deviceTypeIsDDR(18)                    -- the device type is DDR
}
DellMemoryDeviceTypeDetails                ::= INTEGER {
    deviceTypeDeatilIsOther(1),            -- this type is not one of the following:
    deviceTypeDetailIsUnknown(2),          -- the detailed device type is unknown
    deviceTypeDetailIsFastPaged(3),        -- the detailed device type is fast paged
    deviceTypeDetailIsStaticColumn(4),     -- the detailed device type is static column
    deviceTypeDetailIsPseudoStatic(5),     -- the detailed device type is pseudo-static
    deviceTypeDetailIsRAMBUS(6),           -- the detailed device type is RAMBUS
    deviceTypeDetailIsSynchronous(7),      -- the detailed device type is Synchronous
    deviceTypeDetailIsCMOS(8),             -- the detailed device type is CMOS
    deviceTypeDetailIsEDO(9),              -- the detailed device type is EDO
    deviceTypeDetailIsWindowDRAM(10),      -- the detailed device type is Window DRAM
    deviceTypeDetailIsCacheDRAM(11),       -- the detailed device type is Cache DRAM
    deviceTypeDetailIsNonVolatile(12)      -- the detailed device type is Non-volatile
}

MemoryDeviceTableEntry                      ::= SEQUENCE {
    memoryDevicechassisIndex                DellObjectRange,
    memoryDeviceIndex                       DellObjectRange,
    memoryDeviceStateCapabilities           DellStateCapabilities,
    memoryDeviceStateSettings               DellStateSettings,
    memoryDeviceStatus                      DellStatus,
    memoryDeviceMemoryPortIndexReference    DellObjectRange,
    memoryDeviceType                        DellMemoryDeviceType,
    memoryDeviceLocationName                DellString,
    memoryDeviceErrorCount                  DellSigned32BitRange,
    memoryDeviceBankLocationName            DellString,
    memoryDeviceTypeDetails                 DellMemoryDeviceTypeDetails,
    memoryDeviceFormFactor                  DellMemoryDeviceFormFactor,
    memoryDeviceSet                         DellUnsigned32BitRange,
    memoryDeviceSize                        DellUnsigned32BitRange,
    memoryDeviceSpeed                       DellUnsigned32BitRange,
    memoryDeviceTotalBusWidth               DellUnsigned32BitRange,
    memoryDeviceTotalDataBusWidth           DellUnsigned32BitRange,
    memoryDeviceSingleBitErrorCount         DellSigned32BitRange,
    memoryDeviceMultiBitErrorCount          DellSigned32BitRange
}

memoryDeviceTable                   OBJECT-TYPE
    SYNTAX      SEQUENCE OF MemoryDeviceTableEntry
    ACCESS      not-accessible
    STATUS      mandatory
    DESCRIPTION
"1100.0050 This Group defines the Dell Memory Device Table."
    ::= { deviceGroup 50 }
memoryDeviceTableEntry              OBJECT-TYPE
    SYNTAX      MemoryDeviceTableEntry
    ACCESS      not-accessible
    STATUS      mandatory
    DESCRIPTION
"1100.0050.0001 This Group defines the Dell Memory Device Table Entry."
    INDEX       { memoryDevicechassisIndex, memoryDeviceIndex }
    ::= { memoryDeviceTable 1 }
memoryDevicechassisIndex                OBJECT-TYPE
    SYNTAX      DellObjectRange
    ACCESS      read-only
    STATUS      mandatory
    DESCRIPTION
"1100.0050.0001.0001 This attribute defines the index (one based) of
this Dell chassis."
    ::= { memoryDeviceTableEntry 1 }
memoryDeviceIndex                           OBJECT-TYPE
    SYNTAX      DellObjectRange
    ACCESS      read-only
    STATUS      mandatory
    DESCRIPTION
"1100.0050.0001.0002 This attribute defines the index of the Dell Memory
Device in this chassis."
    ::= { memoryDeviceTableEntry 2 }
memoryDeviceStateCapabilities               OBJECT-TYPE
    SYNTAX      DellStateCapabilities
    ACCESS      read-only
    STATUS      mandatory
    DESCRIPTION
"1100.0050.0001.0003 This attribute defines the capabilities of the
Dell Memory Device."
    ::= { memoryDeviceTableEntry 3 }
memoryDeviceStateSettings                   OBJECT-TYPE
    SYNTAX      DellStateSettings
    ACCESS      read-write
    STATUS      mandatory
    DESCRIPTION
"1100.0050.0001.0004 This attribute defines the state of the Dell Memory
Device."
    ::= { memoryDeviceTableEntry 4 }
memoryDeviceStatus                          OBJECT-TYPE
    SYNTAX      DellStatus
    ACCESS      read-only
    STATUS      mandatory
    DESCRIPTION
"1100.0050.0001.0005 This attribute defines the status of the Dell Memory
Device."
    ::= { memoryDeviceTableEntry 5 }
memoryDeviceMemoryPortIndexReference        OBJECT-TYPE
    SYNTAX      DellObjectRange
    ACCESS      read-only
    STATUS      mandatory
    DESCRIPTION
"1100.0050.0001.0006 This attribute defines the index of the Dell memory
port that this memory device is part of."
    ::= { memoryDeviceTableEntry 6 }
memoryDeviceType                            OBJECT-TYPE
    SYNTAX      DellMemoryDeviceType
    ACCESS      read-only
    STATUS      mandatory
    DESCRIPTION
"1100.0050.0001.0007 This attribute defines the type of the Dell Memory
Device."
    ::= { memoryDeviceTableEntry 7 }
memoryDeviceLocationName                   OBJECT-TYPE
    SYNTAX      DellString
    ACCESS      read-only
    STATUS      mandatory
    DESCRIPTION
"1100.0050.0001.0008 This attribute defines location name of the Dell Memory
Device."
    ::= { memoryDeviceTableEntry 8 }
memoryDeviceErrorCount                      OBJECT-TYPE
    SYNTAX      DellSigned32BitRange
    ACCESS      read-write
    STATUS      mandatory
    DESCRIPTION
"1100.0050.0001.0009 This attribute defines the total number of ECC
errors detected by the Dell Memory Device. Writing a 0 (zero) to
this variable, will reset the devices error counts."
    ::= { memoryDeviceTableEntry 9 }
memoryDeviceBankLocationName               OBJECT-TYPE
    SYNTAX      DellString
    ACCESS      read-write
    STATUS      mandatory
    DESCRIPTION
"1100.0050.0001.0010 This attribute defines bank location name of the Dell
Memory Device."
    ::= { memoryDeviceTableEntry 10 }
memoryDeviceTypeDetails                    OBJECT-TYPE
    SYNTAX      DellMemoryDeviceTypeDetails
    ACCESS      read-only
    STATUS      mandatory
    DESCRIPTION
"1100.0050.0001.0011 This attribute defines the detailed type of the Dell
Memory Device."
    ::= { memoryDeviceTableEntry 11 }
memoryDeviceFormFactor                      OBJECT-TYPE
    SYNTAX      DellMemoryDeviceFormFactor
    ACCESS      read-only
    STATUS      mandatory
    DESCRIPTION
"1100.0050.0001.0012 This attribute defines the form factor of the Dell
Memory Device."
    ::= { memoryDeviceTableEntry 12 }
memoryDeviceSet                             OBJECT-TYPE
    SYNTAX      DellUnsigned32BitRange
    ACCESS      read-only
    STATUS      mandatory
    DESCRIPTION
"1100.0050.0001.0013 This attribute defines if the Dell Memory Device is a
part of a set.
0 (zero) indicates it is not part of a set,
2,147,483,647 indicates it is unknown if it is a part of a set."
    ::= { memoryDeviceTableEntry 13 }
memoryDeviceSize                            OBJECT-TYPE
    SYNTAX      DellUnsigned32BitRange
    ACCESS      read-only
    STATUS      mandatory
    DESCRIPTION
"1100.0050.0001.0014 This attribute defines the size in KBytes of the
Dell Memory Device.
0 (zero) indicates no memory installed,
2,147,483,647 indicates an unknown memory size."
    ::= { memoryDeviceTableEntry 14 }
memoryDeviceSpeed                           OBJECT-TYPE
    SYNTAX      DellUnsigned32BitRange
    ACCESS      read-only
    STATUS      mandatory
    DESCRIPTION
"1100.0050.0001.0015 This attribute defines the speed in NanoSeconds
of the Dell Memory Device. 0 (zero) indicates an unknown speed."
    ::= { memoryDeviceTableEntry 15 }
memoryDeviceTotalBusWidth                   OBJECT-TYPE
    SYNTAX      DellUnsigned32BitRange
    ACCESS      read-only
    STATUS      mandatory
    DESCRIPTION
"1100.0050.0001.0016 This attribute defines the total number bits,
including ECC, used by the Dell Memory Device.
2,147,483,647 indicates an unknown number of bits."
    ::= { memoryDeviceTableEntry 16 }
memoryDeviceTotalDataBusWidth               OBJECT-TYPE
    SYNTAX      DellUnsigned32BitRange
    ACCESS      read-only
    STATUS      mandatory
    DESCRIPTION
"1100.0050.0001.0017 This attribute defines the total number of
data bits used by the Dell Memory Device.
2,147,483,647 indicates an unknown number of bits."
    ::= { memoryDeviceTableEntry 17 }
memoryDeviceSingleBitErrorCount             OBJECT-TYPE
    SYNTAX      DellSigned32BitRange
    ACCESS      read-only
    STATUS      mandatory
    DESCRIPTION
"1100.0050.0001.0018 This attribute defines the total number of single
bit ECC errors detected by the Dell Memory Device."
    ::= { memoryDeviceTableEntry 18 }
memoryDeviceMultiBitErrorCount              OBJECT-TYPE
    SYNTAX      DellSigned32BitRange
    ACCESS      read-only
    STATUS      mandatory
    DESCRIPTION
"1100.0050.0001.0019 This attribute defines the total number of multibit
ECC errors detected by the Dell Memory Device."
    ::= { memoryDeviceTableEntry 19 }


-------------------------------------------------------------------------------
-- Memory Device Mapped Address Table
-------------------------------------------------------------------------------

MemoryDeviceMappedAddressTableEntry                 ::= SEQUENCE {
    memoryDeviceMappedAddresschassisIndex           DellObjectRange,
    memoryDeviceMappedAddressIndex                  DellObjectRange,
    memoryDeviceMappedAddressStateCapabilities      DellStateCapabilities,
    memoryDeviceMappedAddressStateSettings          DellStateSettings,
    memoryDeviceMappedAddressStatus                 DellStatus,
    memoryDeviceIndexReference                      DellObjectRange,
    memoryDeviceMappedAddressRowPosition            DellUnsigned32BitRange,
    memoryDeviceMappedAddressInterleavePosition     DellUnsigned32BitRange,
    memoryDeviceMappedAddressInterleaveDepth        DellUnsigned32BitRange,
    memoryDeviceMappedAddressStartingAddress        DellUnsigned64BitRange,
    memoryDeviceMappedAddressEndingAddress          DellUnsigned64BitRange
}

memoryDeviceMappedAddressTable                      OBJECT-TYPE
    SYNTAX      SEQUENCE OF MemoryDeviceMappedAddressTableEntry
    ACCESS      not-accessible
    STATUS      mandatory
    DESCRIPTION
"1100.0060 This Group defines the Dell Memory Device Mapped Address Table.
It references the Memory Device Index."
    ::= { deviceGroup 60 }
memoryDeviceMappedAddressTableEntry                 OBJECT-TYPE
    SYNTAX      MemoryDeviceMappedAddressTableEntry
    ACCESS      not-accessible
    STATUS      mandatory
    DESCRIPTION
"1100.0060.0001 This Group defines the Dell Memory Device Mapped Address
Table Entry."
    INDEX {memoryDeviceMappedAddresschassisIndex,memoryDeviceMappedAddressIndex}
    ::= { memoryDeviceMappedAddressTable 1 }
memoryDeviceMappedAddresschassisIndex               OBJECT-TYPE
    SYNTAX      DellObjectRange
    ACCESS      read-only
    STATUS      mandatory
    DESCRIPTION
"1100.0060.0001.0001 This attribute defines the index (one based) of
this Dell chassis."
    ::= { memoryDeviceMappedAddressTableEntry 1 }
memoryDeviceMappedAddressIndex                      OBJECT-TYPE
    SYNTAX      DellObjectRange
    ACCESS      read-only
    STATUS      mandatory
    DESCRIPTION
"1100.0060.0001.0002 This attribute defines the index of the Dell Memory
Device Mapped Address in this chassis."
    ::= { memoryDeviceMappedAddressTableEntry 2 }
memoryDeviceMappedAddressStateCapabilities         OBJECT-TYPE
    SYNTAX      DellStateCapabilities
    ACCESS      read-only
    STATUS      mandatory
    DESCRIPTION
"1100.0060.0001.0003 This attribute defines the capabilities of the
Dell Memory Device Mapped Address."
    ::= { memoryDeviceMappedAddressTableEntry 3 }
memoryDeviceMappedAddressStateSettings              OBJECT-TYPE
    SYNTAX      DellStateSettings
    ACCESS      read-write
    STATUS      mandatory
    DESCRIPTION
"1100.0060.0001.0004 This attribute defines the state of the Dell Memory
Device Mapped Address."
    ::= { memoryDeviceMappedAddressTableEntry 4 }
memoryDeviceMappedAddressStatus                     OBJECT-TYPE
    SYNTAX      DellStatus
    ACCESS      read-only
    STATUS      mandatory
    DESCRIPTION
"1100.0060.0001.0005 This attribute defines the status of the Dell Memory
Device Mapped Address."
    ::= { memoryDeviceMappedAddressTableEntry 5 }
memoryDeviceIndexReference                         OBJECT-TYPE
    SYNTAX      DellObjectRange
    ACCESS      read-only
    STATUS      mandatory
    DESCRIPTION
"1100.0060.0001.0006 This attribute defines the index of the memory
device(s) associated with this Dell Memory Device Mapped Address."
    ::= { memoryDeviceMappedAddressTableEntry 6 }
memoryDeviceMappedAddressRowPosition                OBJECT-TYPE
    SYNTAX      DellUnsigned32BitRange
    ACCESS      read-only
    STATUS      mandatory
    DESCRIPTION
"1100.0060.0001.0007 This attribute defines the position of the referenced
memory in a row of the Dell Memory Device Mapped Address.
2,147,483,647 indicates an unknown position."
    ::= { memoryDeviceMappedAddressTableEntry 7 }
memoryDeviceMappedAddressInterleavePosition         OBJECT-TYPE
    SYNTAX      DellUnsigned32BitRange
    ACCESS      read-only
    STATUS      mandatory
    DESCRIPTION
"1100.0060.0001.0008 This attribute defines the position of the referenced
memory in an interleave of the Dell Memory Device Mapped Address.
2,147,483,647 indicates an unknown position."
    ::= { memoryDeviceMappedAddressTableEntry 8 }
memoryDeviceMappedAddressInterleaveDepth            OBJECT-TYPE
    SYNTAX      DellUnsigned32BitRange
    ACCESS      read-only
    STATUS      mandatory
    DESCRIPTION
"1100.0060.0001.0009 This attribute defines the maximum number of
consecutive rows from the referenced Memory Device that are accessed
in a single interleaved transfer in the Dell Memory Device Mapped Address.
2,147,483,647 indicates an unknown number of rows."
    ::= { memoryDeviceMappedAddressTableEntry 9 }
memoryDeviceMappedAddressStartingAddress            OBJECT-TYPE
    SYNTAX      DellUnsigned64BitRange
    ACCESS      read-only
    STATUS      mandatory
    DESCRIPTION
"1100.0060.0001.0010 This attribute defines the physical starting
address in KBytes of the Dell Memory Device Mapped Address."
    ::= { memoryDeviceMappedAddressTableEntry 10 }
memoryDeviceMappedAddressEndingAddress              OBJECT-TYPE
    SYNTAX      DellUnsigned64BitRange
    ACCESS      read-only
    STATUS      mandatory
    DESCRIPTION
"1100.0060.0001.0011 This attribute defines the physical ending address
in KBytes of the Dell Memory Device Mapped Address."
    ::= { memoryDeviceMappedAddressTableEntry 11 }


-------------------------------------------------------------------------------
-- Generic Device Table
-------------------------------------------------------------------------------

DellGenericDeviceType                ::= INTEGER {
    deviceTypeIsOther(1),            -- there is not one of the following:
    deviceTypeIsUnknown(2),          -- the device type is unknown
    deviceTypeIsAVideoDevice(3),     -- the type of device is a video
    deviceTypeIsASCSIController(4),  -- the type of device is a scsi controller
    deviceTypeIsAnEthernetDevice(5), -- the type of device is ethernet
    deviceTypeIsTokenRingDevice(6),  -- the type of device is token ring
    deviceTypeIsASoundDevice(7)      -- the type of device is sound
}

GenericDeviceTableEntry                     ::= SEQUENCE {
    genericDevicechassisIndex               DellObjectRange,
    genericDeviceIndex                      DellObjectRange,
    genericDeviceStateCapabilities          DellStateCapabilities,
    genericDeviceStateSettings              DellStateSettings,
    genericDeviceStatus                     DellStatus,
    genericDeviceSystemSlotIndexReference   DellObjectRange,
    genericDeviceType                       DellGenericDeviceType,
    genericDeviceName                       DellString
}

genericDeviceTable              OBJECT-TYPE
    SYNTAX      SEQUENCE OF GenericDeviceTableEntry
    ACCESS      not-accessible
    STATUS      mandatory
    DESCRIPTION
"1100.0070 This Group defines the Dell Generic Device Table."
    ::= { deviceGroup 70 }
genericDeviceTableEntry         OBJECT-TYPE
    SYNTAX      GenericDeviceTableEntry
    ACCESS      not-accessible
    STATUS      mandatory
    DESCRIPTION
"1100.0070.0001 This Group defines the Dell Generic Device Table Entry."
    INDEX       { genericDevicechassisIndex, genericDeviceIndex }
    ::= { genericDeviceTable 1 }
genericDevicechassisIndex               OBJECT-TYPE
    SYNTAX      DellObjectRange
    ACCESS      read-only
    STATUS      mandatory
    DESCRIPTION
"1100.0070.0001.0001 This attribute defines the index (one based) of
this Dell chassis."
    ::= { genericDeviceTableEntry 1 }
genericDeviceIndex              OBJECT-TYPE
    SYNTAX      DellObjectRange
    ACCESS      read-only
    STATUS      mandatory
    DESCRIPTION
"1100.0070.0001.0002 This attribute defines the index of the Dell
Generic Device in this chassis."
    ::= { genericDeviceTableEntry 2 }
genericDeviceStateCapabilities  OBJECT-TYPE
    SYNTAX      DellStateCapabilities
    ACCESS      read-only
    STATUS      mandatory
    DESCRIPTION
"1100.0070.0001.0003 This attribute defines the capabilities of the Dell
Generic Device."
    ::= { genericDeviceTableEntry 3 }
genericDeviceStateSettings      OBJECT-TYPE
    SYNTAX      DellStateSettings
    ACCESS      read-write
    STATUS      mandatory
    DESCRIPTION
"1100.0070.0001.0004 This attribute defines the state of the Dell
Generic Device."
    ::= { genericDeviceTableEntry 4 }
genericDeviceStatus             OBJECT-TYPE
    SYNTAX      DellStatus
    ACCESS      read-only
    STATUS      mandatory
    DESCRIPTION
"1100.0070.0001.0005 This attribute defines the status of the Dell
Generic Device."
    ::= { genericDeviceTableEntry 5 }
genericDeviceSystemSlotIndexReference      OBJECT-TYPE
    SYNTAX      DellObjectRange
    ACCESS      read-only
    STATUS      mandatory
    DESCRIPTION
"1100.0070.0001.0006 This attribute defines the index of the system slot
this generic device is plugged into."
    ::= { genericDeviceTableEntry 6 }
genericDeviceType               OBJECT-TYPE
    SYNTAX      DellGenericDeviceType
    ACCESS      read-only
    STATUS      mandatory
    DESCRIPTION
"1100.0070.0001.0007 This attribute defines the type of the Dell
Generic Device."
    ::= { genericDeviceTableEntry 7 }
genericDeviceName               OBJECT-TYPE
    SYNTAX      DellString
    ACCESS      read-only
    STATUS      mandatory
    DESCRIPTION
"1100.0070.0001.0008 This is the name of the Dell Generic Device."
    ::= { genericDeviceTableEntry 8 }


-------------------------------------------------------------------------------
-- PCI Device Table
-------------------------------------------------------------------------------

PCIDeviceTableEntry                                 ::= SEQUENCE {
    pCIDevicechassisIndex                           DellObjectRange,
    pCIDeviceIndex                                  DellObjectRange,
    pCIDeviceStateCapabilities                      DellStateCapabilities,
    pCIDeviceStateSettings                          DellStateSettings,
    pCIDeviceStatus                                 DellStatus,
    pCIDeviceSystemSlotIndexReference               DellObjectRange,
    pCIDeviceDataBusWidth                           DellUnsigned32BitRange,
    pCIDeviceDescriptionName                        DellString,
    pCIDeviceManufacturerName                       DellString,
    pCIDeviceSpeed                                  DellUnsigned32BitRange,
    pCIDeviceAdapterFault                           DellBoolean
}

pCIDeviceTable                  OBJECT-TYPE
    SYNTAX      SEQUENCE OF PCIDeviceTableEntry
    ACCESS      not-accessible
    STATUS      mandatory
    DESCRIPTION
"1100.0080 This Group defines the Dell PCI Device Detail Table."
    ::= { deviceGroup 80 }
pCIDeviceTableEntry             OBJECT-TYPE
    SYNTAX      PCIDeviceTableEntry
    ACCESS      not-accessible
    STATUS      mandatory
    DESCRIPTION
"1100.0080.0001 This Group defines the Dell PCI Device Table Entry."
    INDEX       { pCIDevicechassisIndex, pCIDeviceIndex }
    ::= { pCIDeviceTable 1 }
pCIDevicechassisIndex               OBJECT-TYPE
    SYNTAX      DellObjectRange
    ACCESS      read-only
    STATUS      mandatory
    DESCRIPTION
"1100.0080.0001.0001 This attribute defines the index (one based) of
this Dell chassis."
    ::= { pCIDeviceTableEntry 1 }
pCIDeviceIndex                  OBJECT-TYPE
    SYNTAX      DellObjectRange
    ACCESS      read-only
    STATUS      mandatory
    DESCRIPTION
"1100.0080.0001.0002 This attribute defines the index of the Dell PCI
Device in this chassis."
    ::= { pCIDeviceTableEntry 2 }
pCIDeviceStateCapabilities      OBJECT-TYPE
    SYNTAX      DellStateCapabilities
    ACCESS      read-only
    STATUS      mandatory
    DESCRIPTION
"1100.0080.0001.0003 This attribute defines the capabilities of the
Dell PCI Device."
    ::= { pCIDeviceTableEntry 3 }
pCIDeviceStateSettings          OBJECT-TYPE
    SYNTAX      DellStateSettings
    ACCESS      read-write
    STATUS      mandatory
    DESCRIPTION
"1100.0080.0001.0004 This attribute defines the state of the Dell PCI
Device."
    ::= { pCIDeviceTableEntry 4 }
pCIDeviceStatus                 OBJECT-TYPE
    SYNTAX      DellStatus
    ACCESS      read-only
    STATUS      mandatory
    DESCRIPTION
"1100.0080.0001.0005 This attribute defines the status of the Dell PCI
Device."
    ::= { pCIDeviceTableEntry 5 }
pCIDeviceSystemSlotIndexReference    OBJECT-TYPE
    SYNTAX      DellObjectRange
    ACCESS      read-only
    STATUS      mandatory
    DESCRIPTION
"1100.0080.0001.0006 This attribute defines the index number of the system
slot that this Dell PCI Device is in."
    ::= { pCIDeviceTableEntry 6 }
pCIDeviceDataBusWidth           OBJECT-TYPE
    SYNTAX      DellUnsigned32BitRange
    ACCESS      read-only
    STATUS      mandatory
    DESCRIPTION
"1100.0080.0001.0007 This attribute defines the bus width of the Dell
PCI Device in this chassis."
    ::= { pCIDeviceTableEntry 7 }
pCIDeviceManufacturerName       OBJECT-TYPE
    SYNTAX      DellString
    ACCESS      read-only
    STATUS      mandatory
    DESCRIPTION
"1100.0080.0001.0008 This is the name of the Dell PCI Device manufacturer."
    ::= { pCIDeviceTableEntry 8 }
pCIDeviceDescriptionName        OBJECT-TYPE
    SYNTAX      DellString
    ACCESS      read-only
    STATUS      mandatory
    DESCRIPTION
"1100.0080.0001.0009 This is the descriptive name of the Dell PCI Device."
    ::= { pCIDeviceTableEntry 9 }
pCIDeviceSpeed                  OBJECT-TYPE
    SYNTAX      DellUnsigned32BitRange
    ACCESS      read-only
    STATUS      mandatory
    DESCRIPTION
"1100.0080.0001.0010 This attribute defines the bus speed in MHz of the
Dell PCI Device in this chassis, 0 (zero) indicates the speed is unknown."
    ::= { pCIDeviceTableEntry 10 }
pCIDeviceAdapterFault           OBJECT-TYPE
    SYNTAX      DellBoolean
    ACCESS      read-only
    STATUS      mandatory
    DESCRIPTION
"1100.0080.0001.0011 This attribute defines if Dell PCI Device in this
chassis has detected a fault or not."
    ::= { pCIDeviceTableEntry 11 }


-------------------------------------------------------------------------------
-- PCI Device Configuration Space Table
-------------------------------------------------------------------------------

PCIDeviceConfigurationSpaceTableEntry                 ::= SEQUENCE {
    pCIDeviceConfigurationSpacechassisIndex           DellObjectRange,
    pCIDeviceConfigurationSpaceIndex                  DellObjectRange,
    pCIDeviceConfigurationSpaceStateCapabilities      DellStateCapabilities,
    pCIDeviceConfigurationSpaceStateSettings          DellStateSettings,
    pCIDeviceConfigurationSpaceStatus                 DellStatus,
    pCIDeviceIndexReference                           DellObjectRange,
    pCIDeviceConfigurationSpaceBusNumber              DellUnsigned32BitRange,
    pCIDeviceConfigurationSpaceDeviceNumber           DellUnsigned32BitRange,
    pCIDeviceConfigurationSpaceFunctionNumber         DellUnsigned32BitRange,
    pCIDeviceConfigurationSpaceHeader                 OCTET STRING(SIZE(0..1025))
}

pCIDeviceConfigurationSpaceTable                 OBJECT-TYPE
    SYNTAX      SEQUENCE OF PCIDeviceConfigurationSpaceTableEntry
    ACCESS      not-accessible
    STATUS      mandatory
    DESCRIPTION
"1100.0082 This Group defines the Dell PCI Device Configuration Table."
    ::= { deviceGroup 82 }
pCIDeviceConfigurationSpaceTableEntry             OBJECT-TYPE
    SYNTAX      PCIDeviceConfigurationSpaceTableEntry
    ACCESS      not-accessible
    STATUS      mandatory
    DESCRIPTION
"1100.0082.0001 This Group defines the Dell PCI Device Configuration Table
Entry."
    INDEX { pCIDeviceConfigurationSpacechassisIndex, pCIDeviceConfigurationSpaceIndex }
    ::= { pCIDeviceConfigurationSpaceTable 1 }
pCIDeviceConfigurationSpacechassisIndex              OBJECT-TYPE
    SYNTAX      DellObjectRange
    ACCESS      read-only
    STATUS      mandatory
    DESCRIPTION
"1100.0082.0001.0001 This attribute defines the index (one based) of
this Dell chassis."
    ::= { pCIDeviceConfigurationSpaceTableEntry 1 }
pCIDeviceConfigurationSpaceIndex                  OBJECT-TYPE
    SYNTAX      DellObjectRange
    ACCESS      read-only
    STATUS      mandatory
    DESCRIPTION
"1100.0082.0001.0002 This attribute defines the index of the Dell PCI
Device Configuration in this chassis."
    ::= { pCIDeviceConfigurationSpaceTableEntry 2 }
pCIDeviceConfigurationSpaceStateCapabilities      OBJECT-TYPE
    SYNTAX      DellStateCapabilities
    ACCESS      read-only
    STATUS      mandatory
    DESCRIPTION
"1100.0082.0001.0003 This attribute defines the capabilities of the
Dell PCI Device Configuration."
    ::= { pCIDeviceConfigurationSpaceTableEntry 3 }
pCIDeviceConfigurationSpaceStateSettings          OBJECT-TYPE
    SYNTAX      DellStateSettings
    ACCESS      read-write
    STATUS      mandatory
    DESCRIPTION
"1100.0082.0001.0004 This attribute defines the state of the Dell PCI
Device Configuration."
    ::= { pCIDeviceConfigurationSpaceTableEntry 4 }
pCIDeviceConfigurationSpaceStatus                 OBJECT-TYPE
    SYNTAX      DellStatus
    ACCESS      read-only
    STATUS      mandatory
    DESCRIPTION
"1100.0082.0001.0005 This attribute defines the status of the Dell PCI
Device Configuration."
    ::= { pCIDeviceConfigurationSpaceTableEntry 5 }
pCIDeviceIndexReference                      OBJECT-TYPE
    SYNTAX      DellObjectRange
    ACCESS      read-only
    STATUS      mandatory
    DESCRIPTION
"1100.0082.0001.0006 This attribute defines the index number of PCI
device that this configuration applies too."
    ::= { pCIDeviceConfigurationSpaceTableEntry 6 }
pCIDeviceConfigurationSpaceBusNumber              OBJECT-TYPE
    SYNTAX      DellUnsigned32BitRange
    ACCESS      read-only
    STATUS      mandatory
    DESCRIPTION
"1100.0082.0001.0007 This attribute defines the bus number of the Dell
PCI Device Configuration in this chassis."
    ::= { pCIDeviceConfigurationSpaceTableEntry 7 }
pCIDeviceConfigurationSpaceDeviceNumber           OBJECT-TYPE
    SYNTAX      DellUnsigned32BitRange
    ACCESS      read-only
    STATUS      mandatory
    DESCRIPTION
"1100.0082.0001.0008 This attribute defines the device number of the Dell
PCI Device in this chassis."
    ::= { pCIDeviceConfigurationSpaceTableEntry 8 }
pCIDeviceConfigurationSpaceFunctionNumber         OBJECT-TYPE
    SYNTAX      DellUnsigned32BitRange
    ACCESS      read-only
    STATUS      mandatory
    DESCRIPTION
"1100.0082.0001.0009 This attribute defines the function number of the Dell
PCI Device in this chassis."
    ::= { pCIDeviceConfigurationSpaceTableEntry 9 }
pCIDeviceConfigurationSpaceHeader                 OBJECT-TYPE
    SYNTAX      OCTET STRING(SIZE(0..1025))
    ACCESS      read-only
    STATUS      mandatory
    DESCRIPTION
"1100.0082.0001.0010 This attribute defines the common configuration space
header of the Dell PCI Device."
    ::= { pCIDeviceConfigurationSpaceTableEntry 10 }


-------------------------------------------------------------------------------
--
-- Slot Group
--
-------------------------------------------------------------------------------

-------------------------------------------------------------------------------
-- System Slot Table
-------------------------------------------------------------------------------

DellSystemSlotStateCapabilities                       ::= INTEGER {
    systemSlotHotPlugIsUnknown(1),                    -- The objects capabilities are unknown
    systemSlotHotPlugIsHotPluggableCapable(2),        -- Set if slot supports Hot-Plug
    systemSlotHotPlugCanBePoweredOn(4),               -- Set if slot power (and corresponding LED) can be powered on
    systemSlotHotPlugCanSignalAttention(8),           -- Set if slot attention state (and corresponding LED) can be set
    systemSlotHotPlugCanSignalPowerFault(16),         -- Set if power on fault (and corresponding LED) can be detected due to a short or overcurrent
    systemSlotHotPlugCanSignalAdapterPresent(32),     -- Set if adapter (card) present in slot (may not be powered) can be detected
    systemSlotHotPlugCanSignalPowerButtonPressed(64), -- Set if slot power button can be pressed to signal a toggle of the power state
    canSupportAllHotPlugCapabilities(126),            -- Set if slot can support all Hot Plug Capabilities
    systemSlotCanProvide5Volts(128),                  -- Set if slot can provide a 5 volt supply
    systemSlotCanProvide3Point3Volts(256),            -- Set if slot can provide a 3.3 volt supply
    systemSlotCanSignalIfShared(512),                 -- Set if the slot's opening if shared with another slot can be detected
    systemSlotCanSupportCard16(1024),                 -- Set if slot can support PC Card-16
    systemSlotCanSupportCardBus(2048),                -- Set if slot can support CardBus
    systemSlotCanSupportZoomVideo(4096),              -- Set if slot can support Zoom Video
    systemSlotCanSupportModemRingResume(8192),        -- Set if slot can support Modem Ring Resume
    systemSlotCanSupportPMESignal(16384),             -- Set if slot can support Power Management Enable (PME#) signal
    canSupportAllSlotCapabilities(32640),             -- Set if slot can support all Slot Capabilities
    canSupportAllSlotAndAllHotPlugCapabilities(32766) -- Set if slot can support all Slot and all Hot Plug Capabilities
}
DellSystemSlotStateSettings              ::= INTEGER {
    systemSlotHotPlugIsUnknown(1),               -- The objects capabilities are unknown
    systemSlotHotPlugIsHotPluggable(2),          -- Set if slot supports Hot-Plug
    systemSlotHotPlugIsPoweredOn(4),             -- Set if slot power (and corresponding LED) is ON
    systemSlotHotPlugIsAtAttention(8),           -- Set if slot attention state (and corresponding LED) is ON
    systemSlotHotPlugHasPowerFaulted(16),        -- Set if power on fault (and corresponding LED) was detected due to a short or overcurrent
    systemSlotHotPlugAdapterIsPresent(32),       -- Set if adapter (card) present in slot (may not be powered)
    systemSlotHotPlugAdapterPresentAndPoweredOn(36),  -- Set if adapter (card) present in slot and powered
    systemSlotHotPlugPowerButtonPressed(64),     -- Set if slot power button pressed to signal a toggle of the power state
    systemSlotProvides5Volts(128),               -- Set if slot provides a 5 volt supply
    systemSlotProvides3Point3Volts(256),         -- Set if slot provides a 3.3 volt supply
    systemSlotIsShared(512),                     -- Set if the slot's opening is shared with another slot, e.g. PCI/EISA shared slot
    systemSlotSupportsCard16(1024),              -- Set if slot supports PC Card-16
    systemSlotSupportsCardBus(2048),             -- Set if slot supports CardBus
    systemSlotSupportsZoomVideo(4096),           -- Set if slot supports Zoom Video
    systemSlotSupportsModemRingResume(8192),     -- Set if slot supports Modem Ring Resume
    systemSlotSupportsPMESignal(16384),          -- Set if slot supports Power Management Enable (PME#) signal
    supportsPMEand3P3Vand5VandHotPluggable(16770), -- Set if slot supports Power Management Enable....
    supportsPMEand3P3Vand5VhasAdapterOn(16804),    -- Set if slot supports Power Management Enable....
    supportsPMEand3P3Vand5VhasAdapterOnandisHotPluggable(16806), -- Set if slot supports Power Management Enable....
    supportsPMEand3P3VIsSharedand5VhasAdapterOnandHotPlugable(17316)  -- Set if slot supports Power Management Enable....
}
DellSystemSlotType                       ::= INTEGER {
    systemSlotIsOther(1),                -- the system slot type is not one of following:
    systemSlotIsUnknown(2),              -- the system slot type is unknown
    systemSlotIsISA(3),                  -- the system slot type is an ISA    bus
    systemSlotIsMCA(4),                  -- the system slot type is an MCA    bus
    systemSlotIsEISA(5),                 -- the system slot type is an EISA   bus
    systemSlotIsPCI(6),                  -- the system slot type is a  PCI    bus
    systemSlotIsPCMCIA(7),               -- the system slot type is a  PCMCIA bus
    systemSlotIsVLVESA(8),               -- the system slot type is a  VLVESA bus
    systemSlotIsProprietary(9),          -- the system slot is proprietary
    systemSlotIsProcessorCard(10),       -- the system slot type is a processor card
    systemSlotIsProprietaryMemory(11),   -- the system slot type is proprietary memory card
    systemSlotIsIORiserCard(12),         -- the system slot type is an IO Riser card
    systemSlotIsNuBUS(13),               -- the system slot type is a  NUBUS  bus
    systemSlotIsPCI66MHz(14),            -- the system slot type is a  PCI 66MHz bus
    systemSlotIsAGP(15),                 -- the system slot type is an AGP    bus
    systemSlotIsAGPx2(16),               -- the system slot type is an AGPx2  bus
    systemSlotIsAGPx4(17),               -- the system slot type is an AGPx4  bus
    systemSlotIsPC98C20(18),             -- the system slot type is PC-98 C20
    systemSlotIsPC98C24(19),             -- the system slot type is PC-98 C24
    systemSlotIsPC98E(20),               -- the system slot type is PC-98 E
    systemSlotIsPC98LocalBus(21),        -- the system slot type is PC-98 Local Bus
    systemSlotIsPC98Card(22),            -- the system slot type is PC-98 card
    systemSlotIsPCIX(23)                 -- the system slot type is a  PCI-X  bus
}
DellSystemSlotUsage                      ::= INTEGER {
    systemSlotUsageIsOther(1),           -- the slot usage is not one of following:
    systemSlotUsageIsUnknown(2),         -- the usage of the slot is unknown
    systemSlotUsageIsAvailable(3),       -- the usage of the slot is available
    systemSlotUsageIsInUse(4)            -- the usage of the slot is in use
}
DellSystemSlotLength                     ::= INTEGER {
    systemSlotLengthIsOther(1),          -- the slot length is not one of following:
    systemSlotLengthIsUnknown(2),        -- the length of the slot is unknown
    systemSlotLengthIsShort(3),          -- the length of the slot is short
    systemSlotLengthIsLong(4)            -- the length of the slot is long
}
DellSystemSlotCategory                   ::= INTEGER {
    systemSlotCategoryIsOther(1),        -- the slot category is not one of following:
    systemSlotCategoryIsUnknown(2),      -- the category of the slot is unknown
    systemSlotCategoryIsBusConnector(3), -- the category of the slot is a bus connector
    systemSlotCategoryIsPCMCIA(4),       -- the category of the slot is PCMCIA
    systemSlotCategoryIsMotherboard(5)   -- the category of the slot is a motherboard
}
DellSystemSlotHotPlugBusWidth            ::= INTEGER {
    busWidthIsOther(1),                  -- the bus width is not one of following:
    busWidthIsUnknown(2),                -- the bus width of the slot is unknown
    busWidthIs8bits(3),                  -- the bus width of the slot is eight bits
    busWidthIs16bits(4),                 -- the bus width of the slot is sixteen bits
    busWidthIs32bits(5),                 -- the bus width of the slot is thirty two bits
    busWidthIs64bits(6),                 -- the bus width of the slot is sixty four bits
    busWidthIs128bits(7)                 -- the bus width of the slot is 128 bits
}

SystemSlotTableEntry                            ::= SEQUENCE {
    systemSlotchassisIndex                      DellObjectRange,
    systemSlotIndex                             DellObjectRange,
    systemSlotStateCapabilitiesUnique           DellSystemSlotStateCapabilities,
    systemSlotStateSettingsUnique               DellSystemSlotStateSettings,
    systemSlotStatus                            DellStatus,
    systemSlotCurrentUsage                      DellSystemSlotUsage,
    systemSlotType                              DellSystemSlotType,
    systemSlotSlotExternalSlotName              DellString,
    systemSlotLength                            DellSystemSlotLength,
    systemSlotSlotID                            DellUnsigned32BitRange,
    systemSlotCategory                          DellSystemSlotCategory,
    systemSlotHotPlugBusWidth                   DellSystemSlotHotPlugBusWidth,
    systemSlotHotPlugSlotSpeed                  DellUnsigned32BitRange,
    systemSlotHotPlugAdapterSpeed               DellUnsigned32BitRange
}

systemSlotTable                                 OBJECT-TYPE
    SYNTAX      SEQUENCE OF SystemSlotTableEntry
    ACCESS      not-accessible
    STATUS      mandatory
    DESCRIPTION
"1200.0010 This Group defines the Dell System Slot Table."
    ::= { slotGroup 10 }
systemSlotTableEntry                            OBJECT-TYPE
    SYNTAX      SystemSlotTableEntry
    ACCESS      not-accessible
    STATUS      mandatory
    DESCRIPTION
"1200.0010.0001 This Group defines the Dell System Slot Table Entry."
    INDEX       { systemSlotchassisIndex, systemSlotIndex }
    ::= { systemSlotTable 1 }
systemSlotchassisIndex              OBJECT-TYPE
    SYNTAX      DellObjectRange
    ACCESS      read-only
    STATUS      mandatory
    DESCRIPTION
"1200.0010.0001.0001 This attribute defines the index (one based) of
this Dell chassis."
    ::= { systemSlotTableEntry 1 }
systemSlotIndex                                 OBJECT-TYPE
    SYNTAX      DellObjectRange
    ACCESS      read-only
    STATUS      mandatory
    DESCRIPTION
"1200.0010.0001.0002 This attribute defines the index of the Dell System
Slot in this chassis."
    ::= { systemSlotTableEntry 2 }
systemSlotStateCapabilitiesUnique              OBJECT-TYPE
    SYNTAX      DellSystemSlotStateCapabilities
    ACCESS      read-only
    STATUS      mandatory
    DESCRIPTION
"1200.0010.0001.0003 This attribute defines the capabilities of the
Dell System Slot."
    ::= { systemSlotTableEntry 3 }
systemSlotStateSettingsUnique                   OBJECT-TYPE
    SYNTAX      DellSystemSlotStateSettings
    ACCESS      read-write
    STATUS      mandatory
    DESCRIPTION
"1200.0010.0001.0004 This attribute defines the state of the Dell System
Slot."
    ::= { systemSlotTableEntry 4 }
systemSlotStatus                                OBJECT-TYPE
    SYNTAX      DellStatus
    ACCESS      read-only
    STATUS      mandatory
    DESCRIPTION
"1200.0010.0001.0005 This attribute defines the status of the Dell System
Slot."
    ::= { systemSlotTableEntry 5 }
systemSlotCurrentUsage                          OBJECT-TYPE
    SYNTAX      DellSystemSlotUsage
    ACCESS      read-only
    STATUS      mandatory
    DESCRIPTION
"1200.0010.0001.0006 This attribute defines the current usage of the Dell
System Slot."
    ::= { systemSlotTableEntry 6 }
systemSlotType                                  OBJECT-TYPE
    SYNTAX      DellSystemSlotType
    ACCESS      read-only
    STATUS      mandatory
    DESCRIPTION
"1200.0010.0001.0007 This attribute defines the type of the Dell System
Slot."
    ::= { systemSlotTableEntry 7 }
systemSlotSlotExternalSlotName                  OBJECT-TYPE
    SYNTAX      DellString
    ACCESS      read-only
    STATUS      mandatory
    DESCRIPTION
"1200.0010.0001.0008 This attribute defines name of the external
connector name of the Dell System Slot."
    ::= { systemSlotTableEntry 8 }
systemSlotLength                                OBJECT-TYPE
    SYNTAX      DellSystemSlotLength
    ACCESS      read-only
    STATUS      mandatory
    DESCRIPTION
"1200.0010.0001.0009 This attribute defines the length of the Dell System
Slot."
    ::= { systemSlotTableEntry 9 }
systemSlotSlotID                                OBJECT-TYPE
    SYNTAX      DellUnsigned32BitRange
    ACCESS      read-only
    STATUS      mandatory
    DESCRIPTION
"1200.0010.0001.0010 This attribute defines the slot identification number
of the Dell System Slot."
    ::= { systemSlotTableEntry 10 }
systemSlotCategory                              OBJECT-TYPE
    SYNTAX      DellSystemSlotCategory
    ACCESS      read-only
    STATUS      mandatory
    DESCRIPTION
"1200.0010.0001.0011 This attribute defines the category of the Dell System
Slot."
    ::= { systemSlotTableEntry 11 }
systemSlotHotPlugBusWidth                       OBJECT-TYPE
    SYNTAX      DellSystemSlotHotPlugBusWidth
    ACCESS      read-only
    STATUS      mandatory
    DESCRIPTION
"1200.0010.0001.0012 This attribute defines the bus width of the Dell Hot
Plug System Slot."
    ::= { systemSlotTableEntry 12 }
systemSlotHotPlugSlotSpeed                      OBJECT-TYPE
    SYNTAX      DellUnsigned32BitRange
    ACCESS      read-only
    STATUS      mandatory
    DESCRIPTION
"1200.0010.0001.0013 This attribute defines the slot speed in MHz of the
Dell Hot Plug System Slot.
Zero, (0) indicated the slot speed is unknown."
    ::= { systemSlotTableEntry 13 }
systemSlotHotPlugAdapterSpeed                   OBJECT-TYPE
    SYNTAX      DellUnsigned32BitRange
    ACCESS      read-only
    STATUS      mandatory
    DESCRIPTION
"1200.0010.0001.0014 This attribute defines the adapter speed in MHz of
the Dell Hot Plug System Slot.
Zero, (0) indicated the slot speed is unknown."
    ::= { systemSlotTableEntry 14 }


-------------------------------------------------------------------------------
--
-- Memory Group
--
-------------------------------------------------------------------------------

-------------------------------------------------------------------------------
-- Physical Memory Array Table
-------------------------------------------------------------------------------

DellPhysicalMemoryArrayLocation                  ::= INTEGER {
    memoryArrayLocationIsOther(1),               -- this device is not one of the following:
    memoryArrayLocationIsUnknown(2),             -- the device location is unknown
    memoryArrayLocationIsSystemOrMotherboard(3), -- the device location is a  System board or motherboard
    memoryArrayLocationIsISA(4),                 -- the device location is an ISA add-on card
    memoryArrayLocationIsEISA(5),                -- the device location is an EISA add-on card
    memoryArrayLocationIsPCI(6),                 -- the device location is a  PCI add-on card
    memoryArrayLocationIsMCA(7),                 -- the device location is a  MCA add-on card
    memoryArrayLocationIsPCMCIA(8),              -- the device location is a  PCMCIA add-on card
    memoryArrayLocationIsProprietary(9),         -- the device location is a Proprietary add-on card
    memoryArrayLocationIsNUBUS(10),              -- the device location is a  NUBUS  bus
    memoryArrayLocationIsPC98C20(11),            -- the device location is PC-98/C20 add-on card
    memoryArrayLocationIsPC98C24(12),            -- the device location is PC-98/C24 add-on card
    memoryArrayLocationIsPC98E(13),              -- the device location is PC-98/E add-on card
    memoryArrayLocationIsPC98LocalBus(14),       -- the device location is PC-98/Local bus add-on card
    memoryArrayLocationIsPC98Card(15)            -- the device location is PC-98/Card slot add-on card
}
DellPhysicalMemoryArrayUse                       ::= INTEGER {
    memoryArrayUseIsOther(1),                    -- this device usage is not one of the following:
    memoryArrayUseIsUnknown(2),                  -- the device use is unknown
    memoryArrayUseIsSystemMemory(3),             -- the device use is System memory
    memoryArrayUseIsVideoMemory(4),              -- the device use is Video memory
    memoryArrayUseIsFLASHMemory(5),              -- the device use is Flash memory
    memoryArrayUseIsNonVolatileRAMMemory(6),     -- the device use is NonVolatile RAM
    memoryArrayUseIsCacheMemory(7)               -- the device use is Cache Memory
}
DellPhysicalMemoryArrayECCType                   ::= INTEGER {
    memoryArrayECCTypeIsOther(1),                -- there is not one of the following:
    memoryArrayECCTypeIsUnknown(2),              -- the device error correction type is unknown
    memoryArrayECCTypeIsNone(3),                 -- the device error correction type is none
    memoryArrayECCTypeIsParity(4),               -- the device error correction type is parity
    memoryArrayECCTypeIsSingleBitECC(5),         -- the device error correction type is single bit ecc
    memoryArrayECCTypeIsMultiBitECC(6),          -- the device error correction type is multibit ecc
    memoryArrayECCTypeIsCRC(7)                   -- the device error correction type is crc
}

PhysicalMemoryArrayTableEntry                           ::= SEQUENCE {
    physicalMemoryArraychassisIndex                     DellObjectRange,
    physicalMemoryArrayIndex                            DellObjectRange,
    physicalMemoryArrayStateCapabilities                DellStateCapabilities,
    physicalMemoryArrayStateSettings                    DellStateSettings,
    physicalMemoryArrayStatus                           DellStatus,
    physicalMemoryArrayUse                              DellPhysicalMemoryArrayUse,
    physicalMemoryArrayECCType                          DellPhysicalMemoryArrayECCType,
    physicalMemoryArrayLocation                         DellPhysicalMemoryArrayLocation,
    physicalMemoryArrayMaximumSize                      DellUnsigned32BitRange,
    physicalMemoryArrayTotalNumberSockets               DellUnsigned32BitRange,
    physicalMemoryArrayInUseNumberSockets               DellUnsigned32BitRange,
    physicalMemoryArrayECCErrorNonRecoverableThreshold  DellSigned32BitRange,
    physicalMemoryArrayECCErrorCriticalThreshold        DellSigned32BitRange,
    physicalMemoryArrayECCErrorNonCriticalThreshold     DellSigned32BitRange,
    physicalMemoryArrayRedundantMemoryUnitIndexReference DellObjectRange
}

physicalMemoryArrayTable                    OBJECT-TYPE
    SYNTAX      SEQUENCE OF PhysicalMemoryArrayTableEntry
    ACCESS      not-accessible
    STATUS      mandatory
    DESCRIPTION
"1300.0010 This Group defines the Dell Physical Memory Array Table."
    ::= { memoryGroup 10 }
physicalMemoryArrayTableEntry               OBJECT-TYPE
    SYNTAX      PhysicalMemoryArrayTableEntry
    ACCESS      not-accessible
    STATUS      mandatory
    DESCRIPTION
"1300.0010.0001 This Group defines the Dell Physical Memory Array
Table Entry."
    INDEX       { physicalMemoryArraychassisIndex, physicalMemoryArrayIndex }
    ::= { physicalMemoryArrayTable 1 }
physicalMemoryArraychassisIndex                 OBJECT-TYPE
    SYNTAX      DellObjectRange
    ACCESS      read-only
    STATUS      mandatory
    DESCRIPTION
"1300.0010.0001.0001 This attribute defines the index (one based) of
this Dell chassis."
    ::= { physicalMemoryArrayTableEntry 1 }
physicalMemoryArrayIndex                    OBJECT-TYPE
    SYNTAX      DellObjectRange
    ACCESS      read-only
    STATUS      mandatory
    DESCRIPTION
"1300.0010.0001.0002 This attribute defines the index of the Dell Physical
Memory Array in this chassis."
    ::= { physicalMemoryArrayTableEntry 2 }
physicalMemoryArrayStateCapabilities       OBJECT-TYPE
    SYNTAX      DellStateCapabilities
    ACCESS      read-only
    STATUS      mandatory
    DESCRIPTION
"1300.0010.0001.0003 This attribute defines the capabilities of the Dell
Physical Memory Array."
    ::= { physicalMemoryArrayTableEntry 3 }
physicalMemoryArrayStateSettings            OBJECT-TYPE
    SYNTAX      DellStateSettings
    ACCESS      read-write
    STATUS      mandatory
    DESCRIPTION
"1300.0010.0001.0004 This attribute defines the state of the Dell Physical
Memory Array."
    ::= { physicalMemoryArrayTableEntry 4 }
physicalMemoryArrayStatus                   OBJECT-TYPE
    SYNTAX      DellStatus
    ACCESS      read-only
    STATUS      mandatory
    DESCRIPTION
"1300.0010.0001.0005 This attribute defines the status of the Dell Physical
Memory Array."
    ::= { physicalMemoryArrayTableEntry 5 }
physicalMemoryArrayUse                      OBJECT-TYPE
    SYNTAX      DellPhysicalMemoryArrayUse
    ACCESS      read-only
    STATUS      mandatory
    DESCRIPTION
"1300.0010.0001.0006 This attribute defines the use of the Dell Physical
Memory Array."
    ::= { physicalMemoryArrayTableEntry 6 }
physicalMemoryArrayECCType                  OBJECT-TYPE
    SYNTAX      DellPhysicalMemoryArrayECCType
    ACCESS      read-only
    STATUS      mandatory
    DESCRIPTION
"1300.0010.0001.0007 This attribute defines the error correction type used
by the Dell Physical Memory Array."
    ::= { physicalMemoryArrayTableEntry 7 }
physicalMemoryArrayLocation                 OBJECT-TYPE
    SYNTAX      DellPhysicalMemoryArrayLocation
    ACCESS      read-only
    STATUS      mandatory
    DESCRIPTION
"1300.0010.0001.0008 This attribute defines the location of the Dell
Physical Memory Array."
    ::= { physicalMemoryArrayTableEntry 8 }
physicalMemoryArrayMaximumSize              OBJECT-TYPE
    SYNTAX      DellUnsigned32BitRange
    ACCESS      read-only
    STATUS      mandatory
    DESCRIPTION
"1300.0010.0001.0009 This attribute defines the size in KBytes of the Dell
Physical Memory Array.
0 (zero) inicates no memory installed,
2,147,483,647 indicates an unknown memory size."
    ::= { physicalMemoryArrayTableEntry 9 }
physicalMemoryArrayTotalNumberSockets       OBJECT-TYPE
    SYNTAX      DellUnsigned32BitRange
    ACCESS      read-only
    STATUS      mandatory
    DESCRIPTION
"1300.0010.0001.0010 This attribute defines the total number of memory
sockets available for the Dell Physical Memory Array.
2,147,483,647 indicates an unknown number of sockets."
    ::= { physicalMemoryArrayTableEntry 10 }
physicalMemoryArrayInUseNumberSockets       OBJECT-TYPE
    SYNTAX      DellUnsigned32BitRange
    ACCESS      read-only
    STATUS      mandatory
    DESCRIPTION
"1300.0010.0001.0011 This attribute defines the total number of memory
sockets in use by the Dell Physical Memory Array.
2,147,483,647 indicates an unknown number of sockets."
    ::= { physicalMemoryArrayTableEntry 11 }
physicalMemoryArrayECCErrorNonRecoverableThreshold        OBJECT-TYPE
    SYNTAX      DellSigned32BitRange
    ACCESS      read-only
    STATUS      mandatory
    DESCRIPTION
"1300.0010.0001.0012 This attribute defines the value of the Dell
physical memory array ECC error nonrecoverable threshold.
The value is an integer representing the the number of errors detected."
    ::= { physicalMemoryArrayTableEntry 12 }
physicalMemoryArrayECCErrorCriticalThreshold              OBJECT-TYPE
    SYNTAX      DellSigned32BitRange
    ACCESS      read-only
    STATUS      mandatory
    DESCRIPTION
"1300.0010.0001.00013 This attribute defines the value of the Dell
physical memory array ECC error critical threshold.
The value is an integer representing the the number of errors detected."
    ::= { physicalMemoryArrayTableEntry 13 }
physicalMemoryArrayECCErrorNonCriticalThreshold           OBJECT-TYPE
    SYNTAX      DellSigned32BitRange
    ACCESS      read-write
    STATUS      mandatory
    DESCRIPTION
"1300.0010.0001.00014 This attribute defines the value of the Dell
physical memory array ECC error noncritical threshold.
The value is an integer representing the the number of errors detected."
    ::= { physicalMemoryArrayTableEntry 14 }
physicalMemoryArrayRedundantMemoryUnitIndexReference    OBJECT-TYPE
    SYNTAX      DellObjectRange
    ACCESS      read-only
    STATUS      mandatory
    DESCRIPTION
"1300.0010.0001.0015 This attribute defines the index to the associated
Redundant Memory Unit in this chassis."
    ::= { physicalMemoryArrayTableEntry 15 }


-------------------------------------------------------------------------------
-- Physical Memory Array Mapped Table
-------------------------------------------------------------------------------

PhysicalMemoryArrayMappedTableEntry            ::= SEQUENCE {
    physicalMemoryArrayMappedchassisIndex      DellObjectRange,
    physicalMemoryArrayMappedIndex             DellObjectRange,
    physicalMemoryArrayMappedStateCapabilities DellStateCapabilities,
    physicalMemoryArrayMappedStateSettings     DellStateSettings,
    physicalMemoryArrayMappedStatus            DellStatus,
    physicalMemoryArrayIndexReference          DellObjectRange,
    physicalMemoryArrayMappedStartingAddress   DellUnsigned64BitRange,
    physicalMemoryArrayMappedEndingAddress     DellUnsigned64BitRange,
    physicalMemoryArrayMappedPartitionWidth    DellUnsigned32BitRange
}

physicalMemoryArrayMappedTable                  OBJECT-TYPE
    SYNTAX      SEQUENCE OF PhysicalMemoryArrayMappedTableEntry
    ACCESS      not-accessible
    STATUS      mandatory
    DESCRIPTION
"1300.0020 This Group defines the Dell Physical Memory Array Mapped Table.
It references the Physical Memory Array Index."
    ::= { memoryGroup 20 }
physicalMemoryArrayMappedTableEntry             OBJECT-TYPE
    SYNTAX      PhysicalMemoryArrayMappedTableEntry
    ACCESS      not-accessible
    STATUS      mandatory
    DESCRIPTION
"1300.0020.0001 This Group defines the Dell Physical Memory Array Mapped
Table Entry."
INDEX { physicalMemoryArrayMappedchassisIndex, physicalMemoryArrayMappedIndex }
    ::= { physicalMemoryArrayMappedTable 1 }
physicalMemoryArrayMappedchassisIndex               OBJECT-TYPE
    SYNTAX      DellObjectRange
    ACCESS      read-only
    STATUS      mandatory
    DESCRIPTION
"1300.0020.0001.0001 This attribute defines the index (one based) of
this Dell chassis."
    ::= { physicalMemoryArrayMappedTableEntry 1 }
physicalMemoryArrayMappedIndex                          OBJECT-TYPE
    SYNTAX      DellObjectRange
    ACCESS      read-only
    STATUS      mandatory
    DESCRIPTION
"1300.0020.0001.0002 This attribute defines the index of the Dell Memory
Array Mapped Address in this chassis."
    ::= { physicalMemoryArrayMappedTableEntry 2 }
physicalMemoryArrayMappedStateCapabilities             OBJECT-TYPE
    SYNTAX      DellStateCapabilities
    ACCESS      read-only
    STATUS      mandatory
    DESCRIPTION
"1300.0020.0001.0003 This attribute defines the capabilities of the
Dell Memory Array Mapped Address."
    ::= { physicalMemoryArrayMappedTableEntry 3 }
physicalMemoryArrayMappedStateSettings                 OBJECT-TYPE
    SYNTAX      DellStateSettings
    ACCESS      read-write
    STATUS      mandatory
    DESCRIPTION
"1300.0020.0001.0004 This attribute defines the state of the Dell Memory
Array Mapped Address."
    ::= { physicalMemoryArrayMappedTableEntry 4 }
physicalMemoryArrayMappedStatus                         OBJECT-TYPE
    SYNTAX      DellStatus
    ACCESS      read-only
    STATUS      mandatory
    DESCRIPTION
"1300.0020.0001.0005 This attribute defines the status of the Dell Memory
Array Mapped Address."
    ::= { physicalMemoryArrayMappedTableEntry 5 }
physicalMemoryArrayIndexReference                       OBJECT-TYPE
    SYNTAX      DellObjectRange
    ACCESS      read-only
    STATUS      mandatory
    DESCRIPTION
"1300.0020.0001.0006 This attribute defines the index to the associated
Dell Physical Memory Array in this chassis."
    ::= { physicalMemoryArrayMappedTableEntry 6 }
physicalMemoryArrayMappedStartingAddress                OBJECT-TYPE
    SYNTAX      DellUnsigned64BitRange
    ACCESS      read-only
    STATUS      mandatory
    DESCRIPTION
"1300.0020.0001.0007 This attribute defines the physical starting address
in KBytes of the Dell Memory Array Mapped Address."
    ::= { physicalMemoryArrayMappedTableEntry 7 }
physicalMemoryArrayMappedEndingAddress                  OBJECT-TYPE
    SYNTAX      DellUnsigned64BitRange
    ACCESS      read-only
    STATUS      mandatory
    DESCRIPTION
"1300.0020.0001.0008 This attribute defines the physical ending address
in KBytes of the Dell Memory Array Mapped Address."
    ::= { physicalMemoryArrayMappedTableEntry 8 }
physicalMemoryArrayMappedPartitionWidth                 OBJECT-TYPE
    SYNTAX      DellUnsigned32BitRange
    ACCESS      read-only
    STATUS      mandatory
    DESCRIPTION
"1300.0020.0001.0009 This attribute defines the number of memory
devices that form a single row in the Dell Memory Array Mapped Address.
2,147,483,647 indicates an unknown number of memory devices."
    ::= { physicalMemoryArrayMappedTableEntry 9 }


-------------------------------------------------------------------------------
-- Physical Memory Configuration Table
-------------------------------------------------------------------------------

DellPhysicalMemoryConfigStateCapabilities       ::= INTEGER {
    -- If set to 0 (zero) there are no state capabilities
    unknownCapabilities(1),                     -- State capabilities are unknown
    -- The state capabilities are:
    enableCapable(2),                           -- Object enable/disable is supported
    notReadyCapable(4)                          -- Object "not ready" is supported
}
DellPhysicalMemoryConfigStateSettings           ::= INTEGER {
    -- If set to 0 (zero) there are no state settings
    unknown(1),                                 -- State settings are unknown
    -- The state settings are:
    enabled(2),                                 -- Object is disabled (offline) 0, or enabled (online) 1
    notReady(4),                                -- Object is "not ready"
    redundantMemoryIsActive(8),                 -- Redundant memory is active (in use)
    enabledAndRedundantMemoryIsActive(10)
}
DellPhysicalMemoryConfigRedundantCapabilities   ::= INTEGER {
    -- If set to 0 (zero) there are no redundant memory capabilities
    unknownCapabilities(1),                     -- Redundant capabilities are unknown
    -- The redundant capabilities are:
    spareBankCapable(2),                        -- Spare Bank is supported
    mirrorCapable(4),                           -- Mirror is supported
    spareBankAndMirrorCapable(6)
}
DellPhysicalMemoryConfigRedundantSettings       ::= INTEGER {
    -- If set to 0 (zero) there are no redundant memory settings enabled
    unknown(1),                                 -- Redundant settings are unknown
	-- The redundant settings are:
	-- The following two settings are mutually exclusive:
    spareBankEnabled(2),                        -- Spare Bank support is enabled
    mirrorEnabled(4)                            -- Mirror support is enabled
}

PhysicalMemoryConfigTableEntry                  ::= SEQUENCE {
    physicalMemoryConfigChassisIndex            DellObjectRange,
    physicalMemoryConfigIndex                   DellObjectRange,
    physicalMemoryConfigStateCapabilities       DellPhysicalMemoryConfigStateCapabilities,
    physicalMemoryConfigStateSettings           DellPhysicalMemoryConfigStateSettings,
    physicalMemoryConfigStatus                  DellStatus,
    physicalMemoryConfigRedundantCapabilities   DellPhysicalMemoryConfigRedundantCapabilities,
    physicalMemoryConfigRedundantSettings       DellPhysicalMemoryConfigRedundantSettings
}

physicalMemoryConfigTable                       OBJECT-TYPE
    SYNTAX      SEQUENCE OF PhysicalMemoryConfigTableEntry
    ACCESS      not-accessible
    STATUS      mandatory
    DESCRIPTION
"1300.0030 This object defines the Physical Memory Configuration Table."
    ::= { memoryGroup 30 }
physicalMemoryConfigTableEntry                  OBJECT-TYPE
    SYNTAX      PhysicalMemoryConfigTableEntry
    ACCESS      not-accessible
    STATUS      mandatory
    DESCRIPTION
"1300.0030.0001 This object defines the Physical Memory Configuration
Table Entry."
    INDEX       { physicalMemoryConfigChassisIndex, physicalMemoryConfigIndex }
    ::= { physicalMemoryConfigTable 1 }
physicalMemoryConfigChassisIndex                OBJECT-TYPE
    SYNTAX      DellObjectRange
    ACCESS      read-only
    STATUS      mandatory
    DESCRIPTION
"1300.0030.0001.0001 This attribute defines the index (one based) of
the chassis associated with the physical memory configuration."
    ::= { physicalMemoryConfigTableEntry 1 }
physicalMemoryConfigIndex                       OBJECT-TYPE
    SYNTAX      DellObjectRange
    ACCESS      read-only
    STATUS      mandatory
    DESCRIPTION
"1300.0030.0001.0002 This attribute defines the index (one based) of
the physical memory configuration."
    ::= { physicalMemoryConfigTableEntry 2 }
physicalMemoryConfigStateCapabilities           OBJECT-TYPE
    SYNTAX      DellPhysicalMemoryConfigStateCapabilities
    ACCESS      read-only
    STATUS      mandatory
    DESCRIPTION
"1300.0030.0001.0003 This attribute defines the state capabilities of
the physical memory configuration."
    ::= { physicalMemoryConfigTableEntry 3 }
physicalMemoryConfigStateSettings               OBJECT-TYPE
    SYNTAX      DellPhysicalMemoryConfigStateSettings
    ACCESS      read-write
    STATUS      mandatory
    DESCRIPTION
"1300.0030.0001.0004 This attribute defines the state settings of
the physical memory configuration."
    ::= { physicalMemoryConfigTableEntry 4 }
physicalMemoryConfigStatus                      OBJECT-TYPE
    SYNTAX      DellStatus
    ACCESS      read-only
    STATUS      mandatory
    DESCRIPTION
"1300.0030.0001.0005 This attribute defines the status of
the physical memory configuration."
    ::= { physicalMemoryConfigTableEntry 5 }
physicalMemoryConfigRedundantCapabilities       OBJECT-TYPE
    SYNTAX      DellPhysicalMemoryConfigRedundantCapabilities
    ACCESS      read-only
    STATUS      mandatory
    DESCRIPTION
"1300.0030.0001.0006 This attribute defines the redundant capabilities of
the physical memory."
    ::= { physicalMemoryConfigTableEntry 6 }
physicalMemoryConfigRedundantSettings           OBJECT-TYPE
    SYNTAX      DellPhysicalMemoryConfigRedundantSettings
    ACCESS      read-write
    STATUS      mandatory
    DESCRIPTION
"1300.0030.0001.0007 This attribute defines the redundant settings of
the physical memory."
    ::= { physicalMemoryConfigTableEntry 7 }


-------------------------------------------------------------------------------
-- Physical Memory Logging Table
-------------------------------------------------------------------------------

DellPhysicalMemoryLoggingCapabilities           ::= INTEGER {
    -- If set to 0 (zero) there are no logging capabilities
    unknownCapabilities(1),                     -- Logging capabilities are unknown
    -- The logging capabilities are:
    enableCapable(2)                            -- Logging enable/disable via SNMP is supported
}
DellPhysicalMemoryLoggingSettings               ::= INTEGER {
    -- If set to 0 (zero) there are no logging settings enabled
    unknown(1),                                 -- Logging settings are unknown
	-- The logging settings are:
    enabled(2)                                  -- Logging is disabled (0), or enabled (1)
}

PhysicalMemoryLoggingTableEntry                 ::= SEQUENCE {
    physicalMemoryLoggingChassisIndex           DellObjectRange,
    physicalMemoryLoggingIndex                  DellObjectRange,
    physicalMemoryLoggingCapabilities           DellPhysicalMemoryLoggingCapabilities,
    physicalMemoryLoggingSettings               DellPhysicalMemoryLoggingSettings,
    physicalMemoryLoggingStatus                 DellStatus
}

physicalMemoryLoggingTable                      OBJECT-TYPE
    SYNTAX      SEQUENCE OF PhysicalMemoryLoggingTableEntry
    ACCESS      not-accessible
    STATUS      mandatory
    DESCRIPTION
"1300.0040 This object defines the Physical Memory Logging Table."
    ::= { memoryGroup 40 }
physicalMemoryLoggingTableEntry                 OBJECT-TYPE
    SYNTAX      PhysicalMemoryLoggingTableEntry
    ACCESS      not-accessible
    STATUS      mandatory
    DESCRIPTION
"1300.0040.0001 This object defines the Physical Memory Logging Table Entry."
    INDEX       { physicalMemoryLoggingChassisIndex, physicalMemoryLoggingIndex }
    ::= { physicalMemoryLoggingTable 1 }
physicalMemoryLoggingChassisIndex               OBJECT-TYPE
    SYNTAX      DellObjectRange
    ACCESS      read-only
    STATUS      mandatory
    DESCRIPTION
"1300.0040.0001.0001 This attribute defines the index (one based) of
the chassis associated with the physical memory logging."
    ::= { physicalMemoryLoggingTableEntry 1 }
physicalMemoryLoggingIndex                      OBJECT-TYPE
    SYNTAX      DellObjectRange
    ACCESS      read-only
    STATUS      mandatory
    DESCRIPTION
"1300.0040.0001.0002 This attribute defines the index (one based) of
the physical memory logging."
    ::= { physicalMemoryLoggingTableEntry 2 }
physicalMemoryLoggingCapabilities               OBJECT-TYPE
    SYNTAX      DellPhysicalMemoryLoggingCapabilities
    ACCESS      read-only
    STATUS      mandatory
    DESCRIPTION
"1300.0040.0001.0003 This attribute defines the capabilities of
the physical memory logging."
    ::= { physicalMemoryLoggingTableEntry 3 }
physicalMemoryLoggingSettings                   OBJECT-TYPE
    SYNTAX      DellPhysicalMemoryLoggingSettings
    ACCESS      read-write
    STATUS      mandatory
    DESCRIPTION
"1300.0040.0001.0004 This attribute defines the settings of
the physical memory logging."
    ::= { physicalMemoryLoggingTableEntry 4 }
physicalMemoryLoggingStatus                     OBJECT-TYPE
    SYNTAX      DellStatus
    ACCESS      read-only
    STATUS      mandatory
    DESCRIPTION
"1300.0040.0001.0005 This attribute defines the status of
the physical memory logging."
    ::= { physicalMemoryLoggingTableEntry 5 }


-------------------------------------------------------------------------------
-- Redundant Memory Unit Table
-------------------------------------------------------------------------------

RedundantMemoryUnitTableEntry                   ::= SEQUENCE {
    redundantMemoryUnitChassisIndex             DellObjectRange,
    redundantMemoryUnitIndex                    DellObjectRange,
    redundantMemoryUnitStateCapabilities        DellStateCapabilities,
    redundantMemoryUnitStateSettings            DellStateSettings,
    redundantMemoryUnitRedundancyStatus         DellStatusRedundancy,
    redundantMemoryUnitName                     DellString
}

redundantMemoryUnitTable                        OBJECT-TYPE
    SYNTAX      SEQUENCE OF RedundantMemoryUnitTableEntry
    ACCESS      not-accessible
    STATUS      mandatory
    DESCRIPTION
"1300.0050 This object defines the Redundant Memory Unit Table."
    ::= { memoryGroup 50 }
redundantMemoryUnitTableEntry                   OBJECT-TYPE
    SYNTAX      RedundantMemoryUnitTableEntry
    ACCESS      not-accessible
    STATUS      mandatory
    DESCRIPTION
"1300.0050.0001 This object defines the Redundant Memory Unit Table Entry."
    INDEX       { redundantMemoryUnitChassisIndex, redundantMemoryUnitIndex }
    ::= { redundantMemoryUnitTable 1 }
redundantMemoryUnitChassisIndex                 OBJECT-TYPE
    SYNTAX      DellObjectRange
    ACCESS      read-only
    STATUS      mandatory
    DESCRIPTION
"1300.0050.0001.0001 This attribute defines the index (one based) of
the chassis associated with the redundant memory unit."
    ::= { redundantMemoryUnitTableEntry 1 }
redundantMemoryUnitIndex                        OBJECT-TYPE
    SYNTAX      DellObjectRange
    ACCESS      read-only
    STATUS      mandatory
    DESCRIPTION
"1300.0050.0001.0002 This attribute defines the index (one based) of
the redundant memory unit."
    ::= { redundantMemoryUnitTableEntry 2 }
redundantMemoryUnitStateCapabilities            OBJECT-TYPE
    SYNTAX      DellStateCapabilities
    ACCESS      read-only
    STATUS      mandatory
    DESCRIPTION
"1300.0050.0001.0003 This attribute defines the state capabilities of
the redundant memory unit."
    ::= { redundantMemoryUnitTableEntry 3 }
redundantMemoryUnitStateSettings                OBJECT-TYPE
    SYNTAX      DellStateSettings
    ACCESS      read-write
    STATUS      mandatory
    DESCRIPTION
"1300.0050.0001.0004 This attribute defines the state settings of
the redundant memory unit."
    ::= { redundantMemoryUnitTableEntry 4 }
redundantMemoryUnitRedundancyStatus             OBJECT-TYPE
    SYNTAX      DellStatusRedundancy
    ACCESS      read-only
    STATUS      mandatory
    DESCRIPTION
"1300.0050.0001.0005 This attribute defines the redundancy status of
the redundant memory unit."
    ::= { redundantMemoryUnitTableEntry 5 }
redundantMemoryUnitName                         OBJECT-TYPE
    SYNTAX      DellString
    ACCESS      read-only
    STATUS      mandatory
    DESCRIPTION
"1300.0050.0001.0006 This attribute defines the name of
the redundant memory unit."
    ::= { redundantMemoryUnitTableEntry 6 }


-------------------------------------------------------------------------------
--
-- BIOS Setup Control Group
--
-------------------------------------------------------------------------------

-------------------------------------------------------------------------------
-- BIOS Setup Control Table
-------------------------------------------------------------------------------

DellSpeakerControlCapabilitiesUnique ::= INTEGER {
    unknown(1),                      -- unknown Speaker Control capabilities
    enableCapable(2),                -- Setup BIOS is Capable of enabling Speaker Control
    lowCapable(4),                   -- Setup BIOS is Capable of setting the speaker volume low
    mediumCapable(8),                -- Setup BIOS is Capable of setting the speaker volume medium
    highCapable(16),                 -- Setup BIOS is Capable of setting the speaker volume high
    allVolumeCapable(30)             -- Setup BIOS is Capable of setting to any of the three volumes
}
DellSpeakerControlSettingsUnique     ::= INTEGER {
    unknown(1),                      -- SpeakerControl state is unknown
    enabled(2),                      -- SpeakerControl is enabled
    low(4),                          -- SpeakerControl volume is low
    medium(8),                       -- SpeakerControl volume is medium
    high(16)                         -- SpeakerControl volume is high
}
DellNIFwakeonLanControlCapabilitiesUnique ::= INTEGER {
    unknown(1),                           -- unknown Setup BIOS wake on Lan capabilities
    enableCapable(2),                     -- Setup BIOS is Capable of enabling the NIF wake on Lan
    addInCardCapable(4),                  -- Setup BIOS is Capable of enabling wake on Lan by add in card
    onBoardCapable(8),                    -- Setup BIOS is Capable of enabling wake on Lan by on board NIF
    bothCapable(14)                       -- Setup BIOS is Capable of enabling wake on Lan by either add in or on board
}
DellNIFwakeonLanControlSettingsUnique     ::= INTEGER {
    unknown(1),                           -- NIF wake on Lan state is unknown
    enabled(2),                           -- NIF wake on Lan is enabled
    addInCard(4),                         -- NIF wake on Lan is by add in card
    onBoard(8),                           -- NIF wake on Lan is by on board NIF
    addInCardOrOnBoard(12)                -- NIF wake on Lan is by either
}
DellBootSequenceControlCapabilitiesUnique       ::= INTEGER {
    bootSequenceUnknown(1),                     -- unknown Boot Sequence capabilities
    bootFromDisketteFirstCapable(2),            -- Setup BIOS is Capable of booting by diskette first
    bootFromhardDriveFirstCapable(4),           -- Setup BIOS is Capable of booting by IDE hard drive first
    bootFromDisketteORHardDriveFirstCapable(6), -- Setup BIOS is Capable of booting by IDE hard drive first
    bootFromDeviceListCapable(8),               -- Setup BIOS is Capable of booting by a device list
    bootFromCDROMFirstCapable(16),              -- Setup BIOS is Capable of booting by CD ROM first
    allFirstCapable(30)                         -- Setup BIOS is Capable of booting by any of the above methods first
}
DellBootSequenceControlSettingsUnique           ::= INTEGER {
    bootSequenceUnknown(1),                     -- Boot Sequence state is unknown
    bootFromDisketteFirst(2),                   -- Setup BIOS is set to boot by diskette first
    bootFromHardDriveFirst(4),                  -- Setup BIOS is set to boot by IDE hard drive first
    bootFromDeviceList(8),                      -- Setup BIOS is set to boot by a device list
    bootFromCDROMFirst(16)                      -- Setup BIOS is set to boot by CD ROM first
}
DellBIOSPasswordControlCapabilitiesUnique           ::= INTEGER {
    passwordControlCapabilitiesUnknown(1),          -- unknown BIOS password capabilities
    passwordControlEnableCapable(2),                -- Setup BIOS is Capable of enabling password changes
    passwordControlJumperDisableCapable(4),         -- Setup BIOS is Capable of determining if password control can be jumper disabled
    passwordControlEnableANDJumperDisableCapable(6) -- Setup BIOS is Capable of determining if password control can be both
}
DellBIOSPasswordControlSettingsUnique               ::= INTEGER {
    passwordControlSettingsUnknown(1),              -- Setup BIOS password state is unknown
    passwordControlEnabled(2),                      -- Setup BIOS has password changes enabled
    passwordControlJumperDisabled(4)                -- Setup BIOS has determined that password control has been disabled by a jumper
}

BiosSetUpControlTableEntry                              ::= SEQUENCE {
    biosSetUpControlchassisIndex                        DellObjectRange,
    bSUCpointingDeviceControlCapabilities               DellStateCapabilities,
    bSUCpointingDeviceControlSettings                   DellStateSettings,
    bSUCpointingDeviceControlStatus                     DellStatus,
    bSUCpointingDeviceControlName                       DellString,
    bSUCnumLockControlCapabilities                      DellStateCapabilities,
    bSUCnumLockControlSettings                          DellStateSettings,
    bSUCnumLockControlStatus                            DellStatus,
    bSUCnumLockControlName                              DellString,
    bSUCprocessorSerialNumberControlCapabilities        DellStateCapabilities,
    bSUCprocessorSerialNumberControlSettings            DellStateSettings,
    bSUCprocessorSerialNumberControlStatus              DellStatus,
    bSUCprocessorSerialNumberControlName                DellString,
    bSUCspeakerControlCapabilitiesUnique                DellSpeakerControlCapabilitiesUnique,
    bSUCspeakerControlSettingsUnique                    DellSpeakerControlSettingsUnique,
    bSUCspeakerControlStatus                            DellStatus,
    bSUCspeakerControlName                              DellString,
    bSUCnIFwakeonLanControlCapabilitiesUnique           DellNIFwakeonLanControlCapabilitiesUnique,
    bSUCnIFwakeonLanControlSettingsUnique               DellNIFwakeonLanControlSettingsUnique,
    bSUCnIFwakeonLanControlStatus                       DellStatus,
    bSUCnIFwakeonLanControlName                         DellString,
    bSUCbootSequenceControlCapabilitiesUnique           DellBootSequenceControlCapabilitiesUnique,
    bSUCbootSequenceControlSettingsUnique               DellBootSequenceControlSettingsUnique,
    bSUCbootSequenceControlStatus                       DellStatus,
    bSUCbootSequenceControlName                         DellString,
    bSUCadministratorPasswordControlCapabilitiesUnique  DellBIOSPasswordControlCapabilitiesUnique,
    bSUCadministratorPasswordControlSettingsUnique      DellBIOSPasswordControlSettingsUnique,
    bSUCadministratorPasswordControlStatus              DellStatus,
    bSUCadministratorPasswordPasswordVerifyName         DellString,
    bSUCadministratorPasswordNewPasswordName            DellString,
    bSUCuserPasswordControlCapabilitiesUnique           DellBIOSPasswordControlCapabilitiesUnique,
    bSUCuserPasswordControlSettingsUnique               DellBIOSPasswordControlSettingsUnique,
    bSUCuserPasswordControlStatus                       DellStatus,
    bSUCuserPasswordPasswordVerifyName                  DellString,
    bSUCuserPasswordNewPasswordName                     DellString
}

biosSetUpControlTable                   OBJECT-TYPE
    SYNTAX      SEQUENCE OF BiosSetUpControlTableEntry
    ACCESS      not-accessible
    STATUS      mandatory
    DESCRIPTION
"1400.0010 This Group defines the set of single devices in a Dell
chassis controlled by BIOS."
    ::= { biosSetUpControlGroup 10 }
biosSetUpControlTableEntry              OBJECT-TYPE
    SYNTAX      BiosSetUpControlTableEntry
    ACCESS      not-accessible
    STATUS      mandatory
    DESCRIPTION
"1400.0010.0001 This Group defines the Dell BIOS Control Device Table Entry."
    INDEX       { biosSetUpControlchassisIndex }
    ::= { biosSetUpControlTable 1 }
biosSetUpControlchassisIndex               OBJECT-TYPE
    SYNTAX      DellObjectRange
    ACCESS      read-only
    STATUS      mandatory
    DESCRIPTION
"1400.0010.0001.0001 This attribute defines the index (one based) of
this Dell chassis."
    ::= { biosSetUpControlTableEntry 1 }
bSUCpointingDeviceControlCapabilities           OBJECT-TYPE
    SYNTAX      DellStateCapabilities
    ACCESS      read-only
    STATUS      mandatory
    DESCRIPTION
"1400.0010.0001.0002 This attribute defines the capabilities of the Dell
pointing Device."
    ::= { biosSetUpControlTableEntry 2 }
bSUCpointingDeviceControlSettings               OBJECT-TYPE
    SYNTAX      DellStateSettings
    ACCESS      read-write
    STATUS      mandatory
    DESCRIPTION
"1400.0010.0001.0003 This attribute defines the state of the Dell pointing
Device."
    ::= { biosSetUpControlTableEntry 3 }
bSUCpointingDeviceControlStatus               OBJECT-TYPE
    SYNTAX      DellStatus
    ACCESS      read-only
    STATUS      mandatory
    DESCRIPTION
"1400.0010.0001.0004 This attribute defines the status of the Dell pointing
Device."
    ::= { biosSetUpControlTableEntry 4 }
bSUCpointingDeviceControlName                   OBJECT-TYPE
    SYNTAX      DellString
    ACCESS      read-only
    STATUS      mandatory
    DESCRIPTION
"1400.0010.0001.0005 This attribute defines the setup BIOS name of the
pointing device."
    ::= { biosSetUpControlTableEntry 5 }
bSUCnumLockControlCapabilities          OBJECT-TYPE
    SYNTAX      DellStateCapabilities
    ACCESS      read-only
    STATUS      mandatory
    DESCRIPTION
"1400.0010.0001.0006 This attribute defines the capabilities of the Dell
Numeric Lock."
    ::= { biosSetUpControlTableEntry 6 }
bSUCnumLockControlSettings                 OBJECT-TYPE
    SYNTAX      DellStateSettings
    ACCESS      read-write
    STATUS      mandatory
    DESCRIPTION
"1400.0010.0001.0007 This attribute defines the state of the Dell
Numeric Lock."
    ::= { biosSetUpControlTableEntry 7 }
bSUCnumLockControlStatus                 OBJECT-TYPE
    SYNTAX      DellStatus
    ACCESS      read-only
    STATUS      mandatory
    DESCRIPTION
"1400.0010.0001.0008 This attribute defines the status of the Dell
Numeric Lock."
    ::= { biosSetUpControlTableEntry 8 }
bSUCnumLockControlName                  OBJECT-TYPE
    SYNTAX      DellString
    ACCESS      read-only
    STATUS      mandatory
    DESCRIPTION
"1400.0010.0001.0009 This attribute defines the setup BIOS name of the
numeric lock."
    ::= { biosSetUpControlTableEntry 9 }
bSUCprocessorSerialNumberControlCapabilities            OBJECT-TYPE
    SYNTAX      DellStateCapabilities
    ACCESS      read-only
    STATUS      mandatory
    DESCRIPTION
"1400.0010.0001.0010 This attribute defines the capabilities of the Dell
Processor Serial Number."
    ::= { biosSetUpControlTableEntry 10 }
bSUCprocessorSerialNumberControlSettings               OBJECT-TYPE
    SYNTAX      DellStateSettings
    ACCESS      read-write
    STATUS      mandatory
    DESCRIPTION
"1400.0010.0001.0011 This attribute defines the state of the Dell
Processor Serial Number."
    ::= { biosSetUpControlTableEntry 11 }
bSUCprocessorSerialNumberControlStatus              OBJECT-TYPE
    SYNTAX      DellStatus
    ACCESS      read-only
    STATUS      mandatory
    DESCRIPTION
"1400.0010.0001.0012 This attribute defines the status of the Dell
Processor Serial Number."
    ::= { biosSetUpControlTableEntry 12 }
bSUCprocessorSerialNumberControlName                    OBJECT-TYPE
    SYNTAX      DellString
    ACCESS      read-only
    STATUS      mandatory
    DESCRIPTION
"1400.0010.0001.0013 This attribute defines the setup BIOS name of the
Processor Serial Number."
    ::= { biosSetUpControlTableEntry 13 }
bSUCspeakerControlCapabilitiesUnique          OBJECT-TYPE
    SYNTAX      DellSpeakerControlCapabilitiesUnique
    ACCESS      read-only
    STATUS      mandatory
    DESCRIPTION
"1400.0010.0001.0014 This attribute defines the capabilities of the Dell
Speaker Control."
    ::= { biosSetUpControlTableEntry 14 }
bSUCspeakerControlSettingsUnique             OBJECT-TYPE
    SYNTAX      DellSpeakerControlSettingsUnique
    ACCESS      read-write
    STATUS      mandatory
    DESCRIPTION
"1400.0010.0001.0015 This attribute defines the state of the Dell
Speaker Control."
    ::= { biosSetUpControlTableEntry 15 }
bSUCspeakerControlStatus             OBJECT-TYPE
    SYNTAX      DellStatus
    ACCESS      read-only
    STATUS      mandatory
    DESCRIPTION
"1400.0010.0001.0016 This attribute defines the status of the Dell
Speaker Control."
    ::= { biosSetUpControlTableEntry 16 }
bSUCspeakerControlName                  OBJECT-TYPE
    SYNTAX      DellString
    ACCESS      read-only
    STATUS      mandatory
    DESCRIPTION
"1400.0010.0001.0017 This attribute defines the setup BIOS name of the
Speaker Control."
    ::= { biosSetUpControlTableEntry 17 }
bSUCnIFwakeonLanControlCapabilitiesUnique         OBJECT-TYPE
    SYNTAX      DellNIFwakeonLanControlCapabilitiesUnique
    ACCESS      read-only
    STATUS      mandatory
    DESCRIPTION
"1400.0010.0001.0018 This attribute defines the capabilities of the Dell
NIF wake on Lan."
    ::= { biosSetUpControlTableEntry 18 }
bSUCnIFwakeonLanControlSettingsUnique             OBJECT-TYPE
    SYNTAX      DellNIFwakeonLanControlSettingsUnique
    ACCESS      read-write
    STATUS      mandatory
    DESCRIPTION
"1400.0010.0001.0019 This attribute defines the state of the Dell NIF wake
on Lan."
    ::= { biosSetUpControlTableEntry 19 }
bSUCnIFwakeonLanControlStatus             OBJECT-TYPE
    SYNTAX      DellStatus
    ACCESS      read-only
    STATUS      mandatory
    DESCRIPTION
"1400.0010.0001.0020 This attribute defines the status of the Dell NIF wake
on Lan."
    ::= { biosSetUpControlTableEntry 20 }
bSUCnIFwakeonLanControlName                 OBJECT-TYPE
    SYNTAX      DellString
    ACCESS      read-only
    STATUS      mandatory
    DESCRIPTION
"1400.0010.0001.0021 This attribute defines the setup BIOS name of the
NIF wake on Lan."
    ::= { biosSetUpControlTableEntry 21 }
bSUCbootSequenceControlCapabilitiesUnique         OBJECT-TYPE
    SYNTAX      DellBootSequenceControlCapabilitiesUnique
    ACCESS      read-only
    STATUS      mandatory
    DESCRIPTION
"1400.0010.0001.0022 This attribute defines the capabilities of the Dell
Boot Sequence."
    ::= { biosSetUpControlTableEntry 22 }
bSUCbootSequenceControlSettingsUnique             OBJECT-TYPE
    SYNTAX      DellBootSequenceControlSettingsUnique
    ACCESS      read-write
    STATUS      mandatory
    DESCRIPTION
"1400.0010.0001.0023 This attribute defines the state of the Dell Boot
Sequence."
    ::= { biosSetUpControlTableEntry 23 }
bSUCbootSequenceControlStatus             OBJECT-TYPE
    SYNTAX      DellStatus
    ACCESS      read-only
    STATUS      mandatory
    DESCRIPTION
"1400.0010.0001.0024 This attribute defines the status of the Dell Boot
Sequence."
    ::= { biosSetUpControlTableEntry 24 }
bSUCbootSequenceControlName                 OBJECT-TYPE
    SYNTAX      DellString
    ACCESS      read-only
    STATUS      mandatory
    DESCRIPTION
"1400.0010.0001.0025 This attribute defines the setup BIOS name of the
Boot Sequence."
    ::= { biosSetUpControlTableEntry 25 }
bSUCadministratorPasswordControlCapabilitiesUnique      OBJECT-TYPE
    SYNTAX      DellBIOSPasswordControlCapabilitiesUnique
    ACCESS      read-only
    STATUS      mandatory
    DESCRIPTION
"1400.0010.0001.0026 This attribute defines the capabilities of the Dell
Administrator Password Control."
    ::= { biosSetUpControlTableEntry 26 }
bSUCadministratorPasswordControlSettingsUnique         OBJECT-TYPE
    SYNTAX      DellBIOSPasswordControlSettingsUnique
    ACCESS      read-write
    STATUS      mandatory
    DESCRIPTION
"1400.0010.0001.0027 This attribute defines the state of the Dell
Administrator Password Control."
    ::= { biosSetUpControlTableEntry 27 }
bSUCadministratorPasswordControlStatus              OBJECT-TYPE
    SYNTAX      DellStatus
    ACCESS      read-only
    STATUS      mandatory
    DESCRIPTION
"1400.0010.0001.0028 This attribute defines the status of the Dell
Administrator Password Control."
    ::= { biosSetUpControlTableEntry 28 }
bSUCadministratorPasswordPasswordVerifyName     OBJECT-TYPE
    SYNTAX      DellString
    ACCESS      read-write
    STATUS      mandatory
    DESCRIPTION
"1400.0010.0001.0029 This attribute defines the setup BIOS name of the
current Administrator Password."
    ::= { biosSetUpControlTableEntry 29 }
bSUCadministratorPasswordNewPasswordName     OBJECT-TYPE
    SYNTAX      DellString
    ACCESS      read-write
    STATUS      mandatory
    DESCRIPTION
"1400.0010.0001.0030 This attribute defines the setup BIOS name of the
new Administrator Password.  To set a new Administrator Password,
a successful set of the current Administrator Password must have been
done immediately preceeding this set."
    ::= { biosSetUpControlTableEntry 30 }
bSUCuserPasswordControlCapabilitiesUnique             OBJECT-TYPE
    SYNTAX      DellBIOSPasswordControlCapabilitiesUnique
    ACCESS      read-only
    STATUS      mandatory
    DESCRIPTION
"1400.0010.0001.0031 This attribute defines the capabilities of the Dell
User Password Control."
    ::= { biosSetUpControlTableEntry 31 }
bSUCuserPasswordControlSettingsUnique                 OBJECT-TYPE
    SYNTAX      DellBIOSPasswordControlSettingsUnique
    ACCESS      read-write
    STATUS      mandatory
    DESCRIPTION
"1400.0010.0001.0032 This attribute defines the state of the Dell User
Password Control."
    ::= { biosSetUpControlTableEntry 32 }
bSUCuserPasswordControlStatus                 OBJECT-TYPE
    SYNTAX      DellStatus
    ACCESS      read-only
    STATUS      mandatory
    DESCRIPTION
"1400.0010.0001.0033 This attribute defines the status of the Dell User
Password Control."
    ::= { biosSetUpControlTableEntry 33 }
bSUCuserPasswordPasswordVerifyName         OBJECT-TYPE
    SYNTAX      DellString
    ACCESS      read-write
    STATUS      mandatory
    DESCRIPTION
"1400.0010.0001.0034 This attribute defines the setup BIOS name of the
current User Password."
    ::= { biosSetUpControlTableEntry 34 }
bSUCuserPasswordNewPasswordName         OBJECT-TYPE
    SYNTAX      DellString
    ACCESS      read-write
    STATUS      mandatory
    DESCRIPTION
"1400.0010.0001.0035 This attribute defines the setup BIOS name of the
new User Password.  To set a new User Password, a successful set of the
current User Password must have been done immediately preceeding this set."
    ::= { biosSetUpControlTableEntry 35 }


-------------------------------------------------------------------------------
-- SCSI Control Table
-------------------------------------------------------------------------------

SCSIControlTableEntry       ::= SEQUENCE {
    sCSIControlchassisIndex DellObjectRange,
    sCSIControlIndex        DellObjectRange,
    sCSIControlCapabilities DellStateCapabilities,
    sCSIControlSettings     DellStateSettings,
    sCSIControlStatus       DellStatus,
    sCSIControlName         DellString
}

sCSIControlTable            OBJECT-TYPE
    SYNTAX      SEQUENCE OF SCSIControlTableEntry
    ACCESS      not-accessible
    STATUS      mandatory
    DESCRIPTION
"1400.0020 This Group defines the Dell SCSI Table."
    ::= { biosSetUpControlGroup 20 }
sCSIControlTableEntry       OBJECT-TYPE
    SYNTAX      SCSIControlTableEntry
    ACCESS      not-accessible
    STATUS      mandatory
    DESCRIPTION
"1400.0020.0001 This Group defines the Dell SCSI Table Entry."
    INDEX       { sCSIControlchassisIndex, sCSIControlIndex }
    ::= { sCSIControlTable 1 }
sCSIControlchassisIndex                 OBJECT-TYPE
    SYNTAX      DellObjectRange
    ACCESS      read-only
    STATUS      mandatory
    DESCRIPTION
"1400.0020.0001.0001 This attribute defines the index (one based) of
this Dell chassis."
    ::= { sCSIControlTableEntry 1 }
sCSIControlIndex                   OBJECT-TYPE
    SYNTAX      DellObjectRange
    ACCESS      read-only
    STATUS      mandatory
    DESCRIPTION
"1400.0020.0001.0002 This attribute defines the index of the Dell
SCSI controller in this chassis."
    ::= { sCSIControlTableEntry 2 }
sCSIControlCapabilities     OBJECT-TYPE
    SYNTAX      DellStateCapabilities
    ACCESS      read-only
    STATUS      mandatory
    DESCRIPTION
"1400.0020.0001.0003 This attribute defines the capabilities of the
Dell SCSI controller."
    ::= { sCSIControlTableEntry 3 }
sCSIControlSettings         OBJECT-TYPE
    SYNTAX      DellStateSettings
    ACCESS      read-write
    STATUS      mandatory
    DESCRIPTION
"1400.0020.0001.0004 This attribute defines the state of the Dell
SCSI controller."
    ::= { sCSIControlTableEntry 4 }
sCSIControlStatus         OBJECT-TYPE
    SYNTAX      DellStatus
    ACCESS      read-only
    STATUS      mandatory
    DESCRIPTION
"1400.0020.0001.0005 This attribute defines the status of the Dell
SCSI controller."
    ::= { sCSIControlTableEntry 5 }
sCSIControlName             OBJECT-TYPE
    SYNTAX      DellString
    ACCESS      read-only
    STATUS      mandatory
    DESCRIPTION
"1400.0020.0001.0006 This attribute defines the setup BIOS name of the
Dell SCSI controller."
    ::= { sCSIControlTableEntry 6 }


-------------------------------------------------------------------------------
-- Parallel Port Control Table
-------------------------------------------------------------------------------

DellParallelPortControlCapabilitiesUnique ::= INTEGER {
    unknown(1),                -- unknown Setup BIOS Parallel Port capabilities
    enableCapable(2),          -- Setup BIOS is Capable of enabling the Parallel Port
    lpt1Capable(4),            -- Setup BIOS is Capable of supporting parallel port 1
    lpt1andEnableCapable(6),   -- Setup BIOS has enabled parallel port 1
    lpt2Capable(8),            -- Setup BIOS is Capable of supporting parallel port 2
    lpt2andEnableCapable(10),  -- Setup BIOS has enabled parallel port 1
    lpt3Capable(16),           -- Setup BIOS is Capable of supporting parallel port 3
    lpt3andEnableCapable(18),  -- Setup BIOS has enabled parallel port 1
    allParallelPortCapable(30) -- Setup BIOS is Capable of supporting any of the three parallel ports
}
DellParallelPortControlSettingsUnique ::= INTEGER {
    unknown(1),                -- Parallel Port state is unknown
    enabled(2),                -- Setup BIOS has enabled the Parallel Port
    lpt1(4),                   -- Setup BIOS supports parallel port 1
    lpt1Enabled(6),            -- Setup BIOS has enabled parallel port 1
    lpt2(8),                   -- Setup BIOS supports parallel port 2
    lpt2Enabled(10),           -- Setup BIOS has enabled parallel port 2
    lpt3(16),                  -- Setup BIOS supports parallel port 3
    lpt3Enabled(18)            -- Setup BIOS has enabled parallel port 3
}
DellParallelPortControlModeCapabilitiesUnique ::= INTEGER {
    unknown(1),                -- unknown Setup BIOS Parallel Port mode setting capabilities
    atCapable(2),              -- Setup BIOS is Capable of setting parallel port to AT mode
    ps2Capable(4),             -- Setup BIOS is Capable of setting parallel port to PS2 mode
    atAndPS2Capable(6),        -- Setup BIOS is Capable of setting parallel port to AT or PS2 mode
    ecpCapable(8),             -- Setup BIOS is Capable of setting parallel port to ECP mode
    eppCapable(16),            -- Setup BIOS is Capable of setting parallel port to EPP mode
    allModeCapable(30)         -- Setup BIOS is Capable of enabling any of the parallel modes
}
DellParallelPortControlModeSettingsUnique        ::= INTEGER {
    unknown(1),                -- Parallel Port mode  is unknown
    atModeEnabled(2),          -- Setup BIOS has set the parallel port to AT mode
    ps2ModeEnabled(4),         -- Setup BIOS has set the parallel port to PS2 mode
    ecpModeEnabled(8),         -- Setup BIOS has set the parallel port to ECP mode
    eppModeEnabled(16)         -- Setup BIOS has set the parallel port to EPP mode
}

ParallelPortControlTableEntry                   ::= SEQUENCE {
    parallelPortControlchassisIndex             DellObjectRange,
    parallelPortControlIndex                    DellObjectRange,
    parallelPortControlCapabilitiesUnique       DellParallelPortControlCapabilitiesUnique,
    parallelPortControlSettingsUnique           DellParallelPortControlSettingsUnique,
    parallelPortControlStatus                   DellStatus,
    parallelPortControlName                     DellString,
    parallelPortControlModeCapabilitiesUnique   DellParallelPortControlModeCapabilitiesUnique,
    parallelPortControlModeSettingsUnique       DellParallelPortControlModeSettingsUnique
}

parallelPortControlTable                    OBJECT-TYPE
    SYNTAX      SEQUENCE OF ParallelPortControlTableEntry
    ACCESS      not-accessible
    STATUS      mandatory
    DESCRIPTION
"1400.0030 This Group defines the Dell Parallel Port Table."
    ::= { biosSetUpControlGroup 30 }
parallelPortControlTableEntry               OBJECT-TYPE
    SYNTAX      ParallelPortControlTableEntry
    ACCESS      not-accessible
    STATUS      mandatory
    DESCRIPTION
"1400.0030.0001 This Group defines the Dell Parallel Port Table Entry."
    INDEX       { parallelPortControlchassisIndex, parallelPortControlIndex }
    ::= { parallelPortControlTable 1 }
parallelPortControlchassisIndex                 OBJECT-TYPE
    SYNTAX      DellObjectRange
    ACCESS      read-only
    STATUS      mandatory
    DESCRIPTION
"1400.0030.0001.0001 This attribute defines the index (one based) of
this Dell chassis."
    ::= { parallelPortControlTableEntry 1 }
parallelPortControlIndex                    OBJECT-TYPE
    SYNTAX      DellObjectRange
    ACCESS      read-only
    STATUS      mandatory
    DESCRIPTION
"1400.0030.0001.0002 This attribute defines the index of the Dell
Parallel Port in this chassis."
    ::= { parallelPortControlTableEntry 2 }
parallelPortControlCapabilitiesUnique       OBJECT-TYPE
    SYNTAX      DellParallelPortControlCapabilitiesUnique
    ACCESS      read-only
    STATUS      mandatory
    DESCRIPTION
"1400.0030.0001.0003 This attribute defines the capabilities of the Dell
Parallel Port."
    ::= { parallelPortControlTableEntry 3 }
parallelPortControlSettingsUnique          OBJECT-TYPE
    SYNTAX      DellParallelPortControlSettingsUnique
    ACCESS      read-write
    STATUS      mandatory
    DESCRIPTION
"1400.0030.0001.0004 This attribute defines the state of the Dell
Parallel Port."
    ::= { parallelPortControlTableEntry 4 }
parallelPortControlStatus          OBJECT-TYPE
    SYNTAX      DellStatus
    ACCESS      read-only
    STATUS      mandatory
    DESCRIPTION
"1400.0030.0001.0005 This attribute defines the status of the Dell
Parallel Port."
    ::= { parallelPortControlTableEntry 5 }
parallelPortControlName                     OBJECT-TYPE
    SYNTAX      DellString
    ACCESS      read-only
    STATUS      mandatory
    DESCRIPTION
"1400.0030.0001.0006 This attribute defines the setup BIOS name of the
Parallel Port."
    ::= { parallelPortControlTableEntry 6 }
parallelPortControlModeCapabilitiesUnique         OBJECT-TYPE
    SYNTAX      DellParallelPortControlModeCapabilitiesUnique
    ACCESS      read-only
    STATUS      mandatory
    DESCRIPTION
"1400.0030.0001.0007 This attribute defines the mode capabilities of the
Dell Parallel Port."
    ::= { parallelPortControlTableEntry 7 }
parallelPortControlModeSettingsUnique             OBJECT-TYPE
    SYNTAX      DellParallelPortControlModeSettingsUnique
    ACCESS      read-write
    STATUS      mandatory
    DESCRIPTION
"1400.0030.0001.0008 This attribute defines the mode state of the Dell
Parallel Port."
    ::= { parallelPortControlTableEntry 8 }


-------------------------------------------------------------------------------
-- Serial Port Control Table
-------------------------------------------------------------------------------

DellSerialPortControlCapabilitiesUnique ::= INTEGER {
    unknown(1),              -- unknown Setup BIOS Serial Port capabilities
    enableCapable(2),        -- Setup BIOS is Capable of enabling the Serial Port
    com1Capable(4),          -- Setup BIOS is Capable of supporting serial port 1
    enableAndCom1Capable(6), -- Setup BIOS is Capable of enabling serial port 1
    com2Capable(8),          -- Setup BIOS is Capable of supporting serial port 2
    enableAndCom2Capable(10),-- Setup BIOS is Capable of enabling serial port 2
    com3Capable(16),         -- Setup BIOS is Capable of supporting serial port 3
    enableAndCom3Capable(18),-- Setup BIOS is Capable of enabling serial port 3
    com4Capable(32),         -- Setup BIOS is Capable of supporting serial port 4
    enableAndCom4Capable(34),-- Setup BIOS is Capable of enabling serial port 4
    autoConfigCapable(64),   -- Setup BIOS is Capable of autoconfiguring all serial ports
    com1OrCom3CapableAndAutoConfigCapable(86),  -- Setup BIOS has enabled autoconfiguration of com1 and com3 serial ports
    com2OrCom4CapableAndAutoConfigCapable(106), -- Setup BIOS has enabled autoconfiguration of com2 and com4 serial ports
    allcomCapable(126)       -- Setup BIOS is Capable of enabling or autoconfiguring all serial ports
}
DellSerialPortControlSettingsUnique ::= INTEGER {
    unknown(1),              -- Serial Port state is unknown
    enabled(2),              -- Setup BIOS has enabled the Serial Port
    com1(4),                 -- Setup BIOS has selected serial port 1
    com1Enabled(6),          -- Setup BIOS has enabled serial port 1
    com2(8),                 -- Setup BIOS has selected serial port 2
    com2Enabled(10),         -- Setup BIOS has enabled serial port 2
    com3(16),                -- Setup BIOS has selected serial port 3
    com3Enabled(18),         -- Setup BIOS has enabled serial port 3
    com4(32),                -- Setup BIOS has selected serial port 4
    com4Enabled(34),         -- Setup BIOS has enabled serial port 4
    comPortsAutoConfig(64),  -- Setup BIOS has selected autoconfiguration of serial ports
    enabledAndAutoConfig(66) -- Setup BIOS has enabled autoconfiguration of serial ports
}

SerialPortControlTableEntry             ::= SEQUENCE {
    serialPortControlchassisIndex       DellObjectRange,
    serialPortControlIndex              DellObjectRange,
    serialPortControlCapabilitiesUnique DellSerialPortControlCapabilitiesUnique,
    serialPortControlSettingsUnique     DellSerialPortControlSettingsUnique,
    serialPortControlStatus             DellStatus,
    serialPortControlName               DellString
}

serialPortControlTable                  OBJECT-TYPE
    SYNTAX      SEQUENCE OF SerialPortControlTableEntry
    ACCESS      not-accessible
    STATUS      mandatory
    DESCRIPTION
"1400.0040 This Group defines the Dell Serial Port Table."
    ::= { biosSetUpControlGroup 40 }
serialPortControlTableEntry             OBJECT-TYPE
    SYNTAX      SerialPortControlTableEntry
    ACCESS      not-accessible
    STATUS      mandatory
    DESCRIPTION
"1400.0040.0001 This Group defines the Dell Serial Port Table Entry."
    INDEX       { serialPortControlchassisIndex, serialPortControlIndex }
    ::= { serialPortControlTable 1 }
serialPortControlchassisIndex               OBJECT-TYPE
    SYNTAX      DellObjectRange
    ACCESS      read-only
    STATUS      mandatory
    DESCRIPTION
"1400.0040.0001.0001 This attribute defines the index (one based) of
this Dell chassis."
    ::= { serialPortControlTableEntry 1 }
serialPortControlIndex                  OBJECT-TYPE
    SYNTAX      DellObjectRange
    ACCESS      read-only
    STATUS      mandatory
    DESCRIPTION
"1400.0040.0001.0002 This attribute defines the index of the Dell
Serial Port in this chassis."
    ::= { serialPortControlTableEntry 2 }
serialPortControlCapabilitiesUnique    OBJECT-TYPE
    SYNTAX      DellSerialPortControlCapabilitiesUnique
    ACCESS      read-only
    STATUS      mandatory
    DESCRIPTION
"1400.0040.0001.0003 This attribute defines the capabilities of the
Dell Serial Port."
    ::= { serialPortControlTableEntry 3 }
serialPortControlSettingsUnique        OBJECT-TYPE
    SYNTAX      DellSerialPortControlSettingsUnique
    ACCESS      read-write
    STATUS      mandatory
    DESCRIPTION
"1400.0040.0001.0004 This attribute defines the state of the
Dell Serial Port."
    ::= { serialPortControlTableEntry 4 }
serialPortControlStatus        OBJECT-TYPE
    SYNTAX      DellStatus
    ACCESS      read-only
    STATUS      mandatory
    DESCRIPTION
"1400.0040.0001.0005 This attribute defines the status of the
Dell Serial Port."
    ::= { serialPortControlTableEntry 5 }
serialPortControlName                  OBJECT-TYPE
    SYNTAX      DellString
    ACCESS      read-only
    STATUS      mandatory
    DESCRIPTION
"1400.0040.0001.0006 This attribute defines the setup BIOS name of the
Serial Port."
    ::= { serialPortControlTableEntry 6 }


-------------------------------------------------------------------------------
-- USB Control Table
-------------------------------------------------------------------------------

UsbControlTableEntry            ::= SEQUENCE {
    usbControlchassisIndex      DellObjectRange,
    usbControlIndex             DellObjectRange,
    usbControlCapabilities      DellStateCapabilities,
    usbControlSettings          DellStateSettings,
    usbControlStatus            DellStatus,
    usbControlName              DellString
}

usbControlTable                 OBJECT-TYPE
    SYNTAX      SEQUENCE OF UsbControlTableEntry
    ACCESS      not-accessible
    STATUS      mandatory
    DESCRIPTION
"1400.0050 This Group defines the Dell Universal Serial Bus Table."
    ::= { biosSetUpControlGroup 50 }
usbControlTableEntry            OBJECT-TYPE
    SYNTAX      UsbControlTableEntry
    ACCESS      not-accessible
    STATUS      mandatory
    DESCRIPTION
"1400.0050.0001 This Group defines the Dell Universal Serial Bus
Table Entry."
    INDEX       { usbControlchassisIndex, usbControlIndex }
    ::= { usbControlTable 1 }
usbControlchassisIndex              OBJECT-TYPE
    SYNTAX      DellObjectRange
    ACCESS      read-only
    STATUS      mandatory
    DESCRIPTION
"1400.0050.0001.0001 This attribute defines the index (one based) of
this Dell chassis."
    ::= { usbControlTableEntry 1 }
usbControlIndex                        OBJECT-TYPE
    SYNTAX      DellObjectRange
    ACCESS      read-only
    STATUS      mandatory
    DESCRIPTION
"1400.0050.0001.0002 This attribute defines the index of the Dell Universal
Serial Bus in this chassis."
    ::= { usbControlTableEntry 2 }
usbControlCapabilities          OBJECT-TYPE
    SYNTAX      DellStateCapabilities
    ACCESS      read-only
    STATUS      mandatory
    DESCRIPTION
"1400.0050.0001.0003 This attribute defines the capabilities of the
Dell Universal Serial Bus."
    ::= { usbControlTableEntry 3 }
usbControlSettings              OBJECT-TYPE
    SYNTAX      DellStateSettings
    ACCESS      read-write
    STATUS      mandatory
    DESCRIPTION
"1400.0050.0001.0004 This attribute defines the state of the Dell
Universal Serial Bus."
    ::= { usbControlTableEntry 4 }
usbControlStatus              OBJECT-TYPE
    SYNTAX      DellStatus
    ACCESS      read-only
    STATUS      mandatory
    DESCRIPTION
"1400.0050.0001.0005 This attribute defines the status of the Dell
Universal Serial Bus."
    ::= { usbControlTableEntry 5 }
usbControlName                  OBJECT-TYPE
    SYNTAX      DellString
    ACCESS      read-only
    STATUS      mandatory
    DESCRIPTION
"1400.0050.0001.0006 This attribute defines the setup BIOS name of the
Universal Serial Bus."
    ::= { usbControlTableEntry 6 }


-------------------------------------------------------------------------------
-- IDE Control Table
-------------------------------------------------------------------------------

DellideControlCapabilitiesUnique              ::= INTEGER {
    unknown(1),                               -- unknown IDE control capabilities
    ideControlAutoConfigOrEnableCapable(2)    -- IDE controller is autoconfigurable or enable capable
}
DellideControlSettingsUnique                  ::= INTEGER {
    unknown(1),                               -- unknown IDE control settings
    ideControlAutoConfigEnabledOrEnabled(2)   -- IDE controller is set as autoconfigurable or enabled
}

IdeControlTableEntry             ::= SEQUENCE {
    ideControlchassisIndex       DellObjectRange,
    ideControlIndex              DellObjectRange,
    ideControlCapabilitiesUnique DellideControlCapabilitiesUnique,
    ideControlSettingsUnique     DellideControlSettingsUnique,
    ideControlStatus             DellStatus,
    ideControlName               DellString
}

ideControlTable                 OBJECT-TYPE
    SYNTAX      SEQUENCE OF IdeControlTableEntry
    ACCESS      not-accessible
    STATUS      mandatory
    DESCRIPTION
"1400.0060 This Group defines the Dell IDE  Table."
    ::= { biosSetUpControlGroup 60 }
ideControlTableEntry            OBJECT-TYPE
    SYNTAX      IdeControlTableEntry
    ACCESS      not-accessible
    STATUS      mandatory
    DESCRIPTION
"1400.0060.0001 This Group defines the Dell IDE  Table Entry."
    INDEX       { ideControlchassisIndex, ideControlIndex }
    ::= { ideControlTable 1 }
ideControlchassisIndex              OBJECT-TYPE
    SYNTAX      DellObjectRange
    ACCESS      read-only
    STATUS      mandatory
    DESCRIPTION
"1400.0060.0001.0001 This attribute defines the index (one based) of
this Dell chassis."
    ::= { ideControlTableEntry 1 }
ideControlIndex                        OBJECT-TYPE
    SYNTAX      DellObjectRange
    ACCESS      read-only
    STATUS      mandatory
    DESCRIPTION
"1400.0060.0001.0002 This attribute defines the index of the Dell IDE
controller in this chassis."
    ::= { ideControlTableEntry 2 }
ideControlCapabilitiesUnique          OBJECT-TYPE
    SYNTAX      DellideControlCapabilitiesUnique
    ACCESS      read-only
    STATUS      mandatory
    DESCRIPTION
"1400.0060.0001.0003 This attribute defines the capabilities of the
Dell IDE controller."
    ::= { ideControlTableEntry 3 }
ideControlSettingsUnique              OBJECT-TYPE
    SYNTAX      DellideControlSettingsUnique
    ACCESS      read-write
    STATUS      mandatory
    DESCRIPTION
"1400.0060.0001.0004 This attribute defines the state of the Dell
IDE controller."
    ::= { ideControlTableEntry 4 }
ideControlStatus              OBJECT-TYPE
    SYNTAX      DellStatus
    ACCESS      read-only
    STATUS      mandatory
    DESCRIPTION
"1400.0060.0001.0005 This attribute defines the state of the Dell
IDE controller."
    ::= { ideControlTableEntry 5 }
ideControlName                  OBJECT-TYPE
    SYNTAX      DellString
    ACCESS      read-only
    STATUS      mandatory
    DESCRIPTION
"1400.0060.0001.0006 This attribute defines the setup BIOS name of the
IDE controller."
    ::= { ideControlTableEntry 6 }


-------------------------------------------------------------------------------
-- Diskette Control Table
-------------------------------------------------------------------------------

DellDisketteControlCapabilitiesUnique       ::= INTEGER {
    unknown(1),                             -- unknown Setup BIOS Diskette Control capabilities
    disketteAutoConfigOrEnableCapable(2),   -- Setup BIOS is Capable of enabling Diskette Control
    disketteReadOnlyCapable(4),             -- Setup BIOS is Capable of enabling read only Diskette Control
    disketteAutoConfigOrEnableCapableandReadOnlyCapable(6)   -- Setup BIOS is Capable of enabling a read only Diskette Control
}
DellDisketteControlSettingsUnique           ::= INTEGER {
    unknown(1),                             -- Diskette Control state is unknown
    disketteAutoConfigEnabledOrEnabled(2),  -- Diskette Control is autoconfigurable or enabled
    disketteisReadOnly(4)                   -- Diskette is in read only operation
}

DisketteControlTableEntry               ::= SEQUENCE {
    disketteControlchassisIndex         DellObjectRange,
    disketteControlIndex                DellObjectRange,
    disketteControlCapabilitiesUnique   DellDisketteControlCapabilitiesUnique,
    disketteControlSettingsUnique       DellDisketteControlSettingsUnique,
    disketteControlStatus               DellStatus,
    disketteControlName                 DellString
}

disketteControlTable                OBJECT-TYPE
    SYNTAX      SEQUENCE OF DisketteControlTableEntry
    ACCESS      not-accessible
    STATUS      mandatory
    DESCRIPTION
"1400.0070 This Group defines the Dell Diskette Control Table."
    ::= { biosSetUpControlGroup 70 }
disketteControlTableEntry           OBJECT-TYPE
    SYNTAX      DisketteControlTableEntry
    ACCESS      not-accessible
    STATUS      mandatory
    DESCRIPTION
"1400.0070.0001 This Group defines the Dell Diskette Control Table Entry."
    INDEX       { disketteControlchassisIndex, disketteControlIndex }
    ::= { disketteControlTable 1 }
disketteControlchassisIndex                 OBJECT-TYPE
    SYNTAX      DellObjectRange
    ACCESS      read-only
    STATUS      mandatory
    DESCRIPTION
"1400.0070.0001.0001 This attribute defines the index (one based) of
this Dell chassis."
    ::= { disketteControlTableEntry 1 }
disketteControlIndex                       OBJECT-TYPE
    SYNTAX      DellObjectRange
    ACCESS      read-only
    STATUS      mandatory
    DESCRIPTION
"1400.0070.0001.0002 This attribute defines the index of Dell diskette
controllers in this chassis."
    ::= { disketteControlTableEntry 2 }
disketteControlCapabilitiesUnique         OBJECT-TYPE
    SYNTAX      DellDisketteControlCapabilitiesUnique
    ACCESS      read-only
    STATUS      mandatory
    DESCRIPTION
"1400.0070.0001.0003 This attribute defines the capabilities of the Dell
diskette controller."
    ::= { disketteControlTableEntry 3 }
disketteControlSettingsUnique            OBJECT-TYPE
    SYNTAX      DellDisketteControlSettingsUnique
    ACCESS      read-write
    STATUS      mandatory
    DESCRIPTION
"1400.0070.0001.0004 This attribute defines the settings of the Dell
diskette controller."
    ::= { disketteControlTableEntry 4 }
disketteControlStatus            OBJECT-TYPE
    SYNTAX      DellStatus
    ACCESS      read-only
    STATUS      mandatory
    DESCRIPTION
"1400.0070.0001.0005 This attribute defines the status of the Dell
diskette controller."
    ::= { disketteControlTableEntry 5 }
disketteControlName                 OBJECT-TYPE
    SYNTAX      DellString
    ACCESS      read-only
    STATUS      mandatory
    DESCRIPTION
"1400.0070.0001.0006 This attribute defines the setup BIOS name of the
diskette controller."
    ::= { disketteControlTableEntry 6 }


-------------------------------------------------------------------------------
-- Network Interface Control Table
-------------------------------------------------------------------------------

DellNetworkInterfaceControlCapabilitiesUnique ::= INTEGER {
    unknown(1),                -- unknown Setup BIOS Network Interface capabilities
    enableCapable(2),          -- Setup BIOS is Capable of enabling the Network Interface
    enableWithoutPXECapable(4) -- Setup BIOS is Capable of enabling the NIF without PXE
}
DellNetworkInterfaceControlSettingsUnique ::= INTEGER {
    unknown(1),                -- Network Interface state is unknown
    enabled(2),                -- Network Interface is enabled
    enabledWithoutPXE(4)       -- Network Interface is enabled without PXE
}

NetworkInterfaceControlTableEntry               ::= SEQUENCE {
    networkInterfaceControlchassisIndex         DellObjectRange,
    networkInterfaceControlIndex                DellObjectRange,
    networkInterfaceControlCapabilitiesUnique   DellNetworkInterfaceControlCapabilitiesUnique,
    networkInterfaceControlSettingsUnique       DellNetworkInterfaceControlSettingsUnique,
    networkInterfaceControlStatus               DellStatus,
    networkInterfaceControlName                 DellString
}

networkInterfaceControlTable                OBJECT-TYPE
    SYNTAX      SEQUENCE OF NetworkInterfaceControlTableEntry
    ACCESS      not-accessible
    STATUS      mandatory
    DESCRIPTION
"1400.0080 This Group defines the Dell Network Interface Table."
    ::= { biosSetUpControlGroup 80 }
networkInterfaceControlTableEntry           OBJECT-TYPE
    SYNTAX      NetworkInterfaceControlTableEntry
    ACCESS      not-accessible
    STATUS      mandatory
    DESCRIPTION
"1400.0080.0001 This Group defines the Dell Network Interface Table Entry."
INDEX { networkInterfaceControlchassisIndex, networkInterfaceControlIndex }
    ::= { networkInterfaceControlTable 1 }
networkInterfaceControlchassisIndex                 OBJECT-TYPE
    SYNTAX      DellObjectRange
    ACCESS      read-only
    STATUS      mandatory
    DESCRIPTION
"1400.0080.0001.0001 This attribute defines the index (one based) of
this Dell chassis."
    ::= { networkInterfaceControlTableEntry 1 }
networkInterfaceControlIndex                       OBJECT-TYPE
    SYNTAX      DellObjectRange
    ACCESS      read-only
    STATUS      mandatory
    DESCRIPTION
"1400.0080.0001.0002 This attribute defines the index of Dell network
interfaces in this chassis."
    ::= { networkInterfaceControlTableEntry 2 }
networkInterfaceControlCapabilitiesUnique   OBJECT-TYPE
    SYNTAX      DellNetworkInterfaceControlCapabilitiesUnique
    ACCESS      read-only
    STATUS      mandatory
    DESCRIPTION
"1400.0080.0001.0003 This attribute defines the capabilities of the Dell
network interface."
    ::= { networkInterfaceControlTableEntry 3 }
networkInterfaceControlSettingsUnique       OBJECT-TYPE
    SYNTAX      DellNetworkInterfaceControlSettingsUnique
    ACCESS      read-write
    STATUS      mandatory
    DESCRIPTION
"1400.0080.0001.0004 This attribute defines the state of the Dell
network interface."
    ::= { networkInterfaceControlTableEntry 4 }
networkInterfaceControlStatus       OBJECT-TYPE
    SYNTAX      DellStatus
    ACCESS      read-only
    STATUS      mandatory
    DESCRIPTION
"1400.0080.0001.0005 This attribute defines the status of the Dell
network interface."
    ::= { networkInterfaceControlTableEntry 5 }
networkInterfaceControlName                 OBJECT-TYPE
    SYNTAX      DellString
    ACCESS      read-write
    STATUS      mandatory
    DESCRIPTION
"1400.0080.0001.0006 This attribute defines the setup BIOS name of the
network interface."
    ::= { networkInterfaceControlTableEntry 6 }


-------------------------------------------------------------------------------
--
-- Local Response Agent (LRA) Group
--
-------------------------------------------------------------------------------

-------------------------------------------------------------------------------
-- LRA Global Settings Table
-------------------------------------------------------------------------------

DellLocalResponseAgentCapabilitiesUnique ::= INTEGER {
    speakerControlCapable(1),       -- the LRA is Capable of a speaker beep
    consoleAlertCapable(2),         -- the LRA is Capable of a console alert
    broadcastMessageCapable(4),     -- the LRA is Capable of a broadcast message
    osShutDownCapable(8),           -- the LRA is Capable of an operating system shutdown
    rebootCapable(16),              -- the LRA is Capable of a system reboot
    powerCycleCapable(32),          -- the LRA is Capable of a system power cycle
    powerOFFCapable(64),            -- the LRA is Capable of a system power off
    executeApplicationCapable(256), -- the LRA is Capable of executing a user mode application
    lraFullyCapable(383)            -- the LRA is fully Capable
}
DellLRAThermalShutdownCapabilitiesUnique ::= INTEGER {
    -- If set to 0 (zero) the object has no capabilities
    unknownCapabilities(1),             -- The objects capabilities are unknown
    -- The objects capabilities allow it to be set to:
    enableCapable(2),                   -- be disabled (offline) or be enabled (online)
    warningCapable(4),                  -- be capable of the chassis determined action(s) on warning.
    enableOnWarningCapable(6),          -- enable activation of the the chassis determined action(s) on warning.
    failureCapable(8),                  -- be capable of the the chassis determined action(s) on failure.
    enableOnFailureCapable(10),         -- enable activation of the the chassis determined action(s) on failure.
    enableOnWarningOrFailureCapable(14) -- enable activation of the the chassis determined action(s) on failure.
}
DellLRAThermalShutdownStateSettingsUnique ::= INTEGER {
    -- If set to 0 (zero) the object has no settings capabilities, and it's state is disabled
    unknown(1),                        -- The objects state is unknown
    activatedOnWarning(6),             -- The objects state is activated on warning
    activatedOnFailure(10)             -- The objects state is activated on failure
}

LRAGlobalSettingsTableEntry                     ::= SEQUENCE {
    lRAGlobalchassisIndex                       DellObjectRange,
    lRAGlobalState                              DellStateSettings,
    lRAGlobalSettingsDisableTimeoutValue        DellUnsigned32BitRange,
    lRAGlobalSettingsCapabilitiesUnique         DellLocalResponseAgentCapabilitiesUnique,
    lRAGlobalThermalShutdownCapabilitiesUnique  DellLRAThermalShutdownCapabilitiesUnique,
    lRAGlobalThermalShutdownStateSettingsUnique DellLRAThermalShutdownStateSettingsUnique
}

lRAGlobalSettingsTable                      OBJECT-TYPE
    SYNTAX      SEQUENCE OF LRAGlobalSettingsTableEntry
    ACCESS      not-accessible
    STATUS      mandatory
    DESCRIPTION
"1500.0010 This Group defines the Dell Global Settings
Local Response Agent Table."
    ::= { lraGroup 10 }
lRAGlobalSettingsTableEntry                 OBJECT-TYPE
    SYNTAX      LRAGlobalSettingsTableEntry
    ACCESS      not-accessible
    STATUS      mandatory
    DESCRIPTION
"1500.0010.0001 This Group defines the Dell Global Settings
Local Response Agent Table Entry."
    INDEX       { lRAGlobalchassisIndex }
    ::= { lRAGlobalSettingsTable 1 }
lRAGlobalchassisIndex               OBJECT-TYPE
    SYNTAX      DellObjectRange
    ACCESS      read-only
    STATUS      mandatory
    DESCRIPTION
"1500.0010.0001.0001 This attribute defines the index (one based) of
this Dell chassis."
    ::= { lRAGlobalSettingsTableEntry 1 }
lRAGlobalState                             OBJECT-TYPE
    SYNTAX     DellStateSettings
    ACCESS      read-only
    STATUS      mandatory
    DESCRIPTION
"1500.0010.0001.0002 This attribute defines the state of the Dell
Global Settings Local Response Agent."
    ::= { lRAGlobalSettingsTableEntry 2 }
lRAGlobalSettingsDisableTimeoutValue        OBJECT-TYPE
    SYNTAX      DellUnsigned32BitRange
    ACCESS      read-only
    STATUS      mandatory
    DESCRIPTION
"1500.0010.0001.0003 This attribute defines the timeout duration in seconds
the that Dell Global Settings Local Response Agent will be disabled after a
machine shutdown and reboot."
    ::= { lRAGlobalSettingsTableEntry 3 }
lRAGlobalSettingsCapabilitiesUnique         OBJECT-TYPE
    SYNTAX      DellLocalResponseAgentCapabilitiesUnique
    ACCESS      read-only
    STATUS      mandatory
    DESCRIPTION
"1500.0010.0001.0004 This attribute defines the set of Global
Capabilities that all Local Response Agents may or may not
allow to be set or reset."
    ::= { lRAGlobalSettingsTableEntry 4 }
lRAGlobalThermalShutdownCapabilitiesUnique         OBJECT-TYPE
    SYNTAX      DellLRAThermalShutdownCapabilitiesUnique
    ACCESS      read-only
    STATUS      mandatory
    DESCRIPTION
"1500.0010.0001.0005 This attribute defines the set of Thermal Shutdown
Capabilities that the Local Response Agent supports."
    ::= { lRAGlobalSettingsTableEntry 5 }
lRAGlobalThermalShutdownStateSettingsUnique         OBJECT-TYPE
    SYNTAX      DellLRAThermalShutdownStateSettingsUnique
    ACCESS      read-write
    STATUS      mandatory
    DESCRIPTION
"1500.0010.0001.0006 This attribute defines the Thermal Shutdown state
that the Local Response Agent supports."
    ::= { lRAGlobalSettingsTableEntry 6 }


-------------------------------------------------------------------------------
-- LRA Action Table
-------------------------------------------------------------------------------

DellLocalResponseAgentSettingsUnique    ::= INTEGER {
    speakerControl(1),                  -- issue a speaker beep
    consoleAlert(2),                    -- issue a console alert
    broadcastMessage(4),                -- issue a broadcast message
    osShutDown(8),                      -- issue an operating system shutdown
    reboot(16),                         -- issue a system reboot
    powerCycle(32),                     -- issue a system power cycle
    powerOFF(64),                       -- issue a system power off
    executeApplication(256),            -- start a user mode application execution
    allLRASettingsUnique(511)           -- allow all LRA settings combinations
}

LRAActionTableTableEntry                ::= SEQUENCE {
    lRAActionTablechassisIndex          DellObjectRange,
    lRAActionTableActionNumberIndex     DellUnsigned16BitRange,
    lRAActionTableUserApplicationName   DisplayString (SIZE (0..256)),
    lRAActionTableSettingsUnique        DellLocalResponseAgentSettingsUnique
}

lRAActionTableTable                     OBJECT-TYPE
    SYNTAX      SEQUENCE OF LRAActionTableTableEntry
    ACCESS      not-accessible
    STATUS      mandatory
    DESCRIPTION
"1500.0020 This Group defines the Dell Local Response Agent Action Table."
    ::= { lraGroup 20 }
lRAActionTableTableEntry                OBJECT-TYPE
    SYNTAX      LRAActionTableTableEntry
    ACCESS      not-accessible
    STATUS      mandatory
    DESCRIPTION
"1500.0020.0001 This Group defines the Dell Local Response Agent Table
Entry."
    INDEX       { lRAActionTablechassisIndex, lRAActionTableActionNumberIndex }
    ::= { lRAActionTableTable 1 }
lRAActionTablechassisIndex              OBJECT-TYPE
    SYNTAX      DellObjectRange
    ACCESS      read-only
    STATUS      mandatory
    DESCRIPTION
"1500.0020.0001.0001 This attribute defines the index (one based) of
this Dell chassis."
    ::= { lRAActionTableTableEntry 1 }
lRAActionTableActionNumberIndex         OBJECT-TYPE
    SYNTAX      DellUnsigned16BitRange
    ACCESS      read-only
    STATUS      mandatory
    DESCRIPTION
"1500.0020.0001.0002 This attribute defines the action number index
of the Dell Local Response Agent. These currently supported values are:
    160 temperature failure action definition
    168 cooling device failure action definition
    172 voltage failure action definition
    200 temperature warning action definition
    202 voltage warning action definition
    204 cooling device warning action definition
    206 amperage failure action definition
    208 amperage warning action definition
    210 a power or cooling unit redundancy lost action definition
    212 a power or cooling unit redundancy degraded action definition
    214 power supply failed action definition
    220 chassis intrusion action definition
    228 memory device warning action definition
    474 memory device failure action definition"
    ::= { lRAActionTableTableEntry 2 }
lRAActionTableUserApplicationName       OBJECT-TYPE
    SYNTAX      DisplayString (SIZE (0..256))
    ACCESS      read-write
    STATUS      mandatory
    DESCRIPTION
"1500.0020.0001.0003 This is the name of the user application executable
path and file name to execute by the Dell Local Response Agent if the value
execute application was set."
    ::= { lRAActionTableTableEntry 3 }
lRAActionTableSettingsUnique            OBJECT-TYPE
    SYNTAX      DellLocalResponseAgentSettingsUnique
    ACCESS      read-write
    STATUS      mandatory
    DESCRIPTION
"1500.0020.0001.0004 This attribute defines the capabilities of the Dell
Local Response Agent."
    ::= { lRAActionTableTableEntry 4 }


-------------------------------------------------------------------------------
--
-- Cost Of Ownership (COO) Group
--
-------------------------------------------------------------------------------

DellCooOwnershipCodes   ::= INTEGER {
    other(1),           -- the Ownership Code is not one of following:
    unknown(2),         -- the Ownership Code is unknown
    owned(3),           -- the Ownership Code is owned
    leased(4),          -- the Ownership Code is leased
    rented(5),          -- the Ownership Code is rented
    offOfLease(6),      -- the Ownership Code is off of lease
    transfer(7)         -- the Ownership Code is transfer
}
DellCooHourDayDurationType ::= INTEGER {
    unknown(1),         -- Duration Time Type is unknown
    hours(2),           -- Duration Time Type is in hours
    days(3)             -- Duration Time Type is in days
}
DellCooDayMonthDurationType ::= INTEGER {
    unknown(1),         -- Duration Time Type is unknown
    days(3),            -- Duration Time Type is in days
    months(4)           -- Duration Time Type is in months
}
DellCooMonthYearDurationType ::= INTEGER {
    unknown(1),         -- Duration Time Type is unknown
    months(4),          -- Duration Time Type is in months
    years(5)            -- Duration Time Type is in years
}

-------------------------------------------------------------------------------
-- Cost Of Ownership (COO) Table
-------------------------------------------------------------------------------

CooTableEntry                                   ::= SEQUENCE {
    coochassisIndex                             DellObjectRange,
    cooState                                    DellStateSettings,
    cooAquisitionPurchaseCost                   DellUnsigned32BitRange,
    cooAquisitionWayBillNumber                  DellUnsigned32BitRange,
    cooAquisitionInstallDateName                DellDateName,
    cooAquisitionPurchaseOrder                  DellUnsigned32BitRange,
    cooAquisitionPurchaseDateName               DellDateName,
    cooAquisitionSigningAuthorityName           DellCostofOwnershipString,
    cooOriginalMachineConfigurationExpensed     DellBoolean,
    cooOriginalMachineConfigurationVendorName   DellCostofOwnershipString,
    cooCostCenterInformationVendorName          DellCostofOwnershipString,
    cooUserInformationUserName                  DellCostofOwnershipString,
    cooExtendedWarrantyStartDateName            DellDateName,
    cooExtendedWarrantyEndDateName              DellDateName,
    cooExtendedWarrantyCost                     DellUnsigned32BitRange,
    cooExtendedWarrantyProviderName             DellCostofOwnershipString,
    cooOwnershipCode                            DellCooOwnershipCodes,
    cooCorporateOwnerName                       DellCostofOwnershipString,
    cooHazardousWasteCodeName                   DellCostofOwnershipString,
    cooDeploymentDateLength                     DellUnsigned32BitRange,
    cooDeploymentDurationType                   DellCooHourDayDurationType,
    cooTrainingName                             DellCostofOwnershipString,
    cooOutsourcingProblemDescriptionName        DellCostofOwnershipString,
    cooOutsourcingServiceFeeName                DellCostofOwnershipString,
    cooOutsourcingSigningAuthorityName          DellCostofOwnershipString,
    cooOutsourcingProviderFeeName               DellCostofOwnershipString,
    cooOutsourcingProviderServiceLevelName      DellCostofOwnershipString,
    cooInsuranceCompanyName                     DellCostofOwnershipString,
    cooBoxAssetTagName                          DellCostofOwnershipString,
    cooBoxSystemName                            DellCostofOwnershipString,
    cooBoxCPUSerialNumberName                   DellCostofOwnershipString,
    cooOperatingSystemUpgradeTypeName           DellCostofOwnershipString,
    cooOperatingSystemUpgradePatchLevelName     DellCostofOwnershipString,
    cooOperatingSystemUpgradeDate               DellCostofOwnershipString,
    cooDepreciationDuration                     DellUnsigned32BitRange,
    cooDepreciationDurationType                 DellCooMonthYearDurationType,
    cooDepreciationPercentage                   DellUnsigned32BitRange,
    cooDepreciationMethodName                   DellCostofOwnershipString,
    cooRegistrationIsRegistered                 DellBoolean
}

cooTable                      OBJECT-TYPE
    SYNTAX      SEQUENCE OF CooTableEntry
    ACCESS      not-accessible
    STATUS      mandatory
    DESCRIPTION
"1600.0010 This Group defines the Dell Cost of Ownership:
Table."
    ::= { cooGroup 10 }
cooTableEntry                 OBJECT-TYPE
    SYNTAX      CooTableEntry
    ACCESS      not-accessible
    STATUS      mandatory
    DESCRIPTION
"1600.0010.0001 This Group defines the Dell Cost of Ownership:
Table Entry."
    INDEX       { coochassisIndex }
    ::= { cooTable 1 }
coochassisIndex                 OBJECT-TYPE
    SYNTAX      DellObjectRange
    ACCESS      read-only
    STATUS      mandatory
    DESCRIPTION
"1600.0010.0001.0001 This attribute defines the index (one based) of
this Dell chassis."
    ::= { cooTableEntry 1 }
cooState                      OBJECT-TYPE
    SYNTAX      DellStateSettings
    ACCESS      read-only
    STATUS      mandatory
    DESCRIPTION
"1600.0010.0001.0002 This attribute defines the Dell Cost of Ownership:
Aquisition state of the Dell System."
    ::= { cooTableEntry 2 }
cooAquisitionPurchaseCost               OBJECT-TYPE
    SYNTAX      DellUnsigned32BitRange
    ACCESS      read-write
    STATUS      mandatory
    DESCRIPTION
"1600.0010.0001.0003 This attribute defines the purchase cost of the
Dell System."
    ::= { cooTableEntry 3 }
cooAquisitionWayBillNumber              OBJECT-TYPE
    SYNTAX      DellUnsigned32BitRange
    ACCESS      read-write
    STATUS      mandatory
    DESCRIPTION
"1600.0010.0001.0004 This attribute defines the waybill number of the
Dell System."
    ::= { cooTableEntry 4 }
cooAquisitionInstallDateName            OBJECT-TYPE
    SYNTAX      DellDateName
    ACCESS      read-write
    STATUS      mandatory
    DESCRIPTION
"1600.0010.0001.0005 This attribute defines the install time of the
Dell System.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { cooTableEntry 5 }
cooAquisitionPurchaseOrder              OBJECT-TYPE
    SYNTAX      DellUnsigned32BitRange
    ACCESS      read-write
    STATUS      mandatory
    DESCRIPTION
"1600.0010.0001.0006 This attribute defines the purchase order number
of the Dell System."
    ::= { cooTableEntry 6 }
cooAquisitionPurchaseDateName          OBJECT-TYPE
    SYNTAX      DellDateName
    ACCESS      read-write
    STATUS      mandatory
    DESCRIPTION
"1600.0010.0001.0007 This attribute defines the purchase time of the
Dell System.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { cooTableEntry 7 }
cooAquisitionSigningAuthorityName       OBJECT-TYPE
    SYNTAX      DellCostofOwnershipString
    ACCESS      read-write
    STATUS      mandatory
    DESCRIPTION
"1600.0010.0001.0008 This attribute defines the name of the signing
authority for the Dell System."
    ::= { cooTableEntry 8 }
cooOriginalMachineConfigurationExpensed         OBJECT-TYPE
    SYNTAX      DellBoolean
    ACCESS      read-write
    STATUS      mandatory
    DESCRIPTION
"1600.0010.0001.0009 This attribute defines the purchase of the
Dell System was expensed or not."
    ::= { cooTableEntry 9 }
cooOriginalMachineConfigurationVendorName       OBJECT-TYPE
    SYNTAX      DellCostofOwnershipString
    ACCESS      read-only
    STATUS      mandatory
    DESCRIPTION
"1600.0010.0001.0010 This attribute defines the vendor name of the
Dell System."
    ::= { cooTableEntry 10 }
cooCostCenterInformationVendorName      OBJECT-TYPE
    SYNTAX      DellCostofOwnershipString
    ACCESS      read-write
    STATUS      mandatory
    DESCRIPTION
"1600.0010.0001.0011 This attribute defines the cost center name of the
Dell System."
    ::= { cooTableEntry 11 }
cooUserInformationUserName          OBJECT-TYPE
    SYNTAX      DellCostofOwnershipString
    ACCESS      read-write
    STATUS      mandatory
    DESCRIPTION
"1600.0010.0001.0012 This attribute defines the user name of the
Dell System."
    ::= { cooTableEntry 12 }
cooExtendedWarrantyStartDateName    OBJECT-TYPE
    SYNTAX      DellDateName
    ACCESS      read-write
    STATUS      mandatory
    DESCRIPTION
"1600.0010.0001.0013 This attribute defines Extended Warranty
start date for the Dell System.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { cooTableEntry 13 }
cooExtendedWarrantyEndDateName     OBJECT-TYPE
    SYNTAX      DellDateName
    ACCESS      read-write
    STATUS      mandatory
    DESCRIPTION
"1600.0010.0001.0014 This attribute defines Extended Warranty
end date for the Dell System.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { cooTableEntry 14 }
cooExtendedWarrantyCost                 OBJECT-TYPE
    SYNTAX      DellUnsigned32BitRange
    ACCESS      read-write
    STATUS      mandatory
    DESCRIPTION
"1600.0010.0001.0015 This attribute defines Extended Warranty
cost for the Dell System."
    ::= { cooTableEntry 15 }
cooExtendedWarrantyProviderName         OBJECT-TYPE
    SYNTAX      DellCostofOwnershipString
    ACCESS      read-write
    STATUS      mandatory
    DESCRIPTION
"1600.0010.0001.0016 This attribute defines the Extended Warranty service
provider name for the Dell System."
    ::= { cooTableEntry 16 }
cooOwnershipCode                    OBJECT-TYPE
    SYNTAX      DellCooOwnershipCodes
    ACCESS      read-write
    STATUS      mandatory
    DESCRIPTION
"1600.0010.0001.0017 This attribute defines ownership code for the
Dell System."
    ::= { cooTableEntry 17 }
cooCorporateOwnerName               OBJECT-TYPE
    SYNTAX      DellCostofOwnershipString
    ACCESS      read-write
    STATUS      mandatory
    DESCRIPTION
"1600.0010.0001.0018 This attribute defines the name of the
corporate owner for the Dell System."
    ::= { cooTableEntry 18 }
cooHazardousWasteCodeName           OBJECT-TYPE
    SYNTAX      DellCostofOwnershipString
    ACCESS      read-write
    STATUS      mandatory
    DESCRIPTION
"1600.0010.0001.0019 This attribute defines the name Hazardous Waste code
for the Dell System."
    ::= { cooTableEntry 19 }
cooDeploymentDateLength          OBJECT-TYPE
    SYNTAX      DellUnsigned32BitRange
    ACCESS      read-write
    STATUS      mandatory
    DESCRIPTION
"1600.0010.0001.0020 This attribute defines the Deployment Time for the
Dell System."
    ::= { cooTableEntry 20 }
cooDeploymentDurationType          OBJECT-TYPE
    SYNTAX      DellCooHourDayDurationType
    ACCESS      read-write
    STATUS      mandatory
    DESCRIPTION
"1600.0010.0001.0021 This attribute defines the Deployment Time units
for the Dell System."
    ::= { cooTableEntry 21 }
cooTrainingName             OBJECT-TYPE
    SYNTAX      DellCostofOwnershipString
    ACCESS      read-write
    STATUS      mandatory
    DESCRIPTION
"1600.0010.0001.0022 This attribute defines the training the user has
for the Dell System."
    ::= { cooTableEntry 22 }
cooOutsourcingProblemDescriptionName        OBJECT-TYPE
    SYNTAX      DellCostofOwnershipString
    ACCESS      read-write
    STATUS      mandatory
    DESCRIPTION
"1600.0010.0001.0023 This attribute defines the problem description name
of the Outsourcing service provider."
    ::= { cooTableEntry 23 }
cooOutsourcingServiceFeeName                OBJECT-TYPE
    SYNTAX      DellCostofOwnershipString
    ACCESS      read-write
    STATUS      mandatory
    DESCRIPTION
"1600.0010.0001.0024 This attribute defines the Outsourcing vendors'
charge for service."
    ::= { cooTableEntry 24 }
cooOutsourcingSigningAuthorityName          OBJECT-TYPE
    SYNTAX      DellCostofOwnershipString
    ACCESS      read-write
    STATUS      mandatory
    DESCRIPTION
"1600.0010.0001.0025 This attribute defines the name of the person who has
signing authority for service."
    ::= { cooTableEntry 25 }
cooOutsourcingProviderFeeName               OBJECT-TYPE
    SYNTAX      DellCostofOwnershipString
    ACCESS      read-write
    STATUS      mandatory
    DESCRIPTION
"1600.0010.0001.0026 This attribute defines any additional Outsourcing
charge for service."
    ::= { cooTableEntry 26 }
cooOutsourcingProviderServiceLevelName      OBJECT-TYPE
    SYNTAX      DellCostofOwnershipString
    ACCESS      read-write
    STATUS      mandatory
    DESCRIPTION
"1600.0010.0001.0027 This attribute defines service level agreement
for service."
    ::= { cooTableEntry 27 }
cooInsuranceCompanyName         OBJECT-TYPE
    SYNTAX      DellCostofOwnershipString
    ACCESS      read-write
    STATUS      mandatory
    DESCRIPTION
"1600.0010.0001.0028 This attribute defines the name of the company
insuring the Dell System."
    ::= { cooTableEntry 28 }
cooBoxAssetTagName              OBJECT-TYPE
    SYNTAX      DellCostofOwnershipString
    ACCESS      read-write
    STATUS      mandatory
    DESCRIPTION
"1600.0010.0001.0029 This attribute defines the name the Dell System
asset tag."
    ::= { cooTableEntry 29 }
cooBoxSystemName                OBJECT-TYPE
    SYNTAX      DellCostofOwnershipString
    ACCESS      read-write
    STATUS      mandatory
    DESCRIPTION
"1600.0010.0001.0030 This attribute defines the name of the Dell System."
    ::= { cooTableEntry 30 }
cooBoxCPUSerialNumberName       OBJECT-TYPE
    SYNTAX      DellCostofOwnershipString
    ACCESS      read-write
    STATUS      mandatory
    DESCRIPTION
"1600.0010.0001.0031 This attribute defines the name of the CPU serial
number in the Dell System."
    ::= { cooTableEntry 31 }
cooOperatingSystemUpgradeTypeName           OBJECT-TYPE
    SYNTAX      DellCostofOwnershipString
    ACCESS      read-write
    STATUS      mandatory
    DESCRIPTION
"1600.0010.0001.0032 This attribute defines the name the operating system
on the Dell System."
    ::= { cooTableEntry 32 }
cooOperatingSystemUpgradePatchLevelName     OBJECT-TYPE
    SYNTAX      DellCostofOwnershipString
    ACCESS      read-write
    STATUS      mandatory
    DESCRIPTION
"1600.0010.0001.0033 This attribute defines the name of the operating
system patch level of the Dell System."
    ::= { cooTableEntry 33 }
cooOperatingSystemUpgradeDate           OBJECT-TYPE
    SYNTAX      DellCostofOwnershipString
    ACCESS      read-write
    STATUS      mandatory
    DESCRIPTION
"1600.0010.0001.0034 This attribute defines the upgrade file date."
    ::= { cooTableEntry 34 }
cooDepreciationDuration         OBJECT-TYPE
    SYNTAX      DellUnsigned32BitRange
    ACCESS      read-write
    STATUS      mandatory
    DESCRIPTION
"1600.0010.0001.0035 This attribute defines the Depreciation duration
for the Dell System."
    ::= { cooTableEntry 35 }
cooDepreciationDurationType     OBJECT-TYPE
    SYNTAX      DellCooMonthYearDurationType
    ACCESS      read-write
    STATUS      mandatory
    DESCRIPTION
"1600.0010.0001.0036 This attribute defines the unit of time for
Depreciation for the Dell System."
    ::= { cooTableEntry 36 }
cooDepreciationPercentage       OBJECT-TYPE
    SYNTAX      DellUnsigned32BitRange
    ACCESS      read-write
    STATUS      mandatory
    DESCRIPTION
"1600.0010.0001.0037 This attribute defines the percentage of
Depreciation for the Dell System."
    ::= { cooTableEntry 37 }
cooDepreciationMethodName       OBJECT-TYPE
    SYNTAX      DellCostofOwnershipString
    ACCESS      read-write
    STATUS      mandatory
    DESCRIPTION
"1600.0010.0001.0038 This attribute defines the method name of
Depreciation for the Dell System."
    ::= { cooTableEntry 38 }
cooRegistrationIsRegistered         OBJECT-TYPE
    SYNTAX      DellBoolean
    ACCESS      read-write
    STATUS      mandatory
    DESCRIPTION
"1600.0010.0001.0039 This attribute defines if the Dell System is
registered or not."
    ::= { cooTableEntry 39 }


-------------------------------------------------------------------------------
-- Cost Of Ownership (COO) Service Contract Table
-------------------------------------------------------------------------------

CooServiceContractTableEntry        ::= SEQUENCE {
    cooServiceContractchassisIndex  DellObjectRange,
    cooServiceContractIndex         DellObjectRange,
    cooServiceContractState         DellStateSettings,
    cooServiceContractWasRenewed    DellBoolean,
    cooServiceContractTypeName      DellCostofOwnershipString,
    cooServiceContractVendorName    DellCostofOwnershipString
}

cooServiceContractTable             OBJECT-TYPE
    SYNTAX      SEQUENCE OF CooServiceContractTableEntry
    ACCESS      not-accessible
    STATUS      mandatory
    DESCRIPTION
"1600.0020 This Group defines the Dell Cost of Ownership:
Service Contract Table."
    ::= { cooGroup 20 }
cooServiceContractTableEntry        OBJECT-TYPE
    SYNTAX      CooServiceContractTableEntry
    ACCESS      not-accessible
    STATUS      mandatory
    DESCRIPTION
"1600.0020.0001 This Group defines the Dell Cost of Ownership:
Service Contract Table Entry."
    INDEX { cooServiceContractchassisIndex, cooServiceContractIndex }
    ::= { cooServiceContractTable 1 }
cooServiceContractchassisIndex  OBJECT-TYPE
    SYNTAX      DellObjectRange
    ACCESS      read-only
    STATUS      mandatory
    DESCRIPTION
"1600.0020.0001.0001 This attribute defines the index (one based) of
this Dell chassis."
    ::= { cooServiceContractTableEntry 1 }
cooServiceContractIndex             OBJECT-TYPE
    SYNTAX      DellObjectRange
    ACCESS      read-only
    STATUS      mandatory
    DESCRIPTION
"1600.0020.0001.0002 This attribute defines the index of the
Dell Systems Cost of Ownership: Service Contract."
    ::= { cooServiceContractTableEntry 2 }
cooServiceContractState            OBJECT-TYPE
    SYNTAX      DellStateSettings
    ACCESS      read-only
    STATUS      mandatory
    DESCRIPTION
"1600.0020.0001.0003 This attribute defines the Dell Systems
Cost of Ownership: Service Contract state of the Dell System."
    ::= { cooServiceContractTableEntry 3 }
cooServiceContractWasRenewed        OBJECT-TYPE
    SYNTAX      DellBoolean
    ACCESS      read-write
    STATUS      mandatory
    DESCRIPTION
"1600.0020.0001.0004 This attribute defines if the Dell System Service
Contract was renewed not."
    ::= { cooServiceContractTableEntry 4 }
cooServiceContractTypeName          OBJECT-TYPE
    SYNTAX      DellCostofOwnershipString
    ACCESS      read-write
    STATUS      mandatory
    DESCRIPTION
"1600.0020.0001.0005 This attribute defines the name of the Service
Contract type for the Dell System."
    ::= { cooServiceContractTableEntry 5 }
cooServiceContractVendorName        OBJECT-TYPE
    SYNTAX      DellCostofOwnershipString
    ACCESS      read-write
    STATUS      mandatory
    DESCRIPTION
"1600.0020.0001.0006 This attribute defines the name of the Service
Contract provider for the Dell System."
    ::= { cooServiceContractTableEntry 6 }


-------------------------------------------------------------------------------
-- Cost Of Ownership (COO) Cost Event Log Table
-------------------------------------------------------------------------------

CooCostEventLogTableEntry           ::= SEQUENCE {
    cooCostEventLogchassisIndex     DellObjectRange,
    cooCostEventLogIndex            DellObjectRange,
    cooCostEventLogState            DellStateSettings,
    cooCostEventLogDuration         DellUnsigned32BitRange,
    cooCostEventLogDurationType     DellCooHourDayDurationType,
    cooCostEventLogDescriptionName  DellCostofOwnershipString
}

cooCostEventLogTable            OBJECT-TYPE
    SYNTAX      SEQUENCE OF CooCostEventLogTableEntry
    ACCESS      not-accessible
    STATUS      mandatory
    DESCRIPTION
"1600.0030 This Group defines the Dell Cost of Ownership:
Cost Event Log Table."
    ::= { cooGroup 30 }
cooCostEventLogTableEntry       OBJECT-TYPE
    SYNTAX      CooCostEventLogTableEntry
    ACCESS      not-accessible
    STATUS      mandatory
    DESCRIPTION
"1600.0030.0001 This Group defines the Dell Cost of Ownership:
Cost Event Log Table Entry."
    INDEX       { cooCostEventLogchassisIndex, cooCostEventLogIndex }
    ::= { cooCostEventLogTable 1 }
cooCostEventLogchassisIndex     OBJECT-TYPE
    SYNTAX      DellObjectRange
    ACCESS      read-only
    STATUS      mandatory
    DESCRIPTION
"1600.0030.0001.0001 This attribute defines the index (one based) of
this Dell chassis."
    ::= { cooCostEventLogTableEntry 1 }
cooCostEventLogIndex                OBJECT-TYPE
    SYNTAX      DellObjectRange
    ACCESS      read-only
    STATUS      mandatory
    DESCRIPTION
"1600.0030.0001.0002 This attribute defines the index of the
Dell Systems Cost of Ownership: Cost Event Log."
    ::= { cooCostEventLogTableEntry 2 }
cooCostEventLogState           OBJECT-TYPE
    SYNTAX      DellStateSettings
    ACCESS      read-only
    STATUS      mandatory
    DESCRIPTION
"1600.0030.0001.0003 This attribute defines the Dell Systems
Cost of Ownership: Cost Event Log state of the Dell System."
    ::= { cooCostEventLogTableEntry 3 }
cooCostEventLogDuration         OBJECT-TYPE
    SYNTAX      DellUnsigned32BitRange
    ACCESS      read-write
    STATUS      mandatory
    DESCRIPTION
"1600.0030.0001.0004 This attribute defines duration of the event."
    ::= { cooCostEventLogTableEntry 4 }
cooCostEventLogDurationType     OBJECT-TYPE
    SYNTAX      DellCooHourDayDurationType
    ACCESS      read-write
    STATUS      mandatory
    DESCRIPTION
"1600.0030.0001.0005 This attribute defines the of the Cost Event Log
duration type for the Dell System."
    ::= { cooCostEventLogTableEntry 5 }
cooCostEventLogDescriptionName      OBJECT-TYPE
    SYNTAX      DellCostofOwnershipString
    ACCESS      read-write
    STATUS      mandatory
    DESCRIPTION
"1600.0030.0001.0006 This attribute defines the name of the event
description logged for the event."
    ::= { cooCostEventLogTableEntry 6 }


-------------------------------------------------------------------------------
-- Cost Of Ownership (COO) Warranty Table
-------------------------------------------------------------------------------

CooWarrantyTableEntry            ::= SEQUENCE {
    cooWarrantychassisIndex      DellObjectRange,
    cooWarrantyIndex             DellObjectRange,
    cooWarrantyState             DellStateSettings,
    cooWarrantyDuration          DellUnsigned32BitRange,
    cooWarrantyDurationType      DellCooDayMonthDurationType,
    cooWarrantyEndDateName       DellDateName,
    cooWarrantyCost              DellUnsigned32BitRange
}

cooWarrantyTable            OBJECT-TYPE
    SYNTAX      SEQUENCE OF CooWarrantyTableEntry
    ACCESS      not-accessible
    STATUS      mandatory
    DESCRIPTION
"1600.0040 This Group defines the Dell Cost of Ownership:
Warranty Table."
    ::= { cooGroup 40 }
cooWarrantyTableEntry       OBJECT-TYPE
    SYNTAX      CooWarrantyTableEntry
    ACCESS      not-accessible
    STATUS      mandatory
    DESCRIPTION
"1600.0040.0001 This Group defines the Dell Cost of Ownership:
Warranty Table Entry."
    INDEX       { cooWarrantychassisIndex, cooWarrantyIndex }
    ::= { cooWarrantyTable 1 }
cooWarrantychassisIndex     OBJECT-TYPE
    SYNTAX      DellObjectRange
    ACCESS      read-only
    STATUS      mandatory
    DESCRIPTION
"1600.0040.0001.0001 This attribute defines the index (one based) of
this Dell chassis."
    ::= { cooWarrantyTableEntry 1 }
cooWarrantyIndex                OBJECT-TYPE
    SYNTAX      DellObjectRange
    ACCESS      read-only
    STATUS      mandatory
    DESCRIPTION
"1600.0040.0001.0002 This attribute defines the index of the Dell Systems
Cost of Ownership: Warranty."
    ::= { cooWarrantyTableEntry 2 }
cooWarrantyState           OBJECT-TYPE
    SYNTAX      DellStateSettings
    ACCESS      read-only
    STATUS      mandatory
    DESCRIPTION
"1600.0040.0001.0003 This attribute defines the Dell Systems
Cost of Ownership: Warranty state of the Dell System."
    ::= { cooWarrantyTableEntry 3 }
cooWarrantyDuration         OBJECT-TYPE
    SYNTAX      DellUnsigned32BitRange
    ACCESS      read-write
    STATUS      mandatory
    DESCRIPTION
"1600.0040.0001.0004 This attribute defines duration of the warranty."
    ::= { cooWarrantyTableEntry 4 }
cooWarrantyDurationType     OBJECT-TYPE
    SYNTAX      DellCooDayMonthDurationType
    ACCESS      read-write
    STATUS      mandatory
    DESCRIPTION
"1600.0040.0001.0005 This attribute defines the Warranty duration type
for the Dell System."
    ::= { cooWarrantyTableEntry 5 }
cooWarrantyEndDateName     OBJECT-TYPE
    SYNTAX      DellDateName
    ACCESS      read-write
    STATUS      mandatory
    DESCRIPTION
"1600.0040.0001.0006 This attribute defines the Warranty end date for
the Dell System.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { cooWarrantyTableEntry 6 }
cooWarrantyCost             OBJECT-TYPE
    SYNTAX      DellUnsigned32BitRange
    ACCESS      read-write
    STATUS      mandatory
    DESCRIPTION
"1600.0040.0001.0007 This attribute defines the Warranty cost for the
Dell System."
    ::= { cooWarrantyTableEntry 7 }


-------------------------------------------------------------------------------
-- Cost Of Ownership (COO) Lease Information Table
-------------------------------------------------------------------------------

CooLeaseInformationTableEntry               ::= SEQUENCE {
    cooLeaseInformationchassisIndex         DellObjectRange,
    cooLeaseInformationIndex                DellObjectRange,
    cooLeaseInformationState                DellStateSettings,
    cooLeaseInformationMultipleSchedules    DellBoolean,
    cooLeaseInformationBuyOutAmount         DellUnsigned32BitRange,
    cooLeaseInformationLeaseRateFactor      DellUnsigned32BitRange,
    cooLeaseInformationEndDateName          DellDateName,
    cooLeaseInformationFairMarketValue      DellUnsigned32BitRange,
    cooLeaseInformationLessorName           DellCostofOwnershipString
}

cooLeaseInformationTable                    OBJECT-TYPE
    SYNTAX      SEQUENCE OF CooLeaseInformationTableEntry
    ACCESS      not-accessible
    STATUS      mandatory
    DESCRIPTION
"1600.0050 This Group defines the Dell Cost of Ownership:
Lease Information Table."
    ::= { cooGroup 50 }
cooLeaseInformationTableEntry               OBJECT-TYPE
    SYNTAX      CooLeaseInformationTableEntry
    ACCESS      not-accessible
    STATUS      mandatory
    DESCRIPTION
"1600.0050.0001 This Group defines the Dell Cost of Ownership:
Lease Information Table Entry."
    INDEX       { cooLeaseInformationchassisIndex, cooLeaseInformationIndex }
    ::= { cooLeaseInformationTable 1 }
cooLeaseInformationchassisIndex     OBJECT-TYPE
    SYNTAX      DellObjectRange
    ACCESS      read-only
    STATUS      mandatory
    DESCRIPTION
"1600.0050.0001.0001 This attribute defines the index (one based) of
this Dell chassis."
    ::= { cooLeaseInformationTableEntry 1 }
cooLeaseInformationIndex                    OBJECT-TYPE
    SYNTAX      DellObjectRange
    ACCESS      read-only
    STATUS      mandatory
    DESCRIPTION
"1600.0050.0001.0002 This attribute defines the index of the Dell Systems
Cost of Ownership: Lease Information."
    ::= { cooLeaseInformationTableEntry 2 }
cooLeaseInformationState                   OBJECT-TYPE
    SYNTAX      DellStateSettings
    ACCESS      read-only
    STATUS      mandatory
    DESCRIPTION
"1600.0050.0001.0003 This attribute defines the Dell Systems
Cost of Ownership: Lease Information state of the Dell System."
    ::= { cooLeaseInformationTableEntry 3 }
cooLeaseInformationMultipleSchedules        OBJECT-TYPE
    SYNTAX      DellBoolean
    ACCESS      read-only
    STATUS      mandatory
    DESCRIPTION
"1600.0050.0001.0004 This attribute defines if there are multiple schedules
for this lease."
    ::= { cooLeaseInformationTableEntry 4 }
cooLeaseInformationBuyOutAmount             OBJECT-TYPE
    SYNTAX      DellUnsigned32BitRange
    ACCESS      read-write
    STATUS      mandatory
    DESCRIPTION
"1600.0050.0001.0005 This attribute defines buy out amount for this lease."
    ::= { cooLeaseInformationTableEntry 5 }
cooLeaseInformationLeaseRateFactor          OBJECT-TYPE
    SYNTAX      DellUnsigned32BitRange
    ACCESS      read-write
    STATUS      mandatory
    DESCRIPTION
"1600.0050.0001.0006 This attribute defines the Lease Information lease
rate factor."
    ::= { cooLeaseInformationTableEntry 6 }
cooLeaseInformationEndDateName              OBJECT-TYPE
    SYNTAX      DellDateName
    ACCESS      read-write
    STATUS      mandatory
    DESCRIPTION
"1600.0050.0001.0007 This attribute defines the Lease Information end date
for the Dell System.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { cooLeaseInformationTableEntry 7 }
cooLeaseInformationFairMarketValue          OBJECT-TYPE
    SYNTAX      DellUnsigned32BitRange
    ACCESS      read-write
    STATUS      mandatory
    DESCRIPTION
"1600.0050.0001.0008 This attribute defines the Lease Information fair
market value for the Dell System."
    ::= { cooLeaseInformationTableEntry 8 }
cooLeaseInformationLessorName               OBJECT-TYPE
    SYNTAX      DellCostofOwnershipString
    ACCESS      read-write
    STATUS      mandatory
    DESCRIPTION
"1600.0050.0001.0009 This attribute defines the Lease Information Lessor's
name."
    ::= { cooLeaseInformationTableEntry 9 }


-------------------------------------------------------------------------------
-- Cost Of Ownership (COO) Schedule Number Table
-------------------------------------------------------------------------------

CooScheduleNumberTableEntry                          ::= SEQUENCE {
    cooScheduleNumberchassisIndex                    DellObjectRange,
    cooScheduleNumberIndex                           DellObjectRange,
    cooScheduleNumberState                           DellStateSettings,
    cooScheduleNumberLeaseInformationIndexReference  DellUnsigned32BitRange,
    cooScheduleNumberDescriptionName                 DellCostofOwnershipString
}

cooScheduleNumberTable                          OBJECT-TYPE
    SYNTAX      SEQUENCE OF CooScheduleNumberTableEntry
    ACCESS      not-accessible
    STATUS      mandatory
    DESCRIPTION
"1600.0060 This Group defines the Dell Cost of Ownership:
Schedule Number Information Table."
    ::= { cooGroup 60 }
cooScheduleNumberTableEntry                     OBJECT-TYPE
    SYNTAX      CooScheduleNumberTableEntry
    ACCESS      not-accessible
    STATUS      mandatory
    DESCRIPTION
"1600.0060.0001 This Group defines the Dell Cost of Ownership:
Schedule Number Information Table Entry."
    INDEX       { cooScheduleNumberchassisIndex, cooScheduleNumberIndex }
    ::= { cooScheduleNumberTable 1 }
cooScheduleNumberchassisIndex   OBJECT-TYPE
    SYNTAX      DellObjectRange
    ACCESS      read-only
    STATUS      mandatory
    DESCRIPTION
"1600.0060.0001.0001 This attribute defines the index (one based) of
this Dell chassis."
    ::= { cooScheduleNumberTableEntry 1 }
cooScheduleNumberIndex                          OBJECT-TYPE
    SYNTAX      DellObjectRange
    ACCESS      read-only
    STATUS      mandatory
    DESCRIPTION
"1600.0060.0001.0002 This attribute defines the index of the Dell Systems
Cost of Ownership: Schedule Number Information."
    ::= { cooScheduleNumberTableEntry 2 }
cooScheduleNumberState                         OBJECT-TYPE
    SYNTAX      DellStateSettings
    ACCESS      read-only
    STATUS      mandatory
    DESCRIPTION
"1600.0060.0001.0003 This attribute defines the Dell Systems
Cost of Ownership: Schedule Number Information state of the Dell System."
    ::= { cooScheduleNumberTableEntry 3 }
cooScheduleNumberLeaseInformationIndexReference OBJECT-TYPE
    SYNTAX      DellUnsigned32BitRange
    ACCESS      read-write
    STATUS      mandatory
    DESCRIPTION
"1600.0060.0001.0004 This attribute defines the Lease Information index
number to reference this Schedule Number too."
    ::= { cooScheduleNumberTableEntry 4 }
cooScheduleNumberDescriptionName                OBJECT-TYPE
    SYNTAX      DellCostofOwnershipString
    ACCESS      read-write
    STATUS      mandatory
    DESCRIPTION
"1600.0060.0001.0005 This attribute defines the Schedule Number Information
description name."
    ::= { cooScheduleNumberTableEntry 5 }


-------------------------------------------------------------------------------
-- Cost Of Ownership (COO) Options Table
-------------------------------------------------------------------------------

CooOptionsTableEntry                            ::= SEQUENCE {
    cooOptionschassisIndex                      DellObjectRange,
    cooOptionsIndex                             DellObjectRange,
    cooOptionsState                             DellStateSettings,
    cooOptionsLeaseInformationIndexReference    DellUnsigned32BitRange,
    cooOptionsDescriptionName                   DellCostofOwnershipString
}

cooOptionsTable                         OBJECT-TYPE
    SYNTAX      SEQUENCE OF CooOptionsTableEntry
    ACCESS      not-accessible
    STATUS      mandatory
    DESCRIPTION
"1600.0070 This Group defines the Dell Cost of Ownership:
Option Information Table."
    ::= { cooGroup 70 }
cooOptionsTableEntry                    OBJECT-TYPE
    SYNTAX      CooOptionsTableEntry
    ACCESS      not-accessible
    STATUS      mandatory
    DESCRIPTION
"1600.0070.0001 This Group defines the Dell Cost of Ownership:
Option Information Table Entry."
    INDEX       { cooOptionschassisIndex, cooOptionsIndex }
    ::= { cooOptionsTable 1 }
cooOptionschassisIndex  OBJECT-TYPE
    SYNTAX      DellObjectRange
    ACCESS      read-only
    STATUS      mandatory
    DESCRIPTION
"1600.0070.0001.0001 This attribute defines the index (one based) of
this Dell chassis."
    ::= { cooOptionsTableEntry 1 }
cooOptionsIndex                         OBJECT-TYPE
    SYNTAX      DellObjectRange
    ACCESS      read-only
    STATUS      mandatory
    DESCRIPTION
"1600.0070.0001.0002 This attribute defines the index of the Dell Systems
Cost of Ownership: Option Information."
    ::= { cooOptionsTableEntry 2 }
cooOptionsState                        OBJECT-TYPE
    SYNTAX      DellStateSettings
    ACCESS      read-only
    STATUS      mandatory
    DESCRIPTION
"1600.0070.0001.0003 This attribute defines the Dell Systems
Cost of Ownership: Option Information state of the Dell System."
    ::= { cooOptionsTableEntry 3 }
cooOptionsLeaseInformationIndexReference      OBJECT-TYPE
    SYNTAX      DellUnsigned32BitRange
    ACCESS      read-write
    STATUS      mandatory
    DESCRIPTION
"1600.0070.0001.0004 This attribute defines the Lease Information index
number to reference this option with."
    ::= { cooOptionsTableEntry 4 }
cooOptionsDescriptionName               OBJECT-TYPE
    SYNTAX      DellCostofOwnershipString
    ACCESS      read-write
    STATUS      mandatory
    DESCRIPTION
"1600.0070.0001.0005 This attribute defines the Option Information
description name."
    ::= { cooOptionsTableEntry 5 }


-------------------------------------------------------------------------------
-- Cost Of Ownership (COO) Maintenance Table
-------------------------------------------------------------------------------

CooMaintenanceTableEntry             ::= SEQUENCE {
    cooMaintenancechassisIndex       DellObjectRange,
    cooMaintenanceIndex              DellObjectRange,
    cooMaintenanceState              DellStateSettings,
    cooMaintenanceStartDateName      DellDateName,
    cooMaintenanceEndDateName        DellDateName,
    cooMaintenanceProviderName       DellCostofOwnershipString,
    cooMaintenanceRestrictionsName   DellCostofOwnershipString
}

cooMaintenanceTable             OBJECT-TYPE
    SYNTAX      SEQUENCE OF CooMaintenanceTableEntry
    ACCESS      not-accessible
    STATUS      mandatory
    DESCRIPTION
"1600.0080 This Group defines the Dell Cost of Ownership:
Maintenance Information Table."
    ::= { cooGroup 80 }
cooMaintenanceTableEntry        OBJECT-TYPE
    SYNTAX      CooMaintenanceTableEntry
    ACCESS      not-accessible
    STATUS      mandatory
    DESCRIPTION
"1600.0080.0001 This Group defines the Dell Cost of Ownership:
Maintenance Information Table Entry."
    INDEX       { cooMaintenancechassisIndex, cooMaintenanceIndex }
    ::= { cooMaintenanceTable 1 }
cooMaintenancechassisIndex  OBJECT-TYPE
    SYNTAX      DellObjectRange
    ACCESS      read-only
    STATUS      mandatory
    DESCRIPTION
"1600.0080.0001.0001 This attribute defines the index (one based) of
this Dell chassis."
    ::= { cooMaintenanceTableEntry 1 }
cooMaintenanceIndex                 OBJECT-TYPE
    SYNTAX      DellObjectRange
    ACCESS      read-only
    STATUS      mandatory
    DESCRIPTION
"1600.0080.0001.0002 This attribute defines the index of the Dell Systems
Cost of Ownership: Maintenance Information."
    ::= { cooMaintenanceTableEntry 2 }
cooMaintenanceState                OBJECT-TYPE
    SYNTAX      DellStateSettings
    ACCESS      read-only
    STATUS      mandatory
    DESCRIPTION
"1600.0080.0001.0003 This attribute defines the Dell Systems
Cost of Ownership: Maintenance Information state of the Dell System."
    ::= { cooMaintenanceTableEntry 3 }
cooMaintenanceStartDateName        OBJECT-TYPE
    SYNTAX      DellDateName
    ACCESS      read-write
    STATUS      mandatory
    DESCRIPTION
"1600.0080.0001.0004 This attribute defines the start date for Maintenance.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { cooMaintenanceTableEntry 4 }
cooMaintenanceEndDateName         OBJECT-TYPE
    SYNTAX      DellDateName
    ACCESS      read-write
    STATUS      mandatory
    DESCRIPTION
"1600.0080.0001.0005 This attribute defines the ending date for Maintenance.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { cooMaintenanceTableEntry 5 }
cooMaintenanceProviderName          OBJECT-TYPE
    SYNTAX      DellCostofOwnershipString
    ACCESS      read-write
    STATUS      mandatory
    DESCRIPTION
"1600.0080.0001.0006 This attribute defines the Maintenance provider's name."
    ::= { cooMaintenanceTableEntry 6 }
cooMaintenanceRestrictionsName      OBJECT-TYPE
    SYNTAX      DellCostofOwnershipString
    ACCESS      read-write
    STATUS      mandatory
    DESCRIPTION
"1600.0080.0001.0007 This attribute defines the text of the Maintenance
agreement restrictions."
    ::= { cooMaintenanceTableEntry 7 }


-------------------------------------------------------------------------------
-- Cost Of Ownership (COO) Repair Table
-------------------------------------------------------------------------------

CooRepairTableEntry         ::= SEQUENCE {
    cooRepairchassisIndex   DellObjectRange,
    cooRepairIndex          DellObjectRange,
    cooRepairState          DellStateSettings,
    cooRepairCounter        DellUnsigned32BitRange,
    cooRepairVendorName     DellCostofOwnershipString
}

cooRepairTable              OBJECT-TYPE
    SYNTAX      SEQUENCE OF CooRepairTableEntry
    ACCESS      not-accessible
    STATUS      mandatory
    DESCRIPTION
"1600.0090 This Group defines the Dell Cost of Ownership:
Repair Information Table."
    ::= { cooGroup 90 }
cooRepairTableEntry         OBJECT-TYPE
    SYNTAX      CooRepairTableEntry
    ACCESS      not-accessible
    STATUS      mandatory
    DESCRIPTION
"1600.0090.0001 This Group defines the Dell Cost of Ownership:
Repair Information Table Entry."
    INDEX       { cooRepairchassisIndex, cooRepairIndex }
    ::= { cooRepairTable 1 }
cooRepairchassisIndex   OBJECT-TYPE
    SYNTAX      DellObjectRange
    ACCESS      read-only
    STATUS      mandatory
    DESCRIPTION
"1600.0090.0001.0001 This attribute defines the index (one based) of
this Dell chassis."
    ::= { cooRepairTableEntry 1 }
cooRepairIndex              OBJECT-TYPE
    SYNTAX      DellObjectRange
    ACCESS      read-only
    STATUS      mandatory
    DESCRIPTION
"1600.0090.0001.0002 This attribute defines the index of the Dell Systems
Cost of Ownership: Repair Information."
    ::= { cooRepairTableEntry 2 }
cooRepairState             OBJECT-TYPE
    SYNTAX      DellStateSettings
    ACCESS      read-only
    STATUS      mandatory
    DESCRIPTION
"1600.0090.0001.0003 This attribute defines the Dell Systems
Cost of Ownership: Repair Information state of the Dell System."
    ::= { cooRepairTableEntry 3 }
cooRepairCounter            OBJECT-TYPE
    SYNTAX      DellUnsigned32BitRange
    ACCESS      read-write
    STATUS      mandatory
    DESCRIPTION
"1600.0090.0001.0004 This attribute defines the number of repairs this
system has had."
    ::= { cooRepairTableEntry 4 }
cooRepairVendorName         OBJECT-TYPE
    SYNTAX      DellCostofOwnershipString
    ACCESS      read-write
    STATUS      mandatory
    DESCRIPTION
"1600.0090.0001.0005 This attribute defines the Repair vendors's name."
    ::= { cooRepairTableEntry 5 }


-------------------------------------------------------------------------------
-- Cost Of Ownership (COO) Support Information Table
-------------------------------------------------------------------------------

CooSupportInformationTableEntry         ::= SEQUENCE {
    cooSupportInformationchassisIndex   DellObjectRange,
    cooSupportInformationIndex          DellObjectRange,
    cooSupportInformationState          DellStateSettings,
    cooSupportInformationIsOutsourced   DellBoolean,
    cooSupportInformationType           DellUnsigned32BitRange,
    cooSupportInformationHelpDeskName   DellCostofOwnershipString,
    cooSupportInformationFixTypeName    DellCostofOwnershipString
}

cooSupportInformationTable              OBJECT-TYPE
    SYNTAX      SEQUENCE OF CooSupportInformationTableEntry
    ACCESS      not-accessible
    STATUS      mandatory
    DESCRIPTION
"1600.0100 This Group defines the Dell Cost of Ownership:
Support Information Table."
    ::= { cooGroup 100 }
cooSupportInformationTableEntry         OBJECT-TYPE
    SYNTAX      CooSupportInformationTableEntry
    ACCESS      not-accessible
    STATUS      mandatory
    DESCRIPTION
"1600.0100.0001 This Group defines the Dell Cost of Ownership:
Support Information Table Entry."
    INDEX { cooSupportInformationchassisIndex, cooSupportInformationIndex }
    ::= { cooSupportInformationTable 1 }
cooSupportInformationchassisIndex   OBJECT-TYPE
    SYNTAX      DellObjectRange
    ACCESS      read-only
    STATUS      mandatory
    DESCRIPTION
"1600.0100.0001.0001 This attribute defines the index (one based) of
this Dell chassis."
    ::= { cooSupportInformationTableEntry 1 }
cooSupportInformationIndex              OBJECT-TYPE
    SYNTAX      DellObjectRange
    ACCESS      read-only
    STATUS      mandatory
    DESCRIPTION
"1600.0100.0001.0002 This attribute defines the index of the Dell Systems
Cost of Ownership: Support Information."
    ::= { cooSupportInformationTableEntry 2 }
cooSupportInformationState             OBJECT-TYPE
    SYNTAX      DellStateSettings
    ACCESS      read-only
    STATUS      mandatory
    DESCRIPTION
"1600.0100.0001.0003 This attribute defines the Dell Systems
Cost of Ownership: Support Information state of the Dell System."
    ::= { cooSupportInformationTableEntry 3 }
cooSupportInformationIsOutsourced       OBJECT-TYPE
    SYNTAX      DellBoolean
    ACCESS      read-write
    STATUS      mandatory
    DESCRIPTION
"1600.0100.0001.0004 This attribute defines if support is outsourced or not."
    ::= { cooSupportInformationTableEntry 4 }
cooSupportInformationType               OBJECT-TYPE
    SYNTAX      DellUnsigned32BitRange
    ACCESS      read-write
    STATUS      mandatory
    DESCRIPTION
"1600.0100.0001.0005 This attribute defines the type of of conmponent,
system or network problem that occured."
    ::= { cooSupportInformationTableEntry 5 }
cooSupportInformationHelpDeskName       OBJECT-TYPE
    SYNTAX      DellCostofOwnershipString
    ACCESS      read-write
    STATUS      mandatory
    DESCRIPTION
"1600.0100.0001.0006 This attribute defines the help desk support
Information provided."
    ::= { cooSupportInformationTableEntry 6 }
cooSupportInformationFixTypeName        OBJECT-TYPE
    SYNTAX      DellCostofOwnershipString
    ACCESS      read-write
    STATUS      mandatory
    DESCRIPTION
"1600.0100.0001.0007 This attribute defines the method used to fix
the problem."
    ::= { cooSupportInformationTableEntry 7 }


-------------------------------------------------------------------------------
-- Cost Of Ownership (COO) Trouble Ticket Table
-------------------------------------------------------------------------------

CooTroubleTicketTableEntry                           ::= SEQUENCE {
    cooTroubleTicketchassisIndex                     DellObjectRange,
    cooTroubleTicketIndex                            DellObjectRange,
    cooTroubleTicketState                            DellStateSettings,
    cooTroubleTicketSupportInformationIndexReference DellUnsigned32BitRange,
    cooTroubleTicketNumberName                       DellCostofOwnershipString
}

cooTroubleTicketTable                           OBJECT-TYPE
    SYNTAX      SEQUENCE OF CooTroubleTicketTableEntry
    ACCESS      not-accessible
    STATUS      mandatory
    DESCRIPTION
"1600.0110 This Group defines the Dell Cost of Ownership:
Trouble Ticket Information Table."
    ::= { cooGroup 110 }
cooTroubleTicketTableEntry                      OBJECT-TYPE
    SYNTAX      CooTroubleTicketTableEntry
    ACCESS      not-accessible
    STATUS      mandatory
    DESCRIPTION
"1600.0110.0001 This Group defines the Dell Cost of Ownership:
Trouble Ticket Information Table Entry."
    INDEX       { cooTroubleTicketchassisIndex, cooTroubleTicketIndex }
    ::= { cooTroubleTicketTable 1 }
cooTroubleTicketchassisIndex    OBJECT-TYPE
    SYNTAX      DellObjectRange
    ACCESS      read-only
    STATUS      mandatory
    DESCRIPTION
"1600.0110.0001.0001 This attribute defines the index (one based) of
this Dell chassis."
    ::= { cooTroubleTicketTableEntry 1 }
cooTroubleTicketIndex                           OBJECT-TYPE
    SYNTAX      DellObjectRange
    ACCESS      read-only
    STATUS      mandatory
    DESCRIPTION
"1600.0110.0001.0002 This attribute defines the index of the Dell Systems
Cost of Ownership: Trouble Ticket Information."
    ::= { cooTroubleTicketTableEntry 2 }
cooTroubleTicketState                          OBJECT-TYPE
    SYNTAX      DellStateSettings
    ACCESS      read-only
    STATUS      mandatory
    DESCRIPTION
"1600.0110.0001.0003 This attribute defines the Dell Systems
Cost of Ownership: Trouble Ticket Information state of the Dell System."
    ::= { cooTroubleTicketTableEntry 3 }
cooTroubleTicketSupportInformationIndexReference      OBJECT-TYPE
    SYNTAX      DellUnsigned32BitRange
    ACCESS      read-write
    STATUS      mandatory
    DESCRIPTION
"1600.0110.0001.0004 This attribute defines the Support Information
index number to reference this Trouble Ticket with."
    ::= { cooTroubleTicketTableEntry 4 }
cooTroubleTicketNumberName                      OBJECT-TYPE
    SYNTAX      DellCostofOwnershipString
    ACCESS      read-write
    STATUS      mandatory
    DESCRIPTION
"1600.0110.0001.0005 This attribute defines the Trouble Ticket number
description name."
    ::= { cooTroubleTicketTableEntry 5 }


-------------------------------------------------------------------------------
--
-- Remote Access Group
--
-------------------------------------------------------------------------------

-------------------------------------------------------------------------------
-- Remote Access Table
-------------------------------------------------------------------------------

DellRemoteAccessType                    ::= INTEGER {
    remoteAccessTypeIsOther(1),         -- the type is not one of the following:
    remoteAccessTypeIsUnknown(2),       -- remote access type is unknown
    remoteAccessTypeIsDRACIII(3),       -- remote access type is DRAC III
    remoteAccessTypeIsERA(4)            -- remote access type is ERA
}
DellRemoteAccessControlCapabilities     ::= INTEGER {
    -- If set to 0 (zero) the object has no capabilities
    unknownCapabilities(1),             -- The object's capabilities are unknown
    -- The object's capabilities allow it to be set to:
    logResetCapable(2),                 -- reset its onboard logs
    hardResetCapable(4),                -- be hard reset
    softResetCapable(8),                -- be soft reset
    gracefulResetCapable(16),           -- be gracefully shutdown and soft reset
    defaultConfigResetCapable(32),      -- reset to its default settings for the release version
    allResetCapable(62),
    shutdownCapable(64),                -- shutdown and disable battery if PCI power is off
    allResetAndShutdownCapable(126)
}
DellRemoteAccessControlSettings         ::= INTEGER {
    -- If set to 0 (zero) the object has no settings enabled
    unknown(1),                         -- The object's state is unknown
    -- Only one of the following settings may be enabled in one set request:
    logReset(2),                        -- Reset the onboard logs
    hardReset(4),                       -- Issue a hard reset to the object
    softReset(8),                       -- Issue a soft reset to the object
    gracefulReset(16),                  -- Issue a graceful shutdown and soft reset to the object
    defaultConfigReset(32),             -- Reset the object to its default settings
    shutdown(64)                        -- Shutdown (power off) the object
}
DellRemoteAccessMonitorCapabilities     ::= INTEGER {
    -- If set to 0 (zero) the object has no capabilities
    unknownCapabilities(1),             -- The object's capabilities are unknown
    -- The object's capabilities allow it to be set to:
    extPwrSupplyMonitorIfConnectedCapable(2),-- monitor external power supply if connected
    extPwrSupplyMonitorAlwaysEnabledCapable(4),-- monitor external power supply always
    extPwrSupplyMonitorIfConnectedAndAlwaysEnabledCapable(6)
}
DellRemoteAccessMonitorSettings         ::= INTEGER {
    -- If set to 0 (zero) the object has no settings enabled
    -- Only one extPwrSupplyMonitor setting may be enabled:
    unknown(1),                         -- The object's state is unknown
    extPwrSupplyMonitorIfConnectedEnabled(2), -- Monitor ext pwr supply volt probe
                                              -- if the cable is connected to the DRS
    extPwrSupplyMonitorAlwaysEnabledEnabled(4)-- Monitor ext pwr supply volt probe
                                              -- regardless of the plug state
}
DellRemoteAccessLANCapabilities         ::= INTEGER {
    -- If set to 0 (zero) the object has no capabilities
    unknownCapabilities(1),             -- The object's capabilities are unknown
    -- The object's capabilities allow it to be set to:
    nicCapable(2),                      -- supports a NIC
    nicDHCPCapable(4),                  -- can use DHCP to obtain IP address for NIC
    nicAndNicDHCPCapable(6)
}
DellRemoteAccessLANSettings             ::= INTEGER {
    -- If set to 0 (zero) the object has no settings enabled
    unknown(1),                         -- The object's state is unknown
    nicEnabled(2),                      -- NIC is enabled
    nicDHCPEnabled(4),                  -- NIC should use DHCP to obtain IP address
    nicAndNicDHCPEnabled(6)
}
DellRemoteAccessHostCapabilities        ::= INTEGER {
    -- If set to 0 (zero) the object has no capabilities
    unknownCapabilities(1),             -- The object's capabilities are unknown
    -- The object's capabilities allow it to be set to:
    smtpEmailCapable(2),                -- support email using SMTP
    tftpRemoteFloppyCapable(4),         -- support remote floppy boot from TFTP server
	smtpEmailAndTftpRemoteFloppyCapable(6),
    tftpRemoteFwUpdateCapable(8),       -- support remote FW update from TFTP server
	smtpEmailAndTftpRemoteFwUpdateCapable(10),
	tftpRemoteFloppyAndFwUpdateCapable(12),
    smtpEmailAndTftpRemoteFloppyAndFwUpdateCapable(14)
}
DellRemoteAccessHostSettings            ::= INTEGER {
    -- If set to 0 (zero) the object has no settings enabled
    unknown(1),                         -- The object's state is unknown
    smtpEmailEnabled(2),                -- SMTP client for email is enabled (R)
    tftpRemoteFloppyEnabled(4),         -- TFTP client for remote floppy boot is enabled (R)
	smtpEmailAndTftpRemoteFloppyEnabled(6),
    tftpRemoteFwUpdateEnabled(8),       -- TFTP client for FW update is enabled (R)
	smtpEmailAndTftpRemoteFwUpdateEnabled(10),
	tftpRemoteFloppyAndFwUpdateEnabled(12),
    smtpEmailAndTftpRemoteFloppyAndFwUpdateEnabled(14)
}
DellRemoteAccessOutOfBandSNMPCapabilities ::= INTEGER {
    -- If set to 0 (zero) the object has no capabilities
    unknownCapabilities(1),             -- The object's capabilities are unknown
    -- The object's capabilities allow it to be set to:
    oobSNMPAgentCapable(2),             -- object has an out-of-band SNMP agent
    oobSNMPTrapsCapable(4),             -- object can send out-of-band SNMP traps
    oobSNMPAgentAndTrapsCapable(6)
}
DellRemoteAccessOutOfBandSNMPSettings   ::= INTEGER {
    -- If set to 0 (zero) the object has no settings enabled
    unknown(1),                         -- The object's state is unknown
    oobSNMPAgentEnabled(2),             -- out-of-band SNMP agent is enabled
    oobSNMPTrapsEnabled(4),             -- out-of-band SNMP traps are enabled
    oobSNMPAgentAndTrapsEnabled(6)
}

RemoteAccessTableEntry                  ::= SEQUENCE {
    remoteAccessChassisIndex            DellObjectRange,
    remoteAccessAdapterIndex            DellObjectRange,
    remoteAccessType                    DellRemoteAccessType,
    remoteAccessStateCapabilities       DellStateCapabilities,
    remoteAccessStateSettings           DellStateSettings,
    remoteAccessStatus                  DellStatus,
    remoteAccessProductInfoName         DisplayString (SIZE (0..63)),
    remoteAccessDescriptionInfoName     DisplayString (SIZE (0..255)),
    remoteAccessVersionInfoName         DisplayString (SIZE (0..63)),
    remoteAccessControlCapabilities     DellRemoteAccessControlCapabilities,
    remoteAccessControlSettings         DellRemoteAccessControlSettings,
    remoteAccessMonitorCapabilities     DellRemoteAccessMonitorCapabilities,
    remoteAccessMonitorSettings         DellRemoteAccessMonitorSettings,
    remoteAccessLANCapabilities         DellRemoteAccessLANCapabilities,
    remoteAccessLANSettings             DellRemoteAccessLANSettings,
    remoteAccessHostCapabilities        DellRemoteAccessHostCapabilities,
    remoteAccessHostSettings            DellRemoteAccessHostSettings,
    remoteAccessOutOfBandSNMPCapabilities DellRemoteAccessOutOfBandSNMPCapabilities,
    remoteAccessOutOfBandSNMPSettings   DellRemoteAccessOutOfBandSNMPSettings,
    remoteAccessSMTPServerIPAddress     IpAddress,
    remoteAccessFloppyTFTPIPAddress     IpAddress,
    remoteAccessFloppyTFTPPathName      DisplayString (SIZE (0..255)),
    remoteAccessFirmwareUpdateIPAddress IpAddress,
    remoteAccessFirmwareUpdatePathName  DisplayString (SIZE (0..255)),
	remoteAccessNICStaticIPAddress      IpAddress,
	remoteAccessNICStaticNetmaskAddress IpAddress,
    remoteAccessNICStaticGatewayAddress IpAddress,
    remoteAccessPCMCIAInfoName          DisplayString (SIZE (0..63)),
    remoteAccessMiscInfoName            DisplayString (SIZE (0..63)),
	remoteAccessNICCurrentIPAddress     IpAddress,
	remoteAccessNICCurrentNetmaskAddress IpAddress,
    remoteAccessNICCurrentGatewayAddress IpAddress,
    remoteAccessNICCurrentInfoFromDHCP  DellBoolean
}

remoteAccessTable                       OBJECT-TYPE
    SYNTAX      SEQUENCE OF RemoteAccessTableEntry
    ACCESS      not-accessible
    STATUS      mandatory
    DESCRIPTION
"1700.0010 This object defines the Remote Access table."
    ::= { remoteAccessGroup 10 }
remoteAccessTableEntry                  OBJECT-TYPE
    SYNTAX      RemoteAccessTableEntry
    ACCESS      not-accessible
    STATUS      mandatory
    DESCRIPTION
"1700.0010.0001 This object defines the Remote Access table entry."
    INDEX       { remoteAccessChassisIndex, remoteAccessAdapterIndex }
    ::= { remoteAccessTable 1 }
remoteAccessChassisIndex                OBJECT-TYPE
    SYNTAX      DellObjectRange
    ACCESS      read-only
    STATUS      mandatory
    DESCRIPTION
"1700.0010.0001.0001 This attribute defines the index (one based) of the
chassis containing the Remote Access hardware."
    ::= { remoteAccessTableEntry 1 }
remoteAccessAdapterIndex                OBJECT-TYPE
    SYNTAX      DellObjectRange
    ACCESS      read-only
    STATUS      mandatory
    DESCRIPTION
"1700.0010.0001.0002 This attribute defines the index (one based) of the
Remote Access hardware."
    ::= { remoteAccessTableEntry 2 }
remoteAccessType                        OBJECT-TYPE
    SYNTAX      DellRemoteAccessType
    ACCESS      read-only
    STATUS      mandatory
    DESCRIPTION
"1700.0010.0001.0003 This attribute defines the type of the
Remote Access hardware."
    ::= { remoteAccessTableEntry 3 }
remoteAccessStateCapabilities           OBJECT-TYPE
    SYNTAX      DellStateCapabilities
    ACCESS      read-only
    STATUS      mandatory
    DESCRIPTION
"1700.0010.0001.0004 This attribute defines the state capabilities of the
Remote Access hardware."
    ::= { remoteAccessTableEntry 4 }
remoteAccessStateSettings               OBJECT-TYPE
    SYNTAX      DellStateSettings
    ACCESS      read-write
    STATUS      mandatory
    DESCRIPTION
"1700.0010.0001.0005 This attribute defines the state setting of the
Remote Access hardware."
    ::= { remoteAccessTableEntry 5 }
remoteAccessStatus                      OBJECT-TYPE
    SYNTAX      DellStatus
    ACCESS      read-only
    STATUS      mandatory
    DESCRIPTION
"1700.0010.0001.0006 This attribute defines the status of the
Remote Access hardware."
    ::= { remoteAccessTableEntry 6 }
remoteAccessProductInfoName             OBJECT-TYPE
    SYNTAX      DisplayString (SIZE (0..63))
    ACCESS      read-only
    STATUS      mandatory
    DESCRIPTION
"1700.0010.0001.0007 This attribute defines the name of the
product providing the Remote Access functionality."
    ::= { remoteAccessTableEntry 7 }
remoteAccessDescriptionInfoName         OBJECT-TYPE
    SYNTAX      DisplayString (SIZE (0..255))
    ACCESS      read-only
    STATUS      mandatory
    DESCRIPTION
"1700.0010.0001.0008 This attribute defines the description of the
product providing the Remote Access functionality."
    ::= { remoteAccessTableEntry 8 }
remoteAccessVersionInfoName             OBJECT-TYPE
    SYNTAX      DisplayString (SIZE (0..63))
    ACCESS      read-only
    STATUS      mandatory
    DESCRIPTION
"1700.0010.0001.0009 This attribute defines the version of the
product providing the Remote Access functionality."
    ::= { remoteAccessTableEntry 9 }
remoteAccessControlCapabilities         OBJECT-TYPE
    SYNTAX      DellRemoteAccessControlCapabilities
    ACCESS      read-only
    STATUS      mandatory
    DESCRIPTION
"1700.0010.0001.0010 This attribute defines the control capabilities of the
Remote Access hardware."
    ::= { remoteAccessTableEntry 10 }
remoteAccessControlSettings             OBJECT-TYPE
    SYNTAX      DellRemoteAccessControlSettings
    ACCESS      read-write
    STATUS      mandatory
    DESCRIPTION
"1700.0010.0001.0011 This attribute defines the control settings of the
Remote Access hardware."
    ::= { remoteAccessTableEntry 11 }
remoteAccessMonitorCapabilities         OBJECT-TYPE
    SYNTAX      DellRemoteAccessMonitorCapabilities
    ACCESS      read-only
    STATUS      mandatory
    DESCRIPTION
"1700.0010.0001.0012 This attribute defines the monitor capabilities of the
Remote Access hardware."
    ::= { remoteAccessTableEntry 12 }
remoteAccessMonitorSettings             OBJECT-TYPE
    SYNTAX      DellRemoteAccessMonitorSettings
    ACCESS      read-write
    STATUS      mandatory
    DESCRIPTION
"1700.0010.0001.0013 This attribute defines the monitor settings of the
Remote Access hardware."
    ::= { remoteAccessTableEntry 13 }
remoteAccessLANCapabilities             OBJECT-TYPE
    SYNTAX      DellRemoteAccessLANCapabilities
    ACCESS      read-only
    STATUS      mandatory
    DESCRIPTION
"1700.0010.0001.0014 This attribute defines the LAN capabilities of the
Remote Access hardware."
    ::= { remoteAccessTableEntry 14 }
remoteAccessLANSettings                 OBJECT-TYPE
    SYNTAX      DellRemoteAccessLANSettings
    ACCESS      read-write
    STATUS      mandatory
    DESCRIPTION
"1700.0010.0001.0015 This attribute defines the LAN settings of the
Remote Access hardware."
    ::= { remoteAccessTableEntry 15 }
remoteAccessHostCapabilities            OBJECT-TYPE
    SYNTAX      DellRemoteAccessHostCapabilities
    ACCESS      read-only
    STATUS      mandatory
    DESCRIPTION
"1700.0010.0001.0016 This attribute defines the host capabilities of the
Remote Access hardware."
    ::= { remoteAccessTableEntry 16 }
remoteAccessHostSettings                OBJECT-TYPE
    SYNTAX      DellRemoteAccessHostSettings
    ACCESS      read-write
    STATUS      mandatory
    DESCRIPTION
"1700.0010.0001.0017 This attribute defines the host settings of the
Remote Access hardware."
    ::= { remoteAccessTableEntry 17 }
remoteAccessOutOfBandSNMPCapabilities   OBJECT-TYPE
    SYNTAX      DellRemoteAccessOutOfBandSNMPCapabilities
    ACCESS      read-only
    STATUS      mandatory
    DESCRIPTION
"1700.0010.0001.0018 This attribute defines the out-of-band SNMP capabilities
of the Remote Access hardware."
    ::= { remoteAccessTableEntry 18 }
remoteAccessOutOfBandSNMPSettings       OBJECT-TYPE
    SYNTAX      DellRemoteAccessOutOfBandSNMPSettings
    ACCESS      read-write
    STATUS      mandatory
    DESCRIPTION
"1700.0010.0001.0019 This attribute defines the out-of-band SNMP settings
of the Remote Access hardware."
    ::= { remoteAccessTableEntry 19 }
remoteAccessSMTPServerIPAddress         OBJECT-TYPE
    SYNTAX      IpAddress
    ACCESS      read-write
    STATUS      mandatory
    DESCRIPTION
"1700.0010.0001.0020 This attribute defines the IP address of the
SMTP server provided by the Remote Access hardware."
    ::= { remoteAccessTableEntry 20 }
remoteAccessFloppyTFTPIPAddress         OBJECT-TYPE
    SYNTAX      IpAddress
    ACCESS      read-write
    STATUS      mandatory
    DESCRIPTION
"1700.0010.0001.0021 This attribute defines the IP address of the
TFTP server providing the operating system image used by the
Remote Access hardware."
    ::= { remoteAccessTableEntry 21 }
remoteAccessFloppyTFTPPathName          OBJECT-TYPE
    SYNTAX      DisplayString (SIZE (0..255))
    ACCESS      read-write
    STATUS      mandatory
    DESCRIPTION
"1700.0010.0001.0022 This attribute defines the file name of the
the operating system image obtained from the TFTP server used by the
Remote Access hardware."
    ::= { remoteAccessTableEntry 22 }
remoteAccessFirmwareUpdateIPAddress     OBJECT-TYPE
    SYNTAX      IpAddress
    ACCESS      read-write
    STATUS      mandatory
    DESCRIPTION
"1700.0010.0001.0023 This attribute defines the IP address of the
update server providing the firmware image used by the
Remote Access hardware."
    ::= { remoteAccessTableEntry 23 }
remoteAccessFirmwareUpdatePathName      OBJECT-TYPE
    SYNTAX      DisplayString (SIZE (0..255))
    ACCESS      read-write
    STATUS      mandatory
    DESCRIPTION
"1700.0010.0001.0024 This attribute defines the file name of the
the firmware image obtained from the update server used by the
Remote Access hardware."
    ::= { remoteAccessTableEntry 24 }
remoteAccessNICStaticIPAddress          OBJECT-TYPE
    SYNTAX      IpAddress
    ACCESS      read-write
    STATUS      mandatory
    DESCRIPTION
"1700.0010.0001.0025 This attribute defines the static IP address to be used
by the onboard NIC provided by the Remote Access hardware."
    ::= { remoteAccessTableEntry 25 }
remoteAccessNICStaticNetmaskAddress     OBJECT-TYPE
    SYNTAX      IpAddress
    ACCESS      read-write
    STATUS      mandatory
    DESCRIPTION
"1700.0010.0001.0026 This attribute defines the netmask for the static
IP address to be used by the onboard NIC provided by the Remote Access hardware."
    ::= { remoteAccessTableEntry 26 }
remoteAccessNICStaticGatewayAddress     OBJECT-TYPE
    SYNTAX      IpAddress
    ACCESS      read-write
    STATUS      mandatory
    DESCRIPTION
"1700.0010.0001.0027 This attribute defines the IP address for the gateway
associated with the static IP address to be used by the onboard NIC provided
by the Remote Access hardware."
    ::= { remoteAccessTableEntry 27 }
remoteAccessPCMCIAInfoName              OBJECT-TYPE
    SYNTAX      DisplayString (SIZE (0..63))
    ACCESS      read-only
    STATUS      mandatory
    DESCRIPTION
"1700.0010.0001.0028 This attribute defines the information for the
PCMCIA device used by the Remote Access hardware."
    ::= { remoteAccessTableEntry 28 }
remoteAccessMiscInfoName                OBJECT-TYPE
    SYNTAX      DisplayString (SIZE (0..63))
    ACCESS      read-write
    STATUS      mandatory
    DESCRIPTION
"1700.0010.0001.0029 This attribute defines miscellaneous information
for the Remote Access hardware."
    ::= { remoteAccessTableEntry 29 }
remoteAccessNICCurrentIPAddress         OBJECT-TYPE
    SYNTAX      IpAddress
    ACCESS      read-only
    STATUS      mandatory
    DESCRIPTION
"1700.0010.0001.0030 This attribute defines the IP address currently being used
by the onboard NIC provided by the Remote Access hardware."
    ::= { remoteAccessTableEntry 30 }
remoteAccessNICCurrentNetmaskAddress    OBJECT-TYPE
    SYNTAX      IpAddress
    ACCESS      read-only
    STATUS      mandatory
    DESCRIPTION
"1700.0010.0001.0031 This attribute defines the netmask currently being used
by the onboard NIC provided by the Remote Access hardware."
    ::= { remoteAccessTableEntry 31 }
remoteAccessNICCurrentGatewayAddress    OBJECT-TYPE
    SYNTAX      IpAddress
    ACCESS      read-only
    STATUS      mandatory
    DESCRIPTION
"1700.0010.0001.0032 This attribute defines the IP address for the gateway
currently being used by the onboard NIC provided by the Remote Access hardware."
    ::= { remoteAccessTableEntry 32 }
remoteAccessNICCurrentInfoFromDHCP      OBJECT-TYPE
    SYNTAX      DellBoolean
    ACCESS      read-only
    STATUS      mandatory
    DESCRIPTION
"1700.0010.0001.0033 This attribute defines if DHCP was used to obtain
the NIC information currently being used by the onboard NIC provided by
the Remote Access hardware."
    ::= { remoteAccessTableEntry 33 }


-------------------------------------------------------------------------------
-- Remote User Administration Table
-------------------------------------------------------------------------------

DellRemoteUserAdminStateCapabilities    ::= INTEGER {
    -- If set to 0 (zero) the object has no capabilities
    unknownCapabilities(1),             -- The object's capabilities are unknown
    -- The object's capabilities allow it to be set to:
    enableCapable(2),                   -- be disabled (offline) or be enabled (online)
    notReadyCapable(4),                 -- not ready
    numericPagerCapable(8),             -- support numeric paging
    alphaPagerCapable(16),              -- support alphanumeric paging
    numericPagerAndAlphaPagerCapable(24),
    emailCapable(32),                   -- support electronic mailing
    numericPagerAlphaPagerAndEmailCapable(56),
    privilegeCapable(64),               -- support user privileges
    numericPagerAlphaPagerEmailAndPrivilegeCapable(120)
}
DellRemoteUserAdminStateSettings        ::= INTEGER {
    -- If set to 0 (zero) the object has no settings capabilities, and its state is disabled
    unknown(1),                         -- The object's state is unknown
    enabled(2),                         -- The object's state is disabled (offline) 0, or enabled (online) 1
    notReady(4),                        -- The object's state is not ready
    numericPagerEnabled(8),             -- Numeric paging support is enabled
    enabledAndNumericPagerEnabled(10),
    alphaPagerEnabled(16),              -- Alphanumeric paging support is enabled
    enabledAndAlphaPagerEnabled(18),
    enabledAndNumericPagerAndAlphaPagerEnabled(26),
    emailEnabled(32),                   -- Electronic mailing is enabled
    enabledAndEmailEnabled(34),
    enabledAndNumericPagerAndEmailEnabled(42),
    enabledAndAlphaPagerAndEmailEnabled(50),
    enabledAndNumericPagerAlphaPagerAndEmailEnabled(58)
}
DellRemoteUserAdminControlCapabilities  ::= INTEGER {
    -- If set to 0 (zero) the object has no capabilities
    unknownCapabilities(1),             -- The object's capabilities are unknown
    -- The object's capabilities allow it to be set to:
    numericPagerTestCapable(2),         -- support testing of the numeric paging function
    alphaPagerTestCapable(4),           -- support testing of the alphanumeric pager function
    numericPagerTestAndAlphaPagerTestCapable(6),
    emailTestCapable(8),                -- support sending a test electronic mail message
    numericPagerTestAlphaPagerTestAndEmailTestCapable(14)
}
DellRemoteUserAdminControlSettings      ::= INTEGER {
    -- If set to 0 (zero) the object has no settings capabilities, and its state is disabled
    unknown(1),                         -- The object's state is unknown
    -- Only one of the following settings may be enabled in one set request:
    numericPagerTest(2),                -- Perform a numeric pager test
    alphaPagerTest(4),                  -- Perform an alphanumeric pager test
    emailTest(8)                        -- Send a test email
}
DellRemoteUserAdminAlphaProtocolType    ::= INTEGER {
    other(1),                           -- the alphanumeric protocol is not one of the following:
    unknown(2),                         -- alphanumeric protocol is unknown
    alpha7E0(3),                        -- alphanumeric protocol is 7E0
    alpha8N1(4)                         -- alphanumeric protocol is 8N1
}
DellRemoteUserAdminAlphaBaudType        ::= INTEGER {
    other(1),                           -- the alphanumeric baud rate is not one of the following:
    unknown(2),                         -- alphanumeric baud rate is unknown
    alphaBaud300(3),                    -- alphanumeric baud rate is 300
    alphaBaud1200(4)                    -- alphanumeric baud rate is 1200
}

RemoteUserAdminTableEntry                        ::= SEQUENCE {
    remoteUserAdminChassisIndex                  DellObjectRange,
    remoteUserAdminAdapterIndex                  DellObjectRange,
    remoteUserAdminUserIndex                     DellObjectRange,
    remoteUserAdminStateCapabilities             DellRemoteUserAdminStateCapabilities,
    remoteUserAdminStateSettings                 DellRemoteUserAdminStateSettings,
    remoteUserAdminStatus                        DellStatus,
    remoteUserAdminUserName                      DisplayString (SIZE (0..19)),
    remoteUserAdminUserPasswordName              DisplayString (SIZE (0..255)),
    remoteUserAdminUserPrivilege                 DisplayString (SIZE (0..31)),
    remoteUserAdminUserPrivilegeCapabilities     DisplayString (SIZE (0..31)),
    remoteUserAdminAlertFilterDrsEventsMask      DellUnsigned32BitRange,
    remoteUserAdminAlertFilterSysEventsMask      DellUnsigned32BitRange,
    remoteUserAdminAlertFilterDrsCapabilities    DellUnsigned32BitRange,
    remoteUserAdminAlertFilterSysCapabilities    DellUnsigned32BitRange,
    remoteUserAdminPagerNumericNumberName        DisplayString (SIZE (0..95)),
    remoteUserAdminPagerNumericMessageName       DisplayString (SIZE (0..31)),
    remoteUserAdminPagerNumericHangupDelay       DellUnsigned32BitRange,
    remoteUserAdminPagerAlphaPhoneNumberName     DisplayString (SIZE (0..95)),
    remoteUserAdminPagerAlphaProtocol            DellRemoteUserAdminAlphaProtocolType,
    remoteUserAdminPagerAlphaBaudRate            DellRemoteUserAdminAlphaBaudType,
    remoteUserAdminPagerAlphaCustomMessageName   DisplayString (SIZE (0..31)),
    remoteUserAdminPagerAlphaModemConnectTimeout DellUnsigned32BitRange,
    remoteUserAdminPagerAlphaPagerIdName         DisplayString (SIZE (0..31)),
    remoteUserAdminPagerAlphaPasswordName        DisplayString (SIZE (0..31)),
    remoteUserAdminPagerModemInitStringName      DisplayString (SIZE (0..31)),
    remoteUserAdminPagerModemPort                DellUnsigned32BitRange,
    remoteUserAdminEmailAddressName              DisplayString (SIZE (0..63)),
    remoteUserAdminEmailCustomMessageName        DisplayString (SIZE (0..31)),
    remoteUserAdminControlCapabilities           DellRemoteUserAdminControlCapabilities,
    remoteUserAdminControlSettings               DellRemoteUserAdminControlSettings,
    remoteUserAdminUserType                      DellUnsigned8BitRange
}

remoteUserAdminTable                    OBJECT-TYPE
    SYNTAX      SEQUENCE OF RemoteUserAdminTableEntry
    ACCESS      not-accessible
    STATUS      mandatory
    DESCRIPTION
"1700.0020 This object defines the Remote Access User Administration table."
    ::= { remoteAccessGroup 20 }
remoteUserAdminTableEntry               OBJECT-TYPE
    SYNTAX      RemoteUserAdminTableEntry
    ACCESS      not-accessible
    STATUS      mandatory
    DESCRIPTION
"1700.0020.0001 This object defines the Remote Access User Administration
table entry."
    INDEX       { remoteUserAdminChassisIndex,
	              remoteUserAdminAdapterIndex,
				  remoteUserAdminUserIndex }
    ::= { remoteUserAdminTable 1 }
remoteUserAdminChassisIndex             OBJECT-TYPE
    SYNTAX      DellObjectRange
    ACCESS      read-only
    STATUS      mandatory
    DESCRIPTION
"1700.0020.0001.0001 This attribute defines the index (one based) of the
chassis containing the Remote Access hardware."
    ::= { remoteUserAdminTableEntry 1 }
remoteUserAdminAdapterIndex             OBJECT-TYPE
    SYNTAX      DellObjectRange
    ACCESS      read-only
    STATUS      mandatory
    DESCRIPTION
"1700.0020.0001.0002 This attribute defines the index (one based) of the
Remote Access hardware used by this Remote Access user."
    ::= { remoteUserAdminTableEntry 2 }
remoteUserAdminUserIndex                OBJECT-TYPE
    SYNTAX      DellObjectRange
    ACCESS      read-only
    STATUS      mandatory
    DESCRIPTION
"1700.0020.0001.0003 This attribute defines the index (one based) of this
Remote Access user."
    ::= { remoteUserAdminTableEntry 3 }
remoteUserAdminStateCapabilities        OBJECT-TYPE
    SYNTAX      DellRemoteUserAdminStateCapabilities
    ACCESS      read-only
    STATUS      mandatory
    DESCRIPTION
"1700.0020.0001.0004 This attribute defines the state capabilities for this
Remote Access user."
    ::= { remoteUserAdminTableEntry 4 }
remoteUserAdminStateSettings            OBJECT-TYPE
    SYNTAX      DellRemoteUserAdminStateSettings
    ACCESS      read-write
    STATUS      mandatory
    DESCRIPTION
"1700.0020.0001.0005 This attribute defines the state settings for this
Remote Access user."
    ::= { remoteUserAdminTableEntry 5 }
remoteUserAdminStatus                   OBJECT-TYPE
    SYNTAX      DellStatus
    ACCESS      read-only
    STATUS      mandatory
    DESCRIPTION
"1700.0020.0001.0006 This attribute defines the status for this
Remote Access user."
    ::= { remoteUserAdminTableEntry 6 }
remoteUserAdminUserName                 OBJECT-TYPE
    SYNTAX      DisplayString (SIZE (0..19))
    ACCESS      read-write
    STATUS      mandatory
    DESCRIPTION
"1700.0020.0001.0007 This attribute defines the name for this
Remote Access user."
    ::= { remoteUserAdminTableEntry 7 }
remoteUserAdminUserPasswordName         OBJECT-TYPE
    SYNTAX      DisplayString (SIZE (0..255))
    ACCESS      read-write
    STATUS      mandatory
    DESCRIPTION
"1700.0020.0001.0008 This attribute defines the password for this
Remote Access user."
    ::= { remoteUserAdminTableEntry 8 }
remoteUserAdminUserPrivilege            OBJECT-TYPE
    SYNTAX      DisplayString (SIZE (0..31))
    ACCESS      read-write
    STATUS      mandatory
    DESCRIPTION
"1700.0020.0001.0009 This attribute defines the privileges for this
Remote Access user."
    ::= { remoteUserAdminTableEntry 9 }
remoteUserAdminUserPrivilegeCapabilities OBJECT-TYPE
    SYNTAX      DisplayString (SIZE (0..31))
    ACCESS      read-only
    STATUS      mandatory
    DESCRIPTION
"1700.0020.0001.0010 This attribute defines the privilege capabilities for this
Remote Access user."
    ::= { remoteUserAdminTableEntry 10 }
remoteUserAdminAlertFilterDrsEventsMask OBJECT-TYPE
    SYNTAX      DellUnsigned32BitRange
    ACCESS      read-write
    STATUS      mandatory
    DESCRIPTION
"1700.0020.0001.0011 This attribute defines the DRS events filter mask for this
Remote Access user."
    ::= { remoteUserAdminTableEntry 11 }
remoteUserAdminAlertFilterSysEventsMask OBJECT-TYPE
    SYNTAX      DellUnsigned32BitRange
    ACCESS      read-write
    STATUS      mandatory
    DESCRIPTION
"1700.0020.0001.0012 This attribute defines the system events filter mask
for this Remote Access user."
    ::= { remoteUserAdminTableEntry 12 }
remoteUserAdminAlertFilterDrsCapabilities OBJECT-TYPE
    SYNTAX      DellUnsigned32BitRange
    ACCESS      read-only
    STATUS      mandatory
    DESCRIPTION
"1700.0020.0001.0013 This attribute defines the DRS events filter capabilities
for this Remote Access user."
    ::= { remoteUserAdminTableEntry 13 }
remoteUserAdminAlertFilterSysCapabilities OBJECT-TYPE
    SYNTAX      DellUnsigned32BitRange
    ACCESS      read-only
    STATUS      mandatory
    DESCRIPTION
"1700.0020.0001.0014 This attribute defines the system events filter capabilities
for this Remote Access user."
    ::= { remoteUserAdminTableEntry 14 }
remoteUserAdminPagerNumericNumberName   OBJECT-TYPE
    SYNTAX      DisplayString (SIZE (0..95))
    ACCESS      read-write
    STATUS      mandatory
    DESCRIPTION
"1700.0020.0001.0015 This attribute defines the numeric pager number for this
for this Remote Access user."
    ::= { remoteUserAdminTableEntry 15 }
remoteUserAdminPagerNumericMessageName  OBJECT-TYPE
    SYNTAX      DisplayString (SIZE (0..31))
    ACCESS      read-write
    STATUS      mandatory
    DESCRIPTION
"1700.0020.0001.0016 This attribute defines the message to send to the numeric
pager for this Remote Access user."
    ::= { remoteUserAdminTableEntry 16 }
remoteUserAdminPagerNumericHangupDelay  OBJECT-TYPE
    SYNTAX      DellUnsigned32BitRange
    ACCESS      read-write
    STATUS      mandatory
    DESCRIPTION
"1700.0020.0001.0017 This attribute defines the numeric pager hangup delay
for this Remote Access user."
    ::= { remoteUserAdminTableEntry 17 }
remoteUserAdminPagerAlphaPhoneNumberName OBJECT-TYPE
    SYNTAX      DisplayString (SIZE (0..95))
    ACCESS      read-write
    STATUS      mandatory
    DESCRIPTION
"1700.0020.0001.0018 This attribute defines the alphanumeric pager phone number
for this Remote Access user."
    ::= { remoteUserAdminTableEntry 18 }
remoteUserAdminPagerAlphaProtocol       OBJECT-TYPE
    SYNTAX      DellRemoteUserAdminAlphaProtocolType
    ACCESS      read-write
    STATUS      mandatory
    DESCRIPTION
"1700.0020.0001.0019 This attribute defines the protocol used by the
alphanumeric pager provider for this Remote Access user."
    ::= { remoteUserAdminTableEntry 19 }
remoteUserAdminPagerAlphaBaudRate       OBJECT-TYPE
    SYNTAX      DellRemoteUserAdminAlphaBaudType
    ACCESS      read-write
    STATUS      mandatory
    DESCRIPTION
"1700.0020.0001.0020 This attribute defines the baud rate used by the
alphanumeric pager provider for this Remote Access user."
    ::= { remoteUserAdminTableEntry 20 }
remoteUserAdminPagerAlphaCustomMessageName OBJECT-TYPE
    SYNTAX      DisplayString (SIZE (0..31))
    ACCESS      read-write
    STATUS      mandatory
    DESCRIPTION
"1700.0020.0001.0021 This attribute defines the message to be sent to the
alphanumeric pager to inform the user of a call by this Remote Access user."
    ::= { remoteUserAdminTableEntry 21 }
remoteUserAdminPagerAlphaModemConnectTimeout OBJECT-TYPE
    SYNTAX      DellUnsigned32BitRange
    ACCESS      read-write
    STATUS      mandatory
    DESCRIPTION
"1700.0020.0001.0022 This attribute defines the modem connection timeout
for the alhpanumeric pager for this Remote Access user."
    ::= { remoteUserAdminTableEntry 22 }
remoteUserAdminPagerAlphaPagerIdName    OBJECT-TYPE
    SYNTAX      DisplayString (SIZE (0..31))
    ACCESS      read-write
    STATUS      mandatory
    DESCRIPTION
"1700.0020.0001.0023 This attribute defines the ID to be sent to the
alphanumeric pager to inform the user of a call by this Remote Access user."
    ::= { remoteUserAdminTableEntry 23 }
remoteUserAdminPagerAlphaPasswordName   OBJECT-TYPE
    SYNTAX      DisplayString (SIZE (0..31))
    ACCESS      read-write
    STATUS      mandatory
    DESCRIPTION
"1700.0020.0001.0024 This attribute defines the password for the
alphanumeric pager for this Remote Access user."
    ::= { remoteUserAdminTableEntry 24 }
remoteUserAdminPagerModemInitStringName OBJECT-TYPE
    SYNTAX      DisplayString (SIZE (0..31))
    ACCESS      read-write
    STATUS      mandatory
    DESCRIPTION
"1700.0020.0001.0025 This attribute defines the initialization string
to be sent to the pager modem for this Remote Access user."
    ::= { remoteUserAdminTableEntry 25 }
remoteUserAdminPagerModemPort           OBJECT-TYPE
    SYNTAX      DellUnsigned32BitRange
    ACCESS      read-write
    STATUS      mandatory
    DESCRIPTION
"1700.0020.0001.0026 This attribute defines the port for the pager modem
for this Remote Access user."
    ::= { remoteUserAdminTableEntry 26 }
remoteUserAdminEmailAddressName         OBJECT-TYPE
    SYNTAX      DisplayString (SIZE (0..63))
    ACCESS      read-write
    STATUS      mandatory
    DESCRIPTION
"1700.0020.0001.0027 This attribute defines the email address for this
Remote Access user."
    ::= { remoteUserAdminTableEntry 27 }
remoteUserAdminEmailCustomMessageName   OBJECT-TYPE
    SYNTAX      DisplayString (SIZE (0..31))
    ACCESS      read-write
    STATUS      mandatory
    DESCRIPTION
"1700.0020.0001.0028 This attribute defines the email message to send to this
Remote Access user."
    ::= { remoteUserAdminTableEntry 28 }
remoteUserAdminControlCapabilities      OBJECT-TYPE
    SYNTAX      DellRemoteUserAdminControlCapabilities
    ACCESS      read-only
    STATUS      mandatory
    DESCRIPTION
"1700.0020.0001.0029 This attribute defines the control capabilities for this
Remote Access user."
    ::= { remoteUserAdminTableEntry 29 }
remoteUserAdminControlSettings          OBJECT-TYPE
    SYNTAX      DellRemoteUserAdminControlSettings
    ACCESS      read-write
    STATUS      mandatory
    DESCRIPTION
"1700.0020.0001.0030 This attribute defines the control settings for this
Remote Access user."
    ::= { remoteUserAdminTableEntry 30 }
remoteUserAdminUserType                 OBJECT-TYPE
    SYNTAX      DellUnsigned8BitRange
    ACCESS      read-write
    STATUS      mandatory
    DESCRIPTION
"1700.0020.0001.0031 This attribute defines the type of this
Remote Access user."
    ::= { remoteUserAdminTableEntry 31 }


-------------------------------------------------------------------------------
-- Remote SNMP Trap Table
-------------------------------------------------------------------------------

DellRemoteSNMPTrapStateCapabilities     ::= INTEGER {
    -- If set to 0 (zero) the object has no capabilities
    unknownCapabilities(1),             -- The object's capabilities are unknown
    -- The object's capabilities allow it to be set to:
    enableCapable(2),                   -- be disabled (offline) or be enabled (online)
    notReadyCapable(4),                 -- not ready
    enableAndNotReadyCapable(6)
}
DellRemoteSNMPTrapStateSettings         ::= INTEGER {
    -- If set to 0 (zero) the object has no settings capabilities, and its state is disabled
    unknown(1),                         -- The object's state is unknown
    enabled(2),                         -- The object's state is disabled (offline) 0, or enabled (online) 1
    notReady(4),                        -- The object's state is not ready
    enabledAndNotReady(6)
}
DellRemoteSNMPTrapControlCapabilities   ::= INTEGER {
    -- If set to 0 (zero) the object has no capabilities
    unknownCapabilities(1),             -- The object's capabilities are unknown
    -- The object's capabilities allow it to be set to:
    trapTestCapable(2)                  -- support generating a test SNMP trap
}
DellRemoteSNMPTrapControlSettings       ::= INTEGER {
    -- If set to 0 (zero) the object has no settings capabilities, and its state is disabled
    unknown(1),                         -- The object's state is unknown
    -- Only one of the following settings may be enabled in one set request:
    trapTest(2)                         -- Generate a test SNMP trap
}

RemoteSNMPTrapTableEntry                ::= SEQUENCE {
    remoteSNMPTrapChassisIndex          DellObjectRange,
    remoteSNMPTrapAdapterIndex          DellObjectRange,
    remoteSNMPTrapIndex                 DellObjectRange,
    remoteSNMPTrapStateCapabilities     DellRemoteSNMPTrapStateCapabilities,
    remoteSNMPTrapStateSettings         DellRemoteSNMPTrapStateSettings,
    remoteSNMPTrapStatus                DellStatus,
    remoteSNMPTrapDestinationIPAddress  IpAddress,
    remoteSNMPTrapSNMPCommunityName     DisplayString (SIZE (0..31)),
    remoteSNMPTrapFilterDrsEventsMask   DellUnsigned32BitRange,
    remoteSNMPTrapFilterSysEventsMask   DellUnsigned32BitRange,
    remoteSNMPTrapFilterDrsCapabilities DellUnsigned32BitRange,
    remoteSNMPTrapFilterSysCapabilities DellUnsigned32BitRange,
    remoteSNMPTrapControlCapabilities   DellRemoteSNMPTrapControlCapabilities,
    remoteSNMPTrapControlSettings       DellRemoteSNMPTrapControlSettings
}

remoteSNMPTrapTable                     OBJECT-TYPE
    SYNTAX      SEQUENCE OF RemoteSNMPTrapTableEntry
    ACCESS      not-accessible
    STATUS      mandatory
    DESCRIPTION
"1700.0030 This object defines the Remote Access SNMP Trap Destination table."
    ::= { remoteAccessGroup 30 }
remoteSNMPTrapTableEntry                OBJECT-TYPE
    SYNTAX      RemoteSNMPTrapTableEntry
    ACCESS      not-accessible
    STATUS      mandatory
    DESCRIPTION
"1700.0030.0001 This object defines the Remote Access SNMP Trap Destination
table entry."
    INDEX       { remoteSNMPTrapChassisIndex,
	              remoteSNMPTrapAdapterIndex,
				  remoteSNMPTrapIndex }
    ::= { remoteSNMPTrapTable 1 }
remoteSNMPTrapChassisIndex              OBJECT-TYPE
    SYNTAX      DellObjectRange
    ACCESS      read-only
    STATUS      mandatory
    DESCRIPTION
"1700.0030.0001.0001 This attribute defines the index (one based) of the
chassis containing the Remote Access hardware."
    ::= { remoteSNMPTrapTableEntry 1 }
remoteSNMPTrapAdapterIndex              OBJECT-TYPE
    SYNTAX      DellObjectRange
    ACCESS      read-only
    STATUS      mandatory
    DESCRIPTION
"1700.0030.0001.0002 This attribute defines the index (one based) of the
Remote Access hardware that uses this SNMP trap destination."
    ::= { remoteSNMPTrapTableEntry 2 }
remoteSNMPTrapIndex                     OBJECT-TYPE
    SYNTAX      DellObjectRange
    ACCESS      read-only
    STATUS      mandatory
    DESCRIPTION
"1700.0030.0001.0003 This attribute defines the index (one based) of this
Remote Access SNMP trap destination."
    ::= { remoteSNMPTrapTableEntry 3 }
remoteSNMPTrapStateCapabilities         OBJECT-TYPE
    SYNTAX      DellRemoteSNMPTrapStateCapabilities
    ACCESS      read-only
    STATUS      mandatory
    DESCRIPTION
"1700.0030.0001.0004 This attribute defines the state capabilities of this
Remote Access SNMP trap destination."
    ::= { remoteSNMPTrapTableEntry 4 }
remoteSNMPTrapStateSettings             OBJECT-TYPE
    SYNTAX      DellRemoteSNMPTrapStateSettings
    ACCESS      read-write
    STATUS      mandatory
    DESCRIPTION
"1700.0030.0001.0005 This attribute defines the state settings of this
Remote Access SNMP trap destination."
    ::= { remoteSNMPTrapTableEntry 5 }
remoteSNMPTrapStatus                    OBJECT-TYPE
    SYNTAX      DellStatus
    ACCESS      read-only
    STATUS      mandatory
    DESCRIPTION
"1700.0030.0001.0006 This attribute defines the status of this
Remote Access SNMP trap destination."
    ::= { remoteSNMPTrapTableEntry 6 }
remoteSNMPTrapDestinationIPAddress      OBJECT-TYPE
    SYNTAX      IpAddress
    ACCESS      read-write
    STATUS      mandatory
    DESCRIPTION
"1700.0030.0001.0007 This attribute defines the IP address of this
Remote Access SNMP trap destination."
    ::= { remoteSNMPTrapTableEntry 7 }
remoteSNMPTrapSNMPCommunityName         OBJECT-TYPE
    SYNTAX      DisplayString (SIZE (0..31))
    ACCESS      read-write
    STATUS      mandatory
    DESCRIPTION
"1700.0030.0001.0008 This attribute defines the community for traps sent to this
Remote Access SNMP trap destination."
    ::= { remoteSNMPTrapTableEntry 8 }
remoteSNMPTrapFilterDrsEventsMask       OBJECT-TYPE
    SYNTAX      DellUnsigned32BitRange
    ACCESS      read-write
    STATUS      mandatory
    DESCRIPTION
"1700.0030.0001.0009 This attribute defines the DRS events filter mask for this
Remote Access SNMP trap destination."
    ::= { remoteSNMPTrapTableEntry 9 }
remoteSNMPTrapFilterSysEventsMask       OBJECT-TYPE
    SYNTAX      DellUnsigned32BitRange
    ACCESS      read-write
    STATUS      mandatory
    DESCRIPTION
"1700.0030.0001.0010 This attribute defines the system events filter mask for
this Remote Access SNMP trap destination."
    ::= { remoteSNMPTrapTableEntry 10 }
remoteSNMPTrapFilterDrsCapabilities     OBJECT-TYPE
    SYNTAX      DellUnsigned32BitRange
    ACCESS      read-only
    STATUS      mandatory
    DESCRIPTION
"1700.0030.0001.0011 This attribute defines the DRS events filter capabilities
for this Remote Access SNMP trap destination."
    ::= { remoteSNMPTrapTableEntry 11 }
remoteSNMPTrapFilterSysCapabilities     OBJECT-TYPE
    SYNTAX      DellUnsigned32BitRange
    ACCESS      read-only
    STATUS      mandatory
    DESCRIPTION
"1700.0030.0001.0012 This attribute defines the system events filter
capabilities for this Remote Access SNMP trap destination."
    ::= { remoteSNMPTrapTableEntry 12 }
remoteSNMPTrapControlCapabilities       OBJECT-TYPE
    SYNTAX      DellRemoteSNMPTrapControlCapabilities
    ACCESS      read-only
    STATUS      mandatory
    DESCRIPTION
"1700.0030.0001.0013 This attribute defines the control capabilities of this
Remote Access SNMP trap destination."
    ::= { remoteSNMPTrapTableEntry 13 }
remoteSNMPTrapControlSettings           OBJECT-TYPE
    SYNTAX      DellRemoteSNMPTrapControlSettings
    ACCESS      read-write
    STATUS      mandatory
    DESCRIPTION
"1700.0030.0001.0014 This attribute defines the control settings of this
Remote Access SNMP trap destination."
    ::= { remoteSNMPTrapTableEntry 14 }


-------------------------------------------------------------------------------
-- Remote Dial Up Table
-------------------------------------------------------------------------------

DellRemoteDialUpStateCapabilities       ::= INTEGER {
    -- If set to 0 (zero) the object has no capabilities
    unknownCapabilities(1),             -- The object's capabilities are unknown
    -- The object's capabilities allow it to be set to:
    enableCapable(2),                   -- be disabled (offline) or be enabled (online)
    notReadyCapable(4),                 -- not ready
    dialInCapable(8),                   -- support dial-in
    dialOutCapable(16),                 -- support dial-out
    dialInDHCPCapable(32),              -- support use of DHCP to obtain IP addresses
    dialInAuthAnyCapable(64),           -- support any auth type including clear text
	dialInAndOutAndDialInDHCPAndAuthAnyCapable(120),
    dialInAuthEncryptedCapable(128),    -- support only encrypted passwords (CHAP)
	dialInAndOutAndDialInDHCPAndAuthAnyAndEncryptedCapable(248),
    dialInAuthMschapCapable(256),       -- support only MSCHAP
	dialInAndOutAndDialInDHCPAndAllAuthCapable(504)
}
DellRemoteDialUpStateSettings           ::= INTEGER {
    -- If set to 0 (zero) the object has no settings capabilities, and its state is disabled
    -- One and only one dialInAuth setting must be enabled:
    unknown(1),                         -- The object's state is unknown
    enabled(2),                         -- The object's state is disabled (offline) 0, or enabled (online) 1
    notReady(4),                        -- The object's state is not ready
    dialInEnabled(8),                   -- Dial-in is enabled
    dialOutEnabled(16),                 -- Dial-out is enabled
    dialInDHCPEnabled(32),              -- Object uses DHCP to obtain IP addresses
    dialInAuthAnyEnabled(64),           -- Object accepts any auth type including clear text
	enabledDialInAndOutAndDialInAuthAnyEnabled(90),
	enabledDialInAndOutAndDialInDHCPAndAuthAnyEnabled(122),
    dialInAuthEncryptedEnabled(128),    -- Object accepts only encrypted passwords (CHAP)
	enabledDialInAndOutAndDialInAuthEncryptedEnabled(154),
	enabledDialInAndOutAndDialInDHCPAndAuthEncryptedEnabled(186),
    dialInAuthMschapEnabled(256),       -- Object accepts only MSCHAP
	enabledDialInAndOutAndDialInAuthMschapEnabled(282),
	enabledDialInAndOutAndDialInDHCPAndAuthMschapEnabled(314)
}
DellRemoteDialUpModemDialType           ::= INTEGER {
    remoteDialUpIsOther(1),             -- the type is not one of the following:
    remoteDialUpIsUnknown(2),           -- dial type is unknown
    remoteDialUpIsTone(3),              -- dial type is tone
    remoteDialUpIsPulse(4)              -- dial type is pulse
}

RemoteDialUpTableEntry                     ::= SEQUENCE {
    remoteDialUpChassisIndex               DellObjectRange,
    remoteDialUpAdapterIndex               DellObjectRange,
    remoteDialUpIndex                      DellObjectRange,
    remoteDialUpStateCapabilities          DellRemoteDialUpStateCapabilities,
    remoteDialUpStateSettings              DellRemoteDialUpStateSettings,
    remoteDialUpStatus                     DellStatus,
    remoteDialUpPPPDialInBaseIPAddress     IpAddress,
    remoteDialUpPPPDialInIdleTimeout       DellUnsigned32BitRange,
    remoteDialUpPPPDialInMaxConnectTimeout DellUnsigned32BitRange,
    remoteDialUpDialOutModemConnectTimeout DellUnsigned32BitRange,
    remoteDialUpModemDialType              DellRemoteDialUpModemDialType,
    remoteDialUpModemInitStringName        DisplayString (SIZE (0..63)),
    remoteDialUpModemBaudRate              DellUnsigned32BitRange,
    remoteDialUpModemPort                  DellUnsigned32BitRange
}

remoteDialUpTable                       OBJECT-TYPE
    SYNTAX      SEQUENCE OF RemoteDialUpTableEntry
    ACCESS      not-accessible
    STATUS      mandatory
    DESCRIPTION
"1700.0040 This object defines the Remote Access Dial Up table."
    ::= { remoteAccessGroup 40 }
remoteDialUpTableEntry                  OBJECT-TYPE
    SYNTAX      RemoteDialUpTableEntry
    ACCESS      not-accessible
    STATUS      mandatory
    DESCRIPTION
"1700.0040.0001 This object defines the Remote Access Dial Up table entry."
    INDEX       { remoteDialUpChassisIndex,
	              remoteDialUpAdapterIndex,
				  remoteDialUpIndex }
    ::= { remoteDialUpTable 1 }
remoteDialUpChassisIndex                OBJECT-TYPE
    SYNTAX      DellObjectRange
    ACCESS      read-only
    STATUS      mandatory
    DESCRIPTION
"1700.0040.0001.0001 This attribute defines the index (one based) of the
chassis containing the Remote Access hardware."
    ::= { remoteDialUpTableEntry 1 }
remoteDialUpAdapterIndex                OBJECT-TYPE
    SYNTAX      DellObjectRange
    ACCESS      read-only
    STATUS      mandatory
    DESCRIPTION
"1700.0040.0001.0002 This attribute defines the index (one based) of the
Remote Access hardware that supports this Remote Access Dial Up functionality."
    ::= { remoteDialUpTableEntry 2 }
remoteDialUpIndex                       OBJECT-TYPE
    SYNTAX      DellObjectRange
    ACCESS      read-only
    STATUS      mandatory
    DESCRIPTION
"1700.0040.0001.0003 This attribute defines the index (one based) of this
Remote Access Dial Up functionality."
    ::= { remoteDialUpTableEntry 3 }
remoteDialUpStateCapabilities           OBJECT-TYPE
    SYNTAX      DellRemoteDialUpStateCapabilities
    ACCESS      read-only
    STATUS      mandatory
    DESCRIPTION
"1700.0040.0001.0004 This attribute defines the state capabilities of this
Remote Access Dial Up functionality."
    ::= { remoteDialUpTableEntry 4 }
remoteDialUpStateSettings               OBJECT-TYPE
    SYNTAX      DellRemoteDialUpStateSettings
    ACCESS      read-write
    STATUS      mandatory
    DESCRIPTION
"1700.0040.0001.0005 This attribute defines the state settings of this
Remote Access Dial Up functionality."
    ::= { remoteDialUpTableEntry 5 }
remoteDialUpStatus                      OBJECT-TYPE
    SYNTAX      DellStatus
    ACCESS      read-only
    STATUS      mandatory
    DESCRIPTION
"1700.0040.0001.0006 This attribute defines the status of this
Remote Access Dial Up functionality."
    ::= { remoteDialUpTableEntry 6 }
remoteDialUpPPPDialInBaseIPAddress      OBJECT-TYPE
    SYNTAX      IpAddress
    ACCESS      read-write
    STATUS      mandatory
    DESCRIPTION
"1700.0040.0001.0007 This attribute defines the base IP address of the
PPP server for this Remote Access Dial Up functionality."
    ::= { remoteDialUpTableEntry 7 }
remoteDialUpPPPDialInIdleTimeout        OBJECT-TYPE
    SYNTAX      DellUnsigned32BitRange
    ACCESS      read-write
    STATUS      mandatory
    DESCRIPTION
"1700.0040.0001.0008 This attribute defines the PPP idle timeout value
in seconds for this Remote Access Dial Up functionality."
    ::= { remoteDialUpTableEntry 8 }
remoteDialUpPPPDialInMaxConnectTimeout  OBJECT-TYPE
    SYNTAX      DellUnsigned32BitRange
    ACCESS      read-write
    STATUS      mandatory
    DESCRIPTION
"1700.0040.0001.0009 This attribute defines the PPP connect timeout value
in seconds for this Remote Access Dial Up functionality."
    ::= { remoteDialUpTableEntry 9 }
remoteDialUpDialOutModemConnectTimeout  OBJECT-TYPE
    SYNTAX      DellUnsigned32BitRange
    ACCESS      read-write
    STATUS      mandatory
    DESCRIPTION
"1700.0040.0001.0010 This attribute defines the modem dial out connect timeout
value in seconds for this Remote Access Dial Up functionality."
    ::= { remoteDialUpTableEntry 10 }
remoteDialUpModemDialType               OBJECT-TYPE
    SYNTAX      DellRemoteDialUpModemDialType
    ACCESS      read-write
    STATUS      mandatory
    DESCRIPTION
"1700.0040.0001.0011 This attribute defines the dial type for the modem
used by this Remote Access Dial Up functionality."
    ::= { remoteDialUpTableEntry 11 }
remoteDialUpModemInitStringName         OBJECT-TYPE
    SYNTAX      DisplayString (SIZE (0..63))
    ACCESS      read-write
    STATUS      mandatory
    DESCRIPTION
"1700.0040.0001.0012 This attribute defines the initialization string to be sent
to the modem for this Remote Access Dial Up functionality."
    ::= { remoteDialUpTableEntry 12 }
remoteDialUpModemBaudRate               OBJECT-TYPE
    SYNTAX      DellUnsigned32BitRange
    ACCESS      read-write
    STATUS      mandatory
    DESCRIPTION
"1700.0040.0001.0013 This attribute defines the baud rate for the modem
used by this Remote Access Dial Up functionality."
    ::= { remoteDialUpTableEntry 13 }
remoteDialUpModemPort                   OBJECT-TYPE
    SYNTAX      DellUnsigned32BitRange
    ACCESS      read-write
    STATUS      mandatory
    DESCRIPTION
"1700.0040.0001.0014 This attribute defines the port for the modem
used by this Remote Access Dial Up functionality."
    ::= { remoteDialUpTableEntry 14 }


-------------------------------------------------------------------------------
-- Remote User Dial In Configuration Table
-------------------------------------------------------------------------------

DellRemoteUserDialInStateCapabilities   ::= INTEGER {
    -- If set to 0 (zero) the object has no capabilities
    unknownCapabilities(1),             -- The object's capabilities are unknown
    -- The object's capabilities allow it to be set to:
    enableCapable(2),                   -- be disabled (offline) or be enabled (online)
    notReadyCapable(4),                 -- not ready
    dialInCallbackPresetNumberCapable(8), -- support callback with preset number
    enableAndDialInCallbackPresetNumberCapable(10),
    dialInCallbackUserSpecifiedCapable(16),-- support callback with user-specified number
    enableAndDialInCallbackUserSpecifiedCapable(18),
    dialInCallbackPresetNumberAndUserSpecifiedCapable(24),
    enableAndDialInCallbackPresetNumberAndUserSpecifiedCapable(26)
}
DellRemoteUserDialInStateSettings       ::= INTEGER {
    -- If set to 0 (zero) the object has no settings capabilities, and its state is disabled
    -- Only one dialInCallback setting may be enabled:
    unknown(1),                         -- The object's state is unknown
    enabled(2),                         -- The object's state is disabled (offline) 0, or enabled (online) 1
    notReady(4),                        -- The object's state is not ready
    dialInCallbackPresetNumberEnabled(8), -- Callback with preset number enabled
    enabledAndDialInCallbackPresetNumberEnabled(10),
    dialInCallbackUserSpecifiedEnabled(16),-- Callback with user-specified number enabled
    enabledAndDialInCallbackUserSpecifiedEnabled(18)
}

RemoteUserDialInCfgTableEntry                  ::= SEQUENCE {
    remoteUserDialInCfgChassisIndex            DellObjectRange,
    remoteUserDialInCfgAdapterIndex            DellObjectRange,
    remoteUserDialInCfgUserIndex               DellObjectRange,
    remoteUserDialInCfgStateCapabilities       DellRemoteUserDialInStateCapabilities,
    remoteUserDialInCfgStateSettings           DellRemoteUserDialInStateSettings,
    remoteUserDialInCfgStatus                  DellStatus,
    remoteUserDialInCfgPPPUserName             DisplayString (SIZE (0..15)),
    remoteUserDialInCfgPPPUserPasswordName     DisplayString (SIZE (0..15)),
    remoteUserDialInCfgCallbackPhoneNumberName DisplayString (SIZE (0..95))
}

remoteUserDialInCfgTable                OBJECT-TYPE
    SYNTAX      SEQUENCE OF RemoteUserDialInCfgTableEntry
    ACCESS      not-accessible
    STATUS      mandatory
    DESCRIPTION
"1700.0050 This object defines the Remote Access User Dial In Configuration
table."
    ::= { remoteAccessGroup 50 }
remoteUserDialInCfgTableEntry           OBJECT-TYPE
    SYNTAX      RemoteUserDialInCfgTableEntry
    ACCESS      not-accessible
    STATUS      mandatory
    DESCRIPTION
"1700.0050.0001 This object defines the Remote Access User Dial In Configuration
table entry."
    INDEX       { remoteUserDialInCfgChassisIndex,
	              remoteUserDialInCfgAdapterIndex,
				  remoteUserDialInCfgUserIndex }
    ::= { remoteUserDialInCfgTable 1 }
remoteUserDialInCfgChassisIndex         OBJECT-TYPE
    SYNTAX      DellObjectRange
    ACCESS      read-only
    STATUS      mandatory
    DESCRIPTION
"1700.0050.0001.0001 This attribute defines the index (one based) of the
chassis containing the Remote Access hardware."
    ::= { remoteUserDialInCfgTableEntry 1 }
remoteUserDialInCfgAdapterIndex         OBJECT-TYPE
    SYNTAX      DellObjectRange
    ACCESS      read-only
    STATUS      mandatory
    DESCRIPTION
"1700.0050.0001.0002 This attribute defines the index (one based) of
Remote Access hardware that supports this Remote Access Dial In user."
    ::= { remoteUserDialInCfgTableEntry 2 }
remoteUserDialInCfgUserIndex            OBJECT-TYPE
    SYNTAX      DellObjectRange
    ACCESS      read-only
    STATUS      mandatory
    DESCRIPTION
"1700.0050.0001.0003 This attribute defines the index (one based) of this
Remote Access Dial In user."
    ::= { remoteUserDialInCfgTableEntry 3 }
remoteUserDialInCfgStateCapabilities    OBJECT-TYPE
    SYNTAX      DellRemoteUserDialInStateCapabilities
    ACCESS      read-only
    STATUS      mandatory
    DESCRIPTION
"1700.0050.0001.0004 This attribute defines the state capabilities of this
Remote Access Dial In user."
    ::= { remoteUserDialInCfgTableEntry 4 }
remoteUserDialInCfgStateSettings        OBJECT-TYPE
    SYNTAX      DellRemoteUserDialInStateSettings
    ACCESS      read-write
    STATUS      mandatory
    DESCRIPTION
"1700.0050.0001.0005 This attribute defines the state settings of this
Remote Access Dial In user."
    ::= { remoteUserDialInCfgTableEntry 5 }
remoteUserDialInCfgStatus               OBJECT-TYPE
    SYNTAX      DellStatus
    ACCESS      read-only
    STATUS      mandatory
    DESCRIPTION
"1700.0050.0001.0006 This attribute defines the status of this
Remote Access Dial In user."
    ::= { remoteUserDialInCfgTableEntry 6 }
remoteUserDialInCfgPPPUserName          OBJECT-TYPE
    SYNTAX      DisplayString (SIZE (0..15))
    ACCESS      read-write
    STATUS      mandatory
    DESCRIPTION
"1700.0050.0001.0007 This attribute defines the PPP user name of this
Remote Access Dial In user."
    ::= { remoteUserDialInCfgTableEntry 7 }
remoteUserDialInCfgPPPUserPasswordName  OBJECT-TYPE
    SYNTAX      DisplayString (SIZE (0..15))
    ACCESS      read-write
    STATUS      mandatory
    DESCRIPTION
"1700.0050.0001.0008 This attribute defines the PPP password for this
Remote Access Dial In user."
    ::= { remoteUserDialInCfgTableEntry 8 }
remoteUserDialInCfgCallbackPhoneNumberName OBJECT-TYPE
    SYNTAX      DisplayString (SIZE (0..95))
    ACCESS      read-write
    STATUS      mandatory
    DESCRIPTION
"1700.0050.0001.0009 This attribute defines the callback phone number for this
Remote Access Dial In user."
    ::= { remoteUserDialInCfgTableEntry 9 }


-------------------------------------------------------------------------------
-- Remote Dial Out Table
-------------------------------------------------------------------------------

DellRemoteDialOutStateCapabilities      ::= INTEGER {
    -- If set to 0 (zero) the object has no capabilities
    unknownCapabilities(1),             -- The object's capabilities are unknown
    -- The object's capabilities allow it to be set to:
    enableCapable(2),                   -- be disabled (offline) or be enabled (online)
    notReadyCapable(4),                 -- not ready
    dialOutPPPAuthAnyCapable(8),        -- support "any PPP auth including clear text"
    dialOutPPPAuthEncryptedCapable(16), -- support "require encrypted PPP Password"
    dialOutPPPAuthAnyAndEncryptedCapable(24),
    dialOutPPPAuthMschapCapable(32),    -- support "require MSCHAP"
    dialOutPPPAuthAnyAndMschapCapable(40),
    dialOutPPPAuthEncryptedAndMschapCapable(48),
    dialOutPPPAuthAnyEncryptedAndMschapCapable(56)
}
DellRemoteDialOutStateSettings          ::= INTEGER {
    -- If set to 0 (zero) the object has no settings capabilities, and its state is disabled
    -- One and only one dialOutPPPAuth setting must be enabled:
    unknown(1),                         -- The object's state is unknown
    enabled(2),                         -- The object's state is disabled (offline) 0, or enabled (online) 1
    notReady(4),                        -- The object's state is not ready
    dialOutPPPAuthAnyEnabled(8),        -- Ojbect supports "use any PPP authentication including clear text"
    enabledAnddialOutPPPAuthAnyEnabled(10),
    dialOutPPPAuthEncryptedEnabled(16), -- Object supports "require encrypted PPP Authentication"
    enabledAnddialOutPPPAuthEncryptedEnabled(18),
    dialOutPPPAuthMschapEnabled(32),    -- Object supports "require MSCHAP PPP Authentication"
    enabledAnddialOutPPPAuthMschapEnabled(34)
}

RemoteDialOutTableEntry                 ::= SEQUENCE {
    remoteDialOutChassisIndex           DellObjectRange,
    remoteDialOutAdapterIndex           DellObjectRange,
    remoteDialOutDialOutIndex           DellObjectRange,
    remoteDialOutStateCapabilities      DellRemoteDialOutStateCapabilities,
    remoteDialOutStateSettings          DellRemoteDialOutStateSettings,
    remoteDialOutStatus                 DellStatus,
    remoteDialOutIPAddress              IpAddress,
    remoteDialOutPhoneNumberName        DisplayString (SIZE (0..95)),
    remoteDialOutPPPUserName            DisplayString (SIZE (0..31)),
    remoteDialOutPPPPasswordName        DisplayString (SIZE (0..31))
}

remoteDialOutTable                      OBJECT-TYPE
    SYNTAX      SEQUENCE OF RemoteDialOutTableEntry
    ACCESS      not-accessible
    STATUS      mandatory
    DESCRIPTION
"1700.0060 This object defines the Remote Access Dial Out table."
    ::= { remoteAccessGroup 60 }
remoteDialOutTableEntry                 OBJECT-TYPE
    SYNTAX      RemoteDialOutTableEntry
    ACCESS      not-accessible
    STATUS      mandatory
    DESCRIPTION
"1700.0060.0001 This object defines the Remote Access Dial Out table entry."
    INDEX       { remoteDialOutChassisIndex,
	              remoteDialOutAdapterIndex,
				  remoteDialOutDialOutIndex }
    ::= { remoteDialOutTable 1 }
remoteDialOutChassisIndex               OBJECT-TYPE
    SYNTAX      DellObjectRange
    ACCESS      read-only
    STATUS      mandatory
    DESCRIPTION
"1700.0060.0001.0001 This attribute defines the index (one based) of the
chassis containing the Remote Access hardware."
    ::= { remoteDialOutTableEntry 1 }
remoteDialOutAdapterIndex               OBJECT-TYPE
    SYNTAX      DellObjectRange
    ACCESS      read-only
    STATUS      mandatory
    DESCRIPTION
"1700.0060.0001.0002 This attribute defines the index (one based) of the
Remote Access hardware that supports this Remote Access Dial Out functionality."
    ::= { remoteDialOutTableEntry 2 }
remoteDialOutDialOutIndex               OBJECT-TYPE
    SYNTAX      DellObjectRange
    ACCESS      read-only
    STATUS      mandatory
    DESCRIPTION
"1700.0060.0001.0003 This attribute defines the index (one based) of this
Remote Access Dial Out functionality."
    ::= { remoteDialOutTableEntry 3 }
remoteDialOutStateCapabilities          OBJECT-TYPE
    SYNTAX      DellRemoteDialOutStateCapabilities
    ACCESS      read-only
    STATUS      mandatory
    DESCRIPTION
"1700.0060.0001.0004 This attribute defines the state capabilities of this
Remote Access Dial Out functionality."
    ::= { remoteDialOutTableEntry 4 }
remoteDialOutStateSettings              OBJECT-TYPE
    SYNTAX      DellRemoteDialOutStateSettings
    ACCESS      read-write
    STATUS      mandatory
    DESCRIPTION
"1700.0060.0001.0005 This attribute defines the state settings of this
Remote Access Dial Out functionality."
    ::= { remoteDialOutTableEntry 5 }
remoteDialOutStatus                     OBJECT-TYPE
    SYNTAX      DellStatus
    ACCESS      read-only
    STATUS      mandatory
    DESCRIPTION
"1700.0060.0001.0006 This attribute defines the status of this
Remote Dial Out functionality."
    ::= { remoteDialOutTableEntry 6 }
remoteDialOutIPAddress                  OBJECT-TYPE
    SYNTAX      IpAddress
    ACCESS      read-write
    STATUS      mandatory
    DESCRIPTION
"1700.0060.0001.0007 This attribute defines the IP address for this
Remote Access Dial Out destination."
    ::= { remoteDialOutTableEntry 7 }
remoteDialOutPhoneNumberName            OBJECT-TYPE
    SYNTAX      DisplayString (SIZE (0..95))
    ACCESS      read-write
    STATUS      mandatory
    DESCRIPTION
"1700.0060.0001.0008 This attribute defines the phone number for this
Remote Access Dial Out destination."
    ::= { remoteDialOutTableEntry 8 }
remoteDialOutPPPUserName                OBJECT-TYPE
    SYNTAX      DisplayString (SIZE (0..31))
    ACCESS      read-write
    STATUS      mandatory
    DESCRIPTION
"1700.0060.0001.0009 This attribute defines the PPP user name for this
Remote Access Dial Out destination."
    ::= { remoteDialOutTableEntry 9 }
remoteDialOutPPPPasswordName            OBJECT-TYPE
    SYNTAX      DisplayString (SIZE (0..31))
    ACCESS      read-write
    STATUS      mandatory
    DESCRIPTION
"1700.0060.0001.0010 This attribute defines the PPP password for this
Remote Access Dial Out destination."
    ::= { remoteDialOutTableEntry 10 }


-------------------------------------------------------------------------------
--
-- Alert Group
--
-------------------------------------------------------------------------------

-------------------------------------------------------------------------------
-- Alert Variables
-------------------------------------------------------------------------------

alertVariables                  OBJECT IDENTIFIER ::= { alertGroup     10    }

alertSystem                     OBJECT-TYPE
    SYNTAX      DisplayString (SIZE (0..255))
    ACCESS      read-only
    STATUS      mandatory
    DESCRIPTION
"5000.0010.0001 Name of the system generating the alert."
    ::= { alertVariables 1 }

alertTableIndexOID              OBJECT-TYPE
    SYNTAX      OBJECT IDENTIFIER
    ACCESS      read-only
    STATUS      mandatory
    DESCRIPTION
"5000.0010.0002 OID for the index attribute in the table that contains the object
causing the alert.  This value can be used to uniquely identify the object
causing the alert and to correlate different alerts caused by an object.
If not applicable, the value will be 0.0."
    ::= { alertVariables 2 }

alertMessage                    OBJECT-TYPE
    SYNTAX      DisplayString (SIZE (0..1024))
    ACCESS      read-only
    STATUS      mandatory
    DESCRIPTION
"5000.0010.0003 Message describing the alert."
    ::= { alertVariables 3 }

alertCurrentStatus              OBJECT-TYPE
    SYNTAX      DellStatus
    ACCESS      read-only
    STATUS      mandatory
    DESCRIPTION
"5000.0010.0004 Current status of object causing the alert."
    ::= { alertVariables 4 }

alertPreviousStatus             OBJECT-TYPE
    SYNTAX      DellStatus
    ACCESS      read-only
    STATUS      mandatory
    DESCRIPTION
"5000.0010.0005 Previous status of object causing the alert."
    ::= { alertVariables 5 }

alertData                       OBJECT-TYPE
    SYNTAX      OCTET STRING (SIZE (0..1024))
    ACCESS      read-only
    STATUS      mandatory
    DESCRIPTION
"5000.0010.0006 Alert data."
    ::= { alertVariables 6 }


-------------------------------------------------------------------------------
-- Alerts
-------------------------------------------------------------------------------

alertSystemUp                       TRAP-TYPE
    ENTERPRISE  baseboardGroup
    VARIABLES { alertSystem,
                alertTableIndexOID,
                alertMessage,
                alertCurrentStatus,
                alertPreviousStatus,
                alertData }
    DESCRIPTION
"Server Administrator has completed its initialization."

    --Novell NMS trap annotation
    --#TYPE       "Server Administrator Startup Complete"
    --#SUMMARY    "%s"
    --#ARGUMENTS  {2}
    --#SEVERITY   INFORMATIONAL
    --#TIMEINDEX  99
    --#STATE      OPERATIONAL

    ::= 1001

alertThermalShutdown                TRAP-TYPE
    ENTERPRISE  baseboardGroup
    VARIABLES { alertSystem,
                alertTableIndexOID,
                alertMessage,
                alertCurrentStatus,
                alertPreviousStatus,
                alertData }
    DESCRIPTION
"Thermal shutdown protection has been initiated."

    --Novell NMS trap annotation
    --#TYPE       "Server Thermal Shutdown"
    --#SUMMARY    "%s"
    --#ARGUMENTS  {2}
    --#SEVERITY   CRITICAL
    --#TIMEINDEX  99
    --#STATE      NONOPERATIONAL

    ::= 1004

alertTemperatureProbeNormal         TRAP-TYPE
    ENTERPRISE  baseboardGroup
    VARIABLES { alertSystem,
                alertTableIndexOID,
                alertMessage,
                alertCurrentStatus,
                alertPreviousStatus,
                alertData }
    DESCRIPTION
"Temperature probe has returned to a normal value."

    --Novell NMS trap annotation
    --#TYPE       "Server Temperature Normal"
    --#SUMMARY    "%s"
    --#ARGUMENTS  {2}
    --#SEVERITY   INFORMATIONAL
    --#TIMEINDEX  99
    --#STATE      OPERATIONAL

    ::= 1052

alertTemperatureProbeWarning        TRAP-TYPE
    ENTERPRISE  baseboardGroup
    VARIABLES { alertSystem,
                alertTableIndexOID,
                alertMessage,
                alertCurrentStatus,
                alertPreviousStatus,
                alertData }
    DESCRIPTION
"Temperature probe has detected a warning value."

    --Novell NMS trap annotation
    --#TYPE       "Server Temperature Warning"
    --#SUMMARY    "%s"
    --#ARGUMENTS  {2}
    --#SEVERITY   MINOR
    --#TIMEINDEX  99
    --#STATE      DEGRADED

    ::= 1053

alertTemperatureProbeFailure        TRAP-TYPE
    ENTERPRISE  baseboardGroup
    VARIABLES { alertSystem,
                alertTableIndexOID,
                alertMessage,
                alertCurrentStatus,
                alertPreviousStatus,
                alertData }
    DESCRIPTION
"Temperature probe has detected a failure value."

    --Novell NMS trap annotation
    --#TYPE       "Server Temperature Failure"
    --#SUMMARY    "%s"
    --#ARGUMENTS  {2}
    --#SEVERITY   CRITICAL
    --#TIMEINDEX  99
    --#STATE      DEGRADED

    ::= 1054

alertTemperatureProbeNonRecoverable TRAP-TYPE
    ENTERPRISE  baseboardGroup
    VARIABLES { alertSystem,
                alertTableIndexOID,
                alertMessage,
                alertCurrentStatus,
                alertPreviousStatus,
                alertData }
    DESCRIPTION
"Temperature probe has detected a non-recoverable value."

    --Novell NMS trap annotation
    --#TYPE       "Server Temperature Non-recoverable"
    --#SUMMARY    "%s"
    --#ARGUMENTS  {2}
    --#SEVERITY   CRITICAL
    --#TIMEINDEX  99
    --#STATE      DEGRADED

    ::= 1055

alertCoolingDeviceNormal            TRAP-TYPE
    ENTERPRISE  baseboardGroup
    VARIABLES { alertSystem,
                alertTableIndexOID,
                alertMessage,
                alertCurrentStatus,
                alertPreviousStatus,
                alertData }
    DESCRIPTION
"Cooling device sensor has returned to a normal value."

    --Novell NMS trap annotation
    --#TYPE       "Server Cooling Device Normal"
    --#SUMMARY    "%s"
    --#ARGUMENTS  {2}
    --#SEVERITY   INFORMATIONAL
    --#TIMEINDEX  99
    --#STATE      OPERATIONAL

    ::= 1102

alertCoolingDeviceWarning           TRAP-TYPE
    ENTERPRISE  baseboardGroup
    VARIABLES { alertSystem,
                alertTableIndexOID,
                alertMessage,
                alertCurrentStatus,
                alertPreviousStatus,
                alertData }
    DESCRIPTION
"Cooling device sensor has detected a warning value."

    --Novell NMS trap annotation
    --#TYPE       "Server Cooling Device Warning"
    --#SUMMARY    "%s"
    --#ARGUMENTS  {2}
    --#SEVERITY   MINOR
    --#TIMEINDEX  99
    --#STATE      DEGRADED

    ::= 1103

alertCoolingDeviceFailure           TRAP-TYPE
    ENTERPRISE  baseboardGroup
    VARIABLES { alertSystem,
                alertTableIndexOID,
                alertMessage,
                alertCurrentStatus,
                alertPreviousStatus,
                alertData }
    DESCRIPTION
"Cooling device sensor has detected a failure value."

    --Novell NMS trap annotation
    --#TYPE       "Server Cooling Device Failure"
    --#SUMMARY    "%s"
    --#ARGUMENTS  {2}
    --#SEVERITY   CRITICAL
    --#TIMEINDEX  99
    --#STATE      DEGRADED

    ::= 1104

alertCoolingDeviceNonRecoverable    TRAP-TYPE
    ENTERPRISE  baseboardGroup
    VARIABLES { alertSystem,
                alertTableIndexOID,
                alertMessage,
                alertCurrentStatus,
                alertPreviousStatus,
                alertData }
    DESCRIPTION
"Cooling device sensor has detected a non-recoverable value."

    --Novell NMS trap annotation
    --#TYPE       "Server Cooling Device Non-recoverable"
    --#SUMMARY    "%s"
    --#ARGUMENTS  {2}
    --#SEVERITY   CRITICAL
    --#TIMEINDEX  99
    --#STATE      DEGRADED

    ::= 1105

alertVoltageProbeNormal             TRAP-TYPE
    ENTERPRISE  baseboardGroup
    VARIABLES { alertSystem,
                alertTableIndexOID,
                alertMessage,
                alertCurrentStatus,
                alertPreviousStatus,
                alertData }
    DESCRIPTION
"Voltage probe has returned to a normal value."

    --Novell NMS trap annotation
    --#TYPE       "Server Voltage Normal"
    --#SUMMARY    "%s"
    --#ARGUMENTS  {2}
    --#SEVERITY   INFORMATIONAL
    --#TIMEINDEX  99
    --#STATE      OPERATIONAL

    ::= 1152

alertVoltageProbeWarning            TRAP-TYPE
    ENTERPRISE  baseboardGroup
    VARIABLES { alertSystem,
                alertTableIndexOID,
                alertMessage,
                alertCurrentStatus,
                alertPreviousStatus,
                alertData }
    DESCRIPTION
"Voltage probe has detected a warning value."

    --Novell NMS trap annotation
    --#TYPE       "Server Voltage Warning"
    --#SUMMARY    "%s"
    --#ARGUMENTS  {2}
    --#SEVERITY   MINOR
    --#TIMEINDEX  99
    --#STATE      DEGRADED

    ::= 1153

alertVoltageProbeFailure            TRAP-TYPE
    ENTERPRISE  baseboardGroup
    VARIABLES { alertSystem,
                alertTableIndexOID,
                alertMessage,
                alertCurrentStatus,
                alertPreviousStatus,
                alertData }
    DESCRIPTION
"Voltage probe has detected a failure value."

    --Novell NMS trap annotation
    --#TYPE       "Server Voltage Failure"
    --#SUMMARY    "%s"
    --#ARGUMENTS  {2}
    --#SEVERITY   CRITICAL
    --#TIMEINDEX  99
    --#STATE      DEGRADED

    ::= 1154

alertVoltageProbeNonRecoverable     TRAP-TYPE
    ENTERPRISE  baseboardGroup
    VARIABLES { alertSystem,
                alertTableIndexOID,
                alertMessage,
                alertCurrentStatus,
                alertPreviousStatus,
                alertData }
    DESCRIPTION
"Voltage probe has detected a non-recoverable value."

    --Novell NMS trap annotation
    --#TYPE       "Server Voltage Non-recoverable"
    --#SUMMARY    "%s"
    --#ARGUMENTS  {2}
    --#SEVERITY   CRITICAL
    --#TIMEINDEX  99
    --#STATE      DEGRADED

    ::= 1155

alertAmperageProbeNormal            TRAP-TYPE
    ENTERPRISE  baseboardGroup
    VARIABLES { alertSystem,
                alertTableIndexOID,
                alertMessage,
                alertCurrentStatus,
                alertPreviousStatus,
                alertData }
    DESCRIPTION
"Amperage probe has returned to a normal value."

    --Novell NMS trap annotation
    --#TYPE       "Server Amperage Normal"
    --#SUMMARY    "%s"
    --#ARGUMENTS  {2}
    --#SEVERITY   INFORMATIONAL
    --#TIMEINDEX  99
    --#STATE      OPERATIONAL

    ::= 1202

alertAmperageProbeWarning           TRAP-TYPE
    ENTERPRISE  baseboardGroup
    VARIABLES { alertSystem,
                alertTableIndexOID,
                alertMessage,
                alertCurrentStatus,
                alertPreviousStatus,
                alertData }
    DESCRIPTION
"Amperage probe has detected a warning value."

    --Novell NMS trap annotation
    --#TYPE       "Server Amperage Warning"
    --#SUMMARY    "%s"
    --#ARGUMENTS  {2}
    --#SEVERITY   MINOR
    --#TIMEINDEX  99
    --#STATE      DEGRADED

    ::= 1203

alertAmperageProbeFailure           TRAP-TYPE
    ENTERPRISE  baseboardGroup
    VARIABLES { alertSystem,
                alertTableIndexOID,
                alertMessage,
                alertCurrentStatus,
                alertPreviousStatus,
                alertData }
    DESCRIPTION
"Amperage probe has detected a failure value."

    --Novell NMS trap annotation
    --#TYPE       "Server Amperage Failure"
    --#SUMMARY    "%s"
    --#ARGUMENTS  {2}
    --#SEVERITY   CRITICAL
    --#TIMEINDEX  99
    --#STATE      DEGRADED

    ::= 1204

alertAmperageProbeNonRecoverable    TRAP-TYPE
    ENTERPRISE  baseboardGroup
    VARIABLES { alertSystem,
                alertTableIndexOID,
                alertMessage,
                alertCurrentStatus,
                alertPreviousStatus,
                alertData }
    DESCRIPTION
"Amperage probe has detected a non-recoverable value."

    --Novell NMS trap annotation
    --#TYPE       "Server Amperage Non-recoverable"
    --#SUMMARY    "%s"
    --#ARGUMENTS  {2}
    --#SEVERITY   CRITICAL
    --#TIMEINDEX  99
    --#STATE      DEGRADED

    ::= 1205

alertChassisIntrusionNormal         TRAP-TYPE
    ENTERPRISE  baseboardGroup
    VARIABLES { alertSystem,
                alertTableIndexOID,
                alertMessage,
                alertCurrentStatus,
                alertPreviousStatus,
                alertData }
    DESCRIPTION
"Chassis intrusion has returned to normal."

    --Novell NMS trap annotation
    --#TYPE       "Server Chassis Intrusion Normal"
    --#SUMMARY    "%s"
    --#ARGUMENTS  {2}
    --#SEVERITY   INFORMATIONAL
    --#TIMEINDEX  99
    --#STATE      OPERATIONAL

    ::= 1252

alertChassisIntrusionDetected       TRAP-TYPE
    ENTERPRISE  baseboardGroup
    VARIABLES { alertSystem,
                alertTableIndexOID,
                alertMessage,
                alertCurrentStatus,
                alertPreviousStatus,
                alertData }
    DESCRIPTION
"Chassis intrusion has been detected."

    --Novell NMS trap annotation
    --#TYPE       "Server Chassis Intrusion Detected"
    --#SUMMARY    "%s"
    --#ARGUMENTS  {2}
    --#SEVERITY   CRITICAL
    --#TIMEINDEX  99
    --#STATE      OPERATIONAL

    ::= 1254

alertRedundancyNormal               TRAP-TYPE
    ENTERPRISE  baseboardGroup
    VARIABLES { alertSystem,
                alertTableIndexOID,
                alertMessage,
                alertCurrentStatus,
                alertPreviousStatus,
                alertData }
    DESCRIPTION
"Redundancy has returned to normal."

    --Novell NMS trap annotation
    --#TYPE       "Server Redundancy Normal"
    --#SUMMARY    "%s"
    --#ARGUMENTS  {2}
    --#SEVERITY   INFORMATIONAL
    --#TIMEINDEX  99
    --#STATE      OPERATIONAL

    ::= 1304

alertRedundancyDegraded             TRAP-TYPE
    ENTERPRISE  baseboardGroup
    VARIABLES { alertSystem,
                alertTableIndexOID,
                alertMessage,
                alertCurrentStatus,
                alertPreviousStatus,
                alertData }
    DESCRIPTION
"Redundancy has been degraded."

    --Novell NMS trap annotation
    --#TYPE       "Server Redundancy Degraded"
    --#SUMMARY    "%s"
    --#ARGUMENTS  {2}
    --#SEVERITY   MINOR
    --#TIMEINDEX  99
    --#STATE      DEGRADED

    ::= 1305

alertRedundancyLost                 TRAP-TYPE
    ENTERPRISE  baseboardGroup
    VARIABLES { alertSystem,
                alertTableIndexOID,
                alertMessage,
                alertCurrentStatus,
                alertPreviousStatus,
                alertData }
    DESCRIPTION
"Redundancy has been lost."

    --Novell NMS trap annotation
    --#TYPE       "Server Redundancy Lost"
    --#SUMMARY    "%s"
    --#ARGUMENTS  {2}
    --#SEVERITY   MAJOR
    --#TIMEINDEX  99
    --#STATE      DEGRADED

    ::= 1306

alertPowerSupplyNormal              TRAP-TYPE
    ENTERPRISE  baseboardGroup
    VARIABLES { alertSystem,
                alertTableIndexOID,
                alertMessage,
                alertCurrentStatus,
                alertPreviousStatus,
                alertData }
    DESCRIPTION
"Power supply has returned to normal."

    --Novell NMS trap annotation
    --#TYPE       "Server Power Supply Normal"
    --#SUMMARY    "%s"
    --#ARGUMENTS  {2}
    --#SEVERITY   INFORMATIONAL
    --#TIMEINDEX  99
    --#STATE      OPERATIONAL

    ::= 1352

alertPowerSupplyFailure             TRAP-TYPE
    ENTERPRISE  baseboardGroup
    VARIABLES { alertSystem,
                alertTableIndexOID,
                alertMessage,
                alertCurrentStatus,
                alertPreviousStatus,
                alertData }
    DESCRIPTION
"Power supply has failed."

    --Novell NMS trap annotation
    --#TYPE       "Server Power Supply Failure"
    --#SUMMARY    "%s"
    --#ARGUMENTS  {2}
    --#SEVERITY   CRITICAL
    --#TIMEINDEX  99
    --#STATE      DEGRADED

    ::= 1354

alertMemoryDeviceWarning            TRAP-TYPE
    ENTERPRISE  baseboardGroup
    VARIABLES { alertSystem,
                alertTableIndexOID,
                alertMessage,
                alertCurrentStatus,
                alertPreviousStatus,
                alertData }
    DESCRIPTION
"Memory device ECC correctable error count crossed a warning threshold."

    --Novell NMS trap annotation
    --#TYPE       "Server Memory ECC Count Warning"
    --#SUMMARY    "%s"
    --#ARGUMENTS  {2}
    --#SEVERITY   MINOR
    --#TIMEINDEX  99
    --#STATE      DEGRADED

    ::= 1403

alertMemoryDeviceFailure            TRAP-TYPE
    ENTERPRISE  baseboardGroup
    VARIABLES { alertSystem,
                alertTableIndexOID,
                alertMessage,
                alertCurrentStatus,
                alertPreviousStatus,
                alertData }
    DESCRIPTION
"Memory device ECC correctable error count crossed a failure threshold."

    --Novell NMS trap annotation
    --#TYPE       "Server Memory ECC Count Failure"
    --#SUMMARY    "%s"
    --#ARGUMENTS  {2}
    --#SEVERITY   CRITICAL
    --#TIMEINDEX  99
    --#STATE      DEGRADED

    ::= 1404

alertMemoryDeviceNonRecoverable     TRAP-TYPE
    ENTERPRISE  baseboardGroup
    VARIABLES { alertSystem,
                alertTableIndexOID,
                alertMessage,
                alertCurrentStatus,
                alertPreviousStatus,
                alertData }
    DESCRIPTION
"Memory device ECC correctable error count crossed a non-recoverable threshold."

    --Novell NMS trap annotation
    --#TYPE       "Server Memory ECC Count Non-recoverable"
    --#SUMMARY    "%s"
    --#ARGUMENTS  {2}
    --#SEVERITY   CRITICAL
    --#TIMEINDEX  99
    --#STATE      DEGRADED

    ::= 1405

alertFanEnclosureInsertion          TRAP-TYPE
    ENTERPRISE  baseboardGroup
    VARIABLES { alertSystem,
                alertTableIndexOID,
                alertMessage,
                alertCurrentStatus,
                alertPreviousStatus,
                alertData }
    DESCRIPTION
"Fan enclosure has been inserted into system."

    --Novell NMS trap annotation
    --#TYPE       "Server Fan Enclosure Insertion"
    --#SUMMARY    "%s"
    --#ARGUMENTS  {2}
    --#SEVERITY   INFORMATIONAL
    --#TIMEINDEX  99
    --#STATE      OPERATIONAL

    ::= 1452

alertFanEnclosureRemoval            TRAP-TYPE
    ENTERPRISE  baseboardGroup
    VARIABLES { alertSystem,
                alertTableIndexOID,
                alertMessage,
                alertCurrentStatus,
                alertPreviousStatus,
                alertData }
    DESCRIPTION
"Fan enclosure has been removed from system."

    --Novell NMS trap annotation
    --#TYPE       "Server Fan Enclosure Removal"
    --#SUMMARY    "%s"
    --#ARGUMENTS  {2}
    --#SEVERITY   MINOR
    --#TIMEINDEX  99
    --#STATE      DEGRADED

    ::= 1453

alertFanEnclosureExtendedRemoval    TRAP-TYPE
    ENTERPRISE  baseboardGroup
    VARIABLES { alertSystem,
                alertTableIndexOID,
                alertMessage,
                alertCurrentStatus,
                alertPreviousStatus,
                alertData }
    DESCRIPTION
"Fan enclosure has been removed from system for an extended amount of time."

    --Novell NMS trap annotation
    --#TYPE       "Server Fan Enclosure Extended Removal"
    --#SUMMARY    "%s"
    --#ARGUMENTS  {2}
    --#SEVERITY   CRITICAL
    --#TIMEINDEX  99
    --#STATE      DEGRADED

    ::= 1454

alertACPowerCordNoPowerNonRedundant TRAP-TYPE
    ENTERPRISE  baseboardGroup
    VARIABLES { alertSystem,
                alertTableIndexOID,
                alertMessage,
                alertCurrentStatus,
                alertPreviousStatus,
                alertData }
    DESCRIPTION
"AC power cord does not have power, and the reduncancy mode
for its AC power switch has been set to non-redundant."

    --Novell NMS trap annotation
    --#TYPE       "Server AC Cord No Power Non-redundant"
    --#SUMMARY    "%s"
    --#ARGUMENTS  {2}
    --#SEVERITY   INFORMATIONAL
    --#TIMEINDEX  99
    --#STATE      OPERATIONAL

    ::= 1501

alertACPowerCordNormal              TRAP-TYPE
    ENTERPRISE  baseboardGroup
    VARIABLES { alertSystem,
                alertTableIndexOID,
                alertMessage,
                alertCurrentStatus,
                alertPreviousStatus,
                alertData }
    DESCRIPTION
"AC power cord has regained power."

    --Novell NMS trap annotation
    --#TYPE       "Server AC Cord Normal"
    --#SUMMARY    "%s"
    --#ARGUMENTS  {2}
    --#SEVERITY   INFORMATIONAL
    --#TIMEINDEX  99
    --#STATE      OPERATIONAL

    ::= 1502

alertACPowerCordFailure             TRAP-TYPE
    ENTERPRISE  baseboardGroup
    VARIABLES { alertSystem,
                alertTableIndexOID,
                alertMessage,
                alertCurrentStatus,
                alertPreviousStatus,
                alertData }
    DESCRIPTION
"AC power cord has lost power."

    --Novell NMS trap annotation
    --#TYPE       "Server AC Cord Failure"
    --#SUMMARY    "%s"
    --#ARGUMENTS  {2}
    --#SEVERITY   CRITICAL
    --#TIMEINDEX  99
    --#STATE      DEGRADED

    ::= 1504

alertLogNormal                      TRAP-TYPE
    ENTERPRISE  baseboardGroup
    VARIABLES { alertSystem,
                alertTableIndexOID,
                alertMessage,
                alertCurrentStatus,
                alertPreviousStatus,
                alertData }
    DESCRIPTION
"Log size returned to a normal level."

    --Novell NMS trap annotation
    --#TYPE       "Server Log Normal"
    --#SUMMARY    "%s"
    --#ARGUMENTS  {2}
    --#SEVERITY   INFORMATIONAL
    --#TIMEINDEX  99
    --#STATE      OPERATIONAL

    ::= 1552

alertLogWarning                     TRAP-TYPE
    ENTERPRISE  baseboardGroup
    VARIABLES { alertSystem,
                alertTableIndexOID,
                alertMessage,
                alertCurrentStatus,
                alertPreviousStatus,
                alertData }
    DESCRIPTION
"Log size is near or at capacity."

    --Novell NMS trap annotation
    --#TYPE       "Server Log Warning"
    --#SUMMARY    "%s"
    --#ARGUMENTS  {2}
    --#SEVERITY   MINOR
    --#TIMEINDEX  99
    --#STATE      OPERATIONAL

    ::= 1553

END
