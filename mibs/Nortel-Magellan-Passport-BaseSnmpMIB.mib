Nortel-Magellan-Passport-BaseSnmpMIB
DEFINITIONS ::= BEGIN



IMPORTS

      OBJECT-TYPE
   FROM RFC-1212

      IpAddress
   FROM RFC1155-SMI

      passportMIBs
   FROM Nortel-Magellan-Passport-UsefulDefinitionsMIB

      TruthValue,
      DisplayString,
      StorageType,
      RowStatus,
      Status,
      Integer32,
      Unsigned32
   FROM Nortel-Magellan-Passport-StandardTextualConventionsMIB

      AsciiString,
      NonReplicated,
      HexString
   FROM Nortel-Magellan-Passport-TextualConventionsMIB

      vrIndex,
      vr
   FROM Nortel-Magellan-Passport-VirtualRouterMIB;




-- LAST-UPDATED   "9706300000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     BaseSnmp Enterprise MIB."

baseSnmpMIB OBJECT IDENTIFIER ::= { passportMIBs 36 }










-- Vr/Vr_String Snmp
-- This component contains all provisionable and operational data 
-- relating to the SNMP Management of a Virtual Router.
-- If the Vr/Vr_String SnmpInitialConfiguration component exists and 
-- its agentAddress and managerAddress attributes have been set then 
-- when this component is added, initial instances of SnmpV2Acl, 
-- SnmpV2Party, SnmpV2Context, and SnmpView components will be 
-- added automatically.

vrSnmp OBJECT IDENTIFIER ::= { vr 8 }



vrSnmpRowStatusTable OBJECT-TYPE
   SYNTAX     SEQUENCE OF VrSnmpRowStatusEntry
   ACCESS     not-accessible
   STATUS     mandatory
   DESCRIPTION
     "This entry controls the addition and deletion of 
      vrSnmp components."
::= { vrSnmp 1 }

vrSnmpRowStatusEntry OBJECT-TYPE
   SYNTAX     VrSnmpRowStatusEntry
   ACCESS     not-accessible
   STATUS     mandatory
   DESCRIPTION
     "A single entry in the table represents a single 
      vrSnmp component."
   INDEX {
      vrIndex,
      vrSnmpIndex }
::= { vrSnmpRowStatusTable 1 }

VrSnmpRowStatusEntry ::= SEQUENCE {
   vrSnmpRowStatus
      RowStatus,
   vrSnmpComponentName
      DisplayString,
   vrSnmpStorageType
      StorageType,
   vrSnmpIndex
      NonReplicated }

vrSnmpRowStatus OBJECT-TYPE
   SYNTAX     RowStatus 
   ACCESS     read-write
   STATUS     mandatory
   DESCRIPTION
     "This variable is used as the basis for SNMP naming of
      vrSnmp components.
      These components can be added and deleted."
::= { vrSnmpRowStatusEntry 1 }

vrSnmpComponentName OBJECT-TYPE
   SYNTAX     DisplayString 
   ACCESS     read-only
   STATUS     mandatory
   DESCRIPTION
     "This variable provides the component's string name for
      use with the ASCII Console Interface"
::= { vrSnmpRowStatusEntry 2 }

vrSnmpStorageType OBJECT-TYPE
   SYNTAX     StorageType 
   ACCESS     read-only
   STATUS     mandatory
   DESCRIPTION
     "This variable represents the storage type value for the
      vrSnmp tables."
::= { vrSnmpRowStatusEntry 4 }

vrSnmpIndex OBJECT-TYPE
   SYNTAX     NonReplicated 
   ACCESS     not-accessible
   STATUS     mandatory
   DESCRIPTION
     "This variable represents the index for the vrSnmp tables."
::= { vrSnmpRowStatusEntry 10 }

vrSnmpProvTable OBJECT-TYPE
   SYNTAX     SEQUENCE OF VrSnmpProvEntry
   ACCESS     not-accessible
   STATUS     mandatory
   DESCRIPTION
     "This group contains provisionable attributes defining the SNMP 
      management entity's capabilities, particularly in regards to 
      standardV1 and V2 traps."
::= { vrSnmp 20 }

vrSnmpProvEntry OBJECT-TYPE
   SYNTAX     VrSnmpProvEntry
   ACCESS     not-accessible
   STATUS     mandatory
   DESCRIPTION
     "An entry in the vrSnmpProvTable."
   INDEX {
      vrIndex,
      vrSnmpIndex }
::= { vrSnmpProvTable 1 }

VrSnmpProvEntry ::= SEQUENCE {
   vrSnmpV1EnableAuthenTraps
      Status,
   vrSnmpV2EnableAuthenTraps
      Status,
   vrSnmpAlarmsAsTraps
      Status,
   vrSnmpIpStack
      INTEGER,
   vrSnmpCidInEntTraps
      Status }

vrSnmpV1EnableAuthenTraps OBJECT-TYPE
   SYNTAX     Status 
   ACCESS     read-write
   STATUS     mandatory
   DESCRIPTION
     "This attribute controls whether the Snmp component will generate 
      V1 authentication failure traps or not. The attribute is derived from 
      rfc1213."
::= { vrSnmpProvEntry 1 }

vrSnmpV2EnableAuthenTraps OBJECT-TYPE
   SYNTAX     Status 
   ACCESS     read-write
   STATUS     mandatory
   DESCRIPTION
     "This attribute controls whether the Snmp component will generate 
      V2 authentication failure traps or not. The attribute is derived from 
      rfc1450."
::= { vrSnmpProvEntry 2 }

vrSnmpAlarmsAsTraps OBJECT-TYPE
   SYNTAX     Status 
   ACCESS     read-write
   STATUS     mandatory
   DESCRIPTION
     "This attribute controls whether the Snmp component will send 
      Alarms as SNMPv1 and SNMPv2 Traps. If enabled, Alarms will be 
      sent as SNMPv2 Traps to target Parties identified in 
      AccessPrivileges components where v2Trap privileges are allowed, 
      and as SNMPv1 Traps to Managers with v1Trap privileges 
      allowed."
::= { vrSnmpProvEntry 3 }

vrSnmpIpStack OBJECT-TYPE
   SYNTAX     INTEGER  {
                 vrIp(1),
                 ipiFrIpiVc(2) }
   ACCESS     read-write
   STATUS     mandatory
   DESCRIPTION
     "This attribute controls which IP stack the Snmp component will use 
      to send and receive Snmp traffic for Communites and Parties whose 
      tdomain attribute specifies snmpUdpDomain as the transport 
      protocol.
      If the value of this attribute is vrIp then Snmp Udp traffic will be 
      sent and received using Ip as provisioned under the VirtualRouter. 
      This requires provisioning of the ip feature.
      If the value of this attribute is ipiFrIpiVc then Snmp Udp traffic 
      will be sent and received using IpiFr (Ip over Frame Relay) or IpiVc 
      (Ip over Vc), whichever is provisioned. This requires provisioning 
      of one of the ipiVc or ipiFr features."
   DEFVAL     { vrIp }
::= { vrSnmpProvEntry 4 }

vrSnmpCidInEntTraps OBJECT-TYPE
   SYNTAX     Status 
   ACCESS     read-write
   STATUS     mandatory
   DESCRIPTION
     "This attribute controls whether the Customer Identifier (CID) will 
      be included in the SNMP Enterprise Traps. If enabled, the CID will 
      be included in the SNMP Enterprise traps."
::= { vrSnmpProvEntry 5 }

vrSnmpStateTable OBJECT-TYPE
   SYNTAX     SEQUENCE OF VrSnmpStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { vrSnmp 21 }

vrSnmpStateEntry OBJECT-TYPE
   SYNTAX     VrSnmpStateEntry
   ACCESS     not-accessible
   STATUS     mandatory
   DESCRIPTION
     "An entry in the vrSnmpStateTable."
   INDEX {
      vrIndex,
      vrSnmpIndex }
::= { vrSnmpStateTable 1 }

VrSnmpStateEntry ::= SEQUENCE {
   vrSnmpAdminState
      INTEGER,
   vrSnmpOperationalState
      INTEGER,
   vrSnmpUsageState
      INTEGER,
   vrSnmpAvailabilityStatus
      OCTET STRING,
   vrSnmpProceduralStatus
      OCTET STRING,
   vrSnmpControlStatus
      OCTET STRING,
   vrSnmpAlarmStatus
      OCTET STRING,
   vrSnmpStandbyStatus
      INTEGER,
   vrSnmpUnknownStatus
      INTEGER }

vrSnmpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { vrSnmpStateEntry 1 }

vrSnmpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { vrSnmpStateEntry 2 }

vrSnmpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { vrSnmpStateEntry 3 }

vrSnmpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { vrSnmpStateEntry 4 }

vrSnmpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { vrSnmpStateEntry 5 }

vrSnmpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { vrSnmpStateEntry 6 }

vrSnmpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { vrSnmpStateEntry 7 }

vrSnmpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { vrSnmpStateEntry 8 }

vrSnmpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { vrSnmpStateEntry 9 }

vrSnmpStatsTable OBJECT-TYPE
   SYNTAX     SEQUENCE OF VrSnmpStatsEntry
   ACCESS     not-accessible
   STATUS     mandatory
   DESCRIPTION
     "This attribute group contains miscellaneous SNMP management 
      entity operational attributes. Statistics in the group are derived from 
      rfc 1450 and rfc 1213. Also included in the group are statistics due 
      to non-SNMP authorization errors, and non-SNMP statistics."
::= { vrSnmp 22 }

vrSnmpStatsEntry OBJECT-TYPE
   SYNTAX     VrSnmpStatsEntry
   ACCESS     not-accessible
   STATUS     mandatory
   DESCRIPTION
     "An entry in the vrSnmpStatsTable."
   INDEX {
      vrIndex,
      vrSnmpIndex }
::= { vrSnmpStatsTable 1 }

VrSnmpStatsEntry ::= SEQUENCE {
   vrSnmpLastOrChange
      Unsigned32,
   vrSnmpTrapsProcessed
      Unsigned32,
   vrSnmpTrapsDiscarded
      Unsigned32,
   vrSnmpLastAuthFailure
      Unsigned32,
   vrSnmpMgrOfLastAuthFailure
      IpAddress }

vrSnmpLastOrChange OBJECT-TYPE
   SYNTAX     Unsigned32 (0..4294967295)
   ACCESS     read-only
   STATUS     mandatory
   DESCRIPTION
     "This attribute indicates the value of sysUpTime (in 1/100's of a 
      second) at the time of the most recent change to a SNMPv2 Object 
      Resource entry. The attribute forms part of the SNMPv2 MIB Base 
      Object Resource Group found in rfc1450."
::= { vrSnmpStatsEntry 1 }

vrSnmpTrapsProcessed OBJECT-TYPE
   SYNTAX     Unsigned32 (0..4294967295)
   ACCESS     read-only
   STATUS     mandatory
   DESCRIPTION
     "This counter contains the cumulative number of Trap Indications 
      and Alarm Indications received from the DCS Collectors since the 
      processor last restarted. These Traps and Alarms are sent to 
      SNMPv1 Managers and SNMPv2 Parties which are configured to 
      receive Traps. This total includes the number discarded by the Snmp 
      component when it was locked or disabled."
   DEFVAL     { 0 }
::= { vrSnmpStatsEntry 2 }

vrSnmpTrapsDiscarded OBJECT-TYPE
   SYNTAX     Unsigned32 (0..4294967295)
   ACCESS     read-only
   STATUS     mandatory
   DESCRIPTION
     "This counter contains the cumulative number of Trap Indications 
      and Alarm Indications discarded since the processor last restarted. 
      They are discarded when the Snmp component is locked or 
      disabled."
   DEFVAL     { 0 }
::= { vrSnmpStatsEntry 3 }

vrSnmpLastAuthFailure OBJECT-TYPE
   SYNTAX     Unsigned32 (0..4294967295)
   ACCESS     read-only
   STATUS     mandatory
   DESCRIPTION
     "This attribute indicates the value of sysUpTime (in 1/100's of a 
      second) at the time the last authentication failure. This 
      attribute is a non-SNMP statistic."
   DEFVAL     { 0 }
::= { vrSnmpStatsEntry 4 }

vrSnmpMgrOfLastAuthFailure OBJECT-TYPE
   SYNTAX     IpAddress 
   ACCESS     read-only
   STATUS     mandatory
   DESCRIPTION
     "This attribute indicates the IP address of the manager station that 
      caused the last authentication failure. This attribute is a non-SNMP 
      statistic."
   DEFVAL     { '00000000'H }  -- "0.0.0.0"
::= { vrSnmpStatsEntry 5 }


-- VirtualRouter/string Snmp System
-- This component represents the SNMP System Group. The 
-- component attributes are derived from rfc1213.

vrSnmpSys OBJECT IDENTIFIER ::= { vrSnmp 2 }



vrSnmpSysRowStatusTable OBJECT-TYPE
   SYNTAX     SEQUENCE OF VrSnmpSysRowStatusEntry
   ACCESS     not-accessible
   STATUS     mandatory
   DESCRIPTION
     "This entry controls the addition and deletion of 
      vrSnmpSys components."
::= { vrSnmpSys 1 }

vrSnmpSysRowStatusEntry OBJECT-TYPE
   SYNTAX     VrSnmpSysRowStatusEntry
   ACCESS     not-accessible
   STATUS     mandatory
   DESCRIPTION
     "A single entry in the table represents a single 
      vrSnmpSys component."
   INDEX {
      vrIndex,
      vrSnmpIndex,
      vrSnmpSysIndex }
::= { vrSnmpSysRowStatusTable 1 }

VrSnmpSysRowStatusEntry ::= SEQUENCE {
   vrSnmpSysRowStatus
      RowStatus,
   vrSnmpSysComponentName
      DisplayString,
   vrSnmpSysStorageType
      StorageType,
   vrSnmpSysIndex
      NonReplicated }

vrSnmpSysRowStatus OBJECT-TYPE
   SYNTAX     RowStatus 
   ACCESS     read-only
   STATUS     mandatory
   DESCRIPTION
     "This variable is used as the basis for SNMP naming of
      vrSnmpSys components.
      These components cannot be added nor deleted."
::= { vrSnmpSysRowStatusEntry 1 }

vrSnmpSysComponentName OBJECT-TYPE
   SYNTAX     DisplayString 
   ACCESS     read-only
   STATUS     mandatory
   DESCRIPTION
     "This variable provides the component's string name for
      use with the ASCII Console Interface"
::= { vrSnmpSysRowStatusEntry 2 }

vrSnmpSysStorageType OBJECT-TYPE
   SYNTAX     StorageType 
   ACCESS     read-only
   STATUS     mandatory
   DESCRIPTION
     "This variable represents the storage type value for the
      vrSnmpSys tables."
::= { vrSnmpSysRowStatusEntry 4 }

vrSnmpSysIndex OBJECT-TYPE
   SYNTAX     NonReplicated 
   ACCESS     not-accessible
   STATUS     mandatory
   DESCRIPTION
     "This variable represents the index for the vrSnmpSys tables."
::= { vrSnmpSysRowStatusEntry 10 }

vrSnmpSysProvTable OBJECT-TYPE
   SYNTAX     SEQUENCE OF VrSnmpSysProvEntry
   ACCESS     not-accessible
   STATUS     mandatory
   DESCRIPTION
     "The group contains provisionable attributes relating to the SNMP 
      System Group. The attributes are derived from rfc1213."
::= { vrSnmpSys 10 }

vrSnmpSysProvEntry OBJECT-TYPE
   SYNTAX     VrSnmpSysProvEntry
   ACCESS     not-accessible
   STATUS     mandatory
   DESCRIPTION
     "An entry in the vrSnmpSysProvTable."
   INDEX {
      vrIndex,
      vrSnmpIndex,
      vrSnmpSysIndex }
::= { vrSnmpSysProvTable 1 }

VrSnmpSysProvEntry ::= SEQUENCE {
   vrSnmpSysContact
      AsciiString,
   vrSnmpSysName
      AsciiString,
   vrSnmpSysLocation
      AsciiString }

vrSnmpSysContact OBJECT-TYPE
   SYNTAX     AsciiString (SIZE (0..255))
   ACCESS     read-write
   STATUS     mandatory
   DESCRIPTION
     "This attribute identifies the contact person for this managed node, 
      together with information on how to contact this person."
::= { vrSnmpSysProvEntry 1 }

vrSnmpSysName OBJECT-TYPE
   SYNTAX     AsciiString (SIZE (0..255))
   ACCESS     read-write
   STATUS     mandatory
   DESCRIPTION
     "This attribute identifies the administratively assigned name for this 
      managed node. By convention, it is the node's fully qualified 
      domain name."
::= { vrSnmpSysProvEntry 2 }

vrSnmpSysLocation OBJECT-TYPE
   SYNTAX     AsciiString (SIZE (0..255))
   ACCESS     read-write
   STATUS     mandatory
   DESCRIPTION
     "This attribute identifies the physical location of this node. For 
      example, 'telephone closet, third floor'."
::= { vrSnmpSysProvEntry 3 }

vrSnmpSysOpTable OBJECT-TYPE
   SYNTAX     SEQUENCE OF VrSnmpSysOpEntry
   ACCESS     not-accessible
   STATUS     mandatory
   DESCRIPTION
     "The group contains operational attributes relating to the SNMP 
      System Group. The attributes are derived from rfc1213."
::= { vrSnmpSys 11 }

vrSnmpSysOpEntry OBJECT-TYPE
   SYNTAX     VrSnmpSysOpEntry
   ACCESS     not-accessible
   STATUS     mandatory
   DESCRIPTION
     "An entry in the vrSnmpSysOpTable."
   INDEX {
      vrIndex,
      vrSnmpIndex,
      vrSnmpSysIndex }
::= { vrSnmpSysOpTable 1 }

VrSnmpSysOpEntry ::= SEQUENCE {
   vrSnmpSysDescription
      AsciiString,
   vrSnmpSysObjectId
      OBJECT IDENTIFIER,
   vrSnmpSysUpTime
      Unsigned32,
   vrSnmpSysServices
      Unsigned32 }

vrSnmpSysDescription OBJECT-TYPE
   SYNTAX     AsciiString (SIZE (0..255))
   ACCESS     read-only
   STATUS     mandatory
   DESCRIPTION
     "This attribute presents a textual description of the entity. This value 
      should include the full name and version identification of the 
      system's hardware type, software operating-system, and networking 
      software."
::= { vrSnmpSysOpEntry 1 }

vrSnmpSysObjectId OBJECT-TYPE
   SYNTAX     OBJECT IDENTIFIER 
   ACCESS     read-only
   STATUS     mandatory
   DESCRIPTION
     "This attribute identifies the vendor's authoritative identification of 
      the network management subsystem contained in the entity. This 
      value is allocated within the Structure of Management Information 
      (SMI) enterprises subtree (1.3.6.1.4.1) and provides an easy and 
      unambiguous means for determining 'what kind of box' is being 
      managed."
::= { vrSnmpSysOpEntry 2 }

vrSnmpSysUpTime OBJECT-TYPE
   SYNTAX     Unsigned32 (0..4294967295)
   ACCESS     read-only
   STATUS     mandatory
   DESCRIPTION
     "This attribute represents the time (in hundredths of a second) since 
      the network management portion of the system was last re-
      initialized."
::= { vrSnmpSysOpEntry 3 }

vrSnmpSysServices OBJECT-TYPE
   SYNTAX     Unsigned32 (0..127)
   ACCESS     read-only
   STATUS     mandatory
   DESCRIPTION
     "This attribute indicates the set of services that this entity primarily 
      offers.
      The value is a sum. This sum initially takes the value zero, then, for 
      each layer, L, in the range 1 through 7, that this node performs 
      transactions for, 2 raised to (L-1) is added to the sum. For example, 
      a node which performs primarily routing functions would have a 
      value of 4 (2^(3-1)). In contrast, a node which is a host offering 
      application services would have a value of 72 ((2^4-1) + 2^(7-1)). 
      Note that in the context of the Internet suite of protocols, values 
      should be calculated accordingly:
      layer 1 - physical (for example, repeaters)
      layer 2 - datalink/subnetwork (for example, bridges)
      layer 3 - internet (for example, IP gateways)
      layer 4 - end-to-end (for example, IP hosts)
      layer 7 - applications (for example, mail relays)
      For systems including OSI protocols, layers 5 and 6 may also be 
      counted."
   DEFVAL     { 6 }
::= { vrSnmpSysOpEntry 4 }


-- VirtualRouter/string Snmp Community/n
-- This component represents an SNMPv1 Community. A community 
-- represents a pairing of an SNMP Agent with an arbitrary set of 
-- application entities. 
-- The combination of communityString and tDomain attributes must 
-- be unique across all Communies.

vrSnmpCom OBJECT IDENTIFIER ::= { vrSnmp 3 }



vrSnmpComRowStatusTable OBJECT-TYPE
   SYNTAX     SEQUENCE OF VrSnmpComRowStatusEntry
   ACCESS     not-accessible
   STATUS     mandatory
   DESCRIPTION
     "This entry controls the addition and deletion of 
      vrSnmpCom components."
::= { vrSnmpCom 1 }

vrSnmpComRowStatusEntry OBJECT-TYPE
   SYNTAX     VrSnmpComRowStatusEntry
   ACCESS     not-accessible
   STATUS     mandatory
   DESCRIPTION
     "A single entry in the table represents a single 
      vrSnmpCom component."
   INDEX {
      vrIndex,
      vrSnmpIndex,
      vrSnmpComIndex }
::= { vrSnmpComRowStatusTable 1 }

VrSnmpComRowStatusEntry ::= SEQUENCE {
   vrSnmpComRowStatus
      RowStatus,
   vrSnmpComComponentName
      DisplayString,
   vrSnmpComStorageType
      StorageType,
   vrSnmpComIndex
      Integer32 }

vrSnmpComRowStatus OBJECT-TYPE
   SYNTAX     RowStatus 
   ACCESS     read-write
   STATUS     mandatory
   DESCRIPTION
     "This variable is used as the basis for SNMP naming of
      vrSnmpCom components.
      These components can be added and deleted."
::= { vrSnmpComRowStatusEntry 1 }

vrSnmpComComponentName OBJECT-TYPE
   SYNTAX     DisplayString 
   ACCESS     read-only
   STATUS     mandatory
   DESCRIPTION
     "This variable provides the component's string name for
      use with the ASCII Console Interface"
::= { vrSnmpComRowStatusEntry 2 }

vrSnmpComStorageType OBJECT-TYPE
   SYNTAX     StorageType 
   ACCESS     read-only
   STATUS     mandatory
   DESCRIPTION
     "This variable represents the storage type value for the
      vrSnmpCom tables."
::= { vrSnmpComRowStatusEntry 4 }

vrSnmpComIndex OBJECT-TYPE
   SYNTAX     Integer32 (1..1024)
   ACCESS     not-accessible
   STATUS     mandatory
   DESCRIPTION
     "This variable represents the index for the vrSnmpCom tables."
::= { vrSnmpComRowStatusEntry 10 }

vrSnmpComProvTable OBJECT-TYPE
   SYNTAX     SEQUENCE OF VrSnmpComProvEntry
   ACCESS     not-accessible
   STATUS     mandatory
   DESCRIPTION
     "The group contains provisionable attributes relating to SNMPv1 
      Communities."
::= { vrSnmpCom 10 }

vrSnmpComProvEntry OBJECT-TYPE
   SYNTAX     VrSnmpComProvEntry
   ACCESS     not-accessible
   STATUS     mandatory
   DESCRIPTION
     "An entry in the vrSnmpComProvTable."
   INDEX {
      vrIndex,
      vrSnmpIndex,
      vrSnmpComIndex }
::= { vrSnmpComProvTable 1 }

VrSnmpComProvEntry ::= SEQUENCE {
   vrSnmpComCommunityString
      AsciiString,
   vrSnmpComAccessMode
      INTEGER,
   vrSnmpComViewIndex
      Unsigned32,
   vrSnmpComTDomain
      INTEGER }

vrSnmpComCommunityString OBJECT-TYPE
   SYNTAX     AsciiString (SIZE (1..255))
   ACCESS     read-write
   STATUS     mandatory
   DESCRIPTION
     "This attribute is the SNMPv1 Community name. The value of this 
      attribute is used to authenticate SNMP messages received from 
      SNMPv1 management entities, and is placed in SNMP messages 
      sent out by the SNMPv1 network management entity. The string 
      'public' is commonly used.
      When an SNMPv1 message is received, the community name in the 
      message is checked to ensure that it matches a Community string. If 
      there are no Manager subcomponents for that Community then the 
      level of access is determined by the accessMode attribute. If there 
      are Manager subcomponents for the Community then the 
      originating transport address in the message must match the 
      transportAddress of one of the Manager subcomponents, and the 
      level of access of the sending entity is determined by the privileges 
      attribute for that Manager.
      The combination of communityString and tDomain attributes must 
      be unique across all Communies."
   DEFVAL     { '7075626c6963'H }  -- "public"
::= { vrSnmpComProvEntry 1 }

vrSnmpComAccessMode OBJECT-TYPE
   SYNTAX     INTEGER  {
                 readOnly(1),
                 readWrite(2) }
   ACCESS     read-write
   STATUS     mandatory
   DESCRIPTION
     "Once the sending SNMP entity is authenticated as a member of a 
      community, the community access mode determines what level of 
      access it has for each object in its view."
   DEFVAL     { readOnly }
::= { vrSnmpComProvEntry 3 }

vrSnmpComViewIndex OBJECT-TYPE
   SYNTAX     Unsigned32 (1..1024)
   ACCESS     read-write
   STATUS     mandatory
   DESCRIPTION
     "The community view index selects an entry in the SnmpViewTable 
      that this community will use. This index must correspond to the first 
      index of one of the SnmpView entries. Note that SNMPv2 Views are 
      used for SNMPv1 communities, as the SNMPv2 View model is 
      sufficiently general to handle the SNMPv1 case."
::= { vrSnmpComProvEntry 4 }

vrSnmpComTDomain OBJECT-TYPE
   SYNTAX     INTEGER  {
                 snmpUdpDomain(1) }
   ACCESS     read-write
   STATUS     mandatory
   DESCRIPTION
     "This attribute indicates the kind of transport service by which the 
      community receives and sends network management traffic. 
      The combination of communityString and tDomain attributes must 
      be unique across all Communies"
   DEFVAL     { snmpUdpDomain }
::= { vrSnmpComProvEntry 5 }


-- VirtualRouter/string Snmp Community/n Manager/n
-- This component defines the access privileges for an SNMPv1 
-- Manager within the Community. If a Community has no Manager 
-- components, SNMPv1 messages are accepted from all source 
-- addresses using the proper communityString, and no Traps are sent 
-- out using the communityString. If at least one Manager component 
-- exists for a Community then SNMPv1 messages containing that 
-- Community string are only accepted if they originate from a 
-- transport address which matches the transportAddress of one of the 
-- Manager components.
-- The value of transportAddress must be unique for all Manager 
-- components under the same Community.

vrSnmpComMan OBJECT IDENTIFIER ::= { vrSnmpCom 2 }



vrSnmpComManRowStatusTable OBJECT-TYPE
   SYNTAX     SEQUENCE OF VrSnmpComManRowStatusEntry
   ACCESS     not-accessible
   STATUS     mandatory
   DESCRIPTION
     "This entry controls the addition and deletion of 
      vrSnmpComMan components."
::= { vrSnmpComMan 1 }

vrSnmpComManRowStatusEntry OBJECT-TYPE
   SYNTAX     VrSnmpComManRowStatusEntry
   ACCESS     not-accessible
   STATUS     mandatory
   DESCRIPTION
     "A single entry in the table represents a single 
      vrSnmpComMan component."
   INDEX {
      vrIndex,
      vrSnmpIndex,
      vrSnmpComIndex,
      vrSnmpComManIndex }
::= { vrSnmpComManRowStatusTable 1 }

VrSnmpComManRowStatusEntry ::= SEQUENCE {
   vrSnmpComManRowStatus
      RowStatus,
   vrSnmpComManComponentName
      DisplayString,
   vrSnmpComManStorageType
      StorageType,
   vrSnmpComManIndex
      Integer32 }

vrSnmpComManRowStatus OBJECT-TYPE
   SYNTAX     RowStatus 
   ACCESS     read-write
   STATUS     mandatory
   DESCRIPTION
     "This variable is used as the basis for SNMP naming of
      vrSnmpComMan components.
      These components can be added and deleted."
::= { vrSnmpComManRowStatusEntry 1 }

vrSnmpComManComponentName OBJECT-TYPE
   SYNTAX     DisplayString 
   ACCESS     read-only
   STATUS     mandatory
   DESCRIPTION
     "This variable provides the component's string name for
      use with the ASCII Console Interface"
::= { vrSnmpComManRowStatusEntry 2 }

vrSnmpComManStorageType OBJECT-TYPE
   SYNTAX     StorageType 
   ACCESS     read-only
   STATUS     mandatory
   DESCRIPTION
     "This variable represents the storage type value for the
      vrSnmpComMan tables."
::= { vrSnmpComManRowStatusEntry 4 }

vrSnmpComManIndex OBJECT-TYPE
   SYNTAX     Integer32 (0..100)
   ACCESS     not-accessible
   STATUS     mandatory
   DESCRIPTION
     "This variable represents the index for the vrSnmpComMan tables."
::= { vrSnmpComManRowStatusEntry 10 }

vrSnmpComManProvTable OBJECT-TYPE
   SYNTAX     SEQUENCE OF VrSnmpComManProvEntry
   ACCESS     not-accessible
   STATUS     mandatory
   DESCRIPTION
     "The group contains provisionable attributes relating to an SNMPv1 
      Community Manager."
::= { vrSnmpComMan 10 }

vrSnmpComManProvEntry OBJECT-TYPE
   SYNTAX     VrSnmpComManProvEntry
   ACCESS     not-accessible
   STATUS     mandatory
   DESCRIPTION
     "An entry in the vrSnmpComManProvTable."
   INDEX {
      vrIndex,
      vrSnmpIndex,
      vrSnmpComIndex,
      vrSnmpComManIndex }
::= { vrSnmpComManProvTable 1 }

VrSnmpComManProvEntry ::= SEQUENCE {
   vrSnmpComManTransportAddress
      AsciiString,
   vrSnmpComManPrivileges
      OCTET STRING }

vrSnmpComManTransportAddress OBJECT-TYPE
   SYNTAX     AsciiString (SIZE (1..100))
   ACCESS     read-write
   STATUS     mandatory
   DESCRIPTION
     "This attribute is the transport service address of SNMPv1 Manager, 
      formatted according to the value of SnmpV1Community tDomain. 
      The only currently supported format is that of a UDP Transport 
      Address. It must be of the form 'IpAddress-UDP Port', where UDP 
      Port = 162. For example, 23.45.67.89-162 is a suitable UDP 
      Transport Address. 
      The value of transportAddress must be unique for all Manager 
      components under the same Community."
::= { vrSnmpComManProvEntry 1 }

vrSnmpComManPrivileges OBJECT-TYPE
   SYNTAX     OCTET STRING (SIZE (1))
   ACCESS     read-write
   STATUS     mandatory
   DESCRIPTION
     "This attribute identifies the access privileges which govern what 
      management operations the SNMPv1 Manager may perform.
      v1trap operations are only allowed if the Community accessMode is 
      readOnly or readWrite.
      set operations are only allowed if the Community accessMode is 
      readWrite.
      get operations are only allowed if the Community accessMode is 
      readOnly or readWrite.

      Description of bits:
      sets(0)
      gets(1)
      v1trap(2)"
   DEFVAL     { '40'H }
::= { vrSnmpComManProvEntry 2 }


-- VirtualRouter/string Snmp AccessPrivileges/n,n,n
-- This component is used to add SNMPv2 Access Privilege Table 
-- Entries. The component attributes are derived from rfc1445, and 
-- rfc1447.
-- The target index identifies a SNMPv2 party which is the target of 
-- an access control policy. This index must correspond to the 
-- SnmpV2PartyEntry index of a provisioned SnmpV2Party.
-- The subject index identifies a SNMPv2 party which is the subject of 
-- an access control policy. This index must correspond to the 
-- SnmpV2PartyEntryProv index of one of the provisioned 
-- SnmpV2Party's.
-- If the party identified by target is local (SnmpV2PartyEntryProv 
-- local = true), then subject must identify a party that is non-local 
-- (SnmpV2PartyEntryProv local = false). If the party identified by 
-- target is non-local, then subject must indicate a local party.
-- The resources index identifies an SNMPv2 context in an access 
-- control policy. This index must correspond to the 
-- SnmpV2ContextEntryProv index of one of the provisioned 
-- SnmpV2Context's. 

vrSnmpAcl OBJECT IDENTIFIER ::= { vrSnmp 4 }



vrSnmpAclRowStatusTable OBJECT-TYPE
   SYNTAX     SEQUENCE OF VrSnmpAclRowStatusEntry
   ACCESS     not-accessible
   STATUS     obsolete
   DESCRIPTION
     "This entry controls the addition and deletion of 
      vrSnmpAcl components."
::= { vrSnmpAcl 1 }

vrSnmpAclRowStatusEntry OBJECT-TYPE
   SYNTAX     VrSnmpAclRowStatusEntry
   ACCESS     not-accessible
   STATUS     obsolete
   DESCRIPTION
     "A single entry in the table represents a single 
      vrSnmpAcl component."
   INDEX {
      vrIndex,
      vrSnmpIndex,
      vrSnmpAclTargetIndex,
      vrSnmpAclSubjectIndex,
      vrSnmpAclResourcesIndex }
::= { vrSnmpAclRowStatusTable 1 }

VrSnmpAclRowStatusEntry ::= SEQUENCE {
   vrSnmpAclRowStatus
      RowStatus,
   vrSnmpAclComponentName
      DisplayString,
   vrSnmpAclStorageType
      StorageType,
   vrSnmpAclTargetIndex
      Integer32,
   vrSnmpAclSubjectIndex
      Integer32,
   vrSnmpAclResourcesIndex
      Integer32 }

vrSnmpAclRowStatus OBJECT-TYPE
   SYNTAX     RowStatus 
   ACCESS     read-write
   STATUS     obsolete
   DESCRIPTION
     "This variable is used as the basis for SNMP naming of
      vrSnmpAcl components.
      These components can be added and deleted."
::= { vrSnmpAclRowStatusEntry 1 }

vrSnmpAclComponentName OBJECT-TYPE
   SYNTAX     DisplayString 
   ACCESS     read-only
   STATUS     obsolete
   DESCRIPTION
     "This variable provides the component's string name for
      use with the ASCII Console Interface"
::= { vrSnmpAclRowStatusEntry 2 }

vrSnmpAclStorageType OBJECT-TYPE
   SYNTAX     StorageType 
   ACCESS     read-only
   STATUS     obsolete
   DESCRIPTION
     "This variable represents the storage type value for the
      vrSnmpAcl tables."
::= { vrSnmpAclRowStatusEntry 4 }

vrSnmpAclTargetIndex OBJECT-TYPE
   SYNTAX     Integer32 (1..2048)
   ACCESS     not-accessible
   STATUS     obsolete
   DESCRIPTION
     "This variable represents an index for the vrSnmpAcl tables."
::= { vrSnmpAclRowStatusEntry 10 }

vrSnmpAclSubjectIndex OBJECT-TYPE
   SYNTAX     Integer32 (1..2048)
   ACCESS     not-accessible
   STATUS     obsolete
   DESCRIPTION
     "This variable represents an index for the vrSnmpAcl tables."
::= { vrSnmpAclRowStatusEntry 11 }

vrSnmpAclResourcesIndex OBJECT-TYPE
   SYNTAX     Integer32 (1..2048)
   ACCESS     not-accessible
   STATUS     obsolete
   DESCRIPTION
     "This variable represents an index for the vrSnmpAcl tables."
::= { vrSnmpAclRowStatusEntry 12 }

vrSnmpAclProvTable OBJECT-TYPE
   SYNTAX     SEQUENCE OF VrSnmpAclProvEntry
   ACCESS     not-accessible
   STATUS     obsolete
   DESCRIPTION
     "This group contains provisionable attributes relating to SNMPv2 
      Access Privilege Table Entries. The provisionable attributes are 
      derived from rfc1445, and rfc1447."
::= { vrSnmpAcl 10 }

vrSnmpAclProvEntry OBJECT-TYPE
   SYNTAX     VrSnmpAclProvEntry
   ACCESS     not-accessible
   STATUS     obsolete
   DESCRIPTION
     "An entry in the vrSnmpAclProvTable."
   INDEX {
      vrIndex,
      vrSnmpIndex,
      vrSnmpAclTargetIndex,
      vrSnmpAclSubjectIndex,
      vrSnmpAclResourcesIndex }
::= { vrSnmpAclProvTable 1 }

VrSnmpAclProvEntry ::= SEQUENCE {
   vrSnmpAclPrivileges
      OCTET STRING,
   vrSnmpAclRowStorageType
      INTEGER,
   vrSnmpAclStdRowStatus
      INTEGER }

vrSnmpAclPrivileges OBJECT-TYPE
   SYNTAX     OCTET STRING (SIZE (1))
   ACCESS     read-write
   STATUS     obsolete
   DESCRIPTION
     "This attribute identifies the access privileges which govern what 
      management operations a particular target part may perform with 
      respect to a particular SNMPv2 context when requested by a 
      particular subject party. Gets and set operations are only permitted 
      if the target Party is local (SnmpV2PartyEntryProv local = true). 
      Response and v2trap operations are only permitted if the target 
      Party is non-local (SnmpV2PartyEntryProv local = false).

      Description of bits:
      response(0)
      set(1)
      gets(2)
      v2trap(3)"
   DEFVAL     { '60'H }
::= { vrSnmpAclProvEntry 1 }

vrSnmpAclRowStorageType OBJECT-TYPE
   SYNTAX     INTEGER  {
                 nonVolatile(3) }
   ACCESS     read-write
   STATUS     obsolete
   DESCRIPTION
     "This attribute indicates the storage type for this conceptual row in 
      the SNMPv2 aclTable. This is a constant - nonVolatile."
   DEFVAL     { nonVolatile }
::= { vrSnmpAclProvEntry 2 }

vrSnmpAclStdRowStatus OBJECT-TYPE
   SYNTAX     INTEGER  {
                 active(1) }
   ACCESS     read-write
   STATUS     obsolete
   DESCRIPTION
     "This attribute indicates the status of this conceptual row in the 
      SNMPv2 aclTable. This is a constant - active."
   DEFVAL     { active }
::= { vrSnmpAclProvEntry 3 }


-- VirtualRouter/string Snmp Party/Int_Sequence
-- This component is used to add SNMPv2 Party Table Entries. The 
-- maximum number of Table Entries is 1024. The component 
-- attributes are derived from rfc1321, rfc1445, rfc1446, rfc1447, 
-- rfc1449, and rfc1450.

vrSnmpParty OBJECT IDENTIFIER ::= { vrSnmp 5 }



vrSnmpPartyRowStatusTable OBJECT-TYPE
   SYNTAX     SEQUENCE OF VrSnmpPartyRowStatusEntry
   ACCESS     not-accessible
   STATUS     obsolete
   DESCRIPTION
     "This entry controls the addition and deletion of 
      vrSnmpParty components."
::= { vrSnmpParty 1 }

vrSnmpPartyRowStatusEntry OBJECT-TYPE
   SYNTAX     VrSnmpPartyRowStatusEntry
   ACCESS     not-accessible
   STATUS     obsolete
   DESCRIPTION
     "A single entry in the table represents a single 
      vrSnmpParty component."
   INDEX {
      vrIndex,
      vrSnmpIndex,
      vrSnmpPartyIdentityIndex }
::= { vrSnmpPartyRowStatusTable 1 }

VrSnmpPartyRowStatusEntry ::= SEQUENCE {
   vrSnmpPartyRowStatus
      RowStatus,
   vrSnmpPartyComponentName
      DisplayString,
   vrSnmpPartyStorageType
      StorageType,
   vrSnmpPartyIdentityIndex
      OBJECT IDENTIFIER }

vrSnmpPartyRowStatus OBJECT-TYPE
   SYNTAX     RowStatus 
   ACCESS     read-write
   STATUS     obsolete
   DESCRIPTION
     "This variable is used as the basis for SNMP naming of
      vrSnmpParty components.
      These components can be added and deleted."
::= { vrSnmpPartyRowStatusEntry 1 }

vrSnmpPartyComponentName OBJECT-TYPE
   SYNTAX     DisplayString 
   ACCESS     read-only
   STATUS     obsolete
   DESCRIPTION
     "This variable provides the component's string name for
      use with the ASCII Console Interface"
::= { vrSnmpPartyRowStatusEntry 2 }

vrSnmpPartyStorageType OBJECT-TYPE
   SYNTAX     StorageType 
   ACCESS     read-only
   STATUS     obsolete
   DESCRIPTION
     "This variable represents the storage type value for the
      vrSnmpParty tables."
::= { vrSnmpPartyRowStatusEntry 4 }

vrSnmpPartyIdentityIndex OBJECT-TYPE
   SYNTAX     OBJECT IDENTIFIER 
   ACCESS     not-accessible
   STATUS     obsolete
   DESCRIPTION
     "This variable represents the index for the vrSnmpParty tables."
::= { vrSnmpPartyRowStatusEntry 10 }

vrSnmpPartyProvTable OBJECT-TYPE
   SYNTAX     SEQUENCE OF VrSnmpPartyProvEntry
   ACCESS     not-accessible
   STATUS     obsolete
   DESCRIPTION
     "This group contains provisionable attributes relating to SNMPv2 
      Party Table Entries.The attributes are derived from rfc1321, 
      rfc1445, rfc1446, rfc1447, and rfc1450."
::= { vrSnmpParty 10 }

vrSnmpPartyProvEntry OBJECT-TYPE
   SYNTAX     VrSnmpPartyProvEntry
   ACCESS     not-accessible
   STATUS     obsolete
   DESCRIPTION
     "An entry in the vrSnmpPartyProvTable."
   INDEX {
      vrIndex,
      vrSnmpIndex,
      vrSnmpPartyIdentityIndex }
::= { vrSnmpPartyProvTable 1 }

VrSnmpPartyProvEntry ::= SEQUENCE {
   vrSnmpPartyStdIndex
      Unsigned32,
   vrSnmpPartyTDomain
      INTEGER,
   vrSnmpPartyTransportAddress
      AsciiString,
   vrSnmpPartyMaxMessageSize
      Unsigned32,
   vrSnmpPartyLocal
      TruthValue,
   vrSnmpPartyAuthProtocol
      INTEGER,
   vrSnmpPartyAuthPrivate
      HexString,
   vrSnmpPartyAuthPublic
      HexString,
   vrSnmpPartyAuthLifetime
      Unsigned32,
   vrSnmpPartyPrivProtocol
      INTEGER,
   vrSnmpPartyRowStorageType
      INTEGER,
   vrSnmpPartyStdRowStatus
      INTEGER }

vrSnmpPartyStdIndex OBJECT-TYPE
   SYNTAX     Unsigned32 (1..2048)
   ACCESS     read-only
   STATUS     obsolete
   DESCRIPTION
     "This attribute represents the SNMPv2 Party table partyIndex. This 
      index is unique and its value is automatically selected for you."
::= { vrSnmpPartyProvEntry 1 }

vrSnmpPartyTDomain OBJECT-TYPE
   SYNTAX     INTEGER  {
                 snmpUdpDomain(1) }
   ACCESS     read-write
   STATUS     obsolete
   DESCRIPTION
     "This attribute indicates the kind of transport service by which the 
      party receives and sends network management traffic."
   DEFVAL     { snmpUdpDomain }
::= { vrSnmpPartyProvEntry 2 }

vrSnmpPartyTransportAddress OBJECT-TYPE
   SYNTAX     AsciiString (SIZE (1..100))
   ACCESS     read-write
   STATUS     obsolete
   DESCRIPTION
     "This attribute is the transport service address by which the party 
      receives network management traffic, formatted according to the 
      corresponding value of tDomain. 
      For local (Agent) Parties (SnmpV2PartyEntryProv local = true) this 
      is the address of the Virtual Router. 
      For non-local (Manager) Parties (SnmpV2PartyEntryProv local = 
      false) this is the address of the SNMP Manager.
      The only currently supported format is that of a UDP Transport 
      Address. It must be of the form 'IpAddress-UDP Port', where UDP 
      Port = 161 for a local Party and UDP Port = 162 for a non-local 
      Party. For example, 23.45.67.89-161 or 23.45.67.89-162 are suitable 
      UDP Transport Addresses."
::= { vrSnmpPartyProvEntry 3 }

vrSnmpPartyMaxMessageSize OBJECT-TYPE
   SYNTAX     Unsigned32 (484..65507)
   ACCESS     read-write
   STATUS     obsolete
   DESCRIPTION
     "This attribute is the maximum length in octets of a SNMPv2 
      message that this party will accept. For local (Agent) Parties 
      (SnmpV2PartyEntryProv local = true) this cannot be set to greater 
      than the fixed Agent maximum of 1400. For non-local (Manager) 
      Parties (SnmpV2PartyEntryProv local = false) the maximum is 
      65507."
   DEFVAL     { 1400 }
::= { vrSnmpPartyProvEntry 4 }

vrSnmpPartyLocal OBJECT-TYPE
   SYNTAX     TruthValue 
   ACCESS     read-write
   STATUS     obsolete
   DESCRIPTION
     "This attribute indicates whether this party executes at this SNMPv2 
      entity. If this attribute has a value of true, then the SNMPv2 entity 
      is an Agent, and will listen for SNMPv2 messages on the ipAddress 
      associated with this party. If this attribute has the value false, then 
      the SNMPv2 entity is a Manager."
::= { vrSnmpPartyProvEntry 5 }

vrSnmpPartyAuthProtocol OBJECT-TYPE
   SYNTAX     INTEGER  {
                 noAuth(1),
                 v2Md5AuthProtocol(4) }
   ACCESS     read-write
   STATUS     obsolete
   DESCRIPTION
     "This attribute indicates the authentication protocol by which all 
      messages generated by the party are authenticated as to origin and 
      integrity. The value noAuth signifies that messages generated by the 
      party are not authenticated."
   DEFVAL     { noAuth }
::= { vrSnmpPartyProvEntry 6 }

vrSnmpPartyAuthPrivate OBJECT-TYPE
   SYNTAX     HexString (SIZE (0..16))
   ACCESS     write-only
   STATUS     obsolete
   DESCRIPTION
     "This attribute is the Party's private authentication key. As with 
      passwords this attribute cannot be displayed by the display 
      command and is stored in encoded form. For Parties with an 
      authentication protocol, this key must be provisioned."
   DEFVAL     { ''H }  -- ""
::= { vrSnmpPartyProvEntry 7 }

vrSnmpPartyAuthPublic OBJECT-TYPE
   SYNTAX     HexString (SIZE (0..16))
   ACCESS     read-write
   STATUS     obsolete
   DESCRIPTION
     "This attribute is the Party's public authentication key. It is the 
      'public information' used by the Party's authentication protocol."
   DEFVAL     { ''H }  -- ""
::= { vrSnmpPartyProvEntry 8 }

vrSnmpPartyAuthLifetime OBJECT-TYPE
   SYNTAX     Unsigned32 (0..2147483647)
   ACCESS     read-write
   STATUS     obsolete
   DESCRIPTION
     "This attribute represents the maximum acceptable delivery delay 
      (lifetime) in seconds for messages from this Party."
   DEFVAL     { 300 }
::= { vrSnmpPartyProvEntry 9 }

vrSnmpPartyPrivProtocol OBJECT-TYPE
   SYNTAX     INTEGER  {
                 noPriv(2) }
   ACCESS     read-write
   STATUS     obsolete
   DESCRIPTION
     "This attribute identifies the privacy protocol by which all protocol 
      messages received by the party are protected from disclosure. The 
      value noPriv signifies that messages received by the party are not 
      protected. As DES is not supported, this is a constant noPriv."
   DEFVAL     { noPriv }
::= { vrSnmpPartyProvEntry 10 }

vrSnmpPartyRowStorageType OBJECT-TYPE
   SYNTAX     INTEGER  {
                 nonVolatile(3) }
   ACCESS     read-write
   STATUS     obsolete
   DESCRIPTION
     "The attribute indicates the storage type for this conceptual row in 
      the SNMPv2 aclTable. This is a constant - nonVolatile."
   DEFVAL     { nonVolatile }
::= { vrSnmpPartyProvEntry 11 }

vrSnmpPartyStdRowStatus OBJECT-TYPE
   SYNTAX     INTEGER  {
                 active(1) }
   ACCESS     read-write
   STATUS     obsolete
   DESCRIPTION
     "This attribute indicates the status of this conceptual row in the 
      SNMPv2 partyTable. This is a constant - active."
   DEFVAL     { active }
::= { vrSnmpPartyProvEntry 12 }

vrSnmpPartyOpTable OBJECT-TYPE
   SYNTAX     SEQUENCE OF VrSnmpPartyOpEntry
   ACCESS     not-accessible
   STATUS     obsolete
   DESCRIPTION
     "This group contains Operational Attributes relating SNMPv2 
      parties. based upon rfc1321, rfc1445, rfc1446, rfc1447, and 
      rfc1450."
::= { vrSnmpParty 11 }

vrSnmpPartyOpEntry OBJECT-TYPE
   SYNTAX     VrSnmpPartyOpEntry
   ACCESS     not-accessible
   STATUS     obsolete
   DESCRIPTION
     "An entry in the vrSnmpPartyOpTable."
   INDEX {
      vrIndex,
      vrSnmpIndex,
      vrSnmpPartyIdentityIndex }
::= { vrSnmpPartyOpTable 1 }

VrSnmpPartyOpEntry ::= SEQUENCE {
   vrSnmpPartyTrapNumbers
      Unsigned32,
   vrSnmpPartyAuthClock
      Unsigned32 }

vrSnmpPartyTrapNumbers OBJECT-TYPE
   SYNTAX     Unsigned32 (0..4294967295)
   ACCESS     read-only
   STATUS     obsolete
   DESCRIPTION
     "This attribute is a count of the total number of SNMPv2 traps sent 
      to a SNMPv2 non-Local (Manager) party (SnmpV2PartyEntryProv 
      local = false). This counter is never incremented for Local (Agent) 
      parties (SnmpV2PartyEntryProv local = true)."
   DEFVAL     { 0 }
::= { vrSnmpPartyOpEntry 1 }

vrSnmpPartyAuthClock OBJECT-TYPE
   SYNTAX     Unsigned32 (0..4294967295)
   ACCESS     read-write
   STATUS     obsolete
   DESCRIPTION
     "This attribute is the authentication clock which represents the notion 
      of current time specific to a Party. This value is not permitted to 
      'roll-over'. In other words once it reaches the maximum it stays 
      there, unless explicitly decremented."
   DEFVAL     { 0 }
::= { vrSnmpPartyOpEntry 2 }


-- VirtualRouter/string Snmp Context/Int_Sequence
-- This component is used to add SNMPv2 Context Table Entries. The 
-- maximum number of Table Entries is 1024. The component 
-- attributes are derived from rfc1445, and rfc1447. 

vrSnmpCon OBJECT IDENTIFIER ::= { vrSnmp 6 }



vrSnmpConRowStatusTable OBJECT-TYPE
   SYNTAX     SEQUENCE OF VrSnmpConRowStatusEntry
   ACCESS     not-accessible
   STATUS     obsolete
   DESCRIPTION
     "This entry controls the addition and deletion of 
      vrSnmpCon components."
::= { vrSnmpCon 1 }

vrSnmpConRowStatusEntry OBJECT-TYPE
   SYNTAX     VrSnmpConRowStatusEntry
   ACCESS     not-accessible
   STATUS     obsolete
   DESCRIPTION
     "A single entry in the table represents a single 
      vrSnmpCon component."
   INDEX {
      vrIndex,
      vrSnmpIndex,
      vrSnmpConIdentityIndex }
::= { vrSnmpConRowStatusTable 1 }

VrSnmpConRowStatusEntry ::= SEQUENCE {
   vrSnmpConRowStatus
      RowStatus,
   vrSnmpConComponentName
      DisplayString,
   vrSnmpConStorageType
      StorageType,
   vrSnmpConIdentityIndex
      OBJECT IDENTIFIER }

vrSnmpConRowStatus OBJECT-TYPE
   SYNTAX     RowStatus 
   ACCESS     read-write
   STATUS     obsolete
   DESCRIPTION
     "This variable is used as the basis for SNMP naming of
      vrSnmpCon components.
      These components can be added and deleted."
::= { vrSnmpConRowStatusEntry 1 }

vrSnmpConComponentName OBJECT-TYPE
   SYNTAX     DisplayString 
   ACCESS     read-only
   STATUS     obsolete
   DESCRIPTION
     "This variable provides the component's string name for
      use with the ASCII Console Interface"
::= { vrSnmpConRowStatusEntry 2 }

vrSnmpConStorageType OBJECT-TYPE
   SYNTAX     StorageType 
   ACCESS     read-only
   STATUS     obsolete
   DESCRIPTION
     "This variable represents the storage type value for the
      vrSnmpCon tables."
::= { vrSnmpConRowStatusEntry 4 }

vrSnmpConIdentityIndex OBJECT-TYPE
   SYNTAX     OBJECT IDENTIFIER 
   ACCESS     not-accessible
   STATUS     obsolete
   DESCRIPTION
     "This variable represents the index for the vrSnmpCon tables."
::= { vrSnmpConRowStatusEntry 10 }

vrSnmpConProvTable OBJECT-TYPE
   SYNTAX     SEQUENCE OF VrSnmpConProvEntry
   ACCESS     not-accessible
   STATUS     obsolete
   DESCRIPTION
     "This group contains provisionable attributes relating to SNMPv2 
      Contexts Table Entries. The attributes are derived from rfc1445, and 
      rfc1447."
::= { vrSnmpCon 10 }

vrSnmpConProvEntry OBJECT-TYPE
   SYNTAX     VrSnmpConProvEntry
   ACCESS     not-accessible
   STATUS     obsolete
   DESCRIPTION
     "An entry in the vrSnmpConProvTable."
   INDEX {
      vrIndex,
      vrSnmpIndex,
      vrSnmpConIdentityIndex }
::= { vrSnmpConProvTable 1 }

VrSnmpConProvEntry ::= SEQUENCE {
   vrSnmpConStdIndex
      Unsigned32,
   vrSnmpConLocal
      INTEGER,
   vrSnmpConViewIndex
      Unsigned32,
   vrSnmpConLocalTime
      INTEGER,
   vrSnmpConRowStorageType
      INTEGER,
   vrSnmpConStdRowStatus
      INTEGER }

vrSnmpConStdIndex OBJECT-TYPE
   SYNTAX     Unsigned32 (1..1024)
   ACCESS     read-only
   STATUS     obsolete
   DESCRIPTION
     "This attribute represents the SNMPv2 Contexts table contextIndex. 
      This index is unique and its value is automatically selected for you."
::= { vrSnmpConProvEntry 1 }

vrSnmpConLocal OBJECT-TYPE
   SYNTAX     INTEGER  {
                 true(1) }
   ACCESS     read-write
   STATUS     obsolete
   DESCRIPTION
     "This attribute indicates whether this context is realized by this 
      SNMPv2 entity. This is a constant - true."
   DEFVAL     { true }
::= { vrSnmpConProvEntry 2 }

vrSnmpConViewIndex OBJECT-TYPE
   SYNTAX     Unsigned32 (1..1024)
   ACCESS     read-write
   STATUS     obsolete
   DESCRIPTION
     "The SNMPv2 Contexts view index selects a particular MIB view 
      entry in the SNMPv2 viewTable. This index must correspond to the 
      first replication index (index) of one of the entries in the SnmpView. 
      The value of the localTime attribute provides further information on 
      the temporal domain of the MIB view."
::= { vrSnmpConProvEntry 3 }

vrSnmpConLocalTime OBJECT-TYPE
   SYNTAX     INTEGER  {
                 currentTime(1) }
   ACCESS     read-write
   STATUS     obsolete
   DESCRIPTION
     "This attribute identifies the temporal context of the management 
      information in the MIB view identified by the viewIndex attribute. 
      This is a constant - currentTime. The SNMPv2 alternatives 
      restartTime and cacheTime are not currently supported."
   DEFVAL     { currentTime }
::= { vrSnmpConProvEntry 4 }

vrSnmpConRowStorageType OBJECT-TYPE
   SYNTAX     INTEGER  {
                 nonVolatile(3) }
   ACCESS     read-write
   STATUS     obsolete
   DESCRIPTION
     "The attribute indicates the storage type for this conceptual row in 
      the SNMPv2 contextTable. This is a constant - nonVolatile."
   DEFVAL     { nonVolatile }
::= { vrSnmpConProvEntry 5 }

vrSnmpConStdRowStatus OBJECT-TYPE
   SYNTAX     INTEGER  {
                 active(1) }
   ACCESS     read-write
   STATUS     obsolete
   DESCRIPTION
     "This attribute indicates the status of this conceptual row in the 
      SNMPv2 aclTable. This is a constant - active."
   DEFVAL     { active }
::= { vrSnmpConProvEntry 6 }


-- VirtualRouter/string Snmp View/n,Int_Sequence
-- This component is used to add SNMPv2 View Table Entries. These 
-- Views can also used by SNMPv1 Communities. The index index 
-- represents the SNMPv2 Table Entry viewIndex and the subTree 
-- index identifies a MIB subTree.The component attributes are 
-- derived from rfc1445, and rfc1447. 

vrSnmpView OBJECT IDENTIFIER ::= { vrSnmp 7 }



vrSnmpViewRowStatusTable OBJECT-TYPE
   SYNTAX     SEQUENCE OF VrSnmpViewRowStatusEntry
   ACCESS     not-accessible
   STATUS     mandatory
   DESCRIPTION
     "This entry controls the addition and deletion of 
      vrSnmpView components."
::= { vrSnmpView 1 }

vrSnmpViewRowStatusEntry OBJECT-TYPE
   SYNTAX     VrSnmpViewRowStatusEntry
   ACCESS     not-accessible
   STATUS     mandatory
   DESCRIPTION
     "A single entry in the table represents a single 
      vrSnmpView component."
   INDEX {
      vrIndex,
      vrSnmpIndex,
      vrSnmpViewIndex,
      vrSnmpViewSubtreeIndex }
::= { vrSnmpViewRowStatusTable 1 }

VrSnmpViewRowStatusEntry ::= SEQUENCE {
   vrSnmpViewRowStatus
      RowStatus,
   vrSnmpViewComponentName
      DisplayString,
   vrSnmpViewStorageType
      StorageType,
   vrSnmpViewIndex
      Integer32,
   vrSnmpViewSubtreeIndex
      OBJECT IDENTIFIER }

vrSnmpViewRowStatus OBJECT-TYPE
   SYNTAX     RowStatus 
   ACCESS     read-write
   STATUS     mandatory
   DESCRIPTION
     "This variable is used as the basis for SNMP naming of
      vrSnmpView components.
      These components can be added and deleted."
::= { vrSnmpViewRowStatusEntry 1 }

vrSnmpViewComponentName OBJECT-TYPE
   SYNTAX     DisplayString 
   ACCESS     read-only
   STATUS     mandatory
   DESCRIPTION
     "This variable provides the component's string name for
      use with the ASCII Console Interface"
::= { vrSnmpViewRowStatusEntry 2 }

vrSnmpViewStorageType OBJECT-TYPE
   SYNTAX     StorageType 
   ACCESS     read-only
   STATUS     mandatory
   DESCRIPTION
     "This variable represents the storage type value for the
      vrSnmpView tables."
::= { vrSnmpViewRowStatusEntry 4 }

vrSnmpViewIndex OBJECT-TYPE
   SYNTAX     Integer32 (1..1024)
   ACCESS     not-accessible
   STATUS     mandatory
   DESCRIPTION
     "This variable represents an index for the vrSnmpView tables."
::= { vrSnmpViewRowStatusEntry 10 }

vrSnmpViewSubtreeIndex OBJECT-TYPE
   SYNTAX     OBJECT IDENTIFIER 
   ACCESS     not-accessible
   STATUS     mandatory
   DESCRIPTION
     "This variable represents an index for the vrSnmpView tables."
::= { vrSnmpViewRowStatusEntry 11 }

vrSnmpViewProvTable OBJECT-TYPE
   SYNTAX     SEQUENCE OF VrSnmpViewProvEntry
   ACCESS     not-accessible
   STATUS     mandatory
   DESCRIPTION
     "This group contains provisionable attributes relating to SNMPv2 
      View Table SubTrees. The attributes are derived from rfc1445, and 
      rfc1447."
::= { vrSnmpView 10 }

vrSnmpViewProvEntry OBJECT-TYPE
   SYNTAX     VrSnmpViewProvEntry
   ACCESS     not-accessible
   STATUS     mandatory
   DESCRIPTION
     "An entry in the vrSnmpViewProvTable."
   INDEX {
      vrIndex,
      vrSnmpIndex,
      vrSnmpViewIndex,
      vrSnmpViewSubtreeIndex }
::= { vrSnmpViewProvTable 1 }

VrSnmpViewProvEntry ::= SEQUENCE {
   vrSnmpViewMask
      HexString,
   vrSnmpViewType
      INTEGER,
   vrSnmpViewRowStorageType
      INTEGER,
   vrSnmpViewStdRowStatus
      INTEGER }

vrSnmpViewMask OBJECT-TYPE
   SYNTAX     HexString (SIZE (0..16))
   ACCESS     read-write
   STATUS     mandatory
   DESCRIPTION
     "This attribute is the View mask which, in combination with the 
      corresponding instance of SnmpView subTree, defines a family of 
      view subtrees. 
      Each bit of this bit mask corresponds to a subindentifier of 
      SnmpView subTree, with the most significant bit of the i-th octet of 
      this octet string value (extended if necessary, see below) 
      corresponding to the (8*i - 7)-th sub-identifier, and the least 
      significant bit of the i-th octet of this octet string corresponding to 
      the (8*i)-th sub-identifier, where i is in the range 1 through 16.
      Each bit of this bit mask specifies whether or not the corresponding 
      sub-identifiers must match when determining if an OBJECT 
      IDENTIFIER is in this family of view subtrees; a '1' indicates that 
      an exact match must occur; a '0' indicates 'wild card', meaning that 
      any sub-identifier value matches.
      Thus, the OBJECT IDENTIFIER X of an object instance is 
      contained in a family of view subtrees if the following criteria are 
      met:
      For each sub-identifier of the value of SnmpView subTree, either the 
      i-th bit of mask is 0, or the i-th sub-identifier of X is equal to the i-th 
      sub-identifier of the value of SnmpView subTree. 
      If the value of this bit mask is M bits long and there are more than 
      M sub-identifiers in the corresponding instance of SnmpView 
      subTree, then the bit mask is extended with 1's to be the required 
      length.
      Note that when the value of this object is the zero-length string, this 
      extension rule results in a mask of all 1's being used (no wild card) 
      and the family of SnmpView subTrees is the one snmpView subTree 
      uniquely identified by the corresponding instance of subTree."
   DEFVAL     { ''H }  -- ""
::= { vrSnmpViewProvEntry 1 }

vrSnmpViewType OBJECT-TYPE
   SYNTAX     INTEGER  {
                 includedSubtree(1),
                 excludedSubtree(2) }
   ACCESS     read-write
   STATUS     mandatory
   DESCRIPTION
     "This attribute indicates whether the particular family of view 
      subtrees is included or excluded in the SNMPv2 context's (or 
      SNMPv1 community's) MIB view.
      The value 'includedSubtree' indicates that the corresponding 
      instances of subTree and mask define a family of view subtrees 
      included in the MIB view.
      The value 'excludedSubtree' indicates that the corresponding 
      instances of subTree and mask define a family of view subtrees 
      excluded in the MIB view."
   DEFVAL     { includedSubtree }
::= { vrSnmpViewProvEntry 2 }

vrSnmpViewRowStorageType OBJECT-TYPE
   SYNTAX     INTEGER  {
                 nonVolatile(3) }
   ACCESS     read-write
   STATUS     mandatory
   DESCRIPTION
     "The attribute indicates the storage type for this conceptual row in 
      the SNMPv2 viewTable. This is a constant - nonVolatile."
   DEFVAL     { nonVolatile }
::= { vrSnmpViewProvEntry 3 }

vrSnmpViewStdRowStatus OBJECT-TYPE
   SYNTAX     INTEGER  {
                 active(1) }
   ACCESS     read-write
   STATUS     mandatory
   DESCRIPTION
     "This attribute indicates the status of this conceptual row in the 
      SNMPv2 snmpViewTable. This is a constant - active."
   DEFVAL     { active }
::= { vrSnmpViewProvEntry 4 }


-- Vr/Vr_String Snmp ObjectResource/n
-- This component represents an entry in the SNMPv2 Object 
-- Resources Table (rfc1450). It lists the MIBs currently supported by 
-- the SNMP management entity.

vrSnmpOr OBJECT IDENTIFIER ::= { vrSnmp 8 }



vrSnmpOrRowStatusTable OBJECT-TYPE
   SYNTAX     SEQUENCE OF VrSnmpOrRowStatusEntry
   ACCESS     not-accessible
   STATUS     mandatory
   DESCRIPTION
     "This entry controls the addition and deletion of 
      vrSnmpOr components."
::= { vrSnmpOr 1 }

vrSnmpOrRowStatusEntry OBJECT-TYPE
   SYNTAX     VrSnmpOrRowStatusEntry
   ACCESS     not-accessible
   STATUS     mandatory
   DESCRIPTION
     "A single entry in the table represents a single 
      vrSnmpOr component."
   INDEX {
      vrIndex,
      vrSnmpIndex,
      vrSnmpOrIndex }
::= { vrSnmpOrRowStatusTable 1 }

VrSnmpOrRowStatusEntry ::= SEQUENCE {
   vrSnmpOrRowStatus
      RowStatus,
   vrSnmpOrComponentName
      DisplayString,
   vrSnmpOrStorageType
      StorageType,
   vrSnmpOrIndex
      Integer32 }

vrSnmpOrRowStatus OBJECT-TYPE
   SYNTAX     RowStatus 
   ACCESS     read-only
   STATUS     mandatory
   DESCRIPTION
     "This variable is used as the basis for SNMP naming of
      vrSnmpOr components.
      These components cannot be added nor deleted."
::= { vrSnmpOrRowStatusEntry 1 }

vrSnmpOrComponentName OBJECT-TYPE
   SYNTAX     DisplayString 
   ACCESS     read-only
   STATUS     mandatory
   DESCRIPTION
     "This variable provides the component's string name for
      use with the ASCII Console Interface"
::= { vrSnmpOrRowStatusEntry 2 }

vrSnmpOrStorageType OBJECT-TYPE
   SYNTAX     StorageType 
   ACCESS     read-only
   STATUS     mandatory
   DESCRIPTION
     "This variable represents the storage type value for the
      vrSnmpOr tables."
::= { vrSnmpOrRowStatusEntry 4 }

vrSnmpOrIndex OBJECT-TYPE
   SYNTAX     Integer32 (1..1024)
   ACCESS     not-accessible
   STATUS     mandatory
   DESCRIPTION
     "This variable represents the index for the vrSnmpOr tables."
::= { vrSnmpOrRowStatusEntry 10 }

vrSnmpOrOrTable OBJECT-TYPE
   SYNTAX     SEQUENCE OF VrSnmpOrOrEntry
   ACCESS     not-accessible
   STATUS     mandatory
   DESCRIPTION
     "The attributes of this group describe a MIB currently supported by 
      the SNMP agent. SNMP managers make use of these entries to 
      determine what is supported. The group is derived from rfc 1450."
::= { vrSnmpOr 10 }

vrSnmpOrOrEntry OBJECT-TYPE
   SYNTAX     VrSnmpOrOrEntry
   ACCESS     not-accessible
   STATUS     mandatory
   DESCRIPTION
     "An entry in the vrSnmpOrOrTable."
   INDEX {
      vrIndex,
      vrSnmpIndex,
      vrSnmpOrIndex }
::= { vrSnmpOrOrTable 1 }

VrSnmpOrOrEntry ::= SEQUENCE {
   vrSnmpOrId
      OBJECT IDENTIFIER,
   vrSnmpOrDescr
      AsciiString }

vrSnmpOrId OBJECT-TYPE
   SYNTAX     OBJECT IDENTIFIER 
   ACCESS     read-only
   STATUS     mandatory
   DESCRIPTION
     "This attribute represents the authoritative identification of a 
      dynamically-configurable management entity object resource. This 
      is a MIB Object Identifier."
::= { vrSnmpOrOrEntry 2 }

vrSnmpOrDescr OBJECT-TYPE
   SYNTAX     AsciiString (SIZE (0..255))
   ACCESS     read-only
   STATUS     mandatory
   DESCRIPTION
     "This attribute represents the textual description of a dynamically-
      configurable management entity object resource. This is an ASCII 
      description of a supported MIB."
::= { vrSnmpOrOrEntry 3 }


-- This component contains statistics based upon the SnmpV2 
-- Management Information Base SnmpV2 Statistics group (rfc1450).

vrSnmpV2Stats OBJECT IDENTIFIER ::= { vrSnmp 9 }



vrSnmpV2StatsRowStatusTable OBJECT-TYPE
   SYNTAX     SEQUENCE OF VrSnmpV2StatsRowStatusEntry
   ACCESS     not-accessible
   STATUS     obsolete
   DESCRIPTION
     "This entry controls the addition and deletion of 
      vrSnmpV2Stats components."
::= { vrSnmpV2Stats 1 }

vrSnmpV2StatsRowStatusEntry OBJECT-TYPE
   SYNTAX     VrSnmpV2StatsRowStatusEntry
   ACCESS     not-accessible
   STATUS     obsolete
   DESCRIPTION
     "A single entry in the table represents a single 
      vrSnmpV2Stats component."
   INDEX {
      vrIndex,
      vrSnmpIndex,
      vrSnmpV2StatsIndex }
::= { vrSnmpV2StatsRowStatusTable 1 }

VrSnmpV2StatsRowStatusEntry ::= SEQUENCE {
   vrSnmpV2StatsRowStatus
      RowStatus,
   vrSnmpV2StatsComponentName
      DisplayString,
   vrSnmpV2StatsStorageType
      StorageType,
   vrSnmpV2StatsIndex
      NonReplicated }

vrSnmpV2StatsRowStatus OBJECT-TYPE
   SYNTAX     RowStatus 
   ACCESS     read-only
   STATUS     obsolete
   DESCRIPTION
     "This variable is used as the basis for SNMP naming of
      vrSnmpV2Stats components.
      These components cannot be added nor deleted."
::= { vrSnmpV2StatsRowStatusEntry 1 }

vrSnmpV2StatsComponentName OBJECT-TYPE
   SYNTAX     DisplayString 
   ACCESS     read-only
   STATUS     obsolete
   DESCRIPTION
     "This variable provides the component's string name for
      use with the ASCII Console Interface"
::= { vrSnmpV2StatsRowStatusEntry 2 }

vrSnmpV2StatsStorageType OBJECT-TYPE
   SYNTAX     StorageType 
   ACCESS     read-only
   STATUS     obsolete
   DESCRIPTION
     "This variable represents the storage type value for the
      vrSnmpV2Stats tables."
::= { vrSnmpV2StatsRowStatusEntry 4 }

vrSnmpV2StatsIndex OBJECT-TYPE
   SYNTAX     NonReplicated 
   ACCESS     not-accessible
   STATUS     obsolete
   DESCRIPTION
     "This variable represents the index for the vrSnmpV2Stats tables."
::= { vrSnmpV2StatsRowStatusEntry 10 }

vrSnmpV2StatsStatsTable OBJECT-TYPE
   SYNTAX     SEQUENCE OF VrSnmpV2StatsStatsEntry
   ACCESS     not-accessible
   STATUS     obsolete
   DESCRIPTION
     "This attribute group contains the collection of statistics as defined 
      by SNMPv2 providing basic instrumentation of a SNMPv2 Agent. 
      The group is derived from rfc 1450. As the implementation is fully 
      bilingual in regards to Snmp V2/V1, statistics which apply only to 
      unilingual V2 Agents do not appear as attributes. Similarly as 
      privacy protocols are not supported, the relevant statistics have no 
      corresponding attributes."
::= { vrSnmpV2Stats 10 }

vrSnmpV2StatsStatsEntry OBJECT-TYPE
   SYNTAX     VrSnmpV2StatsStatsEntry
   ACCESS     not-accessible
   STATUS     obsolete
   DESCRIPTION
     "An entry in the vrSnmpV2StatsStatsTable."
   INDEX {
      vrIndex,
      vrSnmpIndex,
      vrSnmpV2StatsIndex }
::= { vrSnmpV2StatsStatsTable 1 }

VrSnmpV2StatsStatsEntry ::= SEQUENCE {
   vrSnmpV2StatsPackets
      Unsigned32,
   vrSnmpV2StatsEncodingErrors
      Unsigned32,
   vrSnmpV2StatsUnknownSrcParties
      Unsigned32,
   vrSnmpV2StatsBadAuths
      Unsigned32,
   vrSnmpV2StatsNotInLifetime
      Unsigned32,
   vrSnmpV2StatsWrongDigestValues
      Unsigned32,
   vrSnmpV2StatsUnknownContexts
      Unsigned32,
   vrSnmpV2StatsBadOperations
      Unsigned32,
   vrSnmpV2StatsSilentDrops
      Unsigned32 }

vrSnmpV2StatsPackets OBJECT-TYPE
   SYNTAX     Unsigned32 (0..4294967295)
   ACCESS     read-only
   STATUS     obsolete
   DESCRIPTION
     "This attribute represents the total number of SNMP messages 
      received by the SNMP management entity from the transport 
      service. This has the same value as inPackets in the 
      SnmpMibIIStatsOp group."
   DEFVAL     { 0 }
::= { vrSnmpV2StatsStatsEntry 1 }

vrSnmpV2StatsEncodingErrors OBJECT-TYPE
   SYNTAX     Unsigned32 (0..4294967295)
   ACCESS     read-only
   STATUS     obsolete
   DESCRIPTION
     "This attribute represents the total number of SNMP messages 
      received by the SNMP management entity which were improperly 
      BER encoded or had an invalid ASN.1 syntax. This has the same 
      value as inAsnParseErrs in the SnmpMibIIStatsOp group."
   DEFVAL     { 0 }
::= { vrSnmpV2StatsStatsEntry 2 }

vrSnmpV2StatsUnknownSrcParties OBJECT-TYPE
   SYNTAX     Unsigned32 (0..4294967295)
   ACCESS     read-only
   STATUS     obsolete
   DESCRIPTION
     "This attribute represents the total number of SNMPv2 messages 
      received by the SNMP management entity for which the message 
      source Party was not locally recognized."
   DEFVAL     { 0 }
::= { vrSnmpV2StatsStatsEntry 3 }

vrSnmpV2StatsBadAuths OBJECT-TYPE
   SYNTAX     Unsigned32 (0..4294967295)
   ACCESS     read-only
   STATUS     obsolete
   DESCRIPTION
     "This attribute represents the total number of SNMPv2 messages 
      received by the SNMP management entity for which the message 
      authentication protocol did not match that of the local source Party."
   DEFVAL     { 0 }
::= { vrSnmpV2StatsStatsEntry 4 }

vrSnmpV2StatsNotInLifetime OBJECT-TYPE
   SYNTAX     Unsigned32 (0..4294967295)
   ACCESS     read-only
   STATUS     obsolete
   DESCRIPTION
     "This attribute represents the total number of SNMPv2 messages 
      received by the SNMP management entity for which the message 
      source TimeStamp was less than the combination of the local source 
      Party's clock and lifetime."
   DEFVAL     { 0 }
::= { vrSnmpV2StatsStatsEntry 5 }

vrSnmpV2StatsWrongDigestValues OBJECT-TYPE
   SYNTAX     Unsigned32 (0..4294967295)
   ACCESS     read-only
   STATUS     obsolete
   DESCRIPTION
     "This attribute represents the total number of SNMPv2 messages 
      received by the SNMP management entity for which the message 
      authentication Digest Value was invalid."
   DEFVAL     { 0 }
::= { vrSnmpV2StatsStatsEntry 6 }

vrSnmpV2StatsUnknownContexts OBJECT-TYPE
   SYNTAX     Unsigned32 (0..4294967295)
   ACCESS     read-only
   STATUS     obsolete
   DESCRIPTION
     "This attribute represents the total number of SNMPv2 messages 
      received by the SNMP management entity for which the message 
      Context was not locally known."
   DEFVAL     { 0 }
::= { vrSnmpV2StatsStatsEntry 7 }

vrSnmpV2StatsBadOperations OBJECT-TYPE
   SYNTAX     Unsigned32 (0..4294967295)
   ACCESS     read-only
   STATUS     obsolete
   DESCRIPTION
     "This attribute represents the total number of SNMPv2 messages 
      received by the SNMP management entity for which the PDU type 
      was not allowed in the local Access Privileges Entry."
   DEFVAL     { 0 }
::= { vrSnmpV2StatsStatsEntry 8 }

vrSnmpV2StatsSilentDrops OBJECT-TYPE
   SYNTAX     Unsigned32 (0..4294967295)
   ACCESS     read-only
   STATUS     obsolete
   DESCRIPTION
     "This attribute represents the total number of SNMPv2 messages 
      received by the SNMP management entity which were silently 
      ignored because an alternate response message was greater than a 
      local constraint or greater than the maximum message size allowed 
      for the source Party. In other words, this attribute counts the number 
      of error responses pdu's which could not be generated due to size 
      constraints."
   DEFVAL     { 0 }
::= { vrSnmpV2StatsStatsEntry 9 }


-- This component contains statistics based upon the SnmpV2 
-- Management Information Base SnmpV1 Statistics group (rfc1450).

vrSnmpV1Stats OBJECT IDENTIFIER ::= { vrSnmp 10 }



vrSnmpV1StatsRowStatusTable OBJECT-TYPE
   SYNTAX     SEQUENCE OF VrSnmpV1StatsRowStatusEntry
   ACCESS     not-accessible
   STATUS     mandatory
   DESCRIPTION
     "This entry controls the addition and deletion of 
      vrSnmpV1Stats components."
::= { vrSnmpV1Stats 1 }

vrSnmpV1StatsRowStatusEntry OBJECT-TYPE
   SYNTAX     VrSnmpV1StatsRowStatusEntry
   ACCESS     not-accessible
   STATUS     mandatory
   DESCRIPTION
     "A single entry in the table represents a single 
      vrSnmpV1Stats component."
   INDEX {
      vrIndex,
      vrSnmpIndex,
      vrSnmpV1StatsIndex }
::= { vrSnmpV1StatsRowStatusTable 1 }

VrSnmpV1StatsRowStatusEntry ::= SEQUENCE {
   vrSnmpV1StatsRowStatus
      RowStatus,
   vrSnmpV1StatsComponentName
      DisplayString,
   vrSnmpV1StatsStorageType
      StorageType,
   vrSnmpV1StatsIndex
      NonReplicated }

vrSnmpV1StatsRowStatus OBJECT-TYPE
   SYNTAX     RowStatus 
   ACCESS     read-only
   STATUS     mandatory
   DESCRIPTION
     "This variable is used as the basis for SNMP naming of
      vrSnmpV1Stats components.
      These components cannot be added nor deleted."
::= { vrSnmpV1StatsRowStatusEntry 1 }

vrSnmpV1StatsComponentName OBJECT-TYPE
   SYNTAX     DisplayString 
   ACCESS     read-only
   STATUS     mandatory
   DESCRIPTION
     "This variable provides the component's string name for
      use with the ASCII Console Interface"
::= { vrSnmpV1StatsRowStatusEntry 2 }

vrSnmpV1StatsStorageType OBJECT-TYPE
   SYNTAX     StorageType 
   ACCESS     read-only
   STATUS     mandatory
   DESCRIPTION
     "This variable represents the storage type value for the
      vrSnmpV1Stats tables."
::= { vrSnmpV1StatsRowStatusEntry 4 }

vrSnmpV1StatsIndex OBJECT-TYPE
   SYNTAX     NonReplicated 
   ACCESS     not-accessible
   STATUS     mandatory
   DESCRIPTION
     "This variable represents the index for the vrSnmpV1Stats tables."
::= { vrSnmpV1StatsRowStatusEntry 10 }

vrSnmpV1StatsStatsTable OBJECT-TYPE
   SYNTAX     SEQUENCE OF VrSnmpV1StatsStatsEntry
   ACCESS     not-accessible
   STATUS     mandatory
   DESCRIPTION
     "This attribute group contains the collection of statistics as defined 
      by SNMPv2 providing basic instrumentation of a SNMPv2 Agent 
      which also implements SNMPv1. The group is derived from rfc 
      1450."
::= { vrSnmpV1Stats 10 }

vrSnmpV1StatsStatsEntry OBJECT-TYPE
   SYNTAX     VrSnmpV1StatsStatsEntry
   ACCESS     not-accessible
   STATUS     mandatory
   DESCRIPTION
     "An entry in the vrSnmpV1StatsStatsTable."
   INDEX {
      vrIndex,
      vrSnmpIndex,
      vrSnmpV1StatsIndex }
::= { vrSnmpV1StatsStatsTable 1 }

VrSnmpV1StatsStatsEntry ::= SEQUENCE {
   vrSnmpV1StatsBadCommunityNames
      Unsigned32,
   vrSnmpV1StatsBadCommunityUses
      Unsigned32 }

vrSnmpV1StatsBadCommunityNames OBJECT-TYPE
   SYNTAX     Unsigned32 (0..4294967295)
   ACCESS     read-only
   STATUS     mandatory
   DESCRIPTION
     "This attribute counts the SNMPv1 messages received by the SNMP 
      management entity which had an unknown SNMPv1 Community 
      string. This has the same value as the attribute 
      inBadCommunityNames under the SnmpMibIIStats component."
   DEFVAL     { 0 }
::= { vrSnmpV1StatsStatsEntry 1 }

vrSnmpV1StatsBadCommunityUses OBJECT-TYPE
   SYNTAX     Unsigned32 (0..4294967295)
   ACCESS     read-only
   STATUS     mandatory
   DESCRIPTION
     "This attribute counts the SNMPv1 messages received by the SNMP 
      management entity which attempted to perform an operation not 
      allowed for the indicated SNMPv1 Community. This has the same 
      value as the attribute inBadCommunityUses under the 
      SnmpMibIIStats component."
   DEFVAL     { 0 }
::= { vrSnmpV1StatsStatsEntry 2 }


-- This component contains statistics based upon the MIB II Snmp 
-- group (rfc1213).

vrSnmpMibIIStats OBJECT IDENTIFIER ::= { vrSnmp 11 }



vrSnmpMibIIStatsRowStatusTable OBJECT-TYPE
   SYNTAX     SEQUENCE OF VrSnmpMibIIStatsRowStatusEntry
   ACCESS     not-accessible
   STATUS     mandatory
   DESCRIPTION
     "This entry controls the addition and deletion of 
      vrSnmpMibIIStats components."
::= { vrSnmpMibIIStats 1 }

vrSnmpMibIIStatsRowStatusEntry OBJECT-TYPE
   SYNTAX     VrSnmpMibIIStatsRowStatusEntry
   ACCESS     not-accessible
   STATUS     mandatory
   DESCRIPTION
     "A single entry in the table represents a single 
      vrSnmpMibIIStats component."
   INDEX {
      vrIndex,
      vrSnmpIndex,
      vrSnmpMibIIStatsIndex }
::= { vrSnmpMibIIStatsRowStatusTable 1 }

VrSnmpMibIIStatsRowStatusEntry ::= SEQUENCE {
   vrSnmpMibIIStatsRowStatus
      RowStatus,
   vrSnmpMibIIStatsComponentName
      DisplayString,
   vrSnmpMibIIStatsStorageType
      StorageType,
   vrSnmpMibIIStatsIndex
      NonReplicated }

vrSnmpMibIIStatsRowStatus OBJECT-TYPE
   SYNTAX     RowStatus 
   ACCESS     read-only
   STATUS     mandatory
   DESCRIPTION
     "This variable is used as the basis for SNMP naming of
      vrSnmpMibIIStats components.
      These components cannot be added nor deleted."
::= { vrSnmpMibIIStatsRowStatusEntry 1 }

vrSnmpMibIIStatsComponentName OBJECT-TYPE
   SYNTAX     DisplayString 
   ACCESS     read-only
   STATUS     mandatory
   DESCRIPTION
     "This variable provides the component's string name for
      use with the ASCII Console Interface"
::= { vrSnmpMibIIStatsRowStatusEntry 2 }

vrSnmpMibIIStatsStorageType OBJECT-TYPE
   SYNTAX     StorageType 
   ACCESS     read-only
   STATUS     mandatory
   DESCRIPTION
     "This variable represents the storage type value for the
      vrSnmpMibIIStats tables."
::= { vrSnmpMibIIStatsRowStatusEntry 4 }

vrSnmpMibIIStatsIndex OBJECT-TYPE
   SYNTAX     NonReplicated 
   ACCESS     not-accessible
   STATUS     mandatory
   DESCRIPTION
     "This variable represents the index for the vrSnmpMibIIStats tables."
::= { vrSnmpMibIIStatsRowStatusEntry 10 }

vrSnmpMibIIStatsStatsTable OBJECT-TYPE
   SYNTAX     SEQUENCE OF VrSnmpMibIIStatsStatsEntry
   ACCESS     not-accessible
   STATUS     mandatory
   DESCRIPTION
     "This attribute group contains the collection of statistics as defined 
      by MIB II providing basic instrumentation of a SNMP Agent. The 
      group is derived from rfc 1213. Statistics which are only relevant 
      for SNMP Managers do not appear."
::= { vrSnmpMibIIStats 10 }

vrSnmpMibIIStatsStatsEntry OBJECT-TYPE
   SYNTAX     VrSnmpMibIIStatsStatsEntry
   ACCESS     not-accessible
   STATUS     mandatory
   DESCRIPTION
     "An entry in the vrSnmpMibIIStatsStatsTable."
   INDEX {
      vrIndex,
      vrSnmpIndex,
      vrSnmpMibIIStatsIndex }
::= { vrSnmpMibIIStatsStatsTable 1 }

VrSnmpMibIIStatsStatsEntry ::= SEQUENCE {
   vrSnmpMibIIStatsInPackets
      Unsigned32,
   vrSnmpMibIIStatsInBadCommunityNames
      Unsigned32,
   vrSnmpMibIIStatsInBadCommunityUses
      Unsigned32,
   vrSnmpMibIIStatsInAsnParseErrs
      Unsigned32,
   vrSnmpMibIIStatsOutPackets
      Unsigned32,
   vrSnmpMibIIStatsInBadVersions
      Unsigned32,
   vrSnmpMibIIStatsInTotalReqVars
      Unsigned32,
   vrSnmpMibIIStatsInTotalSetVars
      Unsigned32,
   vrSnmpMibIIStatsInGetRequests
      Unsigned32,
   vrSnmpMibIIStatsInGetNexts
      Unsigned32,
   vrSnmpMibIIStatsInSetRequests
      Unsigned32,
   vrSnmpMibIIStatsOutTooBigs
      Unsigned32,
   vrSnmpMibIIStatsOutNoSuchNames
      Unsigned32,
   vrSnmpMibIIStatsOutBadValues
      Unsigned32,
   vrSnmpMibIIStatsOutGenErrs
      Unsigned32,
   vrSnmpMibIIStatsOutGetResponses
      Unsigned32,
   vrSnmpMibIIStatsOutTraps
      Unsigned32 }

vrSnmpMibIIStatsInPackets OBJECT-TYPE
   SYNTAX     Unsigned32 (0..4294967295)
   ACCESS     read-only
   STATUS     mandatory
   DESCRIPTION
     "This attribute represents the total number of SNMP messages 
      received by the SNMP management entity."
   DEFVAL     { 0 }
::= { vrSnmpMibIIStatsStatsEntry 1 }

vrSnmpMibIIStatsInBadCommunityNames OBJECT-TYPE
   SYNTAX     Unsigned32 (0..4294967295)
   ACCESS     read-only
   STATUS     mandatory
   DESCRIPTION
     "This attribute counts the SNMPv1 messages received by the SNMP 
      management entity which had an unknown SNMPv1 Community 
      string. This has the same value as the attribute 
      badCommunityNames under the SnmpV1Stats component."
   DEFVAL     { 0 }
::= { vrSnmpMibIIStatsStatsEntry 2 }

vrSnmpMibIIStatsInBadCommunityUses OBJECT-TYPE
   SYNTAX     Unsigned32 (0..4294967295)
   ACCESS     read-only
   STATUS     mandatory
   DESCRIPTION
     "This attribute counts the SNMPv1 messages received by the SNMP 
      management entity which attempted to perform an operation not 
      allowed for the indicated SNMPv1 Community. This has the same 
      value as the attribute badCommunityUses under the SnmpV1Stats 
      component."
   DEFVAL     { 0 }
::= { vrSnmpMibIIStatsStatsEntry 3 }

vrSnmpMibIIStatsInAsnParseErrs OBJECT-TYPE
   SYNTAX     Unsigned32 (0..4294967295)
   ACCESS     read-only
   STATUS     mandatory
   DESCRIPTION
     "This attribute counts the SNMP messages received by the SNMP 
      management entity which were improperly BER encoded or had an 
      invalid ASN.1 syntax."
   DEFVAL     { 0 }
::= { vrSnmpMibIIStatsStatsEntry 4 }

vrSnmpMibIIStatsOutPackets OBJECT-TYPE
   SYNTAX     Unsigned32 (0..4294967295)
   ACCESS     read-only
   STATUS     mandatory
   DESCRIPTION
     "This attribute counts the SNMP messages transmitted by the SNMP 
      management entity."
   DEFVAL     { 0 }
::= { vrSnmpMibIIStatsStatsEntry 5 }

vrSnmpMibIIStatsInBadVersions OBJECT-TYPE
   SYNTAX     Unsigned32 (0..4294967295)
   ACCESS     read-only
   STATUS     mandatory
   DESCRIPTION
     "This attribute counts the SNMPv1 messages received by the SNMP 
      management entity with an invalid SNMP version number."
   DEFVAL     { 0 }
::= { vrSnmpMibIIStatsStatsEntry 6 }

vrSnmpMibIIStatsInTotalReqVars OBJECT-TYPE
   SYNTAX     Unsigned32 (0..4294967295)
   ACCESS     read-only
   STATUS     mandatory
   DESCRIPTION
     "This attribute counts the MIB objects successfully retrieved by Get, 
      and Get-Next requests."
   DEFVAL     { 0 }
::= { vrSnmpMibIIStatsStatsEntry 7 }

vrSnmpMibIIStatsInTotalSetVars OBJECT-TYPE
   SYNTAX     Unsigned32 (0..4294967295)
   ACCESS     read-only
   STATUS     mandatory
   DESCRIPTION
     "This attribute counts the MIB objects successfully Set by SNMP 
      requests."
   DEFVAL     { 0 }
::= { vrSnmpMibIIStatsStatsEntry 8 }

vrSnmpMibIIStatsInGetRequests OBJECT-TYPE
   SYNTAX     Unsigned32 (0..4294967295)
   ACCESS     read-only
   STATUS     mandatory
   DESCRIPTION
     "This attribute counts the Get requests accepted and processed by the 
      SNMP management entity."
   DEFVAL     { 0 }
::= { vrSnmpMibIIStatsStatsEntry 9 }

vrSnmpMibIIStatsInGetNexts OBJECT-TYPE
   SYNTAX     Unsigned32 (0..4294967295)
   ACCESS     read-only
   STATUS     mandatory
   DESCRIPTION
     "This attribute counts the Get-Next requests accepted and processed 
      by the SNMP management entity."
   DEFVAL     { 0 }
::= { vrSnmpMibIIStatsStatsEntry 10 }

vrSnmpMibIIStatsInSetRequests OBJECT-TYPE
   SYNTAX     Unsigned32 (0..4294967295)
   ACCESS     read-only
   STATUS     mandatory
   DESCRIPTION
     "This attribute counts the Set requests accepted and processed by the 
      SNMP management entity."
   DEFVAL     { 0 }
::= { vrSnmpMibIIStatsStatsEntry 11 }

vrSnmpMibIIStatsOutTooBigs OBJECT-TYPE
   SYNTAX     Unsigned32 (0..4294967295)
   ACCESS     read-only
   STATUS     mandatory
   DESCRIPTION
     "This attribute counts the responses generated by the SNMP 
      management entity with an error-status field of tooBig."
   DEFVAL     { 0 }
::= { vrSnmpMibIIStatsStatsEntry 12 }

vrSnmpMibIIStatsOutNoSuchNames OBJECT-TYPE
   SYNTAX     Unsigned32 (0..4294967295)
   ACCESS     read-only
   STATUS     mandatory
   DESCRIPTION
     "This attribute counts the SNMPv1 responses generated by the 
      SNMP management entity with an error status field of 
      noSuchName."
   DEFVAL     { 0 }
::= { vrSnmpMibIIStatsStatsEntry 13 }

vrSnmpMibIIStatsOutBadValues OBJECT-TYPE
   SYNTAX     Unsigned32 (0..4294967295)
   ACCESS     read-only
   STATUS     mandatory
   DESCRIPTION
     "This attribute counts the SNMPv1 responses generated by the 
      SNMP management entity with an error status field of badValue."
   DEFVAL     { 0 }
::= { vrSnmpMibIIStatsStatsEntry 14 }

vrSnmpMibIIStatsOutGenErrs OBJECT-TYPE
   SYNTAX     Unsigned32 (0..4294967295)
   ACCESS     read-only
   STATUS     mandatory
   DESCRIPTION
     "This attribute counts the SNMP responses generated by the SNMP 
      management entity with an error-status field of genErr."
   DEFVAL     { 0 }
::= { vrSnmpMibIIStatsStatsEntry 15 }

vrSnmpMibIIStatsOutGetResponses OBJECT-TYPE
   SYNTAX     Unsigned32 (0..4294967295)
   ACCESS     read-only
   STATUS     mandatory
   DESCRIPTION
     "This attribute counts the Get responses generated by the SNMP 
      management entity."
   DEFVAL     { 0 }
::= { vrSnmpMibIIStatsStatsEntry 16 }

vrSnmpMibIIStatsOutTraps OBJECT-TYPE
   SYNTAX     Unsigned32 (0..4294967295)
   ACCESS     read-only
   STATUS     mandatory
   DESCRIPTION
     "This attribute counts the Traps generated by the SNMP management 
      entity."
   DEFVAL     { 0 }
::= { vrSnmpMibIIStatsStatsEntry 17 }


-- VirtualRouter/string SnmpInitialConfiguration
-- This component contains the information required for the definition 
-- of SNMPv2 initial parties, contexts, views, and access control 
-- policies. The definition of initial parties is described in rfc1447.
-- If this component is present and its attributes are properly set when 
-- the Snmp component is added, then the initial instances of Acl, 
-- Party, Context, and View components will be added automatically. 
-- If this component is not present or its attributes are not set, then 
-- when the Snmp component is added, no initial instances of the 
-- aforementioned components will be added.

vrInitSnmpConfig OBJECT IDENTIFIER ::= { vr 9 }



vrInitSnmpConfigRowStatusTable OBJECT-TYPE
   SYNTAX     SEQUENCE OF VrInitSnmpConfigRowStatusEntry
   ACCESS     not-accessible
   STATUS     obsolete
   DESCRIPTION
     "This entry controls the addition and deletion of 
      vrInitSnmpConfig components."
::= { vrInitSnmpConfig 1 }

vrInitSnmpConfigRowStatusEntry OBJECT-TYPE
   SYNTAX     VrInitSnmpConfigRowStatusEntry
   ACCESS     not-accessible
   STATUS     obsolete
   DESCRIPTION
     "A single entry in the table represents a single 
      vrInitSnmpConfig component."
   INDEX {
      vrIndex,
      vrInitSnmpConfigIndex }
::= { vrInitSnmpConfigRowStatusTable 1 }

VrInitSnmpConfigRowStatusEntry ::= SEQUENCE {
   vrInitSnmpConfigRowStatus
      RowStatus,
   vrInitSnmpConfigComponentName
      DisplayString,
   vrInitSnmpConfigStorageType
      StorageType,
   vrInitSnmpConfigIndex
      NonReplicated }

vrInitSnmpConfigRowStatus OBJECT-TYPE
   SYNTAX     RowStatus 
   ACCESS     read-write
   STATUS     obsolete
   DESCRIPTION
     "This variable is used as the basis for SNMP naming of
      vrInitSnmpConfig components.
      These components can be added and deleted."
::= { vrInitSnmpConfigRowStatusEntry 1 }

vrInitSnmpConfigComponentName OBJECT-TYPE
   SYNTAX     DisplayString 
   ACCESS     read-only
   STATUS     obsolete
   DESCRIPTION
     "This variable provides the component's string name for
      use with the ASCII Console Interface"
::= { vrInitSnmpConfigRowStatusEntry 2 }

vrInitSnmpConfigStorageType OBJECT-TYPE
   SYNTAX     StorageType 
   ACCESS     read-only
   STATUS     obsolete
   DESCRIPTION
     "This variable represents the storage type value for the
      vrInitSnmpConfig tables."
::= { vrInitSnmpConfigRowStatusEntry 4 }

vrInitSnmpConfigIndex OBJECT-TYPE
   SYNTAX     NonReplicated 
   ACCESS     not-accessible
   STATUS     obsolete
   DESCRIPTION
     "This variable represents the index for the vrInitSnmpConfig tables."
::= { vrInitSnmpConfigRowStatusEntry 10 }

vrInitSnmpConfigProvTable OBJECT-TYPE
   SYNTAX     SEQUENCE OF VrInitSnmpConfigProvEntry
   ACCESS     not-accessible
   STATUS     obsolete
   DESCRIPTION
     "This group contains provisionable attributes required for the 
      definition of initial SNMPv2 parties, contexts, views, and access 
      control policies, as defined in rfc1447."
::= { vrInitSnmpConfig 10 }

vrInitSnmpConfigProvEntry OBJECT-TYPE
   SYNTAX     VrInitSnmpConfigProvEntry
   ACCESS     not-accessible
   STATUS     obsolete
   DESCRIPTION
     "An entry in the vrInitSnmpConfigProvTable."
   INDEX {
      vrIndex,
      vrInitSnmpConfigIndex }
::= { vrInitSnmpConfigProvTable 1 }

VrInitSnmpConfigProvEntry ::= SEQUENCE {
   vrInitSnmpConfigAgentAddress
      AsciiString,
   vrInitSnmpConfigManagerAddress
      AsciiString }

vrInitSnmpConfigAgentAddress OBJECT-TYPE
   SYNTAX     AsciiString (SIZE (1..80))
   ACCESS     read-write
   STATUS     obsolete
   DESCRIPTION
     "This attribute is the address of the Virtual Router where the initial 
      Agent parties will receive network management traffic. It is used to 
      initialize the transport address of the initial local parties and also is 
      used to define initial party and context identifiers.
      The format of the agentAddress is an IpAddress."
::= { vrInitSnmpConfigProvEntry 1 }

vrInitSnmpConfigManagerAddress OBJECT-TYPE
   SYNTAX     AsciiString (SIZE (1..80))
   ACCESS     read-write
   STATUS     obsolete
   DESCRIPTION
     "This attribute is the address of the SNMPv2 manager. It is used to 
      initialize the transport address of the initial non-local parties.
      The format of the managerAddress is an IpAddress."
::= { vrInitSnmpConfigProvEntry 2 }




-- 
-- Version and Compliance statements
-- 



-- Object-Group Statement:
-- A list of all current accessible leaf objects.

-- OBJECTS { vrSnmpMibIIStatsComponentName,
--           vrSnmpOrId,
--           vrSnmpMibIIStatsOutGetResponses,
--           vrSnmpOrStorageType,
--           vrSnmpV1EnableAuthenTraps,
--           vrSnmpV1StatsBadCommunityUses,
--           vrSnmpMibIIStatsInTotalSetVars,
--           vrSnmpSysStorageType,
--           vrSnmpComRowStatus,
--           vrSnmpSysName,
--           vrSnmpControlStatus,
--           vrSnmpAdminState,
--           vrSnmpV1StatsBadCommunityNames,
--           vrSnmpMibIIStatsInBadVersions,
--           vrSnmpSysServices,
--           vrSnmpMibIIStatsOutGenErrs,
--           vrSnmpMibIIStatsOutBadValues,
--           vrSnmpViewStorageType,
--           vrSnmpRowStatus,
--           vrSnmpViewRowStatus,
--           vrSnmpSysContact,
--           vrSnmpProceduralStatus,
--           vrSnmpComManStorageType,
--           vrSnmpMibIIStatsInGetNexts,
--           vrSnmpMgrOfLastAuthFailure,
--           vrSnmpMibIIStatsInBadCommunityUses,
--           vrSnmpComComponentName,
--           vrSnmpOrRowStatus,
--           vrSnmpUsageState,
--           vrSnmpSysRowStatus,
--           vrSnmpOrDescr,
--           vrSnmpViewRowStorageType,
--           vrSnmpMibIIStatsOutTraps,
--           vrSnmpComponentName,
--           vrSnmpMibIIStatsOutNoSuchNames,
--           vrSnmpV1StatsStorageType,
--           vrSnmpTrapsProcessed,
--           vrSnmpComManRowStatus,
--           vrSnmpSysObjectId,
--           vrSnmpSysLocation,
--           vrSnmpMibIIStatsInBadCommunityNames,
--           vrSnmpOrComponentName,
--           vrSnmpOperationalState,
--           vrSnmpLastAuthFailure,
--           vrSnmpSysComponentName,
--           vrSnmpMibIIStatsInTotalReqVars,
--           vrSnmpViewStdRowStatus,
--           vrSnmpViewMask,
--           vrSnmpLastOrChange,
--           vrSnmpViewType,
--           vrSnmpAlarmsAsTraps,
--           vrSnmpComManComponentName,
--           vrSnmpComStorageType,
--           vrSnmpMibIIStatsOutTooBigs,
--           vrSnmpMibIIStatsInSetRequests,
--           vrSnmpV1StatsRowStatus,
--           vrSnmpViewComponentName,
--           vrSnmpAvailabilityStatus,
--           vrSnmpMibIIStatsInAsnParseErrs,
--           vrSnmpComManTransportAddress,
--           vrSnmpMibIIStatsOutPackets,
--           vrSnmpCidInEntTraps,
--           vrSnmpComViewIndex,
--           vrSnmpIpStack,
--           vrSnmpMibIIStatsRowStatus,
--           vrSnmpMibIIStatsInGetRequests,
--           vrSnmpAlarmStatus,
--           vrSnmpComAccessMode,
--           vrSnmpMibIIStatsInPackets,
--           vrSnmpV1StatsComponentName,
--           vrSnmpUnknownStatus,
--           vrSnmpStandbyStatus,
--           vrSnmpV2EnableAuthenTraps,
--           vrSnmpSysDescription,
--           vrSnmpTrapsDiscarded,
--           vrSnmpSysUpTime,
--           vrSnmpStorageType,
--           vrSnmpComManPrivileges,
--           vrSnmpComTDomain,
--           vrSnmpMibIIStatsStorageType,
--           vrSnmpComCommunityString }
-- STATUS  mandatory
-- DESCRIPTION
--   "A list of all current accessible leaf objects."

baseSnmpGroup OBJECT IDENTIFIER ::= { baseSnmpMIB 1 }
baseSnmpGroupBD OBJECT IDENTIFIER ::= { baseSnmpGroup 4 }
baseSnmpGroupBD01 OBJECT IDENTIFIER ::= { baseSnmpGroupBD 2 }
baseSnmpGroupBD01A OBJECT IDENTIFIER ::= { baseSnmpGroupBD01 2 }



-- Agent-Capabilities Statement:

-- PRODUCT-RELEASE "Passport Release 7.0 BaseSnmp."
-- STATUS          mandatory
-- DESCRIPTION     "BaseSnmp MIB: MIB Version BD01A,
--                  Software Version BG00S4C."
-- SUPPORTS        Nortel-Magellan-Passport-BaseSnmpMIB
--    INCLUDES     { baseSnmpGroupBD01A }
--       rfc1213 (MIB II)
-- 
-- SUPPORTS          RFC1213-MIB
--    INCLUDES	        { system, interfaces, snmp }
-- 
--       variations for SNMP group of rfc1213
-- 
--    VARIATION		snmpInTooBigs
--       ACCESS		not-implemented
--       DESCRIPTION	"Not applicable for Agent"
-- 
--    VARIATION		snmpInNoSuchNames
--       ACCESS		not-implemented
--       DESCRIPTION	"Not applicable for Agent"
-- 
--    VARIATION		snmpInBadValues
--       ACCESS		not-implemented
--       DESCRIPTION	"Not applicable for Agent"
-- 
--    VARIATION		snmpInReadOnlys
--       ACCESS		not-implemented
--       DESCRIPTION	"Not applicable for Agent"
-- 
--    VARIATION		snmpInGenErrs
--       ACCESS		not-implemented
--       DESCRIPTION	"Not applicable for Agent"
-- 
--    VARIATION		snmpInGetResponses
--       ACCESS		not-implemented
--       DESCRIPTION	"Not applicable for Agent"
-- 
--    VARIATION		snmpInTraps
--       ACCESS		not-implemented
--       DESCRIPTION	"Not applicable for Agent"
-- 
--    VARIATION		snmpOutGetRequests
--       ACCESS		not-implemented
--       DESCRIPTION	"Not applicable for Agent"
-- 
--    VARIATION		snmpOutGetNexts
--       ACCESS		not-implemented
--       DESCRIPTION	"Not applicable for Agent"
-- 
--    VARIATION		snmpOutSetRequests
--       ACCESS		not-implemented
--       DESCRIPTION	"Not applicable for Agent"
-- 
-- 
--    rfc1450
-- 
-- SUPPORTS SNMPv2-MIB
--    INCLUDES          { snmpStats, snmpV1, snmpOR, snmpTrap, snmpSet }
-- 
--       variations for snmpStats group
-- 
--    VARIATION		snmpStats30Something
--       ACCESS		not-implemented
--       DESCRIPTION	"Inapplicable for an agent supporting V1"
-- 
--    VARIATION		snmpStatsUnknownDstParties
--       ACCESS		not-implemented
--       DESCRIPTION	"Inapplicable since privacy not supported"
-- 
--    VARIATION 		snmpStatsDstPartyMismatches
--       ACCESS		not-implemented
--       DESCRIPTION	"Inapplicable since privacy not supported"
-- 
-- 

baseSnmpCapabilities OBJECT IDENTIFIER ::= { baseSnmpMIB 3 }
baseSnmpCapabilitiesBD OBJECT IDENTIFIER ::= { baseSnmpCapabilities 4 }
baseSnmpCapabilitiesBD01 OBJECT IDENTIFIER ::= { baseSnmpCapabilitiesBD 2 }
baseSnmpCapabilitiesBD01A OBJECT IDENTIFIER ::= { baseSnmpCapabilitiesBD01 2 }





END
