Nortel-Magellan-Passport-PorsAtmTrunksMIB
DEFINITIONS ::= BEGIN



IMPORTS

      OBJECT-TYPE
   FROM RFC-1212

      passportMIBs
   FROM Nortel-Magellan-Passport-UsefulDefinitionsMIB

      DisplayString,
      StorageType,
      RowStatus
   FROM Nortel-Magellan-Passport-StandardTextualConventionsMIB

      NonReplicated,
      Link
   FROM Nortel-Magellan-Passport-TextualConventionsMIB

      trkPaIndex,
      trkPa
   FROM Nortel-Magellan-Passport-PorsTrunksMIB

      trkIndex
   FROM Nortel-Magellan-Passport-TrunksMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     PorsAtmTrunks Enterprise MIB."

porsAtmTrunksMIB OBJECT IDENTIFIER ::= { passportMIBs 137 }










-- Trunk/n PathAdmin AtmAccess
-- This subcomponent is optionally added to the PathAdmin 
-- component on ATM hardware. 
-- Without this subcomponent the PathAdmin will transport all Path 
-- Oriented traffic as AAL5 encapsulated cells on the Trunk 
-- AtmAccess localConnection VCC.
-- With this subcomponent added under the PathAdmin the PathAdmin 
-- will operate in one of two modes. These modes are referred to as 
-- mapping and multiplexing and the selection of the mode is done by 
-- setting the PathAdmin AtmAccess mode attribute to either mapping 
-- or multiplexing.
-- When the mode is set to mapping, the PathAdmin will create new 
-- VCCs for each new LCh that it sets up. In mapped mode the CPU 
-- usage is normally 0 for a connection and so the ATM FP can 
-- support a great many more mapped mode connections than it can 
-- multiplexed mode connections. Connections whose 
-- maximumTransmissionUnit is exactly 45 will use the SPO adaption 
-- layer to efficiently fit a single voice frame into a single cell with 
-- minimum overhead. All other connections will use the AAL5 
-- adaption layer protocol.
-- When the mode is set to multiplexing, the PathAdmin will look at 
-- the attribute atmConnection which points to a second provisioned 
-- ATM VCC. The PathAdmin will then multiplex voice frames onto 
-- this second VCC using a proprietary Short Path Oriented adaption 
-- layer which encapsulates one voice frame into one voice cell with 
-- low overhead. The PathAdmin will multiplex all non voice traffic 
-- over the Trunk/n AtmAccess atmConnection VCC using the AAL5 
-- protocol.

trkPaAtm OBJECT IDENTIFIER ::= { trkPa 3 }



trkPaAtmRowStatusTable OBJECT-TYPE
   SYNTAX     SEQUENCE OF TrkPaAtmRowStatusEntry
   ACCESS     not-accessible
   STATUS     mandatory
   DESCRIPTION
     "This entry controls the addition and deletion of 
      trkPaAtm components."
::= { trkPaAtm 1 }

trkPaAtmRowStatusEntry OBJECT-TYPE
   SYNTAX     TrkPaAtmRowStatusEntry
   ACCESS     not-accessible
   STATUS     mandatory
   DESCRIPTION
     "A single entry in the table represents a single 
      trkPaAtm component."
   INDEX {
      trkIndex,
      trkPaIndex,
      trkPaAtmIndex }
::= { trkPaAtmRowStatusTable 1 }

TrkPaAtmRowStatusEntry ::= SEQUENCE {
   trkPaAtmRowStatus
      RowStatus,
   trkPaAtmComponentName
      DisplayString,
   trkPaAtmStorageType
      StorageType,
   trkPaAtmIndex
      NonReplicated }

trkPaAtmRowStatus OBJECT-TYPE
   SYNTAX     RowStatus 
   ACCESS     read-write
   STATUS     mandatory
   DESCRIPTION
     "This variable is used as the basis for SNMP naming of
      trkPaAtm components.
      These components can be added and deleted."
::= { trkPaAtmRowStatusEntry 1 }

trkPaAtmComponentName OBJECT-TYPE
   SYNTAX     DisplayString 
   ACCESS     read-only
   STATUS     mandatory
   DESCRIPTION
     "This variable provides the component's string name for
      use with the ASCII Console Interface"
::= { trkPaAtmRowStatusEntry 2 }

trkPaAtmStorageType OBJECT-TYPE
   SYNTAX     StorageType 
   ACCESS     read-only
   STATUS     mandatory
   DESCRIPTION
     "This variable represents the storage type value for the
      trkPaAtm tables."
::= { trkPaAtmRowStatusEntry 4 }

trkPaAtmIndex OBJECT-TYPE
   SYNTAX     NonReplicated 
   ACCESS     not-accessible
   STATUS     mandatory
   DESCRIPTION
     "This variable represents the index for the trkPaAtm tables."
::= { trkPaAtmRowStatusEntry 10 }

trkPaAtmProvTable OBJECT-TYPE
   SYNTAX     SEQUENCE OF TrkPaAtmProvEntry
   ACCESS     not-accessible
   STATUS     mandatory
   DESCRIPTION
     "This group of attributes provides the parameters used by the 
      AtmAccess component for specifying access to an ATM interface."
::= { trkPaAtm 10 }

trkPaAtmProvEntry OBJECT-TYPE
   SYNTAX     TrkPaAtmProvEntry
   ACCESS     not-accessible
   STATUS     mandatory
   DESCRIPTION
     "An entry in the trkPaAtmProvTable."
   INDEX {
      trkIndex,
      trkPaIndex,
      trkPaAtmIndex }
::= { trkPaAtmProvTable 1 }

TrkPaAtmProvEntry ::= SEQUENCE {
   trkPaAtmAtmConnection
      Link,
   trkPaAtmMode
      INTEGER }

trkPaAtmAtmConnection OBJECT-TYPE
   SYNTAX     Link 
   ACCESS     read-write
   STATUS     mandatory
   DESCRIPTION
     "This attribute specifies the component name of the ATM Virtual 
      Circuit that the AtmAccess component will use. The format of the 
      component name is AtmIf/n Vcc/x.y Nep"
::= { trkPaAtmProvEntry 1 }

trkPaAtmMode OBJECT-TYPE
   SYNTAX     INTEGER  {
                 multiplexing(0),
                 mapping(1) }
   ACCESS     read-write
   STATUS     mandatory
   DESCRIPTION
     "This attribute specifies the operating mode of the PathAdmin. When 
      set to multiplexing the PathAdmin to multiplex voice calls to the 
      given atmConnection using single cell per voice packet transport. 
      All other calls will be multiplexed using AAL5 over the Trunk's 
      VCC. When set to mapping the PathAdmin will allocate a VCC per 
      LCh/n. In mapping mode the atmConnection should not be set. The 
      VCC chosen for a given connection can be seen in the LCh 
      localConnection attribute."
   DEFVAL     { multiplexing }
::= { trkPaAtmProvEntry 2 }




-- 
-- Version and Compliance statements
-- 



-- Object-Group Statement:
-- A list of all current accessible leaf objects.

-- OBJECTS { trkPaAtmRowStatus,
--           trkPaAtmMode,
--           trkPaAtmComponentName,
--           trkPaAtmAtmConnection,
--           trkPaAtmStorageType }
-- STATUS  mandatory
-- DESCRIPTION
--   "A list of all current accessible leaf objects."

porsAtmTrunksGroup OBJECT IDENTIFIER ::= { porsAtmTrunksMIB 1 }
porsAtmTrunksGroupBE OBJECT IDENTIFIER ::= { porsAtmTrunksGroup 5 }
porsAtmTrunksGroupBE01 OBJECT IDENTIFIER ::= { porsAtmTrunksGroupBE 2 }
porsAtmTrunksGroupBE01A OBJECT IDENTIFIER ::= { porsAtmTrunksGroupBE01 2 }



-- Agent-Capabilities Statement:

-- PRODUCT-RELEASE "Passport Release 7.0 PorsAtmTrunks."
-- STATUS          mandatory
-- DESCRIPTION     "PorsAtmTrunks MIB: MIB Version BE01A,
--                  Software Version BG00S4C."
-- SUPPORTS        Nortel-Magellan-Passport-PorsAtmTrunksMIB
--    INCLUDES     { porsAtmTrunksGroupBE01A }

porsAtmTrunksCapabilities OBJECT IDENTIFIER ::= { porsAtmTrunksMIB 3 }
porsAtmTrunksCapabilitiesBE OBJECT IDENTIFIER ::= { porsAtmTrunksCapabilities 5 }
porsAtmTrunksCapabilitiesBE01 OBJECT IDENTIFIER ::= { porsAtmTrunksCapabilitiesBE 2 }
porsAtmTrunksCapabilitiesBE01A OBJECT IDENTIFIER ::= { porsAtmTrunksCapabilitiesBE01 2 }





END
