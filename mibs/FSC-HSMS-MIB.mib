-->#
--># Copyright (C) Fujitsu Siemens Computers 1999
-->#               All rights reserved
-->#
-->#protocol specification
-->%PROTOCOL SNMP
-->#
-->#configuration
-->%REMCONFIG NO
-->%REMOPERATION NO
-->#
 
FSC-HSMS-MIB DEFINITIONS ::= BEGIN
--  MIB-Version: 1
 
--
-- Title:   MIB for HSMS (BS2000)
-- Date:    November 1999
-- Author:  Birgit Lamers        BS2000 DC3
--
 
 
IMPORTS
        IpAddress, enterprises
            FROM RFC1155-SMI
        DisplayString
            FROM RFC1213-MIB
        OBJECT-TYPE
            FROM RFC-1212;
--      DateAndTime     FROM RFC1514;
 
--      copied from RFC1514:
   DateAndTime ::= OCTET STRING (SIZE (8 | 11))
   --        A date-time specification for the local time of day.
   --        This data type is intended to provide a consistent
   --        method of reporting date information.
   --
   --            field  octets  contents                  range
   --            _____  ______  ________                  _____
   --              1      1-2   year                      0..65536
   --                           (in network byte order)
   --              2       3    month                     1..12
   --              3       4    day                       1..31
   --              4       5    hour                      0..23
   --              5       6    minutes                   0..59
   --              6       7    seconds                   0..60
   --                           (use 60 for leap-second)
   --              7       8    deci-seconds              0..9
   --              8       9    direction from UTC        "+" / "-"
   --                           (in ascii notation)
   --              9      10    hours from UTC            0..11
   --             10      11    minutes from UTC          0..59
   --
   --            Note that if only local time is known, then
   --            timezone information (fields 8-10) is not present.
 
 
 
sni                        OBJECT IDENTIFIER ::= { enterprises 231 }
sniProductMibs             OBJECT IDENTIFIER ::= { sni 2 }
fscHSMS                    OBJECT IDENTIFIER ::= { sniProductMibs 40 }
fscHSMSGlobalData          OBJECT IDENTIFIER ::= { fscHSMS 1 }
fscHSMSInstances           OBJECT IDENTIFIER ::= { fscHSMS 2 }
fscHSMSRequests            OBJECT IDENTIFIER ::= { fscHSMS 3 }
 
---
---  Global Data
---
hsmsGDVersion      OBJECT-TYPE
        SYNTAX  DisplayString (SIZE (1..8))
        ACCESS  read-only
        STATUS  mandatory
        DESCRIPTION "Version of subagent "
        ::= {fscHSMSGlobalData  1}
 
hsmsGDOpmode       OBJECT-TYPE
        SYNTAX  INTEGER
        {
           defineshow  (1),
           simulation  (2),
           operation   (3),
           unknown     (255)
        }
        ACCESS  read-write
        STATUS  mandatory
        DESCRIPTION "The current operational mode specifies the scope
                     of actions to be performed by HSMS"
        ::= {fscHSMSGlobalData 2}
 
hsmsGDServertask     OBJECT-TYPE
        SYNTAX  INTEGER (0..99)
        ACCESS  read-write
        STATUS  mandatory
        DESCRIPTION "Number of current server tasks"
        ::= {fscHSMSGlobalData 3}
 
hsmsGDSysMigrate     OBJECT-TYPE
        SYNTAX  DisplayString
        ACCESS  read-only
        STATUS  mandatory
        DESCRIPTION "Name of the default system archive for migration"
        ::= {fscHSMSGlobalData 4}
 
hsmsGDSysBackup      OBJECT-TYPE
        SYNTAX  DisplayString
        ACCESS  read-only
        STATUS  mandatory
        DESCRIPTION "Name of the default system archive for backup"
        ::= {fscHSMSGlobalData 5}
 
hsmsGDSysArchive     OBJECT-TYPE
        SYNTAX  DisplayString
        ACCESS  read-only
        STATUS  mandatory
        DESCRIPTION "Name of the default system archive for archival"
        ::= {fscHSMSGlobalData 6}
 
hsmsGDSysNodeBackup  OBJECT-TYPE
        SYNTAX  DisplayString
        ACCESS  read-only
        STATUS  mandatory
        DESCRIPTION "Name of the default system archive for
              the backup of nodes"
        ::= {fscHSMSGlobalData 7}
 
hsmsGDSysNodeArchive OBJECT-TYPE
        SYNTAX  DisplayString
        ACCESS  read-only
        STATUS  mandatory
        DESCRIPTION "Name of the default system archive for
              the archival of nodes"
        ::= {fscHSMSGlobalData 8}
 
hsmsGDS1Pubset       OBJECT-TYPE
        SYNTAX  DisplayString
        ACCESS  read-only
        STATUS  mandatory
        DESCRIPTION "Name of the pubset which is used as the default
              S1 pubset"
        ::= {fscHSMSGlobalData 9}
 
---
---  HSMS Instances
---
hsmsInSubTabNum             OBJECT-TYPE
        SYNTAX  INTEGER
        ACCESS  read-only
        STATUS  mandatory
        DESCRIPTION "The number of entries in the table hsmsInSubTable"
        ::= {fscHSMSInstances 1}
 
hsmsInSubTable           OBJECT-TYPE
        SYNTAX  SEQUENCE OF HsmsInSubEntry
        ACCESS  not-accessible
        STATUS  mandatory
        DESCRIPTION "The HSMS subsystem table"
        ::= {fscHSMSInstances 2}
 
hsmsInSubEntry        OBJECT-TYPE
        SYNTAX  HsmsInSubEntry
        ACCESS  not-accessible
        STATUS  mandatory
        DESCRIPTION "An entry in the table"
        INDEX {hsmsInSubIndex}
        ::= {hsmsInSubTable 1}
HsmsInSubEntry ::=
        SEQUENCE 
        {
            hsmsInSubIndex                INTEGER,
            hsmsInSubName                 DisplayString,
            hsmsInSubVersion              DisplayString,
            hsmsInSubState                INTEGER
        }
 
hsmsInSubIndex   OBJECT-TYPE
        SYNTAX  INTEGER
        ACCESS  read-only
        STATUS  mandatory
        DESCRIPTION "A unique value for each entry, its value
                     ranges between 1 and the value of hsmsInSubTabNum"
        ::= {hsmsInSubEntry 1}
 
hsmsInSubName       OBJECT-TYPE
        SYNTAX  DisplayString
        ACCESS  read-only
        STATUS  mandatory
        DESCRIPTION "The name of the subsystem"
        ::= {hsmsInSubEntry 2}
 
hsmsInSubVersion    OBJECT-TYPE
        SYNTAX  DisplayString
        ACCESS  read-only
        STATUS  mandatory
        DESCRIPTION "The installed version of the subsystem"
        ::= {hsmsInSubEntry 3}
 
hsmsInSubState                OBJECT-TYPE
        SYNTAX  INTEGER 
        {
                 created       (1),
                 not-created   (2),
                 in-delete     (3),
                 in-create     (4),
                 in-resume     (5),
                 in-hold       (6),
                 not-resumed   (7),
                 locked        (8),
                 not-installed (255)
        }
        ACCESS  read-only
        STATUS  mandatory
        DESCRIPTION "Current state of the subsystem"
        ::= {hsmsInSubEntry 4}
 
 
---
-- HSMS Requests
---
 
hsmsRequestTabState               OBJECT-TYPE
        SYNTAX  INTEGER
                {
                   any           (1),
                   completed     (2),
                   accepted      (3),
                   started       (4),
                   interrupted   (5)
                }
        ACCESS  read-write
        STATUS  mandatory
        DESCRIPTION "Selects the requests using their processing
                     state as the selection criterion."
        ::= {fscHSMSRequests 1 }
 
hsmsRequestTabOrigin              OBJECT-TYPE
        SYNTAX  INTEGER
                {
                   bs2000      (1),
                   node-cl     (2)
                }
        ACCESS  read-write
        STATUS  mandatory
        DESCRIPTION "Selects the requests using their place of origin:
          this can be either the central BS2000 host (DMS and
          node requests) or a client on which HSMS-CL is active."
        ::= {fscHSMSRequests 2 }
 
hsmsRequestTabNodeID              OBJECT-TYPE
        SYNTAX  DisplayString (SIZE (1..48))
        ACCESS  read-write
        STATUS  mandatory
        DESCRIPTION "Selects only the requests of the specified
          client on which HSMS-CL is active."
        ::= {fscHSMSRequests 3 }
 
hsmsRequestTable                  OBJECT-TYPE
        SYNTAX  SEQUENCE OF HsmsRequestEntry
        ACCESS  not-accessible
        STATUS  mandatory
        DESCRIPTION "The HSMS request table"
        ::= {fscHSMSRequests 10 }
 
hsmsRequestEntry                  OBJECT-TYPE
        SYNTAX  HsmsRequestEntry
        ACCESS  not-accessible
        STATUS  mandatory
        DESCRIPTION "An entry in the table"
        INDEX {hsmsRequestIndex}
        ::= {hsmsRequestTable 1}
 
 
HsmsRequestEntry ::=
        SEQUENCE 
        {
            hsmsRequestIndex                INTEGER,
            hsmsRequestName                 DisplayString,
            hsmsRequestDateAndTime          DisplayString,
            hsmsRequestAction               INTEGER,
            hsmsRequestArchiveName          DisplayString,
            hsmsRequestSim                  INTEGER,
            hsmsRequestExp                  INTEGER,
            hsmsRequestRestart              INTEGER,
            hsmsRequestRem                  INTEGER,
            hsmsRequestState                INTEGER,
            hsmsRequestSubState             INTEGER,
            hsmsRequestProcessor            DisplayString,
            hsmsRequestTSN                  DisplayString,
--  only for Origin=BS2000:
            hsmsRequestUser                 DisplayString,
--  only for Origin=NODE-Cl:
            hsmsRequestUserNo               INTEGER,
            hsmsRequestNodeId               DisplayString,
            hsmsRequestIPAddr               IpAddress,
            hsmsRequestIPPort               INTEGER,
            hsmsRequestBspiId               DisplayString
        }
 
hsmsRequestIndex              OBJECT-TYPE
        SYNTAX  INTEGER
        ACCESS  read-only
        STATUS  mandatory
        DESCRIPTION "An index to uniquely identify an entry in
                     the request table."
::= {hsmsRequestEntry 1}
 
hsmsRequestName               OBJECT-TYPE
        SYNTAX  DisplayString (SIZE (1..8))
        ACCESS  read-only
        STATUS  mandatory
        DESCRIPTION "Name of the request"
        ::= {hsmsRequestEntry 2}
 
hsmsRequestDateAndTime       OBJECT-TYPE
        SYNTAX  DateAndTime
        ACCESS  read-only
        STATUS  mandatory
        DESCRIPTION "Creation date and time of the request"
        ::= {hsmsRequestEntry 3}
 
hsmsRequestAction            OBJECT-TYPE
        SYNTAX  DisplayString
        ACCESS  read-only
        STATUS  mandatory
        DESCRIPTION "HSMS Statement or anchor command"
        ::= {hsmsRequestEntry 4}
 
hsmsRequestArchiveName             OBJECT-TYPE
        SYNTAX  DisplayString
        ACCESS  read-only
        STATUS  mandatory
        DESCRIPTION "Name of the involved archive"
        ::= {hsmsRequestEntry 5}
 
hsmsRequestSim               OBJECT-TYPE
        SYNTAX  INTEGER
                {
                   yes (1),
                   no  (2)
                }
        ACCESS  read-only
        STATUS  mandatory
        DESCRIPTION "Simulated request"
        ::= {hsmsRequestEntry 6}
 
hsmsRequestExp               OBJECT-TYPE
        SYNTAX  INTEGER
                {
                   yes (1),
                   no  (2)
                }
        ACCESS  read-only
        STATUS  mandatory
        DESCRIPTION "Express request"
        ::= {hsmsRequestEntry 7}
 
hsmsRequestRestart            OBJECT-TYPE
        SYNTAX  INTEGER
                {
                   yes (1),
                   no  (2)
                }
        ACCESS  read-only
        STATUS  mandatory
        DESCRIPTION "Request after restart"
        ::= {hsmsRequestEntry 8}
 
hsmsRequestRem                OBJECT-TYPE
        SYNTAX  INTEGER
                {
                   yes (1),
                   no  (2)
                }
        ACCESS  read-only
        STATUS  mandatory
        DESCRIPTION "Remote request"
        ::= {hsmsRequestEntry 9}
 
hsmsRequestState             OBJECT-TYPE
        SYNTAX  INTEGER
                {
                   incomplete(1),
                   accepted (2),
                   started (3),
                   completed (4),
                   cancelled (5),
                   interrupted (6),
                   unknown (255)
                }
        ACCESS  read-only
        STATUS  mandatory
        DESCRIPTION "State request"
        ::= {hsmsRequestEntry 10}
 
hsmsRequestSubState          OBJECT-TYPE
        SYNTAX  INTEGER
                {
                   collected (1),
                   start-archive (2),
                   archive-completed (3),
                   start-report (4),
                   sent-to-master (5),
                   master-replied (6),
                   master-timeout (7),
                   master-no-connect (8),
                   in-transmit (9),
                   with-warnings (10),
                   with-errors (11),
                   none (20),
                   unknown (255)
                }
        ACCESS  read-only
        STATUS  mandatory
        DESCRIPTION "Additional information about the state. Notice: some
                     states don't have a substate. In this case  "
        ::= {hsmsRequestEntry 11}
 
hsmsRequestProcessor         OBJECT-TYPE
        SYNTAX  DisplayString (SIZE (1..8))
        ACCESS  read-only
        STATUS  mandatory
        DESCRIPTION ""
        ::= {hsmsRequestEntry 12}
 
hsmsRequestTSN               OBJECT-TYPE
        SYNTAX  DisplayString (SIZE (1..4))
        ACCESS  read-only
        STATUS  mandatory
        DESCRIPTION "TSN of executing server task"
        ::= {hsmsRequestEntry 13}
 
-- only for Origin=BS2000:
hsmsRequestUser              OBJECT-TYPE
        SYNTAX  DisplayString (SIZE (1..8))
        ACCESS  read-only
        STATUS  mandatory
        DESCRIPTION "User ID under which the request was created"
        ::= {hsmsRequestEntry 14}
 
-- only for Origin=NODE-Cl:
hsmsRequestUserNo             OBJECT-TYPE
        SYNTAX  INTEGER
        ACCESS  read-only
        STATUS  mandatory
        DESCRIPTION "UNIX user number"
        ::= {hsmsRequestEntry 15}
 
hsmsRequestNodeId             OBJECT-TYPE
        SYNTAX  DisplayString (SIZE (1..8))
        ACCESS  read-only
        STATUS  mandatory
        DESCRIPTION "ID of the node"
        ::= {hsmsRequestEntry 16}
 
hsmsRequestIPAddr             OBJECT-TYPE
        SYNTAX  IpAddress
        ACCESS  read-only
        STATUS  mandatory
        DESCRIPTION "IP address of the node"
        ::= {hsmsRequestEntry 17}
 
hsmsRequestIPPort             OBJECT-TYPE
        SYNTAX  INTEGER
        ACCESS  read-only
        STATUS  mandatory
        DESCRIPTION "IP port number of the node"
        ::= {hsmsRequestEntry 18}
 
hsmsRequestBspiId              OBJECT-TYPE
        SYNTAX  DisplayString (SIZE (1..12))
        ACCESS  read-only
        STATUS  mandatory
        DESCRIPTION "Request ID on the client"
        ::= {hsmsRequestEntry 19}
 
END
