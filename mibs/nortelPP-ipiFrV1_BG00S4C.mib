Nortel-Magellan-Passport-IpiFrMIB
DEFINITIONS ::= BEGIN



IMPORTS

      OBJECT-TYPE
   FROM RFC-1212

      IpAddress
   FROM RFC1155-SMI

      components,
      passportMIBs
   FROM Nortel-Magellan-Passport-UsefulDefinitionsMIB

      Counter32,
      RowPointer,
      DisplayString,
      StorageType,
      RowStatus,
      Integer32,
      Unsigned32
   FROM Nortel-Magellan-Passport-StandardTextualConventionsMIB

      AsciiString,
      Hex,
      NonReplicated,
      HexString,
      EnterpriseDateAndTime,
      DigitString
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     IpiFr Enterprise MIB."

ipiFrMIB OBJECT IDENTIFIER ::= { passportMIBs 35 }










-- IP Interface over Frame Relay
-- 
-- The IP interface over Frame Relay component allows external 
-- Network Management Stations using Frame Relay PVC 
-- connections to perform the network management functions on the 
-- Passport module.
-- 
-- Network Management Stations can be directly connected to a 
-- Passport module with a FrameRelay PVC connection, or indirectly 
-- connected via an IP routing capable device which has a FrameRelay 
-- PVC connection to the Passport module.

ipiFr OBJECT IDENTIFIER ::= { components 50 }



ipiFrRowStatusTable OBJECT-TYPE
   SYNTAX     SEQUENCE OF IpiFrRowStatusEntry
   ACCESS     not-accessible
   STATUS     mandatory
   DESCRIPTION
     "This entry controls the addition and deletion of 
      ipiFr components."
::= { ipiFr 1 }

ipiFrRowStatusEntry OBJECT-TYPE
   SYNTAX     IpiFrRowStatusEntry
   ACCESS     not-accessible
   STATUS     mandatory
   DESCRIPTION
     "A single entry in the table represents a single 
      ipiFr component."
   INDEX {
      ipiFrIndex }
::= { ipiFrRowStatusTable 1 }

IpiFrRowStatusEntry ::= SEQUENCE {
   ipiFrRowStatus
      RowStatus,
   ipiFrComponentName
      DisplayString,
   ipiFrStorageType
      StorageType,
   ipiFrIndex
      NonReplicated }

ipiFrRowStatus OBJECT-TYPE
   SYNTAX     RowStatus 
   ACCESS     read-write
   STATUS     mandatory
   DESCRIPTION
     "This variable is used as the basis for SNMP naming of
      ipiFr components.
      These components can be added and deleted."
::= { ipiFrRowStatusEntry 1 }

ipiFrComponentName OBJECT-TYPE
   SYNTAX     DisplayString 
   ACCESS     read-only
   STATUS     mandatory
   DESCRIPTION
     "This variable provides the component's string name for
      use with the ASCII Console Interface"
::= { ipiFrRowStatusEntry 2 }

ipiFrStorageType OBJECT-TYPE
   SYNTAX     StorageType 
   ACCESS     read-only
   STATUS     mandatory
   DESCRIPTION
     "This variable represents the storage type value for the
      ipiFr tables."
::= { ipiFrRowStatusEntry 4 }

ipiFrIndex OBJECT-TYPE
   SYNTAX     NonReplicated 
   ACCESS     not-accessible
   STATUS     mandatory
   DESCRIPTION
     "This variable represents the index for the ipiFr tables."
::= { ipiFrRowStatusEntry 10 }

ipiFrProvTable OBJECT-TYPE
   SYNTAX     SEQUENCE OF IpiFrProvEntry
   ACCESS     not-accessible
   STATUS     mandatory
   DESCRIPTION
     "This group provides the provisionable attributes for the IpiFr 
      component."
::= { ipiFr 10 }

ipiFrProvEntry OBJECT-TYPE
   SYNTAX     IpiFrProvEntry
   ACCESS     not-accessible
   STATUS     mandatory
   DESCRIPTION
     "An entry in the ipiFrProvTable."
   INDEX {
      ipiFrIndex }
::= { ipiFrProvTable 1 }

IpiFrProvEntry ::= SEQUENCE {
   ipiFrIpAddress
      IpAddress,
   ipiFrMaximumNumberOfLcn
      Unsigned32,
   ipiFrSubnetMask
      IpAddress }

ipiFrIpAddress OBJECT-TYPE
   SYNTAX     IpAddress 
   ACCESS     read-write
   STATUS     mandatory
   DESCRIPTION
     "This attribute specifies the unique Internet Protocol (IP) Address 
      that represents the IP address of the IPI service."
   DEFVAL     { '00000000'H }  -- "0.0.0.0"
::= { ipiFrProvEntry 1 }

ipiFrMaximumNumberOfLcn OBJECT-TYPE
   SYNTAX     Unsigned32 (24)
   ACCESS     read-only
   STATUS     mandatory
   DESCRIPTION
     "This attribute specifies the maximum number of LCNs that are 
      supported on this service. It specifies the maximum number of 
      connections from external network management sites to this IpiFr 
      service."
   DEFVAL     { 24 }
::= { ipiFrProvEntry 2 }

ipiFrSubnetMask OBJECT-TYPE
   SYNTAX     IpAddress 
   ACCESS     read-write
   STATUS     mandatory
   DESCRIPTION
     "This attribute specifies the subnetwork mask for the IPI service."
   DEFVAL     { 'ff000000'H }  -- "255.0.0.0"
::= { ipiFrProvEntry 3 }


-- IpiFr Dna
-- This is the description of the Ipi Frame Relay Dna component. It is 
-- offers a subset of the generic Dna component attributes

ipiFrDna OBJECT IDENTIFIER ::= { ipiFr 2 }



ipiFrDnaRowStatusTable OBJECT-TYPE
   SYNTAX     SEQUENCE OF IpiFrDnaRowStatusEntry
   ACCESS     not-accessible
   STATUS     mandatory
   DESCRIPTION
     "This entry controls the addition and deletion of 
      ipiFrDna components."
::= { ipiFrDna 1 }

ipiFrDnaRowStatusEntry OBJECT-TYPE
   SYNTAX     IpiFrDnaRowStatusEntry
   ACCESS     not-accessible
   STATUS     mandatory
   DESCRIPTION
     "A single entry in the table represents a single 
      ipiFrDna component."
   INDEX {
      ipiFrIndex,
      ipiFrDnaIndex }
::= { ipiFrDnaRowStatusTable 1 }

IpiFrDnaRowStatusEntry ::= SEQUENCE {
   ipiFrDnaRowStatus
      RowStatus,
   ipiFrDnaComponentName
      DisplayString,
   ipiFrDnaStorageType
      StorageType,
   ipiFrDnaIndex
      NonReplicated }

ipiFrDnaRowStatus OBJECT-TYPE
   SYNTAX     RowStatus 
   ACCESS     read-only
   STATUS     mandatory
   DESCRIPTION
     "This variable is used as the basis for SNMP naming of
      ipiFrDna components.
      These components cannot be added nor deleted."
::= { ipiFrDnaRowStatusEntry 1 }

ipiFrDnaComponentName OBJECT-TYPE
   SYNTAX     DisplayString 
   ACCESS     read-only
   STATUS     mandatory
   DESCRIPTION
     "This variable provides the component's string name for
      use with the ASCII Console Interface"
::= { ipiFrDnaRowStatusEntry 2 }

ipiFrDnaStorageType OBJECT-TYPE
   SYNTAX     StorageType 
   ACCESS     read-only
   STATUS     mandatory
   DESCRIPTION
     "This variable represents the storage type value for the
      ipiFrDna tables."
::= { ipiFrDnaRowStatusEntry 4 }

ipiFrDnaIndex OBJECT-TYPE
   SYNTAX     NonReplicated 
   ACCESS     not-accessible
   STATUS     mandatory
   DESCRIPTION
     "This variable represents the index for the ipiFrDna tables."
::= { ipiFrDnaRowStatusEntry 10 }

ipiFrDnaAddressTable OBJECT-TYPE
   SYNTAX     SEQUENCE OF IpiFrDnaAddressEntry
   ACCESS     not-accessible
   STATUS     mandatory
   DESCRIPTION
     "Address group contains attributes common to all Dna's. Every Dna 
      used in the network is defined with this group of 2 attributes. String 
      of address digits is complemented by type of address and Npi. 
      These attributes are used to interpret format of the address digits."
::= { ipiFrDna 10 }

ipiFrDnaAddressEntry OBJECT-TYPE
   SYNTAX     IpiFrDnaAddressEntry
   ACCESS     not-accessible
   STATUS     mandatory
   DESCRIPTION
     "An entry in the ipiFrDnaAddressTable."
   INDEX {
      ipiFrIndex,
      ipiFrDnaIndex }
::= { ipiFrDnaAddressTable 1 }

IpiFrDnaAddressEntry ::= SEQUENCE {
   ipiFrDnaNumberingPlanIndicator
      INTEGER,
   ipiFrDnaDataNetworkAddress
      DigitString }

ipiFrDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans. 
      X.121 is used in packet svitched data networks."
   DEFVAL     { x121 }
::= { ipiFrDnaAddressEntry 1 }

ipiFrDnaDataNetworkAddress OBJECT-TYPE
   SYNTAX     DigitString (SIZE (1..15))
   ACCESS     read-write
   STATUS     mandatory
   DESCRIPTION
     "Dna attribute contains digits which form unique identifier of the 
      customer interface. It can be compared (approximation only) to 
      telephone number where phone number identifies unique telephone 
      set. Dna digits are selected and assigned by network operators. 
      MaximumLenOfDna is 15digits."
::= { ipiFrDnaAddressEntry 2 }

ipiFrDnaOutgoingOptionsTable OBJECT-TYPE
   SYNTAX     SEQUENCE OF IpiFrDnaOutgoingOptionsEntry
   ACCESS     not-accessible
   STATUS     mandatory
   DESCRIPTION
     "OutgoingOptions group defines call options of a Dna for calls 
      which are made out of the interface represented by Dna. All these 
      options are not used for calls arriving to the interface represented by 
      Dna."
::= { ipiFrDna 11 }

ipiFrDnaOutgoingOptionsEntry OBJECT-TYPE
   SYNTAX     IpiFrDnaOutgoingOptionsEntry
   ACCESS     not-accessible
   STATUS     mandatory
   DESCRIPTION
     "An entry in the ipiFrDnaOutgoingOptionsTable."
   INDEX {
      ipiFrIndex,
      ipiFrDnaIndex }
::= { ipiFrDnaOutgoingOptionsTable 1 }

IpiFrDnaOutgoingOptionsEntry ::= SEQUENCE {
   ipiFrDnaOutCalls
      INTEGER,
   ipiFrDnaOutDefaultPriority
      INTEGER,
   ipiFrDnaOutDefaultPathSensitivity
      INTEGER,
   ipiFrDnaOutPathSensitivityOverRide
      INTEGER,
   ipiFrDnaDefaultTransferPriority
      INTEGER,
   ipiFrDnaTransferPriorityOverRide
      INTEGER }

ipiFrDnaOutCalls OBJECT-TYPE
   SYNTAX     INTEGER  {
                 disallowed(0),
                 allowed(1) }
   ACCESS     read-only
   STATUS     mandatory
   DESCRIPTION
     "This attribute, if set to a value of allowed indicates that outgoing 
      calls (from the DTE to the network) can be made using this 
      particular Dna. If set to a value of disallowed , then outgoing calls 
      cannot be made using this Dna - such calls will be cleared by the 
      local DCE. This attribute corresponds to the CCITT 'Outgoing Calls 
      Barred' feature for Dnas in that outgoing calls are barred if this 
      attribute is set to a value of disallowed. Either outCalls, or incCalls 
      (or both) must be set to a value of allowed for this Dna to be 
      useable."
   DEFVAL     { disallowed }
::= { ipiFrDnaOutgoingOptionsEntry 1 }

ipiFrDnaOutDefaultPriority OBJECT-TYPE
   SYNTAX     INTEGER  {
                 normal(0),
                 high(1) }
   ACCESS     read-only
   STATUS     mandatory
   DESCRIPTION
     "This attribute, if set to normal indicates that the default priority for 
      outgoing calls (from the DTE to the network) using this particular 
      Dna is normal priority - if the priority is not specified by the DTE.  
      If this attribute is set to high then the default priority for outgoing 
      calls using this particular Dna is high priority.
      
      It can be overridden by the discardPriority under DLCI Direct Call 
      subcomponent."
   DEFVAL     { high }
::= { ipiFrDnaOutgoingOptionsEntry 7 }

ipiFrDnaOutDefaultPathSensitivity OBJECT-TYPE
   SYNTAX     INTEGER  {
                 throughput(0),
                 delay(1) }
   ACCESS     read-write
   STATUS     obsolete
   DESCRIPTION
     "This attribute specifies the default class of path sensitivity to 
      network for all outgoing calls using this particular Dna. The chosen 
      default class of path sensitivity applies to all outgoing calls 
      established using this Dna. 
      
      This attribute, if set to a value of throughput, indicates that the 
      default class is throughput sensitive. If set to a value of delay, then 
      the default class is delay sensitive. The default of 
      outDefaultPathSensitivity is delay."
   DEFVAL     { delay }
::= { ipiFrDnaOutgoingOptionsEntry 11 }

ipiFrDnaOutPathSensitivityOverRide OBJECT-TYPE
   SYNTAX     INTEGER  {
                 no(0),
                 yes(1) }
   ACCESS     read-write
   STATUS     obsolete
   DESCRIPTION
     "If this attribute is set to in the call request, the called end will use 
      the calling end provisioning data on path sensitivity to override its 
      own provisioning data.
      
      The default of outPathSensitivityOverRide is yes."
   DEFVAL     { yes }
::= { ipiFrDnaOutgoingOptionsEntry 12 }

ipiFrDnaDefaultTransferPriority OBJECT-TYPE
   SYNTAX     INTEGER  {
                 normal(0),
                 high(9) }
   ACCESS     read-write
   STATUS     mandatory
   DESCRIPTION
     "This attribute specifies the default transfer priority to network for 
      all outgoing calls using this particular Dna. It is overRidden by 
      the transferPriority provisioned in the DLCI Direct Call sub-
      component.
      
      The transfer priority is a preference specified by an application 
      according to its delay-sensitivity requirement. Frames with high
      transfer priority are served by the network before the frames with 
      normal priority. 
      
      Each transfer priority contains a predetermined setting for trunk 
      queue (interrupting, delay or throughput), routing metric (delay or 
      throughput). 
      
      When the transfer priority is set at high, the trunk queue is set to 
      high, the routing metric is set to delay.
      
      When the transfer priority is set at normal, the trunk queue is set to 
      normal, the routing metric is set to throughput.
      
      The default of defaultTransferPriority is high."
   DEFVAL     { high }
::= { ipiFrDnaOutgoingOptionsEntry 18 }

ipiFrDnaTransferPriorityOverRide OBJECT-TYPE
   SYNTAX     INTEGER  {
                 no(0),
                 yes(1) }
   ACCESS     read-write
   STATUS     mandatory
   DESCRIPTION
     "When this attribute is set to yes, the called end will use the calling 
      end provisioning data on transfer priority to override its own 
      provisioning data. If it is set no, the called end will use its own 
      provisioning data on transfer priority.
      
      For more information about transfer priority, please refer to the 
      previous attribute defaultTransferPriority.
      
      The default of transferPriorityOverRide is yes."
   DEFVAL     { yes }
::= { ipiFrDnaOutgoingOptionsEntry 19 }

ipiFrDnaIncomingOptionsTable OBJECT-TYPE
   SYNTAX     SEQUENCE OF IpiFrDnaIncomingOptionsEntry
   ACCESS     not-accessible
   STATUS     mandatory
   DESCRIPTION
     "IncomingOptions defines set of options for incoming calls. These 
      options are used for calls arriving to the interface represented by 
      Dna. For calls originated from the interfasce, IncomingOptions 
      attributes are not used."
::= { ipiFrDna 12 }

ipiFrDnaIncomingOptionsEntry OBJECT-TYPE
   SYNTAX     IpiFrDnaIncomingOptionsEntry
   ACCESS     not-accessible
   STATUS     mandatory
   DESCRIPTION
     "An entry in the ipiFrDnaIncomingOptionsTable."
   INDEX {
      ipiFrIndex,
      ipiFrDnaIndex }
::= { ipiFrDnaIncomingOptionsTable 1 }

IpiFrDnaIncomingOptionsEntry ::= SEQUENCE {
   ipiFrDnaIncCalls
      INTEGER,
   ipiFrDnaIncAccess
      INTEGER }

ipiFrDnaIncCalls OBJECT-TYPE
   SYNTAX     INTEGER  {
                 disallowed(0),
                 allowed(1) }
   ACCESS     read-only
   STATUS     mandatory
   DESCRIPTION
     "This attribute, if set to a value of allowed  indicates that incoming 
      calls (from the network to the DTE) can be made to this Dna. If set 
      to a value of disallowed, then incoming calls cannot be made to this 
      Dna - such calls will be cleared by the local DCE. This attribute 
      corresponds to the CCITT 'Incoming Calls Barred' feature for Dna's 
      in that incoming calls are barred if this attribute is set to a value of 
      disallowed.
      
      Either outCalls, or incCalls (or both) must be set to a value of 
      allowed for this Dna to be useable."
   DEFVAL     { allowed }
::= { ipiFrDnaIncomingOptionsEntry 1 }

ipiFrDnaIncAccess OBJECT-TYPE
   SYNTAX     INTEGER  {
                 disallowed(0),
                 allowed(1) }
   ACCESS     read-write
   STATUS     mandatory
   DESCRIPTION
     "This attribute is an extension of the Closed User Group (CUG) 
      facility, as follows:
      This attribute, if set to a value of allowed indicates that incoming 
      calls (from the network to the DTE) from the open (non-CUG) part 
      of the network are permitted. It also permits incoming calls from 
      DTEs that have Outgoing Access capabilities. If set to a value of 
      disallowed, then such calls cannot be made to this Dna - such calls 
      will be cleared by the local DCE.
      This attribute corresponds to the CCITT 'Closed User Group with 
      Incoming Access' feature for Dnas in that incoming access is 
      granted if this attribute is set to a value of allowed."
   DEFVAL     { disallowed }
::= { ipiFrDnaIncomingOptionsEntry 9 }

ipiFrDnaCallOptionsTable OBJECT-TYPE
   SYNTAX     SEQUENCE OF IpiFrDnaCallOptionsEntry
   ACCESS     not-accessible
   STATUS     mandatory
   DESCRIPTION
     "CallOptions group defines additional options for calls not related 
      directly to direction of a call."
::= { ipiFrDna 13 }

ipiFrDnaCallOptionsEntry OBJECT-TYPE
   SYNTAX     IpiFrDnaCallOptionsEntry
   ACCESS     not-accessible
   STATUS     mandatory
   DESCRIPTION
     "An entry in the ipiFrDnaCallOptionsTable."
   INDEX {
      ipiFrIndex,
      ipiFrDnaIndex }
::= { ipiFrDnaCallOptionsTable 1 }

IpiFrDnaCallOptionsEntry ::= SEQUENCE {
   ipiFrDnaServiceCategory
      INTEGER,
   ipiFrDnaAccountClass
      Unsigned32,
   ipiFrDnaServiceExchange
      Unsigned32 }

ipiFrDnaServiceCategory OBJECT-TYPE
   SYNTAX     INTEGER  {
                 gsp(0),
                 x25(1),
                 enhancedIti(2),
                 ncs(3),
                 mlti(4),
                 sm(5),
                 ici(6),
                 dsp3270(7),
                 iam(8),
                 mlhi(9),
                 term3270(10),
                 iti(11),
                 bsi(13),
                 hostIti(14),
                 x75(15),
                 hdsp3270(16),
                 api3201(20),
                 sdlc(21),
                 snaMultiHost(22),
                 redirectionServ(23),
                 trSnaTpad(24),
                 offnetNui(25),
                 gasServer(26),
                 vapServer(28),
                 vapAgent(29),
                 frameRelay(30),
                 ipiVc(31),
                 ipiFr(32) }
   ACCESS     read-only
   STATUS     mandatory
   DESCRIPTION
     "This attribute is assigned for each different type of service within 
      which this Dna is configured. It is placed into the Service Category 
      attribute in the accounting record by both ends of the Vc."
   DEFVAL     { ipiFr }
::= { ipiFrDnaCallOptionsEntry 1 }

ipiFrDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator and it is an arbitrary 
      number."
   DEFVAL     { 0 }
::= { ipiFrDnaCallOptionsEntry 10 }

ipiFrDnaServiceExchange OBJECT-TYPE
   SYNTAX     Unsigned32 (0..255)
   ACCESS     read-write
   STATUS     mandatory
   DESCRIPTION
     "This attribute is an arbitrary number, entered by the network 
      operator. It is included in the accounting record created by Vc."
   DEFVAL     { 0 }
::= { ipiFrDnaCallOptionsEntry 12 }


-- 
-- IpiFr Dna ClosedUserGroup
-- This group defines options associated with national or international 
-- CUG Identifier. Other DNAs in the network can have CUGs defined 
-- which groups these DNAs by CUG interlockCode. If DNAs are 
-- defined with CUGs, calls from DNAs which do not have the same 
-- interlockCode defined are refused. Attributes incAccess and 
-- outAccess can override this rule. IpiFr handles only incoming calls. 
-- Therefore, Closed User Group for this interface is defined for 
-- validation of incoming PVC calls only.

ipiFrDnaCug OBJECT IDENTIFIER ::= { ipiFrDna 2 }



ipiFrDnaCugRowStatusTable OBJECT-TYPE
   SYNTAX     SEQUENCE OF IpiFrDnaCugRowStatusEntry
   ACCESS     not-accessible
   STATUS     mandatory
   DESCRIPTION
     "This entry controls the addition and deletion of 
      ipiFrDnaCug components."
::= { ipiFrDnaCug 1 }

ipiFrDnaCugRowStatusEntry OBJECT-TYPE
   SYNTAX     IpiFrDnaCugRowStatusEntry
   ACCESS     not-accessible
   STATUS     mandatory
   DESCRIPTION
     "A single entry in the table represents a single 
      ipiFrDnaCug component."
   INDEX {
      ipiFrIndex,
      ipiFrDnaIndex,
      ipiFrDnaCugIndex }
::= { ipiFrDnaCugRowStatusTable 1 }

IpiFrDnaCugRowStatusEntry ::= SEQUENCE {
   ipiFrDnaCugRowStatus
      RowStatus,
   ipiFrDnaCugComponentName
      DisplayString,
   ipiFrDnaCugStorageType
      StorageType,
   ipiFrDnaCugIndex
      Integer32 }

ipiFrDnaCugRowStatus OBJECT-TYPE
   SYNTAX     RowStatus 
   ACCESS     read-write
   STATUS     mandatory
   DESCRIPTION
     "This variable is used as the basis for SNMP naming of
      ipiFrDnaCug components.
      These components can be added and deleted."
::= { ipiFrDnaCugRowStatusEntry 1 }

ipiFrDnaCugComponentName OBJECT-TYPE
   SYNTAX     DisplayString 
   ACCESS     read-only
   STATUS     mandatory
   DESCRIPTION
     "This variable provides the component's string name for
      use with the ASCII Console Interface"
::= { ipiFrDnaCugRowStatusEntry 2 }

ipiFrDnaCugStorageType OBJECT-TYPE
   SYNTAX     StorageType 
   ACCESS     read-only
   STATUS     mandatory
   DESCRIPTION
     "This variable represents the storage type value for the
      ipiFrDnaCug tables."
::= { ipiFrDnaCugRowStatusEntry 4 }

ipiFrDnaCugIndex OBJECT-TYPE
   SYNTAX     Integer32 (0..255)
   ACCESS     not-accessible
   STATUS     mandatory
   DESCRIPTION
     "This variable represents the index for the ipiFrDnaCug tables."
::= { ipiFrDnaCugRowStatusEntry 10 }

ipiFrDnaCugCugOptionsTable OBJECT-TYPE
   SYNTAX     SEQUENCE OF IpiFrDnaCugCugOptionsEntry
   ACCESS     not-accessible
   STATUS     mandatory
   DESCRIPTION
     "This group defines options for a CUG. Attributes in this group 
      define ClosedUserGroup options associated with interlockCode. 
      DNA's with the same CUG (interlockCode) can make calls within 
      this group. Various combinations which permit or prevent calls in 
      the same CUG group are defined here."
::= { ipiFrDnaCug 10 }

ipiFrDnaCugCugOptionsEntry OBJECT-TYPE
   SYNTAX     IpiFrDnaCugCugOptionsEntry
   ACCESS     not-accessible
   STATUS     mandatory
   DESCRIPTION
     "An entry in the ipiFrDnaCugCugOptionsTable."
   INDEX {
      ipiFrIndex,
      ipiFrDnaIndex,
      ipiFrDnaCugIndex }
::= { ipiFrDnaCugCugOptionsTable 1 }

IpiFrDnaCugCugOptionsEntry ::= SEQUENCE {
   ipiFrDnaCugType
      INTEGER,
   ipiFrDnaCugDnic
      DigitString,
   ipiFrDnaCugInterlockCode
      Unsigned32,
   ipiFrDnaCugIncCalls
      INTEGER }

ipiFrDnaCugType OBJECT-TYPE
   SYNTAX     INTEGER  {
                 national(0),
                 international(1) }
   ACCESS     read-write
   STATUS     mandatory
   DESCRIPTION
     "This attribute specifies the CUG type - the CUG is either a national 
      CUG, or an international CUG. International closed user groups are 
      usually established between DTEs for which there is an X.75 
      Gateway between; whereas national closed user groups are usually 
      established between DTEs for which there is no X.75 Gateway 
      between. (National CUGs cannot normally traverse an X.75 
      Gateway).
      If this attribute is set to national, then the CUG is a national CUG, 
      in which case, the dnic should be left at its default value since it is 
      not part of a national CUG. If this attribute is set to international, 
      then the CUG is an international CUG, in which case, the dnic 
      should be set appropriately as part of the CUG interlockCode."
   DEFVAL     { national }
::= { ipiFrDnaCugCugOptionsEntry 1 }

ipiFrDnaCugDnic OBJECT-TYPE
   SYNTAX     DigitString (SIZE (4))
   ACCESS     read-write
   STATUS     mandatory
   DESCRIPTION
     "This attribute specifies the dnic (Data Network ID Code) of the 
      CUG by which packet networks are identified. This attribute is not 
      applicable if the CUG is a national CUG, as specified by the CUG 
      type attribute. There are usually 1 or 2 dnics assigned per country, 
      for public networks. The U.S. is an exception where each BOC has 
      a dnic. Also, a group of private networks can have its own dnic.
      
      dnic value is not an arbitrary number. It is assigned by international 
      agreement and controlled by CCITT."
   DEFVAL     { '30303030'H }  -- "0000"
::= { ipiFrDnaCugCugOptionsEntry 2 }

ipiFrDnaCugInterlockCode OBJECT-TYPE
   SYNTAX     Unsigned32 (0..65535)
   ACCESS     read-write
   STATUS     mandatory
   DESCRIPTION
     "This attribute specifies the CUG identifier of a national or 
      international CUG call. It is an arbitrary number and it also can be 
      called CUG in some descriptions. Interfaces (DNA's) defined with 
      this number can make calls to DNA's with the same interlockCode."
   DEFVAL     { 65535 }
::= { ipiFrDnaCugCugOptionsEntry 3 }

ipiFrDnaCugIncCalls OBJECT-TYPE
   SYNTAX     INTEGER  {
                 disallowed(0),
                 allowed(1) }
   ACCESS     read-write
   STATUS     mandatory
   DESCRIPTION
     "This attribute, if set to allowed indicates that incoming calls (from 
      the network to the DTE) can be made using this particular CUG. If 
      set to disallowed, then incoming calls cannot be made using this 
      CUG - such calls will be cleared by the local DCE.
      This attribute corresponds to the CCITT 'Incoming Calls Barred' 
      feature for CUGs in that incoming calls are barred if this attribute is 
      set to a value of disallowed."
   DEFVAL     { allowed }
::= { ipiFrDnaCugCugOptionsEntry 6 }


-- IpiFr Lcn/n 
-- 
-- This component represents one Logical Channel Number 
-- responsible for logical connection with the PVC. There can be up to 
-- 24 instances of Lcn on the IpiFr component.

ipiFrLcn OBJECT IDENTIFIER ::= { ipiFr 4 }



ipiFrLcnRowStatusTable OBJECT-TYPE
   SYNTAX     SEQUENCE OF IpiFrLcnRowStatusEntry
   ACCESS     not-accessible
   STATUS     mandatory
   DESCRIPTION
     "This entry controls the addition and deletion of 
      ipiFrLcn components."
::= { ipiFrLcn 1 }

ipiFrLcnRowStatusEntry OBJECT-TYPE
   SYNTAX     IpiFrLcnRowStatusEntry
   ACCESS     not-accessible
   STATUS     mandatory
   DESCRIPTION
     "A single entry in the table represents a single 
      ipiFrLcn component."
   INDEX {
      ipiFrIndex,
      ipiFrLcnIndex }
::= { ipiFrLcnRowStatusTable 1 }

IpiFrLcnRowStatusEntry ::= SEQUENCE {
   ipiFrLcnRowStatus
      RowStatus,
   ipiFrLcnComponentName
      DisplayString,
   ipiFrLcnStorageType
      StorageType,
   ipiFrLcnIndex
      Integer32 }

ipiFrLcnRowStatus OBJECT-TYPE
   SYNTAX     RowStatus 
   ACCESS     read-write
   STATUS     mandatory
   DESCRIPTION
     "This variable is used as the basis for SNMP naming of
      ipiFrLcn components.
      These components can be added and deleted."
::= { ipiFrLcnRowStatusEntry 1 }

ipiFrLcnComponentName OBJECT-TYPE
   SYNTAX     DisplayString 
   ACCESS     read-only
   STATUS     mandatory
   DESCRIPTION
     "This variable provides the component's string name for
      use with the ASCII Console Interface"
::= { ipiFrLcnRowStatusEntry 2 }

ipiFrLcnStorageType OBJECT-TYPE
   SYNTAX     StorageType 
   ACCESS     read-only
   STATUS     mandatory
   DESCRIPTION
     "This variable represents the storage type value for the
      ipiFrLcn tables."
::= { ipiFrLcnRowStatusEntry 4 }

ipiFrLcnIndex OBJECT-TYPE
   SYNTAX     Integer32 (16..39)
   ACCESS     not-accessible
   STATUS     mandatory
   DESCRIPTION
     "This variable represents the index for the ipiFrLcn tables."
::= { ipiFrLcnRowStatusEntry 10 }

ipiFrLcnStateTable OBJECT-TYPE
   SYNTAX     SEQUENCE OF IpiFrLcnStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { ipiFrLcn 10 }

ipiFrLcnStateEntry OBJECT-TYPE
   SYNTAX     IpiFrLcnStateEntry
   ACCESS     not-accessible
   STATUS     mandatory
   DESCRIPTION
     "An entry in the ipiFrLcnStateTable."
   INDEX {
      ipiFrIndex,
      ipiFrLcnIndex }
::= { ipiFrLcnStateTable 1 }

IpiFrLcnStateEntry ::= SEQUENCE {
   ipiFrLcnAdminState
      INTEGER,
   ipiFrLcnOperationalState
      INTEGER,
   ipiFrLcnUsageState
      INTEGER,
   ipiFrLcnAvailabilityStatus
      OCTET STRING,
   ipiFrLcnProceduralStatus
      OCTET STRING,
   ipiFrLcnControlStatus
      OCTET STRING,
   ipiFrLcnAlarmStatus
      OCTET STRING,
   ipiFrLcnStandbyStatus
      INTEGER,
   ipiFrLcnUnknownStatus
      INTEGER }

ipiFrLcnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { ipiFrLcnStateEntry 1 }

ipiFrLcnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { ipiFrLcnStateEntry 2 }

ipiFrLcnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { ipiFrLcnStateEntry 3 }

ipiFrLcnAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { ipiFrLcnStateEntry 4 }

ipiFrLcnProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { ipiFrLcnStateEntry 5 }

ipiFrLcnControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { ipiFrLcnStateEntry 6 }

ipiFrLcnAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { ipiFrLcnStateEntry 7 }

ipiFrLcnStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { ipiFrLcnStateEntry 8 }

ipiFrLcnUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { ipiFrLcnStateEntry 9 }

ipiFrLcnOperTable OBJECT-TYPE
   SYNTAX     SEQUENCE OF IpiFrLcnOperEntry
   ACCESS     not-accessible
   STATUS     mandatory
   DESCRIPTION
     "This group contains status of the internal IP network interface."
::= { ipiFrLcn 11 }

ipiFrLcnOperEntry OBJECT-TYPE
   SYNTAX     IpiFrLcnOperEntry
   ACCESS     not-accessible
   STATUS     mandatory
   DESCRIPTION
     "An entry in the ipiFrLcnOperTable."
   INDEX {
      ipiFrIndex,
      ipiFrLcnIndex }
::= { ipiFrLcnOperTable 1 }

IpiFrLcnOperEntry ::= SEQUENCE {
   ipiFrLcnIpInterfaceDevice
      INTEGER,
   ipiFrLcnOpRemoteIpAddress
      IpAddress,
   ipiFrLcnPacketsSent
      Counter32,
   ipiFrLcnPacketsReceived
      Counter32,
   ipiFrLcnDiscardTxPackets
      Counter32,
   ipiFrLcnDiscardRcvPackets
      Counter32 }

ipiFrLcnIpInterfaceDevice OBJECT-TYPE
   SYNTAX     INTEGER  {
                 inactive(0),
                 active(1) }
   ACCESS     read-only
   STATUS     mandatory
   DESCRIPTION
     "The status of the internal IP network interface is inactive until either 
      the remoteIpAddress attribute is provisioned, or an IP packet is 
      exchanged between a Network Management Station and the internal 
      IP network interface (via the LCN). At this point, the status changes 
      to active."
   DEFVAL     { inactive }
::= { ipiFrLcnOperEntry 1 }

ipiFrLcnOpRemoteIpAddress OBJECT-TYPE
   SYNTAX     IpAddress 
   ACCESS     read-only
   STATUS     mandatory
   DESCRIPTION
     "This attribute indicates the IP address of the remote network device 
      connected to this interface. The value is either 0.0.0.0 until the frist 
      data packe tis received from the remote end, or is the value 
      provisioned in remoteIpAddress."
   DEFVAL     { '00000000'H }  -- "0.0.0.0"
::= { ipiFrLcnOperEntry 2 }

ipiFrLcnPacketsSent OBJECT-TYPE
   SYNTAX     Counter32 
   ACCESS     read-only
   STATUS     mandatory
   DESCRIPTION
     "This attribute counts the number of IP packets sent from this 
      interface."
::= { ipiFrLcnOperEntry 3 }

ipiFrLcnPacketsReceived OBJECT-TYPE
   SYNTAX     Counter32 
   ACCESS     read-only
   STATUS     mandatory
   DESCRIPTION
     "This attribute counts the number of IP packets received from the 
      remote network device."
::= { ipiFrLcnOperEntry 4 }

ipiFrLcnDiscardTxPackets OBJECT-TYPE
   SYNTAX     Counter32 
   ACCESS     read-only
   STATUS     mandatory
   DESCRIPTION
     "This attribute counts the number of IP packets destined to the 
      remote end which were discarded by this interface."
::= { ipiFrLcnOperEntry 5 }

ipiFrLcnDiscardRcvPackets OBJECT-TYPE
   SYNTAX     Counter32 
   ACCESS     read-only
   STATUS     mandatory
   DESCRIPTION
     "This attribute counts the number of IP packets received from the 
      remote end which were discarded by this interface."
::= { ipiFrLcnOperEntry 6 }

ipiFrLcnProvTable OBJECT-TYPE
   SYNTAX     SEQUENCE OF IpiFrLcnProvEntry
   ACCESS     not-accessible
   STATUS     mandatory
   DESCRIPTION
     "This group provides the provisionable attributes for the IpiFR Lcn 
      component."
::= { ipiFrLcn 12 }

ipiFrLcnProvEntry OBJECT-TYPE
   SYNTAX     IpiFrLcnProvEntry
   ACCESS     not-accessible
   STATUS     mandatory
   DESCRIPTION
     "An entry in the ipiFrLcnProvTable."
   INDEX {
      ipiFrIndex,
      ipiFrLcnIndex }
::= { ipiFrLcnProvTable 1 }

IpiFrLcnProvEntry ::= SEQUENCE {
   ipiFrLcnRemoteIpAddress
      IpAddress }

ipiFrLcnRemoteIpAddress OBJECT-TYPE
   SYNTAX     IpAddress 
   ACCESS     read-write
   STATUS     mandatory
   DESCRIPTION
     "This attribute specifies the IP address of the remote device 
      connected to this Lcn interface. This device can be a host, and / or a 
      gateway. If the device is a gateway, and StaticRoutes are defined 
      using this gateway, it is recommended that this attribute be set. It is 
      also recommended to set this attribute, if management applications 
      such as Software Download and SNMP, which can initiate IP traffic 
      with Network Management Stations, are potentially using this Lcn 
      interface. IP routing information within IpiFr is not known or 
      activated for this Lcn interface until the remoteIpAddress is known.
      
      When the destination IpAddress is left at its default value of 0.0.0.0, 
      the calling IP address is learnt from the first data packet received."
   DEFVAL     { '00000000'H }  -- "0.0.0.0"
::= { ipiFrLcnProvEntry 1 }


-- IPIFR Lcn/x DC
-- This component defines direct call options for calls issued without 
-- operator intervention. Connection is complete and can be initiated 
-- automatically.

ipiFrLcnDc OBJECT IDENTIFIER ::= { ipiFrLcn 2 }



ipiFrLcnDcRowStatusTable OBJECT-TYPE
   SYNTAX     SEQUENCE OF IpiFrLcnDcRowStatusEntry
   ACCESS     not-accessible
   STATUS     mandatory
   DESCRIPTION
     "This entry controls the addition and deletion of 
      ipiFrLcnDc components."
::= { ipiFrLcnDc 1 }

ipiFrLcnDcRowStatusEntry OBJECT-TYPE
   SYNTAX     IpiFrLcnDcRowStatusEntry
   ACCESS     not-accessible
   STATUS     mandatory
   DESCRIPTION
     "A single entry in the table represents a single 
      ipiFrLcnDc component."
   INDEX {
      ipiFrIndex,
      ipiFrLcnIndex,
      ipiFrLcnDcIndex }
::= { ipiFrLcnDcRowStatusTable 1 }

IpiFrLcnDcRowStatusEntry ::= SEQUENCE {
   ipiFrLcnDcRowStatus
      RowStatus,
   ipiFrLcnDcComponentName
      DisplayString,
   ipiFrLcnDcStorageType
      StorageType,
   ipiFrLcnDcIndex
      NonReplicated }

ipiFrLcnDcRowStatus OBJECT-TYPE
   SYNTAX     RowStatus 
   ACCESS     read-only
   STATUS     mandatory
   DESCRIPTION
     "This variable is used as the basis for SNMP naming of
      ipiFrLcnDc components.
      These components cannot be added nor deleted."
::= { ipiFrLcnDcRowStatusEntry 1 }

ipiFrLcnDcComponentName OBJECT-TYPE
   SYNTAX     DisplayString 
   ACCESS     read-only
   STATUS     mandatory
   DESCRIPTION
     "This variable provides the component's string name for
      use with the ASCII Console Interface"
::= { ipiFrLcnDcRowStatusEntry 2 }

ipiFrLcnDcStorageType OBJECT-TYPE
   SYNTAX     StorageType 
   ACCESS     read-only
   STATUS     mandatory
   DESCRIPTION
     "This variable represents the storage type value for the
      ipiFrLcnDc tables."
::= { ipiFrLcnDcRowStatusEntry 4 }

ipiFrLcnDcIndex OBJECT-TYPE
   SYNTAX     NonReplicated 
   ACCESS     not-accessible
   STATUS     mandatory
   DESCRIPTION
     "This variable represents the index for the ipiFrLcnDc tables."
::= { ipiFrLcnDcRowStatusEntry 10 }

ipiFrLcnDcOptionsTable OBJECT-TYPE
   SYNTAX     SEQUENCE OF IpiFrLcnDcOptionsEntry
   ACCESS     not-accessible
   STATUS     mandatory
   DESCRIPTION
     "Options group defines attributes associated with direct call. It 
      defines complete connection in terms of path and call options. This 
      connection can be permanent (pvc) or, in future release, switched 
      (svc). It can have facilities. The total number of bytes of facilities 
      including the facility codes, and all of the facility data from all of 
      the four classes of facilities:
      CCITT_Facilities
      DTE_Facilities
      National_Facilities
      International_Facilities
      must not exceed 512 bytes."
::= { ipiFrLcnDc 10 }

ipiFrLcnDcOptionsEntry OBJECT-TYPE
   SYNTAX     IpiFrLcnDcOptionsEntry
   ACCESS     not-accessible
   STATUS     mandatory
   DESCRIPTION
     "An entry in the ipiFrLcnDcOptionsTable."
   INDEX {
      ipiFrIndex,
      ipiFrLcnIndex,
      ipiFrLcnDcIndex }
::= { ipiFrLcnDcOptionsTable 1 }

IpiFrLcnDcOptionsEntry ::= SEQUENCE {
   ipiFrLcnDcRemoteNpi
      INTEGER,
   ipiFrLcnDcRemoteDna
      DigitString,
   ipiFrLcnDcRemoteDlci
      Unsigned32,
   ipiFrLcnDcType
      INTEGER,
   ipiFrLcnDcTransferPriority
      INTEGER,
   ipiFrLcnDcDiscardPriority
      INTEGER }

ipiFrLcnDcRemoteNpi OBJECT-TYPE
   SYNTAX     INTEGER  {
                 x121(0),
                 e164(1) }
   ACCESS     read-write
   STATUS     mandatory
   DESCRIPTION
     "RemoteNumbering Plan Indicator (Npi) indicates the numbering 
      plan used in the remoteDna."
   DEFVAL     { x121 }
::= { ipiFrLcnDcOptionsEntry 3 }

ipiFrLcnDcRemoteDna OBJECT-TYPE
   SYNTAX     DigitString (SIZE (1..15))
   ACCESS     read-write
   STATUS     mandatory
   DESCRIPTION
     "This attribute specifies the Data Network Address (Dna) of the 
      remote. This is the called (destination) DTE address (Dna) to which 
      this direct call will be sent.  Initially, the called DTE address 
      attribute must be present, that is, there must be a valid destination 
      address.  However, it may be possible in the future to configure the 
      direct call with a mnemonic address, in which case, this attribute 
      will contain a zero-length Dna, and the mnemonic address will be 
      carried as one of the facilities."
::= { ipiFrLcnDcOptionsEntry 4 }

ipiFrLcnDcRemoteDlci OBJECT-TYPE
   SYNTAX     Unsigned32 (16..1007)
   ACCESS     read-write
   STATUS     mandatory
   DESCRIPTION
     "This attribute provides the value of the remote DLCI (Data Link 
      Connection Identifier)"
::= { ipiFrLcnDcOptionsEntry 5 }

ipiFrLcnDcType OBJECT-TYPE
   SYNTAX     INTEGER  {
                 permanentMaster(1),
                 permanentSlave(2) }
   ACCESS     read-only
   STATUS     mandatory
   DESCRIPTION
     "This attribute specifies the type of Vc call:
      permanentMaster, 
      permanentSlave, 
      
      If the value is set to permanentMaster, then a permanent 
      connection will be established between 2 ends. The remote end 
      must be defined as a permanentSlave, permanentBackupSlave or 
      permanentSlaveWithBackup. The connection cannot be established 
      if the remote end is defined as anything else. The end defined as 
      permanentMaster always initiates the calls. It will attempt to call 
      once per minute.
      
      If the value is set to permanentSlave then a permanent connection 
      will be established between 2 ends. The remote end must be defined 
      as a permanentMaster. The connection cannot be established if the 
      remote end is defined as anything else. The permanentSlave end 
      will attempt to call once per minute."
   DEFVAL     { permanentSlave }
::= { ipiFrLcnDcOptionsEntry 6 }

ipiFrLcnDcTransferPriority OBJECT-TYPE
   SYNTAX     INTEGER  {
                 normal(0),
                 high(9),
                 useDnaDefTP(255) }
   ACCESS     read-write
   STATUS     mandatory
   DESCRIPTION
     "This attribute specifies the transfer priority to network for the 
      outgoing calls using this particular DLCI. It overRides the 
      defaultTransferPriority provisioned in its associated Dna 
      component.
      
      The transfer priority is a preference specified by an application 
      according to its delay-sensitivity requirement. Frames with high 
      transfer priority are served by the network before the frames with 
      normal priority.
      
      Each transfer priority contains a predetermined setting for trunk 
      queue (interrupting, delay or throughput), routing metric (delay or 
      throughput). 
      
      When the transfer priority is set at high, the trunk queue is set to 
      high, the routing metric is set to delay.
      
      When the transfer priority is set at normal, the trunk queue is set to 
      normal, the routing metric is set to throughput.
      
      The default of transferPriority is useDnaDefTP. It means using the 
      provisioning value under defaultTransferPriority of its associated 
      Dna for this DLCI."
   DEFVAL     { useDnaDefTP }
::= { ipiFrLcnDcOptionsEntry 9 }

ipiFrLcnDcDiscardPriority OBJECT-TYPE
   SYNTAX     INTEGER  {
                 normal(0),
                 high(1),
                 useDnaDefPriority(3) }
   ACCESS     read-write
   STATUS     mandatory
   DESCRIPTION
     "This attribute specifies the discard priority for outgoing call using 
      this DLCI. 
      
      The discard priority has three provisioning values: normal, high, 
      and useDnaDefPriority. Traffic with normal priority are discarded 
      first than the traffic with high priority. The Dna default value 
      (provisioned by outDefaultPriority) is taken if this attribute is set 
      to the value useDnaDefPriority.
      
      The default of discardPriority is useDnaDefPriority."
   DEFVAL     { useDnaDefPriority }
::= { ipiFrLcnDcOptionsEntry 10 }

ipiFrLcnDcNfaTable OBJECT-TYPE
   SYNTAX     SEQUENCE OF IpiFrLcnDcNfaEntry
   ACCESS     not-accessible
   STATUS     obsolete
   DESCRIPTION
     "This is the i'th National facility required for this direct call. Within 
      the provisioning system, the user specifies the facility code along 
      with the facility parameters. The facility is represented internally as 
      a hexadecimal string following the X.25 CCITT representation for 
      facility data.
      
      Two explicit attributes discardPriority and transferPriority are 
      created to replace H.01 and H.30 in the group 
      VcsDirectCallOptionsProv of this file. The migrate escape here 
      (DcComponent::migrateFaxEscape) propagates the old 
      provisioning data under H.01. 
      
      The rule of the above propagation are: 0 in H.01 is equivalent to 
      discardPriority 0; 1 in H.01 is equivalent to discardPriority 1. And 
      0 in H.30 is equivalent to transferPriority normal; 1 in H.30 is 
      equivalent to transferPriority high.
      
      Please refer to discardPriority and transferPriority for more 
      information on how to use them."
::= { ipiFrLcnDc 222 }

ipiFrLcnDcNfaEntry OBJECT-TYPE
   SYNTAX     IpiFrLcnDcNfaEntry
   ACCESS     not-accessible
   STATUS     obsolete
   DESCRIPTION
     "An entry in the ipiFrLcnDcNfaTable."
   INDEX {
      ipiFrIndex,
      ipiFrLcnIndex,
      ipiFrLcnDcIndex,
      ipiFrLcnDcNfaIndex }
::= { ipiFrLcnDcNfaTable 1 }

IpiFrLcnDcNfaEntry ::= SEQUENCE {
   ipiFrLcnDcNfaIndex
      Integer32,
   ipiFrLcnDcNfaValue
      HexString,
   ipiFrLcnDcNfaRowStatus
      RowStatus }

ipiFrLcnDcNfaIndex OBJECT-TYPE
   SYNTAX     Integer32 (1)
   ACCESS     not-accessible
   STATUS     obsolete
   DESCRIPTION
     "This variable represents the index for the ipiFrLcnDcNfaTable."
::= { ipiFrLcnDcNfaEntry 1 }

ipiFrLcnDcNfaValue OBJECT-TYPE
   SYNTAX     HexString (SIZE (0..128))
   ACCESS     read-write
   STATUS     obsolete
   DESCRIPTION
     "This variable represents an individual value for the
      ipiFrLcnDcNfaTable."
::= { ipiFrLcnDcNfaEntry 2 }

ipiFrLcnDcNfaRowStatus OBJECT-TYPE
   SYNTAX     RowStatus 
   ACCESS     write-only
   STATUS     obsolete
   DESCRIPTION
     "This variable is used to control the addition and deletion 
      of individual values of the ipiFrLcnDcNfaTable."
::= { ipiFrLcnDcNfaEntry 3 }


-- This component defines attributes collected by Frame Relay Vc.

ipiFrLcnVc OBJECT IDENTIFIER ::= { ipiFrLcn 3 }



ipiFrLcnVcRowStatusTable OBJECT-TYPE
   SYNTAX     SEQUENCE OF IpiFrLcnVcRowStatusEntry
   ACCESS     not-accessible
   STATUS     mandatory
   DESCRIPTION
     "This entry controls the addition and deletion of 
      ipiFrLcnVc components."
::= { ipiFrLcnVc 1 }

ipiFrLcnVcRowStatusEntry OBJECT-TYPE
   SYNTAX     IpiFrLcnVcRowStatusEntry
   ACCESS     not-accessible
   STATUS     mandatory
   DESCRIPTION
     "A single entry in the table represents a single 
      ipiFrLcnVc component."
   INDEX {
      ipiFrIndex,
      ipiFrLcnIndex,
      ipiFrLcnVcIndex }
::= { ipiFrLcnVcRowStatusTable 1 }

IpiFrLcnVcRowStatusEntry ::= SEQUENCE {
   ipiFrLcnVcRowStatus
      RowStatus,
   ipiFrLcnVcComponentName
      DisplayString,
   ipiFrLcnVcStorageType
      StorageType,
   ipiFrLcnVcIndex
      NonReplicated }

ipiFrLcnVcRowStatus OBJECT-TYPE
   SYNTAX     RowStatus 
   ACCESS     read-only
   STATUS     mandatory
   DESCRIPTION
     "This variable is used as the basis for SNMP naming of
      ipiFrLcnVc components.
      These components cannot be added nor deleted."
::= { ipiFrLcnVcRowStatusEntry 1 }

ipiFrLcnVcComponentName OBJECT-TYPE
   SYNTAX     DisplayString 
   ACCESS     read-only
   STATUS     mandatory
   DESCRIPTION
     "This variable provides the component's string name for
      use with the ASCII Console Interface"
::= { ipiFrLcnVcRowStatusEntry 2 }

ipiFrLcnVcStorageType OBJECT-TYPE
   SYNTAX     StorageType 
   ACCESS     read-only
   STATUS     mandatory
   DESCRIPTION
     "This variable represents the storage type value for the
      ipiFrLcnVc tables."
::= { ipiFrLcnVcRowStatusEntry 4 }

ipiFrLcnVcIndex OBJECT-TYPE
   SYNTAX     NonReplicated 
   ACCESS     not-accessible
   STATUS     mandatory
   DESCRIPTION
     "This variable represents the index for the ipiFrLcnVc tables."
::= { ipiFrLcnVcRowStatusEntry 10 }

ipiFrLcnVcCadTable OBJECT-TYPE
   SYNTAX     SEQUENCE OF IpiFrLcnVcCadEntry
   ACCESS     not-accessible
   STATUS     mandatory
   DESCRIPTION
     "This group represents operational call data related to Frame Relay 
      Vc. It can be displayed only for Frame Relay Vc which is created by 
      application."
::= { ipiFrLcnVc 10 }

ipiFrLcnVcCadEntry OBJECT-TYPE
   SYNTAX     IpiFrLcnVcCadEntry
   ACCESS     not-accessible
   STATUS     mandatory
   DESCRIPTION
     "An entry in the ipiFrLcnVcCadTable."
   INDEX {
      ipiFrIndex,
      ipiFrLcnIndex,
      ipiFrLcnVcIndex }
::= { ipiFrLcnVcCadTable 1 }

IpiFrLcnVcCadEntry ::= SEQUENCE {
   ipiFrLcnVcType
      INTEGER,
   ipiFrLcnVcState
      INTEGER,
   ipiFrLcnVcPreviousState
      INTEGER,
   ipiFrLcnVcDiagnosticCode
      Unsigned32,
   ipiFrLcnVcPreviousDiagnosticCode
      Unsigned32,
   ipiFrLcnVcCalledNpi
      INTEGER,
   ipiFrLcnVcCalledDna
      DigitString,
   ipiFrLcnVcCalledLcn
      Unsigned32,
   ipiFrLcnVcCallingNpi
      INTEGER,
   ipiFrLcnVcCallingDna
      DigitString,
   ipiFrLcnVcCallingLcn
      Unsigned32,
   ipiFrLcnVcAccountingEnabled
      INTEGER,
   ipiFrLcnVcFastSelectCall
      INTEGER,
   ipiFrLcnVcPathReliability
      INTEGER,
   ipiFrLcnVcAccountingEnd
      INTEGER,
   ipiFrLcnVcPriority
      INTEGER,
   ipiFrLcnVcSegmentSize
      Unsigned32,
   ipiFrLcnVcMaxSubnetPktSize
      Unsigned32,
   ipiFrLcnVcRcosToNetwork
      INTEGER,
   ipiFrLcnVcRcosFromNetwork
      INTEGER,
   ipiFrLcnVcEmissionPriorityToNetwork
      INTEGER,
   ipiFrLcnVcEmissionPriorityFromNetwork
      INTEGER,
   ipiFrLcnVcDataPath
      AsciiString }

ipiFrLcnVcType OBJECT-TYPE
   SYNTAX     INTEGER  {
                 svc(0),
                 pvc(1),
                 spvc(2) }
   ACCESS     read-only
   STATUS     mandatory
   DESCRIPTION
     "This attribute displays the type of call, pvc,svc or spvc."
::= { ipiFrLcnVcCadEntry 1 }

ipiFrLcnVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { ipiFrLcnVcCadEntry 2 }

ipiFrLcnVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { ipiFrLcnVcCadEntry 3 }

ipiFrLcnVcDiagnosticCode OBJECT-TYPE
   SYNTAX     Unsigned32 (0..255)
   ACCESS     read-only
   STATUS     mandatory
   DESCRIPTION
     "This attribute displays the internal substate of call control. It is used 
      to further refine state of call processing."
::= { ipiFrLcnVcCadEntry 4 }

ipiFrLcnVcPreviousDiagnosticCode OBJECT-TYPE
   SYNTAX     Unsigned32 (0..255)
   ACCESS     read-only
   STATUS     mandatory
   DESCRIPTION
     "This attribute displays the internal substate of call control. It is used 
      to further refine state of call processing."
::= { ipiFrLcnVcCadEntry 5 }

ipiFrLcnVcCalledNpi OBJECT-TYPE
   SYNTAX     INTEGER  {
                 x121(0),
                 e164(1) }
   ACCESS     read-only
   STATUS     mandatory
   DESCRIPTION
     "This attribute displays the Numbering Plan Indicator (NPI) of the 
      called end."
::= { ipiFrLcnVcCadEntry 6 }

ipiFrLcnVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { ipiFrLcnVcCadEntry 7 }

ipiFrLcnVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { ipiFrLcnVcCadEntry 8 }

ipiFrLcnVcCallingNpi OBJECT-TYPE
   SYNTAX     INTEGER  {
                 x121(0),
                 e164(1) }
   ACCESS     read-only
   STATUS     mandatory
   DESCRIPTION
     "This attribute displays the Numbering Plan Indicator (NPI) of the 
      calling end."
::= { ipiFrLcnVcCadEntry 9 }

ipiFrLcnVcCallingDna OBJECT-TYPE
   SYNTAX     DigitString (SIZE (1..15))
   ACCESS     read-only
   STATUS     mandatory
   DESCRIPTION
     "This attribute displays the Data Network Address (Dna) of the 
      calling end."
::= { ipiFrLcnVcCadEntry 10 }

ipiFrLcnVcCallingLcn OBJECT-TYPE
   SYNTAX     Unsigned32 (1..65535)
   ACCESS     read-only
   STATUS     mandatory
   DESCRIPTION
     "This attribute displays the Logical Channel Number of the calling 
      end."
::= { ipiFrLcnVcCadEntry 11 }

ipiFrLcnVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { ipiFrLcnVcCadEntry 12 }

ipiFrLcnVcFastSelectCall OBJECT-TYPE
   SYNTAX     INTEGER  {
                 no(0),
                 yes(1) }
   ACCESS     read-only
   STATUS     mandatory
   DESCRIPTION
     "This attribute displays that this is a fast select call."
::= { ipiFrLcnVcCadEntry 13 }

ipiFrLcnVcPathReliability OBJECT-TYPE
   SYNTAX     INTEGER  {
                 high(0),
                 normal(1) }
   ACCESS     read-only
   STATUS     mandatory
   DESCRIPTION
     "This attribute displays the path reliability."
::= { ipiFrLcnVcCadEntry 19 }

ipiFrLcnVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { ipiFrLcnVcCadEntry 20 }

ipiFrLcnVcPriority OBJECT-TYPE
   SYNTAX     INTEGER  {
                 normal(0),
                 high(1) }
   ACCESS     read-only
   STATUS     mandatory
   DESCRIPTION
     "This attribute displays whether the call is a normal or a high 
      priority call."
::= { ipiFrLcnVcCadEntry 21 }

ipiFrLcnVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { ipiFrLcnVcCadEntry 22 }

ipiFrLcnVcMaxSubnetPktSize OBJECT-TYPE
   SYNTAX     Unsigned32 (0..4096)
   ACCESS     read-only
   STATUS     mandatory
   DESCRIPTION
     "This attribute indicates the maximum packet size allowed on the Vc."
::= { ipiFrLcnVcCadEntry 27 }

ipiFrLcnVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { ipiFrLcnVcCadEntry 28 }

ipiFrLcnVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { ipiFrLcnVcCadEntry 29 }

ipiFrLcnVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { ipiFrLcnVcCadEntry 30 }

ipiFrLcnVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { ipiFrLcnVcCadEntry 31 }

ipiFrLcnVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { ipiFrLcnVcCadEntry 32 }

ipiFrLcnVcIntdTable OBJECT-TYPE
   SYNTAX     SEQUENCE OF IpiFrLcnVcIntdEntry
   ACCESS     not-accessible
   STATUS     mandatory
   DESCRIPTION
     "This group defines display of interval data collected by Vc. Data in 
      this group is variable and may depend on time when this display 
      command is issued."
::= { ipiFrLcnVc 11 }

ipiFrLcnVcIntdEntry OBJECT-TYPE
   SYNTAX     IpiFrLcnVcIntdEntry
   ACCESS     not-accessible
   STATUS     mandatory
   DESCRIPTION
     "An entry in the ipiFrLcnVcIntdTable."
   INDEX {
      ipiFrIndex,
      ipiFrLcnIndex,
      ipiFrLcnVcIndex }
::= { ipiFrLcnVcIntdTable 1 }

IpiFrLcnVcIntdEntry ::= SEQUENCE {
   ipiFrLcnVcCallReferenceNumber
      Hex,
   ipiFrLcnVcElapsedTimeTillNow
      Unsigned32,
   ipiFrLcnVcSegmentsRx
      Unsigned32,
   ipiFrLcnVcSegmentsSent
      Unsigned32,
   ipiFrLcnVcStartTime
      EnterpriseDateAndTime }

ipiFrLcnVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { ipiFrLcnVcIntdEntry 1 }

ipiFrLcnVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { ipiFrLcnVcIntdEntry 2 }

ipiFrLcnVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { ipiFrLcnVcIntdEntry 3 }

ipiFrLcnVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { ipiFrLcnVcIntdEntry 4 }

ipiFrLcnVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { ipiFrLcnVcIntdEntry 5 }

ipiFrLcnVcFrdTable OBJECT-TYPE
   SYNTAX     SEQUENCE OF IpiFrLcnVcFrdEntry
   ACCESS     not-accessible
   STATUS     mandatory
   DESCRIPTION
     "This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { ipiFrLcnVc 12 }

ipiFrLcnVcFrdEntry OBJECT-TYPE
   SYNTAX     IpiFrLcnVcFrdEntry
   ACCESS     not-accessible
   STATUS     mandatory
   DESCRIPTION
     "An entry in the ipiFrLcnVcFrdTable."
   INDEX {
      ipiFrIndex,
      ipiFrLcnIndex,
      ipiFrLcnVcIndex }
::= { ipiFrLcnVcFrdTable 1 }

IpiFrLcnVcFrdEntry ::= SEQUENCE {
   ipiFrLcnVcFrmCongestedToSubnet
      Unsigned32,
   ipiFrLcnVcCannotForwardToSubnet
      Unsigned32,
   ipiFrLcnVcNotDataXferToSubnet
      Unsigned32,
   ipiFrLcnVcOutOfRangeFrmFromSubnet
      Unsigned32,
   ipiFrLcnVcCombErrorsFromSubnet
      Unsigned32,
   ipiFrLcnVcDuplicatesFromSubnet
      Unsigned32,
   ipiFrLcnVcNotDataXferFromSubnet
      Unsigned32,
   ipiFrLcnVcFrmLossTimeouts
      Unsigned32,
   ipiFrLcnVcOoSeqByteCntExceeded
      Unsigned32,
   ipiFrLcnVcPeakOoSeqPktCount
      Unsigned32,
   ipiFrLcnVcPeakOoSeqFrmForwarded
      Unsigned32,
   ipiFrLcnVcSendSequenceNumber
      Unsigned32,
   ipiFrLcnVcPktRetryTimeouts
      Unsigned32,
   ipiFrLcnVcPeakRetryQueueSize
      Unsigned32,
   ipiFrLcnVcSubnetRecoveries
      Unsigned32,
   ipiFrLcnVcOoSeqPktCntExceeded
      Unsigned32,
   ipiFrLcnVcPeakOoSeqByteCount
      Unsigned32 }

ipiFrLcnVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { ipiFrLcnVcFrdEntry 2 }

ipiFrLcnVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { ipiFrLcnVcFrdEntry 3 }

ipiFrLcnVcNotDataXferToSubnet OBJECT-TYPE
   SYNTAX     Unsigned32 (0..5000)
   ACCESS     read-only
   STATUS     mandatory
   DESCRIPTION
     "This attribute records the number of frames from link discarded 
      when the Vc tries to recover from internal path failure."
::= { ipiFrLcnVcFrdEntry 4 }

ipiFrLcnVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { ipiFrLcnVcFrdEntry 5 }

ipiFrLcnVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { ipiFrLcnVcFrdEntry 6 }

ipiFrLcnVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { ipiFrLcnVcFrdEntry 7 }

ipiFrLcnVcNotDataXferFromSubnet OBJECT-TYPE
   SYNTAX     Unsigned32 (0..5000)
   ACCESS     read-only
   STATUS     mandatory
   DESCRIPTION
     "This attribute displays the number of subnet packets discarded when 
      data transfer is suspended in Vc recovery."
::= { ipiFrLcnVcFrdEntry 8 }

ipiFrLcnVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { ipiFrLcnVcFrdEntry 9 }

ipiFrLcnVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { ipiFrLcnVcFrdEntry 10 }

ipiFrLcnVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { ipiFrLcnVcFrdEntry 11 }

ipiFrLcnVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { ipiFrLcnVcFrdEntry 12 }

ipiFrLcnVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { ipiFrLcnVcFrdEntry 13 }

ipiFrLcnVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { ipiFrLcnVcFrdEntry 15 }

ipiFrLcnVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { ipiFrLcnVcFrdEntry 16 }

ipiFrLcnVcSubnetRecoveries OBJECT-TYPE
   SYNTAX     Unsigned32 (0..5000)
   ACCESS     read-only
   STATUS     mandatory
   DESCRIPTION
     "This attribute displays the number of successful Vc recovery 
      attempts."
::= { ipiFrLcnVcFrdEntry 17 }

ipiFrLcnVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { ipiFrLcnVcFrdEntry 19 }

ipiFrLcnVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { ipiFrLcnVcFrdEntry 20 }

ipiFrLcnVcDmepTable OBJECT-TYPE
   SYNTAX     SEQUENCE OF IpiFrLcnVcDmepEntry
   ACCESS     not-accessible
   STATUS     mandatory
   DESCRIPTION
     "This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { ipiFrLcnVc 417 }

ipiFrLcnVcDmepEntry OBJECT-TYPE
   SYNTAX     IpiFrLcnVcDmepEntry
   ACCESS     not-accessible
   STATUS     mandatory
   DESCRIPTION
     "An entry in the ipiFrLcnVcDmepTable."
   INDEX {
      ipiFrIndex,
      ipiFrLcnIndex,
      ipiFrLcnVcIndex,
      ipiFrLcnVcDmepValue }
::= { ipiFrLcnVcDmepTable 1 }

IpiFrLcnVcDmepEntry ::= SEQUENCE {
   ipiFrLcnVcDmepValue
      RowPointer }

ipiFrLcnVcDmepValue OBJECT-TYPE
   SYNTAX     RowPointer 
   ACCESS     read-only
   STATUS     mandatory
   DESCRIPTION
     "This variable represents both the value and the index for the
      ipiFrLcnVcDmepTable."
::= { ipiFrLcnVcDmepEntry 1 }


-- IpiFr StaticRoute/destIpAddress
-- 
-- This component contains information for setting up a static routes 
-- on the IpiFr service. These provisioned static IP routes allow the 
-- ability to specify IP routes to Network Management Stations which 
-- are not directly connected to the Passport module. The component 
-- is indexed by a destination IP Address. It represents the static IP 
-- route to a particular IP host, subnetwork, or network. The default 
-- route IP address is indexed by 0.0.0.0 .
-- 
-- Note that subnetwork routes are identified using IpiFr's provisioned 
-- subnetMask. This subnetMask only applies to the IP network for 
-- which IpiFr's IP Address belongs. Therefore, subnetwork routes are 
-- only supported for this local IP network.

ipiFrSr OBJECT IDENTIFIER ::= { ipiFr 5 }



ipiFrSrRowStatusTable OBJECT-TYPE
   SYNTAX     SEQUENCE OF IpiFrSrRowStatusEntry
   ACCESS     not-accessible
   STATUS     mandatory
   DESCRIPTION
     "This entry controls the addition and deletion of 
      ipiFrSr components."
::= { ipiFrSr 1 }

ipiFrSrRowStatusEntry OBJECT-TYPE
   SYNTAX     IpiFrSrRowStatusEntry
   ACCESS     not-accessible
   STATUS     mandatory
   DESCRIPTION
     "A single entry in the table represents a single 
      ipiFrSr component."
   INDEX {
      ipiFrIndex,
      ipiFrSrIndex }
::= { ipiFrSrRowStatusTable 1 }

IpiFrSrRowStatusEntry ::= SEQUENCE {
   ipiFrSrRowStatus
      RowStatus,
   ipiFrSrComponentName
      DisplayString,
   ipiFrSrStorageType
      StorageType,
   ipiFrSrIndex
      IpAddress }

ipiFrSrRowStatus OBJECT-TYPE
   SYNTAX     RowStatus 
   ACCESS     read-write
   STATUS     mandatory
   DESCRIPTION
     "This variable is used as the basis for SNMP naming of
      ipiFrSr components.
      These components can be added and deleted."
::= { ipiFrSrRowStatusEntry 1 }

ipiFrSrComponentName OBJECT-TYPE
   SYNTAX     DisplayString 
   ACCESS     read-only
   STATUS     mandatory
   DESCRIPTION
     "This variable provides the component's string name for
      use with the ASCII Console Interface"
::= { ipiFrSrRowStatusEntry 2 }

ipiFrSrStorageType OBJECT-TYPE
   SYNTAX     StorageType 
   ACCESS     read-only
   STATUS     mandatory
   DESCRIPTION
     "This variable represents the storage type value for the
      ipiFrSr tables."
::= { ipiFrSrRowStatusEntry 4 }

ipiFrSrIndex OBJECT-TYPE
   SYNTAX     IpAddress 
   ACCESS     not-accessible
   STATUS     mandatory
   DESCRIPTION
     "This variable represents the index for the ipiFrSr tables."
::= { ipiFrSrRowStatusEntry 10 }

ipiFrSrProvTable OBJECT-TYPE
   SYNTAX     SEQUENCE OF IpiFrSrProvEntry
   ACCESS     not-accessible
   STATUS     mandatory
   DESCRIPTION
     "This group provides the provisionable parameters for setting up a 
      static route."
::= { ipiFrSr 10 }

ipiFrSrProvEntry OBJECT-TYPE
   SYNTAX     IpiFrSrProvEntry
   ACCESS     not-accessible
   STATUS     mandatory
   DESCRIPTION
     "An entry in the ipiFrSrProvTable."
   INDEX {
      ipiFrIndex,
      ipiFrSrIndex }
::= { ipiFrSrProvTable 1 }

IpiFrSrProvEntry ::= SEQUENCE {
   ipiFrSrGatewayIpAddress
      IpAddress }

ipiFrSrGatewayIpAddress OBJECT-TYPE
   SYNTAX     IpAddress 
   ACCESS     read-write
   STATUS     mandatory
   DESCRIPTION
     "The attribute specifies the IP Address of the next hop in this route to 
      the destination IP Address. For this static route to be active, the 
      value of this attribute must match the opRemoteIpAddress attribute 
      of one of the Lcn components."
   DEFVAL     { '00000000'H }  -- "0.0.0.0"
::= { ipiFrSrProvEntry 1 }

ipiFrSrBGtyIpaTable OBJECT-TYPE
   SYNTAX     SEQUENCE OF IpiFrSrBGtyIpaEntry
   ACCESS     not-accessible
   STATUS     mandatory
   DESCRIPTION
     "The attribute specifies an ordered list of alternative gateways to use 
      for the route to the destination IP Address. This attribute is only 
      supported for the default route. 
      
      If the Lcn interface of the current gateway IP Address fails, then the 
      backupGatewayIpAddresses, listed in this attribute, are searched, in 
      order, for a gatewayIpAddress with an enabled Lcn. If found, the 
      static route to this destination IP Address is updated to use the 
      found gateway IP Address.
      
      Note that an Lcn interface can fail due to either the Vc through the 
      Passport Network failing, or an Lmi indication that the far-end link 
      is failed."
::= { ipiFrSr 327 }

ipiFrSrBGtyIpaEntry OBJECT-TYPE
   SYNTAX     IpiFrSrBGtyIpaEntry
   ACCESS     not-accessible
   STATUS     mandatory
   DESCRIPTION
     "An entry in the ipiFrSrBGtyIpaTable."
   INDEX {
      ipiFrIndex,
      ipiFrSrIndex,
      ipiFrSrBGtyIpaIndex }
::= { ipiFrSrBGtyIpaTable 1 }

IpiFrSrBGtyIpaEntry ::= SEQUENCE {
   ipiFrSrBGtyIpaIndex
      Integer32,
   ipiFrSrBGtyIpaValue
      IpAddress,
   ipiFrSrBGtyIpaRowStatus
      RowStatus }

ipiFrSrBGtyIpaIndex OBJECT-TYPE
   SYNTAX     Integer32 (1..23)
   ACCESS     not-accessible
   STATUS     mandatory
   DESCRIPTION
     "This variable represents the index for the ipiFrSrBGtyIpaTable."
::= { ipiFrSrBGtyIpaEntry 1 }

ipiFrSrBGtyIpaValue OBJECT-TYPE
   SYNTAX     IpAddress 
   ACCESS     read-write
   STATUS     mandatory
   DESCRIPTION
     "This variable represents an individual value for the
      ipiFrSrBGtyIpaTable."
::= { ipiFrSrBGtyIpaEntry 2 }

ipiFrSrBGtyIpaRowStatus OBJECT-TYPE
   SYNTAX     RowStatus 
   ACCESS     write-only
   STATUS     mandatory
   DESCRIPTION
     "This variable is used to control the addition and deletion 
      of individual values of the ipiFrSrBGtyIpaTable."
::= { ipiFrSrBGtyIpaEntry 3 }

-- 
-- *** THIS SUBTREE CURRENTLY NOT IMPLEMENTED ***
-- 

-- IpiFr Route/destIpAddress
-- 
-- This dynamic component represents an active IP route within the 
-- IpiFr service. The component is indexed by the destination IP 
-- Address of the IP route. It represents the IP route to a particular IP 
-- host, subnetwork, or network. The default route IP address is 
-- indexed by 0.0.0.0 .
-- 
-- Note that only an active route is shown as an IpiFr Route/
-- <IP_Address> . A provisioned static route (i.e. IpiFr StaticRoute/
-- <IP_Address>) will be listed as an active route only if it's Lcn 
-- interface is enabled (i.e. the associated Vc through the Passport 
-- network is up, and the FrameRelay Lmi is reporting the far-end link 
-- is up ) .
-- 

ipiFrR OBJECT IDENTIFIER ::= { ipiFr 6 }



ipiFrRRowStatusTable OBJECT-TYPE
   SYNTAX     SEQUENCE OF IpiFrRRowStatusEntry
   ACCESS     not-accessible
   STATUS     mandatory
   DESCRIPTION
     "*** THIS TABLE CURRENTLY NOT IMPLEMENTED ***

      This entry controls the addition and deletion of 
      ipiFrR components."
::= { ipiFrR 1 }

ipiFrRRowStatusEntry OBJECT-TYPE
   SYNTAX     IpiFrRRowStatusEntry
   ACCESS     not-accessible
   STATUS     mandatory
   DESCRIPTION
     "A single entry in the table represents a single 
      ipiFrR component."
   INDEX {
      ipiFrIndex,
      ipiFrRIndex }
::= { ipiFrRRowStatusTable 1 }

IpiFrRRowStatusEntry ::= SEQUENCE {
   ipiFrRRowStatus
      RowStatus,
   ipiFrRComponentName
      DisplayString,
   ipiFrRStorageType
      StorageType,
   ipiFrRIndex
      IpAddress }

ipiFrRRowStatus OBJECT-TYPE
   SYNTAX     RowStatus 
   ACCESS     read-only
   STATUS     mandatory
   DESCRIPTION
     "This variable is used as the basis for SNMP naming of
      ipiFrR components.
      These components cannot be added nor deleted."
::= { ipiFrRRowStatusEntry 1 }

ipiFrRComponentName OBJECT-TYPE
   SYNTAX     DisplayString 
   ACCESS     read-only
   STATUS     mandatory
   DESCRIPTION
     "This variable provides the component's string name for
      use with the ASCII Console Interface"
::= { ipiFrRRowStatusEntry 2 }

ipiFrRStorageType OBJECT-TYPE
   SYNTAX     StorageType 
   ACCESS     read-only
   STATUS     mandatory
   DESCRIPTION
     "This variable represents the storage type value for the
      ipiFrR tables."
::= { ipiFrRRowStatusEntry 4 }

ipiFrRIndex OBJECT-TYPE
   SYNTAX     IpAddress 
   ACCESS     not-accessible
   STATUS     mandatory
   DESCRIPTION
     "This variable represents the index for the ipiFrR tables."
::= { ipiFrRRowStatusEntry 10 }

ipiFrROperTable OBJECT-TYPE
   SYNTAX     SEQUENCE OF IpiFrROperEntry
   ACCESS     not-accessible
   STATUS     mandatory
   DESCRIPTION
     "*** THIS TABLE CURRENTLY NOT IMPLEMENTED ***

      This group contains operational status of the static route"
::= { ipiFrR 10 }

ipiFrROperEntry OBJECT-TYPE
   SYNTAX     IpiFrROperEntry
   ACCESS     not-accessible
   STATUS     mandatory
   DESCRIPTION
     "An entry in the ipiFrROperTable."
   INDEX {
      ipiFrIndex,
      ipiFrRIndex }
::= { ipiFrROperTable 1 }

IpiFrROperEntry ::= SEQUENCE {
   ipiFrRGtyIpAddr
      IpAddress,
   ipiFrRLcnIf
      Unsigned32,
   ipiFrRType
      INTEGER }

ipiFrRGtyIpAddr OBJECT-TYPE
   SYNTAX     IpAddress 
   ACCESS     read-only
   STATUS     mandatory
   DESCRIPTION
     "The attribute specifies the IP Address of the next hop in this route to 
      the destination IP Address."
   DEFVAL     { '00000000'H }  -- "0.0.0.0"
::= { ipiFrROperEntry 1 }

ipiFrRLcnIf OBJECT-TYPE
   SYNTAX     Unsigned32 (16..39)
   ACCESS     read-only
   STATUS     mandatory
   DESCRIPTION
     "This attribute specifies the Lcn interface used by this IP route."
::= { ipiFrROperEntry 3 }

ipiFrRType OBJECT-TYPE
   SYNTAX     INTEGER  {
                 host(1),
                 subnet(2),
                 network(3) }
   ACCESS     read-only
   STATUS     mandatory
   DESCRIPTION
     "This attribute indicates whether a route is going to a host or a 
      subnet or a network."
::= { ipiFrROperEntry 4 }




-- 
-- Version and Compliance statements
-- 



-- Object-Group Statement:
-- A list of all current accessible leaf objects.

-- OBJECTS { ipiFrDnaCugComponentName,
--           ipiFrLcnVcFrmCongestedToSubnet,
--           ipiFrDnaTransferPriorityOverRide,
--           ipiFrDnaCugInterlockCode,
--           ipiFrDnaServiceCategory,
--           ipiFrDnaServiceExchange,
--           ipiFrLcnUnknownStatus,
--           ipiFrLcnStandbyStatus,
--           ipiFrLcnDcStorageType,
--           ipiFrLcnVcCallingLcn,
--           ipiFrLcnStorageType,
--           ipiFrLcnVcDmepValue,
--           ipiFrRComponentName,
--           ipiFrLcnVcRcosFromNetwork,
--           ipiFrIpAddress,
--           ipiFrLcnVcDuplicatesFromSubnet,
--           ipiFrLcnDcRemoteDlci,
--           ipiFrLcnVcStartTime,
--           ipiFrSubnetMask,
--           ipiFrLcnControlStatus,
--           ipiFrLcnAdminState,
--           ipiFrSrBGtyIpaRowStatus,
--           ipiFrLcnVcDiagnosticCode,
--           ipiFrLcnDcRowStatus,
--           ipiFrStorageType,
--           ipiFrComponentName,
--           ipiFrLcnRowStatus,
--           ipiFrLcnVcOoSeqByteCntExceeded,
--           ipiFrSrBGtyIpaValue,
--           ipiFrLcnDcRemoteNpi,
--           ipiFrSrStorageType,
--           ipiFrDnaStorageType,
--           ipiFrLcnVcEmissionPriorityFromNetwork,
--           ipiFrLcnVcPktRetryTimeouts,
--           ipiFrLcnVcOutOfRangeFrmFromSubnet,
--           ipiFrDnaCugStorageType,
--           ipiFrLcnVcCalledDna,
--           ipiFrLcnUsageState,
--           ipiFrLcnVcType,
--           ipiFrLcnVcAccountingEnabled,
--           ipiFrLcnVcSegmentsSent,
--           ipiFrDnaCugIncCalls,
--           ipiFrLcnDcDiscardPriority,
--           ipiFrLcnVcPreviousState,
--           ipiFrMaximumNumberOfLcn,
--           ipiFrLcnVcSubnetRecoveries,
--           ipiFrLcnVcOoSeqPktCntExceeded,
--           ipiFrLcnVcPeakRetryQueueSize,
--           ipiFrLcnIpInterfaceDevice,
--           ipiFrLcnOperationalState,
--           ipiFrSrRowStatus,
--           ipiFrLcnDcTransferPriority,
--           ipiFrLcnVcSendSequenceNumber,
--           ipiFrRGtyIpAddr,
--           ipiFrLcnVcSegmentSize,
--           ipiFrRStorageType,
--           ipiFrDnaCugRowStatus,
--           ipiFrLcnVcPeakOoSeqPktCount,
--           ipiFrLcnVcCallingNpi,
--           ipiFrLcnVcNotDataXferFromSubnet,
--           ipiFrDnaOutDefaultPriority,
--           ipiFrLcnVcFastSelectCall,
--           ipiFrLcnVcComponentName,
--           ipiFrLcnPacketsReceived,
--           ipiFrLcnVcMaxSubnetPktSize,
--           ipiFrLcnAvailabilityStatus,
--           ipiFrDnaCugDnic,
--           ipiFrLcnAlarmStatus,
--           ipiFrLcnVcPriority,
--           ipiFrLcnVcPathReliability,
--           ipiFrLcnVcCannotForwardToSubnet,
--           ipiFrDnaComponentName,
--           ipiFrDnaAccountClass,
--           ipiFrSrGatewayIpAddress,
--           ipiFrLcnVcCallReferenceNumber,
--           ipiFrLcnRemoteIpAddress,
--           ipiFrLcnVcState,
--           ipiFrRowStatus,
--           ipiFrLcnDcType,
--           ipiFrDnaOutCalls,
--           ipiFrLcnVcEmissionPriorityToNetwork,
--           ipiFrDnaNumberingPlanIndicator,
--           ipiFrLcnDcRemoteDna,
--           ipiFrLcnVcStorageType,
--           ipiFrLcnProceduralStatus,
--           ipiFrDnaDefaultTransferPriority,
--           ipiFrLcnDiscardRcvPackets,
--           ipiFrLcnDcComponentName,
--           ipiFrLcnVcAccountingEnd,
--           ipiFrDnaDataNetworkAddress,
--           ipiFrLcnVcCalledNpi,
--           ipiFrLcnOpRemoteIpAddress,
--           ipiFrLcnVcElapsedTimeTillNow,
--           ipiFrLcnComponentName,
--           ipiFrLcnVcPeakOoSeqByteCount,
--           ipiFrLcnVcNotDataXferToSubnet,
--           ipiFrDnaCugType,
--           ipiFrLcnPacketsSent,
--           ipiFrRLcnIf,
--           ipiFrLcnVcRowStatus,
--           ipiFrDnaIncCalls,
--           ipiFrLcnVcFrmLossTimeouts,
--           ipiFrRRowStatus,
--           ipiFrLcnVcSegmentsRx,
--           ipiFrLcnVcRcosToNetwork,
--           ipiFrDnaIncAccess,
--           ipiFrSrComponentName,
--           ipiFrLcnVcPreviousDiagnosticCode,
--           ipiFrLcnVcDataPath,
--           ipiFrLcnDiscardTxPackets,
--           ipiFrLcnVcCalledLcn,
--           ipiFrDnaRowStatus,
--           ipiFrRType,
--           ipiFrLcnVcCombErrorsFromSubnet,
--           ipiFrLcnVcCallingDna,
--           ipiFrLcnVcPeakOoSeqFrmForwarded }
-- STATUS  mandatory
-- DESCRIPTION
--   "A list of all current accessible leaf objects."

ipiFrGroup OBJECT IDENTIFIER ::= { ipiFrMIB 1 }
ipiFrGroupBE OBJECT IDENTIFIER ::= { ipiFrGroup 5 }
ipiFrGroupBE01 OBJECT IDENTIFIER ::= { ipiFrGroupBE 2 }
ipiFrGroupBE01A OBJECT IDENTIFIER ::= { ipiFrGroupBE01 2 }



-- Agent-Capabilities Statement:

-- PRODUCT-RELEASE "Passport Release 7.0 IpiFr."
-- STATUS          mandatory
-- DESCRIPTION     "IpiFr MIB: MIB Version BE01A,
--                  Software Version BG00S4C."
-- SUPPORTS        Nortel-Magellan-Passport-IpiFrMIB
--    INCLUDES     { ipiFrGroupBE01A }

ipiFrCapabilities OBJECT IDENTIFIER ::= { ipiFrMIB 3 }
ipiFrCapabilitiesBE OBJECT IDENTIFIER ::= { ipiFrCapabilities 5 }
ipiFrCapabilitiesBE01 OBJECT IDENTIFIER ::= { ipiFrCapabilitiesBE 2 }
ipiFrCapabilitiesBE01A OBJECT IDENTIFIER ::= { ipiFrCapabilitiesBE01 2 }





END
