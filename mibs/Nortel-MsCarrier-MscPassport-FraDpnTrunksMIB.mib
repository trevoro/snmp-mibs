Nortel-MsCarrier-MscPassport-FraDpnTrunksMIB
DEFINITIONS ::= BEGIN



IMPORTS

      OBJECT-TYPE
   FROM RFC-1212

      mscPassportMIBs
   FROM Nortel-MsCarrier-MscPassport-UsefulDefinitionsMIB

      Counter32,
      RowPointer,
      DisplayString,
      StorageType,
      RowStatus,
      Gauge32,
      Unsigned32
   FROM Nortel-MsCarrier-MscPassport-StandardTextualConventionsMIB

      NonReplicated,
      Link
   FROM Nortel-MsCarrier-MscPassport-TextualConventionsMIB

      mscDpnGateIndex,
      mscDpnGate
   FROM Nortel-MsCarrier-MscPassport-DpnTrunksMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     FraDpnTrunks Enterprise MIB."

fraDpnTrunksMIB OBJECT IDENTIFIER ::= { mscPassportMIBs 68 }










-- DpnGate/n FrAccess
-- This component provides Layer 2 trunking protocol, to be used by 
-- DpnGateway running over FrMux frame relay interface.

mscDpnGateFrAccess OBJECT IDENTIFIER ::= { mscDpnGate 4 }



mscDpnGateFrAccessRowStatusTable OBJECT-TYPE
   SYNTAX     SEQUENCE OF MscDpnGateFrAccessRowStatusEntry
   ACCESS     not-accessible
   STATUS     mandatory
   DESCRIPTION
     "This entry controls the addition and deletion of 
      mscDpnGateFrAccess components."
::= { mscDpnGateFrAccess 1 }

mscDpnGateFrAccessRowStatusEntry OBJECT-TYPE
   SYNTAX     MscDpnGateFrAccessRowStatusEntry
   ACCESS     not-accessible
   STATUS     mandatory
   DESCRIPTION
     "A single entry in the table represents a single 
      mscDpnGateFrAccess component."
   INDEX {
      mscDpnGateIndex,
      mscDpnGateFrAccessIndex }
::= { mscDpnGateFrAccessRowStatusTable 1 }

MscDpnGateFrAccessRowStatusEntry ::= SEQUENCE {
   mscDpnGateFrAccessRowStatus
      RowStatus,
   mscDpnGateFrAccessComponentName
      DisplayString,
   mscDpnGateFrAccessStorageType
      StorageType,
   mscDpnGateFrAccessIndex
      NonReplicated }

mscDpnGateFrAccessRowStatus OBJECT-TYPE
   SYNTAX     RowStatus 
   ACCESS     read-write
   STATUS     mandatory
   DESCRIPTION
     "This variable is used as the basis for SNMP naming of
      mscDpnGateFrAccess components.
      These components can be added and deleted."
::= { mscDpnGateFrAccessRowStatusEntry 1 }

mscDpnGateFrAccessComponentName OBJECT-TYPE
   SYNTAX     DisplayString 
   ACCESS     read-only
   STATUS     mandatory
   DESCRIPTION
     "This variable provides the component's string name for
      use with the ASCII Console Interface"
::= { mscDpnGateFrAccessRowStatusEntry 2 }

mscDpnGateFrAccessStorageType OBJECT-TYPE
   SYNTAX     StorageType 
   ACCESS     read-only
   STATUS     mandatory
   DESCRIPTION
     "This variable represents the storage type value for the
      mscDpnGateFrAccess tables."
::= { mscDpnGateFrAccessRowStatusEntry 4 }

mscDpnGateFrAccessIndex OBJECT-TYPE
   SYNTAX     NonReplicated 
   ACCESS     not-accessible
   STATUS     mandatory
   DESCRIPTION
     "This variable represents the index for the mscDpnGateFrAccess tables."
::= { mscDpnGateFrAccessRowStatusEntry 10 }

mscDpnGateFrAccessProvTable OBJECT-TYPE
   SYNTAX     SEQUENCE OF MscDpnGateFrAccessProvEntry
   ACCESS     not-accessible
   STATUS     mandatory
   DESCRIPTION
     "This group of provisionable attributes contains the parameters used 
      by Unacknowledged, Utp, and FrAccess for monitoring link quality."
::= { mscDpnGateFrAccess 10 }

mscDpnGateFrAccessProvEntry OBJECT-TYPE
   SYNTAX     MscDpnGateFrAccessProvEntry
   ACCESS     not-accessible
   STATUS     mandatory
   DESCRIPTION
     "An entry in the mscDpnGateFrAccessProvTable."
   INDEX {
      mscDpnGateIndex,
      mscDpnGateFrAccessIndex }
::= { mscDpnGateFrAccessProvTable 1 }

MscDpnGateFrAccessProvEntry ::= SEQUENCE {
   mscDpnGateFrAccessMaximumErroredInterval
      Unsigned32,
   mscDpnGateFrAccessReceiveErrorSensitivity
      Unsigned32 }

mscDpnGateFrAccessMaximumErroredInterval OBJECT-TYPE
   SYNTAX     Unsigned32 (0 | 1..15)
   ACCESS     read-write
   STATUS     mandatory
   DESCRIPTION
     "This attribute specifies the interval time over which the error 
      threshold (as specified by receiveErrorSensitivity) must be 
      continuously exceeded before the Unacknowledged, Utp, or 
      FrAccess component can be degraded. Once the error interval count 
      exceeds the provisioned value, the Unacknowledged, Utp, or 
      FrAccess component issues an alarm indicating that link quality has 
      degraded, and it disables its parent component. The exception to 
      this is a value of zero, the default, which indicates that the 
      mechanism is completely disabled."
   DEFVAL     { 0 }
::= { mscDpnGateFrAccessProvEntry 1 }

mscDpnGateFrAccessReceiveErrorSensitivity OBJECT-TYPE
   SYNTAX     Unsigned32 (0 | 1..10)
   ACCESS     read-write
   STATUS     mandatory
   DESCRIPTION
     "This attribute is the allowable error rate beyond which the 
      Unacknowledged, Utp, or FrAccess component can be degraded if it 
      persists for a duration longer than the maximumErrorInterval. The 
      threshold is expressed as a percentage of number of errored frames 
      in the last interval per number of frames received in the last interval. 
      The exception to this is a value of zero, which indicates that the 
      mechanism is completely disabled. The configurable values are:
      0 = the mechanism is completely disabled
      1 = 1/(2**1)
      2 = 1/(2**2)
      3 = 1/(2**3)
      :
      10 = 1/(2**10)"
   DEFVAL     { 3 }
::= { mscDpnGateFrAccessProvEntry 2 }

mscDpnGateFrAccessStateTable OBJECT-TYPE
   SYNTAX     SEQUENCE OF MscDpnGateFrAccessStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscDpnGateFrAccess 11 }

mscDpnGateFrAccessStateEntry OBJECT-TYPE
   SYNTAX     MscDpnGateFrAccessStateEntry
   ACCESS     not-accessible
   STATUS     mandatory
   DESCRIPTION
     "An entry in the mscDpnGateFrAccessStateTable."
   INDEX {
      mscDpnGateIndex,
      mscDpnGateFrAccessIndex }
::= { mscDpnGateFrAccessStateTable 1 }

MscDpnGateFrAccessStateEntry ::= SEQUENCE {
   mscDpnGateFrAccessAdminState
      INTEGER,
   mscDpnGateFrAccessOperationalState
      INTEGER,
   mscDpnGateFrAccessUsageState
      INTEGER,
   mscDpnGateFrAccessAvailabilityStatus
      OCTET STRING,
   mscDpnGateFrAccessProceduralStatus
      OCTET STRING,
   mscDpnGateFrAccessControlStatus
      OCTET STRING,
   mscDpnGateFrAccessAlarmStatus
      OCTET STRING,
   mscDpnGateFrAccessStandbyStatus
      INTEGER,
   mscDpnGateFrAccessUnknownStatus
      INTEGER }

mscDpnGateFrAccessAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscDpnGateFrAccessStateEntry 1 }

mscDpnGateFrAccessOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscDpnGateFrAccessStateEntry 2 }

mscDpnGateFrAccessUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscDpnGateFrAccessStateEntry 3 }

mscDpnGateFrAccessAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscDpnGateFrAccessStateEntry 4 }

mscDpnGateFrAccessProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscDpnGateFrAccessStateEntry 5 }

mscDpnGateFrAccessControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscDpnGateFrAccessStateEntry 6 }

mscDpnGateFrAccessAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscDpnGateFrAccessStateEntry 7 }

mscDpnGateFrAccessStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscDpnGateFrAccessStateEntry 8 }

mscDpnGateFrAccessUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscDpnGateFrAccessStateEntry 9 }

mscDpnGateFrAccessOpTable OBJECT-TYPE
   SYNTAX     SEQUENCE OF MscDpnGateFrAccessOpEntry
   ACCESS     not-accessible
   STATUS     mandatory
   DESCRIPTION
     "This group of attributes contains the set of LTP operational 
      parameters measured and maintained by this component."
::= { mscDpnGateFrAccess 12 }

mscDpnGateFrAccessOpEntry OBJECT-TYPE
   SYNTAX     MscDpnGateFrAccessOpEntry
   ACCESS     not-accessible
   STATUS     mandatory
   DESCRIPTION
     "An entry in the mscDpnGateFrAccessOpTable."
   INDEX {
      mscDpnGateIndex,
      mscDpnGateFrAccessIndex }
::= { mscDpnGateFrAccessOpTable 1 }

MscDpnGateFrAccessOpEntry ::= SEQUENCE {
   mscDpnGateFrAccessRoundTripDelay
      Gauge32 }

mscDpnGateFrAccessRoundTripDelay OBJECT-TYPE
   SYNTAX     Gauge32 (0..1500)
   ACCESS     read-only
   STATUS     mandatory
   DESCRIPTION
     "This is the measured Round Trip Delay (ms) discovered with the 
      remote through the LTP staging protocol. The value includes 
      emission, propagation, and queuing delays. A 2 byte control frame 
      is used to perform the measurement. A value of zero is displayed 
      when the link is disabled or the measured Round Trip Delay is 
      unknown."
::= { mscDpnGateFrAccessOpEntry 1 }

mscDpnGateFrAccessStatsTable OBJECT-TYPE
   SYNTAX     SEQUENCE OF MscDpnGateFrAccessStatsEntry
   ACCESS     not-accessible
   STATUS     mandatory
   DESCRIPTION
     "This group contains the operational statistics for FrAccess."
::= { mscDpnGateFrAccess 13 }

mscDpnGateFrAccessStatsEntry OBJECT-TYPE
   SYNTAX     MscDpnGateFrAccessStatsEntry
   ACCESS     not-accessible
   STATUS     mandatory
   DESCRIPTION
     "An entry in the mscDpnGateFrAccessStatsTable."
   INDEX {
      mscDpnGateIndex,
      mscDpnGateFrAccessIndex }
::= { mscDpnGateFrAccessStatsTable 1 }

MscDpnGateFrAccessStatsEntry ::= SEQUENCE {
   mscDpnGateFrAccessReceivedBytesFromIf
      Counter32,
   mscDpnGateFrAccessLostFramesFromIf
      Counter32,
   mscDpnGateFrAccessDiscardBadFromIf
      Counter32,
   mscDpnGateFrAccessDiscardExcessToIf
      Counter32 }

mscDpnGateFrAccessReceivedBytesFromIf OBJECT-TYPE
   SYNTAX     Counter32 
   ACCESS     read-only
   STATUS     mandatory
   DESCRIPTION
     "This attribute counts the number of bytes received by FrAccess in 
      information frames. When the maximum count is reached the count 
      wraps to zero."
::= { mscDpnGateFrAccessStatsEntry 1 }

mscDpnGateFrAccessLostFramesFromIf OBJECT-TYPE
   SYNTAX     Counter32 
   ACCESS     read-only
   STATUS     mandatory
   DESCRIPTION
     "This attribute counts the frames lost in the direction from interface, 
      the loss of which is detected based on the sequence number 
      mechanism. The reason for a loss may be the congestion-related 
      loss in the external frame relay network, or errors/congestion 
      developing in the FrMux service. When FrMux statistics do not 
      show errors/congestion developing internally in FrMux, then the 
      losses visible through this statistic should be attributed to the 
      external frame relay network. When the maximum count is reached 
      the count wraps to zero."
::= { mscDpnGateFrAccessStatsEntry 2 }

mscDpnGateFrAccessDiscardBadFromIf OBJECT-TYPE
   SYNTAX     Counter32 
   ACCESS     read-only
   STATUS     mandatory
   DESCRIPTION
     "This attribute counts the number of frames discarded in the 
      direction 'from interface', because they are unknown to the 
      FrAccess protocol. When the maximum count is reached the count 
      wraps to zero."
::= { mscDpnGateFrAccessStatsEntry 3 }

mscDpnGateFrAccessDiscardExcessToIf OBJECT-TYPE
   SYNTAX     Counter32 
   ACCESS     read-only
   STATUS     mandatory
   DESCRIPTION
     "This attribute counts the number of frames discarded in the 
      direction 'to interface' because of congestion on the transmit queue. 
      When the maximum count is reached the count wraps to zero."
::= { mscDpnGateFrAccessStatsEntry 4 }


-- DpnGate/n FrAccess FrMuxSetup
-- This component contains operational and provisionable attributes 
-- for setting up a FrMux Dlci to act as a transport for DpnGate/n 
-- FrAccess. 

mscDpnGateFrAccessFrMuxSetup OBJECT IDENTIFIER ::= { mscDpnGateFrAccess 2 }



mscDpnGateFrAccessFrMuxSetupRowStatusTable OBJECT-TYPE
   SYNTAX     SEQUENCE OF MscDpnGateFrAccessFrMuxSetupRowStatusEntry
   ACCESS     not-accessible
   STATUS     mandatory
   DESCRIPTION
     "This entry controls the addition and deletion of 
      mscDpnGateFrAccessFrMuxSetup components."
::= { mscDpnGateFrAccessFrMuxSetup 1 }

mscDpnGateFrAccessFrMuxSetupRowStatusEntry OBJECT-TYPE
   SYNTAX     MscDpnGateFrAccessFrMuxSetupRowStatusEntry
   ACCESS     not-accessible
   STATUS     mandatory
   DESCRIPTION
     "A single entry in the table represents a single 
      mscDpnGateFrAccessFrMuxSetup component."
   INDEX {
      mscDpnGateIndex,
      mscDpnGateFrAccessIndex,
      mscDpnGateFrAccessFrMuxSetupIndex }
::= { mscDpnGateFrAccessFrMuxSetupRowStatusTable 1 }

MscDpnGateFrAccessFrMuxSetupRowStatusEntry ::= SEQUENCE {
   mscDpnGateFrAccessFrMuxSetupRowStatus
      RowStatus,
   mscDpnGateFrAccessFrMuxSetupComponentName
      DisplayString,
   mscDpnGateFrAccessFrMuxSetupStorageType
      StorageType,
   mscDpnGateFrAccessFrMuxSetupIndex
      NonReplicated }

mscDpnGateFrAccessFrMuxSetupRowStatus OBJECT-TYPE
   SYNTAX     RowStatus 
   ACCESS     read-only
   STATUS     mandatory
   DESCRIPTION
     "This variable is used as the basis for SNMP naming of
      mscDpnGateFrAccessFrMuxSetup components.
      These components cannot be added nor deleted."
::= { mscDpnGateFrAccessFrMuxSetupRowStatusEntry 1 }

mscDpnGateFrAccessFrMuxSetupComponentName OBJECT-TYPE
   SYNTAX     DisplayString 
   ACCESS     read-only
   STATUS     mandatory
   DESCRIPTION
     "This variable provides the component's string name for
      use with the ASCII Console Interface"
::= { mscDpnGateFrAccessFrMuxSetupRowStatusEntry 2 }

mscDpnGateFrAccessFrMuxSetupStorageType OBJECT-TYPE
   SYNTAX     StorageType 
   ACCESS     read-only
   STATUS     mandatory
   DESCRIPTION
     "This variable represents the storage type value for the
      mscDpnGateFrAccessFrMuxSetup tables."
::= { mscDpnGateFrAccessFrMuxSetupRowStatusEntry 4 }

mscDpnGateFrAccessFrMuxSetupIndex OBJECT-TYPE
   SYNTAX     NonReplicated 
   ACCESS     not-accessible
   STATUS     mandatory
   DESCRIPTION
     "This variable represents the index for the mscDpnGateFrAccessFrMuxSetup tables."
::= { mscDpnGateFrAccessFrMuxSetupRowStatusEntry 10 }

mscDpnGateFrAccessFrMuxSetupTrafficDescrTable OBJECT-TYPE
   SYNTAX     SEQUENCE OF MscDpnGateFrAccessFrMuxSetupTrafficDescrEntry
   ACCESS     not-accessible
   STATUS     mandatory
   DESCRIPTION
     "This group contains the provisionable attributes for the application 
      of which this FrMuxSetup is a subcomponent. The parameters are 
      used for maximum frame size checking and traffic shaping and are 
      to be passed over to FrMux Dlci associated with the application. 
      The attributes in this group are defined in T1.606 Addendum 1."
::= { mscDpnGateFrAccessFrMuxSetup 10 }

mscDpnGateFrAccessFrMuxSetupTrafficDescrEntry OBJECT-TYPE
   SYNTAX     MscDpnGateFrAccessFrMuxSetupTrafficDescrEntry
   ACCESS     not-accessible
   STATUS     mandatory
   DESCRIPTION
     "An entry in the mscDpnGateFrAccessFrMuxSetupTrafficDescrTable."
   INDEX {
      mscDpnGateIndex,
      mscDpnGateFrAccessIndex,
      mscDpnGateFrAccessFrMuxSetupIndex }
::= { mscDpnGateFrAccessFrMuxSetupTrafficDescrTable 1 }

MscDpnGateFrAccessFrMuxSetupTrafficDescrEntry ::= SEQUENCE {
   mscDpnGateFrAccessFrMuxSetupCommittedInformationRate
      Unsigned32,
   mscDpnGateFrAccessFrMuxSetupCommittedBurstSize
      Unsigned32,
   mscDpnGateFrAccessFrMuxSetupMaximumFrameSize
      Unsigned32 }

mscDpnGateFrAccessFrMuxSetupCommittedInformationRate OBJECT-TYPE
   SYNTAX     Unsigned32 (4800..2048000)
   ACCESS     read-write
   STATUS     mandatory
   DESCRIPTION
     "This attribute specifies, in bit/s, the committed information rate 
      (CIR) to which the traffic transmitted towards the interface is 
      shaped. The minimum value is 4800 bit/s."
   DEFVAL     { 64000 }
::= { mscDpnGateFrAccessFrMuxSetupTrafficDescrEntry 1 }

mscDpnGateFrAccessFrMuxSetupCommittedBurstSize OBJECT-TYPE
   SYNTAX     Unsigned32 (0..2048000)
   ACCESS     read-write
   STATUS     obsolete
   DESCRIPTION
     "THIS ATTRIBUTE IS NOT BEING USED."
   DEFVAL     { 64000 }
::= { mscDpnGateFrAccessFrMuxSetupTrafficDescrEntry 2 }

mscDpnGateFrAccessFrMuxSetupMaximumFrameSize OBJECT-TYPE
   SYNTAX     Unsigned32 (1..4096)
   ACCESS     read-write
   STATUS     mandatory
   DESCRIPTION
     "This attribute specifies the maximum number of octets which may 
      be included in the information field. The frame relay header and 
      CRC octets are not included in this definition. This attribute 
      corresponds to the dN1 parameter described in the Vendor Forum 
      Specification."
   DEFVAL     { 4096 }
::= { mscDpnGateFrAccessFrMuxSetupTrafficDescrEntry 3 }

mscDpnGateFrAccessFrMuxSetupDlciCompNameOpTable OBJECT-TYPE
   SYNTAX     SEQUENCE OF MscDpnGateFrAccessFrMuxSetupDlciCompNameOpEntry
   ACCESS     not-accessible
   STATUS     mandatory
   DESCRIPTION
     "This group contains the component name of the Dlci which carries 
      the traffic for this application."
::= { mscDpnGateFrAccessFrMuxSetup 11 }

mscDpnGateFrAccessFrMuxSetupDlciCompNameOpEntry OBJECT-TYPE
   SYNTAX     MscDpnGateFrAccessFrMuxSetupDlciCompNameOpEntry
   ACCESS     not-accessible
   STATUS     mandatory
   DESCRIPTION
     "An entry in the mscDpnGateFrAccessFrMuxSetupDlciCompNameOpTable."
   INDEX {
      mscDpnGateIndex,
      mscDpnGateFrAccessIndex,
      mscDpnGateFrAccessFrMuxSetupIndex }
::= { mscDpnGateFrAccessFrMuxSetupDlciCompNameOpTable 1 }

MscDpnGateFrAccessFrMuxSetupDlciCompNameOpEntry ::= SEQUENCE {
   mscDpnGateFrAccessFrMuxSetupDlciCompName
      RowPointer }

mscDpnGateFrAccessFrMuxSetupDlciCompName OBJECT-TYPE
   SYNTAX     RowPointer 
   ACCESS     read-only
   STATUS     mandatory
   DESCRIPTION
     "This attribute specifies the component name of the Dlci with which 
      the application using this FrMuxSetup component is associated. The 
      name is a string FrMux/n Dlci/m. For a PVC this is the same 
      component name as provisioned under the subcomponent 
      FrMuxPvcSetup."
::= { mscDpnGateFrAccessFrMuxSetupDlciCompNameOpEntry 1 }


-- DpnGate/n FrAccess FrMuxSetup PvcSetup
-- This component contains provisionable attributes for setting up a 
-- Dlci associated with the application using this component. The Dlci 
-- is of a PVC type. 

mscDpnGateFrAccessFrMuxSetupPvcSetup OBJECT IDENTIFIER ::= { mscDpnGateFrAccessFrMuxSetup 2 }



mscDpnGateFrAccessFrMuxSetupPvcSetupRowStatusTable OBJECT-TYPE
   SYNTAX     SEQUENCE OF MscDpnGateFrAccessFrMuxSetupPvcSetupRowStatusEntry
   ACCESS     not-accessible
   STATUS     mandatory
   DESCRIPTION
     "This entry controls the addition and deletion of 
      mscDpnGateFrAccessFrMuxSetupPvcSetup components."
::= { mscDpnGateFrAccessFrMuxSetupPvcSetup 1 }

mscDpnGateFrAccessFrMuxSetupPvcSetupRowStatusEntry OBJECT-TYPE
   SYNTAX     MscDpnGateFrAccessFrMuxSetupPvcSetupRowStatusEntry
   ACCESS     not-accessible
   STATUS     mandatory
   DESCRIPTION
     "A single entry in the table represents a single 
      mscDpnGateFrAccessFrMuxSetupPvcSetup component."
   INDEX {
      mscDpnGateIndex,
      mscDpnGateFrAccessIndex,
      mscDpnGateFrAccessFrMuxSetupIndex,
      mscDpnGateFrAccessFrMuxSetupPvcSetupIndex }
::= { mscDpnGateFrAccessFrMuxSetupPvcSetupRowStatusTable 1 }

MscDpnGateFrAccessFrMuxSetupPvcSetupRowStatusEntry ::= SEQUENCE {
   mscDpnGateFrAccessFrMuxSetupPvcSetupRowStatus
      RowStatus,
   mscDpnGateFrAccessFrMuxSetupPvcSetupComponentName
      DisplayString,
   mscDpnGateFrAccessFrMuxSetupPvcSetupStorageType
      StorageType,
   mscDpnGateFrAccessFrMuxSetupPvcSetupIndex
      NonReplicated }

mscDpnGateFrAccessFrMuxSetupPvcSetupRowStatus OBJECT-TYPE
   SYNTAX     RowStatus 
   ACCESS     read-only
   STATUS     mandatory
   DESCRIPTION
     "This variable is used as the basis for SNMP naming of
      mscDpnGateFrAccessFrMuxSetupPvcSetup components.
      These components cannot be added nor deleted."
::= { mscDpnGateFrAccessFrMuxSetupPvcSetupRowStatusEntry 1 }

mscDpnGateFrAccessFrMuxSetupPvcSetupComponentName OBJECT-TYPE
   SYNTAX     DisplayString 
   ACCESS     read-only
   STATUS     mandatory
   DESCRIPTION
     "This variable provides the component's string name for
      use with the ASCII Console Interface"
::= { mscDpnGateFrAccessFrMuxSetupPvcSetupRowStatusEntry 2 }

mscDpnGateFrAccessFrMuxSetupPvcSetupStorageType OBJECT-TYPE
   SYNTAX     StorageType 
   ACCESS     read-only
   STATUS     mandatory
   DESCRIPTION
     "This variable represents the storage type value for the
      mscDpnGateFrAccessFrMuxSetupPvcSetup tables."
::= { mscDpnGateFrAccessFrMuxSetupPvcSetupRowStatusEntry 4 }

mscDpnGateFrAccessFrMuxSetupPvcSetupIndex OBJECT-TYPE
   SYNTAX     NonReplicated 
   ACCESS     not-accessible
   STATUS     mandatory
   DESCRIPTION
     "This variable represents the index for the mscDpnGateFrAccessFrMuxSetupPvcSetup tables."
::= { mscDpnGateFrAccessFrMuxSetupPvcSetupRowStatusEntry 10 }

mscDpnGateFrAccessFrMuxSetupPvcSetupProvTable OBJECT-TYPE
   SYNTAX     SEQUENCE OF MscDpnGateFrAccessFrMuxSetupPvcSetupProvEntry
   ACCESS     not-accessible
   STATUS     mandatory
   DESCRIPTION
     "This group contains provisionable attributes for setting up a Dlci 
      associated with the application using the FrMuxSetup component. 
      The Dlci is of the PVC type."
::= { mscDpnGateFrAccessFrMuxSetupPvcSetup 10 }

mscDpnGateFrAccessFrMuxSetupPvcSetupProvEntry OBJECT-TYPE
   SYNTAX     MscDpnGateFrAccessFrMuxSetupPvcSetupProvEntry
   ACCESS     not-accessible
   STATUS     mandatory
   DESCRIPTION
     "An entry in the mscDpnGateFrAccessFrMuxSetupPvcSetupProvTable."
   INDEX {
      mscDpnGateIndex,
      mscDpnGateFrAccessIndex,
      mscDpnGateFrAccessFrMuxSetupIndex,
      mscDpnGateFrAccessFrMuxSetupPvcSetupIndex }
::= { mscDpnGateFrAccessFrMuxSetupPvcSetupProvTable 1 }

MscDpnGateFrAccessFrMuxSetupPvcSetupProvEntry ::= SEQUENCE {
   mscDpnGateFrAccessFrMuxSetupPvcSetupDlciName
      Link }

mscDpnGateFrAccessFrMuxSetupPvcSetupDlciName OBJECT-TYPE
   SYNTAX     Link 
   ACCESS     read-write
   STATUS     mandatory
   DESCRIPTION
     "This attribute is the link to the Dlci which is associated with the 
      application using the FrMuxSetup component."
::= { mscDpnGateFrAccessFrMuxSetupPvcSetupProvEntry 1 }




-- 
-- Version and Compliance statements
-- 



-- Object-Group Statement:
-- A list of all current accessible leaf objects.

-- OBJECTS { mscDpnGateFrAccessFrMuxSetupPvcSetupDlciName,
--           mscDpnGateFrAccessOperationalState,
--           mscDpnGateFrAccessStorageType,
--           mscDpnGateFrAccessFrMuxSetupPvcSetupStorageType,
--           mscDpnGateFrAccessReceiveErrorSensitivity,
--           mscDpnGateFrAccessFrMuxSetupMaximumFrameSize,
--           mscDpnGateFrAccessFrMuxSetupPvcSetupComponentName,
--           mscDpnGateFrAccessMaximumErroredInterval,
--           mscDpnGateFrAccessFrMuxSetupCommittedInformationRate,
--           mscDpnGateFrAccessControlStatus,
--           mscDpnGateFrAccessAdminState,
--           mscDpnGateFrAccessFrMuxSetupDlciCompName,
--           mscDpnGateFrAccessFrMuxSetupRowStatus,
--           mscDpnGateFrAccessDiscardExcessToIf,
--           mscDpnGateFrAccessRowStatus,
--           mscDpnGateFrAccessProceduralStatus,
--           mscDpnGateFrAccessFrMuxSetupStorageType,
--           mscDpnGateFrAccessAvailabilityStatus,
--           mscDpnGateFrAccessDiscardBadFromIf,
--           mscDpnGateFrAccessStandbyStatus,
--           mscDpnGateFrAccessLostFramesFromIf,
--           mscDpnGateFrAccessReceivedBytesFromIf,
--           mscDpnGateFrAccessUsageState,
--           mscDpnGateFrAccessComponentName,
--           mscDpnGateFrAccessFrMuxSetupPvcSetupRowStatus,
--           mscDpnGateFrAccessFrMuxSetupComponentName,
--           mscDpnGateFrAccessUnknownStatus,
--           mscDpnGateFrAccessRoundTripDelay,
--           mscDpnGateFrAccessAlarmStatus }
-- STATUS  mandatory
-- DESCRIPTION
--   "A list of all current accessible leaf objects."

fraDpnTrunksGroup OBJECT IDENTIFIER ::= { fraDpnTrunksMIB 1 }
fraDpnTrunksGroupCA OBJECT IDENTIFIER ::= { fraDpnTrunksGroup 1 }
fraDpnTrunksGroupCA02 OBJECT IDENTIFIER ::= { fraDpnTrunksGroupCA 3 }
fraDpnTrunksGroupCA02A OBJECT IDENTIFIER ::= { fraDpnTrunksGroupCA02 2 }



-- Agent-Capabilities Statement:

-- PRODUCT-RELEASE "MscPassport Release 1.2 FraDpnTrunks."
-- STATUS          mandatory
-- DESCRIPTION     "Carrier Passport FraDpnTrunks MIB: MIB Version CA02A,
--                  Software Version CA02S9C."
-- SUPPORTS        Nortel-MsCarrier-MscPassport-FraDpnTrunksMIB
--    INCLUDES     { fraDpnTrunksGroupCA02A }

fraDpnTrunksCapabilities OBJECT IDENTIFIER ::= { fraDpnTrunksMIB 3 }
fraDpnTrunksCapabilitiesCA OBJECT IDENTIFIER ::= { fraDpnTrunksCapabilities 1 }
fraDpnTrunksCapabilitiesCA02 OBJECT IDENTIFIER ::= { fraDpnTrunksCapabilitiesCA 3 }
fraDpnTrunksCapabilitiesCA02A OBJECT IDENTIFIER ::= { fraDpnTrunksCapabilitiesCA02 2 }





END
