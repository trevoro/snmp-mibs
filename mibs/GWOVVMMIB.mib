GWOVVMMIB DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

wpcorp          OBJECT IDENTIFIER   ::= { enterprises 922 }
gateways        OBJECT IDENTIFIER   ::= { wpcorp        2 }
ngwovvm         OBJECT IDENTIFIER   ::= { gateways      2 }
ngwovvmInfo     OBJECT IDENTIFIER   ::= { ngwovvm       1 }
ngwovvmTrapInfo OBJECT IDENTIFIER   ::= { ngwovvm       2 }


-- ====================================== NGWOVVM Get/Set Variables =========
ngwovvmGatewayName OBJECT-TYPE
       SYNTAX  DisplayString (SIZE (0..255))
       ACCESS  read-only
       STATUS  mandatory
       DESCRIPTION
       "The GroupWise OVVM Gateway name."
   ::= { ngwovvmInfo 1 }
 
ngwovvmUptime OBJECT-TYPE
       SYNTAX  TimeTicks
       ACCESS  read-only
       STATUS  mandatory
       DESCRIPTION
      "Uptime of the GroupWise OVVM Gateway."
   ::= { ngwovvmInfo 2 }

ngwovvmGroupWiseLink OBJECT-TYPE
       SYNTAX  DisplayString (SIZE (0..5))
       ACCESS  read-only
       STATUS  mandatory
       DESCRIPTION
      "GroupWise OVVM Gateway Link: UP or DOWN"
   ::= { ngwovvmInfo 3 }

ngwovvmFrgnLink OBJECT-TYPE
       SYNTAX  DisplayString (SIZE (0..5))
       ACCESS  read-only
       STATUS  mandatory
       DESCRIPTION
      "GroupWise OVVM Gateway Foreign Link: UP or DOWN"
   ::= { ngwovvmInfo 4 }

ngwovvmOutBytes OBJECT-TYPE
       SYNTAX  Counter
       ACCESS  read-only
       STATUS  mandatory
       DESCRIPTION
      "The number of message bytes sent to GroupWise OVVM."
   ::= { ngwovvmInfo 5 }
 
ngwovvmInBytes OBJECT-TYPE
       SYNTAX  Counter
       ACCESS  read-only
       STATUS  mandatory
       DESCRIPTION
      "The number of message bytes received from GroupWise OVVM."
   ::= { ngwovvmInfo 6 }
 
ngwovvmOutMsgs OBJECT-TYPE
       SYNTAX  Counter
       ACCESS  read-only
       STATUS  mandatory
       DESCRIPTION
      "The number of messages sent to GroupWise OVVM."
   ::= { ngwovvmInfo 7 }
 
ngwovvmInMsgs OBJECT-TYPE
       SYNTAX  Counter
       ACCESS  read-only
       STATUS  mandatory
       DESCRIPTION
      "The number of messages received from OVVM."
   ::= { ngwovvmInfo 8 }
 
ngwovvmOutStatuses OBJECT-TYPE
       SYNTAX  Counter
       ACCESS  read-only
       STATUS  mandatory
       DESCRIPTION
      "The number of statuses sent to OVVM."
   ::= { ngwovvmInfo 9 }
 
ngwovvmInStatuses OBJECT-TYPE
       SYNTAX  Counter
       ACCESS  read-only
       STATUS  mandatory
       DESCRIPTION
      "The number of statuses received from OVVM."
   ::= { ngwovvmInfo 10 }
 
ngwovvmOutErrors OBJECT-TYPE
       SYNTAX  Counter
       ACCESS  read-only
       STATUS  mandatory
       DESCRIPTION
      "The number of failed transfers to OVVM."
   ::= { ngwovvmInfo 11 }
 
ngwovvmInErrors OBJECT-TYPE
       SYNTAX  Counter
       ACCESS  read-only
       STATUS  mandatory
       DESCRIPTION
      "The number of failed transfers from OVVM."
   ::= { ngwovvmInfo 12 }

-- ================================================== ngwovvmTrapInfo ========
-- The ngwovvmTrapInfo group
-- These objects are used only in traps produced by NGWOVVM
 
ngwovvmTrapTime OBJECT-TYPE
		SYNTAX  INTEGER
		ACCESS  not-accessible
		STATUS  mandatory
		DESCRIPTION "The time the trap occurred. Seconds since Jan 1, 1970 (GMT)"
	::= { ngwovvmTrapInfo 1 }

-- ================================================== NGWOVVM Traps =========
ngwovvmStartTrap TRAP-TYPE
		ENTERPRISE    ngwovvmInfo
		VARIABLES     {ngwovvmTrapTime, ngwovvmGatewayName}
		DESCRIPTION   "GroupWise OVVM Gateway start."
		--NMS Trap annotation
		--#TYPE       "GroupWise OVVM Gateway start."
		--#SUMMARY    "GroupWise OVVM Gateway %s has started."
		--#ARGUMENTS  {1}
		--#SEVERITY   INFORMATIONAL
		--#TIMEINDEX  0
		--#HELP       "NGWALARM.HLP"
		--#HELPTAG    101		
		--#STATE      OPERATIONAL
		::= 1

ngwovvmStopTrap TRAP-TYPE
		ENTERPRISE    ngwovvmInfo
		VARIABLES     {ngwovvmTrapTime, ngwovvmGatewayName}
		DESCRIPTION   "GroupWise OVVM Gateway stop."
		--NMS Trap annotation
		--#TYPE       "GroupWise OVVM Gateway stop."
		--#SUMMARY    "GroupWise OVVM Gateway %s has stopped."
		--#ARGUMENTS  {1}
		--#SEVERITY   CRITICAL
		--#TIMEINDEX  0
		--#HELP       "NGWALARM.HLP"
		--#HELPTAG    102		
		--#STATE      NONOPERATIONAL
		::= 2

ngwovvmRestartTrap TRAP-TYPE
		ENTERPRISE    ngwovvmInfo
		VARIABLES     {ngwovvmTrapTime, ngwovvmGatewayName}
		DESCRIPTION   "GroupWise OVVM Gateway restart."
		--NMS Trap annotation
		--#TYPE       "GroupWise OVVM Gateway restart."
		--#SUMMARY    "GroupWise OVVM Gateway %s has been restarted."
		--#ARGUMENTS  {1}
		--#SEVERITY   INFORMATIONAL
		--#TIMEINDEX  0
		--#HELP       "NGWALARM.HLP"
		--#HELPTAG    503		
		--#STATE      OPERATIONAL
		::= 3
 
ngwovvmGroupWiseLinkTrap TRAP-TYPE
		ENTERPRISE    ngwovvmInfo
		VARIABLES     {ngwovvmTrapTime, ngwovvmGatewayName}
		DESCRIPTION   "GroupWise Link lost by GroupWise OVVM Gateway"
		--NMS Trap annotation
		--#TYPE       "GroupWise Link lost by GroupWise OVVM Gateway"
		--#SUMMARY    "GroupWise OVVM Gateway %s has lost its GroupWise Link"
		--#ARGUMENTS  {1}
		--#SEVERITY   INFORMATIONAL
		--#TIMEINDEX  0
		--#HELP       "NGWALARM.HLP"
		--#HELPTAG    504		
		--#STATE      OPERATIONAL
		::= 4

ngwovvmFgnLinkTrap TRAP-TYPE
		ENTERPRISE    ngwovvmInfo
		VARIABLES     {ngwovvmTrapTime, ngwovvmGatewayName}
		DESCRIPTION   "OVVM Link lost by GroupWise OVVM Gateway"
		--NMS Trap annotation
		--#TYPE       "OVVM Link lost by GroupWise OVVM Gateway"
		--#SUMMARY    "GroupWise OVVM Gateway %s has lost its OVVM Link"
		--#ARGUMENTS  {1}
		--#SEVERITY   INFORMATIONAL
		--#TIMEINDEX  0
		--#HELP       "NGWALARM.HLP"
		--#HELPTAG    505		
		--#STATE      OPERATIONAL
		::= 5


END
