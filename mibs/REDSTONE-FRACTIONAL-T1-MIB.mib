-- *****************************************************************
-- REDSTONE-FRACTIONAL-T1-MIB
--
-- Redstone Communications Inc. Enterprise MIB
-- Fractional T1 MIB
--
-- Copyright 1998-1999 Redstone Communications, Incorporated.
-- All Rights Reserved.
-- *****************************************************************

REDSTONE-FRACTIONAL-T1-MIB DEFINITIONS ::= BEGIN

IMPORTS
	MODULE-IDENTITY,
	OBJECT-TYPE,
	Integer32
		FROM SNMPv2-SMI
	OBJECT-GROUP, MODULE-COMPLIANCE FROM SNMPv2-CONF

	RowStatus
		FROM SNMPv2-TC

    InterfaceIndex, InterfaceIndexOrZero
        FROM IF-MIB

	rsMgmt
		FROM REDSTONE-SMI

    RsNextIfIndex, RsTimeSlotMap
        FROM REDSTONE-TC;


rsFt1MIB  MODULE-IDENTITY
	LAST-UPDATED "9907140000Z"
	ORGANIZATION "Redstone Communications, Inc."
	CONTACT-INFO
        "
        Redstone Communications, Inc.
		5 Carlisle Road
        Westford MA 01886
        USA
        Tel:    +1-978-692-1999
		Email:  mib@redstonecom.com
        "
	DESCRIPTION
		"The Fractional T1 MIB for the 
		Redstone Communications Inc. enterprise."
	REVISION      "9907140000Z"
	DESCRIPTION
		"Obsoleted rsFt1IfDataPolarity and updated 
        corresponding compliances."
	REVISION      "9801010000Z"
	DESCRIPTION
		"Initial version of this MIB module."
	::= { rsMgmt 6 }

-- ++++++++++++++++++++++++++++++++++++++++++++++++++++++++++++++++++++++
-- Textual conventions
-- ++++++++++++++++++++++++++++++++++++++++++++++++++++++++++++++++++++++

-- No textual conventions are defined in this MIB



-- ++++++++++++++++++++++++++++++++++++++++++++++++++++++++++++++++++++++
-- Managed objects
-- ++++++++++++++++++++++++++++++++++++++++++++++++++++++++++++++++++++++

rsFt1Objects     OBJECT IDENTIFIER ::= { rsFt1MIB 1 }

-- 
-- This MIB contains managed objects for Fractional T1 arrangements.
-- Management objects are provided to query for an available
-- interface index, and to create/delete interfaces of this type.
-- Creating/deleting this interface type using this MIB has
-- the side effect of creating/deleting corresponding entries
-- in the Interface MIB ifTable/ifXTable, and in the Redstone
-- Enterprise Interface MIB rsIfTable.
--



-- //////////////////////////////////////////////////////////////////////
--
-- Fractional T1 Interfaces
--
-- //////////////////////////////////////////////////////////////////////

--
-- IfIndex selection for creating new FT1 interfaces
--

rsFt1NextIfIndex OBJECT-TYPE
    SYNTAX      RsNextIfIndex
    MAX-ACCESS  read-only
    STATUS      current
    DESCRIPTION
        "Coordinate ifIndex value allocation for entries
        in rsFt1IfTable.

        A GET of this object returns the next available ifIndex 
        value to be used to create an entry in the associated
        interface table; or zero, if no valid ifIndex value is
        available. This object also returns a value of zero when 
        it is the lexicographic successor of a varbind presented 
        in an SNMP GETNEXT or GETBULK request, for which circumstance
        it is assumed that ifIndex allocation is unintended.

        Successive GETs will typically return different
        values, thus avoiding collisions among cooperating
        management clients seeking to create table entries
        simultaneously.
        "
    ::= { rsFt1Objects 1 }

--
-- The FT1 Interface Table
--

rsFt1IfTable OBJECT-TYPE
    SYNTAX      SEQUENCE OF RsFt1IfEntry
    MAX-ACCESS  not-accessible
    STATUS      current
    DESCRIPTION
        "This table contains entries for FT1 interfaces present in the system."
    ::= { rsFt1Objects 2 }

rsFt1IfEntry OBJECT-TYPE
    SYNTAX      RsFt1IfEntry
    MAX-ACCESS  not-accessible
    STATUS      current
    DESCRIPTION
        "Each entry describes the characteristics of an FT1 interface. 
        Creating/deleting entries in this table causes corresponding 
        entries for be created /deleted in ifTable/ifXTable/rsIfTable."
    INDEX   { rsFt1IfIndex }
    ::= { rsFt1IfTable 1 }

RsFt1IfEntry ::= SEQUENCE {
    rsFt1IfIndex
        InterfaceIndex,
    rsFt1IfRowStatus
        RowStatus,
    rsFt1IfLowerIfIndex
        InterfaceIndexOrZero,
    rsFt1IfTimeSlotMap
        RsTimeSlotMap,
    rsFt1IfTimeSlotRate
        INTEGER,
    rsFt1IfDataPolarity
        INTEGER,
    rsFt1IfLoopbackConfig
        INTEGER
    }


rsFt1IfIndex OBJECT-TYPE
    SYNTAX      InterfaceIndex
    MAX-ACCESS  not-accessible
    STATUS      current
    DESCRIPTION
        "The ifIndex of the FT1 interface. When 
        creating entries in this table, suitable values
        for this object are determined by reading
        rsFt1NextIfIndex."
    ::= { rsFt1IfEntry 1 }

rsFt1IfRowStatus OBJECT-TYPE
    SYNTAX      RowStatus
    MAX-ACCESS  read-create
    STATUS      current
    DESCRIPTION
        "Controls creation/deletion of entries in this table
        according to the RowStatus textual convention, 
        constrained to support the following values only:

            createAndGo
            destroy
            
        To create an entry in this table, the following 
        entry objects MUST be explicitly configured:

            rsFt1IfRowStatus
            rsFt1IfLowerIfIndex
            rsFt1IfTimeSlotMap

        In addition, when creating an entry the following
        conditions must hold:

            A value for rsFt1IfIndex must have been determined
            previously, by reading rsFt1NextIfIndex. 

            The DS1 interface identified by rsFt1IfLowerIfIndex
            must exist.

            The DS0s specified in rsFt1IfTimeSlotMap must be 
            available (unallocated) on the DS1 interface
            identified by rsFt1IfLowerIfIndex.

        A corresponding entry in ifTable/ifXTable/rsIfTable is 
        created/destroyed as a result of creating/destroying an entry 
        in this table.
        "
    ::= { rsFt1IfEntry 2 }

rsFt1IfLowerIfIndex OBJECT-TYPE
    SYNTAX      InterfaceIndexOrZero
    MAX-ACCESS  read-create
    STATUS      current
    DESCRIPTION
        "The ifIndex of a DS1 interface over which this FT1 interface 
        is to be layered. A value of zero indicates no layering.
        An implementation may choose to require that a nonzero value
        be configured at entry creation."
    ::= { rsFt1IfEntry 3 }

rsFt1IfTimeSlotMap OBJECT-TYPE
    SYNTAX      RsTimeSlotMap
    MAX-ACCESS  read-create
    STATUS      current
    DESCRIPTION
        "A bitmap representing the DS0s on the underlying DS1 interface
        that have been allocated to this FT1 interface."
    ::= { rsFt1IfEntry 4 }

rsFt1IfTimeSlotRate OBJECT-TYPE
    SYNTAX      INTEGER {
                    nx56kbps(0),
                    nx64kbps(1)
                }
    MAX-ACCESS  read-create
    STATUS      current
    DESCRIPTION
        "Data rate per time slot allocated to this FT1 interface."
    DEFVAL  { nx64kbps }
    ::= { rsFt1IfEntry 5 }

rsFt1IfDataPolarity OBJECT-TYPE
    SYNTAX      INTEGER {
                    normal(0),
                    inverted(1)
                }
    MAX-ACCESS  read-create
    STATUS      obsolete
    DESCRIPTION
        "Polarity of data transmitted on this FT1 interface. Inverted data is
        used for certain line coding configurations to ensure sufficient
        one's density for timing recovery by the remote end."
    DEFVAL  { normal }
    ::= { rsFt1IfEntry 6 }

rsFt1IfLoopbackConfig OBJECT-TYPE
    SYNTAX      INTEGER {
                    noLoop(0),
                    loop(1)
                }
    MAX-ACCESS  read-create
    STATUS      current
    DESCRIPTION
        "Selects loopback configuration. loop(1) causes received data to be 
        looped back out the transmitter."
    DEFVAL  { noLoop }
    ::= { rsFt1IfEntry 7 }


-- ++++++++++++++++++++++++++++++++++++++++++++++++++++++++++++++++++++++
-- Notification control objects
-- ++++++++++++++++++++++++++++++++++++++++++++++++++++++++++++++++++++++

-- No notifications are defined in this MIB. Placeholder follows.

-- rsFt1TrapControl      OBJECT IDENTIFIER ::= { rsFt1MIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- rsFt1Traps            OBJECT IDENTIFIER ::= { rsFt1MIB 3 }
-- rsFt1TrapPrefix       OBJECT IDENTIFIER ::= { rsFt1Traps 0 }



-- ++++++++++++++++++++++++++++++++++++++++++++++++++++++++++++++++++++++
-- Conformance information
-- ++++++++++++++++++++++++++++++++++++++++++++++++++++++++++++++++++++++

rsFt1Conformance OBJECT IDENTIFIER ::= { rsFt1MIB 4 }
rsFt1Compliances OBJECT IDENTIFIER ::= { rsFt1Conformance 1 }
rsFt1Groups      OBJECT IDENTIFIER ::= { rsFt1Conformance 2 }

-- compliance statements

rsFt1Compliance MODULE-COMPLIANCE
        STATUS  obsolete
        DESCRIPTION
                "The compliance statement for entities which implement
                the Redstone FT1 MIB."
        MODULE  -- this module
                MANDATORY-GROUPS { rsFt1Group }
        ::= { rsFt1Compliances 1 }

rsFt1Compliance2 MODULE-COMPLIANCE
        STATUS  current
        DESCRIPTION
                "The compliance statement for entities which implement
                the Redstone FT1 MIB."
        MODULE  -- this module
                MANDATORY-GROUPS { rsFt1Group2 }
        ::= { rsFt1Compliances 2 }

-- units of conformance

rsFt1Group OBJECT-GROUP
        OBJECTS {
		rsFt1NextIfIndex,

		rsFt1IfRowStatus,
		rsFt1IfLowerIfIndex,
        rsFt1IfTimeSlotMap,
        rsFt1IfTimeSlotRate,
        rsFt1IfDataPolarity,
        rsFt1IfLoopbackConfig
	}
	STATUS  obsolete
	DESCRIPTION
		"A collection of objects providing management of FT1 interfaces
		in a Redstone product."
    ::= { rsFt1Groups 1 }

rsFt1Group2 OBJECT-GROUP
        OBJECTS {
		rsFt1NextIfIndex,

		rsFt1IfRowStatus,
		rsFt1IfLowerIfIndex,
        rsFt1IfTimeSlotMap,
        rsFt1IfTimeSlotRate,
        rsFt1IfLoopbackConfig
	}
	STATUS  current
	DESCRIPTION
		"A collection of objects providing management of FT1 interfaces
		in a Redstone product."
    ::= { rsFt1Groups 2 }

END
