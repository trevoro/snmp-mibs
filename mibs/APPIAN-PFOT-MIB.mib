--
--  Title:  Appian Pluggable Fiber Optic Transceiver MIB
--
--  Dated:  9/15/00
--  Author: D. Theriault
--
--  Description:
--
--  This MIB file contains the definitions and support for the Appian
--  Optical Services Access Platform(s).
--
--  The Pfot MIB is a single table supporting information regarding the
--  use of Pluggable Fiber Optic Transceiver technology in the OSAP
--  products.  This table supports use of both GBIC and SFP transceivers.
--
APPIAN-PFOT-MIB DEFINITIONS ::= BEGIN

    IMPORTS

        acPport, AcSlotNumber, AcPortNumber, 
        AcNodeId                                        FROM APPIAN-SMI-MIB

        acChassisCurrentTime, acChassisRingId           FROM APPIAN-CHASSIS-MIB

        MODULE-IDENTITY, OBJECT-TYPE,
        NOTIFICATION-TYPE                               FROM SNMPv2-SMI

        TEXTUAL-CONVENTION, DisplayString               FROM SNMPv2-TC;
        

acPfot  MODULE-IDENTITY

    LAST-UPDATED    "0002231600Z"
    ORGANIZATION    "Appian Communications, Inc."
    CONTACT-INFO    "Douglas Theriault"

    DESCRIPTION     "Appian Communications Pluggable Fiber Optic Transceiver MIB 
                    which contains the configuration attributes for use of pluggable
                    fiber optic transceiver technology in the OSAP product."

    REVISION        "0002231600Z"

    DESCRIPTION     "Draft revision, Engineering use only."

    ::= { acPport 7 }

    --
    --  Common Textual Conventions for Pluggable Fiber Optic Transceivers
    --
    AcPfotType ::= TEXTUAL-CONVENTION
    STATUS  current
    DESCRIPTION
    "The type of transceiver in use on a port expressed as an integer 
    enumeration. This name includes an indication of the technology
    supported (Gigabit, Sonet etc), and reach (short, intermediate,
    or long). "
    SYNTAX  INTEGER {
                not-present(0),
		sfp-gbe-sx(1), 
		sfp-gbe-lx-sr(2), 
		sfp-gbe-lx-ir(3), 
		sfp-gbe-lx-lr(4) 
            }
    
-- 
-- Pluggable Fiber Optic Transceiver MIB
-- 
acPfotTable    OBJECT-TYPE
    SYNTAX          SEQUENCE OF AcPfotEntry
    MAX-ACCESS      not-accessible
    STATUS          current
    DESCRIPTION
    "A table containing the configuration parameters for pluggable fiber
    optic transceiver in use on a port.  The index keys used in this table 
    (node-id.slot.port) are mapped to ifIndex under the 
    appian(2785).interfaces(4).ifTable(1) group.  The configuration table 
    will be automatically created by the module driver, regardless of if 
    a transceiver exists on the port or not."

    ::= { acPfot 1 }
    
acPfotEntry        OBJECT-TYPE
    SYNTAX          AcPfotEntry
    MAX-ACCESS      not-accessible
    STATUS          current
    DESCRIPTION
    "A row which contains the configuration parameters for an physical port
    equipped with pluggable fiber optic transceiver technology.  These rows 
    are automatically instantiated by default."

    INDEX   { acPfotNodeId, acPfotSlot, acPfotPort }

    ::= { acPfotTable 1 }

    AcPfotEntry ::=
        SEQUENCE {
            acPfotNodeId                    AcNodeId,
            acPfotSlot                      AcSlotNumber,
            acPfotPort                      AcPortNumber,
            acPfotCfgType                   AcPfotType,
            acPfotType                      AcPfotType,
            acPfotConnectorType             INTEGER,
            acPfotVendorName                DisplayString,
            acPfotVendorPartNumber          DisplayString
        }


acPfotNodeId  OBJECT-TYPE
    SYNTAX  AcNodeId
    MAX-ACCESS  accessible-for-notify
    STATUS  current
    DESCRIPTION
    "The node id is the id for this specific node in the OSAP ring."

    ::= { acPfotEntry 1 }

acPfotSlot  OBJECT-TYPE
    SYNTAX  AcSlotNumber
    MAX-ACCESS  accessible-for-notify
    STATUS      current
    DESCRIPTION
    "The slot number within the chassis where this module entry resides."
        
    ::= { acPfotEntry 2 }

acPfotPort  OBJECT-TYPE
    SYNTAX  AcPortNumber
    MAX-ACCESS  accessible-for-notify
    STATUS      current
    DESCRIPTION
    "The port number on the module which is equipped with a pluggable fiber
    optic transceiver."

    ::= { acPfotEntry 3 }

acPfotCfgType    OBJECT-TYPE
    SYNTAX  AcPfotType
    MAX-ACCESS  read-create
    STATUS      current
    DESCRIPTION
    "The desired configured type of transceiver to be used on this port. 
    By default, set to not-present."

    DEFVAL { not-present }

    ::= { acPfotEntry 4 }
                                
acPfotType    OBJECT-TYPE
    SYNTAX  AcPfotType
    MAX-ACCESS  read-only
    STATUS      current
    DESCRIPTION
    "The current transceiver type detected on this port."

    ::= { acPfotEntry 5 }

acPfotConnectorType   OBJECT-TYPE
    SYNTAX  INTEGER {
                none(0),
		sc(1),
		lc(2),
		mtrj(3)
	    }

    MAX-ACCESS  read-only
    STATUS      current
    DESCRIPTION
    "The current type of connector detected on the tranceiver installed in 
    this port."

    ::= { acPfotEntry 6 }

acPfotVendorName  OBJECT-TYPE
    SYNTAX  DisplayString (SIZE(0..64))
    MAX-ACCESS  read-only
    STATUS      current
    DESCRIPTION
    "A string represetning the name of the Vendor that manufactured the 
    transceiver installed in this port."

    ::= { acPfotEntry 7 }

acPfotVendorPartNumber   OBJECT-TYPE
    SYNTAX  DisplayString (SIZE(0..64))
    MAX-ACCESS  read-only
    STATUS      current
    DESCRIPTION
    "A string representing the vendor part number used to identify the
    transceiver installed in this port."

    ::= { acPfotEntry 8 }

-- 
-- Pfot Trap Definitions
--
--

acPfotTraps   OBJECT IDENTIFIER ::= { acPfot 0 }

acPfotCfgErrorTrap  NOTIFICATION-TYPE 
    OBJECTS { acChassisCurrentTime, acChassisRingId, acPfotNodeId, 
              acPfotSlot, acPfotPort, acPfotCfgType, acPfotType } 
    STATUS  current
    DESCRIPTION
    "The transeiver type for a port is different than the type configured for use."
    
    ::= { acPfotTraps 1 }
    
--
-- End Appian Pfot MIB
--

END
