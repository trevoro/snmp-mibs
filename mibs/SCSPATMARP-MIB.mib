-- extracted from draft-ietf-ion-scsp-atmarp-mib-00.txt
-- at Mon Nov 15 17:11:08 1999

   SCSPATMARP-MIB DEFINITIONS ::= BEGIN

   IMPORTS
       MODULE-IDENTITY, OBJECT-TYPE, NOTIFICATION-TYPE,
       experimental, Integer32, IpAddress, Counter32
          FROM SNMPv2-SMI
       TEXTUAL-CONVENTION, RowStatus
          FROM SNMPv2-TC
       MODULE-COMPLIANCE, OBJECT-GROUP
          FROM SNMPv2-CONF
       AtmAddr, AtmConnKind
          FROM ATM-TC-MIB

       scspServerGroupID, scspServerGroupPID, scspLSID, scspDCSID,
       ScspHFSMStateType, SCSPVPIInteger,SCSPVCIInteger
          FROM SCSP-MIB
       ;



   scspAtmarpMIB MODULE-IDENTITY
       LAST-UPDATED "9808020000Z" -- October 10, 1998
       ORGANIZATION "IETF Internetworking Over NBMA Working Group (ion)"
       CONTACT-INFO
         "Jim Luciani (jliciani@BayNetworks.com
          Bay Networks

          Cliff X. Wang (cliff_wang@vnet.ibm.com)
          Colin Verrilli (verrilli@vnet.ibm.com)
          IBM Corp."

       DESCRIPTION
          "This module defines a portion of the management
           information base (MIB) for managing Server Cache
           Synchronizatio protocol applied to ATMARP servers."
       ::= { experimental 2002 }



    -- *****************************************************
    --   Top Level structure of the SCSP MIB
    -- *****************************************************

   scspAtmarpObjects        OBJECT IDENTIFIER ::= { scspAtmarpMIB 1}
   scspAtmarpNotifications  OBJECT IDENTIFIER ::= { scspAtmarpMIB 2}
   scspAtmarpConformance    OBJECT IDENTIFIER ::= { scspAtmarpMIB 3}


    -- *****************************************************
    --   SCSP MIB Objects
    -- *****************************************************


    -- *****************************************************
    --   SCSP atmarp Server Group Objects
    -- *****************************************************

   scspAtmarpServerGroupTable OBJECT-TYPE
       SYNTAX   SEQUENCE OF ScspAtmarpServerGroupEntry
       MAX-ACCESS  not-accessible
       STATUS   current
       DESCRIPTION
           "The objects defined in this table are used to for the
            management of SCSP server groups with application to
            IP over ATM operation (Classic IP). These objects SHOULD
            be used along with the protocol independent part objects
            to support the management of the SCSP protocol applied
            to synchronizing the atmarp servers in a LIS.

            There is one entry in this table for each server group.
            In the case of IP over ATM, each server group corresponds to
            a Logical IP Subnet."
       ::= { scspAtmarpObjects 1}


   scspAtmarpServerGroupEntry OBJECT-TYPE
       SYNTAX   ScspAtmarpServerGroupEntry
       MAX-ACCESS  not-accessible
       STATUS   current
       DESCRIPTION
           "Information about SCSP server group running IP over ATM
            operation. This table is indexed by scspServerGroupID and
            scspServerGroupPID. The two indeces point to a corresponding
            entry in the scspServerGroupTable."
       INDEX {scspServerGroupID, scspServerGroupPID}
       ::= { scspAtmarpServerGroupTable 1}


   ScspAtmarpServerGroupEntry ::=
       SEQUENCE {
         scspAtmarpServerGroupNetMask                  IpAddress,
         scspAtmarpServerGroupSubnetAddr               IpAddress,
         scspAtmarpServerGroupRowStatus                RowStatus }


   scspAtmarpServerGroupNetMask  OBJECT-TYPE
       SYNTAX   IpAddress
       MAX-ACCESS  read-only
       STATUS   current
       DESCRIPTION
          "The subnet mask associated with this Server Group."
       ::= { scspAtmarpServerGroupEntry 1 }


   scspAtmarpServerGroupSubnetAddr  OBJECT-TYPE
       SYNTAX   IpAddress
       MAX-ACCESS  read-only
       STATUS   current
       DESCRIPTION
          "The IP subnet address associated with this Server Group."
       ::= { scspAtmarpServerGroupEntry 2 }


   scspAtmarpServerGroupRowStatus   OBJECT-TYPE
       SYNTAX   RowStatus
       MAX-ACCESS  read-create
       STATUS   current
       DESCRIPTION
          "This object allows Atmarp Server Group Table entries to be
           created and deleted from the scspAtmarpServerGroupTable. Note
           that scspAtmarpServerGroupTable entry creation and deletion
           is coupled with scspServerGroupTable entry creation and
           deletion. A scspAtmarpServerGroupTable entry cannot be
           created until its corresponding  scspServerGroupTable entry
           is created. When a scspServerGroupTable entry is deleted,
           it also removes the corresponding scspAtmarpServerGroupTable
           entry."
       REFERENCE
           "RFC 1903, 'Textual Conventions for version 2 of the Simple
            Network Management Protocol (SNMPv2).'"
       ::= { scspAtmarpServerGroupEntry 3 }



    -- ****************************************************
    --   SCSP atmarp Local Server Objects
    -- ****************************************************

   scspAtmarpLSTable OBJECT-TYPE
       SYNTAX   SEQUENCE OF ScspAtmarpLSEntry
       MAX-ACCESS  not-accessible
       STATUS   current
       DESCRIPTION
           "The objects defined in this table are used to for the
            management of the Atmarp Local server in a SCSP server group
            for IP over ATM operation. These objects SHOULD
            be used along with the protocol independent part objects
            to support the management of the SCSP protocol applied
            to synchronizing the IP over ATM servers."
       ::= { scspAtmarpObjects 2}


   scspAtmarpLSEntry OBJECT-TYPE
       SYNTAX   ScspAtmarpLSEntry
       MAX-ACCESS  not-accessible
       STATUS   current
       DESCRIPTION
          "Information about Atmarp Local Server in a SCSP server
           group. This table is indexed by scspServerGroupID,
           scspServerGroupPID, and scspLSID. The three indeces point
           to a corresponding entry in the scspLSTable."
       INDEX {scspServerGroupID,
              scspServerGroupPID,
              scspLSID
             }
       ::= { scspAtmarpLSTable 1}


   ScspAtmarpLSEntry ::=
       SEQUENCE {
           scspAtmarpLSLSIPAddr                 IpAddress,
           scspAtmarpLSLSAtmAddr                AtmAddr,
           scspAtmarpLSRowStatus                RowStatus
       }



   scspAtmarpLSLSIPAddr  OBJECT-TYPE
       SYNTAX   IpAddress
       MAX-ACCESS  read-only
       STATUS   current
       DESCRIPTION
           "The IP address of the Atmarp Local Server. Since an Atmarp
            server does not have to be assigned an IP address, this
            object is optional."
       ::= { scspAtmarpLSEntry 1 }


   scspAtmarpLSLSAtmAddr OBJECT-TYPE
       SYNTAX   AtmAddr
       MAX-ACCESS  read-only
       STATUS   current
       DESCRIPTION
           "The ATM address of the Atmarp Local Server."
       ::= { scspAtmarpLSEntry 2 }


   scspAtmarpLSRowStatus   OBJECT-TYPE
       SYNTAX   RowStatus
       MAX-ACCESS  read-create
       STATUS   current
       DESCRIPTION
          "This object allows Atmarp Local Server Table entries to be
           created and deleted from the scspAtmarpLSTable. Note
           that scspAtmarpLSTable entry creation and deletion
           is coupled with scspLSTable entry creation and deletion.
           A scspAtmarpLSTable entry cannot be created until
           its corresponding scspLSTable entry is created.
           When a scspLSTable entry is deleted, it also removes
           the corresponding scspAtmarpLSTable entry."
       ::= { scspAtmarpLSEntry 3 }


    -- ***************************************************
    --     SCSP Atmarp Peer Objects
    -- ***************************************************

   scspAtmarpPeerTable OBJECT-TYPE
       SYNTAX   SEQUENCE OF ScspAtmarpPeerEntry
       MAX-ACCESS  not-accessible
       STATUS   current
       DESCRIPTION
           "The objects defined in this table are used to for the
            management of the ATMARP sever peers."
       ::= { scspAtmarpObjects 3}


   scspAtmarpPeerEntry OBJECT-TYPE
       SYNTAX   ScspAtmarpPeerEntry
       MAX-ACCESS  not-accessible
       STATUS   current
       DESCRIPTION
           "Information about each peer ATMARP server participated
            in the scsp Server group. The table is indexed by
            scspServerGroupID, scspServerGroupPID, and
            scspAtmarpPeerIndex."
       INDEX { scspServerGroupID,
               scspServerGroupPID,
               scspAtmarpPeerIndex
             }
       ::= { scspAtmarpPeerTable 1}


   ScspAtmarpPeerEntry ::=
       SEQUENCE {
           scspAtmarpPeerIndex               Integer32,
           scspAtmarpPeerIPAddr              IpAddress,
           scspAtmarpPeerAtmAddr             AtmAddr,
           scspAtmarpPeerVCType              AtmConnKind,
           scspAtmarpPeerVPI                 SCSPVPIInteger,
           scspAtmarpPeerVCI                 SCSPVCIInteger,
           scspAtmarpPeerDCSID               OCTET STRING(SIZE(0..63)),
           scspAtmarpPeerRowStatus           RowStatus

       }



   scspAtmarpPeerIndex  OBJECT-TYPE
       SYNTAX   Integer32
       MAX-ACCESS  read-only
       STATUS   current
       DESCRIPTION
            "The table index of the peer Atmarp server table."
       ::= { scspAtmarpPeerEntry 1 }



   scspAtmarpPeerIPAddr  OBJECT-TYPE
       SYNTAX   IpAddress
       MAX-ACCESS  read-only
       STATUS   current
       DESCRIPTION
            "The IP address of the peer Atmarp server. Since an Atmarp
             server does not have to be assigned an IP address,
             this object is optional."
       ::= { scspAtmarpPeerEntry 2 }


   scspAtmarpPeerAtmAddr OBJECT-TYPE
       SYNTAX   AtmAddr
       MAX-ACCESS  read-only
       STATUS   current
       DESCRIPTION
           "The ATM address of the Peer. If SVC is used between LS and
            Peer, Peer's ATM address should be valid. However, if PVC is
            used instead SVC, the Peer's ATM address may be a Null OCTET
            STRING."
       ::= { scspAtmarpPeerEntry 3 }



   scspAtmarpPeerVCType OBJECT-TYPE
       SYNTAX   AtmConnKind
       MAX-ACCESS  read-only
       STATUS   current
       DESCRIPTION
           "The type of the virtual circuit between LS and Peer."
       ::= { scspAtmarpPeerEntry 4 }


   scspAtmarpPeerVPI OBJECT-TYPE
       SYNTAX   SCSPVPIInteger
       MAX-ACCESS  read-only
       STATUS   current
       DESCRIPTION
            "The VPI value for the virtual circuit between LS and Peer."
       ::= { scspAtmarpPeerEntry 5 }


   scspAtmarpPeerVCI OBJECT-TYPE
       SYNTAX   SCSPVCIInteger
       MAX-ACCESS  read-only
       STATUS   current
       DESCRIPTION
           "The VCI value for the virtual circuit between LS and Peer."
       ::= { scspAtmarpPeerEntry 6 }


   scspAtmarpPeerDCSID OBJECT-TYPE
       SYNTAX   OCTET STRING(SIZE(0..63))
       MAX-ACCESS  read-only
       STATUS   current
       DESCRIPTION
           "The DCS ID for this peer. When the peer tabel is created,
            DCS ID may not have been discovered. Tt is set to a
            Null string. It will be update when the DCS ID
            associated with this peer (ATM address) is discovered."
       ::= { scspAtmarpPeerEntry 7 }



   scspAtmarpPeerRowStatus   OBJECT-TYPE
       SYNTAX   RowStatus
       MAX-ACCESS  read-create
       STATUS   current
       DESCRIPTION
           "This object allows Atmarp Peer table entries to be created
            and deleted from the scspAtmarpPeerTable. Note that
            scspAtmarpPeerTable entry is created when a peer is
            configured loaclly or when a peer not previously
            configured connects to LS."
       REFERENCE
           "RFC 1903, 'Textual Conventions for version 2 of the Simple
            Network Management Protocol (SNMPv2).'"
       ::= { scspAtmarpPeerEntry 8 }

    -- ****************************************************
    --     SCSP atmarp HFSM Objects
    -- ****************************************************


   scspAtmarpHFSMTable OBJECT-TYPE
       SYNTAX   SEQUENCE OF ScspAtmarpHFSMEntry
       MAX-ACCESS  not-accessible
       STATUS   current
       DESCRIPTION
            "The objects defined in this table are used to for the
             management of the HFSM  between the LS and the DCS."
       ::= { scspAtmarpObjects 4}


   scspAtmarpHFSMEntry OBJECT-TYPE
       SYNTAX   ScspAtmarpHFSMEntry
       MAX-ACCESS  not-accessible
       STATUS   current
       DESCRIPTION
            "Information about SCSP HFSM session between the LS and
             its HFSMs. The table is indexed by
             scspServerGroupID, scspServerGroupPID, and
             scspAtmarpPeerIndex."
       INDEX { scspServerGroupID,
               scspServerGroupPID,
               scspAtmarpPeerIndex
             }
       ::= { scspAtmarpHFSMTable 1}


   ScspAtmarpHFSMEntry ::=
       SEQUENCE {
            scspHFSMHFSMState                ScspHFSMStateType,
            scspHFSMHelloIn                   Counter32,
            scspHFSMHelloOut                 Counter32,
            scspHFSMHelloInvalidIn           Counter32,
            scspHFSMHelloInterval            Integer32,
            scspHFSMDeadFactor               Integer32,
            scspHFSMFamilyID                 Integer32,
            scspAtmarpHFSMRowStatus          RowStatus
       }


   scspHFSMHFSMState  OBJECT-TYPE
       SYNTAX   ScspHFSMStateType
       MAX-ACCESS  read-only
       STATUS   current
       DESCRIPTION
            "The current state of the Hello Finite State Machine.
             The allowable states are:
                 down(1),
                 waiting(2),
                 uniConn(3),
                 biConn(4)."
       REFERENCE
            "SCSP draft, Section 2.1"
       ::= { scspAtmarpHFSMEntry 1 }


   scspHFSMHelloIn  OBJECT-TYPE
       SYNTAX   Counter32
       MAX-ACCESS  read-only
       STATUS   current
       DESCRIPTION
            "The number of 'Hello' messages received from this HFSM."
       ::= { scspAtmarpHFSMEntry 2 }


   scspHFSMHelloOut  OBJECT-TYPE
       SYNTAX   Counter32
       MAX-ACCESS  read-only
       STATUS   current
       DESCRIPTION
            "The number of 'Hello' messages sent from LS to this
             HFSM."
       ::= { scspAtmarpHFSMEntry 3 }

   scspHFSMHelloInvalidIn  OBJECT-TYPE
       SYNTAX   Counter32
       MAX-ACCESS  read-only
       STATUS   current
       DESCRIPTION
             "The number of invalid 'Hello' messages received from
              this HFSM. Possible message errors include:
              Hello message when the HFSM is in 'Down' state;
              Hello message is too short to contain the number of
              Receiver ID records specified in the header, etc.
              Other common errors include failed authentication if
              applicable, errors in the message fields, etc."
       ::= { scspAtmarpHFSMEntry 4 }


   scspHFSMHelloInterval  OBJECT-TYPE
       SYNTAX   Integer32 (0..65535)
       MAX-ACCESS  read-create
       STATUS   current
       DESCRIPTION
             "This object contains the value for HelloInterval with
              the associated HFSM. It is the time (in seconds)
              between sending of consecutive Hello messages from the
              HFSM."
       ::= { scspAtmarpHFSMEntry 5 }


   scspHFSMDeadFactor  OBJECT-TYPE
       SYNTAX   Integer32 (0..65535)
       MAX-ACCESS  read-create
       STATUS   current
       DESCRIPTION
            "This object contains the value for DeadFactor with
             this associated server. The DeadFactor along with
             HelloInterval are contained in 'Hello' messages sent
             from this HFSM. If 'Hello' messages are not received
             from this HFSM within the time out interval
             'HelloInterval*DeadFactor' (in seconds),
             then the HFSM MUST be considered  to be stalled."
       ::= { scspAtmarpHFSMEntry 6 }


   scspHFSMFamilyID  OBJECT-TYPE
       SYNTAX   Integer32 (0..65535)
       MAX-ACCESS  read-only
       STATUS   current
       DESCRIPTION
            "The family ID is used to refer an aggregate of
             Protocol ID/SGID pairs. Only a single HFSM is
             run for all Protocol ID/SGID pairs assigned to
             a Family ID. When the HFSM is not shared by an
             aggregate of Protocol ID/SGID pairs, this
             object should be set to 0."
       REFERENCE
            "SCSP draft, Sec.2 and Sec. B.2.5"
       ::= { scspAtmarpHFSMEntry 7 }


   scspAtmarpHFSMRowStatus   OBJECT-TYPE
       SYNTAX   RowStatus
       MAX-ACCESS  read-create
       STATUS   current
       DESCRIPTION
           "This object allows Atmarp HFSM table entries to be created
            and deleted from the scspAtmarpHFSMTable. Note that
            scspAtmarpHFSMTable entry creation and deletion is
            closely coupled with scspHFSMTable entry creation.
            A scspAtmarpHFSMTable entry cannot be created until
            its corresponding scspHFSMTable entry is created.
            When a scspHFSMTable entry is deleted, it also removes
            the corresponding scspAtmarpHFSMTable entry."
       REFERENCE
           "RFC 1903, 'Textual Conventions for version 2 of the Simple
            Network Management Protocol (SNMPv2).'"
       ::= { scspAtmarpHFSMEntry 8 }


    -- ***********************************************************
    --       Notifications
    -- ***********************************************************

   scspHFSMDown NOTIFICATION-TYPE
       OBJECTS {
                scspServerGroupID,
                scspServerGroupPID,
                scspAtmarpPeerIndex
               }
       STATUS  current
       DESCRIPTION
            "The Hello Finite State Machine associated with this
             LS/DCS pair enters 'Down' state."
       ::= { scspAtmarpNotifications 1 }

   scspHFSMWaiting NOTIFICATION-TYPE
       OBJECTS {
                scspServerGroupID,
                scspServerGroupPID,
                scspAtmarpPeerIndex
         }
       STATUS  current
       DESCRIPTION
             "The Hello Finite State Machine associated with
              this LS/DCS pair enters 'Waiting' state."
       ::= { scspAtmarpNotifications 2 }


   scspHFSMBiConn NOTIFICATION-TYPE
       OBJECTS {
                  scspServerGroupID,
                  scspServerGroupPID,
                  scspAtmarpPeerIndex
       }
       STATUS  current
       DESCRIPTION
             "The Hello Finite State Machine associated with this
              LS/DCS pair enters 'Bidirectional connection' state."
       ::= { scspAtmarpNotifications 3 }


    -- *********************************************************
    -- Conformance Definitions
    -- *********************************************************

   scspAtmarpCompliances OBJECT IDENTIFIER ::={scspAtmarpConformance 1}
   scspAtmarpGroups      OBJECT IDENTIFIER ::={scspAtmarpConformance 2}


    --**********************************************************
    --  SCSP MIB Compliance Statements
    --**********************************************************


   scspAtmarpCompliance MODULE-COMPLIANCE
       STATUS  current
       DESCRIPTION
           "The compliance statement for entities that are required
            for the management of SCSP when applied to ATMARP servers."
       MODULE
            MANDATORY-GROUPS {
               scspAtmarpGroup
              }
       ::= { scspAtmarpCompliances 1 }



   scspAtmarpGroup OBJECT-GROUP
       OBJECTS {
            scspAtmarpServerGroupNetMask,
            scspAtmarpServerGroupSubnetAddr,
            scspAtmarpLSLSIPAddr,
            scspAtmarpLSLSAtmAddr,
            scspAtmarpPeerIndex,
            scspAtmarpPeerAtmAddr,
            scspAtmarpPeerVCType,
            scspAtmarpPeerVPI,
            scspAtmarpPeerVCI,
            scspAtmarpPeerDCSID,
            scspHFSMHFSMState,
            scspHFSMHelloIn,
            scspHFSMHelloOut,
            scspHFSMHelloInvalidIn,
            scspHFSMHelloInterval,
            scspHFSMDeadFactor,
            scspHFSMFamilyID
        }
       STATUS   current
       DESCRIPTION
            "This group is mandatory when Atmarp is the client/server
             protocol running SCSP."
       ::= { scspAtmarpGroups 1 }

   END
