ChrComProtectionVpNextPeerSetVp-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComProtectionVp			FROM  Chromatis-MIB;

-- chrComProtectionVpNextPeerSetVp Table

chrComProtectionVpNextPeerSetVpTable		OBJECT-TYPE
	SYNTAX		SEQUENCE OF ChrComProtectionVpNextPeerSetVpEntry
	MAX-ACCESS	not-accessible
	STATUS		current
	DESCRIPTION
	""
	::= { chrComProtectionVp 3}

chrComProtectionVpNextPeerSetVpEntry		OBJECT-TYPE
	SYNTAX		ChrComProtectionVpNextPeerSetVpEntry
	MAX-ACCESS	not-accessible
	STATUS		current
	DESCRIPTION
	""
	INDEX  {  chrComProtectionVpNextVPPeerSetID }

--DEFAULT  get-function-async  MNIL_GetRoutine
--DEFAULT  set-function-async  MNIL_SetRoutine
--DEFAULT  next-function-async MNIL_NextRoutine
--DEFAULT  test-function-async MNIL_TestRoutine
--DEFAULT  cookie "nextPeerSetVp"
	::= { chrComProtectionVpNextPeerSetVpTable  1 }

ChrComProtectionVpNextPeerSetVpEntry  ::=
	SEQUENCE  {
	chrComProtectionVpNextVPPeerSetID		Unsigned32	(0..4294967295)
}

chrComProtectionVpNextVPPeerSetID 	OBJECT-TYPE
	SYNTAX		Unsigned32	(0..4294967295)
	MAX-ACCESS 	read-only
	STATUS 		current
	DESCRIPTION
	"The next vacant PeerSet ID in the VP Protection PeerSet Table
This field enables the NMS to create new VP protection PeerSet
"
	::= { chrComProtectionVpNextPeerSetVpEntry  1 }


END
