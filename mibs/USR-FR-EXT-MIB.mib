USR-FR-EXT-MIB DEFINITIONS ::= BEGIN
     IMPORTS
             DisplayString, UsrConfigStatus, common          FROM USR-DEFINITIONS-MIB
             MODULE-IDENTITY, NOTIFICATION-TYPE,
             Integer32, Counter32, OBJECT-TYPE                  FROM SNMPv2-SMI
             DisplayString, RowStatus, TimeStamp, TruthValue    FROM SNMPv2-TC;
     --  Frame Relay DTE MIB Extensions
     --
     --      the range of ifIndex
     --
     Index ::= Integer32       -- 1..ifNumber
     --
     --      the range of a Data Link Connection Identifier
     --
     DLCI ::= INTEGER(16..1023)        -- 0..DLCINumber
     --
     --  The Frame Relay Base Group.
     --
    usrFRExt MODULE-IDENTITY
         LAST-UPDATED "200205141520Z"
         ORGANIZATION "CommWorks Corporation, a 3Com company"
         CONTACT-INFO "Customer Support"
         DESCRIPTION
                 "The CommWorks Frame Relay DTE MIB Extensions"
--       REVISION "200205141520Z"
--       DESCRIPTION "Add structured trap comments"
         ::= { common 64 }
     usrfrExtBaseCfgFileName OBJECT-TYPE
         SYNTAX      DisplayString
         MAX-ACCESS  read-only
         STATUS  current
         DESCRIPTION
                 "The name of a Frame Relay ConfigFile to read/write
                 permanent database records. If the value of this
                 object is an empty string, then the FR process
                 uses the default name '@file://FrFile.cfg'."
         ::= { usrFRExt 1 }
     usrfrExtBaseCFMSaveStatus OBJECT-TYPE
         SYNTAX  UsrConfigStatus
         MAX-ACCESS  read-write
         STATUS  current
         DESCRIPTION
                 "Setting the value of this object to 'save'
                 causes the values of the FR Base Group
                 entries to be written out to the current FR
                 configuration file. While the new configuration file 
                 is being written, the FR process will set the value
                 of this flag set to 'saving'. Any attempts to set
                 the value while it is not 'normal' (i.e. the file
                 is currently being written to the config file)
                 will result in a badValue error being returned.
                 Setting the value to 'normal' will result in no
                 action."
         ::= { usrFRExt 2 }
     --
     --  Frame Relay Conformance Options
     --
     usrfrExtBaseConformanceOption OBJECT-TYPE
         SYNTAX INTEGER {
                 sprint  (1),
                 idacom  (2)
         }
         MAX-ACCESS  read-write
         STATUS  current
         DESCRIPTION
                 "This variable indicates the Conformance Option
                 of the Frame Relay Datalink."
         DEFVAL { 2 }
         --CONFIGURABLE
         ::= { usrFRExt 3 }
     --
     --  Data Link Connection Management Interface Extensions
     --
     --  The variables that configure the DLC Management Interface.
     --
     usrfrExtDlcmiTable OBJECT-TYPE
         SYNTAX   SEQUENCE OF UsrFrExtDlcmiEntry
         MAX-ACCESS   not-accessible
         STATUS   current
         DESCRIPTION
            "The Parameters for the Data Link Connection Management
            Interface for the frame relay service on this
            interface."
         REFERENCE
            "Draft American National Standard T1.617-1991, Annex D"
         ::= { usrFRExt 4 }
         usrfrExtDlcmiEntry OBJECT-TYPE
             SYNTAX   UsrFrExtDlcmiEntry
             MAX-ACCESS   not-accessible
             STATUS   current
             DESCRIPTION
                "The Parameters for a particular Data Link Connection
                 Management Interface."
            INDEX { usrfrExtDlcmiIfIndex }
            ::= { usrfrExtDlcmiTable 1 }
         UsrFrExtDlcmiEntry ::=
             SEQUENCE {
                 usrfrExtDlcmiIfIndex
                     Index,
                 usrfrExtDlcmiOperStatus
                     INTEGER,
                 usrfrExtDlcmiMaximumTransferUnit
                     INTEGER,
                 usrfrExtDlcmiAccessRate
                     INTEGER,
                 usrfrExtDlcmiNewPVCLearning
                     INTEGER,
                 usrfrExtDlcmiTrace
                     INTEGER
         }
         usrfrExtDlcmiIfIndex OBJECT-TYPE
             SYNTAX  Index
             MAX-ACCESS  read-only
             STATUS  current
             DESCRIPTION
                 "The ifIndex value of the  corresponding  ifEntry."
             ::= { usrfrExtDlcmiEntry 1 }
         usrfrExtDlcmiOperStatus OBJECT-TYPE
             SYNTAX  INTEGER {
                 ready         (1),
                 waitForDriver (2),
                 recovery      (3),
                 down          (4),
                 disabled      (5)
             }
             MAX-ACCESS  read-only
             STATUS  current
             DESCRIPTION
                 "This variable indicates the operational status of 
                 the Frame Relay link. The Status is determined by a 
                 success or failure of the LMI message exchange with
                 the Frame Relay switch, the WAN Interface state and 
                 Administrator Link State."
             ::= { usrfrExtDlcmiEntry 2 }
         usrfrExtDlcmiMaximumTransferUnit OBJECT-TYPE
             SYNTAX  INTEGER (260..2048)
             MAX-ACCESS  read-write
             STATUS  current
             DESCRIPTION
                 "This is the largest number of bytes the Frame Relay
                 DLL Layer will attempt to transmit through its 
                 physical interface in a single frame."
             DEFVAL { 1600 }
             --CONFIGURABLE
             ::= { usrfrExtDlcmiEntry 3 }
         usrfrExtDlcmiAccessRate OBJECT-TYPE
             SYNTAX  INTEGER (0..8192000)
             MAX-ACCESS  read-write
             STATUS  current
             DESCRIPTION
                 "This is the speed of access channel, a Frame Relay
                 DLL Layer will use for data transfer. This value is
                 expressed in bits per second.
                 If value 0 is selected, then the Access Rate value used
                 by Frame Relay to its calculations will be taken from
                 physical WAN driver."
             REFERENCE
                 "CCITT Recommendation I.370, Section 1.2 access rate"
             DEFVAL { 1544000 }
             --CONFIGURABLE
             ::= { usrfrExtDlcmiEntry 4 }
         usrfrExtDlcmiNewPVCLearning OBJECT-TYPE
             SYNTAX  INTEGER {
                 on  (1),
                 off (2)
             }
             MAX-ACCESS  read-write
             STATUS  current
             DESCRIPTION
                 "This indicates if the Frame Relay interface 
                 can dynamically create a new PVC based on
                 information received in LMI Full Status message."
             DEFVAL { 2 }
             --CONFIGURABLE
             ::= { usrfrExtDlcmiEntry 5 }
         usrfrExtDlcmiTrace OBJECT-TYPE
             SYNTAX  INTEGER {
                 on  (1),
                 off (2)
             }
             MAX-ACCESS  read-write
             STATUS  current
             DESCRIPTION
                 "This indicates if the LMI Protocol frames trace 
                 information will be displayed on the console."
             DEFVAL { 2 }
             --CONFIGURABLE
             ::= { usrfrExtDlcmiEntry 6 }
     -- A Frame Relay service is a multiplexing service.  Data
     -- Link Connection Identifiers enumerate virtual circuits
     -- (permanent or switched) which are layered onto the underlying
     -- interface, represented by ifEntry.  Therefore, each of the entries
     -- in the Standard MIB's Interface Table with an IfType of
     -- Frame Relay represents a Q.922 interface.  Zero or more
     -- virtual circuits are layered onto this interface and provide
     -- interconnection with various remote destinations.
     -- Each such virtual circuit is represented by an entry in the
     -- circuit table.
     --   Circuit Table Extensions  
     -- The table describing the use of the PVCs attached to
     -- each Frame Relay Interface.
     usrfrExtCircuitTable OBJECT-TYPE
         SYNTAX   SEQUENCE OF UsrFrExtCircuitEntry
         MAX-ACCESS   not-accessible
         STATUS   current
         DESCRIPTION
            "A table containing information about 
            specific virtual circuits."
         ::= { usrFRExt 5 }
         usrfrExtCircuitEntry OBJECT-TYPE
             SYNTAX   UsrFrExtCircuitEntry
             MAX-ACCESS   not-accessible
             STATUS   current
             DESCRIPTION
                "The information regarding a single  Data  Link
                Connection Identifier."
             INDEX { usrfrExtCircuitIfIndex, usrfrExtCircuitDlci }
             ::= { usrfrExtCircuitTable 1 }
         UsrFrExtCircuitEntry ::=
             SEQUENCE {
                 usrfrExtCircuitIfIndex
                     Index,
                 usrfrExtCircuitDlci
                     DLCI,
                 usrfrExtCircuitOperStatus
                     INTEGER,
                 usrfrExtCircuitCIR
                     INTEGER,
                 usrfrExtCircuitBcMax
                     INTEGER,
                 usrfrExtCircuitBcMin
                     INTEGER,
                 usrfrExtCircuitCurrentBc
                     INTEGER,
                 usrfrExtCircuitTc
                     INTEGER,
                 usrfrExtCircuitBECNMonitoring
                     INTEGER,
                 usrfrExtCircuitCMP
                     INTEGER,
                 usrfrExtCircuitTxFramesCongested             
                     Counter32,             
                 usrfrExtCircuitTxOctetsCongested
                     Counter32,             
                 usrfrExtCircuitTxFramesDiscarded
                     Counter32,             
                 usrfrExtCircuitTxOctetsDiscarded
                     Counter32,             
                 usrfrExtCircuitTxFramesFromForwarder
                     Counter32,             
                 usrfrExtCircuitTxOctetsFromForwarder    
                     Counter32,             
                 usrfrExtCircuitRxFramesCongested    
                     Counter32,             
                 usrfrExtCircuitRxOctetsCongested    
                     Counter32,             
                 usrfrExtCircuitRxOctetsDiscarded    
                     Counter32,             
                 usrfrExtCircuitRxFramesByForwarder    
                     Counter32,             
                 usrfrExtCircuitRxOctetsByForwarder    
                     Counter32,             
                 usrfrExtCircuitTxIPProtocolFrames    
                     Counter32,             
                 usrfrExtCircuitRxIPProtocolFrames    
                     Counter32,             
                 usrfrExtCircuitTxIPXProtocolFrames    
                     Counter32,             
                 usrfrExtCircuitRxIPXProtocolFrames    
                     Counter32,             
                 usrfrExtCircuitTxATProtocolFrames    
                     Counter32,             
                 usrfrExtCircuitRxATProtocolFrames    
                     Counter32,             
                 usrfrExtCircuitTxBridgedFrames    
                     Counter32,             
                 usrfrExtCircuitRxBridgedFrames    
                     Counter32,
                 usrfrExtCircuitPVCName
                     DisplayString,
                 usrfrExtCircuitTrace
                     INTEGER,
                 usrfrExtCircuitBECNRatio
                     INTEGER,
                 usrfrExtCircuitTxL2TPProtocolFrames
                     Counter32,
                 usrfrExtCircuitRxL2TPProtocolFrames
                     Counter32,
	         usrfrExtCircuitPTMPGroupState
		     TruthValue,
	         usrfrExtCircuitPTMPGroupName
	             DisplayString	
         }
         usrfrExtCircuitIfIndex OBJECT-TYPE
             SYNTAX  Index
             MAX-ACCESS  read-only
             STATUS  current
             DESCRIPTION
                 "The ifIndex value of the ifEntry this  virtual
                 circuit is layered onto."
             ::= { usrfrExtCircuitEntry 1 }
         usrfrExtCircuitDlci OBJECT-TYPE
             SYNTAX  DLCI
             MAX-ACCESS  read-only
             STATUS  current
             DESCRIPTION
                 "The Data Link Connection Identifier  for  this
                 virtual circuit."
             REFERENCE
                 "Draft American National  Standard  T1.618-1991,
                 Section 3.3.6"
             ::= { usrfrExtCircuitEntry 2 }
         usrfrExtCircuitOperStatus OBJECT-TYPE
             SYNTAX  INTEGER {
                 up       (1),  -- ready to pass packets
                 down     (2),
                 disabled (3)
             }
             MAX-ACCESS  read-only
             STATUS  current
             DESCRIPTION
                 "The current operational state of the FR PVC.  The
                 disabled(3) state indicates that no operational packets
                 can be passed through this PVC.  It reflects the fact that 
                 CircuitAdminStatus is disabled. The up(1) describes
                 a state when packets can be sent and received on the PVC.
                 The down(2) indicates that PVC is not able to operate. 
                 The up(1) and down(2) states are set up based
                 on LMI PVCS IE."
             ::= { usrfrExtCircuitEntry 3 }
         usrfrExtCircuitCIR OBJECT-TYPE
             SYNTAX  INTEGER {
                 on  (1),
                 off (2)
             }
             MAX-ACCESS  read-write
             STATUS  current
             DESCRIPTION
                 "Committed Information Rate (CIR) describes how congestion
                 control is handled.  Off indicates that no attempt
                 at transmit control is made.
                 On indicates that Frame Relay is monitoring amount of
                 data transmitted through the physical interface and
                 restricts this according to CIR rules."
             DEFVAL { 1 }
             --CONFIGURABLE
             ::= { usrfrExtCircuitEntry 4 }
         usrfrExtCircuitBcMax OBJECT-TYPE
             SYNTAX  INTEGER (0..8192000)
             MAX-ACCESS  read-write
             STATUS  current
             DESCRIPTION
                 "The Committed Burst Size is the maximum amount of data
                 (in bits) that the user may offer to the network, under
                 normal conditions, during a time interval Tc.
                 The BcMax value defines the upper boundary of current
                 Bc value."
             REFERENCE 
                 "CCITT Recommendation I.370, Section 1.2 Bc"
             DEFVAL { 256000 }
             --CONFIGURABLE
             ::= { usrfrExtCircuitEntry 5 }
         usrfrExtCircuitBcMin OBJECT-TYPE
             SYNTAX  INTEGER (0..8192000)
             MAX-ACCESS  read-write
             STATUS  current
             DESCRIPTION
                 "The Committed Burst Size is the maximum amount of data
                 (in bits) that the user may offer to the network, under
                 normal conditions, during a time interval Tc.
                 The BcMin value defines the lower boundary of current
                 Bc value."
             REFERENCE 
                 "CCITT Recommendation I.370, Section 1.2 Bc"
             DEFVAL { 128000 }
             --CONFIGURABLE
             ::= { usrfrExtCircuitEntry 6 }
         usrfrExtCircuitCurrentBc OBJECT-TYPE
             SYNTAX  INTEGER (0..8192000)
             MAX-ACCESS  read-only
             STATUS  current
             DESCRIPTION
                 "The Committed Burst Size is the maximum amount of data
                 (in bits) that the user may offer to the network, under
                 normal conditions, during a time interval Tc.
                 The CurrentBc value represents currently used Bc value."
             REFERENCE 
                 "CCITT Recommendation I.370, Section 1.2 Bc"
             ::= { usrfrExtCircuitEntry 7 }
         usrfrExtCircuitTc OBJECT-TYPE
             SYNTAX  INTEGER (0..2147483647)
             MAX-ACCESS  read-only
             STATUS  current
             DESCRIPTION
                 "The Committed Rate Measurement Interval is
                 a time interval during which the user is allowed
                 to send only the committed amount of date (Bc) and
                 the excess amount of data (Be). This value is
                 calculated and is expressed in milliseconds."
             REFERENCE 
                 "CCITT Recommendation I.370, Section 1.2 Tc"
             ::= { usrfrExtCircuitEntry 8 }
         usrfrExtCircuitBECNMonitoring OBJECT-TYPE
             SYNTAX  INTEGER {
                 on  (1),
                 off (2)
             }
             MAX-ACCESS  read-write
             STATUS  current
             DESCRIPTION
                 "BECN Monitoring describes if BECN congestion notification
                 control is handled.  Off indicates that no attempt
                 at congestion notification control is made. 
                 On indicates that the BECN bit of the Q.922 header is
                 monitored. When the BECN bit indicates that the Frame
                 Relay switch is experiencing congestion over this DLCI,
                 the transmission rate will be slowed, to value calculated
                 based on usrfrCircuitBcMin. When the bit indicates 
                 alleviation of congestion, the transmission rate will 
                 be incrementally increased back to a value calculated 
                 based on usrfrCircuitBcMax."
             DEFVAL { 2 }
             --CONFIGURABLE
             ::= { usrfrExtCircuitEntry 9 }
         usrfrExtCircuitCMP OBJECT-TYPE
             SYNTAX  INTEGER (1..100)
             MAX-ACCESS  read-write
             STATUS  current
             DESCRIPTION
                 "The Congestion Monitoring Period - is a period
                 expressed in seconds, during which Frame Relay
                 monitors number of received BECN events."    
             DEFVAL { 10 }
             --CONFIGURABLE
             ::= { usrfrExtCircuitEntry 10 }
         --
         -- Circuit Statistics
         --
         usrfrExtCircuitTxFramesCongested OBJECT-TYPE
             SYNTAX  Counter32
             MAX-ACCESS  read-only
             STATUS  current
             DESCRIPTION
                 "Number of frames congested by a physical driver
                  during transmit action taken by this PVC since 
                  it was created."
             ::= { usrfrExtCircuitEntry 11 }
         usrfrExtCircuitTxOctetsCongested OBJECT-TYPE
             SYNTAX  Counter32
             MAX-ACCESS  read-only
             STATUS  current
             DESCRIPTION
                 "Number of bytes congested by a physical driver
                  during transmit action taken by this PVC since 
                  it was created."
             ::= { usrfrExtCircuitEntry 12 }
         usrfrExtCircuitTxFramesDiscarded OBJECT-TYPE
             SYNTAX  Counter32
             MAX-ACCESS  read-only
             STATUS  current
             DESCRIPTION
                 "Number of frames discarded during transmit 
                  action by this PVC since it was created."
             ::= { usrfrExtCircuitEntry 13 }
         usrfrExtCircuitTxOctetsDiscarded OBJECT-TYPE
             SYNTAX  Counter32
             MAX-ACCESS  read-only
             STATUS  current
             DESCRIPTION
                 "Number of bytes discarded during transmit
                  action by this PVC since it was created."
             ::= { usrfrExtCircuitEntry 14 }
         usrfrExtCircuitTxFramesFromForwarder OBJECT-TYPE
             SYNTAX  Counter32
             MAX-ACCESS  read-only
             STATUS  current
             DESCRIPTION
                 "Number of frames handed down from forwarder to
                  this PVC since it was created."
             ::= { usrfrExtCircuitEntry 15 }
         usrfrExtCircuitTxOctetsFromForwarder OBJECT-TYPE
             SYNTAX  Counter32
             MAX-ACCESS  read-only
             STATUS  current
             DESCRIPTION
                 "Number of bytes handed down from forwarder to
                  this PVC since it was created."
             ::= { usrfrExtCircuitEntry 16 }
         usrfrExtCircuitRxFramesCongested OBJECT-TYPE
             SYNTAX  Counter32
             MAX-ACCESS  read-only
             STATUS  current
             DESCRIPTION
                 "Number of frames congested by a forwarder
                  during receive action taken by this PVC since 
                  it was created."
             ::= { usrfrExtCircuitEntry 17 }
         usrfrExtCircuitRxOctetsCongested OBJECT-TYPE
             SYNTAX  Counter32
             MAX-ACCESS  read-only
             STATUS  current
             DESCRIPTION
                 "Number of bytes congested by a forwarder
                  during receive action taken by this PVC since 
                  it was created."
             ::= { usrfrExtCircuitEntry 18 }
         usrfrExtCircuitRxOctetsDiscarded OBJECT-TYPE
             SYNTAX  Counter32
             MAX-ACCESS  read-only
             STATUS  current
             DESCRIPTION
                 "Number of bytes discarded during receive
                  action by this PVC since it was created."
             ::= { usrfrExtCircuitEntry 19 }
         usrfrExtCircuitRxFramesByForwarder OBJECT-TYPE
             SYNTAX  Counter32
             MAX-ACCESS  read-only
             STATUS  current
             DESCRIPTION
                 "Number of frames passed to forwarder by
                  this PVC since it was created."
             ::= { usrfrExtCircuitEntry 20 }
         usrfrExtCircuitRxOctetsByForwarder OBJECT-TYPE
             SYNTAX  Counter32
             MAX-ACCESS  read-only
             STATUS  current
             DESCRIPTION
                 "Number of bytes passed to forwarder by
                  this PVC since it was created."
             ::= { usrfrExtCircuitEntry 21 }
         usrfrExtCircuitTxIPProtocolFrames OBJECT-TYPE
             SYNTAX  Counter32
             MAX-ACCESS  read-only
             STATUS  current
             DESCRIPTION
                 "Number of IP protocol frames sent by
                  this PVC since it was created."
             ::= { usrfrExtCircuitEntry 22 }
         usrfrExtCircuitRxIPProtocolFrames OBJECT-TYPE
             SYNTAX  Counter32
             MAX-ACCESS  read-only
             STATUS  current
             DESCRIPTION
                 "Number of IP protocol frames received by
                  this PVC since it was created."
             ::= { usrfrExtCircuitEntry 23 }
         usrfrExtCircuitTxIPXProtocolFrames OBJECT-TYPE
             SYNTAX  Counter32
             MAX-ACCESS  read-only
             STATUS  current
             DESCRIPTION
                 "Number of IPX protocol frames sent by
                  this PVC since it was created."
             ::= { usrfrExtCircuitEntry 24 }
         usrfrExtCircuitRxIPXProtocolFrames OBJECT-TYPE
             SYNTAX  Counter32
             MAX-ACCESS  read-only
             STATUS  current
             DESCRIPTION
                 "Number of IPX protocol frames received by
                  this PVC since it was created."
             ::= { usrfrExtCircuitEntry 25 }
         usrfrExtCircuitTxATProtocolFrames OBJECT-TYPE
             SYNTAX  Counter32
             MAX-ACCESS  read-only
             STATUS  current
             DESCRIPTION
                 "Number of AppleTalk protocol frames sent by
                  this PVC since it was created."
             ::= { usrfrExtCircuitEntry 26 }
         usrfrExtCircuitRxATProtocolFrames OBJECT-TYPE
             SYNTAX  Counter32
             MAX-ACCESS  read-only
             STATUS  current
             DESCRIPTION
                 "Number of AppleTalk protocol frames received by
                  this PVC since it was created."
             ::= { usrfrExtCircuitEntry 27 }
         usrfrExtCircuitTxBridgedFrames OBJECT-TYPE
             SYNTAX  Counter32
             MAX-ACCESS  read-only
             STATUS  current
             DESCRIPTION
                 "Number of Bridged frames sent by
                  this PVC since it was created."
             ::= { usrfrExtCircuitEntry 28 }
         usrfrExtCircuitRxBridgedFrames OBJECT-TYPE
             SYNTAX  Counter32
             MAX-ACCESS  read-only
             STATUS  current
             DESCRIPTION
                 "Number of Bridged frames received by
                  this PVC since it was created."
             ::= { usrfrExtCircuitEntry 29 }
         usrfrExtCircuitPVCName OBJECT-TYPE
             SYNTAX  DisplayString (SIZE (1..32))
             MAX-ACCESS  read-write
             STATUS  current
             DESCRIPTION
                 "The name of this PVC. This table allows
                 the Pilgrim CLI process to translate PVC
                 name into IfIndex/DLCI pair."
             --CONFIGURABLE
             ::= { usrfrExtCircuitEntry 30 }
         usrfrExtCircuitTrace OBJECT-TYPE
             SYNTAX  INTEGER {
                 on  (1),
                 off (2)
             }
             MAX-ACCESS  read-write
             STATUS  current
             DESCRIPTION
                 "This indicates if the Frame Relay data frames trace 
                 information will be displayed on the console for this
                 PVC."
             DEFVAL { 2 }
             --CONFIGURABLE
             ::= { usrfrExtCircuitEntry 31 }
         usrfrExtCircuitBECNRatio OBJECT-TYPE
             SYNTAX  INTEGER (1..99)
             MAX-ACCESS  read-write
             STATUS  current
             DESCRIPTION
                 "BECN/(BECN + NO_BECN) percentage ratio used by 
                 BECN Monitoring mechanism to make a BC adjustment
                 decision for this PVC. It is expressed in percents."
             DEFVAL { 50 }
             --CONFIGURABLE
             ::= { usrfrExtCircuitEntry 32 }
         usrfrExtCircuitTxL2TPProtocolFrames OBJECT-TYPE
             SYNTAX  Counter32
             MAX-ACCESS  read-only
             STATUS  current
             DESCRIPTION
                 "Number of L2TP Protocol frames sent by
                  this PVC since it was created."
             ::= { usrfrExtCircuitEntry 33 }
         usrfrExtCircuitRxL2TPProtocolFrames OBJECT-TYPE
             SYNTAX  Counter32
             MAX-ACCESS  read-only
             STATUS  current
             DESCRIPTION
                 "Number of L2TP Protocol frames received by
                  this PVC since it was created."
             ::= { usrfrExtCircuitEntry 34 }
		 usrfrExtCircuitPTMPGroupState	OBJECT-TYPE
			 SYNTAX  TruthValue
			 MAX-ACCESS	read-only
			 STATUS	 current
			 DESCRIPTION
				"Determines whether this PVC is attached to a PTMP
				 Group or not"
			 ::= { usrfrExtCircuitEntry 35 }
		 usrfrExtCircuitPTMPGroupName	OBJECT-TYPE
			 SYNTAX	DisplayString
			 MAX-ACCESS	read-only
			 STATUS	current
			 DESCRIPTION
				"Name of the Point-to-Multipoint group this PVC is
				 assiciated with"
			 ::= { usrfrExtCircuitEntry 36 }
     --        
     --  Frame Relay DLL Error Table Extensions
     --
     -- The table describing errors encountered on each Frame
     -- Relay Interface.
     usrfrExtErrTable OBJECT-TYPE
         SYNTAX   SEQUENCE OF UsrFrExtErrEntry
         MAX-ACCESS   not-accessible
         STATUS   current
         DESCRIPTION
            "A table containing information about Errors on the 
            Frame Relay interface."
         ::= { usrFRExt 6 }
         usrfrExtErrEntry OBJECT-TYPE
             SYNTAX   UsrFrExtErrEntry
             MAX-ACCESS   not-accessible
             STATUS   current
             DESCRIPTION
                "The error information for a single Frame Relay
                interface."
            INDEX { usrfrExtErrIfIndex }
            ::= { usrfrExtErrTable 1 }
         UsrFrExtErrEntry ::=
             SEQUENCE {
                 usrfrExtErrIfIndex
                     Index,
                 usrfrExtErrUnknownError
                     Counter32,
                 usrfrExtErrReceivedShortFrames
                     Counter32,
                 usrfrExtErrReceivedLongFrames
                     Counter32,
                 usrfrExtErrIllegalDlcis
                     Counter32,
                 usrfrExtErrUnknownDlcis
                     Counter32,
                 usrfrExtErrDlmciProtocolErrs
                     Counter32,
                 usrfrExtStatDLLRxFrames
                     Counter32,
                 usrfrExtStatDLLRxOctets
                     Counter32,
                 usrfrExtStatDLLTxFrames    
                     Counter32,
                 usrfrExtStatDLLTxOctets    
                     Counter32,
                 usrfrExtStatLMIRxFrames    
                     Counter32,
                 usrfrExtStatLMITxFrames    
                     Counter32,
                 usrfrExtStatLMIRxStatusEnquiry    
                     Counter32,
                 usrfrExtStatLMITxStatusEnquiry    
                     Counter32,
                 usrfrExtStatLMIRxStatus    
                     Counter32,
                 usrfrExtStatLMITxStatus    
                     Counter32,
                 usrfrExtStatLMIRxStatusUpdate    
                     Counter32,
                 usrfrExtErrLMINoNetworkResponse    
                     Counter32,
                 usrfrExtErrLMIInvQ922    
                     Counter32,
                 usrfrExtErrLMIInvControlField    
                     Counter32,
                 usrfrExtErrLMIInvProtocolDiscr    
                     Counter32,
                 usrfrExtErrLMIInvCallReference    
                     Counter32,
                 usrfrExtErrLMIInvMessageType    
                     Counter32,
                 usrfrExtErrLMIInvLockingShift    
                     Counter32,
                 usrfrExtErrLMIInvReportType    
                     Counter32,
                 usrfrExtErrLMIInvLIV    
                     Counter32,
                 usrfrExtErrLMIInvSeqNum    
                     Counter32,
                 usrfrExtErrLMIInvPVCStatus    
                     Counter32,
                 usrfrExtErrLMIUnsolicitedMessage    
                     Counter32,
                 usrfrExtErrLMIUnrecognizedIE    
                     Counter32,
                 usrfrExtErrLMIIncompleteMessage    
                     Counter32,
                 usrfrExtErrLMIOutOfOrderIE    
                     Counter32,
                 usrfrExtErrLMIInvSpareBits    
                     Counter32,
                 usrfrExtErrLMIInvExtensionBit    
                     Counter32,
                 usrfrExtErrLMIInvNADBits    
                     Counter32,
                 usrfrExtStatLMIRxAsyncStatus    
                     Counter32
         }
         usrfrExtErrIfIndex OBJECT-TYPE
             SYNTAX   Index
             MAX-ACCESS   read-only
             STATUS   current
             DESCRIPTION
                "The ifIndex Value of the ifEntry this  virtual
                circuit is layered onto."
            ::= { usrfrExtErrEntry 1 }
         usrfrExtErrUnknownError OBJECT-TYPE
             SYNTAX   Counter32
             MAX-ACCESS   read-only
             STATUS   current
             DESCRIPTION
                "An error which is not specified by another counter."
           ::= { usrfrExtErrEntry 2 }
         usrfrExtErrReceivedShortFrames OBJECT-TYPE
             SYNTAX   Counter32
             MAX-ACCESS   read-only
             STATUS   current
             DESCRIPTION
                "Number of frames discarded because they were
                too short."
           ::= { usrfrExtErrEntry 3 }
         usrfrExtErrReceivedLongFrames OBJECT-TYPE
             SYNTAX   Counter32
             MAX-ACCESS   read-only
             STATUS   current
             DESCRIPTION
                "Number of frames discarded because they were
                too long."
           ::= { usrfrExtErrEntry 4 }
         usrfrExtErrIllegalDlcis OBJECT-TYPE
             SYNTAX   Counter32
             MAX-ACCESS   read-only
             STATUS   current
             DESCRIPTION
                "Number of frames discarded because they contained
                illegal DLCIs."
           ::= { usrfrExtErrEntry 5 }
         usrfrExtErrUnknownDlcis OBJECT-TYPE
             SYNTAX   Counter32
             MAX-ACCESS   read-only
             STATUS   current
             DESCRIPTION
                "Number of frames discarded because they contained
                unknown DLCIs."
           ::= { usrfrExtErrEntry 6 }
         usrfrExtErrDlmciProtocolErrs OBJECT-TYPE
             SYNTAX   Counter32
             MAX-ACCESS   read-only
             STATUS   current
             DESCRIPTION
                "Number of Frame Relay protocol errors."
           ::= { usrfrExtErrEntry 7 }
         usrfrExtStatDLLRxFrames OBJECT-TYPE
             SYNTAX   Counter32
             MAX-ACCESS   read-only
             STATUS   current
             DESCRIPTION
                "Number of Frame Relay frames received on this DLL."
           ::= { usrfrExtErrEntry 8 }
         usrfrExtStatDLLRxOctets OBJECT-TYPE
             SYNTAX   Counter32
             MAX-ACCESS   read-only
             STATUS   current
             DESCRIPTION
                "Number of bytes received on this DLL."
           ::= { usrfrExtErrEntry 9 }
         usrfrExtStatDLLTxFrames OBJECT-TYPE
             SYNTAX   Counter32
             MAX-ACCESS   read-only
             STATUS   current
             DESCRIPTION
                "Number of Frame Relay frames transmitted on this DLL."
           ::= { usrfrExtErrEntry 10 }
         usrfrExtStatDLLTxOctets OBJECT-TYPE
             SYNTAX   Counter32
             MAX-ACCESS   read-only
             STATUS   current
             DESCRIPTION
                "Number of octets transmitted on this DLL."
           ::= { usrfrExtErrEntry 11 }
         usrfrExtStatLMIRxFrames OBJECT-TYPE
             SYNTAX   Counter32
             MAX-ACCESS   read-only
             STATUS   current
             DESCRIPTION
                "Number of Frame Relay LMI frames received on this DLL."
           ::= { usrfrExtErrEntry 12 }
         usrfrExtStatLMITxFrames OBJECT-TYPE
             SYNTAX   Counter32
             MAX-ACCESS   read-only
             STATUS   current
             DESCRIPTION
                "Number of Frame Relay LMI frames transmitted on this DLL."
           ::= { usrfrExtErrEntry 13 }
         usrfrExtStatLMIRxStatusEnquiry OBJECT-TYPE
             SYNTAX   Counter32
             MAX-ACCESS   read-only
             STATUS   current
             DESCRIPTION
                "Number of Frame Relay LMI Status Enquiry frames 
                 receiveded on this DLL."
           ::= { usrfrExtErrEntry 14 }
         usrfrExtStatLMITxStatusEnquiry OBJECT-TYPE
             SYNTAX   Counter32
             MAX-ACCESS   read-only
             STATUS   current
             DESCRIPTION
                "Number of Frame Relay LMI Status Enquiry frames 
                 transmitted on this DLL."
           ::= { usrfrExtErrEntry 15 }
         usrfrExtStatLMIRxStatus OBJECT-TYPE
             SYNTAX   Counter32
             MAX-ACCESS   read-only
             STATUS   current
             DESCRIPTION
                "Number of Frame Relay LMI Status frames 
                 received on this DLL."
           ::= { usrfrExtErrEntry 16 }
         usrfrExtStatLMITxStatus OBJECT-TYPE
             SYNTAX   Counter32
             MAX-ACCESS   read-only
             STATUS   current
             DESCRIPTION
                "Number of Frame Relay LMI Status frames 
                 transmitted on this DLL."
           ::= { usrfrExtErrEntry 17 }
         usrfrExtStatLMIRxStatusUpdate OBJECT-TYPE
             SYNTAX   Counter32
             MAX-ACCESS   read-only
             STATUS   current
             DESCRIPTION
                "Number of Frame Relay LMI Status Update frames 
                 received on this DLL."
           ::= { usrfrExtErrEntry 18 }
         usrfrExtErrLMINoNetworkResponse OBJECT-TYPE
             SYNTAX   Counter32
             MAX-ACCESS   read-only
             STATUS   current
             DESCRIPTION
                "Number of lacks of Network responses to LMI 
                 Status Enquiry frames sent on this DLL."
           ::= { usrfrExtErrEntry 19 }
         usrfrExtErrLMIInvQ922 OBJECT-TYPE
             SYNTAX   Counter32
             MAX-ACCESS   read-only
             STATUS   current
             DESCRIPTION
                "Number of LMI frames with invalid Q922 header
                 received on this DLL."
           ::= { usrfrExtErrEntry 20 }
         usrfrExtErrLMIInvControlField OBJECT-TYPE
             SYNTAX   Counter32
             MAX-ACCESS   read-only
             STATUS   current
             DESCRIPTION
                "Number of LMI frames with invalid Control Field
                 received on this DLL."
           ::= { usrfrExtErrEntry 21 }
         usrfrExtErrLMIInvProtocolDiscr OBJECT-TYPE
             SYNTAX   Counter32
             MAX-ACCESS   read-only
             STATUS   current
             DESCRIPTION
                "Number of LMI frames with invalid Protocol 
                 Discriominator field received on this DLL."
           ::= { usrfrExtErrEntry 22 }
         usrfrExtErrLMIInvCallReference OBJECT-TYPE
             SYNTAX   Counter32
             MAX-ACCESS   read-only
             STATUS   current
             DESCRIPTION
                "Number of LMI frames with invalid Call Reference
                 field received on this DLL."
           ::= { usrfrExtErrEntry 23 }
         usrfrExtErrLMIInvMessageType OBJECT-TYPE
             SYNTAX   Counter32
             MAX-ACCESS   read-only
             STATUS   current
             DESCRIPTION
                "Number of LMI frames with invalid Message Type
                 field received on this DLL."
           ::= { usrfrExtErrEntry 24 }
         usrfrExtErrLMIInvLockingShift OBJECT-TYPE
             SYNTAX   Counter32
             MAX-ACCESS   read-only
             STATUS   current
             DESCRIPTION
                "Number of LMI frames with invalid Locking Shift
                 IE received on this DLL."
           ::= { usrfrExtErrEntry 25 }
         usrfrExtErrLMIInvReportType OBJECT-TYPE
             SYNTAX   Counter32
             MAX-ACCESS   read-only
             STATUS   current
             DESCRIPTION
                "Number of LMI frames with invalid Report Type
                 IE received on this DLL."
           ::= { usrfrExtErrEntry 26 }
         usrfrExtErrLMIInvLIV OBJECT-TYPE
             SYNTAX   Counter32
             MAX-ACCESS   read-only
             STATUS   current
             DESCRIPTION
                "Number of LMI frames with invalid Link Integrity
                 Verification IE received on this DLL."
           ::= { usrfrExtErrEntry 27 }
         usrfrExtErrLMIInvSeqNum OBJECT-TYPE
             SYNTAX   Counter32
             MAX-ACCESS   read-only
             STATUS   current
             DESCRIPTION
                "Number of LMI frames with invalid Sequence Number
                 field received on this DLL."
           ::= { usrfrExtErrEntry 28 }
         usrfrExtErrLMIInvPVCStatus OBJECT-TYPE
             SYNTAX   Counter32
             MAX-ACCESS   read-only
             STATUS   current
             DESCRIPTION
                "Number of LMI frames with invalid PVC Status
                 IE received on this DLL."
           ::= { usrfrExtErrEntry 29 }
         usrfrExtErrLMIUnsolicitedMessage OBJECT-TYPE
             SYNTAX   Counter32
             MAX-ACCESS   read-only
             STATUS   current
             DESCRIPTION
                "Number of unsolicited LMI frames received on 
                 this DLL."
           ::= { usrfrExtErrEntry 30 }
         usrfrExtErrLMIUnrecognizedIE OBJECT-TYPE
             SYNTAX   Counter32
             MAX-ACCESS   read-only
             STATUS   current
             DESCRIPTION
                "Number of LMI frames with unrecognized
                 IE received on this DLL."
           ::= { usrfrExtErrEntry 31 }
         usrfrExtErrLMIIncompleteMessage OBJECT-TYPE
             SYNTAX   Counter32
             MAX-ACCESS   read-only
             STATUS   current
             DESCRIPTION
                "Number of LMI frames with incomplete current
                 IE received on this DLL."
           ::= { usrfrExtErrEntry 32 }
         usrfrExtErrLMIOutOfOrderIE OBJECT-TYPE
             SYNTAX   Counter32
             MAX-ACCESS   read-only
             STATUS   current
             DESCRIPTION
                "Number of LMI frames with out_of_order IE 
                 received on this DLL."
           ::= { usrfrExtErrEntry 33 }
         usrfrExtErrLMIInvSpareBits OBJECT-TYPE
             SYNTAX   Counter32
             MAX-ACCESS   read-only
             STATUS   current
             DESCRIPTION
                "Number of LMI frames with invalid Spare Bits
                 values in IE received on this DLL."
           ::= { usrfrExtErrEntry 34 }
         usrfrExtErrLMIInvExtensionBit OBJECT-TYPE
             SYNTAX   Counter32
             MAX-ACCESS   read-only
             STATUS   current
             DESCRIPTION
                "Number of LMI frames with invalid Extension Bit
                 value in IE received on this DLL."
           ::= { usrfrExtErrEntry 35 }
         usrfrExtErrLMIInvNADBits OBJECT-TYPE
             SYNTAX   Counter32
             MAX-ACCESS   read-only
             STATUS   current
             DESCRIPTION
                "Number of LMI frames with invalid New, Active or
                 Delete bits in PVCS IE received on this DLL."
           ::= { usrfrExtErrEntry 36 }
         usrfrExtStatLMIRxAsyncStatus OBJECT-TYPE
             SYNTAX   Counter32
             MAX-ACCESS   read-only
             STATUS   current
             DESCRIPTION
                "Number of LMI Async Status frames received on this DLL."
           ::= { usrfrExtErrEntry 37 }    
     -- 
     --  Frame Relay Trap Extensions
     --  
     usrfrExtTraps OBJECT IDENTIFIER ::= { usrFRExt 7}
     usrfrExtDLCMIStatusChange NOTIFICATION-TYPE
         OBJECTS  { usrfrExtDlcmiOperStatus }
         STATUS   current
         DESCRIPTION
         " This trap indicates that the indicated Data Link Layer
         has changed state. It has either been created or invalidated,
         or has toggled between the active and inactive states. " 
         --#TYPE "Warning"
         --#SUMMARY "Data Link Layer has changed state (%d)"
         --#ARGUMENTS { 0 }
         --#SEVERITY MAJOR
         --#STATE    OPERATIONAL
         --#PROBABLECAUSE "State Change"
         ::= { usrfrExtTraps 1 }
	--
	--  Frame Relay PTMP PVC Group Definition
	-- The Point-to-Multipoint PVC Group is a logical
      -- interface between Layer 3 protocol forwarders
      -- and a Group of PTP PVCs participating in this
      -- Group.
      --
usrfrExtPTMPGroupTable OBJECT-TYPE
         SYNTAX   SEQUENCE OF UsrFrExtPTMPGroupEntry
         MAX-ACCESS   not-accessible
         STATUS   current
         DESCRIPTION
            "A table containing information about 
            PTMP PVC Group specific"
         ::= { usrFRExt 8 }
         usrfrExtPTMPGroupEntry OBJECT-TYPE
             SYNTAX   UsrFrExtPTMPGroupEntry
             MAX-ACCESS   not-accessible
             STATUS   current
             DESCRIPTION
                "The information regarding a single PTMP PVC
                Group entry."
             INDEX { usrfrExtPTMPGroupName }
             ::= { usrfrExtPTMPGroupTable 1 }
         UsrFrExtPTMPGroupEntry ::=
             SEQUENCE {
                 usrfrExtPTMPGroupName
                     DisplayString,
                 usrfrExtPTMPGroupIndex
                     Index,
                 usrfrExtPTMPGroupOperStatus
                     INTEGER,
                 usrfrExtPTMPNumberOfPVCs
                     Counter32,
                 usrfrExtPTMPTxUcastFrames
                     Counter32,
                 usrfrExtPTMPTxUcastOctets
                     Counter32,
                 usrfrExtPTMPTxMcastFrames
                     Counter32,
                 usrfrExtPTMPTxMcastOctets
                     Counter32,
                 usrfrExtPTMPTxDiscardedFrames
                     Counter32,
                 usrfrExtPTMPTxDiscardedOctets
                     Counter32,
                 usrfrExtPTMPRxFrames
                     Counter32,
                 usrfrExtPTMPRxOctets 
                     Counter32,
                 usrfrExtPTMPRxCongestedFrames
                     Counter32,
                 usrfrExtPTMPRxCongestedOctets
                     Counter32,
                 usrfrExtPTMPRxDiscardedFrames
                     Counter32,
                 usrfrExtPTMPRxDiscardedOctets
                     Counter32,
                 usrfrExtPTMPTxIPProtocolFrames
                     Counter32,    
                 usrfrExtPTMPRxIPProtocolFrames
                     Counter32,    
                 usrfrExtPTMPTxIPXProtocolFrames
                     Counter32,
                 usrfrExtPTMPRxIPXProtocolFrames
                     Counter32,
                 usrfrExtPTMPTxATProtocolFrames
                     Counter32,    
                 usrfrExtPTMPRxATProtocolFrames
                     Counter32,    
                 usrfrExtPTMPTxBridgedFrames
                     Counter32,    
                 usrfrExtPTMPRxBridgedFrames
                     Counter32,    
                 usrfrExtPTMPTxL2TPProtocolFrames
                     Counter32,    
                 usrfrExtPTMPRxL2TPProtocolFrames
                     Counter32,
                 usrfrExtPTMPCreationTime
                     TimeStamp,
                 usrfrExtPTMPLastTimeChange
                     TimeStamp,
                 usrfrExtPTMPRowStatus
                     RowStatus,
                 usrfrExtPTMPTrace
                     INTEGER
         }
         usrfrExtPTMPGroupName OBJECT-TYPE
             SYNTAX  DisplayString (SIZE (1..32))
             MAX-ACCESS  read-only
             STATUS  current
             DESCRIPTION
                "The name of the PTMP PVC Group. It is a unique
                 name used as a index to PTMP PVC Group Table."
             ::= { usrfrExtPTMPGroupEntry 1 }
         usrfrExtPTMPGroupIndex OBJECT-TYPE
             SYNTAX  Index
             MAX-ACCESS  read-only
             STATUS  current
             DESCRIPTION
                "Logical Index used by a PVC as a reference to 
                a PTMP PVC Group. This index is a unique number."
             --CONFIGURABLE
             ::= { usrfrExtPTMPGroupEntry 2 }   
         usrfrExtPTMPGroupOperStatus OBJECT-TYPE
             SYNTAX  INTEGER {
                 up       (1),  -- ready to pass packets
                 down     (2),
                 disabled (3)
             }
             MAX-ACCESS  read-only
             STATUS  current
             DESCRIPTION
                 "The current operational state of the PTMP PVC Group. The
                 disabled(3) state indicates that no data packets
                 can be passed through this PTMP PVC Group. It reflects the fact that 
                 RowStatus is set to notInService. The up(1) describes
                 a state when packets can be sent and received on the PTMP PVC Group.
                 The down(2) indicates that PTMP PVC Group is not able to operate. 
                 The up(1) and down(2) states are set up based
                 on status of all PVC participating in this Group. "
             ::= { usrfrExtPTMPGroupEntry 3 }
         usrfrExtPTMPNumberOfPVCs OBJECT-TYPE
             SYNTAX  Counter32
             MAX-ACCESS  read-only
             STATUS  current
             DESCRIPTION
                "Number of PVCs associated with this PTMP PVC
                Group."
             ::= { usrfrExtPTMPGroupEntry 4 }   
         usrfrExtPTMPTxUcastFrames OBJECT-TYPE
             SYNTAX  Counter32
             MAX-ACCESS  read-only
             STATUS  current
             DESCRIPTION
                "Number of unicast frames sent by a forwarder 
                to this PTMP PVC Group, since it was enabled."
             ::= { usrfrExtPTMPGroupEntry 5 }
         usrfrExtPTMPTxUcastOctets OBJECT-TYPE
             SYNTAX  Counter32
             MAX-ACCESS  read-only
             STATUS  current
             DESCRIPTION
                "Number of octets in unicast frames sent by a forwarder
                to this PTMP PVC Group, since it was enabled."
             ::= { usrfrExtPTMPGroupEntry 6 }   
         usrfrExtPTMPTxMcastFrames OBJECT-TYPE
             SYNTAX  Counter32
             MAX-ACCESS  read-only
             STATUS  current
             DESCRIPTION
                "Number of multicast frames sent by a forwarder 
                to this PTMP PVC Group, since it was enabled."
             ::= { usrfrExtPTMPGroupEntry 7 }   
         usrfrExtPTMPTxMcastOctets OBJECT-TYPE
             SYNTAX  Counter32
             MAX-ACCESS  read-only
             STATUS  current
             DESCRIPTION
                "Number of octets in multicast frames sent by a forwarder
                to this PTMP PVC Group, since it was enabled."
             ::= { usrfrExtPTMPGroupEntry 8 }
         usrfrExtPTMPTxDiscardedFrames OBJECT-TYPE
             SYNTAX  Counter32
             MAX-ACCESS  read-only
             STATUS  current
             DESCRIPTION
                "Number of frames discarded, which were sent by forwarder 
                to this PTMP PVC Group, since it was enabled."
             ::= { usrfrExtPTMPGroupEntry 9 }
         usrfrExtPTMPTxDiscardedOctets OBJECT-TYPE
             SYNTAX  Counter32
             MAX-ACCESS  read-only
             STATUS  current
             DESCRIPTION
                "Number of octets in a discarded frames sent by a 
                forwarder to this PTMP PVC Group, since it was enabled."
             ::= { usrfrExtPTMPGroupEntry 10 }
         usrfrExtPTMPRxFrames OBJECT-TYPE
             SYNTAX  Counter32
             MAX-ACCESS  read-only
             STATUS  current
             DESCRIPTION
                "Number of frames received from all associated PVCS
                by this PTMP PVC Group, since it was enabled."
             ::= { usrfrExtPTMPGroupEntry 11 }
         usrfrExtPTMPRxOctets OBJECT-TYPE
             SYNTAX  Counter32
             MAX-ACCESS  read-only
             STATUS  current
             DESCRIPTION
                "Number of octets received from all associated PVCS
                by this PTMP PVC Group, since it was enabled."
             ::= { usrfrExtPTMPGroupEntry 12 }
         usrfrExtPTMPRxCongestedFrames OBJECT-TYPE
             SYNTAX  Counter32
             MAX-ACCESS  read-only
             STATUS  current
             DESCRIPTION
                "Number of frames received from all associated PVCS,
                which were congested by the forwarder on attempt of
                passing them by PTMP PVC Group, since the group was enabled."
             ::= { usrfrExtPTMPGroupEntry 13 }
         usrfrExtPTMPRxCongestedOctets OBJECT-TYPE
             SYNTAX  Counter32
             MAX-ACCESS  read-only
             STATUS  current
             DESCRIPTION
                "Number of octets in frames received from all associated PVCS,
                which were congested by the forwarder on attempt of
                passing them by PTMP PVC Group, since the group was enabled."
             ::= { usrfrExtPTMPGroupEntry 14 }
         usrfrExtPTMPRxDiscardedFrames OBJECT-TYPE
             SYNTAX  Counter32
             MAX-ACCESS  read-only
             STATUS  current
             DESCRIPTION
                "Number of received frames from all associated PVCs which 
                were discarded by this PTMP PVC Group, since it was enabled."
             ::= { usrfrExtPTMPGroupEntry 15 }
         usrfrExtPTMPRxDiscardedOctets OBJECT-TYPE
             SYNTAX  Counter32
             MAX-ACCESS  read-only
             STATUS  current
             DESCRIPTION
                "Number of octets in a received frames from all associated
                PVCs which were discarded by  this PTMP PVC Group, since it 
                was enabled."
             ::= { usrfrExtPTMPGroupEntry 16 }
         usrfrExtPTMPTxIPProtocolFrames OBJECT-TYPE
             SYNTAX  Counter32
             MAX-ACCESS  read-only
             STATUS  current
             DESCRIPTION
                 "Number of IP protocol frames sent by
                  this PTMP PVC Group since it was enabled."
             ::= { usrfrExtPTMPGroupEntry 17 }
         usrfrExtPTMPRxIPProtocolFrames OBJECT-TYPE
             SYNTAX  Counter32
             MAX-ACCESS  read-only
             STATUS  current
             DESCRIPTION
                 "Number of IP protocol frames received by
                  this PTMP PVC Group since it was enabled."
             ::= { usrfrExtPTMPGroupEntry 18 }
         usrfrExtPTMPTxIPXProtocolFrames OBJECT-TYPE
             SYNTAX  Counter32
             MAX-ACCESS  read-only
             STATUS  current
             DESCRIPTION
                 "Number of IPX protocol frames sent by
                  this PTMP PVC Group since it was enabled."
             ::= { usrfrExtPTMPGroupEntry 19 }
         usrfrExtPTMPRxIPXProtocolFrames OBJECT-TYPE
             SYNTAX  Counter32
             MAX-ACCESS  read-only
             STATUS  current
             DESCRIPTION
                 "Number of IPX protocol frames received by
                  this PTMP PVC Group since it was enabled."
             ::= { usrfrExtPTMPGroupEntry 20 }
         usrfrExtPTMPTxATProtocolFrames OBJECT-TYPE
             SYNTAX  Counter32
             MAX-ACCESS  read-only
             STATUS  current
             DESCRIPTION
                 "Number of AppleTalk protocol frames sent by
                  this PTMP PVC Group since it was enabled."
             ::= { usrfrExtPTMPGroupEntry 21 }
         usrfrExtPTMPRxATProtocolFrames OBJECT-TYPE
             SYNTAX  Counter32
             MAX-ACCESS  read-only
             STATUS  current
             DESCRIPTION
                 "Number of AppleTalk protocol frames received by
                  this PTMP PVC Group since it was enabled."
             ::= { usrfrExtPTMPGroupEntry 22 }
         usrfrExtPTMPTxBridgedFrames OBJECT-TYPE
             SYNTAX  Counter32
             MAX-ACCESS  read-only
             STATUS  current
             DESCRIPTION
                 "Number of Bridged frames sent by
                  this PTMP PVC Group since it was enabled."
             ::= { usrfrExtPTMPGroupEntry 23 }
         usrfrExtPTMPRxBridgedFrames OBJECT-TYPE
             SYNTAX  Counter32
             MAX-ACCESS  read-only
             STATUS  current
             DESCRIPTION
                 "Number of Bridged frames received by
                  this PTMP PVC Group since it was enabled."
             ::= { usrfrExtPTMPGroupEntry 24 }
         usrfrExtPTMPTxL2TPProtocolFrames OBJECT-TYPE
             SYNTAX  Counter32
             MAX-ACCESS  read-only
             STATUS  current
             DESCRIPTION
                 "Number of L2TP Protocol frames sent by
                  this PTMP PVC Group since it was enabled."
             ::= { usrfrExtPTMPGroupEntry 25 }
         usrfrExtPTMPRxL2TPProtocolFrames OBJECT-TYPE
             SYNTAX  Counter32
             MAX-ACCESS  read-only
             STATUS  current
             DESCRIPTION
                 "Number of L2TP Protocol frames received by
                  this PTMP PVC Group since it was enabled."
             ::= { usrfrExtPTMPGroupEntry 26 }
         usrfrExtPTMPCreationTime OBJECT-TYPE
             SYNTAX  TimeStamp
             MAX-ACCESS  read-only
             STATUS  current
             DESCRIPTION
                 "The value of sysUpTime when this PTMP PVC Group was created."
             ::= { usrfrExtPTMPGroupEntry 27 }
         usrfrExtPTMPLastTimeChange OBJECT-TYPE
             SYNTAX  TimeStamp
             MAX-ACCESS  read-only
             STATUS  current
             DESCRIPTION
                 "The value of sysUpTime when last there was a change
                  in this PTMP PVC Group state."
             ::= { usrfrExtPTMPGroupEntry 28 }
         usrfrExtPTMPRowStatus OBJECT-TYPE
             SYNTAX  RowStatus
             MAX-ACCESS  read-write
             STATUS  current
             DESCRIPTION
                "This object is used to create a new row or destroy or modify an
                existing row in a manner described in the definition of the
                RowStatus textual convention."
             --CONFIGURABLE
             ::= { usrfrExtPTMPGroupEntry 29 }
         usrfrExtPTMPTrace OBJECT-TYPE
             SYNTAX  INTEGER {
                 on  (1),
                 off (2)
             }
             MAX-ACCESS  read-write
             STATUS  current
             DESCRIPTION
                 "This indicates if the Frame Relay data frames trace 
                 information will be displayed on the console for this
                 PTMP PVC Group."
             DEFVAL { 2 }
             --CONFIGURABLE
             ::= { usrfrExtPTMPGroupEntry 30 }
     usrfrExtPTMPGroupStatusChange NOTIFICATION-TYPE
         OBJECTS  { usrfrExtPTMPGroupOperStatus }
         STATUS   current
         DESCRIPTION
         " This trap indicates that the indicated PTMP PVC Group
         has changed its state. It has either been created or invalidated,
         or has toggled between the active and inactive states. " 
         --#TYPE "Warning"
         --#SUMMARY "PTMP PVC Group has changed state (%d)"
         --#ARGUMENTS { 0 }
         --#SEVERITY MAJOR
         --#STATE    OPERATIONAL
         --#PROBABLECAUSE "State Change"
         ::= { usrfrExtTraps 2 }
     END        -- End of USR-FR-EXT-MIB DEFINITIONS
-- **********************************************************************
--	usr_dhcp.mib
--
--
-- Author:         Fritz Reeve
--
