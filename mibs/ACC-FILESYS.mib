ACC-FILESYS DEFINITIONS ::= BEGIN

    IMPORTS
	 OBJECT-TYPE FROM RFC1155-SMI
                      accTrapLogSeqNum FROM ACC-SYSTEM
	accBRG, DisplayString, RowStatus, IfIndex, SmdsAddress
             FROM ACC-MIB;

-- File System Group
	accFileSys	OBJECT IDENTIFIER ::= { accBRG 41 }
accFsDirectTable	OBJECT-TYPE
		SYNTAX	SEQUENCE OF AccFsDirectEntry
		ACCESS	not-accessible
		STATUS	mandatory
		DESCRIPTION
		" File system directory entries."
		::= { accFileSys 1 }
accFsDirectEntry	OBJECT-TYPE
		SYNTAX	AccFsDirectEntry
		ACCESS	not-accessible
		STATUS	mandatory
		DESCRIPTION
		" Specific entry information."
		INDEX	{ accFsDirectFileSpec }
		::= { accFsDirectTable 1 }
	AccFsDirectEntry  ::= SEQUENCE {
		accFsDirectFileSpec	DisplayString,
		accFsDirectCreate	INTEGER,
		accFsDirectBytSize	INTEGER,
		accFsDirectBlkSize	INTEGER,
		accFsDirectAttribStr	DisplayString,
		accFsDirectSwVers	DisplayString,
		accFsDirectPlatform	DisplayString,
		accFsDirectStatus	INTEGER,
		accFsDirectAction	INTEGER
		}
accFsDirectFileSpec	OBJECT-TYPE
		SYNTAX	DisplayString 
		ACCESS	read-write
		STATUS	mandatory
		DESCRIPTION
		" File name specification - filename with extension
		  and optional file system name.
		  Format: {file_system:}filename.ext"
		::= { accFsDirectEntry 1 }
accFsDirectCreate	OBJECT-TYPE
		SYNTAX	INTEGER
		ACCESS	read-only
		STATUS	mandatory
		DESCRIPTION
		" The UNIX file system compatible time/date stamp of when the 
		  file was created. "
		::= { accFsDirectEntry 2 }
accFsDirectBytSize	OBJECT-TYPE
		SYNTAX	INTEGER 
		ACCESS	read-only
		STATUS	mandatory
		DESCRIPTION
		" File size - in bytes."
		::= { accFsDirectEntry 3 }
accFsDirectBlkSize	OBJECT-TYPE
		SYNTAX	INTEGER 
		ACCESS	read-only
		STATUS	mandatory
		DESCRIPTION
		" File size - in blocks."
		::= { accFsDirectEntry 4 }
accFsDirectAttribStr	OBJECT-TYPE
		SYNTAX	DisplayString
		ACCESS	read-only
		STATUS	mandatory
		DESCRIPTION
		" The concatenated file attributes - for primary and
		  backup images."
		::= { accFsDirectEntry 5 }
accFsDirectSwVers	OBJECT-TYPE
		SYNTAX	DisplayString
		ACCESS	read-only
		STATUS	mandatory
		DESCRIPTION
		" The file software version ."
		::= { accFsDirectEntry 6 }
accFsDirectPlatform	OBJECT-TYPE
		SYNTAX	DisplayString
		ACCESS	read-only
		STATUS	mandatory
		DESCRIPTION
		" The hardware platform type."
		::= { accFsDirectEntry 7 }
accFsDirectStatus	OBJECT-TYPE
		SYNTAX	INTEGER {
			other(1), 
			invalid(2) --  delete the file
			}
		ACCESS	read-write
		STATUS	mandatory
		DESCRIPTION
		" Set this object to invalid to delete the entry"
		::= { accFsDirectEntry 8 }
accFsDirectAction	OBJECT-TYPE
		SYNTAX	INTEGER {
			primary(1), --  set as primary image file
			delete(2), --  delete the file
			backup(3), -- set as backup image file
			copy(4), -- copy the file
			rename(5) -- rename the file
			}
		ACCESS	read-write
		STATUS	mandatory
		DESCRIPTION
		" Describes the type of action to be performed on the file"
		::= { accFsDirectEntry 9 }
accFsVolumeTable	OBJECT-TYPE
		SYNTAX	SEQUENCE OF AccFsVolumeEntry
		ACCESS	not-accessible
		STATUS	mandatory
		DESCRIPTION
		" File sytem table."
		::= { accFileSys 2 }
accFsVolumeEntry	OBJECT-TYPE
		SYNTAX	AccFsVolumeEntry
		ACCESS	not-accessible
		STATUS	mandatory
		DESCRIPTION
		" Specific file system entry  information."
		INDEX	{ accFsVolumeName}
		::= { accFsVolumeTable 1 }
	AccFsVolumeEntry	::= SEQUENCE {
		accFsVolumeName		DisplayString,
		accFsVolumeSize		INTEGER,
		accFsVolumeBlockSize	INTEGER,
		accFsVolumeFileNum	INTEGER,
		accFsVolumeUsedBytes	INTEGER,
		accFsVolumeFreeBlocks	INTEGER,
		accFsVolumeFreeBytes	INTEGER,
		accFsVolumeResBlocks	INTEGER,
		accFsVolumeAction	INTEGER,
		accFsVolumeDst		DisplayString
		}
accFsVolumeName	OBJECT-TYPE
		SYNTAX	DisplayString
		ACCESS	read-only
		STATUS	mandatory
		DESCRIPTION
		" The file system name."
		::= { accFsVolumeEntry 1 }
accFsVolumeSize	OBJECT-TYPE
		SYNTAX	INTEGER 
		ACCESS	read-only
		STATUS	mandatory
		DESCRIPTION
		" Number of bytes of storage on file system."
		::= { accFsVolumeEntry 2 }
accFsVolumeBlockSize	OBJECT-TYPE
		SYNTAX	INTEGER 
		ACCESS	read-only
		STATUS	mandatory
		DESCRIPTION
		" Size of storage blocks on file system."
		::= { accFsVolumeEntry 3 }
accFsVolumeFileNum	OBJECT-TYPE
		SYNTAX	INTEGER 
		ACCESS	read-only
		STATUS	mandatory
		DESCRIPTION
		" Number of files on  file system."
		::= { accFsVolumeEntry 4 }
accFsVolumeUsedBytes	OBJECT-TYPE
		SYNTAX	INTEGER 
		ACCESS	read-only
		STATUS	mandatory
		DESCRIPTION
		" Number of bytes used to store files on  file system."
		::= { accFsVolumeEntry 5 }
accFsVolumeFreeBlocks	OBJECT-TYPE
		SYNTAX	INTEGER 
		ACCESS	read-only
		STATUS	mandatory
		DESCRIPTION
		" Number of free blocks on file system."
		::= { accFsVolumeEntry 6 }
accFsVolumeFreeBytes	OBJECT-TYPE
		SYNTAX	INTEGER 
		ACCESS	read-only
		STATUS	mandatory
		DESCRIPTION
		" Number of free bytes on file system."
		::= { accFsVolumeEntry 7 }
accFsVolumeResBlocks	OBJECT-TYPE
		SYNTAX	INTEGER 
		ACCESS	read-only
		STATUS	mandatory
		DESCRIPTION
		" Number of reserved blocks on file system."
		::= { accFsVolumeEntry 8 }
accFsVolumeAction	OBJECT-TYPE
		SYNTAX	INTEGER {
			copy (4)
		}
		ACCESS	read-write
		STATUS	mandatory
		DESCRIPTION
		" An action to perform on a flash volume."
		::= { accFsVolumeEntry 9 }
accFsVolumeDst		OBJECT-TYPE
		SYNTAX	DisplayString 
		ACCESS	read-write
		STATUS	mandatory
		DESCRIPTION
		" Destination volume for volume operations."
		::= { accFsVolumeEntry 10 }
accFsLoadedFiles	OBJECT IDENTIFIER ::= { accFileSys 3 }
accFsLoadFtkFile	OBJECT-TYPE
		SYNTAX	DisplayString
		ACCESS	read-only
		STATUS	mandatory
		DESCRIPTION
		" The loaded flash toolkit file."
		::= { accFsLoadedFiles 1 }
accFsLoadAplFile	OBJECT-TYPE
		SYNTAX	DisplayString
		ACCESS	read-only
		STATUS	mandatory
		DESCRIPTION
		" The loaded applications file."
		::= { accFsLoadedFiles 2 }
accFsLoadDiaFile	OBJECT-TYPE
		SYNTAX	DisplayString
		ACCESS	read-only
		STATUS	mandatory
		DESCRIPTION
		" The diagnostics file that has been 
		  executed prior to application."
		::= { accFsLoadedFiles 3 }
accFsLoadConFile	OBJECT-TYPE
		SYNTAX	DisplayString
		ACCESS	read-only
		STATUS	mandatory
		DESCRIPTION
		" The config utility  (.con) file that has been
		  executed prior to application."
		::= { accFsLoadedFiles 4 }
accFsLoadScrFile	OBJECT-TYPE 
		SYNTAX	DisplayString
		ACCESS	read-only
		STATUS	mandatory
		DESCRIPTION
		" The currently loaded configuration (.scr) file."
		::= { accFsLoadedFiles 5 }
accFsLoadFrmFile        OBJECT-TYPE
                SYNTAX  DisplayString
                ACCESS  read-only
                STATUS  mandatory
                DESCRIPTION
                " The loaded firmware file."
                ::= { accFsLoadedFiles 6 }
accReloadFileList	OBJECT-TYPE
		SYNTAX	DisplayString
		ACCESS	read-write
		STATUS	mandatory
		DESCRIPTION
		" The user-specified list of files to reload with.
		  If there is more than one file in the list then the
		  files should be enclosed in quotes.  If any of the
		  dia, con, scr or apl file types is missing from
		  the list, the primary of the file type will be used.
		  If .dia is specified in the list, then the diagnostics
		  utility will not be executed upon reload."
		::= { accFileSys 4 }

END
