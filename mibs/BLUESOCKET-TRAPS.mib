BLUESOCKET-TRAPS DEFINITIONS ::= BEGIN

    IMPORTS
	OBJECT-TYPE FROM RFC1155-SMI
	NOTIFICATION-TYPE FROM SNMPv2-SMI
        blueSocket
            FROM BLUESOCKET-ROOT;

blueNotification   OBJECT IDENTIFIER ::= { blueSocket 2 }

-- notification groups
        notifyObjects      OBJECT IDENTIFIER ::=  { blueNotification 1 }
        blueTraps          OBJECT IDENTIFIER ::=  { blueNotification 2 }

        blueConfigTraps    OBJECT IDENTIFIER ::=  { blueTraps 1 }
        blueFailureTraps   OBJECT IDENTIFIER ::=  { blueTraps 2 }
        blueThresholdTraps OBJECT IDENTIFIER ::=  { blueTraps 3 }
        blueGeneralTraps   OBJECT IDENTIFIER ::=  { blueTraps 4 }

-- Notification group
-- notifyObjects group

        ntyobjLevel OBJECT-TYPE
        SYNTAX  OCTET STRING(SIZE(1..20))
        MAX-ACCESS  accessible-for-notify
        STATUS  current
        DESCRIPTION
               "Event priority or log level."
        ::= { notifyObjects 1}

        ntyobjName OBJECT-TYPE
        SYNTAX  OCTET STRING(SIZE(1..255))
        MAX-ACCESS  accessible-for-notify
        STATUS  current
        DESCRIPTION
             "The name of the object that triggered the event.
              In case of no objects assosicated with
              failures, the value will be NULL.  "
                ::= { notifyObjects 2 }

        ntyobjDesc OBJECT-TYPE
        SYNTAX  OCTET STRING(SIZE(0..255))
        MAX-ACCESS  accessible-for-notify
        STATUS  current
        DESCRIPTION
             "Description about event/trap"
        ::= { notifyObjects 3 }

        ntyobjOID OBJECT-TYPE
        SYNTAX  OBJECT IDENTIFIER
        MAX-ACCESS  accessible-for-notify
        STATUS  current
        DESCRIPTION
             "The OID of the object that triggered the event"
        ::= { notifyObjects 4 }

        ntyobjValue OBJECT-TYPE
        SYNTAX  OCTET STRING(SIZE(0..255))
        MAX-ACCESS  accessible-for-notify
        STATUS  current
        DESCRIPTION
             "The value of the object that triggered
              the event at the time of event occurrence"
        ::= { notifyObjects 5 }


-- blueGeneralTraps group

    blueGeneralTraps0 OBJECT IDENTIFIER ::= { blueGeneralTraps 0 }

    btLinkUp NOTIFICATION-TYPE
    OBJECTS { ntyobjLevel,ntyobjName,ntyobjDesc}
    STATUS  current
    DESCRIPTION
            "Link up trap.
             ntyobjLevel   - Indicate the priority or log level
             ntyobjObjName - The name of the object that triggered the event
             ntyobjDesc    - Description about the event/trap
             "
    ::= { blueGeneralTraps0 1 }

    btLinkDown NOTIFICATION-TYPE
    OBJECTS { ntyobjLevel,ntyobjName,ntyobjDesc}
    STATUS  current
    DESCRIPTION
            "Link down trap.
             "
    ::= { blueGeneralTraps0 2 }

    btSystemGeneralTrap NOTIFICATION-TYPE
    OBJECTS { ntyobjLevel,ntyobjName,ntyobjDesc}
    STATUS  current
    DESCRIPTION
            "System status trap.
             ntyobjLevel   - Indicate the priority or log level
             ntyobjObjName - The name of the object that triggered the event
             ntyobjDesc    - Description about the event/trap
             "
    ::= { blueGeneralTraps0 3 }

-- configChangeTraps group

    blueConfigTraps0 OBJECT IDENTIFIER ::= { blueConfigTraps 0 }

    cctSystemConfChange NOTIFICATION-TYPE
    OBJECTS { ntyobjLevel,ntyobjName,ntyobjDesc}

    STATUS  current
    DESCRIPTION
            "This trap will be sent on any system level Configuration
            changes.
             ntyobjLevel   - Indicate the priority or log level
             ntyobjObjName - The name of the object that triggered the event
             ntyobjDesc    - Description about the event/trap
             "
    ::= { blueConfigTraps0 1 }

    cctUserConfChange NOTIFICATION-TYPE
    OBJECTS { ntyobjLevel,ntyobjName,ntyobjDesc}
    STATUS  current
    DESCRIPTION
            "User configuration change trap.
             ntyobjLevel   - Indicate the priority or log level
             ntyobjObjName - The name of the object that triggered the event
             ntyobjDesc    - Description about the event/trap
             "
    ::= { blueConfigTraps0 2 }


    cctExternalServConfChange NOTIFICATION-TYPE
    OBJECTS { ntyobjLevel,ntyobjName,ntyobjDesc}
    STATUS  current
    DESCRIPTION
            "External configuration change trap.
             ntyobjLevel   - Indicate the priority or log level
             ntyobjObjName - The name of the object that triggered the event
             ntyobjDesc    - Description about the event/trap
             "
    ::= { blueConfigTraps0 3 }

    cctRoleConfChange NOTIFICATION-TYPE
    OBJECTS { ntyobjLevel,ntyobjName,ntyobjDesc}
    STATUS  current
    DESCRIPTION
            "Role configuration changes.
             ntyobjLevel   - Indicate the priority or log level
             ntyobjObjName - The name of the object that triggered the event
             ntyobjDesc    - Description about the event/trap
             "
    ::= { blueConfigTraps0 4 }

    cctDestinationConfChange NOTIFICATION-TYPE
    OBJECTS { ntyobjLevel,ntyobjName,ntyobjDesc}
    STATUS  current
    DESCRIPTION
            "Destination configuration changes.
             ntyobjLevel   - Indicate the priority or log level
             ntyobjObjName - The name of the object that triggered the event
             ntyobjDesc    - Description about the event/trap
             "
    ::= { blueConfigTraps0 5 }



    cctServiceConfChange NOTIFICATION-TYPE
    OBJECTS { ntyobjLevel,ntyobjName,ntyobjDesc}
    STATUS  current
    DESCRIPTION
            "Service configuration change traps.
             ntyobjLevel   - Indicate the priority or log level
             ntyobjObjName - The name of the object that triggered the event
             ntyobjDesc    - Description about the event/trap
             "
    ::= { blueConfigTraps0 6 }


    cctNetworkConfChange NOTIFICATION-TYPE
    OBJECTS { ntyobjLevel,ntyobjName,ntyobjDesc}
    STATUS  current
    DESCRIPTION
            "Network configuration change trap.
             ntyobjLevel   - Indicate the priority or log level
             ntyobjObjName - The name of the object that triggered the event
             ntyobjDesc    - Description about the event/trap
             "
    ::= { blueConfigTraps0 7 }


    cctVpnConfChange NOTIFICATION-TYPE
    OBJECTS { ntyobjLevel,ntyobjName,ntyobjDesc}
    STATUS  current
    DESCRIPTION
            "VPN Configuration change trap.
             ntyobjLevel   - Indicate the priority or log level
             ntyobjObjName - The name of the object that triggered the event
             ntyobjDesc    - Description about the event/trap
             "
    ::= { blueConfigTraps0 8 }

    cctMobilityConfChange NOTIFICATION-TYPE
    OBJECTS { ntyobjLevel,ntyobjName,ntyobjDesc}
    STATUS  current
    DESCRIPTION
            "Mobility configuration change trap.
             ntyobjLevel   - Indicate the priority or log level
             ntyobjObjName - The name of the object that triggered the event
             ntyobjDesc    - Description about the event/trap
             "
    ::= { blueConfigTraps0 9 }

    cctProcessConfChange NOTIFICATION-TYPE
    OBJECTS { ntyobjLevel,ntyobjName,ntyobjDesc}
    STATUS  current
    DESCRIPTION
            "Process configuration change trap.
             ntyobjLevel   - Indicate the priority or log level
             ntyobjObjName - The name of the object that triggered the event
             ntyobjDesc    - Description about the event/trap
             "
    ::= { blueConfigTraps0 10 }

--FailureTraps group

    blueFailureTraps0 OBJECT IDENTIFIER ::= { blueFailureTraps 0 }

    btSysGeneralFailure  NOTIFICATION-TYPE
    OBJECTS { ntyobjLevel,ntyobjName,ntyobjDesc}
    STATUS  current
    DESCRIPTION
            "System failure trap.
             ntyobjLevel   - Indicate the priority or log level
             ntyobjObjName - The name of the object that triggered the event.
                         In case of no objects assosicated with
                         failures, the value will be NULL.

             ntyobjDesc    - Description about the event/trap
             "
    ::= { blueFailureTraps0 1 }

    btUserLoginFailure  NOTIFICATION-TYPE
    OBJECTS { ntyobjLevel,ntyobjName,ntyobjDesc}
    STATUS  current
    DESCRIPTION
            "User login failure trap.
             ntyobjLevel   - Indicate the priority or log level
             ntyobjObjName - The name of the object that triggered the event.
                         In case of no objects assosicated with
                         failures, the value will be NULL.

             ntyobjDesc    - Description about the event/trap
             "
    ::= { blueFailureTraps0 2 }

    btProcessFailure  NOTIFICATION-TYPE
    OBJECTS { ntyobjLevel,ntyobjName,ntyobjDesc}
    STATUS  current
    DESCRIPTION

            "Process failure trap.
             ntyobjLevel   - Indicate the priority or log level
             ntyobjObjName - The name of the object that triggered the event.
                         In case of no objects assosicated with
                         failures, the value will be NULL.

             ntyobjDesc    - Description about the event/trap
             "
    ::= { blueFailureTraps0 3 }

    btAuthFailure  NOTIFICATION-TYPE
    OBJECTS { ntyobjLevel,ntyobjName,ntyobjDesc}
    STATUS  current
    DESCRIPTION
            " Authentication failure trap.
             ntyobjLevel   - Indicate the priority or log level
             ntyobjObjName - The name of the object that triggered the event.
                         In case of no objects assosicated with
                         failures, the value will be NULL.
             ntyobjDesc    - Description about the event/trap
             "
    ::= { blueFailureTraps0 4 }

    btSystemFailover  NOTIFICATION-TYPE
    OBJECTS { ntyobjLevel,ntyobjName,ntyobjDesc}
    STATUS  current
    DESCRIPTION
            "This trap will be sent on system failover.
             ntyobjObjName - The name of the object that triggered the event.
                         In case of no objects assosicated with
                         failures, the value will be NULL.
             ntyobjDesc    - Description about the event/trap
             "
    ::= { blueFailureTraps0 5 }

--blueThresholdTraps group

    blueThresholdTraps0 OBJECT IDENTIFIER ::= { blueThresholdTraps 0 }


    btConditionalEvent NOTIFICATION-TYPE
    OBJECTS { ntyobjLevel,ntyobjOID,ntyobjValue,ntyobjDesc}
    STATUS  current
    DESCRIPTION
            "This trap will be sent if the threshold have been met for
            the underlaying Object.
             ntyobjLevel    - Indicate the trap priority or log level
             ntyobjObjOID  - The OID of the object that triggered the event
             ntyobjObjValue - The value of the object that triggered
                          the event at the time of event occurrence.
             trDesc     - Description about the event/trap
             "

    ::= { blueThresholdTraps0 1 }

    btCpuLoadEvent NOTIFICATION-TYPE
    OBJECTS { ntyobjLevel,ntyobjOID,ntyobjValue,ntyobjDesc}
    STATUS  current
    DESCRIPTION
            "This trap will be sent if the threshold have been met for
            the CPU usage.
             ntyobjLevel    - Indicate the trap priority or log level
             ntyobjObjOID  - The OID of the object that triggered the event
             ntyobjObjValue - The value of the object that triggered
                          the event at the time of event occurrence.
             trDesc     - Description about the event/trap
             "
    ::= { blueThresholdTraps0 2 }
    btMemSwapUsageEvent NOTIFICATION-TYPE
    OBJECTS { ntyobjLevel,ntyobjOID,ntyobjValue,ntyobjDesc}
    STATUS  current
    DESCRIPTION
            "This trap will be sent if the threshold have been met for
            the memory or swap space.
             ntyobjLevel    - Indicate the trap priority or log level
             ntyobjObjOID  - The OID of the object that triggered the event
             ntyobjObjValue - The value of the object that triggered
                          the event at the time of event occurrence.
             trDesc     - Description about the event/trap
             "
    ::= { blueThresholdTraps0 3 }

    btDiskUsageEvent NOTIFICATION-TYPE
    OBJECTS { ntyobjLevel,ntyobjOID,ntyobjValue,ntyobjDesc}
    STATUS  current
    DESCRIPTION
            "This trap will be sent if the threshold have been met for
            the Disk usage Object.
             ntyobjLevel    - Indicate the trap priority or log level
             ntyobjObjOID  - The OID of the object that triggered the event
             ntyobjObjValue - The value of the object that triggered
                          the event at the time of event occurrence.
             trDesc     - Description about the event/trap
             "
    ::= { blueThresholdTraps0 4 }

END
