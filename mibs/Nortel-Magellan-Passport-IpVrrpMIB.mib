Nortel-Magellan-Passport-IpVrrpMIB
DEFINITIONS ::= BEGIN



IMPORTS

      OBJECT-TYPE
   FROM RFC-1212

      IpAddress
   FROM RFC1155-SMI

      passportMIBs
   FROM Nortel-Magellan-Passport-UsefulDefinitionsMIB

      DisplayString,
      StorageType,
      RowStatus,
      Integer32,
      MacAddress,
      Unsigned32
   FROM Nortel-Magellan-Passport-StandardTextualConventionsMIB

      NonReplicated,
      Link
   FROM Nortel-Magellan-Passport-TextualConventionsMIB

      vrIpIndex,
      vrPpIpPortIndex,
      vrIp,
      vrPpIpPort
   FROM Nortel-Magellan-Passport-IpMIB

      vrIndex,
      vrPpIndex
   FROM Nortel-Magellan-Passport-VirtualRouterMIB;




-- LAST-UPDATED   "0002250000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     IpVrrp Enterprise MIB."

ipVrrpMIB OBJECT IDENTIFIER ::= { passportMIBs 161 }










-- Vr/<string> Ip IpVrrpPort
-- IpVrrpPort component contains attributes that define a VRRP router 
-- under this ipPort.

vrPpIpPortVrrp OBJECT IDENTIFIER ::= { vrPpIpPort 17 }



vrPpIpPortVrrpRowStatusTable OBJECT-TYPE
   SYNTAX     SEQUENCE OF VrPpIpPortVrrpRowStatusEntry
   ACCESS     not-accessible
   STATUS     mandatory
   DESCRIPTION
     "This entry controls the addition and deletion of 
      vrPpIpPortVrrp components."
::= { vrPpIpPortVrrp 1 }

vrPpIpPortVrrpRowStatusEntry OBJECT-TYPE
   SYNTAX     VrPpIpPortVrrpRowStatusEntry
   ACCESS     not-accessible
   STATUS     mandatory
   DESCRIPTION
     "A single entry in the table represents a single 
      vrPpIpPortVrrp component."
   INDEX {
      vrIndex,
      vrPpIndex,
      vrPpIpPortIndex,
      vrPpIpPortVrrpIndex }
::= { vrPpIpPortVrrpRowStatusTable 1 }

VrPpIpPortVrrpRowStatusEntry ::= SEQUENCE {
   vrPpIpPortVrrpRowStatus
      RowStatus,
   vrPpIpPortVrrpComponentName
      DisplayString,
   vrPpIpPortVrrpStorageType
      StorageType,
   vrPpIpPortVrrpIndex
      Integer32 }

vrPpIpPortVrrpRowStatus OBJECT-TYPE
   SYNTAX     RowStatus 
   ACCESS     read-write
   STATUS     mandatory
   DESCRIPTION
     "This variable is used as the basis for SNMP naming of
      vrPpIpPortVrrp components.
      These components can be added and deleted."
::= { vrPpIpPortVrrpRowStatusEntry 1 }

vrPpIpPortVrrpComponentName OBJECT-TYPE
   SYNTAX     DisplayString 
   ACCESS     read-only
   STATUS     mandatory
   DESCRIPTION
     "This variable provides the component's string name for
      use with the ASCII Console Interface"
::= { vrPpIpPortVrrpRowStatusEntry 2 }

vrPpIpPortVrrpStorageType OBJECT-TYPE
   SYNTAX     StorageType 
   ACCESS     read-only
   STATUS     mandatory
   DESCRIPTION
     "This variable represents the storage type value for the
      vrPpIpPortVrrp tables."
::= { vrPpIpPortVrrpRowStatusEntry 4 }

vrPpIpPortVrrpIndex OBJECT-TYPE
   SYNTAX     Integer32 (1..255)
   ACCESS     not-accessible
   STATUS     mandatory
   DESCRIPTION
     "This variable represents the index for the vrPpIpPortVrrp tables."
::= { vrPpIpPortVrrpRowStatusEntry 10 }

vrPpIpPortVrrpProvTable OBJECT-TYPE
   SYNTAX     SEQUENCE OF VrPpIpPortVrrpProvEntry
   ACCESS     not-accessible
   STATUS     mandatory
   DESCRIPTION
     "This group contains the provisionable attributes for the IpVrrpPort 
      component."
::= { vrPpIpPortVrrp 2 }

vrPpIpPortVrrpProvEntry OBJECT-TYPE
   SYNTAX     VrPpIpPortVrrpProvEntry
   ACCESS     not-accessible
   STATUS     mandatory
   DESCRIPTION
     "An entry in the vrPpIpPortVrrpProvTable."
   INDEX {
      vrIndex,
      vrPpIndex,
      vrPpIpPortIndex,
      vrPpIpPortVrrpIndex }
::= { vrPpIpPortVrrpProvTable 1 }

VrPpIpPortVrrpProvEntry ::= SEQUENCE {
   vrPpIpPortVrrpPriority
      Unsigned32,
   vrPpIpPortVrrpAdvertInterval
      Unsigned32,
   vrPpIpPortVrrpLinkToCriticalIp
      Link }

vrPpIpPortVrrpPriority OBJECT-TYPE
   SYNTAX     Unsigned32 (1..255)
   ACCESS     read-write
   STATUS     mandatory
   DESCRIPTION
     "This attribute specifies the priority of the IpVrrpPort in Master election. 
      Value of 0 (zero) is reserved for Master router to indicate it is releasing 
      responsibility for the virtual router. The value of 255 (decimal) is 
      reserved fro the router that owns the IP addresses associated with the 
      IpVrrpPort."
   DEFVAL     { 100 }
::= { vrPpIpPortVrrpProvEntry 1 }

vrPpIpPortVrrpAdvertInterval OBJECT-TYPE
   SYNTAX     Unsigned32 (1..255)
   ACCESS     read-write
   STATUS     mandatory
   DESCRIPTION
     "This attribute specifies the time interval between 
      ADVERTIMSEMENTS (seconds). Default is 1 second."
   DEFVAL     { 1 }
::= { vrPpIpPortVrrpProvEntry 3 }

vrPpIpPortVrrpLinkToCriticalIp OBJECT-TYPE
   SYNTAX     Link 
   ACCESS     read-write
   STATUS     mandatory
   DESCRIPTION
     "This attribute specifies the ip interface this IpVrrpPort is linked to. 
      When the ip interface it is linked to is down, the vrrp component should 
      go down."
::= { vrPpIpPortVrrpProvEntry 5 }

vrPpIpPortVrrpOperTable OBJECT-TYPE
   SYNTAX     SEQUENCE OF VrPpIpPortVrrpOperEntry
   ACCESS     not-accessible
   STATUS     mandatory
   DESCRIPTION
     "This group contains operational attributes for an IpVrrpPort component."
::= { vrPpIpPortVrrp 13 }

vrPpIpPortVrrpOperEntry OBJECT-TYPE
   SYNTAX     VrPpIpPortVrrpOperEntry
   ACCESS     not-accessible
   STATUS     mandatory
   DESCRIPTION
     "An entry in the vrPpIpPortVrrpOperTable."
   INDEX {
      vrIndex,
      vrPpIndex,
      vrPpIpPortIndex,
      vrPpIpPortVrrpIndex }
::= { vrPpIpPortVrrpOperTable 1 }

VrPpIpPortVrrpOperEntry ::= SEQUENCE {
   vrPpIpPortVrrpVirtualRouterState
      INTEGER,
   vrPpIpPortVrrpVirtualRouterPhysicalAddress
      MacAddress }

vrPpIpPortVrrpVirtualRouterState OBJECT-TYPE
   SYNTAX     INTEGER  {
                 initialize(0),
                 backup(1),
                 master(2) }
   ACCESS     read-only
   STATUS     mandatory
   DESCRIPTION
     "This attribute indicates the state of this IpVrrpPort. It will be one the 
      three states: initialize, backup and master."
   DEFVAL     { initialize }
::= { vrPpIpPortVrrpOperEntry 1 }

vrPpIpPortVrrpVirtualRouterPhysicalAddress OBJECT-TYPE
   SYNTAX     MacAddress (SIZE (6))
   ACCESS     read-only
   STATUS     mandatory
   DESCRIPTION
     "This attributes indicates the Mac address of the IpVrrpPort. The address 
      is 00 00 5e 00 01 vrrpId"
::= { vrPpIpPortVrrpOperEntry 2 }

vrPpIpPortVrrpAdminControlTable OBJECT-TYPE
   SYNTAX     SEQUENCE OF VrPpIpPortVrrpAdminControlEntry
   ACCESS     not-accessible
   STATUS     mandatory
   DESCRIPTION
     "This group includes the Administrative Control attribute. This 
      attribute defines the current administrative state of this component."
::= { vrPpIpPortVrrp 30 }

vrPpIpPortVrrpAdminControlEntry OBJECT-TYPE
   SYNTAX     VrPpIpPortVrrpAdminControlEntry
   ACCESS     not-accessible
   STATUS     mandatory
   DESCRIPTION
     "An entry in the vrPpIpPortVrrpAdminControlTable."
   INDEX {
      vrIndex,
      vrPpIndex,
      vrPpIpPortIndex,
      vrPpIpPortVrrpIndex }
::= { vrPpIpPortVrrpAdminControlTable 1 }

VrPpIpPortVrrpAdminControlEntry ::= SEQUENCE {
   vrPpIpPortVrrpSnmpAdminStatus
      INTEGER }

vrPpIpPortVrrpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrPpIpPortVrrpAdminControlEntry 1 }

vrPpIpPortVrrpOperStatusTable OBJECT-TYPE
   SYNTAX     SEQUENCE OF VrPpIpPortVrrpOperStatusEntry
   ACCESS     not-accessible
   STATUS     mandatory
   DESCRIPTION
     "This group includes the Operational Status attribute. This attribute 
      defines the current operational state of this component."
::= { vrPpIpPortVrrp 31 }

vrPpIpPortVrrpOperStatusEntry OBJECT-TYPE
   SYNTAX     VrPpIpPortVrrpOperStatusEntry
   ACCESS     not-accessible
   STATUS     mandatory
   DESCRIPTION
     "An entry in the vrPpIpPortVrrpOperStatusTable."
   INDEX {
      vrIndex,
      vrPpIndex,
      vrPpIpPortIndex,
      vrPpIpPortVrrpIndex }
::= { vrPpIpPortVrrpOperStatusTable 1 }

VrPpIpPortVrrpOperStatusEntry ::= SEQUENCE {
   vrPpIpPortVrrpSnmpOperStatus
      INTEGER }

vrPpIpPortVrrpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpIpPortVrrpOperStatusEntry 1 }

vrPpIpPortVrrpStateTable OBJECT-TYPE
   SYNTAX     SEQUENCE OF VrPpIpPortVrrpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpIpPortVrrp 32 }

vrPpIpPortVrrpStateEntry OBJECT-TYPE
   SYNTAX     VrPpIpPortVrrpStateEntry
   ACCESS     not-accessible
   STATUS     mandatory
   DESCRIPTION
     "An entry in the vrPpIpPortVrrpStateTable."
   INDEX {
      vrIndex,
      vrPpIndex,
      vrPpIpPortIndex,
      vrPpIpPortVrrpIndex }
::= { vrPpIpPortVrrpStateTable 1 }

VrPpIpPortVrrpStateEntry ::= SEQUENCE {
   vrPpIpPortVrrpAdminState
      INTEGER,
   vrPpIpPortVrrpOperationalState
      INTEGER,
   vrPpIpPortVrrpUsageState
      INTEGER }

vrPpIpPortVrrpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpIpPortVrrpStateEntry 1 }

vrPpIpPortVrrpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpIpPortVrrpStateEntry 2 }

vrPpIpPortVrrpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpIpPortVrrpStateEntry 3 }

vrPpIpPortVrrpIpAddressesTable OBJECT-TYPE
   SYNTAX     SEQUENCE OF VrPpIpPortVrrpIpAddressesEntry
   ACCESS     not-accessible
   STATUS     mandatory
   DESCRIPTION
     "This attribute specifies one or more IP addresses associated with this 
      IpVrrpPort."
::= { vrPpIpPortVrrp 700 }

vrPpIpPortVrrpIpAddressesEntry OBJECT-TYPE
   SYNTAX     VrPpIpPortVrrpIpAddressesEntry
   ACCESS     not-accessible
   STATUS     mandatory
   DESCRIPTION
     "An entry in the vrPpIpPortVrrpIpAddressesTable."
   INDEX {
      vrIndex,
      vrPpIndex,
      vrPpIpPortIndex,
      vrPpIpPortVrrpIndex,
      vrPpIpPortVrrpIpAddressesValue }
::= { vrPpIpPortVrrpIpAddressesTable 1 }

VrPpIpPortVrrpIpAddressesEntry ::= SEQUENCE {
   vrPpIpPortVrrpIpAddressesValue
      IpAddress,
   vrPpIpPortVrrpIpAddressesRowStatus
      RowStatus }

vrPpIpPortVrrpIpAddressesValue OBJECT-TYPE
   SYNTAX     IpAddress 
   ACCESS     read-write
   STATUS     mandatory
   DESCRIPTION
     "This variable represents both the value and the index for the
      vrPpIpPortVrrpIpAddressesTable."
::= { vrPpIpPortVrrpIpAddressesEntry 1 }

vrPpIpPortVrrpIpAddressesRowStatus OBJECT-TYPE
   SYNTAX     RowStatus 
   ACCESS     write-only
   STATUS     mandatory
   DESCRIPTION
     "This variable is used to control the addition and deletion 
      of individual values of the vrPpIpPortVrrpIpAddressesTable."
::= { vrPpIpPortVrrpIpAddressesEntry 2 }


-- The CriticalIp component defines a local IP interface for an IpVrrpPort. 
-- It is added under an ipPort and then linked to a IpVrrpPort component. 
-- When this interface goes down, the IpVrrpPort is considered inactive, 
-- therefor, can not be elected as master.

vrPpIpPortCriticalIp OBJECT IDENTIFIER ::= { vrPpIpPort 18 }



vrPpIpPortCriticalIpRowStatusTable OBJECT-TYPE
   SYNTAX     SEQUENCE OF VrPpIpPortCriticalIpRowStatusEntry
   ACCESS     not-accessible
   STATUS     mandatory
   DESCRIPTION
     "This entry controls the addition and deletion of 
      vrPpIpPortCriticalIp components."
::= { vrPpIpPortCriticalIp 1 }

vrPpIpPortCriticalIpRowStatusEntry OBJECT-TYPE
   SYNTAX     VrPpIpPortCriticalIpRowStatusEntry
   ACCESS     not-accessible
   STATUS     mandatory
   DESCRIPTION
     "A single entry in the table represents a single 
      vrPpIpPortCriticalIp component."
   INDEX {
      vrIndex,
      vrPpIndex,
      vrPpIpPortIndex,
      vrPpIpPortCriticalIpIndex }
::= { vrPpIpPortCriticalIpRowStatusTable 1 }

VrPpIpPortCriticalIpRowStatusEntry ::= SEQUENCE {
   vrPpIpPortCriticalIpRowStatus
      RowStatus,
   vrPpIpPortCriticalIpComponentName
      DisplayString,
   vrPpIpPortCriticalIpStorageType
      StorageType,
   vrPpIpPortCriticalIpIndex
      Integer32 }

vrPpIpPortCriticalIpRowStatus OBJECT-TYPE
   SYNTAX     RowStatus 
   ACCESS     read-write
   STATUS     mandatory
   DESCRIPTION
     "This variable is used as the basis for SNMP naming of
      vrPpIpPortCriticalIp components.
      These components can be added and deleted."
::= { vrPpIpPortCriticalIpRowStatusEntry 1 }

vrPpIpPortCriticalIpComponentName OBJECT-TYPE
   SYNTAX     DisplayString 
   ACCESS     read-only
   STATUS     mandatory
   DESCRIPTION
     "This variable provides the component's string name for
      use with the ASCII Console Interface"
::= { vrPpIpPortCriticalIpRowStatusEntry 2 }

vrPpIpPortCriticalIpStorageType OBJECT-TYPE
   SYNTAX     StorageType 
   ACCESS     read-only
   STATUS     mandatory
   DESCRIPTION
     "This variable represents the storage type value for the
      vrPpIpPortCriticalIp tables."
::= { vrPpIpPortCriticalIpRowStatusEntry 4 }

vrPpIpPortCriticalIpIndex OBJECT-TYPE
   SYNTAX     Integer32 (1..255)
   ACCESS     not-accessible
   STATUS     mandatory
   DESCRIPTION
     "This variable represents the index for the vrPpIpPortCriticalIp tables."
::= { vrPpIpPortCriticalIpRowStatusEntry 10 }

vrPpIpPortCriticalIpProvTable OBJECT-TYPE
   SYNTAX     SEQUENCE OF VrPpIpPortCriticalIpProvEntry
   ACCESS     not-accessible
   STATUS     mandatory
   DESCRIPTION
     "This group contains the provisionable attributes for the CriticalIp 
      component."
::= { vrPpIpPortCriticalIp 24 }

vrPpIpPortCriticalIpProvEntry OBJECT-TYPE
   SYNTAX     VrPpIpPortCriticalIpProvEntry
   ACCESS     not-accessible
   STATUS     mandatory
   DESCRIPTION
     "An entry in the vrPpIpPortCriticalIpProvTable."
   INDEX {
      vrIndex,
      vrPpIndex,
      vrPpIpPortIndex,
      vrPpIpPortCriticalIpIndex }
::= { vrPpIpPortCriticalIpProvTable 1 }

VrPpIpPortCriticalIpProvEntry ::= SEQUENCE {
   vrPpIpPortCriticalIpLinkToVrrp
      Link }

vrPpIpPortCriticalIpLinkToVrrp OBJECT-TYPE
   SYNTAX     Link 
   ACCESS     read-write
   STATUS     mandatory
   DESCRIPTION
     "This attribute defines which IpVrrpPort this CriticalIp interface belongs 
      to. When this interface goes down, the IpVrrpPort that this Critical Ip 
      interface is associated with is inactive and can not be elected as master."
::= { vrPpIpPortCriticalIpProvEntry 1 }


-- Vr/<string> Ip IpVrrpVr
-- The IpVrrpPort component supports the control protocol of VRRP 
-- which provides the dynamic election of a master VRRP router among 
-- multiple VRRP routers on a LAN. Locking this component will disable 
-- all IpVrrpPorts provisioned under Ip ports.

vrIpIpVrrp OBJECT IDENTIFIER ::= { vrIp 25 }



vrIpIpVrrpRowStatusTable OBJECT-TYPE
   SYNTAX     SEQUENCE OF VrIpIpVrrpRowStatusEntry
   ACCESS     not-accessible
   STATUS     mandatory
   DESCRIPTION
     "This entry controls the addition and deletion of 
      vrIpIpVrrp components."
::= { vrIpIpVrrp 1 }

vrIpIpVrrpRowStatusEntry OBJECT-TYPE
   SYNTAX     VrIpIpVrrpRowStatusEntry
   ACCESS     not-accessible
   STATUS     mandatory
   DESCRIPTION
     "A single entry in the table represents a single 
      vrIpIpVrrp component."
   INDEX {
      vrIndex,
      vrIpIndex,
      vrIpIpVrrpIndex }
::= { vrIpIpVrrpRowStatusTable 1 }

VrIpIpVrrpRowStatusEntry ::= SEQUENCE {
   vrIpIpVrrpRowStatus
      RowStatus,
   vrIpIpVrrpComponentName
      DisplayString,
   vrIpIpVrrpStorageType
      StorageType,
   vrIpIpVrrpIndex
      NonReplicated }

vrIpIpVrrpRowStatus OBJECT-TYPE
   SYNTAX     RowStatus 
   ACCESS     read-write
   STATUS     mandatory
   DESCRIPTION
     "This variable is used as the basis for SNMP naming of
      vrIpIpVrrp components.
      These components can be added and deleted."
::= { vrIpIpVrrpRowStatusEntry 1 }

vrIpIpVrrpComponentName OBJECT-TYPE
   SYNTAX     DisplayString 
   ACCESS     read-only
   STATUS     mandatory
   DESCRIPTION
     "This variable provides the component's string name for
      use with the ASCII Console Interface"
::= { vrIpIpVrrpRowStatusEntry 2 }

vrIpIpVrrpStorageType OBJECT-TYPE
   SYNTAX     StorageType 
   ACCESS     read-only
   STATUS     mandatory
   DESCRIPTION
     "This variable represents the storage type value for the
      vrIpIpVrrp tables."
::= { vrIpIpVrrpRowStatusEntry 4 }

vrIpIpVrrpIndex OBJECT-TYPE
   SYNTAX     NonReplicated 
   ACCESS     not-accessible
   STATUS     mandatory
   DESCRIPTION
     "This variable represents the index for the vrIpIpVrrp tables."
::= { vrIpIpVrrpRowStatusEntry 10 }

vrIpIpVrrpAdminControlTable OBJECT-TYPE
   SYNTAX     SEQUENCE OF VrIpIpVrrpAdminControlEntry
   ACCESS     not-accessible
   STATUS     mandatory
   DESCRIPTION
     "This group includes the Administrative Control attribute. This 
      attribute defines the current administrative state of this component."
::= { vrIpIpVrrp 30 }

vrIpIpVrrpAdminControlEntry OBJECT-TYPE
   SYNTAX     VrIpIpVrrpAdminControlEntry
   ACCESS     not-accessible
   STATUS     mandatory
   DESCRIPTION
     "An entry in the vrIpIpVrrpAdminControlTable."
   INDEX {
      vrIndex,
      vrIpIndex,
      vrIpIpVrrpIndex }
::= { vrIpIpVrrpAdminControlTable 1 }

VrIpIpVrrpAdminControlEntry ::= SEQUENCE {
   vrIpIpVrrpSnmpAdminStatus
      INTEGER }

vrIpIpVrrpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpIpVrrpAdminControlEntry 1 }

vrIpIpVrrpOperStatusTable OBJECT-TYPE
   SYNTAX     SEQUENCE OF VrIpIpVrrpOperStatusEntry
   ACCESS     not-accessible
   STATUS     mandatory
   DESCRIPTION
     "This group includes the Operational Status attribute. This attribute 
      defines the current operational state of this component."
::= { vrIpIpVrrp 31 }

vrIpIpVrrpOperStatusEntry OBJECT-TYPE
   SYNTAX     VrIpIpVrrpOperStatusEntry
   ACCESS     not-accessible
   STATUS     mandatory
   DESCRIPTION
     "An entry in the vrIpIpVrrpOperStatusTable."
   INDEX {
      vrIndex,
      vrIpIndex,
      vrIpIpVrrpIndex }
::= { vrIpIpVrrpOperStatusTable 1 }

VrIpIpVrrpOperStatusEntry ::= SEQUENCE {
   vrIpIpVrrpSnmpOperStatus
      INTEGER }

vrIpIpVrrpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpIpVrrpOperStatusEntry 1 }

vrIpIpVrrpStateTable OBJECT-TYPE
   SYNTAX     SEQUENCE OF VrIpIpVrrpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpIpVrrp 32 }

vrIpIpVrrpStateEntry OBJECT-TYPE
   SYNTAX     VrIpIpVrrpStateEntry
   ACCESS     not-accessible
   STATUS     mandatory
   DESCRIPTION
     "An entry in the vrIpIpVrrpStateTable."
   INDEX {
      vrIndex,
      vrIpIndex,
      vrIpIpVrrpIndex }
::= { vrIpIpVrrpStateTable 1 }

VrIpIpVrrpStateEntry ::= SEQUENCE {
   vrIpIpVrrpAdminState
      INTEGER,
   vrIpIpVrrpOperationalState
      INTEGER,
   vrIpIpVrrpUsageState
      INTEGER }

vrIpIpVrrpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpIpVrrpStateEntry 1 }

vrIpIpVrrpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpIpVrrpStateEntry 2 }

vrIpIpVrrpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpIpVrrpStateEntry 3 }




-- 
-- Version and Compliance statements
-- 



-- Object-Group Statement:
-- A list of all current accessible leaf objects.

-- OBJECTS { vrIpIpVrrpRowStatus,
--           vrPpIpPortVrrpLinkToCriticalIp,
--           vrPpIpPortVrrpOperationalState,
--           vrPpIpPortVrrpVirtualRouterState,
--           vrPpIpPortCriticalIpComponentName,
--           vrPpIpPortVrrpIpAddressesRowStatus,
--           vrPpIpPortVrrpPriority,
--           vrIpIpVrrpSnmpOperStatus,
--           vrPpIpPortCriticalIpStorageType,
--           vrPpIpPortVrrpAdvertInterval,
--           vrIpIpVrrpSnmpAdminStatus,
--           vrPpIpPortVrrpAdminState,
--           vrPpIpPortCriticalIpRowStatus,
--           vrPpIpPortVrrpIpAddressesValue,
--           vrIpIpVrrpComponentName,
--           vrPpIpPortVrrpRowStatus,
--           vrPpIpPortVrrpSnmpAdminStatus,
--           vrIpIpVrrpUsageState,
--           vrIpIpVrrpOperationalState,
--           vrPpIpPortVrrpSnmpOperStatus,
--           vrPpIpPortVrrpUsageState,
--           vrPpIpPortVrrpComponentName,
--           vrIpIpVrrpAdminState,
--           vrPpIpPortCriticalIpLinkToVrrp,
--           vrIpIpVrrpStorageType,
--           vrPpIpPortVrrpStorageType,
--           vrPpIpPortVrrpVirtualRouterPhysicalAddress }
-- STATUS  mandatory
-- DESCRIPTION
--   "A list of all current accessible leaf objects."

ipVrrpGroup OBJECT IDENTIFIER ::= { ipVrrpMIB 1 }
ipVrrpGroupBG OBJECT IDENTIFIER ::= { ipVrrpGroup 7 }
ipVrrpGroupBG00 OBJECT IDENTIFIER ::= { ipVrrpGroupBG 1 }
ipVrrpGroupBG00A OBJECT IDENTIFIER ::= { ipVrrpGroupBG00 2 }



-- Agent-Capabilities Statement:

-- PRODUCT-RELEASE "Passport Release 7.0 IpVrrp."
-- STATUS          mandatory
-- DESCRIPTION     "IpVrrp MIB: MIB Version BG00A,
--                  Software Version BG00S4C."
-- SUPPORTS        Nortel-Magellan-Passport-IpVrrpMIB
--    INCLUDES     { ipVrrpGroupBG00A }

ipVrrpCapabilities OBJECT IDENTIFIER ::= { ipVrrpMIB 3 }
ipVrrpCapabilitiesBG OBJECT IDENTIFIER ::= { ipVrrpCapabilities 7 }
ipVrrpCapabilitiesBG00 OBJECT IDENTIFIER ::= { ipVrrpCapabilitiesBG 1 }
ipVrrpCapabilitiesBG00A OBJECT IDENTIFIER ::= { ipVrrpCapabilitiesBG00 2 }





END
