Nortel-MsCarrier-MscPassport-BaseShelfMIB
DEFINITIONS ::= BEGIN



IMPORTS

      OBJECT-TYPE
   FROM RFC-1212

      mscPassportMIBs,
      mscComponents
   FROM Nortel-MsCarrier-MscPassport-UsefulDefinitionsMIB

      RowPointer,
      DisplayString,
      StorageType,
      RowStatus,
      Gauge32,
      Integer32,
      Unsigned32
   FROM Nortel-MsCarrier-MscPassport-StandardTextualConventionsMIB

      AsciiString,
      Hex,
      NonReplicated,
      Link,
      ExtendedAsciiString
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     BaseShelf Enterprise MIB."

baseShelfMIB OBJECT IDENTIFIER ::= { mscPassportMIBs 146 }










-- Shelf
-- There is one Shelf component per module. It is the parent 
-- component of the hardware components (which include Card and 
-- Bus components).

mscShelf OBJECT IDENTIFIER ::= { mscComponents 13 }



mscShelfRowStatusTable OBJECT-TYPE
   SYNTAX     SEQUENCE OF MscShelfRowStatusEntry
   ACCESS     not-accessible
   STATUS     mandatory
   DESCRIPTION
     "This entry controls the addition and deletion of 
      mscShelf components."
::= { mscShelf 1 }

mscShelfRowStatusEntry OBJECT-TYPE
   SYNTAX     MscShelfRowStatusEntry
   ACCESS     not-accessible
   STATUS     mandatory
   DESCRIPTION
     "A single entry in the table represents a single 
      mscShelf component."
   INDEX {
      mscShelfIndex }
::= { mscShelfRowStatusTable 1 }

MscShelfRowStatusEntry ::= SEQUENCE {
   mscShelfRowStatus
      RowStatus,
   mscShelfComponentName
      DisplayString,
   mscShelfStorageType
      StorageType,
   mscShelfIndex
      NonReplicated }

mscShelfRowStatus OBJECT-TYPE
   SYNTAX     RowStatus 
   ACCESS     read-only
   STATUS     mandatory
   DESCRIPTION
     "This variable is used as the basis for SNMP naming of
      mscShelf components.
      These components cannot be added nor deleted."
::= { mscShelfRowStatusEntry 1 }

mscShelfComponentName OBJECT-TYPE
   SYNTAX     DisplayString 
   ACCESS     read-only
   STATUS     mandatory
   DESCRIPTION
     "This variable provides the component's string name for
      use with the ASCII Console Interface"
::= { mscShelfRowStatusEntry 2 }

mscShelfStorageType OBJECT-TYPE
   SYNTAX     StorageType 
   ACCESS     read-only
   STATUS     mandatory
   DESCRIPTION
     "This variable represents the storage type value for the
      mscShelf tables."
::= { mscShelfRowStatusEntry 4 }

mscShelfIndex OBJECT-TYPE
   SYNTAX     NonReplicated 
   ACCESS     not-accessible
   STATUS     mandatory
   DESCRIPTION
     "This variable represents the index for the mscShelf tables."
::= { mscShelfRowStatusEntry 10 }

mscShelfProvTable OBJECT-TYPE
   SYNTAX     SEQUENCE OF MscShelfProvEntry
   ACCESS     not-accessible
   STATUS     mandatory
   DESCRIPTION
     "This group contains the provisionable attributes for the Shelf 
      component."
::= { mscShelf 10 }

mscShelfProvEntry OBJECT-TYPE
   SYNTAX     MscShelfProvEntry
   ACCESS     not-accessible
   STATUS     mandatory
   DESCRIPTION
     "An entry in the mscShelfProvTable."
   INDEX {
      mscShelfIndex }
::= { mscShelfProvTable 1 }

MscShelfProvEntry ::= SEQUENCE {
   mscShelfCommentText
      AsciiString }

mscShelfCommentText OBJECT-TYPE
   SYNTAX     AsciiString (SIZE (0..80))
   ACCESS     read-write
   STATUS     mandatory
   DESCRIPTION
     "This is an arbitrary string that can be used to specify the location of 
      the module. It is not used by the system."
   DEFVAL     { ''H }  -- ""
::= { mscShelfProvEntry 1 }

mscShelfOperTable OBJECT-TYPE
   SYNTAX     SEQUENCE OF MscShelfOperEntry
   ACCESS     not-accessible
   STATUS     mandatory
   DESCRIPTION
     "This group contains the operational attributes for the Shelf 
      component."
::= { mscShelf 11 }

mscShelfOperEntry OBJECT-TYPE
   SYNTAX     MscShelfOperEntry
   ACCESS     not-accessible
   STATUS     mandatory
   DESCRIPTION
     "An entry in the mscShelfOperTable."
   INDEX {
      mscShelfIndex }
::= { mscShelfOperTable 1 }

MscShelfOperEntry ::= SEQUENCE {
   mscShelfBusOperatingMode
      INTEGER,
   mscShelfHardwareFailures
      OCTET STRING,
   mscShelfNumberOfSlots
      Unsigned32,
   mscShelfShelfType
      INTEGER,
   mscShelfBackplaneOperatingMode
      INTEGER }

mscShelfBusOperatingMode OBJECT-TYPE
   SYNTAX     INTEGER  {
                 noBus(0),
                 singleBusX(1),
                 singleBusY(2),
                 dualBus(3) }
   ACCESS     read-only
   STATUS     obsolete
   DESCRIPTION
     "This attribute indicates the current backplane bus operating mode:
      noBus            No bus is in service now.
      singleBusX     The shelf is running on bus X only.
      singleBusY     The shelf is running on bus Y only.
      dualBus         The shelf is running on bus X and bus Y."
::= { mscShelfOperEntry 1 }

mscShelfHardwareFailures OBJECT-TYPE
   SYNTAX     OCTET STRING (SIZE (2))
   ACCESS     read-only
   STATUS     mandatory
   DESCRIPTION
     "This attribute indicates which type of components have failed.The 
      hardware's fault detection system can report the following kinds of 
      component failures: card, power converter, cooling unit, terminator 
      card, fan, input power feed or fabric card failures. 
      card   - The passport card has failed.
      powerConverter  - The power converter has failed.
      coolingUnit - The cooling unit has failed.
      terminatorCard - The terminator card has failed.
      The following types only apply to fabric-based shelf:
      fan - The fan has failed.
      inputPowerFeed - The input power feed has failed.
      fabricCard - The fabric card has failed.
      macAddressCard - Mac address card has failed.
      alarmBitsCard - Alarm bit card has failed.

      Description of bits:
      card(0)
      powerConverter(1)
      coolingUnit(2)
      terminatorCard(3)
      fan(4)
      powerSupply(5)
      fabricCard(6)
      macAddressCard(7)
      alarmBitsCard(8)"
::= { mscShelfOperEntry 2 }

mscShelfNumberOfSlots OBJECT-TYPE
   SYNTAX     Unsigned32 (1..16)
   ACCESS     read-only
   STATUS     mandatory
   DESCRIPTION
     "This attribute specifies the number of slots for this shelf."
::= { mscShelfOperEntry 3 }

mscShelfShelfType OBJECT-TYPE
   SYNTAX     INTEGER  {
                 busBasedShelf(0),
                 fabricBasedShelf(1) }
   ACCESS     read-only
   STATUS     mandatory
   DESCRIPTION
     "This attribute displays the shelf type:
      busBasedShelf		-  bus based backplane shelf.
      fabricBasedShelf		-  fabric base backplane shelf."
::= { mscShelfOperEntry 5 }

mscShelfBackplaneOperatingMode OBJECT-TYPE
   SYNTAX     INTEGER  {
                 noBus(0),
                 singleBusX(1),
                 singleBusY(2),
                 dualBus(3),
                 noFabric(4),
                 singleFabricX(5),
                 singleFabricY(6),
                 dualFabric(7) }
   ACCESS     read-only
   STATUS     mandatory
   DESCRIPTION
     "This attribute indicates the current backplane operating mode. On 
      the fabric-based shelf:
      noFabric            - No fabric is in service now.
      singleFabricX    - The shelf is running on fabric X only.
      singleFabricY    - The shelf is running on fabric Y only.
      dualFabric        - The shelf is running on fabric X and fabric Y.
      On the bus-based shelf:
      noBus		 		 - No bus is in service now.
      singleBusX		  	- The shelf is running on bus X only.
      singleBusY        - The shelf is running on bus Y only.
      dualBus             - The shelf is running on bus X and bus Y"
::= { mscShelfOperEntry 7 }


-- Shelf Card/n
-- The Card component is a subcomponent of the Shelf component. 
-- There are a maximum of 16 Card components defined, one 
-- corresponding to each phsyical card slot. This is necessary in order 
-- to be able to reflect which processor card is present in each slot at 
-- any time.  
-- For a Passport Model-50 it is possible to have Card components not 
-- defined for instances 5 through 15.  This is can be accomplished via 
-- the Start-Up initial provisioning system.   It is, however,  possible to 
-- add a Card component since it may be desireable to move a CP 
-- from a Passport Model-50 to a Passport Model-160.  This move of 
-- the CP would result in  adding the provisioning information 
-- associated with the other processor cards instead of starting from 
-- scratch.  
-- It is however not possible to delete a Card component per se, but its 
-- type can be changed to "None".

mscShelfCard OBJECT IDENTIFIER ::= { mscShelf 2 }



mscShelfCardRowStatusTable OBJECT-TYPE
   SYNTAX     SEQUENCE OF MscShelfCardRowStatusEntry
   ACCESS     not-accessible
   STATUS     mandatory
   DESCRIPTION
     "This entry controls the addition and deletion of 
      mscShelfCard components."
::= { mscShelfCard 1 }

mscShelfCardRowStatusEntry OBJECT-TYPE
   SYNTAX     MscShelfCardRowStatusEntry
   ACCESS     not-accessible
   STATUS     mandatory
   DESCRIPTION
     "A single entry in the table represents a single 
      mscShelfCard component."
   INDEX {
      mscShelfIndex,
      mscShelfCardIndex }
::= { mscShelfCardRowStatusTable 1 }

MscShelfCardRowStatusEntry ::= SEQUENCE {
   mscShelfCardRowStatus
      RowStatus,
   mscShelfCardComponentName
      DisplayString,
   mscShelfCardStorageType
      StorageType,
   mscShelfCardIndex
      Integer32 }

mscShelfCardRowStatus OBJECT-TYPE
   SYNTAX     RowStatus 
   ACCESS     read-write
   STATUS     mandatory
   DESCRIPTION
     "This variable is used as the basis for SNMP naming of
      mscShelfCard components.
      These components can be added."
::= { mscShelfCardRowStatusEntry 1 }

mscShelfCardComponentName OBJECT-TYPE
   SYNTAX     DisplayString 
   ACCESS     read-only
   STATUS     mandatory
   DESCRIPTION
     "This variable provides the component's string name for
      use with the ASCII Console Interface"
::= { mscShelfCardRowStatusEntry 2 }

mscShelfCardStorageType OBJECT-TYPE
   SYNTAX     StorageType 
   ACCESS     read-only
   STATUS     mandatory
   DESCRIPTION
     "This variable represents the storage type value for the
      mscShelfCard tables."
::= { mscShelfCardRowStatusEntry 4 }

mscShelfCardIndex OBJECT-TYPE
   SYNTAX     Integer32 (0..15)
   ACCESS     not-accessible
   STATUS     mandatory
   DESCRIPTION
     "This variable represents the index for the mscShelfCard tables."
::= { mscShelfCardRowStatusEntry 10 }

mscShelfCardProvTable OBJECT-TYPE
   SYNTAX     SEQUENCE OF MscShelfCardProvEntry
   ACCESS     not-accessible
   STATUS     mandatory
   DESCRIPTION
     "This group contains the provisionable attributes for the Card 
      component."
::= { mscShelfCard 10 }

mscShelfCardProvEntry OBJECT-TYPE
   SYNTAX     MscShelfCardProvEntry
   ACCESS     not-accessible
   STATUS     mandatory
   DESCRIPTION
     "An entry in the mscShelfCardProvTable."
   INDEX {
      mscShelfIndex,
      mscShelfCardIndex }
::= { mscShelfCardProvTable 1 }

MscShelfCardProvEntry ::= SEQUENCE {
   mscShelfCardCardType
      INTEGER,
   mscShelfCardSparingConnection
      INTEGER,
   mscShelfCardCommentText
      AsciiString }

mscShelfCardCardType OBJECT-TYPE
   SYNTAX     INTEGER  {
                 cP(0),
                 v11(1),
                 v35(2),
                 dS1(3),
                 dS1V(4),
                 dS3(5),
                 e1(6),
                 e1V(7),
                 e3(8),
                 none(9),
                 n1pFddiMultiMode(10),
                 n4pTokenRing(11),
                 n6pEth10BaseT(12),
                 dS1C(13),
                 e1C(14),
                 n3pE3Atm(15),
                 n3pDS3Atm(16),
                 n3pOC3MmAtm(17),
                 n3pOC3SmAtm(19),
                 n3pE1Atm(20),
                 n3pDS1Atm(21),
                 j2MV(22),
                 n4pEthAui(23),
                 n1pFddiSingleMode(24),
                 n1pDS1V(25),
                 n1pE1V(26),
                 n2pJ6MAtm(27),
                 hSSI(33),
                 n8pDS1(34),
                 cFP1(35),
                 dEV1(36),
                 cFP2(37),
                 dEV2(38),
                 n4pDS1Aal1(39),
                 n4pE1Aal1(40),
                 n1pDS3C(41),
                 ilsForwarder(42),
                 n8pDS1Atm(43),
                 n8pE1Atm(44),
                 n1pE1Mvp(45),
                 n1pDS1Mvp(46),
                 n1pTTC2mMvp(47),
                 n1pDS3cAal(51),
                 n2pDS3cAal(52),
                 n12mVspAal(53),
                 n2pEth100BaseT(54),
                 n2pOC3MmAtm2(55),
                 n2pOC3SmAtm2(56),
                 n3pDS3Atm2(57),
                 n3pE3Atm2(58),
                 cPeD(59),
                 cPeE(60),
                 n4pOC3SmIrAtm(61),
                 n4pOC3MmAtm(62),
                 n12pDS3Atm(63),
                 n12pE3Atm(64),
                 n1pOC12SmLrAtm(65),
                 n1pE1Mvpe(66),
                 n1pDS1Mvpe(67),
                 n1pTTC2mMvpe(68),
                 n32pDS1Msa(69),
                 n32pDS1MsaMt(70),
                 n32pDS1MsaMtp(71),
                 n32pDS1MsaSt(72),
                 n32pDS1MsaStp(73),
                 n32pE1Aal(74),
                 n1pOC48SmSrAtm(75),
                 n4pDS3Ch(76),
                 n4pDS3ChAtm(77),
                 n1pSTM1ChSmIr(78),
                 n1pSTM1ChSmIrAtm(79),
                 n4pOC12SmIrAtm(80),
                 n4pOC12SmLrAtm(81),
                 n12mPcusp(82),
                 n32pE1Msa(84),
                 n32pE1MsaMt(85),
                 n32pE1MsaMtp(86),
                 n32pE1MsaSt(87),
                 n32pE1MsaStp(88) }
   ACCESS     read-write
   STATUS     mandatory
   DESCRIPTION
     "This is the type of card expected in this slot. Specifying a card type 
      here has the effect of configuring a card to run in this slot. A value 
      of none means that no card is configured to run in this slot."
   DEFVAL     { none }
::= { mscShelfCardProvEntry 1 }

mscShelfCardSparingConnection OBJECT-TYPE
   SYNTAX     INTEGER  {
                 notApplicable(0),
                 mainA(1),
                 mainB(2),
                 mainC(3),
                 mainD(4),
                 mainE(5),
                 mainF(6),
                 spare(16) }
   ACCESS     read-write
   STATUS     mandatory
   DESCRIPTION
     "This attribute contains the identification of the 1 for N sparing panel 
      group of connectors to which the card is connected. This 
      identification should coincide with the label located on the sparing 
      panel."
   DEFVAL     { notApplicable }
::= { mscShelfCardProvEntry 2 }

mscShelfCardCommentText OBJECT-TYPE
   SYNTAX     AsciiString (SIZE (0..80))
   ACCESS     read-write
   STATUS     mandatory
   DESCRIPTION
     "This is an arbitrary string that can be used to specify the location of 
      the sparing panel."
   DEFVAL     { ''H }  -- ""
::= { mscShelfCardProvEntry 4 }

mscShelfCardStateTable OBJECT-TYPE
   SYNTAX     SEQUENCE OF MscShelfCardStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { mscShelfCard 11 }

mscShelfCardStateEntry OBJECT-TYPE
   SYNTAX     MscShelfCardStateEntry
   ACCESS     not-accessible
   STATUS     mandatory
   DESCRIPTION
     "An entry in the mscShelfCardStateTable."
   INDEX {
      mscShelfIndex,
      mscShelfCardIndex }
::= { mscShelfCardStateTable 1 }

MscShelfCardStateEntry ::= SEQUENCE {
   mscShelfCardAdminState
      INTEGER,
   mscShelfCardOperationalState
      INTEGER,
   mscShelfCardUsageState
      INTEGER,
   mscShelfCardAvailabilityStatus
      OCTET STRING,
   mscShelfCardProceduralStatus
      OCTET STRING,
   mscShelfCardControlStatus
      OCTET STRING,
   mscShelfCardAlarmStatus
      OCTET STRING,
   mscShelfCardStandbyStatus
      INTEGER,
   mscShelfCardUnknownStatus
      INTEGER }

mscShelfCardAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscShelfCardStateEntry 1 }

mscShelfCardOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscShelfCardStateEntry 2 }

mscShelfCardUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscShelfCardStateEntry 3 }

mscShelfCardAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { mscShelfCardStateEntry 4 }

mscShelfCardProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscShelfCardStateEntry 5 }

mscShelfCardControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscShelfCardStateEntry 6 }

mscShelfCardAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscShelfCardStateEntry 7 }

mscShelfCardStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscShelfCardStateEntry 8 }

mscShelfCardUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscShelfCardStateEntry 9 }

mscShelfCardOperTable OBJECT-TYPE
   SYNTAX     SEQUENCE OF MscShelfCardOperEntry
   ACCESS     not-accessible
   STATUS     mandatory
   DESCRIPTION
     "This group contains the operational attributes that reflect the current 
      status of the card."
::= { mscShelfCard 12 }

mscShelfCardOperEntry OBJECT-TYPE
   SYNTAX     MscShelfCardOperEntry
   ACCESS     not-accessible
   STATUS     mandatory
   DESCRIPTION
     "An entry in the mscShelfCardOperTable."
   INDEX {
      mscShelfIndex,
      mscShelfCardIndex }
::= { mscShelfCardOperTable 1 }

MscShelfCardOperEntry ::= SEQUENCE {
   mscShelfCardCurrentLP
      RowPointer,
   mscShelfCardFailureCause
      INTEGER,
   mscShelfCardSelfTestFault
      INTEGER,
   mscShelfCardSparingConnectionStatus
      INTEGER,
   mscShelfCardHardwareAlarm
      INTEGER }

mscShelfCardCurrentLP OBJECT-TYPE
   SYNTAX     RowPointer 
   ACCESS     read-only
   STATUS     obsolete
   DESCRIPTION
     "This is the component name of the LP currently running on this 
      card."
::= { mscShelfCardOperEntry 1 }

mscShelfCardFailureCause OBJECT-TYPE
   SYNTAX     INTEGER  {
                 none(0),
                 wrongCardType(1),
                 notConfigured(2),
                 cannotLoadSoftware(3),
                 failedSelfTests(4),
                 notResponding(5),
                 backplaneConnectivityProblem(6),
                 unsupportedPecCode(7) }
   ACCESS     read-only
   STATUS     mandatory
   DESCRIPTION
     "This attribute indicates why the card has failed. This attribute is 
      meaningful when the OSI AvailabilityStatus attribute is set to 
      failed.
      none - The card is operational.
      wrongCardType - The wrong card type has been inserted.
      notConfigured - The card is not configured.
      cannotLoadSoftware - The card can not load software.
      failedSelfTests - The card failed itself test.
      notResponding - The card is not responding.
      backplaneConnectivityProblem - The card is not properly 
      connected to the backplane.
      unsupportedPecCode - The card is with unsupported PEC code 
      is inserted."
::= { mscShelfCardOperEntry 2 }

mscShelfCardSelfTestFault OBJECT-TYPE
   SYNTAX     INTEGER  {
                 none(0) }
   ACCESS     read-only
   STATUS     mandatory
   DESCRIPTION
     "This attribute indicates the result of the processor card's self-tests 
      that were performed when it initially came up."
::= { mscShelfCardOperEntry 3 }

mscShelfCardSparingConnectionStatus OBJECT-TYPE
   SYNTAX     INTEGER  {
                 notApplicable(0),
                 n1for1Ok(1),
                 n1forNOk(2),
                 unconfirmed(3),
                 notConnected(4),
                 incorrectlyConnected(5),
                 inconsistentlyConnected(6) }
   ACCESS     read-only
   STATUS     mandatory
   DESCRIPTION
     "This attribute indicates if the control signal received from a 1forN 
      sparing panel or a 1for1 sparing panel is properly terminated.
      notApplicable - The card is not provisioned as part of a 
      sparing configuration, and is not connected to any sparing panel.
      1for1Ok -The card is provisioned correctly for 1for1 sparing and is 
      connected to the active relay of a 1for1 sparing panel.
      1forNOk -The card is provisioned correctly for either 1for1 or 
      1forN sparing and is connected to either the standby or active relay 
      of a 1forN sparing panel.
      unconfirmed -The card is provisioned as part of a sparing 
      configuration, but  its connection status cannot be determined.
      To determine if the card is connected to a sparing panel, perform a 
      switchover of the LP to see if the card will grab a relay when it is 
      active. If the card has grabbed the relay, the sparing connection 
      status should change from, unconfirmed, to 1for1Ok and the LED 
      on the sparing panel corresponfing to that relay should be 
      illuminated.
      Please note: Performing the switchover will disrupt traffic on the 
      other card and this test should be conducted when no traffic is 
      running on the active card.
      notConnected - The card is provisioned as part of a sparing 
      configuration, but is not connected to a sparing panel.
      Remedial Action: Check the cable connectivity between the card 
      and the sparing panel.
      incorrectlyConnected - The card is provisioned as part of a sparing 
      configuration, but is connected to the wrong port on a 1forN panel, 
      or is connected to a 1for1 sparing panel while configured for 1forN.
      Remedial Action: Connect the cable to the port that was specified 
      by the sparingConnection attribute.
      inconsistentlyConnected - The card is provisioned as part of a 
      1forN sparing configuration, but is connected to a sparing panel 
      which is not the same as the other cards sharing the same spare 
      card.
      Remedial Action: Ensure all cards that share the same spare card 
      are connected to the same sparing panel.
      This value is also used to indicate that two sparing panels with the 
      same sparing panel IDs are being used by cards on the same shelf.
      Remedial Action: Replace one of the sparing panels with another 
      panel that has a different sparing panel ID. Sparing panel IDs are 
      assigned at the time of manufacture and cannot be changed by the 
      user."
::= { mscShelfCardOperEntry 4 }

mscShelfCardHardwareAlarm OBJECT-TYPE
   SYNTAX     INTEGER  {
                 none(0),
                 batteryFeedFailure(1) }
   ACCESS     read-only
   STATUS     mandatory
   DESCRIPTION
     "This attribute indicates whether and why the card is generating a 
      hardware alarm."
::= { mscShelfCardOperEntry 5 }

mscShelfCardPropTable OBJECT-TYPE
   SYNTAX     SEQUENCE OF MscShelfCardPropEntry
   ACCESS     not-accessible
   STATUS     mandatory
   DESCRIPTION
     "This group contains the operational attributes that specify the fixed 
      characteristics of the card."
::= { mscShelfCard 13 }

mscShelfCardPropEntry OBJECT-TYPE
   SYNTAX     MscShelfCardPropEntry
   ACCESS     not-accessible
   STATUS     mandatory
   DESCRIPTION
     "An entry in the mscShelfCardPropTable."
   INDEX {
      mscShelfIndex,
      mscShelfCardIndex }
::= { mscShelfCardPropTable 1 }

MscShelfCardPropEntry ::= SEQUENCE {
   mscShelfCardInsertedCardType
      INTEGER,
   mscShelfCardPmRevisionCode
      AsciiString,
   mscShelfCardImRevisionCode
      AsciiString,
   mscShelfCardSerialNumber
      AsciiString,
   mscShelfCardActiveFirmwareVersion
      AsciiString,
   mscShelfCardInactiveFirmwareVersion
      AsciiString,
   mscShelfCardProductCode
      AsciiString }

mscShelfCardInsertedCardType OBJECT-TYPE
   SYNTAX     INTEGER  {
                 cP(0),
                 v11(1),
                 v35(2),
                 dS1(3),
                 dS1V(4),
                 dS3(5),
                 e1(6),
                 e1V(7),
                 e3(8),
                 none(9),
                 n1pFddiMultiMode(10),
                 n4pTokenRing(11),
                 n6pEth10BaseT(12),
                 dS1C(13),
                 e1C(14),
                 n3pE3Atm(15),
                 n3pDS3Atm(16),
                 n3pOC3MmAtm(17),
                 n1pOC3MmAtm(18),
                 n3pOC3SmAtm(19),
                 n3pE1Atm(20),
                 n3pDS1Atm(21),
                 j2MV(22),
                 n4pEthAui(23),
                 n1pFddiSingleMode(24),
                 n1pDS1V(25),
                 n1pE1V(26),
                 n2pJ6MAtm(27),
                 hSSI(33),
                 n8pDS1(34),
                 cFP1(35),
                 dEV1(36),
                 cFP2(37),
                 dEV2(38),
                 n4pDS1Aal1(39),
                 n4pE1Aal1(40),
                 n1pDS3C(41),
                 ilsForwarder(42),
                 n8pDS1Atm(43),
                 n8pE1Atm(44),
                 n1pE1Mvp(45),
                 n1pDS1Mvp(46),
                 n1pTTC2mMvp(47),
                 n1pDS3cAal(51),
                 n2pDS3cAal(52),
                 n12mVspAal(53),
                 n2pEth100BaseT(54),
                 n2pOC3MmAtm2(55),
                 n2pOC3SmAtm2(56),
                 n3pDS3Atm2(57),
                 n3pE3Atm2(58),
                 cPeD(59),
                 cPeE(60),
                 n4pOC3SmIrAtm(61),
                 n4pOC3MmAtm(62),
                 n12pDS3Atm(63),
                 n12pE3Atm(64),
                 n1pOC12SmLrAtm(65),
                 n1pE1Mvpe(66),
                 n1pDS1Mvpe(67),
                 n1pTTC2mMvpe(68),
                 n32pDS1Msa(69),
                 n32pDS1MsaMt(70),
                 n32pDS1MsaMtp(71),
                 n32pDS1MsaSt(72),
                 n32pDS1MsaStp(73),
                 n32pE1Aal(74),
                 n1pOC48SmSrAtm(75),
                 n4pDS3Ch(76),
                 n4pDS3ChAtm(77),
                 n1pSTM1ChSmIr(78),
                 n1pSTM1ChSmIrAtm(79),
                 n4pOC12SmIrAtm(80),
                 n4pOC12SmLrAtm(81),
                 n12mPcusp(82),
                 n32pE1Msa(84),
                 n32pE1MsaMt(85),
                 n32pE1MsaMtp(86),
                 n32pE1MsaSt(87),
                 n32pE1MsaStp(88) }
   ACCESS     read-only
   STATUS     mandatory
   DESCRIPTION
     "This attribute indicates the type of card that is currently inserted in 
      this slot."
::= { mscShelfCardPropEntry 1 }

mscShelfCardPmRevisionCode OBJECT-TYPE
   SYNTAX     AsciiString (SIZE (0..16))
   ACCESS     read-only
   STATUS     mandatory
   DESCRIPTION
     "This attribute indicates the hardware revision level of the Processor 
      Module (PM)."
::= { mscShelfCardPropEntry 2 }

mscShelfCardImRevisionCode OBJECT-TYPE
   SYNTAX     AsciiString (SIZE (0..16))
   ACCESS     read-only
   STATUS     mandatory
   DESCRIPTION
     "This attribute indicates the hardware revision level of the Interface 
      Module (IM)."
::= { mscShelfCardPropEntry 3 }

mscShelfCardSerialNumber OBJECT-TYPE
   SYNTAX     AsciiString (SIZE (0..16))
   ACCESS     read-only
   STATUS     mandatory
   DESCRIPTION
     "This attribute indicates the processor card's serial number."
::= { mscShelfCardPropEntry 4 }

mscShelfCardActiveFirmwareVersion OBJECT-TYPE
   SYNTAX     AsciiString (SIZE (0..16))
   ACCESS     read-only
   STATUS     mandatory
   DESCRIPTION
     "This attribute indicates the firmware version of the currently active 
      flash memory bank."
::= { mscShelfCardPropEntry 5 }

mscShelfCardInactiveFirmwareVersion OBJECT-TYPE
   SYNTAX     AsciiString (SIZE (0..16))
   ACCESS     read-only
   STATUS     mandatory
   DESCRIPTION
     "This attribute indicates the firmware version of the currently 
      inactive flash memory bank."
::= { mscShelfCardPropEntry 6 }

mscShelfCardProductCode OBJECT-TYPE
   SYNTAX     AsciiString (SIZE (0..12))
   ACCESS     read-only
   STATUS     mandatory
   DESCRIPTION
     "This attribute indicates the product ordering code and release of the 
      card."
::= { mscShelfCardPropEntry 7 }

mscShelfCardUtilTable OBJECT-TYPE
   SYNTAX     SEQUENCE OF MscShelfCardUtilEntry
   ACCESS     not-accessible
   STATUS     mandatory
   DESCRIPTION
     "This group contains the operational attributes that specify the 
      processor's utilization levels. When this group exists for an LP 
      component, the attributes are representative of the active card."
::= { mscShelfCard 14 }

mscShelfCardUtilEntry OBJECT-TYPE
   SYNTAX     MscShelfCardUtilEntry
   ACCESS     not-accessible
   STATUS     mandatory
   DESCRIPTION
     "An entry in the mscShelfCardUtilTable."
   INDEX {
      mscShelfIndex,
      mscShelfCardIndex }
::= { mscShelfCardUtilTable 1 }

MscShelfCardUtilEntry ::= SEQUENCE {
   mscShelfCardTimeInterval
      Unsigned32,
   mscShelfCardCpuUtil
      Gauge32,
   mscShelfCardCpuUtilAvg
      Gauge32,
   mscShelfCardCpuUtilAvgMin
      Gauge32,
   mscShelfCardCpuUtilAvgMax
      Gauge32,
   mscShelfCardMsgBlockUsage
      Gauge32,
   mscShelfCardMsgBlockUsageAvg
      Gauge32,
   mscShelfCardMsgBlockUsageAvgMin
      Gauge32,
   mscShelfCardMsgBlockUsageAvgMax
      Gauge32,
   mscShelfCardLocalMsgBlockUsage
      Gauge32,
   mscShelfCardLocalMsgBlockUsageAvg
      Gauge32,
   mscShelfCardLocalMsgBlockUsageMin
      Gauge32,
   mscShelfCardLocalMsgBlockUsageMax
      Gauge32 }

mscShelfCardTimeInterval OBJECT-TYPE
   SYNTAX     Unsigned32 (0..15)
   ACCESS     read-only
   STATUS     mandatory
   DESCRIPTION
     "This attribute indicates the time period (in minutes) for which the 
      average, minimum and maximum utilization values are calculated.  
      This attribute is reset to 0 every 15 minutes."
::= { mscShelfCardUtilEntry 1 }

mscShelfCardCpuUtil OBJECT-TYPE
   SYNTAX     Gauge32 (0..100)
   ACCESS     read-only
   STATUS     mandatory
   DESCRIPTION
     "This attribute indicates an approximation of the current processor 
      utilization level (expressed as a percentage)."
::= { mscShelfCardUtilEntry 2 }

mscShelfCardCpuUtilAvg OBJECT-TYPE
   SYNTAX     Gauge32 (0..100)
   ACCESS     read-only
   STATUS     mandatory
   DESCRIPTION
     "This attribute indicates an average processor utilization level over 
      the specified time period, timeInterval. This average is calculated 
      based on one minute CPU utilization averages."
::= { mscShelfCardUtilEntry 3 }

mscShelfCardCpuUtilAvgMin OBJECT-TYPE
   SYNTAX     Gauge32 (0..100)
   ACCESS     read-only
   STATUS     mandatory
   DESCRIPTION
     "This attribute indicates the minimum processor utilization level over 
      a specified time period, timeInterval. This is based on one minute 
      CPU utilization averages."
::= { mscShelfCardUtilEntry 4 }

mscShelfCardCpuUtilAvgMax OBJECT-TYPE
   SYNTAX     Gauge32 (0..100)
   ACCESS     read-only
   STATUS     mandatory
   DESCRIPTION
     "This attribute indicates the maximum processor utilization level 
      over a specified time period, timeInterval. This is based on one 
      minute CPU utilization averages."
::= { mscShelfCardUtilEntry 5 }

mscShelfCardMsgBlockUsage OBJECT-TYPE
   SYNTAX     Gauge32 (0..2147483647)
   ACCESS     read-only
   STATUS     mandatory
   DESCRIPTION
     "This attribute indicates the processor's current shared message 
      block memory utilization.
      If there is no shared memory on the card, this attribute indicates 0."
::= { mscShelfCardUtilEntry 6 }

mscShelfCardMsgBlockUsageAvg OBJECT-TYPE
   SYNTAX     Gauge32 (0..2147483647)
   ACCESS     read-only
   STATUS     mandatory
   DESCRIPTION
     "This attribute indicates the processor's average memory utilization 
      of shared message blocks, calculated over a specified time period, 
      timeInterval.  This utilization value is calculated using 15 second 
      samples.  At the start of each timeInterval, this average memory 
      utilization is reset to the current usage, sharedMsgBlockUsage.
      If there is no shared memory on the card, this attribute indicates 0."
::= { mscShelfCardUtilEntry 7 }

mscShelfCardMsgBlockUsageAvgMin OBJECT-TYPE
   SYNTAX     Gauge32 (0..2147483647)
   ACCESS     read-only
   STATUS     mandatory
   DESCRIPTION
     "This attribute indicates the processor's minimum memory 
      utilization  of shared message blocks, calculated over a specified 
      time period, timeInterval.  This utilization value is calculated using 
      15 second samples.  At the start of each timeInterval, this minimum 
      memory utilization is reset to the current usage, 
      sharedMsgBlockUsage.
      If there is no shared memory on the card, this attribute indicates 0."
::= { mscShelfCardUtilEntry 8 }

mscShelfCardMsgBlockUsageAvgMax OBJECT-TYPE
   SYNTAX     Gauge32 (0..2147483647)
   ACCESS     read-only
   STATUS     mandatory
   DESCRIPTION
     "This attribute indicates the processor's maximum memory 
      utilization of shared message blocks, calculated over a specified 
      time period, timeInterval.  This utilization value is calculated using 
      15 second samples.  At the start of each timeInterval, this maximum 
      memory utilization is reset to the current usage, 
      sharedMsgBlockUsage.
      If there is no shared memory on the card, this attribute indicates 0."
::= { mscShelfCardUtilEntry 9 }

mscShelfCardLocalMsgBlockUsage OBJECT-TYPE
   SYNTAX     Gauge32 (0..2147483647)
   ACCESS     read-only
   STATUS     mandatory
   DESCRIPTION
     "This attribute indicates the processor's current memory utilization 
      of message blocks which are used for local messaging on the card."
::= { mscShelfCardUtilEntry 10 }

mscShelfCardLocalMsgBlockUsageAvg OBJECT-TYPE
   SYNTAX     Gauge32 (0..2147483647)
   ACCESS     read-only
   STATUS     mandatory
   DESCRIPTION
     "This attribute indicates the processor's average memory utilization 
      of message blocks used for local messaging on the card, calculated 
      over a specified time period, timeInterval.  This utilization value is 
      calculated using 15 second samples.  At the start of each 
      timeInterval, this average memory utilization is reset to the current 
      usage, localMsgBlockUsage."
::= { mscShelfCardUtilEntry 11 }

mscShelfCardLocalMsgBlockUsageMin OBJECT-TYPE
   SYNTAX     Gauge32 (0..2147483647)
   ACCESS     read-only
   STATUS     mandatory
   DESCRIPTION
     "This attribute indicates the processor's minimum memory 
      utilization of message blocks used for local messaging on the card, 
      calculated over a specified time period, timeInterval.  This 
      utilization value is updated at 15 second intervals.  At the start of 
      each timeInterval, this minimum memory utilization is reset to the 
      current usage, localMsgBlockUsage."
::= { mscShelfCardUtilEntry 12 }

mscShelfCardLocalMsgBlockUsageMax OBJECT-TYPE
   SYNTAX     Gauge32 (0..2147483647)
   ACCESS     read-only
   STATUS     mandatory
   DESCRIPTION
     "This attribute indicates the processor's maximum memory 
      utilization of message blocks used for local messaging on the card, 
      calculated over a specified time period, timeInterval.  This 
      utilization value is updated at 15 second intervals.  At the start of 
      each timeInterval, this maximum memory utilization is reset to the 
      current usage, localMsgBlockUsage."
::= { mscShelfCardUtilEntry 13 }

mscShelfCardCapTable OBJECT-TYPE
   SYNTAX     SEQUENCE OF MscShelfCardCapEntry
   ACCESS     not-accessible
   STATUS     mandatory
   DESCRIPTION
     "This group contains the operational attributes that specify the 
      processor's capacity levels. When this group exists for an LP 
      component, the attributes are representative of the active Card."
::= { mscShelfCard 15 }

mscShelfCardCapEntry OBJECT-TYPE
   SYNTAX     MscShelfCardCapEntry
   ACCESS     not-accessible
   STATUS     mandatory
   DESCRIPTION
     "An entry in the mscShelfCardCapTable."
   INDEX {
      mscShelfIndex,
      mscShelfCardIndex }
::= { mscShelfCardCapTable 1 }

MscShelfCardCapEntry ::= SEQUENCE {
   mscShelfCardMsgBlockCapacity
      Unsigned32,
   mscShelfCardLocalMsgBlockCapacity
      Unsigned32 }

mscShelfCardMsgBlockCapacity OBJECT-TYPE
   SYNTAX     Unsigned32 (0..2147483647)
   ACCESS     read-only
   STATUS     mandatory
   DESCRIPTION
     "This attribute indicates the processor card's shared message block 
      memory capacity."
::= { mscShelfCardCapEntry 1 }

mscShelfCardLocalMsgBlockCapacity OBJECT-TYPE
   SYNTAX     Unsigned32 (0..2147483647)
   ACCESS     read-only
   STATUS     mandatory
   DESCRIPTION
     "This attribute indicates the processor card's local message block 
      memory capacity.  These message blocks are used for local 
      messaging on the card."
::= { mscShelfCardCapEntry 2 }

mscShelfCardConfiguredLPsTable OBJECT-TYPE
   SYNTAX     SEQUENCE OF MscShelfCardConfiguredLPsEntry
   ACCESS     not-accessible
   STATUS     mandatory
   DESCRIPTION
     "This is a read-only attribute that shows which LPs are currently 
      configured to run on this card (it is the opposite side of the LP 
      component's mainCard and spareCard link attributes). Note that 
      there is only one case where more than one LP can be configured to 
      run on a card. This is when the card is configured as an N+1 spare. 
      If this is not the case, the card is configured as a main card or as a 
      1for1 spare, only one LP can appear in this list."
::= { mscShelfCard 243 }

mscShelfCardConfiguredLPsEntry OBJECT-TYPE
   SYNTAX     MscShelfCardConfiguredLPsEntry
   ACCESS     not-accessible
   STATUS     mandatory
   DESCRIPTION
     "An entry in the mscShelfCardConfiguredLPsTable."
   INDEX {
      mscShelfIndex,
      mscShelfCardIndex,
      mscShelfCardConfiguredLPsValue }
::= { mscShelfCardConfiguredLPsTable 1 }

MscShelfCardConfiguredLPsEntry ::= SEQUENCE {
   mscShelfCardConfiguredLPsValue
      Link }

mscShelfCardConfiguredLPsValue OBJECT-TYPE
   SYNTAX     Link 
   ACCESS     read-only
   STATUS     mandatory
   DESCRIPTION
     "This variable represents both the value and the index for the
      mscShelfCardConfiguredLPsTable."
::= { mscShelfCardConfiguredLPsEntry 1 }

mscShelfCardMemoryCapacityTable OBJECT-TYPE
   SYNTAX     SEQUENCE OF MscShelfCardMemoryCapacityEntry
   ACCESS     not-accessible
   STATUS     mandatory
   DESCRIPTION
     "This attribute indicates the processor card's memory capacity for 
      each type of memory."
::= { mscShelfCard 244 }

mscShelfCardMemoryCapacityEntry OBJECT-TYPE
   SYNTAX     MscShelfCardMemoryCapacityEntry
   ACCESS     not-accessible
   STATUS     mandatory
   DESCRIPTION
     "An entry in the mscShelfCardMemoryCapacityTable."
   INDEX {
      mscShelfIndex,
      mscShelfCardIndex,
      mscShelfCardMemoryCapacityIndex }
::= { mscShelfCardMemoryCapacityTable 1 }

MscShelfCardMemoryCapacityEntry ::= SEQUENCE {
   mscShelfCardMemoryCapacityIndex
      INTEGER,
   mscShelfCardMemoryCapacityValue
      Unsigned32 }

mscShelfCardMemoryCapacityIndex OBJECT-TYPE
   SYNTAX     INTEGER  {
                 fastRam(0),
                 normalRam(1),
                 sharedRam(2) }
   ACCESS     not-accessible
   STATUS     mandatory
   DESCRIPTION
     "This variable represents the mscShelfCardMemoryCapacityTable
      specific index for the mscShelfCardMemoryCapacityTable."
::= { mscShelfCardMemoryCapacityEntry 1 }

mscShelfCardMemoryCapacityValue OBJECT-TYPE
   SYNTAX     Unsigned32 (0..2147483647)
   ACCESS     read-only
   STATUS     mandatory
   DESCRIPTION
     "This variable represents an individual value for the
      mscShelfCardMemoryCapacityTable."
::= { mscShelfCardMemoryCapacityEntry 2 }

mscShelfCardMemoryUsageTable OBJECT-TYPE
   SYNTAX     SEQUENCE OF MscShelfCardMemoryUsageEntry
   ACCESS     not-accessible
   STATUS     mandatory
   DESCRIPTION
     "This attribute indicates the processor's current memory utilization 
      for each type of memory."
::= { mscShelfCard 245 }

mscShelfCardMemoryUsageEntry OBJECT-TYPE
   SYNTAX     MscShelfCardMemoryUsageEntry
   ACCESS     not-accessible
   STATUS     mandatory
   DESCRIPTION
     "An entry in the mscShelfCardMemoryUsageTable."
   INDEX {
      mscShelfIndex,
      mscShelfCardIndex,
      mscShelfCardMemoryUsageIndex }
::= { mscShelfCardMemoryUsageTable 1 }

MscShelfCardMemoryUsageEntry ::= SEQUENCE {
   mscShelfCardMemoryUsageIndex
      INTEGER,
   mscShelfCardMemoryUsageValue
      Gauge32 }

mscShelfCardMemoryUsageIndex OBJECT-TYPE
   SYNTAX     INTEGER  {
                 fastRam(0),
                 normalRam(1),
                 sharedRam(2) }
   ACCESS     not-accessible
   STATUS     mandatory
   DESCRIPTION
     "This variable represents the mscShelfCardMemoryUsageTable
      specific index for the mscShelfCardMemoryUsageTable."
::= { mscShelfCardMemoryUsageEntry 1 }

mscShelfCardMemoryUsageValue OBJECT-TYPE
   SYNTAX     Gauge32 (0..2147483647)
   ACCESS     read-only
   STATUS     mandatory
   DESCRIPTION
     "This variable represents an individual value for the
      mscShelfCardMemoryUsageTable."
::= { mscShelfCardMemoryUsageEntry 2 }

mscShelfCardMemoryUsageAvgTable OBJECT-TYPE
   SYNTAX     SEQUENCE OF MscShelfCardMemoryUsageAvgEntry
   ACCESS     not-accessible
   STATUS     mandatory
   DESCRIPTION
     "This attribute indicates the processor's average memory utilization 
      for each type of memory in the specified time period, timeInterval. 
      This value is calculated using 15 second samples."
::= { mscShelfCard 276 }

mscShelfCardMemoryUsageAvgEntry OBJECT-TYPE
   SYNTAX     MscShelfCardMemoryUsageAvgEntry
   ACCESS     not-accessible
   STATUS     mandatory
   DESCRIPTION
     "An entry in the mscShelfCardMemoryUsageAvgTable."
   INDEX {
      mscShelfIndex,
      mscShelfCardIndex,
      mscShelfCardMemoryUsageAvgIndex }
::= { mscShelfCardMemoryUsageAvgTable 1 }

MscShelfCardMemoryUsageAvgEntry ::= SEQUENCE {
   mscShelfCardMemoryUsageAvgIndex
      INTEGER,
   mscShelfCardMemoryUsageAvgValue
      Gauge32 }

mscShelfCardMemoryUsageAvgIndex OBJECT-TYPE
   SYNTAX     INTEGER  {
                 fastRam(0),
                 normalRam(1),
                 sharedRam(2) }
   ACCESS     not-accessible
   STATUS     mandatory
   DESCRIPTION
     "This variable represents the mscShelfCardMemoryUsageAvgTable
      specific index for the mscShelfCardMemoryUsageAvgTable."
::= { mscShelfCardMemoryUsageAvgEntry 1 }

mscShelfCardMemoryUsageAvgValue OBJECT-TYPE
   SYNTAX     Gauge32 (0..2147483647)
   ACCESS     read-only
   STATUS     mandatory
   DESCRIPTION
     "This variable represents an individual value for the
      mscShelfCardMemoryUsageAvgTable."
::= { mscShelfCardMemoryUsageAvgEntry 2 }

mscShelfCardMemoryUsageAvgMinTable OBJECT-TYPE
   SYNTAX     SEQUENCE OF MscShelfCardMemoryUsageAvgMinEntry
   ACCESS     not-accessible
   STATUS     mandatory
   DESCRIPTION
     "This attribute indicates the processor's minimum memory 
      utilization for each type of memory in the specified time period, 
      timeInterval. This value is calculated using 15 second samples."
::= { mscShelfCard 277 }

mscShelfCardMemoryUsageAvgMinEntry OBJECT-TYPE
   SYNTAX     MscShelfCardMemoryUsageAvgMinEntry
   ACCESS     not-accessible
   STATUS     mandatory
   DESCRIPTION
     "An entry in the mscShelfCardMemoryUsageAvgMinTable."
   INDEX {
      mscShelfIndex,
      mscShelfCardIndex,
      mscShelfCardMemoryUsageAvgMinIndex }
::= { mscShelfCardMemoryUsageAvgMinTable 1 }

MscShelfCardMemoryUsageAvgMinEntry ::= SEQUENCE {
   mscShelfCardMemoryUsageAvgMinIndex
      INTEGER,
   mscShelfCardMemoryUsageAvgMinValue
      Gauge32 }

mscShelfCardMemoryUsageAvgMinIndex OBJECT-TYPE
   SYNTAX     INTEGER  {
                 fastRam(0),
                 normalRam(1),
                 sharedRam(2) }
   ACCESS     not-accessible
   STATUS     mandatory
   DESCRIPTION
     "This variable represents the mscShelfCardMemoryUsageAvgMinTable
      specific index for the mscShelfCardMemoryUsageAvgMinTable."
::= { mscShelfCardMemoryUsageAvgMinEntry 1 }

mscShelfCardMemoryUsageAvgMinValue OBJECT-TYPE
   SYNTAX     Gauge32 (0..2147483647)
   ACCESS     read-only
   STATUS     mandatory
   DESCRIPTION
     "This variable represents an individual value for the
      mscShelfCardMemoryUsageAvgMinTable."
::= { mscShelfCardMemoryUsageAvgMinEntry 2 }

mscShelfCardMemoryUsageAvgMaxTable OBJECT-TYPE
   SYNTAX     SEQUENCE OF MscShelfCardMemoryUsageAvgMaxEntry
   ACCESS     not-accessible
   STATUS     mandatory
   DESCRIPTION
     "This attribute indicates the processor's maximum memory 
      utilization for each type of memory in the specified time period, 
      timeInterval. This value is calculated using 15 second samples."
::= { mscShelfCard 278 }

mscShelfCardMemoryUsageAvgMaxEntry OBJECT-TYPE
   SYNTAX     MscShelfCardMemoryUsageAvgMaxEntry
   ACCESS     not-accessible
   STATUS     mandatory
   DESCRIPTION
     "An entry in the mscShelfCardMemoryUsageAvgMaxTable."
   INDEX {
      mscShelfIndex,
      mscShelfCardIndex,
      mscShelfCardMemoryUsageAvgMaxIndex }
::= { mscShelfCardMemoryUsageAvgMaxTable 1 }

MscShelfCardMemoryUsageAvgMaxEntry ::= SEQUENCE {
   mscShelfCardMemoryUsageAvgMaxIndex
      INTEGER,
   mscShelfCardMemoryUsageAvgMaxValue
      Gauge32 }

mscShelfCardMemoryUsageAvgMaxIndex OBJECT-TYPE
   SYNTAX     INTEGER  {
                 fastRam(0),
                 normalRam(1),
                 sharedRam(2) }
   ACCESS     not-accessible
   STATUS     mandatory
   DESCRIPTION
     "This variable represents the mscShelfCardMemoryUsageAvgMaxTable
      specific index for the mscShelfCardMemoryUsageAvgMaxTable."
::= { mscShelfCardMemoryUsageAvgMaxEntry 1 }

mscShelfCardMemoryUsageAvgMaxValue OBJECT-TYPE
   SYNTAX     Gauge32 (0..2147483647)
   ACCESS     read-only
   STATUS     mandatory
   DESCRIPTION
     "This variable represents an individual value for the
      mscShelfCardMemoryUsageAvgMaxTable."
::= { mscShelfCardMemoryUsageAvgMaxEntry 2 }

mscShelfCardCurrentLpTable OBJECT-TYPE
   SYNTAX     SEQUENCE OF MscShelfCardCurrentLpEntry
   ACCESS     not-accessible
   STATUS     mandatory
   DESCRIPTION
     "This attribute indicates which LPs are currently associated with this 
      card.  A card configured as a 1forN spare may be associated with 
      more than one LP."
::= { mscShelfCard 406 }

mscShelfCardCurrentLpEntry OBJECT-TYPE
   SYNTAX     MscShelfCardCurrentLpEntry
   ACCESS     not-accessible
   STATUS     mandatory
   DESCRIPTION
     "An entry in the mscShelfCardCurrentLpTable."
   INDEX {
      mscShelfIndex,
      mscShelfCardIndex,
      mscShelfCardCurrentLpValue }
::= { mscShelfCardCurrentLpTable 1 }

MscShelfCardCurrentLpEntry ::= SEQUENCE {
   mscShelfCardCurrentLpValue
      RowPointer }

mscShelfCardCurrentLpValue OBJECT-TYPE
   SYNTAX     RowPointer 
   ACCESS     read-only
   STATUS     mandatory
   DESCRIPTION
     "This variable represents both the value and the index for the
      mscShelfCardCurrentLpTable."
::= { mscShelfCardCurrentLpEntry 1 }


-- Shelf Card/n Test
-- This component is used to verify the operation of a module's cards. 
-- A card test may be run when new hardware or services are 
-- commissioned, as part of a routine maintenance program, or to 
-- diagnose the cause of card- or bus-related problems. The Test 
-- component is created automatically for each card that is running as 
-- an active or standby LP; Test components cannot be added or 
-- deleted.
-- 
-- A card test allows the operator to stress test new or existing cards 
-- under controlled conditions. The test circulates frames over the 
-- Passport bus between the card under test and a distinct "target 
-- card", thereby exercising both cards and consuming bus bandwidth. 
-- The test frames follow the same route to their destination as normal 
-- frames. If the Passport node is in dual bus mode, each card test that 
-- is activated consumes bandwidth from both backplane buses in 
-- equal amounts; if the module is in single bus mode, only the bus in 
-- service is utilized.
-- 
-- The test frames generated by the card under test are grouped into 
-- two independent streams.
-- 1) The loading frame stream circulates a set of "loading frames" 
-- between the card under test and the target card as rapidly as 
-- possible. The intent of this stream is to verify the operation of the 
-- cards and the backplane buses under a controlled load.
-- 2) The verification stream transmits a series of "verification frames" 
-- from the card under test to the the target card; as each frame is 
-- returned, its contents are verified and the next verification frame in 
-- the series is transmitted. The intent of this stream is to verify that 
-- frames are not being corrupted during transfer from card to card.
-- The card test can be configured to send frames from either or both 
-- streams. The priority, size, and content of the test frames can also be 
-- controlled.
-- 
-- Each card in Passport can run the card test independently. The 
-- operator can run the card test on any subset of the cards 
-- simultaneously and can specify different test frame configurations 
-- for each test. It is also possible for a card to act as the target card for 
-- more than one card under test, and for a card to act as a target card 
-- while it is itself under test. The flexibility provided by the card test 
-- allows the operator to tailor a set of card tests according to the 
-- testing to be performed.

mscShelfCardTest OBJECT IDENTIFIER ::= { mscShelfCard 3 }



mscShelfCardTestRowStatusTable OBJECT-TYPE
   SYNTAX     SEQUENCE OF MscShelfCardTestRowStatusEntry
   ACCESS     not-accessible
   STATUS     mandatory
   DESCRIPTION
     "This entry controls the addition and deletion of 
      mscShelfCardTest components."
::= { mscShelfCardTest 1 }

mscShelfCardTestRowStatusEntry OBJECT-TYPE
   SYNTAX     MscShelfCardTestRowStatusEntry
   ACCESS     not-accessible
   STATUS     mandatory
   DESCRIPTION
     "A single entry in the table represents a single 
      mscShelfCardTest component."
   INDEX {
      mscShelfIndex,
      mscShelfCardIndex,
      mscShelfCardTestIndex }
::= { mscShelfCardTestRowStatusTable 1 }

MscShelfCardTestRowStatusEntry ::= SEQUENCE {
   mscShelfCardTestRowStatus
      RowStatus,
   mscShelfCardTestComponentName
      DisplayString,
   mscShelfCardTestStorageType
      StorageType,
   mscShelfCardTestIndex
      NonReplicated }

mscShelfCardTestRowStatus OBJECT-TYPE
   SYNTAX     RowStatus 
   ACCESS     read-only
   STATUS     mandatory
   DESCRIPTION
     "This variable is used as the basis for SNMP naming of
      mscShelfCardTest components.
      These components cannot be added nor deleted."
::= { mscShelfCardTestRowStatusEntry 1 }

mscShelfCardTestComponentName OBJECT-TYPE
   SYNTAX     DisplayString 
   ACCESS     read-only
   STATUS     mandatory
   DESCRIPTION
     "This variable provides the component's string name for
      use with the ASCII Console Interface"
::= { mscShelfCardTestRowStatusEntry 2 }

mscShelfCardTestStorageType OBJECT-TYPE
   SYNTAX     StorageType 
   ACCESS     read-only
   STATUS     mandatory
   DESCRIPTION
     "This variable represents the storage type value for the
      mscShelfCardTest tables."
::= { mscShelfCardTestRowStatusEntry 4 }

mscShelfCardTestIndex OBJECT-TYPE
   SYNTAX     NonReplicated 
   ACCESS     not-accessible
   STATUS     mandatory
   DESCRIPTION
     "This variable represents the index for the mscShelfCardTest tables."
::= { mscShelfCardTestRowStatusEntry 10 }

mscShelfCardTestStateTable OBJECT-TYPE
   SYNTAX     SEQUENCE OF MscShelfCardTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscShelfCardTest 10 }

mscShelfCardTestStateEntry OBJECT-TYPE
   SYNTAX     MscShelfCardTestStateEntry
   ACCESS     not-accessible
   STATUS     mandatory
   DESCRIPTION
     "An entry in the mscShelfCardTestStateTable."
   INDEX {
      mscShelfIndex,
      mscShelfCardIndex,
      mscShelfCardTestIndex }
::= { mscShelfCardTestStateTable 1 }

MscShelfCardTestStateEntry ::= SEQUENCE {
   mscShelfCardTestAdminState
      INTEGER,
   mscShelfCardTestOperationalState
      INTEGER,
   mscShelfCardTestUsageState
      INTEGER }

mscShelfCardTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscShelfCardTestStateEntry 1 }

mscShelfCardTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscShelfCardTestStateEntry 2 }

mscShelfCardTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscShelfCardTestStateEntry 3 }

mscShelfCardTestSetupTable OBJECT-TYPE
   SYNTAX     SEQUENCE OF MscShelfCardTestSetupEntry
   ACCESS     not-accessible
   STATUS     mandatory
   DESCRIPTION
     "This attribute group contains the attributes that govern the operation 
      of a card test. These attributes cannot be changed while a card test 
      is running."
::= { mscShelfCardTest 11 }

mscShelfCardTestSetupEntry OBJECT-TYPE
   SYNTAX     MscShelfCardTestSetupEntry
   ACCESS     not-accessible
   STATUS     mandatory
   DESCRIPTION
     "An entry in the mscShelfCardTestSetupTable."
   INDEX {
      mscShelfIndex,
      mscShelfCardIndex,
      mscShelfCardTestIndex }
::= { mscShelfCardTestSetupTable 1 }

MscShelfCardTestSetupEntry ::= SEQUENCE {
   mscShelfCardTestTargetCard
      Unsigned32,
   mscShelfCardTestFrmTypes
      OCTET STRING,
   mscShelfCardTestFrmPriorities
      OCTET STRING,
   mscShelfCardTestFrmPatternType
      INTEGER,
   mscShelfCardTestCustomizedPattern
      Hex,
   mscShelfCardTestDuration
      Unsigned32 }

mscShelfCardTestTargetCard OBJECT-TYPE
   SYNTAX     Unsigned32 (0..15)
   ACCESS     read-write
   STATUS     mandatory
   DESCRIPTION
     "This attribute specifies the slot number of the card to which frames 
      are sent during the card test. There is no single default value for this 
      attributeit defaults to the slot number of the Test component's 
      own card and must be changed to a different value before the test 
      can be started."
::= { mscShelfCardTestSetupEntry 1 }

mscShelfCardTestFrmTypes OBJECT-TYPE
   SYNTAX     OCTET STRING (SIZE (1))
   ACCESS     read-write
   STATUS     mandatory
   DESCRIPTION
     "This attribute specifies the types of frames that are sent during the 
      card test. It must contain at least one of the following values.
      loading: A set of 'loading frames' is circulated between the Test 
      component and the Test component on the target card as rapidly as 
      possible. This frame type should be selected when the test is 
      intended to verify the operation of the cards and the backplane 
      buses under a specified load.
      verification: A single 'verification frame' is transmitted to the Test 
      component on the target card; when the frame is returned, its 
      contents are verified and the next verification frame in the series is 
      transmitted. This frame type should be selected when the test is 
      intended to verify that frames are not being corrupted as they pass 
      from card to card.

      Description of bits:
      loading(0)
      verification(1)"
   DEFVAL     { 'c0'H }
::= { mscShelfCardTestSetupEntry 2 }

mscShelfCardTestFrmPriorities OBJECT-TYPE
   SYNTAX     OCTET STRING (SIZE (1))
   ACCESS     read-write
   STATUS     mandatory
   DESCRIPTION
     "This attribute specifies the priorities of the frames that are sent 
      during the card test. It must contain at least one of the following 
      values.
      lowPriority: Low priority frames are sent.
      highPriority: High priority frames are sent.

      Description of bits:
      lowPriority(0)
      highPriority(1)"
   DEFVAL     { '80'H }
::= { mscShelfCardTestSetupEntry 3 }

mscShelfCardTestFrmPatternType OBJECT-TYPE
   SYNTAX     INTEGER  {
                 ccitt32kBitPattern(0),
                 ccitt8MBitPattern(1),
                 customizedPattern(2) }
   ACCESS     read-write
   STATUS     mandatory
   DESCRIPTION
     "This attribute specifies the bit sequence to fill the frames used in the 
      card test. It must contain one of the following values.
      ccitt32kBitPattern: a pseudo-random sequence of 32 Kbit is used
      ccitt8MBitPattern: a pseudo-random sequence of 8 Mbit is used
      customizedPattern: the pattern defined by the customizedPattern 
      attribute is used"
   DEFVAL     { ccitt32kBitPattern }
::= { mscShelfCardTestSetupEntry 4 }

mscShelfCardTestCustomizedPattern OBJECT-TYPE
   SYNTAX     Hex (0..4294967295)
   ACCESS     read-write
   STATUS     mandatory
   DESCRIPTION
     "This attribute specifies a 32 bit sequence used to fill frames when 
      the framePatternType attribute has a value of customizedPattern. 
      The default value gives a pattern of alternating 0 and 1 bits."
   DEFVAL     { 1431655765 }
::= { mscShelfCardTestSetupEntry 5 }

mscShelfCardTestDuration OBJECT-TYPE
   SYNTAX     Unsigned32 (1..43200)
   ACCESS     read-write
   STATUS     mandatory
   DESCRIPTION
     "This attribute specifies the maximum length of time that the card 
      test is allowed to run. The value is expressed in minutes. The 
      maximum allowed value permits the card test to be run for up to 30 
      days."
   DEFVAL     { 60 }
::= { mscShelfCardTestSetupEntry 6 }

mscShelfCardTestResultsTable OBJECT-TYPE
   SYNTAX     SEQUENCE OF MscShelfCardTestResultsEntry
   ACCESS     not-accessible
   STATUS     mandatory
   DESCRIPTION
     "This attribute group contains the results of the card test that is 
      currently running; if no test is running, the attribute group contains 
      the results of the most recently completed card test. The attributes 
      of the Results group are reset to their inital values whenever a card 
      test is started or any attribute of the Setup group is set."
::= { mscShelfCardTest 12 }

mscShelfCardTestResultsEntry OBJECT-TYPE
   SYNTAX     MscShelfCardTestResultsEntry
   ACCESS     not-accessible
   STATUS     mandatory
   DESCRIPTION
     "An entry in the mscShelfCardTestResultsTable."
   INDEX {
      mscShelfIndex,
      mscShelfCardIndex,
      mscShelfCardTestIndex }
::= { mscShelfCardTestResultsTable 1 }

MscShelfCardTestResultsEntry ::= SEQUENCE {
   mscShelfCardTestElapsedTime
      Unsigned32,
   mscShelfCardTestTimeRemaining
      Unsigned32,
   mscShelfCardTestCauseOfTermination
      INTEGER }

mscShelfCardTestElapsedTime OBJECT-TYPE
   SYNTAX     Unsigned32 (0..43200)
   ACCESS     read-only
   STATUS     mandatory
   DESCRIPTION
     "This attribute records the length of time that the card test has been 
      running."
::= { mscShelfCardTestResultsEntry 1 }

mscShelfCardTestTimeRemaining OBJECT-TYPE
   SYNTAX     Unsigned32 (0..43200)
   ACCESS     read-only
   STATUS     mandatory
   DESCRIPTION
     "This attribute records the maximum length of time that the card test 
      will continue to run before stopping."
::= { mscShelfCardTestResultsEntry 2 }

mscShelfCardTestCauseOfTermination OBJECT-TYPE
   SYNTAX     INTEGER  {
                 neverStarted(0),
                 testRunning(1),
                 testTimeExpired(2),
                 stoppedByOperator(3),
                 targetFailed(4),
                 becameActive(5) }
   ACCESS     read-only
   STATUS     mandatory
   DESCRIPTION
     "This attribute records the reason the card test ended. It contains one 
      of the following values:
      neverStarted: the card test has not been started.
      testRunning: the card test is currently running.
      testTimeExpired: the card test ran for the specified duration.
      stoppedByOperator: a Stop command was issued.
      targetFailed: the target card became non-operational.
      becameActive: the source card became the active card for some LP."
::= { mscShelfCardTestResultsEntry 3 }

mscShelfCardTestSizeTable OBJECT-TYPE
   SYNTAX     SEQUENCE OF MscShelfCardTestSizeEntry
   ACCESS     not-accessible
   STATUS     mandatory
   DESCRIPTION
     "This attribute specifies for each priority level the number of data 
      bytes in each frame sent during the card test. (The value specified 
      does not include the 4-byte header that is automatically added to a 
      frame when it is transmitted over the backplane.)"
::= { mscShelfCardTest 253 }

mscShelfCardTestSizeEntry OBJECT-TYPE
   SYNTAX     MscShelfCardTestSizeEntry
   ACCESS     not-accessible
   STATUS     mandatory
   DESCRIPTION
     "An entry in the mscShelfCardTestSizeTable."
   INDEX {
      mscShelfIndex,
      mscShelfCardIndex,
      mscShelfCardTestIndex,
      mscShelfCardTestSizeIndex }
::= { mscShelfCardTestSizeTable 1 }

MscShelfCardTestSizeEntry ::= SEQUENCE {
   mscShelfCardTestSizeIndex
      INTEGER,
   mscShelfCardTestSizeValue
      Unsigned32 }

mscShelfCardTestSizeIndex OBJECT-TYPE
   SYNTAX     INTEGER  {
                 lowPriority(0),
                 highPriority(1) }
   ACCESS     not-accessible
   STATUS     mandatory
   DESCRIPTION
     "This variable represents the mscShelfCardTestSizeTable
      specific index for the mscShelfCardTestSizeTable."
::= { mscShelfCardTestSizeEntry 1 }

mscShelfCardTestSizeValue OBJECT-TYPE
   SYNTAX     Unsigned32 (16..16000)
   ACCESS     read-write
   STATUS     mandatory
   DESCRIPTION
     "This variable represents an individual value for the
      mscShelfCardTestSizeTable."
::= { mscShelfCardTestSizeEntry 2 }

mscShelfCardTestLoadingFrmDataTable OBJECT-TYPE
   SYNTAX     SEQUENCE OF MscShelfCardTestLoadingFrmDataEntry
   ACCESS     not-accessible
   STATUS     mandatory
   DESCRIPTION
     "This attribute records information about the loading frames that 
      have been transmitted to the Test component on the target card. The 
      following data is shown for each priority level:
      the number of frames that have been transmitted,
      the number of frames that were not returned successfully.
      The attribute's value wraps to zero when they exceed the maximum 
      permitted value.
      
      Note: A loading frame is considered to have been successfully 
      returned even if it contains bit errors. Frame error statistics are 
      recorded in the verificationFrmData attribute."
::= { mscShelfCardTest 254 }

mscShelfCardTestLoadingFrmDataEntry OBJECT-TYPE
   SYNTAX     MscShelfCardTestLoadingFrmDataEntry
   ACCESS     not-accessible
   STATUS     mandatory
   DESCRIPTION
     "An entry in the mscShelfCardTestLoadingFrmDataTable."
   INDEX {
      mscShelfIndex,
      mscShelfCardIndex,
      mscShelfCardTestIndex,
      mscShelfCardTestLoadingFrmDataResultsIndex,
      mscShelfCardTestLoadingFrmDataPriorityIndex }
::= { mscShelfCardTestLoadingFrmDataTable 1 }

MscShelfCardTestLoadingFrmDataEntry ::= SEQUENCE {
   mscShelfCardTestLoadingFrmDataResultsIndex
      INTEGER,
   mscShelfCardTestLoadingFrmDataPriorityIndex
      INTEGER,
   mscShelfCardTestLoadingFrmDataValue
      Unsigned32 }

mscShelfCardTestLoadingFrmDataResultsIndex OBJECT-TYPE
   SYNTAX     INTEGER  {
                 framesSent(0),
                 framesLost(1) }
   ACCESS     not-accessible
   STATUS     mandatory
   DESCRIPTION
     "This variable represents the next to last index for the 
      mscShelfCardTestLoadingFrmDataTable."
::= { mscShelfCardTestLoadingFrmDataEntry 1 }

mscShelfCardTestLoadingFrmDataPriorityIndex OBJECT-TYPE
   SYNTAX     INTEGER  {
                 low(0),
                 high(1) }
   ACCESS     not-accessible
   STATUS     mandatory
   DESCRIPTION
     "This variable represents the final index for the 
      mscShelfCardTestLoadingFrmDataTable."
::= { mscShelfCardTestLoadingFrmDataEntry 2 }

mscShelfCardTestLoadingFrmDataValue OBJECT-TYPE
   SYNTAX     Unsigned32 (0..4294967295)
   ACCESS     read-only
   STATUS     mandatory
   DESCRIPTION
     "This variable represents an individual value for the
      mscShelfCardTestLoadingFrmDataTable."
::= { mscShelfCardTestLoadingFrmDataEntry 3 }

mscShelfCardTestVerificationFrmDataTable OBJECT-TYPE
   SYNTAX     SEQUENCE OF MscShelfCardTestVerificationFrmDataEntry
   ACCESS     not-accessible
   STATUS     mandatory
   DESCRIPTION
     "This attribute records information about the verification frames that 
      have been transmitted to the Test component on the target card. The 
      following data is shown for each priority level:
      the number of frames that have been tested,
      the number of frames that had incorrect bits when returned. 
      The attribute's values wrap around to zero when they exceed the 
      maximum permitted value.
      
      Note: Verification frames that are not returned at all, or are returned 
      too late, are considered 'lost' and are not counted in either of the 
      above values. Frame loss statistics are recorded in the 
      loadingFrmData attribute."
::= { mscShelfCardTest 255 }

mscShelfCardTestVerificationFrmDataEntry OBJECT-TYPE
   SYNTAX     MscShelfCardTestVerificationFrmDataEntry
   ACCESS     not-accessible
   STATUS     mandatory
   DESCRIPTION
     "An entry in the mscShelfCardTestVerificationFrmDataTable."
   INDEX {
      mscShelfIndex,
      mscShelfCardIndex,
      mscShelfCardTestIndex,
      mscShelfCardTestVerificationFrmDataResultsIndex,
      mscShelfCardTestVerificationFrmDataPriorityIndex }
::= { mscShelfCardTestVerificationFrmDataTable 1 }

MscShelfCardTestVerificationFrmDataEntry ::= SEQUENCE {
   mscShelfCardTestVerificationFrmDataResultsIndex
      INTEGER,
   mscShelfCardTestVerificationFrmDataPriorityIndex
      INTEGER,
   mscShelfCardTestVerificationFrmDataValue
      Unsigned32 }

mscShelfCardTestVerificationFrmDataResultsIndex OBJECT-TYPE
   SYNTAX     INTEGER  {
                 framesTested(0),
                 framesBad(1) }
   ACCESS     not-accessible
   STATUS     mandatory
   DESCRIPTION
     "This variable represents the next to last index for the 
      mscShelfCardTestVerificationFrmDataTable."
::= { mscShelfCardTestVerificationFrmDataEntry 1 }

mscShelfCardTestVerificationFrmDataPriorityIndex OBJECT-TYPE
   SYNTAX     INTEGER  {
                 low(0),
                 high(1) }
   ACCESS     not-accessible
   STATUS     mandatory
   DESCRIPTION
     "This variable represents the final index for the 
      mscShelfCardTestVerificationFrmDataTable."
::= { mscShelfCardTestVerificationFrmDataEntry 2 }

mscShelfCardTestVerificationFrmDataValue OBJECT-TYPE
   SYNTAX     Unsigned32 (0..4294967295)
   ACCESS     read-only
   STATUS     mandatory
   DESCRIPTION
     "This variable represents an individual value for the
      mscShelfCardTestVerificationFrmDataTable."
::= { mscShelfCardTestVerificationFrmDataEntry 3 }


-- Shelf Card/n Diagnostics		 
-- This component manages all diagnostic information for a specific 
-- Card. The diagnostic information under this component are 
-- intended to be used by Nortel technical support. 

mscShelfCardDiag OBJECT IDENTIFIER ::= { mscShelfCard 4 }



mscShelfCardDiagRowStatusTable OBJECT-TYPE
   SYNTAX     SEQUENCE OF MscShelfCardDiagRowStatusEntry
   ACCESS     not-accessible
   STATUS     mandatory
   DESCRIPTION
     "This entry controls the addition and deletion of 
      mscShelfCardDiag components."
::= { mscShelfCardDiag 1 }

mscShelfCardDiagRowStatusEntry OBJECT-TYPE
   SYNTAX     MscShelfCardDiagRowStatusEntry
   ACCESS     not-accessible
   STATUS     mandatory
   DESCRIPTION
     "A single entry in the table represents a single 
      mscShelfCardDiag component."
   INDEX {
      mscShelfIndex,
      mscShelfCardIndex,
      mscShelfCardDiagIndex }
::= { mscShelfCardDiagRowStatusTable 1 }

MscShelfCardDiagRowStatusEntry ::= SEQUENCE {
   mscShelfCardDiagRowStatus
      RowStatus,
   mscShelfCardDiagComponentName
      DisplayString,
   mscShelfCardDiagStorageType
      StorageType,
   mscShelfCardDiagIndex
      NonReplicated }

mscShelfCardDiagRowStatus OBJECT-TYPE
   SYNTAX     RowStatus 
   ACCESS     read-only
   STATUS     mandatory
   DESCRIPTION
     "This variable is used as the basis for SNMP naming of
      mscShelfCardDiag components.
      These components cannot be added nor deleted."
::= { mscShelfCardDiagRowStatusEntry 1 }

mscShelfCardDiagComponentName OBJECT-TYPE
   SYNTAX     DisplayString 
   ACCESS     read-only
   STATUS     mandatory
   DESCRIPTION
     "This variable provides the component's string name for
      use with the ASCII Console Interface"
::= { mscShelfCardDiagRowStatusEntry 2 }

mscShelfCardDiagStorageType OBJECT-TYPE
   SYNTAX     StorageType 
   ACCESS     read-only
   STATUS     mandatory
   DESCRIPTION
     "This variable represents the storage type value for the
      mscShelfCardDiag tables."
::= { mscShelfCardDiagRowStatusEntry 4 }

mscShelfCardDiagIndex OBJECT-TYPE
   SYNTAX     NonReplicated 
   ACCESS     not-accessible
   STATUS     mandatory
   DESCRIPTION
     "This variable represents the index for the mscShelfCardDiag tables."
::= { mscShelfCardDiagRowStatusEntry 10 }


-- Shelf Card/n Diag TrapData
-- On Passport control and function processors, hardware or software 
-- detected critical faults are preserved on the card until the power is 
-- lost. These critical faults lead to the reboot of the card and the 
-- captured trap data survives the rebooting of the card.
-- This component manages trap data stored in the persistent memory 
-- on the card. The trap data can be retrieved from the card to 
-- determine the cause of the fault.

mscShelfCardDiagTrapData OBJECT IDENTIFIER ::= { mscShelfCardDiag 2 }



mscShelfCardDiagTrapDataRowStatusTable OBJECT-TYPE
   SYNTAX     SEQUENCE OF MscShelfCardDiagTrapDataRowStatusEntry
   ACCESS     not-accessible
   STATUS     mandatory
   DESCRIPTION
     "This entry controls the addition and deletion of 
      mscShelfCardDiagTrapData components."
::= { mscShelfCardDiagTrapData 1 }

mscShelfCardDiagTrapDataRowStatusEntry OBJECT-TYPE
   SYNTAX     MscShelfCardDiagTrapDataRowStatusEntry
   ACCESS     not-accessible
   STATUS     mandatory
   DESCRIPTION
     "A single entry in the table represents a single 
      mscShelfCardDiagTrapData component."
   INDEX {
      mscShelfIndex,
      mscShelfCardIndex,
      mscShelfCardDiagIndex,
      mscShelfCardDiagTrapDataIndex }
::= { mscShelfCardDiagTrapDataRowStatusTable 1 }

MscShelfCardDiagTrapDataRowStatusEntry ::= SEQUENCE {
   mscShelfCardDiagTrapDataRowStatus
      RowStatus,
   mscShelfCardDiagTrapDataComponentName
      DisplayString,
   mscShelfCardDiagTrapDataStorageType
      StorageType,
   mscShelfCardDiagTrapDataIndex
      NonReplicated }

mscShelfCardDiagTrapDataRowStatus OBJECT-TYPE
   SYNTAX     RowStatus 
   ACCESS     read-only
   STATUS     mandatory
   DESCRIPTION
     "This variable is used as the basis for SNMP naming of
      mscShelfCardDiagTrapData components.
      These components cannot be added nor deleted."
::= { mscShelfCardDiagTrapDataRowStatusEntry 1 }

mscShelfCardDiagTrapDataComponentName OBJECT-TYPE
   SYNTAX     DisplayString 
   ACCESS     read-only
   STATUS     mandatory
   DESCRIPTION
     "This variable provides the component's string name for
      use with the ASCII Console Interface"
::= { mscShelfCardDiagTrapDataRowStatusEntry 2 }

mscShelfCardDiagTrapDataStorageType OBJECT-TYPE
   SYNTAX     StorageType 
   ACCESS     read-only
   STATUS     mandatory
   DESCRIPTION
     "This variable represents the storage type value for the
      mscShelfCardDiagTrapData tables."
::= { mscShelfCardDiagTrapDataRowStatusEntry 4 }

mscShelfCardDiagTrapDataIndex OBJECT-TYPE
   SYNTAX     NonReplicated 
   ACCESS     not-accessible
   STATUS     mandatory
   DESCRIPTION
     "This variable represents the index for the mscShelfCardDiagTrapData tables."
::= { mscShelfCardDiagTrapDataRowStatusEntry 10 }

-- 
-- *** THIS SUBTREE CURRENTLY NOT IMPLEMENTED ***
-- 

-- Shelf Card/m Diag TrapData Line/n		
-- This component represents one line of trap data report.

mscShelfCardDiagTrapDataLine OBJECT IDENTIFIER ::= { mscShelfCardDiagTrapData 2 }



mscShelfCardDiagTrapDataLineRowStatusTable OBJECT-TYPE
   SYNTAX     SEQUENCE OF MscShelfCardDiagTrapDataLineRowStatusEntry
   ACCESS     not-accessible
   STATUS     mandatory
   DESCRIPTION
     "*** THIS TABLE CURRENTLY NOT IMPLEMENTED ***

      This entry controls the addition and deletion of 
      mscShelfCardDiagTrapDataLine components."
::= { mscShelfCardDiagTrapDataLine 1 }

mscShelfCardDiagTrapDataLineRowStatusEntry OBJECT-TYPE
   SYNTAX     MscShelfCardDiagTrapDataLineRowStatusEntry
   ACCESS     not-accessible
   STATUS     mandatory
   DESCRIPTION
     "A single entry in the table represents a single 
      mscShelfCardDiagTrapDataLine component."
   INDEX {
      mscShelfIndex,
      mscShelfCardIndex,
      mscShelfCardDiagIndex,
      mscShelfCardDiagTrapDataIndex,
      mscShelfCardDiagTrapDataLineIndex }
::= { mscShelfCardDiagTrapDataLineRowStatusTable 1 }

MscShelfCardDiagTrapDataLineRowStatusEntry ::= SEQUENCE {
   mscShelfCardDiagTrapDataLineRowStatus
      RowStatus,
   mscShelfCardDiagTrapDataLineComponentName
      DisplayString,
   mscShelfCardDiagTrapDataLineStorageType
      StorageType,
   mscShelfCardDiagTrapDataLineIndex
      Integer32 }

mscShelfCardDiagTrapDataLineRowStatus OBJECT-TYPE
   SYNTAX     RowStatus 
   ACCESS     read-only
   STATUS     mandatory
   DESCRIPTION
     "This variable is used as the basis for SNMP naming of
      mscShelfCardDiagTrapDataLine components.
      These components cannot be added nor deleted."
::= { mscShelfCardDiagTrapDataLineRowStatusEntry 1 }

mscShelfCardDiagTrapDataLineComponentName OBJECT-TYPE
   SYNTAX     DisplayString 
   ACCESS     read-only
   STATUS     mandatory
   DESCRIPTION
     "This variable provides the component's string name for
      use with the ASCII Console Interface"
::= { mscShelfCardDiagTrapDataLineRowStatusEntry 2 }

mscShelfCardDiagTrapDataLineStorageType OBJECT-TYPE
   SYNTAX     StorageType 
   ACCESS     read-only
   STATUS     mandatory
   DESCRIPTION
     "This variable represents the storage type value for the
      mscShelfCardDiagTrapDataLine tables."
::= { mscShelfCardDiagTrapDataLineRowStatusEntry 4 }

mscShelfCardDiagTrapDataLineIndex OBJECT-TYPE
   SYNTAX     Integer32 (1..500)
   ACCESS     not-accessible
   STATUS     mandatory
   DESCRIPTION
     "This variable represents the index for the mscShelfCardDiagTrapDataLine tables."
::= { mscShelfCardDiagTrapDataLineRowStatusEntry 10 }

mscShelfCardDiagTrapDataLineOperTable OBJECT-TYPE
   SYNTAX     SEQUENCE OF MscShelfCardDiagTrapDataLineOperEntry
   ACCESS     not-accessible
   STATUS     mandatory
   DESCRIPTION
     "*** THIS TABLE CURRENTLY NOT IMPLEMENTED ***

      This attribute group contains operational attributes for one line of 
      trap data or recoverable error report."
::= { mscShelfCardDiagTrapDataLine 10 }

mscShelfCardDiagTrapDataLineOperEntry OBJECT-TYPE
   SYNTAX     MscShelfCardDiagTrapDataLineOperEntry
   ACCESS     not-accessible
   STATUS     mandatory
   DESCRIPTION
     "An entry in the mscShelfCardDiagTrapDataLineOperTable."
   INDEX {
      mscShelfIndex,
      mscShelfCardIndex,
      mscShelfCardDiagIndex,
      mscShelfCardDiagTrapDataIndex,
      mscShelfCardDiagTrapDataLineIndex }
::= { mscShelfCardDiagTrapDataLineOperTable 1 }

MscShelfCardDiagTrapDataLineOperEntry ::= SEQUENCE {
   mscShelfCardDiagTrapDataLineData
      ExtendedAsciiString }

mscShelfCardDiagTrapDataLineData OBJECT-TYPE
   SYNTAX     ExtendedAsciiString (SIZE (0..512))
   ACCESS     read-only
   STATUS     mandatory
   DESCRIPTION
     "This attribute contains one line of trap data or recoverable error 
      report."
::= { mscShelfCardDiagTrapDataLineOperEntry 1 }


-- Shelf Card/n Diag RecoverableError
-- This component manages recoverable errors stored in the persistent 
-- memory which are preserved on the card until the power is lost. 
-- Recoverable errors do not cause the reboot of a card. Information 
-- about the errors can be retrieved from the card to determine the 
-- cause of the fault.

mscShelfCardDiagRecErr OBJECT IDENTIFIER ::= { mscShelfCardDiag 3 }



mscShelfCardDiagRecErrRowStatusTable OBJECT-TYPE
   SYNTAX     SEQUENCE OF MscShelfCardDiagRecErrRowStatusEntry
   ACCESS     not-accessible
   STATUS     mandatory
   DESCRIPTION
     "This entry controls the addition and deletion of 
      mscShelfCardDiagRecErr components."
::= { mscShelfCardDiagRecErr 1 }

mscShelfCardDiagRecErrRowStatusEntry OBJECT-TYPE
   SYNTAX     MscShelfCardDiagRecErrRowStatusEntry
   ACCESS     not-accessible
   STATUS     mandatory
   DESCRIPTION
     "A single entry in the table represents a single 
      mscShelfCardDiagRecErr component."
   INDEX {
      mscShelfIndex,
      mscShelfCardIndex,
      mscShelfCardDiagIndex,
      mscShelfCardDiagRecErrIndex }
::= { mscShelfCardDiagRecErrRowStatusTable 1 }

MscShelfCardDiagRecErrRowStatusEntry ::= SEQUENCE {
   mscShelfCardDiagRecErrRowStatus
      RowStatus,
   mscShelfCardDiagRecErrComponentName
      DisplayString,
   mscShelfCardDiagRecErrStorageType
      StorageType,
   mscShelfCardDiagRecErrIndex
      NonReplicated }

mscShelfCardDiagRecErrRowStatus OBJECT-TYPE
   SYNTAX     RowStatus 
   ACCESS     read-only
   STATUS     mandatory
   DESCRIPTION
     "This variable is used as the basis for SNMP naming of
      mscShelfCardDiagRecErr components.
      These components cannot be added nor deleted."
::= { mscShelfCardDiagRecErrRowStatusEntry 1 }

mscShelfCardDiagRecErrComponentName OBJECT-TYPE
   SYNTAX     DisplayString 
   ACCESS     read-only
   STATUS     mandatory
   DESCRIPTION
     "This variable provides the component's string name for
      use with the ASCII Console Interface"
::= { mscShelfCardDiagRecErrRowStatusEntry 2 }

mscShelfCardDiagRecErrStorageType OBJECT-TYPE
   SYNTAX     StorageType 
   ACCESS     read-only
   STATUS     mandatory
   DESCRIPTION
     "This variable represents the storage type value for the
      mscShelfCardDiagRecErr tables."
::= { mscShelfCardDiagRecErrRowStatusEntry 4 }

mscShelfCardDiagRecErrIndex OBJECT-TYPE
   SYNTAX     NonReplicated 
   ACCESS     not-accessible
   STATUS     mandatory
   DESCRIPTION
     "This variable represents the index for the mscShelfCardDiagRecErr tables."
::= { mscShelfCardDiagRecErrRowStatusEntry 10 }

-- 
-- *** THIS SUBTREE CURRENTLY NOT IMPLEMENTED ***
-- 

-- Shelf Card/m Diag RecErr Line/n		
-- This component represents one line of recoverable error report.

mscShelfCardDiagRecErrLine OBJECT IDENTIFIER ::= { mscShelfCardDiagRecErr 2 }



mscShelfCardDiagRecErrLineRowStatusTable OBJECT-TYPE
   SYNTAX     SEQUENCE OF MscShelfCardDiagRecErrLineRowStatusEntry
   ACCESS     not-accessible
   STATUS     mandatory
   DESCRIPTION
     "*** THIS TABLE CURRENTLY NOT IMPLEMENTED ***

      This entry controls the addition and deletion of 
      mscShelfCardDiagRecErrLine components."
::= { mscShelfCardDiagRecErrLine 1 }

mscShelfCardDiagRecErrLineRowStatusEntry OBJECT-TYPE
   SYNTAX     MscShelfCardDiagRecErrLineRowStatusEntry
   ACCESS     not-accessible
   STATUS     mandatory
   DESCRIPTION
     "A single entry in the table represents a single 
      mscShelfCardDiagRecErrLine component."
   INDEX {
      mscShelfIndex,
      mscShelfCardIndex,
      mscShelfCardDiagIndex,
      mscShelfCardDiagRecErrIndex,
      mscShelfCardDiagRecErrLineIndex }
::= { mscShelfCardDiagRecErrLineRowStatusTable 1 }

MscShelfCardDiagRecErrLineRowStatusEntry ::= SEQUENCE {
   mscShelfCardDiagRecErrLineRowStatus
      RowStatus,
   mscShelfCardDiagRecErrLineComponentName
      DisplayString,
   mscShelfCardDiagRecErrLineStorageType
      StorageType,
   mscShelfCardDiagRecErrLineIndex
      Integer32 }

mscShelfCardDiagRecErrLineRowStatus OBJECT-TYPE
   SYNTAX     RowStatus 
   ACCESS     read-only
   STATUS     mandatory
   DESCRIPTION
     "This variable is used as the basis for SNMP naming of
      mscShelfCardDiagRecErrLine components.
      These components cannot be added nor deleted."
::= { mscShelfCardDiagRecErrLineRowStatusEntry 1 }

mscShelfCardDiagRecErrLineComponentName OBJECT-TYPE
   SYNTAX     DisplayString 
   ACCESS     read-only
   STATUS     mandatory
   DESCRIPTION
     "This variable provides the component's string name for
      use with the ASCII Console Interface"
::= { mscShelfCardDiagRecErrLineRowStatusEntry 2 }

mscShelfCardDiagRecErrLineStorageType OBJECT-TYPE
   SYNTAX     StorageType 
   ACCESS     read-only
   STATUS     mandatory
   DESCRIPTION
     "This variable represents the storage type value for the
      mscShelfCardDiagRecErrLine tables."
::= { mscShelfCardDiagRecErrLineRowStatusEntry 4 }

mscShelfCardDiagRecErrLineIndex OBJECT-TYPE
   SYNTAX     Integer32 (1..500)
   ACCESS     not-accessible
   STATUS     mandatory
   DESCRIPTION
     "This variable represents the index for the mscShelfCardDiagRecErrLine tables."
::= { mscShelfCardDiagRecErrLineRowStatusEntry 10 }

mscShelfCardDiagRecErrLineOperTable OBJECT-TYPE
   SYNTAX     SEQUENCE OF MscShelfCardDiagRecErrLineOperEntry
   ACCESS     not-accessible
   STATUS     mandatory
   DESCRIPTION
     "*** THIS TABLE CURRENTLY NOT IMPLEMENTED ***

      This attribute group contains operational attributes for one line of 
      trap data or recoverable error report."
::= { mscShelfCardDiagRecErrLine 10 }

mscShelfCardDiagRecErrLineOperEntry OBJECT-TYPE
   SYNTAX     MscShelfCardDiagRecErrLineOperEntry
   ACCESS     not-accessible
   STATUS     mandatory
   DESCRIPTION
     "An entry in the mscShelfCardDiagRecErrLineOperTable."
   INDEX {
      mscShelfIndex,
      mscShelfCardIndex,
      mscShelfCardDiagIndex,
      mscShelfCardDiagRecErrIndex,
      mscShelfCardDiagRecErrLineIndex }
::= { mscShelfCardDiagRecErrLineOperTable 1 }

MscShelfCardDiagRecErrLineOperEntry ::= SEQUENCE {
   mscShelfCardDiagRecErrLineData
      ExtendedAsciiString }

mscShelfCardDiagRecErrLineData OBJECT-TYPE
   SYNTAX     ExtendedAsciiString (SIZE (0..512))
   ACCESS     read-only
   STATUS     mandatory
   DESCRIPTION
     "This attribute contains one line of trap data or recoverable error 
      report."
::= { mscShelfCardDiagRecErrLineOperEntry 1 }

-- 
-- *** THIS SUBTREE CURRENTLY NOT IMPLEMENTED ***
-- 

-- DaughterCard/n
-- The DaughterCard component contains the information of a 
-- daughter card located on a card. The instance value of the 
-- daughterCard indicates the physical location of its socket on the 
-- card.

mscShelfCardDcard OBJECT IDENTIFIER ::= { mscShelfCard 16 }



mscShelfCardDcardRowStatusTable OBJECT-TYPE
   SYNTAX     SEQUENCE OF MscShelfCardDcardRowStatusEntry
   ACCESS     not-accessible
   STATUS     mandatory
   DESCRIPTION
     "*** THIS TABLE CURRENTLY NOT IMPLEMENTED ***

      This entry controls the addition and deletion of 
      mscShelfCardDcard components."
::= { mscShelfCardDcard 1 }

mscShelfCardDcardRowStatusEntry OBJECT-TYPE
   SYNTAX     MscShelfCardDcardRowStatusEntry
   ACCESS     not-accessible
   STATUS     mandatory
   DESCRIPTION
     "A single entry in the table represents a single 
      mscShelfCardDcard component."
   INDEX {
      mscShelfIndex,
      mscShelfCardIndex,
      mscShelfCardDcardIndex }
::= { mscShelfCardDcardRowStatusTable 1 }

MscShelfCardDcardRowStatusEntry ::= SEQUENCE {
   mscShelfCardDcardRowStatus
      RowStatus,
   mscShelfCardDcardComponentName
      DisplayString,
   mscShelfCardDcardStorageType
      StorageType,
   mscShelfCardDcardIndex
      Integer32 }

mscShelfCardDcardRowStatus OBJECT-TYPE
   SYNTAX     RowStatus 
   ACCESS     read-only
   STATUS     mandatory
   DESCRIPTION
     "This variable is used as the basis for SNMP naming of
      mscShelfCardDcard components.
      These components cannot be added nor deleted."
::= { mscShelfCardDcardRowStatusEntry 1 }

mscShelfCardDcardComponentName OBJECT-TYPE
   SYNTAX     DisplayString 
   ACCESS     read-only
   STATUS     mandatory
   DESCRIPTION
     "This variable provides the component's string name for
      use with the ASCII Console Interface"
::= { mscShelfCardDcardRowStatusEntry 2 }

mscShelfCardDcardStorageType OBJECT-TYPE
   SYNTAX     StorageType 
   ACCESS     read-only
   STATUS     mandatory
   DESCRIPTION
     "This variable represents the storage type value for the
      mscShelfCardDcard tables."
::= { mscShelfCardDcardRowStatusEntry 4 }

mscShelfCardDcardIndex OBJECT-TYPE
   SYNTAX     Integer32 (1..15)
   ACCESS     not-accessible
   STATUS     mandatory
   DESCRIPTION
     "This variable represents the index for the mscShelfCardDcard tables."
::= { mscShelfCardDcardRowStatusEntry 10 }

mscShelfCardDcardDcardOperTable OBJECT-TYPE
   SYNTAX     SEQUENCE OF MscShelfCardDcardDcardOperEntry
   ACCESS     not-accessible
   STATUS     mandatory
   DESCRIPTION
     "*** THIS TABLE CURRENTLY NOT IMPLEMENTED ***

      This group contains the operational attributes of the DaughterCard 
      component."
::= { mscShelfCardDcard 17 }

mscShelfCardDcardDcardOperEntry OBJECT-TYPE
   SYNTAX     MscShelfCardDcardDcardOperEntry
   ACCESS     not-accessible
   STATUS     mandatory
   DESCRIPTION
     "An entry in the mscShelfCardDcardDcardOperTable."
   INDEX {
      mscShelfIndex,
      mscShelfCardIndex,
      mscShelfCardDcardIndex }
::= { mscShelfCardDcardDcardOperTable 1 }

MscShelfCardDcardDcardOperEntry ::= SEQUENCE {
   mscShelfCardDcardType
      INTEGER,
   mscShelfCardDcardMemorySize
      Unsigned32,
   mscShelfCardDcardProductCode
      AsciiString }

mscShelfCardDcardType OBJECT-TYPE
   SYNTAX     INTEGER  {
                 unknown(0),
                 ram(1),
                 aqm(2),
                 pqc(3),
                 aqmpqc(4),
                 processor(5) }
   ACCESS     read-only
   STATUS     mandatory
   DESCRIPTION
     "This attributes indicates the type of a daugher card."
::= { mscShelfCardDcardDcardOperEntry 1 }

mscShelfCardDcardMemorySize OBJECT-TYPE
   SYNTAX     Unsigned32 (0..2147483647)
   ACCESS     read-only
   STATUS     mandatory
   DESCRIPTION
     "This attribute indicates the memory size in megabytes of the 
      daughter card."
::= { mscShelfCardDcardDcardOperEntry 2 }

mscShelfCardDcardProductCode OBJECT-TYPE
   SYNTAX     AsciiString (SIZE (0..12))
   ACCESS     read-only
   STATUS     mandatory
   DESCRIPTION
     "This attribute indicates the product equipment code of the daughter 
      card."
::= { mscShelfCardDcardDcardOperEntry 3 }


-- Module wide provisioning data is used to define a number of 
-- attributes used by various systems within the module.

mscMod OBJECT IDENTIFIER ::= { mscComponents 16 }



mscModRowStatusTable OBJECT-TYPE
   SYNTAX     SEQUENCE OF MscModRowStatusEntry
   ACCESS     not-accessible
   STATUS     mandatory
   DESCRIPTION
     "This entry controls the addition and deletion of 
      mscMod components."
::= { mscMod 1 }

mscModRowStatusEntry OBJECT-TYPE
   SYNTAX     MscModRowStatusEntry
   ACCESS     not-accessible
   STATUS     mandatory
   DESCRIPTION
     "A single entry in the table represents a single 
      mscMod component."
   INDEX {
      mscModIndex }
::= { mscModRowStatusTable 1 }

MscModRowStatusEntry ::= SEQUENCE {
   mscModRowStatus
      RowStatus,
   mscModComponentName
      DisplayString,
   mscModStorageType
      StorageType,
   mscModIndex
      NonReplicated }

mscModRowStatus OBJECT-TYPE
   SYNTAX     RowStatus 
   ACCESS     read-only
   STATUS     mandatory
   DESCRIPTION
     "This variable is used as the basis for SNMP naming of
      mscMod components.
      These components cannot be added nor deleted."
::= { mscModRowStatusEntry 1 }

mscModComponentName OBJECT-TYPE
   SYNTAX     DisplayString 
   ACCESS     read-only
   STATUS     mandatory
   DESCRIPTION
     "This variable provides the component's string name for
      use with the ASCII Console Interface"
::= { mscModRowStatusEntry 2 }

mscModStorageType OBJECT-TYPE
   SYNTAX     StorageType 
   ACCESS     read-only
   STATUS     mandatory
   DESCRIPTION
     "This variable represents the storage type value for the
      mscMod tables."
::= { mscModRowStatusEntry 4 }

mscModIndex OBJECT-TYPE
   SYNTAX     NonReplicated 
   ACCESS     not-accessible
   STATUS     mandatory
   DESCRIPTION
     "This variable represents the index for the mscMod tables."
::= { mscModRowStatusEntry 10 }

mscModProvTable OBJECT-TYPE
   SYNTAX     SEQUENCE OF MscModProvEntry
   ACCESS     not-accessible
   STATUS     mandatory
   DESCRIPTION
     "Mod Provisionable
      This group provides attributes that are used by internal and external 
      systems to identify the module."
::= { mscMod 10 }

mscModProvEntry OBJECT-TYPE
   SYNTAX     MscModProvEntry
   ACCESS     not-accessible
   STATUS     mandatory
   DESCRIPTION
     "An entry in the mscModProvTable."
   INDEX {
      mscModIndex }
::= { mscModProvTable 1 }

MscModProvEntry ::= SEQUENCE {
   mscModNodeId
      Unsigned32,
   mscModNodeName
      AsciiString,
   mscModNamsId
      Unsigned32,
   mscModRegionId
      Unsigned32,
   mscModNodePrefix
      AsciiString }

mscModNodeId OBJECT-TYPE
   SYNTAX     Unsigned32 (1..4095)
   ACCESS     read-write
   STATUS     mandatory
   DESCRIPTION
     "The nodeId is a number that uniquely identifies a Magellan Passport 
      module in a Passport network.
      
      Changing the value of the nodeId will cause the node to restart."
::= { mscModProvEntry 1 }

mscModNodeName OBJECT-TYPE
   SYNTAX     AsciiString (SIZE (1..12))
   ACCESS     read-write
   STATUS     mandatory
   DESCRIPTION
     "The nodeName is a 12 character ASCII string that is unique to every 
      Passport module in a Passport network. This name is the component 
      instance value of EM - the root of the Passport component 
      hierarchy. It has, therefore, the same restriction and behaviour as 
      any ascii string instance value, e.g., it is converted to upper case.
      
      Note that the EM component is typically suppressed on output.
      
      Changing the value of the nodeName will cause the node to restart."
   DEFVAL     { '4e4f4e414d45'H }  -- "NONAME"
::= { mscModProvEntry 2 }

mscModNamsId OBJECT-TYPE
   SYNTAX     Unsigned32 (256..49151)
   ACCESS     read-write
   STATUS     mandatory
   DESCRIPTION
     "This attribute stores the Network Administration (Nams) Identifier 
      associated with the Passport node. It must be unique across the 
      entire network of Passport nodes supporting the transport of DPN 
      traffic as well as all RMs and AMs in the network.
      
      The namsId must be set when a DpnAddressPlan component is 
      configured on an Passport node.
      
      The namsId is used in the accounting record, statistics record and in 
      time change accounting record and identifies nodes in these records.
      
      The Nams Id is to be assigned by the network administrator.
      Value 49151 indicates that no Nams Id was assigned to the module.
      
      Changing the value of the namsId will cause the node to restart."
   DEFVAL     { 49151 }
::= { mscModProvEntry 3 }

mscModRegionId OBJECT-TYPE
   SYNTAX     Unsigned32 (0..126)
   ACCESS     read-write
   STATUS     mandatory
   DESCRIPTION
     "This attribute identifies the Topology Region to which the node 
      belongs. Nodes will only exchange topological information with 
      connected nodes in the same region.
      
      The default value of 0 indicates that no regionId has been assigned 
      to the module. A module using the default regionId belongs to the 
      same region as the first neighbour which stages with it using a non-
      zero regionId. If another neighbour tries to stage using a different 
      non-zero regionId, the trunk will not be allowed to come up. 
      
      Changing the value of the regionId will NOT cause the node to 
      restart."
   DEFVAL     { 0 }
::= { mscModProvEntry 4 }

mscModNodePrefix OBJECT-TYPE
   SYNTAX     AsciiString (SIZE (0..26))
   ACCESS     read-write
   STATUS     mandatory
   DESCRIPTION
     "This attribute specifies an NSAP prefix which is distributed to all 
      other Passport nodes within a Topology region and by which this 
      node can be identified. This prefix is used by PORS, PNNI routing, 
      and Data Shunts.
      
      PORS calls that use NSAP addressing (for example, CES) will look 
      for the node with the longest NSAP prefix that matches the called 
      party address. The NSAP prefixes that PORS matches against are 
      the nodePrefix and the alternatePorsPrefixes. 
      
      PNNI forms the default value of the nodeAddressPrefix under the 
      AtmPnni component with this NSAP prefix followed by a unique 
      MAC address. 
      
      Data Shunts uses the nodePrefix to form an NSAP address that is 
      registered with the Networking API. This NSAP address is used to 
      identify this node when establishing a Data Shunt.
      
      The value entered must be 26 characters long. All characters must 
      be hexadecimal with the following restrictions:
      - the first two characters must be either '39', '45', or '47'
      - if the first two characters are '45', the 18th character must be an 
      'f' or an 'F'"
   DEFVAL     { ''H }  -- ""
::= { mscModProvEntry 5 }

mscModNodePrefixesTable OBJECT-TYPE
   SYNTAX     SEQUENCE OF MscModNodePrefixesEntry
   ACCESS     not-accessible
   STATUS     obsolete
   DESCRIPTION
     "This attribute specifies five different NSAP prefixes which are 
      distributed to all other Passport nodes within a Topology region and 
      by which this node can be identified. PORS calls that use NSAP 
      addressing (for example, CES) will look for the node with the 
      longest NSAP prefix that matches the called party address. The 
      default value of the nodeAddressPrefix under the AtmPnni 
      component is formed by the first NSAP prefix followed by a unique 
      MAC address. Each NSAP prefix may contain 40 hexadecimal 
      characters with the exception of the first prefix which has a 
      maximum length of 26 chracacters.
      
      This attribute was never deployed and will be removed prior to Gate 
      2.."
::= { mscMod 338 }

mscModNodePrefixesEntry OBJECT-TYPE
   SYNTAX     MscModNodePrefixesEntry
   ACCESS     not-accessible
   STATUS     obsolete
   DESCRIPTION
     "An entry in the mscModNodePrefixesTable."
   INDEX {
      mscModIndex,
      mscModNodePrefixesIndex }
::= { mscModNodePrefixesTable 1 }

MscModNodePrefixesEntry ::= SEQUENCE {
   mscModNodePrefixesIndex
      Integer32,
   mscModNodePrefixesValue
      AsciiString }

mscModNodePrefixesIndex OBJECT-TYPE
   SYNTAX     Integer32 (0..4)
   ACCESS     not-accessible
   STATUS     obsolete
   DESCRIPTION
     "This variable represents the mscModNodePrefixesTable
      specific index for the mscModNodePrefixesTable."
::= { mscModNodePrefixesEntry 1 }

mscModNodePrefixesValue OBJECT-TYPE
   SYNTAX     AsciiString (SIZE (0..40))
   ACCESS     read-write
   STATUS     obsolete
   DESCRIPTION
     "This variable represents an individual value for the
      mscModNodePrefixesTable."
::= { mscModNodePrefixesEntry 2 }

mscModAlternatePorsPrefixesTable OBJECT-TYPE
   SYNTAX     SEQUENCE OF MscModAlternatePorsPrefixesEntry
   ACCESS     not-accessible
   STATUS     mandatory
   DESCRIPTION
     "This attribute specifies four NSAP prefixes which are distributed to 
      all other Passport nodes within a Topology region and by which this 
      node can be identified. These prefixes are used by PORS. 
      
      PORS calls that use NSAP addressing (for example, CES) will look 
      for the node with the longest NSAP prefix that matches the called 
      party address. The NSAP prefixes that PORS matches against are 
      the alternatePorsPrefixes and the nodePrefix. 
      
      These prefixes may contain up to 40 hexadecimal characters."
::= { mscMod 405 }

mscModAlternatePorsPrefixesEntry OBJECT-TYPE
   SYNTAX     MscModAlternatePorsPrefixesEntry
   ACCESS     not-accessible
   STATUS     mandatory
   DESCRIPTION
     "An entry in the mscModAlternatePorsPrefixesTable."
   INDEX {
      mscModIndex,
      mscModAlternatePorsPrefixesIndex }
::= { mscModAlternatePorsPrefixesTable 1 }

MscModAlternatePorsPrefixesEntry ::= SEQUENCE {
   mscModAlternatePorsPrefixesIndex
      Integer32,
   mscModAlternatePorsPrefixesValue
      AsciiString }

mscModAlternatePorsPrefixesIndex OBJECT-TYPE
   SYNTAX     Integer32 (0..3)
   ACCESS     not-accessible
   STATUS     mandatory
   DESCRIPTION
     "This variable represents the mscModAlternatePorsPrefixesTable
      specific index for the mscModAlternatePorsPrefixesTable."
::= { mscModAlternatePorsPrefixesEntry 1 }

mscModAlternatePorsPrefixesValue OBJECT-TYPE
   SYNTAX     AsciiString (SIZE (0..40))
   ACCESS     read-write
   STATUS     mandatory
   DESCRIPTION
     "This variable represents an individual value for the
      mscModAlternatePorsPrefixesTable."
::= { mscModAlternatePorsPrefixesEntry 2 }




-- 
-- Version and Compliance statements
-- 



-- Object-Group Statement:
-- A list of all current accessible leaf objects.

-- OBJECTS { mscShelfCardComponentName,
--           mscShelfCardLocalMsgBlockUsage,
--           mscShelfCardInsertedCardType,
--           mscModStorageType,
--           mscShelfCardTestCauseOfTermination,
--           mscShelfCardActiveFirmwareVersion,
--           mscShelfCardTestTimeRemaining,
--           mscShelfCardLocalMsgBlockUsageMin,
--           mscShelfCardMemoryUsageAvgMaxValue,
--           mscShelfCommentText,
--           mscShelfCardDcardComponentName,
--           mscModRowStatus,
--           mscShelfShelfType,
--           mscShelfCardTestLoadingFrmDataValue,
--           mscShelfCardMemoryUsageAvgValue,
--           mscShelfCardCommentText,
--           mscShelfStorageType,
--           mscModNodeId,
--           mscModNodeName,
--           mscShelfCardMsgBlockUsageAvgMin,
--           mscShelfCardTestCustomizedPattern,
--           mscShelfCardDiagRecErrStorageType,
--           mscShelfCardTestComponentName,
--           mscShelfCardStandbyStatus,
--           mscShelfCardProductCode,
--           mscShelfCardDiagTrapDataLineData,
--           mscShelfCardMemoryUsageAvgMinValue,
--           mscShelfCardDcardMemorySize,
--           mscShelfCardDiagRecErrLineStorageType,
--           mscShelfCardCurrentLpValue,
--           mscShelfCardTestTargetCard,
--           mscShelfCardDcardStorageType,
--           mscShelfCardDcardProductCode,
--           mscModNamsId,
--           mscShelfCardTestSizeValue,
--           mscShelfCardDiagRecErrLineComponentName,
--           mscShelfRowStatus,
--           mscShelfCardAdminState,
--           mscShelfCardImRevisionCode,
--           mscShelfCardControlStatus,
--           mscShelfCardUnknownStatus,
--           mscShelfCardRowStatus,
--           mscShelfCardDiagRecErrRowStatus,
--           mscModNodePrefix,
--           mscShelfCardCpuUtilAvg,
--           mscShelfCardDiagRecErrLineRowStatus,
--           mscShelfCardCpuUtilAvgMax,
--           mscShelfCardTestDuration,
--           mscShelfCardMsgBlockUsageAvgMax,
--           mscShelfCardDiagTrapDataComponentName,
--           mscShelfCardSparingConnection,
--           mscShelfCardDiagComponentName,
--           mscShelfCardDiagTrapDataLineComponentName,
--           mscShelfCardUsageState,
--           mscShelfCardMsgBlockUsageAvg,
--           mscShelfCardDcardRowStatus,
--           mscShelfCardSparingConnectionStatus,
--           mscShelfCardTestStorageType,
--           mscShelfCardLocalMsgBlockUsageAvg,
--           mscShelfCardOperationalState,
--           mscShelfCardMemoryCapacityValue,
--           mscShelfCardSerialNumber,
--           mscShelfCardCpuUtilAvgMin,
--           mscShelfCardTestAdminState,
--           mscShelfNumberOfSlots,
--           mscShelfHardwareFailures,
--           mscShelfCardTestElapsedTime,
--           mscShelfCardConfiguredLPsValue,
--           mscShelfCardTestRowStatus,
--           mscShelfCardSelfTestFault,
--           mscShelfCardMemoryUsageValue,
--           mscShelfCardAvailabilityStatus,
--           mscShelfCardDiagTrapDataStorageType,
--           mscShelfCardDiagStorageType,
--           mscShelfCardAlarmStatus,
--           mscShelfCardTestUsageState,
--           mscModAlternatePorsPrefixesValue,
--           mscShelfCardDiagTrapDataLineStorageType,
--           mscShelfCardTimeInterval,
--           mscShelfCardFailureCause,
--           mscModComponentName,
--           mscShelfCardStorageType,
--           mscModRegionId,
--           mscShelfBackplaneOperatingMode,
--           mscShelfCardDiagRecErrLineData,
--           mscShelfCardTestOperationalState,
--           mscShelfCardDiagTrapDataRowStatus,
--           mscShelfCardPmRevisionCode,
--           mscShelfCardDiagRowStatus,
--           mscShelfCardInactiveFirmwareVersion,
--           mscShelfCardHardwareAlarm,
--           mscShelfCardDcardType,
--           mscShelfCardTestFrmPatternType,
--           mscShelfCardDiagTrapDataLineRowStatus,
--           mscShelfCardTestFrmPriorities,
--           mscShelfComponentName,
--           mscShelfCardCardType,
--           mscShelfCardCpuUtil,
--           mscShelfCardLocalMsgBlockCapacity,
--           mscShelfCardTestVerificationFrmDataValue,
--           mscShelfCardProceduralStatus,
--           mscShelfCardTestFrmTypes,
--           mscShelfCardLocalMsgBlockUsageMax,
--           mscShelfCardMsgBlockCapacity,
--           mscShelfCardMsgBlockUsage,
--           mscShelfCardDiagRecErrComponentName }
-- STATUS  mandatory
-- DESCRIPTION
--   "A list of all current accessible leaf objects."

baseShelfGroup OBJECT IDENTIFIER ::= { baseShelfMIB 1 }
baseShelfGroupCA OBJECT IDENTIFIER ::= { baseShelfGroup 1 }
baseShelfGroupCA02 OBJECT IDENTIFIER ::= { baseShelfGroupCA 3 }
baseShelfGroupCA02A OBJECT IDENTIFIER ::= { baseShelfGroupCA02 2 }



-- Agent-Capabilities Statement:

-- PRODUCT-RELEASE "MscPassport Release 1.2 BaseShelf."
-- STATUS          mandatory
-- DESCRIPTION     "Carrier Passport BaseShelf MIB: MIB Version CA02A,
--                  Software Version CA02S9C."
-- SUPPORTS        Nortel-MsCarrier-MscPassport-BaseShelfMIB
--    INCLUDES     { baseShelfGroupCA02A }

baseShelfCapabilities OBJECT IDENTIFIER ::= { baseShelfMIB 3 }
baseShelfCapabilitiesCA OBJECT IDENTIFIER ::= { baseShelfCapabilities 1 }
baseShelfCapabilitiesCA02 OBJECT IDENTIFIER ::= { baseShelfCapabilitiesCA 3 }
baseShelfCapabilitiesCA02A OBJECT IDENTIFIER ::= { baseShelfCapabilitiesCA02 2 }





END
