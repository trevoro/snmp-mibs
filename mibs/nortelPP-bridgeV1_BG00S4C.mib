Nortel-Magellan-Passport-BridgeMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      BridgeId,
      InterfaceIndex,
      Gauge32,
      Integer32,
      MacAddress,
      Unsigned32
   FROM Nortel-Magellan-Passport-StandardTextualConventionsMIB

      AsciiString,
      Hex,
      NonReplicated,
      HexString,
      Link,
      AsciiStringIndex,
      DashedHexString
   FROM Nortel-Magellan-Passport-TextualConventionsMIB

      vrIndex,
      vrPpIndex,
      vrPp,
      vr
   FROM Nortel-Magellan-Passport-VirtualRouterMIB;




-- LAST-UPDATED   "9904150000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Bridge Enterprise MIB."

bridgeMIB OBJECT IDENTIFIER ::= { passportMIBs 25 }










-- Vr/<string> Pp/<string> ClusterTbBridgePort
-- This component represents the functionality called Cluster Bridging. 
-- Cluster Bridging allows for MAC frames, carrying packets belonging a 
-- certain network protocol, to be bridged and routed at the same time. 
-- Also, it provides for a convenient way to manage the entire cluster of 
-- LANs, using a single attachment point to the cluster of LANs, the 
-- Cluster Bridge Port. To realize these features, the network protocol(s) 
-- should also be provisioned on same port as the Cluster Bridge Port. 
-- ClusterTbBridgePort represents a cluster of Tb LANs. 

vrPpTbcl OBJECT IDENTIFIER ::= { vrPp 2 }



vrPpTbclRowStatusTable OBJECT-TYPE
   SYNTAX     SEQUENCE OF VrPpTbclRowStatusEntry
   ACCESS     not-accessible
   STATUS     mandatory
   DESCRIPTION
     "This entry controls the addition and deletion of 
      vrPpTbcl components."
::= { vrPpTbcl 1 }

vrPpTbclRowStatusEntry OBJECT-TYPE
   SYNTAX     VrPpTbclRowStatusEntry
   ACCESS     not-accessible
   STATUS     mandatory
   DESCRIPTION
     "A single entry in the table represents a single 
      vrPpTbcl component."
   INDEX {
      vrIndex,
      vrPpIndex,
      vrPpTbclIndex }
::= { vrPpTbclRowStatusTable 1 }

VrPpTbclRowStatusEntry ::= SEQUENCE {
   vrPpTbclRowStatus
      RowStatus,
   vrPpTbclComponentName
      DisplayString,
   vrPpTbclStorageType
      StorageType,
   vrPpTbclIndex
      NonReplicated }

vrPpTbclRowStatus OBJECT-TYPE
   SYNTAX     RowStatus 
   ACCESS     read-write
   STATUS     mandatory
   DESCRIPTION
     "This variable is used as the basis for SNMP naming of
      vrPpTbcl components.
      These components can be added and deleted."
::= { vrPpTbclRowStatusEntry 1 }

vrPpTbclComponentName OBJECT-TYPE
   SYNTAX     DisplayString 
   ACCESS     read-only
   STATUS     mandatory
   DESCRIPTION
     "This variable provides the component's string name for
      use with the ASCII Console Interface"
::= { vrPpTbclRowStatusEntry 2 }

vrPpTbclStorageType OBJECT-TYPE
   SYNTAX     StorageType 
   ACCESS     read-only
   STATUS     mandatory
   DESCRIPTION
     "This variable represents the storage type value for the
      vrPpTbcl tables."
::= { vrPpTbclRowStatusEntry 4 }

vrPpTbclIndex OBJECT-TYPE
   SYNTAX     NonReplicated 
   ACCESS     not-accessible
   STATUS     mandatory
   DESCRIPTION
     "This variable represents the index for the vrPpTbcl tables."
::= { vrPpTbclRowStatusEntry 10 }

vrPpTbclProvTable OBJECT-TYPE
   SYNTAX     SEQUENCE OF VrPpTbclProvEntry
   ACCESS     not-accessible
   STATUS     mandatory
   DESCRIPTION
     "This group houses all the provisionable attributes that belong to the this 
      group. This group of attributes is applicable to all types of bridge ports 
      and represent the common factor between them. These attributes 
      influence the working of a bridge port."
::= { vrPpTbcl 10 }

vrPpTbclProvEntry OBJECT-TYPE
   SYNTAX     VrPpTbclProvEntry
   ACCESS     not-accessible
   STATUS     mandatory
   DESCRIPTION
     "An entry in the vrPpTbclProvTable."
   INDEX {
      vrIndex,
      vrPpIndex,
      vrPpTbclIndex }
::= { vrPpTbclProvTable 1 }

VrPpTbclProvEntry ::= SEQUENCE {
   vrPpTbclTranslateIpx
      INTEGER,
   vrPpTbclFragmentIp
      INTEGER,
   vrPpTbclServiceClass
      INTEGER,
   vrPpTbclConvertArpMacAddress
      INTEGER,
   vrPpTbclPortNum
      Unsigned32,
   vrPpTbclOutboundFrameMediaType
      INTEGER }

vrPpTbclTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { vrPpTbclProvEntry 1 }

vrPpTbclFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { vrPpTbclProvEntry 2 }

vrPpTbclServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { vrPpTbclProvEntry 3 }

vrPpTbclConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { vrPpTbclProvEntry 4 }

vrPpTbclPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { vrPpTbclProvEntry 5 }

vrPpTbclOutboundFrameMediaType OBJECT-TYPE
   SYNTAX     INTEGER  {
                 unaltered(1),
                 ethernetConv(2) }
   ACCESS     read-write
   STATUS     mandatory
   DESCRIPTION
     "This attribute specifies the media type the frame must be in before it is 
      to be forwarded over the outbound supported WAN Bridge Protocol 
      Port. The attribute only applies to outbound Bridge Protocol Port.
      
      For supported bridge ports, if the attribute value remains set to the 
      default value of unaltered then there will be no frame conversion. When 
      the value is set to the value ethernetConv then all frames being 
      forwarded out the outbound WAN Port will be converted to ethernet 
      before forwarding takes place. The only outbound WAN medias that 
      currently support conversion are: FR (Frame Relay) and VNS. All other 
      medias will fail the Bridge Port semantic check when attempts are made 
      to alter this attribute. 
      
      The following is an example of what the user may be able to do. Frames 
      originating from a Token Ring are to be flooded out onto another Token 
      Ring and a Frame Relay Port. The token ring Outbound port performs 
      no translation, yet the FR Port has the outboundFrameMediaType 
      attribute set to ethernetConv which results in the frame being translated 
      into Ethernet format from Token Ring format before Frame Relay does 
      its encapsulation and transmits over the FR port."
   DEFVAL     { unaltered }
::= { vrPpTbclProvEntry 6 }

vrPpTbclTbProvTable OBJECT-TYPE
   SYNTAX     SEQUENCE OF VrPpTbclTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { vrPpTbcl 11 }

vrPpTbclTbProvEntry OBJECT-TYPE
   SYNTAX     VrPpTbclTbProvEntry
   ACCESS     not-accessible
   STATUS     mandatory
   DESCRIPTION
     "An entry in the vrPpTbclTbProvTable."
   INDEX {
      vrIndex,
      vrPpIndex,
      vrPpTbclIndex }
::= { vrPpTbclTbProvTable 1 }

VrPpTbclTbProvEntry ::= SEQUENCE {
   vrPpTbclSecureOption
      INTEGER }

vrPpTbclSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { vrPpTbclTbProvEntry 1 }

vrPpTbclStpProvTable OBJECT-TYPE
   SYNTAX     SEQUENCE OF VrPpTbclStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { vrPpTbcl 12 }

vrPpTbclStpProvEntry OBJECT-TYPE
   SYNTAX     VrPpTbclStpProvEntry
   ACCESS     not-accessible
   STATUS     mandatory
   DESCRIPTION
     "An entry in the vrPpTbclStpProvTable."
   INDEX {
      vrIndex,
      vrPpIndex,
      vrPpTbclIndex }
::= { vrPpTbclStpProvTable 1 }

VrPpTbclStpProvEntry ::= SEQUENCE {
   vrPpTbclAdminStatus
      INTEGER,
   vrPpTbclPortStateStpControl
      INTEGER,
   vrPpTbclStpTypeProv
      INTEGER,
   vrPpTbclPortPriority
      Unsigned32,
   vrPpTbclPathCost
      Unsigned32,
   vrPpTbclPathCostMethod
      INTEGER }

vrPpTbclAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { vrPpTbclStpProvEntry 1 }

vrPpTbclPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { vrPpTbclStpProvEntry 2 }

vrPpTbclStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { vrPpTbclStpProvEntry 3 }

vrPpTbclPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { vrPpTbclStpProvEntry 4 }

vrPpTbclPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { vrPpTbclStpProvEntry 5 }

vrPpTbclPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { vrPpTbclStpProvEntry 6 }

vrPpTbclDIProvTable OBJECT-TYPE
   SYNTAX     SEQUENCE OF VrPpTbclDIProvEntry
   ACCESS     not-accessible
   STATUS     mandatory
   DESCRIPTION
     "This group houses all the provisionable, domain specific attributes for a 
      non-encapsulating bridge port."
::= { vrPpTbcl 13 }

vrPpTbclDIProvEntry OBJECT-TYPE
   SYNTAX     VrPpTbclDIProvEntry
   ACCESS     not-accessible
   STATUS     mandatory
   DESCRIPTION
     "An entry in the vrPpTbclDIProvTable."
   INDEX {
      vrIndex,
      vrPpIndex,
      vrPpTbclIndex }
::= { vrPpTbclDIProvTable 1 }

VrPpTbclDIProvEntry ::= SEQUENCE {
   vrPpTbclDomainNum
      Unsigned32,
   vrPpTbclPreserveDomain
      INTEGER }

vrPpTbclDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { vrPpTbclDIProvEntry 1 }

vrPpTbclPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { vrPpTbclDIProvEntry 2 }

vrPpTbclStateTable OBJECT-TYPE
   SYNTAX     SEQUENCE OF VrPpTbclStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpTbcl 14 }

vrPpTbclStateEntry OBJECT-TYPE
   SYNTAX     VrPpTbclStateEntry
   ACCESS     not-accessible
   STATUS     mandatory
   DESCRIPTION
     "An entry in the vrPpTbclStateTable."
   INDEX {
      vrIndex,
      vrPpIndex,
      vrPpTbclIndex }
::= { vrPpTbclStateTable 1 }

VrPpTbclStateEntry ::= SEQUENCE {
   vrPpTbclAdminState
      INTEGER,
   vrPpTbclOperationalState
      INTEGER,
   vrPpTbclUsageState
      INTEGER }

vrPpTbclAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpTbclStateEntry 1 }

vrPpTbclOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpTbclStateEntry 2 }

vrPpTbclUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpTbclStateEntry 3 }

vrPpTbclOperStatusTable OBJECT-TYPE
   SYNTAX     SEQUENCE OF VrPpTbclOperStatusEntry
   ACCESS     not-accessible
   STATUS     mandatory
   DESCRIPTION
     "This group includes the Operational Status attribute. This attribute 
      defines the current operational state of this component."
::= { vrPpTbcl 15 }

vrPpTbclOperStatusEntry OBJECT-TYPE
   SYNTAX     VrPpTbclOperStatusEntry
   ACCESS     not-accessible
   STATUS     mandatory
   DESCRIPTION
     "An entry in the vrPpTbclOperStatusTable."
   INDEX {
      vrIndex,
      vrPpIndex,
      vrPpTbclIndex }
::= { vrPpTbclOperStatusTable 1 }

VrPpTbclOperStatusEntry ::= SEQUENCE {
   vrPpTbclSnmpOperStatus
      INTEGER }

vrPpTbclSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpTbclOperStatusEntry 1 }

vrPpTbclOperTable OBJECT-TYPE
   SYNTAX     SEQUENCE OF VrPpTbclOperEntry
   ACCESS     not-accessible
   STATUS     mandatory
   DESCRIPTION
     "This group houses all the operational attributes belonging to the base 
      group. The base group of attributes is applicable to all types of bridge 
      ports and represent the common factor between them. These attributes in 
      part, reflect the state of a bridge port."
::= { vrPpTbcl 16 }

vrPpTbclOperEntry OBJECT-TYPE
   SYNTAX     VrPpTbclOperEntry
   ACCESS     not-accessible
   STATUS     mandatory
   DESCRIPTION
     "An entry in the vrPpTbclOperTable."
   INDEX {
      vrIndex,
      vrPpIndex,
      vrPpTbclIndex }
::= { vrPpTbclOperTable 1 }

VrPpTbclOperEntry ::= SEQUENCE {
   vrPpTbclPortName
      AsciiString,
   vrPpTbclUpTime
      Unsigned32,
   vrPpTbclDownTime
      Unsigned32,
   vrPpTbclBridgingMode
      INTEGER,
   vrPpTbclBridgePortConfig
      INTEGER,
   vrPpTbclBridgePortType
      INTEGER,
   vrPpTbclIfIndex
      InterfaceIndex,
   vrPpTbclDelayExceededDiscards
      Counter32,
   vrPpTbclMtuExceededDiscards
      Counter32 }

vrPpTbclPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { vrPpTbclOperEntry 1 }

vrPpTbclUpTime OBJECT-TYPE
   SYNTAX     Unsigned32 (0..4294967295)
   ACCESS     read-only
   STATUS     mandatory
   DESCRIPTION
     "This attribute specifies the accumulated up time of this bridge port since 
      the last reset occurred."
   DEFVAL     { 0 }
::= { vrPpTbclOperEntry 3 }

vrPpTbclDownTime OBJECT-TYPE
   SYNTAX     Unsigned32 (0..4294967295)
   ACCESS     read-only
   STATUS     mandatory
   DESCRIPTION
     "This attribute specifies the accumulated down time of this bridge port 
      since the last reset occurred."
   DEFVAL     { 0 }
::= { vrPpTbclOperEntry 4 }

vrPpTbclBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { vrPpTbclOperEntry 5 }

vrPpTbclBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { vrPpTbclOperEntry 6 }

vrPpTbclBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { vrPpTbclOperEntry 7 }

vrPpTbclIfIndex OBJECT-TYPE
   SYNTAX     InterfaceIndex (1..65535)
   ACCESS     read-only
   STATUS     mandatory
   DESCRIPTION
     "This attribute specifies the index into the Interface Table where in 
      information about the media interface corresponding to the bridge port is 
      maintained."
::= { vrPpTbclOperEntry 8 }

vrPpTbclDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { vrPpTbclOperEntry 10 }

vrPpTbclMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { vrPpTbclOperEntry 11 }

vrPpTbclTbOperTable OBJECT-TYPE
   SYNTAX     SEQUENCE OF VrPpTbclTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { vrPpTbcl 17 }

vrPpTbclTbOperEntry OBJECT-TYPE
   SYNTAX     VrPpTbclTbOperEntry
   ACCESS     not-accessible
   STATUS     mandatory
   DESCRIPTION
     "An entry in the vrPpTbclTbOperTable."
   INDEX {
      vrIndex,
      vrPpIndex,
      vrPpTbclIndex }
::= { vrPpTbclTbOperTable 1 }

VrPpTbclTbOperEntry ::= SEQUENCE {
   vrPpTbclMaxInfo
      Unsigned32,
   vrPpTbclBadVerifyDiscards
      Counter32,
   vrPpTbclUnicastNoMatches
      Counter32,
   vrPpTbclStaticEntryDiscards
      Counter32,
   vrPpTbclDynamicEntryDiscards
      Counter32,
   vrPpTbclLearningDiscards
      Counter32,
   vrPpTbclInDiscards
      Counter32,
   vrPpTbclInFrames
      Counter32,
   vrPpTbclOutFrames
      Counter32 }

vrPpTbclMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { vrPpTbclTbOperEntry 2 }

vrPpTbclBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { vrPpTbclTbOperEntry 3 }

vrPpTbclUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { vrPpTbclTbOperEntry 4 }

vrPpTbclStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { vrPpTbclTbOperEntry 5 }

vrPpTbclDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { vrPpTbclTbOperEntry 6 }

vrPpTbclLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { vrPpTbclTbOperEntry 7 }

vrPpTbclInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { vrPpTbclTbOperEntry 8 }

vrPpTbclInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { vrPpTbclTbOperEntry 9 }

vrPpTbclOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { vrPpTbclTbOperEntry 10 }

vrPpTbclStpOperTable OBJECT-TYPE
   SYNTAX     SEQUENCE OF VrPpTbclStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { vrPpTbcl 18 }

vrPpTbclStpOperEntry OBJECT-TYPE
   SYNTAX     VrPpTbclStpOperEntry
   ACCESS     not-accessible
   STATUS     mandatory
   DESCRIPTION
     "An entry in the vrPpTbclStpOperTable."
   INDEX {
      vrIndex,
      vrPpIndex,
      vrPpTbclIndex }
::= { vrPpTbclStpOperTable 1 }

VrPpTbclStpOperEntry ::= SEQUENCE {
   vrPpTbclStpPortState
      INTEGER,
   vrPpTbclStpTypeOper
      INTEGER,
   vrPpTbclDesignatedCost
      Unsigned32,
   vrPpTbclPathCostOper
      Unsigned32,
   vrPpTbclDesignatedBridge
      BridgeId,
   vrPpTbclDesignatedPort
      Hex,
   vrPpTbclForwardTransitions
      Counter32,
   vrPpTbclBlockingDiscards
      Counter32,
   vrPpTbclDesignatedRoot
      BridgeId }

vrPpTbclStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { vrPpTbclStpOperEntry 2 }

vrPpTbclStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { vrPpTbclStpOperEntry 3 }

vrPpTbclDesignatedCost OBJECT-TYPE
   SYNTAX     Unsigned32 (0..4294967295)
   ACCESS     read-only
   STATUS     mandatory
   DESCRIPTION
     "This attribute specifies the path cost of the designated port of the lan 
      segment connected to the port."
::= { vrPpTbclStpOperEntry 4 }

vrPpTbclPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { vrPpTbclStpOperEntry 5 }

vrPpTbclDesignatedBridge OBJECT-TYPE
   SYNTAX     BridgeId (SIZE (8))
   ACCESS     read-only
   STATUS     mandatory
   DESCRIPTION
     "This attribute specifies the identifier of the bridge that this port considers 
      to be the designated bridge."
::= { vrPpTbclStpOperEntry 6 }

vrPpTbclDesignatedPort OBJECT-TYPE
   SYNTAX     Hex (0..65535)
   ACCESS     read-only
   STATUS     mandatory
   DESCRIPTION
     "This attribute specifies the port identifier of the port on the designated 
      bridge, attached to the same lan as this port is attached to."
::= { vrPpTbclStpOperEntry 7 }

vrPpTbclForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { vrPpTbclStpOperEntry 8 }

vrPpTbclBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { vrPpTbclStpOperEntry 9 }

vrPpTbclDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { vrPpTbclStpOperEntry 10 }

vrPpTbclStatsTable OBJECT-TYPE
   SYNTAX     SEQUENCE OF VrPpTbclStatsEntry
   ACCESS     not-accessible
   STATUS     mandatory
   DESCRIPTION
     "This group houses all the statistical attributes applicable to all types of 
      bridge ports and represents the common factor between them. These 
      attributes in part reflect the state of the bridge port."
::= { vrPpTbcl 19 }

vrPpTbclStatsEntry OBJECT-TYPE
   SYNTAX     VrPpTbclStatsEntry
   ACCESS     not-accessible
   STATUS     mandatory
   DESCRIPTION
     "An entry in the vrPpTbclStatsTable."
   INDEX {
      vrIndex,
      vrPpIndex,
      vrPpTbclIndex }
::= { vrPpTbclStatsTable 1 }

VrPpTbclStatsEntry ::= SEQUENCE {
   vrPpTbclBadAbstractDiscards
      Counter32,
   vrPpTbclTinygramFramesIn
      Counter32,
   vrPpTbclTinygramFramesOut
      Counter32,
   vrPpTbclInFilterDiscards
      Counter32,
   vrPpTbclOutFilterDiscards
      Counter32 }

vrPpTbclBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { vrPpTbclStatsEntry 1 }

vrPpTbclTinygramFramesIn OBJECT-TYPE
   SYNTAX     Counter32 
   ACCESS     read-only
   STATUS     mandatory
   DESCRIPTION
     "This attribute is indicative of the number of frames received on this 
      bridge port that used the tinygram compression scheme."
::= { vrPpTbclStatsEntry 2 }

vrPpTbclTinygramFramesOut OBJECT-TYPE
   SYNTAX     Counter32 
   ACCESS     read-only
   STATUS     mandatory
   DESCRIPTION
     "This attribute is indicative of the number of frames transmitted out this 
      bridge port that used the tinygram compression scheme."
::= { vrPpTbclStatsEntry 3 }

vrPpTbclInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { vrPpTbclStatsEntry 4 }

vrPpTbclOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { vrPpTbclStatsEntry 5 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

vrPpTbclNs OBJECT IDENTIFIER ::= { vrPpTbcl 2 }



vrPpTbclNsRowStatusTable OBJECT-TYPE
   SYNTAX     SEQUENCE OF VrPpTbclNsRowStatusEntry
   ACCESS     not-accessible
   STATUS     mandatory
   DESCRIPTION
     "This entry controls the addition and deletion of 
      vrPpTbclNs components."
::= { vrPpTbclNs 1 }

vrPpTbclNsRowStatusEntry OBJECT-TYPE
   SYNTAX     VrPpTbclNsRowStatusEntry
   ACCESS     not-accessible
   STATUS     mandatory
   DESCRIPTION
     "A single entry in the table represents a single 
      vrPpTbclNs component."
   INDEX {
      vrIndex,
      vrPpIndex,
      vrPpTbclIndex,
      vrPpTbclNsIndex }
::= { vrPpTbclNsRowStatusTable 1 }

VrPpTbclNsRowStatusEntry ::= SEQUENCE {
   vrPpTbclNsRowStatus
      RowStatus,
   vrPpTbclNsComponentName
      DisplayString,
   vrPpTbclNsStorageType
      StorageType,
   vrPpTbclNsIndex
      NonReplicated }

vrPpTbclNsRowStatus OBJECT-TYPE
   SYNTAX     RowStatus 
   ACCESS     read-write
   STATUS     mandatory
   DESCRIPTION
     "This variable is used as the basis for SNMP naming of
      vrPpTbclNs components.
      These components can be added and deleted."
::= { vrPpTbclNsRowStatusEntry 1 }

vrPpTbclNsComponentName OBJECT-TYPE
   SYNTAX     DisplayString 
   ACCESS     read-only
   STATUS     mandatory
   DESCRIPTION
     "This variable provides the component's string name for
      use with the ASCII Console Interface"
::= { vrPpTbclNsRowStatusEntry 2 }

vrPpTbclNsStorageType OBJECT-TYPE
   SYNTAX     StorageType 
   ACCESS     read-only
   STATUS     mandatory
   DESCRIPTION
     "This variable represents the storage type value for the
      vrPpTbclNs tables."
::= { vrPpTbclNsRowStatusEntry 4 }

vrPpTbclNsIndex OBJECT-TYPE
   SYNTAX     NonReplicated 
   ACCESS     not-accessible
   STATUS     mandatory
   DESCRIPTION
     "This variable represents the index for the vrPpTbclNs tables."
::= { vrPpTbclNsRowStatusEntry 10 }

vrPpTbclNsProvTable OBJECT-TYPE
   SYNTAX     SEQUENCE OF VrPpTbclNsProvEntry
   ACCESS     not-accessible
   STATUS     mandatory
   DESCRIPTION
     "This group houses all the port specific provisionable attributes 
      associated with Ns. These attributes influence the application of filters to 
      incoming and outgoing frames."
::= { vrPpTbclNs 10 }

vrPpTbclNsProvEntry OBJECT-TYPE
   SYNTAX     VrPpTbclNsProvEntry
   ACCESS     not-accessible
   STATUS     mandatory
   DESCRIPTION
     "An entry in the vrPpTbclNsProvTable."
   INDEX {
      vrIndex,
      vrPpIndex,
      vrPpTbclIndex,
      vrPpTbclNsIndex }
::= { vrPpTbclNsProvTable 1 }

VrPpTbclNsProvEntry ::= SEQUENCE {
   vrPpTbclNsIncomingFilter
      AsciiString,
   vrPpTbclNsOutgoingFilter
      AsciiString }

vrPpTbclNsIncomingFilter OBJECT-TYPE
   SYNTAX     AsciiString (SIZE (0..32))
   ACCESS     read-write
   STATUS     mandatory
   DESCRIPTION
     "This attribute specifies the name of the filter to be applied at the 
      incoming filter point."
::= { vrPpTbclNsProvEntry 2 }

vrPpTbclNsOutgoingFilter OBJECT-TYPE
   SYNTAX     AsciiString (SIZE (0..32))
   ACCESS     read-write
   STATUS     mandatory
   DESCRIPTION
     "This attribute specifies the name of the filter to be applied at the out 
      going filter point."
::= { vrPpTbclNsProvEntry 3 }


-- Vr/<string> Pp/<string> FddiEncapTbPort
-- This component represents a FDDI encapsulated port, working in the 
-- TB mode. It contains all the attribute groups (provisionable and 
-- operational) necessary for the working of this bridge port. In this mode 
-- the domain information can optionally be preserved in the frames. 
-- This bridge port is characterized as a backbone port and can be used to 
-- tunnel TB frames, through the backbone. It participates in the 
-- transparent bridge (man) spanning tree protocol. Backbone ports are not 
-- associated with any domain as multiple domains should be able to 
-- multiplex traffic through them and thus share the backbone's bandwidth.
-- Please note that when this bridge port is provisioned multiple instances 
-- of the component SpanningTreeProtocol exist, there should exist exactly 
-- one instance of the SpanningTreeProtocol component with its attribute 
-- stpMode set to a value of backbone.

vrPpFddiETB OBJECT IDENTIFIER ::= { vrPp 3 }



vrPpFddiETBRowStatusTable OBJECT-TYPE
   SYNTAX     SEQUENCE OF VrPpFddiETBRowStatusEntry
   ACCESS     not-accessible
   STATUS     mandatory
   DESCRIPTION
     "This entry controls the addition and deletion of 
      vrPpFddiETB components."
::= { vrPpFddiETB 1 }

vrPpFddiETBRowStatusEntry OBJECT-TYPE
   SYNTAX     VrPpFddiETBRowStatusEntry
   ACCESS     not-accessible
   STATUS     mandatory
   DESCRIPTION
     "A single entry in the table represents a single 
      vrPpFddiETB component."
   INDEX {
      vrIndex,
      vrPpIndex,
      vrPpFddiETBIndex }
::= { vrPpFddiETBRowStatusTable 1 }

VrPpFddiETBRowStatusEntry ::= SEQUENCE {
   vrPpFddiETBRowStatus
      RowStatus,
   vrPpFddiETBComponentName
      DisplayString,
   vrPpFddiETBStorageType
      StorageType,
   vrPpFddiETBIndex
      NonReplicated }

vrPpFddiETBRowStatus OBJECT-TYPE
   SYNTAX     RowStatus 
   ACCESS     read-write
   STATUS     mandatory
   DESCRIPTION
     "This variable is used as the basis for SNMP naming of
      vrPpFddiETB components.
      These components can be added and deleted."
::= { vrPpFddiETBRowStatusEntry 1 }

vrPpFddiETBComponentName OBJECT-TYPE
   SYNTAX     DisplayString 
   ACCESS     read-only
   STATUS     mandatory
   DESCRIPTION
     "This variable provides the component's string name for
      use with the ASCII Console Interface"
::= { vrPpFddiETBRowStatusEntry 2 }

vrPpFddiETBStorageType OBJECT-TYPE
   SYNTAX     StorageType 
   ACCESS     read-only
   STATUS     mandatory
   DESCRIPTION
     "This variable represents the storage type value for the
      vrPpFddiETB tables."
::= { vrPpFddiETBRowStatusEntry 4 }

vrPpFddiETBIndex OBJECT-TYPE
   SYNTAX     NonReplicated 
   ACCESS     not-accessible
   STATUS     mandatory
   DESCRIPTION
     "This variable represents the index for the vrPpFddiETB tables."
::= { vrPpFddiETBRowStatusEntry 10 }

vrPpFddiETBProvTable OBJECT-TYPE
   SYNTAX     SEQUENCE OF VrPpFddiETBProvEntry
   ACCESS     not-accessible
   STATUS     mandatory
   DESCRIPTION
     "This group houses all the provisionable attributes that belong to the this 
      group. This group of attributes is applicable to all types of bridge ports 
      and represent the common factor between them. These attributes 
      influence the working of a bridge port."
::= { vrPpFddiETB 10 }

vrPpFddiETBProvEntry OBJECT-TYPE
   SYNTAX     VrPpFddiETBProvEntry
   ACCESS     not-accessible
   STATUS     mandatory
   DESCRIPTION
     "An entry in the vrPpFddiETBProvTable."
   INDEX {
      vrIndex,
      vrPpIndex,
      vrPpFddiETBIndex }
::= { vrPpFddiETBProvTable 1 }

VrPpFddiETBProvEntry ::= SEQUENCE {
   vrPpFddiETBTranslateIpx
      INTEGER,
   vrPpFddiETBFragmentIp
      INTEGER,
   vrPpFddiETBServiceClass
      INTEGER,
   vrPpFddiETBConvertArpMacAddress
      INTEGER,
   vrPpFddiETBPortNum
      Unsigned32,
   vrPpFddiETBOutboundFrameMediaType
      INTEGER }

vrPpFddiETBTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { vrPpFddiETBProvEntry 1 }

vrPpFddiETBFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { vrPpFddiETBProvEntry 2 }

vrPpFddiETBServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { vrPpFddiETBProvEntry 3 }

vrPpFddiETBConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { vrPpFddiETBProvEntry 4 }

vrPpFddiETBPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { vrPpFddiETBProvEntry 5 }

vrPpFddiETBOutboundFrameMediaType OBJECT-TYPE
   SYNTAX     INTEGER  {
                 unaltered(1),
                 ethernetConv(2) }
   ACCESS     read-write
   STATUS     mandatory
   DESCRIPTION
     "This attribute specifies the media type the frame must be in before it is 
      to be forwarded over the outbound supported WAN Bridge Protocol 
      Port. The attribute only applies to outbound Bridge Protocol Port.
      
      For supported bridge ports, if the attribute value remains set to the 
      default value of unaltered then there will be no frame conversion. When 
      the value is set to the value ethernetConv then all frames being 
      forwarded out the outbound WAN Port will be converted to ethernet 
      before forwarding takes place. The only outbound WAN medias that 
      currently support conversion are: FR (Frame Relay) and VNS. All other 
      medias will fail the Bridge Port semantic check when attempts are made 
      to alter this attribute. 
      
      The following is an example of what the user may be able to do. Frames 
      originating from a Token Ring are to be flooded out onto another Token 
      Ring and a Frame Relay Port. The token ring Outbound port performs 
      no translation, yet the FR Port has the outboundFrameMediaType 
      attribute set to ethernetConv which results in the frame being translated 
      into Ethernet format from Token Ring format before Frame Relay does 
      its encapsulation and transmits over the FR port."
   DEFVAL     { unaltered }
::= { vrPpFddiETBProvEntry 6 }

vrPpFddiETBTbProvTable OBJECT-TYPE
   SYNTAX     SEQUENCE OF VrPpFddiETBTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { vrPpFddiETB 11 }

vrPpFddiETBTbProvEntry OBJECT-TYPE
   SYNTAX     VrPpFddiETBTbProvEntry
   ACCESS     not-accessible
   STATUS     mandatory
   DESCRIPTION
     "An entry in the vrPpFddiETBTbProvTable."
   INDEX {
      vrIndex,
      vrPpIndex,
      vrPpFddiETBIndex }
::= { vrPpFddiETBTbProvTable 1 }

VrPpFddiETBTbProvEntry ::= SEQUENCE {
   vrPpFddiETBSecureOption
      INTEGER }

vrPpFddiETBSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { vrPpFddiETBTbProvEntry 1 }

vrPpFddiETBStpProvTable OBJECT-TYPE
   SYNTAX     SEQUENCE OF VrPpFddiETBStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { vrPpFddiETB 12 }

vrPpFddiETBStpProvEntry OBJECT-TYPE
   SYNTAX     VrPpFddiETBStpProvEntry
   ACCESS     not-accessible
   STATUS     mandatory
   DESCRIPTION
     "An entry in the vrPpFddiETBStpProvTable."
   INDEX {
      vrIndex,
      vrPpIndex,
      vrPpFddiETBIndex }
::= { vrPpFddiETBStpProvTable 1 }

VrPpFddiETBStpProvEntry ::= SEQUENCE {
   vrPpFddiETBAdminStatus
      INTEGER,
   vrPpFddiETBPortStateStpControl
      INTEGER,
   vrPpFddiETBStpTypeProv
      INTEGER,
   vrPpFddiETBPortPriority
      Unsigned32,
   vrPpFddiETBPathCost
      Unsigned32,
   vrPpFddiETBPathCostMethod
      INTEGER }

vrPpFddiETBAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { vrPpFddiETBStpProvEntry 1 }

vrPpFddiETBPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { vrPpFddiETBStpProvEntry 2 }

vrPpFddiETBStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { vrPpFddiETBStpProvEntry 3 }

vrPpFddiETBPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { vrPpFddiETBStpProvEntry 4 }

vrPpFddiETBPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { vrPpFddiETBStpProvEntry 5 }

vrPpFddiETBPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { vrPpFddiETBStpProvEntry 6 }

vrPpFddiETBDIProvTable OBJECT-TYPE
   SYNTAX     SEQUENCE OF VrPpFddiETBDIProvEntry
   ACCESS     not-accessible
   STATUS     mandatory
   DESCRIPTION
     "This group houses all the provisionable, domain specific attributes for a 
      non-encapsulating bridge port."
::= { vrPpFddiETB 13 }

vrPpFddiETBDIProvEntry OBJECT-TYPE
   SYNTAX     VrPpFddiETBDIProvEntry
   ACCESS     not-accessible
   STATUS     mandatory
   DESCRIPTION
     "An entry in the vrPpFddiETBDIProvTable."
   INDEX {
      vrIndex,
      vrPpIndex,
      vrPpFddiETBIndex }
::= { vrPpFddiETBDIProvTable 1 }

VrPpFddiETBDIProvEntry ::= SEQUENCE {
   vrPpFddiETBDomainNum
      Unsigned32,
   vrPpFddiETBPreserveDomain
      INTEGER }

vrPpFddiETBDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { vrPpFddiETBDIProvEntry 1 }

vrPpFddiETBPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { vrPpFddiETBDIProvEntry 2 }

vrPpFddiETBStateTable OBJECT-TYPE
   SYNTAX     SEQUENCE OF VrPpFddiETBStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpFddiETB 14 }

vrPpFddiETBStateEntry OBJECT-TYPE
   SYNTAX     VrPpFddiETBStateEntry
   ACCESS     not-accessible
   STATUS     mandatory
   DESCRIPTION
     "An entry in the vrPpFddiETBStateTable."
   INDEX {
      vrIndex,
      vrPpIndex,
      vrPpFddiETBIndex }
::= { vrPpFddiETBStateTable 1 }

VrPpFddiETBStateEntry ::= SEQUENCE {
   vrPpFddiETBAdminState
      INTEGER,
   vrPpFddiETBOperationalState
      INTEGER,
   vrPpFddiETBUsageState
      INTEGER }

vrPpFddiETBAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpFddiETBStateEntry 1 }

vrPpFddiETBOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpFddiETBStateEntry 2 }

vrPpFddiETBUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpFddiETBStateEntry 3 }

vrPpFddiETBOperStatusTable OBJECT-TYPE
   SYNTAX     SEQUENCE OF VrPpFddiETBOperStatusEntry
   ACCESS     not-accessible
   STATUS     mandatory
   DESCRIPTION
     "This group includes the Operational Status attribute. This attribute 
      defines the current operational state of this component."
::= { vrPpFddiETB 15 }

vrPpFddiETBOperStatusEntry OBJECT-TYPE
   SYNTAX     VrPpFddiETBOperStatusEntry
   ACCESS     not-accessible
   STATUS     mandatory
   DESCRIPTION
     "An entry in the vrPpFddiETBOperStatusTable."
   INDEX {
      vrIndex,
      vrPpIndex,
      vrPpFddiETBIndex }
::= { vrPpFddiETBOperStatusTable 1 }

VrPpFddiETBOperStatusEntry ::= SEQUENCE {
   vrPpFddiETBSnmpOperStatus
      INTEGER }

vrPpFddiETBSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpFddiETBOperStatusEntry 1 }

vrPpFddiETBOperTable OBJECT-TYPE
   SYNTAX     SEQUENCE OF VrPpFddiETBOperEntry
   ACCESS     not-accessible
   STATUS     mandatory
   DESCRIPTION
     "This group houses all the operational attributes belonging to the base 
      group. The base group of attributes is applicable to all types of bridge 
      ports and represent the common factor between them. These attributes in 
      part, reflect the state of a bridge port."
::= { vrPpFddiETB 16 }

vrPpFddiETBOperEntry OBJECT-TYPE
   SYNTAX     VrPpFddiETBOperEntry
   ACCESS     not-accessible
   STATUS     mandatory
   DESCRIPTION
     "An entry in the vrPpFddiETBOperTable."
   INDEX {
      vrIndex,
      vrPpIndex,
      vrPpFddiETBIndex }
::= { vrPpFddiETBOperTable 1 }

VrPpFddiETBOperEntry ::= SEQUENCE {
   vrPpFddiETBPortName
      AsciiString,
   vrPpFddiETBUpTime
      Unsigned32,
   vrPpFddiETBDownTime
      Unsigned32,
   vrPpFddiETBBridgingMode
      INTEGER,
   vrPpFddiETBBridgePortConfig
      INTEGER,
   vrPpFddiETBBridgePortType
      INTEGER,
   vrPpFddiETBIfIndex
      InterfaceIndex,
   vrPpFddiETBDelayExceededDiscards
      Counter32,
   vrPpFddiETBMtuExceededDiscards
      Counter32 }

vrPpFddiETBPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { vrPpFddiETBOperEntry 1 }

vrPpFddiETBUpTime OBJECT-TYPE
   SYNTAX     Unsigned32 (0..4294967295)
   ACCESS     read-only
   STATUS     mandatory
   DESCRIPTION
     "This attribute specifies the accumulated up time of this bridge port since 
      the last reset occurred."
   DEFVAL     { 0 }
::= { vrPpFddiETBOperEntry 3 }

vrPpFddiETBDownTime OBJECT-TYPE
   SYNTAX     Unsigned32 (0..4294967295)
   ACCESS     read-only
   STATUS     mandatory
   DESCRIPTION
     "This attribute specifies the accumulated down time of this bridge port 
      since the last reset occurred."
   DEFVAL     { 0 }
::= { vrPpFddiETBOperEntry 4 }

vrPpFddiETBBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { vrPpFddiETBOperEntry 5 }

vrPpFddiETBBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { vrPpFddiETBOperEntry 6 }

vrPpFddiETBBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { vrPpFddiETBOperEntry 7 }

vrPpFddiETBIfIndex OBJECT-TYPE
   SYNTAX     InterfaceIndex (1..65535)
   ACCESS     read-only
   STATUS     mandatory
   DESCRIPTION
     "This attribute specifies the index into the Interface Table where in 
      information about the media interface corresponding to the bridge port is 
      maintained."
::= { vrPpFddiETBOperEntry 8 }

vrPpFddiETBDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { vrPpFddiETBOperEntry 10 }

vrPpFddiETBMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { vrPpFddiETBOperEntry 11 }

vrPpFddiETBTbOperTable OBJECT-TYPE
   SYNTAX     SEQUENCE OF VrPpFddiETBTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { vrPpFddiETB 17 }

vrPpFddiETBTbOperEntry OBJECT-TYPE
   SYNTAX     VrPpFddiETBTbOperEntry
   ACCESS     not-accessible
   STATUS     mandatory
   DESCRIPTION
     "An entry in the vrPpFddiETBTbOperTable."
   INDEX {
      vrIndex,
      vrPpIndex,
      vrPpFddiETBIndex }
::= { vrPpFddiETBTbOperTable 1 }

VrPpFddiETBTbOperEntry ::= SEQUENCE {
   vrPpFddiETBMaxInfo
      Unsigned32,
   vrPpFddiETBBadVerifyDiscards
      Counter32,
   vrPpFddiETBUnicastNoMatches
      Counter32,
   vrPpFddiETBStaticEntryDiscards
      Counter32,
   vrPpFddiETBDynamicEntryDiscards
      Counter32,
   vrPpFddiETBLearningDiscards
      Counter32,
   vrPpFddiETBInDiscards
      Counter32,
   vrPpFddiETBInFrames
      Counter32,
   vrPpFddiETBOutFrames
      Counter32 }

vrPpFddiETBMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { vrPpFddiETBTbOperEntry 2 }

vrPpFddiETBBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { vrPpFddiETBTbOperEntry 3 }

vrPpFddiETBUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { vrPpFddiETBTbOperEntry 4 }

vrPpFddiETBStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { vrPpFddiETBTbOperEntry 5 }

vrPpFddiETBDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { vrPpFddiETBTbOperEntry 6 }

vrPpFddiETBLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { vrPpFddiETBTbOperEntry 7 }

vrPpFddiETBInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { vrPpFddiETBTbOperEntry 8 }

vrPpFddiETBInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { vrPpFddiETBTbOperEntry 9 }

vrPpFddiETBOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { vrPpFddiETBTbOperEntry 10 }

vrPpFddiETBStpOperTable OBJECT-TYPE
   SYNTAX     SEQUENCE OF VrPpFddiETBStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { vrPpFddiETB 18 }

vrPpFddiETBStpOperEntry OBJECT-TYPE
   SYNTAX     VrPpFddiETBStpOperEntry
   ACCESS     not-accessible
   STATUS     mandatory
   DESCRIPTION
     "An entry in the vrPpFddiETBStpOperTable."
   INDEX {
      vrIndex,
      vrPpIndex,
      vrPpFddiETBIndex }
::= { vrPpFddiETBStpOperTable 1 }

VrPpFddiETBStpOperEntry ::= SEQUENCE {
   vrPpFddiETBStpPortState
      INTEGER,
   vrPpFddiETBStpTypeOper
      INTEGER,
   vrPpFddiETBDesignatedCost
      Unsigned32,
   vrPpFddiETBPathCostOper
      Unsigned32,
   vrPpFddiETBDesignatedBridge
      BridgeId,
   vrPpFddiETBDesignatedPort
      Hex,
   vrPpFddiETBForwardTransitions
      Counter32,
   vrPpFddiETBBlockingDiscards
      Counter32,
   vrPpFddiETBDesignatedRoot
      BridgeId }

vrPpFddiETBStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { vrPpFddiETBStpOperEntry 2 }

vrPpFddiETBStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { vrPpFddiETBStpOperEntry 3 }

vrPpFddiETBDesignatedCost OBJECT-TYPE
   SYNTAX     Unsigned32 (0..4294967295)
   ACCESS     read-only
   STATUS     mandatory
   DESCRIPTION
     "This attribute specifies the path cost of the designated port of the lan 
      segment connected to the port."
::= { vrPpFddiETBStpOperEntry 4 }

vrPpFddiETBPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { vrPpFddiETBStpOperEntry 5 }

vrPpFddiETBDesignatedBridge OBJECT-TYPE
   SYNTAX     BridgeId (SIZE (8))
   ACCESS     read-only
   STATUS     mandatory
   DESCRIPTION
     "This attribute specifies the identifier of the bridge that this port considers 
      to be the designated bridge."
::= { vrPpFddiETBStpOperEntry 6 }

vrPpFddiETBDesignatedPort OBJECT-TYPE
   SYNTAX     Hex (0..65535)
   ACCESS     read-only
   STATUS     mandatory
   DESCRIPTION
     "This attribute specifies the port identifier of the port on the designated 
      bridge, attached to the same lan as this port is attached to."
::= { vrPpFddiETBStpOperEntry 7 }

vrPpFddiETBForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { vrPpFddiETBStpOperEntry 8 }

vrPpFddiETBBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { vrPpFddiETBStpOperEntry 9 }

vrPpFddiETBDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { vrPpFddiETBStpOperEntry 10 }

vrPpFddiETBStatsTable OBJECT-TYPE
   SYNTAX     SEQUENCE OF VrPpFddiETBStatsEntry
   ACCESS     not-accessible
   STATUS     mandatory
   DESCRIPTION
     "This group houses all the statistical attributes applicable to all types of 
      bridge ports and represents the common factor between them. These 
      attributes in part reflect the state of the bridge port."
::= { vrPpFddiETB 19 }

vrPpFddiETBStatsEntry OBJECT-TYPE
   SYNTAX     VrPpFddiETBStatsEntry
   ACCESS     not-accessible
   STATUS     mandatory
   DESCRIPTION
     "An entry in the vrPpFddiETBStatsTable."
   INDEX {
      vrIndex,
      vrPpIndex,
      vrPpFddiETBIndex }
::= { vrPpFddiETBStatsTable 1 }

VrPpFddiETBStatsEntry ::= SEQUENCE {
   vrPpFddiETBBadAbstractDiscards
      Counter32,
   vrPpFddiETBTinygramFramesIn
      Counter32,
   vrPpFddiETBTinygramFramesOut
      Counter32,
   vrPpFddiETBInFilterDiscards
      Counter32,
   vrPpFddiETBOutFilterDiscards
      Counter32 }

vrPpFddiETBBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { vrPpFddiETBStatsEntry 1 }

vrPpFddiETBTinygramFramesIn OBJECT-TYPE
   SYNTAX     Counter32 
   ACCESS     read-only
   STATUS     mandatory
   DESCRIPTION
     "This attribute is indicative of the number of frames received on this 
      bridge port that used the tinygram compression scheme."
::= { vrPpFddiETBStatsEntry 2 }

vrPpFddiETBTinygramFramesOut OBJECT-TYPE
   SYNTAX     Counter32 
   ACCESS     read-only
   STATUS     mandatory
   DESCRIPTION
     "This attribute is indicative of the number of frames transmitted out this 
      bridge port that used the tinygram compression scheme."
::= { vrPpFddiETBStatsEntry 3 }

vrPpFddiETBInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { vrPpFddiETBStatsEntry 4 }

vrPpFddiETBOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { vrPpFddiETBStatsEntry 5 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

vrPpFddiETBNs OBJECT IDENTIFIER ::= { vrPpFddiETB 2 }



vrPpFddiETBNsRowStatusTable OBJECT-TYPE
   SYNTAX     SEQUENCE OF VrPpFddiETBNsRowStatusEntry
   ACCESS     not-accessible
   STATUS     mandatory
   DESCRIPTION
     "This entry controls the addition and deletion of 
      vrPpFddiETBNs components."
::= { vrPpFddiETBNs 1 }

vrPpFddiETBNsRowStatusEntry OBJECT-TYPE
   SYNTAX     VrPpFddiETBNsRowStatusEntry
   ACCESS     not-accessible
   STATUS     mandatory
   DESCRIPTION
     "A single entry in the table represents a single 
      vrPpFddiETBNs component."
   INDEX {
      vrIndex,
      vrPpIndex,
      vrPpFddiETBIndex,
      vrPpFddiETBNsIndex }
::= { vrPpFddiETBNsRowStatusTable 1 }

VrPpFddiETBNsRowStatusEntry ::= SEQUENCE {
   vrPpFddiETBNsRowStatus
      RowStatus,
   vrPpFddiETBNsComponentName
      DisplayString,
   vrPpFddiETBNsStorageType
      StorageType,
   vrPpFddiETBNsIndex
      NonReplicated }

vrPpFddiETBNsRowStatus OBJECT-TYPE
   SYNTAX     RowStatus 
   ACCESS     read-write
   STATUS     mandatory
   DESCRIPTION
     "This variable is used as the basis for SNMP naming of
      vrPpFddiETBNs components.
      These components can be added and deleted."
::= { vrPpFddiETBNsRowStatusEntry 1 }

vrPpFddiETBNsComponentName OBJECT-TYPE
   SYNTAX     DisplayString 
   ACCESS     read-only
   STATUS     mandatory
   DESCRIPTION
     "This variable provides the component's string name for
      use with the ASCII Console Interface"
::= { vrPpFddiETBNsRowStatusEntry 2 }

vrPpFddiETBNsStorageType OBJECT-TYPE
   SYNTAX     StorageType 
   ACCESS     read-only
   STATUS     mandatory
   DESCRIPTION
     "This variable represents the storage type value for the
      vrPpFddiETBNs tables."
::= { vrPpFddiETBNsRowStatusEntry 4 }

vrPpFddiETBNsIndex OBJECT-TYPE
   SYNTAX     NonReplicated 
   ACCESS     not-accessible
   STATUS     mandatory
   DESCRIPTION
     "This variable represents the index for the vrPpFddiETBNs tables."
::= { vrPpFddiETBNsRowStatusEntry 10 }

vrPpFddiETBNsProvTable OBJECT-TYPE
   SYNTAX     SEQUENCE OF VrPpFddiETBNsProvEntry
   ACCESS     not-accessible
   STATUS     mandatory
   DESCRIPTION
     "This group houses all the port specific provisionable attributes 
      associated with Ns. These attributes influence the application of filters to 
      incoming and outgoing frames."
::= { vrPpFddiETBNs 10 }

vrPpFddiETBNsProvEntry OBJECT-TYPE
   SYNTAX     VrPpFddiETBNsProvEntry
   ACCESS     not-accessible
   STATUS     mandatory
   DESCRIPTION
     "An entry in the vrPpFddiETBNsProvTable."
   INDEX {
      vrIndex,
      vrPpIndex,
      vrPpFddiETBIndex,
      vrPpFddiETBNsIndex }
::= { vrPpFddiETBNsProvTable 1 }

VrPpFddiETBNsProvEntry ::= SEQUENCE {
   vrPpFddiETBNsIncomingFilter
      AsciiString,
   vrPpFddiETBNsOutgoingFilter
      AsciiString }

vrPpFddiETBNsIncomingFilter OBJECT-TYPE
   SYNTAX     AsciiString (SIZE (0..32))
   ACCESS     read-write
   STATUS     mandatory
   DESCRIPTION
     "This attribute specifies the name of the filter to be applied at the 
      incoming filter point."
::= { vrPpFddiETBNsProvEntry 2 }

vrPpFddiETBNsOutgoingFilter OBJECT-TYPE
   SYNTAX     AsciiString (SIZE (0..32))
   ACCESS     read-write
   STATUS     mandatory
   DESCRIPTION
     "This attribute specifies the name of the filter to be applied at the out 
      going filter point."
::= { vrPpFddiETBNsProvEntry 3 }


-- Vr/<string> Pp/<string> TransparentBridgePort
-- This component represents a transparent bridge port. A transparent 
-- bridge port that can transparently bridge frames. It contains all the 
-- attribute groups (provisionable and operational) that are required for the 
-- operation of such a port. Transparent bridge ports participate in the 
-- transparent bridging spanning tree protocol. They also have associated 
-- with them a domain number. Domains are logical partitions of an 
-- extended network and each partition is completely segregated in terms 
-- of traffic. Each domain has an identifier that identifies it uniquely, called 
-- the domain number. 

vrPpTbp OBJECT IDENTIFIER ::= { vrPp 4 }



vrPpTbpRowStatusTable OBJECT-TYPE
   SYNTAX     SEQUENCE OF VrPpTbpRowStatusEntry
   ACCESS     not-accessible
   STATUS     mandatory
   DESCRIPTION
     "This entry controls the addition and deletion of 
      vrPpTbp components."
::= { vrPpTbp 1 }

vrPpTbpRowStatusEntry OBJECT-TYPE
   SYNTAX     VrPpTbpRowStatusEntry
   ACCESS     not-accessible
   STATUS     mandatory
   DESCRIPTION
     "A single entry in the table represents a single 
      vrPpTbp component."
   INDEX {
      vrIndex,
      vrPpIndex,
      vrPpTbpIndex }
::= { vrPpTbpRowStatusTable 1 }

VrPpTbpRowStatusEntry ::= SEQUENCE {
   vrPpTbpRowStatus
      RowStatus,
   vrPpTbpComponentName
      DisplayString,
   vrPpTbpStorageType
      StorageType,
   vrPpTbpIndex
      NonReplicated }

vrPpTbpRowStatus OBJECT-TYPE
   SYNTAX     RowStatus 
   ACCESS     read-write
   STATUS     mandatory
   DESCRIPTION
     "This variable is used as the basis for SNMP naming of
      vrPpTbp components.
      These components can be added and deleted."
::= { vrPpTbpRowStatusEntry 1 }

vrPpTbpComponentName OBJECT-TYPE
   SYNTAX     DisplayString 
   ACCESS     read-only
   STATUS     mandatory
   DESCRIPTION
     "This variable provides the component's string name for
      use with the ASCII Console Interface"
::= { vrPpTbpRowStatusEntry 2 }

vrPpTbpStorageType OBJECT-TYPE
   SYNTAX     StorageType 
   ACCESS     read-only
   STATUS     mandatory
   DESCRIPTION
     "This variable represents the storage type value for the
      vrPpTbp tables."
::= { vrPpTbpRowStatusEntry 4 }

vrPpTbpIndex OBJECT-TYPE
   SYNTAX     NonReplicated 
   ACCESS     not-accessible
   STATUS     mandatory
   DESCRIPTION
     "This variable represents the index for the vrPpTbp tables."
::= { vrPpTbpRowStatusEntry 10 }

vrPpTbpProvTable OBJECT-TYPE
   SYNTAX     SEQUENCE OF VrPpTbpProvEntry
   ACCESS     not-accessible
   STATUS     mandatory
   DESCRIPTION
     "This group houses all the provisionable attributes that belong to the this 
      group. This group of attributes is applicable to all types of bridge ports 
      and represent the common factor between them. These attributes 
      influence the working of a bridge port."
::= { vrPpTbp 10 }

vrPpTbpProvEntry OBJECT-TYPE
   SYNTAX     VrPpTbpProvEntry
   ACCESS     not-accessible
   STATUS     mandatory
   DESCRIPTION
     "An entry in the vrPpTbpProvTable."
   INDEX {
      vrIndex,
      vrPpIndex,
      vrPpTbpIndex }
::= { vrPpTbpProvTable 1 }

VrPpTbpProvEntry ::= SEQUENCE {
   vrPpTbpTranslateIpx
      INTEGER,
   vrPpTbpFragmentIp
      INTEGER,
   vrPpTbpServiceClass
      INTEGER,
   vrPpTbpConvertArpMacAddress
      INTEGER,
   vrPpTbpPortNum
      Unsigned32,
   vrPpTbpOutboundFrameMediaType
      INTEGER }

vrPpTbpTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { vrPpTbpProvEntry 1 }

vrPpTbpFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { vrPpTbpProvEntry 2 }

vrPpTbpServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { vrPpTbpProvEntry 3 }

vrPpTbpConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { vrPpTbpProvEntry 4 }

vrPpTbpPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { vrPpTbpProvEntry 5 }

vrPpTbpOutboundFrameMediaType OBJECT-TYPE
   SYNTAX     INTEGER  {
                 unaltered(1),
                 ethernetConv(2) }
   ACCESS     read-write
   STATUS     mandatory
   DESCRIPTION
     "This attribute specifies the media type the frame must be in before it is 
      to be forwarded over the outbound supported WAN Bridge Protocol 
      Port. The attribute only applies to outbound Bridge Protocol Port.
      
      For supported bridge ports, if the attribute value remains set to the 
      default value of unaltered then there will be no frame conversion. When 
      the value is set to the value ethernetConv then all frames being 
      forwarded out the outbound WAN Port will be converted to ethernet 
      before forwarding takes place. The only outbound WAN medias that 
      currently support conversion are: FR (Frame Relay) and VNS. All other 
      medias will fail the Bridge Port semantic check when attempts are made 
      to alter this attribute. 
      
      The following is an example of what the user may be able to do. Frames 
      originating from a Token Ring are to be flooded out onto another Token 
      Ring and a Frame Relay Port. The token ring Outbound port performs 
      no translation, yet the FR Port has the outboundFrameMediaType 
      attribute set to ethernetConv which results in the frame being translated 
      into Ethernet format from Token Ring format before Frame Relay does 
      its encapsulation and transmits over the FR port."
   DEFVAL     { unaltered }
::= { vrPpTbpProvEntry 6 }

vrPpTbpTbProvTable OBJECT-TYPE
   SYNTAX     SEQUENCE OF VrPpTbpTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { vrPpTbp 11 }

vrPpTbpTbProvEntry OBJECT-TYPE
   SYNTAX     VrPpTbpTbProvEntry
   ACCESS     not-accessible
   STATUS     mandatory
   DESCRIPTION
     "An entry in the vrPpTbpTbProvTable."
   INDEX {
      vrIndex,
      vrPpIndex,
      vrPpTbpIndex }
::= { vrPpTbpTbProvTable 1 }

VrPpTbpTbProvEntry ::= SEQUENCE {
   vrPpTbpSecureOption
      INTEGER }

vrPpTbpSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { vrPpTbpTbProvEntry 1 }

vrPpTbpStpProvTable OBJECT-TYPE
   SYNTAX     SEQUENCE OF VrPpTbpStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { vrPpTbp 12 }

vrPpTbpStpProvEntry OBJECT-TYPE
   SYNTAX     VrPpTbpStpProvEntry
   ACCESS     not-accessible
   STATUS     mandatory
   DESCRIPTION
     "An entry in the vrPpTbpStpProvTable."
   INDEX {
      vrIndex,
      vrPpIndex,
      vrPpTbpIndex }
::= { vrPpTbpStpProvTable 1 }

VrPpTbpStpProvEntry ::= SEQUENCE {
   vrPpTbpAdminStatus
      INTEGER,
   vrPpTbpPortStateStpControl
      INTEGER,
   vrPpTbpStpTypeProv
      INTEGER,
   vrPpTbpPortPriority
      Unsigned32,
   vrPpTbpPathCost
      Unsigned32,
   vrPpTbpPathCostMethod
      INTEGER }

vrPpTbpAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { vrPpTbpStpProvEntry 1 }

vrPpTbpPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { vrPpTbpStpProvEntry 2 }

vrPpTbpStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { vrPpTbpStpProvEntry 3 }

vrPpTbpPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { vrPpTbpStpProvEntry 4 }

vrPpTbpPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { vrPpTbpStpProvEntry 5 }

vrPpTbpPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { vrPpTbpStpProvEntry 6 }

vrPpTbpDIProvTable OBJECT-TYPE
   SYNTAX     SEQUENCE OF VrPpTbpDIProvEntry
   ACCESS     not-accessible
   STATUS     mandatory
   DESCRIPTION
     "This group houses all the provisionable, domain specific attributes for a 
      non-encapsulating bridge port."
::= { vrPpTbp 13 }

vrPpTbpDIProvEntry OBJECT-TYPE
   SYNTAX     VrPpTbpDIProvEntry
   ACCESS     not-accessible
   STATUS     mandatory
   DESCRIPTION
     "An entry in the vrPpTbpDIProvTable."
   INDEX {
      vrIndex,
      vrPpIndex,
      vrPpTbpIndex }
::= { vrPpTbpDIProvTable 1 }

VrPpTbpDIProvEntry ::= SEQUENCE {
   vrPpTbpDomainNum
      Unsigned32,
   vrPpTbpPreserveDomain
      INTEGER }

vrPpTbpDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { vrPpTbpDIProvEntry 1 }

vrPpTbpPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { vrPpTbpDIProvEntry 2 }

vrPpTbpStateTable OBJECT-TYPE
   SYNTAX     SEQUENCE OF VrPpTbpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpTbp 14 }

vrPpTbpStateEntry OBJECT-TYPE
   SYNTAX     VrPpTbpStateEntry
   ACCESS     not-accessible
   STATUS     mandatory
   DESCRIPTION
     "An entry in the vrPpTbpStateTable."
   INDEX {
      vrIndex,
      vrPpIndex,
      vrPpTbpIndex }
::= { vrPpTbpStateTable 1 }

VrPpTbpStateEntry ::= SEQUENCE {
   vrPpTbpAdminState
      INTEGER,
   vrPpTbpOperationalState
      INTEGER,
   vrPpTbpUsageState
      INTEGER }

vrPpTbpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpTbpStateEntry 1 }

vrPpTbpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpTbpStateEntry 2 }

vrPpTbpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpTbpStateEntry 3 }

vrPpTbpOperStatusTable OBJECT-TYPE
   SYNTAX     SEQUENCE OF VrPpTbpOperStatusEntry
   ACCESS     not-accessible
   STATUS     mandatory
   DESCRIPTION
     "This group includes the Operational Status attribute. This attribute 
      defines the current operational state of this component."
::= { vrPpTbp 15 }

vrPpTbpOperStatusEntry OBJECT-TYPE
   SYNTAX     VrPpTbpOperStatusEntry
   ACCESS     not-accessible
   STATUS     mandatory
   DESCRIPTION
     "An entry in the vrPpTbpOperStatusTable."
   INDEX {
      vrIndex,
      vrPpIndex,
      vrPpTbpIndex }
::= { vrPpTbpOperStatusTable 1 }

VrPpTbpOperStatusEntry ::= SEQUENCE {
   vrPpTbpSnmpOperStatus
      INTEGER }

vrPpTbpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpTbpOperStatusEntry 1 }

vrPpTbpOperTable OBJECT-TYPE
   SYNTAX     SEQUENCE OF VrPpTbpOperEntry
   ACCESS     not-accessible
   STATUS     mandatory
   DESCRIPTION
     "This group houses all the operational attributes belonging to the base 
      group. The base group of attributes is applicable to all types of bridge 
      ports and represent the common factor between them. These attributes in 
      part, reflect the state of a bridge port."
::= { vrPpTbp 16 }

vrPpTbpOperEntry OBJECT-TYPE
   SYNTAX     VrPpTbpOperEntry
   ACCESS     not-accessible
   STATUS     mandatory
   DESCRIPTION
     "An entry in the vrPpTbpOperTable."
   INDEX {
      vrIndex,
      vrPpIndex,
      vrPpTbpIndex }
::= { vrPpTbpOperTable 1 }

VrPpTbpOperEntry ::= SEQUENCE {
   vrPpTbpPortName
      AsciiString,
   vrPpTbpUpTime
      Unsigned32,
   vrPpTbpDownTime
      Unsigned32,
   vrPpTbpBridgingMode
      INTEGER,
   vrPpTbpBridgePortConfig
      INTEGER,
   vrPpTbpBridgePortType
      INTEGER,
   vrPpTbpIfIndex
      InterfaceIndex,
   vrPpTbpDelayExceededDiscards
      Counter32,
   vrPpTbpMtuExceededDiscards
      Counter32 }

vrPpTbpPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { vrPpTbpOperEntry 1 }

vrPpTbpUpTime OBJECT-TYPE
   SYNTAX     Unsigned32 (0..4294967295)
   ACCESS     read-only
   STATUS     mandatory
   DESCRIPTION
     "This attribute specifies the accumulated up time of this bridge port since 
      the last reset occurred."
   DEFVAL     { 0 }
::= { vrPpTbpOperEntry 3 }

vrPpTbpDownTime OBJECT-TYPE
   SYNTAX     Unsigned32 (0..4294967295)
   ACCESS     read-only
   STATUS     mandatory
   DESCRIPTION
     "This attribute specifies the accumulated down time of this bridge port 
      since the last reset occurred."
   DEFVAL     { 0 }
::= { vrPpTbpOperEntry 4 }

vrPpTbpBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { vrPpTbpOperEntry 5 }

vrPpTbpBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { vrPpTbpOperEntry 6 }

vrPpTbpBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { vrPpTbpOperEntry 7 }

vrPpTbpIfIndex OBJECT-TYPE
   SYNTAX     InterfaceIndex (1..65535)
   ACCESS     read-only
   STATUS     mandatory
   DESCRIPTION
     "This attribute specifies the index into the Interface Table where in 
      information about the media interface corresponding to the bridge port is 
      maintained."
::= { vrPpTbpOperEntry 8 }

vrPpTbpDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { vrPpTbpOperEntry 10 }

vrPpTbpMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { vrPpTbpOperEntry 11 }

vrPpTbpTbOperTable OBJECT-TYPE
   SYNTAX     SEQUENCE OF VrPpTbpTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { vrPpTbp 17 }

vrPpTbpTbOperEntry OBJECT-TYPE
   SYNTAX     VrPpTbpTbOperEntry
   ACCESS     not-accessible
   STATUS     mandatory
   DESCRIPTION
     "An entry in the vrPpTbpTbOperTable."
   INDEX {
      vrIndex,
      vrPpIndex,
      vrPpTbpIndex }
::= { vrPpTbpTbOperTable 1 }

VrPpTbpTbOperEntry ::= SEQUENCE {
   vrPpTbpMaxInfo
      Unsigned32,
   vrPpTbpBadVerifyDiscards
      Counter32,
   vrPpTbpUnicastNoMatches
      Counter32,
   vrPpTbpStaticEntryDiscards
      Counter32,
   vrPpTbpDynamicEntryDiscards
      Counter32,
   vrPpTbpLearningDiscards
      Counter32,
   vrPpTbpInDiscards
      Counter32,
   vrPpTbpInFrames
      Counter32,
   vrPpTbpOutFrames
      Counter32 }

vrPpTbpMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { vrPpTbpTbOperEntry 2 }

vrPpTbpBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { vrPpTbpTbOperEntry 3 }

vrPpTbpUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { vrPpTbpTbOperEntry 4 }

vrPpTbpStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { vrPpTbpTbOperEntry 5 }

vrPpTbpDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { vrPpTbpTbOperEntry 6 }

vrPpTbpLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { vrPpTbpTbOperEntry 7 }

vrPpTbpInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { vrPpTbpTbOperEntry 8 }

vrPpTbpInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { vrPpTbpTbOperEntry 9 }

vrPpTbpOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { vrPpTbpTbOperEntry 10 }

vrPpTbpStpOperTable OBJECT-TYPE
   SYNTAX     SEQUENCE OF VrPpTbpStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { vrPpTbp 18 }

vrPpTbpStpOperEntry OBJECT-TYPE
   SYNTAX     VrPpTbpStpOperEntry
   ACCESS     not-accessible
   STATUS     mandatory
   DESCRIPTION
     "An entry in the vrPpTbpStpOperTable."
   INDEX {
      vrIndex,
      vrPpIndex,
      vrPpTbpIndex }
::= { vrPpTbpStpOperTable 1 }

VrPpTbpStpOperEntry ::= SEQUENCE {
   vrPpTbpStpPortState
      INTEGER,
   vrPpTbpStpTypeOper
      INTEGER,
   vrPpTbpDesignatedCost
      Unsigned32,
   vrPpTbpPathCostOper
      Unsigned32,
   vrPpTbpDesignatedBridge
      BridgeId,
   vrPpTbpDesignatedPort
      Hex,
   vrPpTbpForwardTransitions
      Counter32,
   vrPpTbpBlockingDiscards
      Counter32,
   vrPpTbpDesignatedRoot
      BridgeId }

vrPpTbpStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { vrPpTbpStpOperEntry 2 }

vrPpTbpStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { vrPpTbpStpOperEntry 3 }

vrPpTbpDesignatedCost OBJECT-TYPE
   SYNTAX     Unsigned32 (0..4294967295)
   ACCESS     read-only
   STATUS     mandatory
   DESCRIPTION
     "This attribute specifies the path cost of the designated port of the lan 
      segment connected to the port."
::= { vrPpTbpStpOperEntry 4 }

vrPpTbpPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { vrPpTbpStpOperEntry 5 }

vrPpTbpDesignatedBridge OBJECT-TYPE
   SYNTAX     BridgeId (SIZE (8))
   ACCESS     read-only
   STATUS     mandatory
   DESCRIPTION
     "This attribute specifies the identifier of the bridge that this port considers 
      to be the designated bridge."
::= { vrPpTbpStpOperEntry 6 }

vrPpTbpDesignatedPort OBJECT-TYPE
   SYNTAX     Hex (0..65535)
   ACCESS     read-only
   STATUS     mandatory
   DESCRIPTION
     "This attribute specifies the port identifier of the port on the designated 
      bridge, attached to the same lan as this port is attached to."
::= { vrPpTbpStpOperEntry 7 }

vrPpTbpForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { vrPpTbpStpOperEntry 8 }

vrPpTbpBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { vrPpTbpStpOperEntry 9 }

vrPpTbpDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { vrPpTbpStpOperEntry 10 }

vrPpTbpStatsTable OBJECT-TYPE
   SYNTAX     SEQUENCE OF VrPpTbpStatsEntry
   ACCESS     not-accessible
   STATUS     mandatory
   DESCRIPTION
     "This group houses all the statistical attributes applicable to all types of 
      bridge ports and represents the common factor between them. These 
      attributes in part reflect the state of the bridge port."
::= { vrPpTbp 19 }

vrPpTbpStatsEntry OBJECT-TYPE
   SYNTAX     VrPpTbpStatsEntry
   ACCESS     not-accessible
   STATUS     mandatory
   DESCRIPTION
     "An entry in the vrPpTbpStatsTable."
   INDEX {
      vrIndex,
      vrPpIndex,
      vrPpTbpIndex }
::= { vrPpTbpStatsTable 1 }

VrPpTbpStatsEntry ::= SEQUENCE {
   vrPpTbpBadAbstractDiscards
      Counter32,
   vrPpTbpTinygramFramesIn
      Counter32,
   vrPpTbpTinygramFramesOut
      Counter32,
   vrPpTbpInFilterDiscards
      Counter32,
   vrPpTbpOutFilterDiscards
      Counter32 }

vrPpTbpBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { vrPpTbpStatsEntry 1 }

vrPpTbpTinygramFramesIn OBJECT-TYPE
   SYNTAX     Counter32 
   ACCESS     read-only
   STATUS     mandatory
   DESCRIPTION
     "This attribute is indicative of the number of frames received on this 
      bridge port that used the tinygram compression scheme."
::= { vrPpTbpStatsEntry 2 }

vrPpTbpTinygramFramesOut OBJECT-TYPE
   SYNTAX     Counter32 
   ACCESS     read-only
   STATUS     mandatory
   DESCRIPTION
     "This attribute is indicative of the number of frames transmitted out this 
      bridge port that used the tinygram compression scheme."
::= { vrPpTbpStatsEntry 3 }

vrPpTbpInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { vrPpTbpStatsEntry 4 }

vrPpTbpOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { vrPpTbpStatsEntry 5 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

vrPpTbpNs OBJECT IDENTIFIER ::= { vrPpTbp 2 }



vrPpTbpNsRowStatusTable OBJECT-TYPE
   SYNTAX     SEQUENCE OF VrPpTbpNsRowStatusEntry
   ACCESS     not-accessible
   STATUS     mandatory
   DESCRIPTION
     "This entry controls the addition and deletion of 
      vrPpTbpNs components."
::= { vrPpTbpNs 1 }

vrPpTbpNsRowStatusEntry OBJECT-TYPE
   SYNTAX     VrPpTbpNsRowStatusEntry
   ACCESS     not-accessible
   STATUS     mandatory
   DESCRIPTION
     "A single entry in the table represents a single 
      vrPpTbpNs component."
   INDEX {
      vrIndex,
      vrPpIndex,
      vrPpTbpIndex,
      vrPpTbpNsIndex }
::= { vrPpTbpNsRowStatusTable 1 }

VrPpTbpNsRowStatusEntry ::= SEQUENCE {
   vrPpTbpNsRowStatus
      RowStatus,
   vrPpTbpNsComponentName
      DisplayString,
   vrPpTbpNsStorageType
      StorageType,
   vrPpTbpNsIndex
      NonReplicated }

vrPpTbpNsRowStatus OBJECT-TYPE
   SYNTAX     RowStatus 
   ACCESS     read-write
   STATUS     mandatory
   DESCRIPTION
     "This variable is used as the basis for SNMP naming of
      vrPpTbpNs components.
      These components can be added and deleted."
::= { vrPpTbpNsRowStatusEntry 1 }

vrPpTbpNsComponentName OBJECT-TYPE
   SYNTAX     DisplayString 
   ACCESS     read-only
   STATUS     mandatory
   DESCRIPTION
     "This variable provides the component's string name for
      use with the ASCII Console Interface"
::= { vrPpTbpNsRowStatusEntry 2 }

vrPpTbpNsStorageType OBJECT-TYPE
   SYNTAX     StorageType 
   ACCESS     read-only
   STATUS     mandatory
   DESCRIPTION
     "This variable represents the storage type value for the
      vrPpTbpNs tables."
::= { vrPpTbpNsRowStatusEntry 4 }

vrPpTbpNsIndex OBJECT-TYPE
   SYNTAX     NonReplicated 
   ACCESS     not-accessible
   STATUS     mandatory
   DESCRIPTION
     "This variable represents the index for the vrPpTbpNs tables."
::= { vrPpTbpNsRowStatusEntry 10 }

vrPpTbpNsProvTable OBJECT-TYPE
   SYNTAX     SEQUENCE OF VrPpTbpNsProvEntry
   ACCESS     not-accessible
   STATUS     mandatory
   DESCRIPTION
     "This group houses all the port specific provisionable attributes 
      associated with Ns. These attributes influence the application of filters to 
      incoming and outgoing frames."
::= { vrPpTbpNs 10 }

vrPpTbpNsProvEntry OBJECT-TYPE
   SYNTAX     VrPpTbpNsProvEntry
   ACCESS     not-accessible
   STATUS     mandatory
   DESCRIPTION
     "An entry in the vrPpTbpNsProvTable."
   INDEX {
      vrIndex,
      vrPpIndex,
      vrPpTbpIndex,
      vrPpTbpNsIndex }
::= { vrPpTbpNsProvTable 1 }

VrPpTbpNsProvEntry ::= SEQUENCE {
   vrPpTbpNsIncomingFilter
      AsciiString,
   vrPpTbpNsOutgoingFilter
      AsciiString }

vrPpTbpNsIncomingFilter OBJECT-TYPE
   SYNTAX     AsciiString (SIZE (0..32))
   ACCESS     read-write
   STATUS     mandatory
   DESCRIPTION
     "This attribute specifies the name of the filter to be applied at the 
      incoming filter point."
::= { vrPpTbpNsProvEntry 2 }

vrPpTbpNsOutgoingFilter OBJECT-TYPE
   SYNTAX     AsciiString (SIZE (0..32))
   ACCESS     read-write
   STATUS     mandatory
   DESCRIPTION
     "This attribute specifies the name of the filter to be applied at the out 
      going filter point."
::= { vrPpTbpNsProvEntry 3 }


-- Vr/<string> Pp/<string> SourceRouteBridgePort
-- This component represents a source route bridge port. It contains all the 
-- attributes (provisionable and operational attributes) necessary for the 
-- operation of this bridge port. The source route bridge port provides a 
-- way to facilitate source route bridging on a media interface.

vrPpSrBp OBJECT IDENTIFIER ::= { vrPp 8 }



vrPpSrBpRowStatusTable OBJECT-TYPE
   SYNTAX     SEQUENCE OF VrPpSrBpRowStatusEntry
   ACCESS     not-accessible
   STATUS     mandatory
   DESCRIPTION
     "This entry controls the addition and deletion of 
      vrPpSrBp components."
::= { vrPpSrBp 1 }

vrPpSrBpRowStatusEntry OBJECT-TYPE
   SYNTAX     VrPpSrBpRowStatusEntry
   ACCESS     not-accessible
   STATUS     mandatory
   DESCRIPTION
     "A single entry in the table represents a single 
      vrPpSrBp component."
   INDEX {
      vrIndex,
      vrPpIndex,
      vrPpSrBpIndex }
::= { vrPpSrBpRowStatusTable 1 }

VrPpSrBpRowStatusEntry ::= SEQUENCE {
   vrPpSrBpRowStatus
      RowStatus,
   vrPpSrBpComponentName
      DisplayString,
   vrPpSrBpStorageType
      StorageType,
   vrPpSrBpIndex
      NonReplicated }

vrPpSrBpRowStatus OBJECT-TYPE
   SYNTAX     RowStatus 
   ACCESS     read-write
   STATUS     mandatory
   DESCRIPTION
     "This variable is used as the basis for SNMP naming of
      vrPpSrBp components.
      These components can be added and deleted."
::= { vrPpSrBpRowStatusEntry 1 }

vrPpSrBpComponentName OBJECT-TYPE
   SYNTAX     DisplayString 
   ACCESS     read-only
   STATUS     mandatory
   DESCRIPTION
     "This variable provides the component's string name for
      use with the ASCII Console Interface"
::= { vrPpSrBpRowStatusEntry 2 }

vrPpSrBpStorageType OBJECT-TYPE
   SYNTAX     StorageType 
   ACCESS     read-only
   STATUS     mandatory
   DESCRIPTION
     "This variable represents the storage type value for the
      vrPpSrBp tables."
::= { vrPpSrBpRowStatusEntry 4 }

vrPpSrBpIndex OBJECT-TYPE
   SYNTAX     NonReplicated 
   ACCESS     not-accessible
   STATUS     mandatory
   DESCRIPTION
     "This variable represents the index for the vrPpSrBp tables."
::= { vrPpSrBpRowStatusEntry 10 }

vrPpSrBpProvTable OBJECT-TYPE
   SYNTAX     SEQUENCE OF VrPpSrBpProvEntry
   ACCESS     not-accessible
   STATUS     mandatory
   DESCRIPTION
     "This group houses all the provisionable attributes that belong to the this 
      group. This group of attributes is applicable to all types of bridge ports 
      and represent the common factor between them. These attributes 
      influence the working of a bridge port."
::= { vrPpSrBp 10 }

vrPpSrBpProvEntry OBJECT-TYPE
   SYNTAX     VrPpSrBpProvEntry
   ACCESS     not-accessible
   STATUS     mandatory
   DESCRIPTION
     "An entry in the vrPpSrBpProvTable."
   INDEX {
      vrIndex,
      vrPpIndex,
      vrPpSrBpIndex }
::= { vrPpSrBpProvTable 1 }

VrPpSrBpProvEntry ::= SEQUENCE {
   vrPpSrBpTranslateIpx
      INTEGER,
   vrPpSrBpFragmentIp
      INTEGER,
   vrPpSrBpServiceClass
      INTEGER,
   vrPpSrBpConvertArpMacAddress
      INTEGER,
   vrPpSrBpPortNum
      Unsigned32,
   vrPpSrBpOutboundFrameMediaType
      INTEGER }

vrPpSrBpTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { vrPpSrBpProvEntry 1 }

vrPpSrBpFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { vrPpSrBpProvEntry 2 }

vrPpSrBpServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { vrPpSrBpProvEntry 3 }

vrPpSrBpConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { vrPpSrBpProvEntry 4 }

vrPpSrBpPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { vrPpSrBpProvEntry 5 }

vrPpSrBpOutboundFrameMediaType OBJECT-TYPE
   SYNTAX     INTEGER  {
                 unaltered(1),
                 ethernetConv(2) }
   ACCESS     read-write
   STATUS     mandatory
   DESCRIPTION
     "This attribute specifies the media type the frame must be in before it is 
      to be forwarded over the outbound supported WAN Bridge Protocol 
      Port. The attribute only applies to outbound Bridge Protocol Port.
      
      For supported bridge ports, if the attribute value remains set to the 
      default value of unaltered then there will be no frame conversion. When 
      the value is set to the value ethernetConv then all frames being 
      forwarded out the outbound WAN Port will be converted to ethernet 
      before forwarding takes place. The only outbound WAN medias that 
      currently support conversion are: FR (Frame Relay) and VNS. All other 
      medias will fail the Bridge Port semantic check when attempts are made 
      to alter this attribute. 
      
      The following is an example of what the user may be able to do. Frames 
      originating from a Token Ring are to be flooded out onto another Token 
      Ring and a Frame Relay Port. The token ring Outbound port performs 
      no translation, yet the FR Port has the outboundFrameMediaType 
      attribute set to ethernetConv which results in the frame being translated 
      into Ethernet format from Token Ring format before Frame Relay does 
      its encapsulation and transmits over the FR port."
   DEFVAL     { unaltered }
::= { vrPpSrBpProvEntry 6 }

vrPpSrBpStpProvTable OBJECT-TYPE
   SYNTAX     SEQUENCE OF VrPpSrBpStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { vrPpSrBp 12 }

vrPpSrBpStpProvEntry OBJECT-TYPE
   SYNTAX     VrPpSrBpStpProvEntry
   ACCESS     not-accessible
   STATUS     mandatory
   DESCRIPTION
     "An entry in the vrPpSrBpStpProvTable."
   INDEX {
      vrIndex,
      vrPpIndex,
      vrPpSrBpIndex }
::= { vrPpSrBpStpProvTable 1 }

VrPpSrBpStpProvEntry ::= SEQUENCE {
   vrPpSrBpAdminStatus
      INTEGER,
   vrPpSrBpPortStateStpControl
      INTEGER,
   vrPpSrBpStpTypeProv
      INTEGER,
   vrPpSrBpPortPriority
      Unsigned32,
   vrPpSrBpPathCost
      Unsigned32,
   vrPpSrBpPathCostMethod
      INTEGER }

vrPpSrBpAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { vrPpSrBpStpProvEntry 1 }

vrPpSrBpPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { vrPpSrBpStpProvEntry 2 }

vrPpSrBpStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { vrPpSrBpStpProvEntry 3 }

vrPpSrBpPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { vrPpSrBpStpProvEntry 4 }

vrPpSrBpPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { vrPpSrBpStpProvEntry 5 }

vrPpSrBpPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { vrPpSrBpStpProvEntry 6 }

vrPpSrBpDIProvTable OBJECT-TYPE
   SYNTAX     SEQUENCE OF VrPpSrBpDIProvEntry
   ACCESS     not-accessible
   STATUS     mandatory
   DESCRIPTION
     "This group houses all the provisionable, domain specific attributes for a 
      non-encapsulating bridge port."
::= { vrPpSrBp 13 }

vrPpSrBpDIProvEntry OBJECT-TYPE
   SYNTAX     VrPpSrBpDIProvEntry
   ACCESS     not-accessible
   STATUS     mandatory
   DESCRIPTION
     "An entry in the vrPpSrBpDIProvTable."
   INDEX {
      vrIndex,
      vrPpIndex,
      vrPpSrBpIndex }
::= { vrPpSrBpDIProvTable 1 }

VrPpSrBpDIProvEntry ::= SEQUENCE {
   vrPpSrBpDomainNum
      Unsigned32,
   vrPpSrBpPreserveDomain
      INTEGER }

vrPpSrBpDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { vrPpSrBpDIProvEntry 1 }

vrPpSrBpPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { vrPpSrBpDIProvEntry 2 }

vrPpSrBpStateTable OBJECT-TYPE
   SYNTAX     SEQUENCE OF VrPpSrBpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpSrBp 14 }

vrPpSrBpStateEntry OBJECT-TYPE
   SYNTAX     VrPpSrBpStateEntry
   ACCESS     not-accessible
   STATUS     mandatory
   DESCRIPTION
     "An entry in the vrPpSrBpStateTable."
   INDEX {
      vrIndex,
      vrPpIndex,
      vrPpSrBpIndex }
::= { vrPpSrBpStateTable 1 }

VrPpSrBpStateEntry ::= SEQUENCE {
   vrPpSrBpAdminState
      INTEGER,
   vrPpSrBpOperationalState
      INTEGER,
   vrPpSrBpUsageState
      INTEGER }

vrPpSrBpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpSrBpStateEntry 1 }

vrPpSrBpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpSrBpStateEntry 2 }

vrPpSrBpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpSrBpStateEntry 3 }

vrPpSrBpOperStatusTable OBJECT-TYPE
   SYNTAX     SEQUENCE OF VrPpSrBpOperStatusEntry
   ACCESS     not-accessible
   STATUS     mandatory
   DESCRIPTION
     "This group includes the Operational Status attribute. This attribute 
      defines the current operational state of this component."
::= { vrPpSrBp 15 }

vrPpSrBpOperStatusEntry OBJECT-TYPE
   SYNTAX     VrPpSrBpOperStatusEntry
   ACCESS     not-accessible
   STATUS     mandatory
   DESCRIPTION
     "An entry in the vrPpSrBpOperStatusTable."
   INDEX {
      vrIndex,
      vrPpIndex,
      vrPpSrBpIndex }
::= { vrPpSrBpOperStatusTable 1 }

VrPpSrBpOperStatusEntry ::= SEQUENCE {
   vrPpSrBpSnmpOperStatus
      INTEGER }

vrPpSrBpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpSrBpOperStatusEntry 1 }

vrPpSrBpOperTable OBJECT-TYPE
   SYNTAX     SEQUENCE OF VrPpSrBpOperEntry
   ACCESS     not-accessible
   STATUS     mandatory
   DESCRIPTION
     "This group houses all the operational attributes belonging to the base 
      group. The base group of attributes is applicable to all types of bridge 
      ports and represent the common factor between them. These attributes in 
      part, reflect the state of a bridge port."
::= { vrPpSrBp 16 }

vrPpSrBpOperEntry OBJECT-TYPE
   SYNTAX     VrPpSrBpOperEntry
   ACCESS     not-accessible
   STATUS     mandatory
   DESCRIPTION
     "An entry in the vrPpSrBpOperTable."
   INDEX {
      vrIndex,
      vrPpIndex,
      vrPpSrBpIndex }
::= { vrPpSrBpOperTable 1 }

VrPpSrBpOperEntry ::= SEQUENCE {
   vrPpSrBpPortName
      AsciiString,
   vrPpSrBpUpTime
      Unsigned32,
   vrPpSrBpDownTime
      Unsigned32,
   vrPpSrBpBridgingMode
      INTEGER,
   vrPpSrBpBridgePortConfig
      INTEGER,
   vrPpSrBpBridgePortType
      INTEGER,
   vrPpSrBpIfIndex
      InterfaceIndex,
   vrPpSrBpDelayExceededDiscards
      Counter32,
   vrPpSrBpMtuExceededDiscards
      Counter32 }

vrPpSrBpPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { vrPpSrBpOperEntry 1 }

vrPpSrBpUpTime OBJECT-TYPE
   SYNTAX     Unsigned32 (0..4294967295)
   ACCESS     read-only
   STATUS     mandatory
   DESCRIPTION
     "This attribute specifies the accumulated up time of this bridge port since 
      the last reset occurred."
   DEFVAL     { 0 }
::= { vrPpSrBpOperEntry 3 }

vrPpSrBpDownTime OBJECT-TYPE
   SYNTAX     Unsigned32 (0..4294967295)
   ACCESS     read-only
   STATUS     mandatory
   DESCRIPTION
     "This attribute specifies the accumulated down time of this bridge port 
      since the last reset occurred."
   DEFVAL     { 0 }
::= { vrPpSrBpOperEntry 4 }

vrPpSrBpBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { vrPpSrBpOperEntry 5 }

vrPpSrBpBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { vrPpSrBpOperEntry 6 }

vrPpSrBpBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { vrPpSrBpOperEntry 7 }

vrPpSrBpIfIndex OBJECT-TYPE
   SYNTAX     InterfaceIndex (1..65535)
   ACCESS     read-only
   STATUS     mandatory
   DESCRIPTION
     "This attribute specifies the index into the Interface Table where in 
      information about the media interface corresponding to the bridge port is 
      maintained."
::= { vrPpSrBpOperEntry 8 }

vrPpSrBpDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { vrPpSrBpOperEntry 10 }

vrPpSrBpMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { vrPpSrBpOperEntry 11 }

vrPpSrBpStpOperTable OBJECT-TYPE
   SYNTAX     SEQUENCE OF VrPpSrBpStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { vrPpSrBp 18 }

vrPpSrBpStpOperEntry OBJECT-TYPE
   SYNTAX     VrPpSrBpStpOperEntry
   ACCESS     not-accessible
   STATUS     mandatory
   DESCRIPTION
     "An entry in the vrPpSrBpStpOperTable."
   INDEX {
      vrIndex,
      vrPpIndex,
      vrPpSrBpIndex }
::= { vrPpSrBpStpOperTable 1 }

VrPpSrBpStpOperEntry ::= SEQUENCE {
   vrPpSrBpStpPortState
      INTEGER,
   vrPpSrBpStpTypeOper
      INTEGER,
   vrPpSrBpDesignatedCost
      Unsigned32,
   vrPpSrBpPathCostOper
      Unsigned32,
   vrPpSrBpDesignatedBridge
      BridgeId,
   vrPpSrBpDesignatedPort
      Hex,
   vrPpSrBpForwardTransitions
      Counter32,
   vrPpSrBpBlockingDiscards
      Counter32,
   vrPpSrBpDesignatedRoot
      BridgeId }

vrPpSrBpStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { vrPpSrBpStpOperEntry 2 }

vrPpSrBpStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { vrPpSrBpStpOperEntry 3 }

vrPpSrBpDesignatedCost OBJECT-TYPE
   SYNTAX     Unsigned32 (0..4294967295)
   ACCESS     read-only
   STATUS     mandatory
   DESCRIPTION
     "This attribute specifies the path cost of the designated port of the lan 
      segment connected to the port."
::= { vrPpSrBpStpOperEntry 4 }

vrPpSrBpPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { vrPpSrBpStpOperEntry 5 }

vrPpSrBpDesignatedBridge OBJECT-TYPE
   SYNTAX     BridgeId (SIZE (8))
   ACCESS     read-only
   STATUS     mandatory
   DESCRIPTION
     "This attribute specifies the identifier of the bridge that this port considers 
      to be the designated bridge."
::= { vrPpSrBpStpOperEntry 6 }

vrPpSrBpDesignatedPort OBJECT-TYPE
   SYNTAX     Hex (0..65535)
   ACCESS     read-only
   STATUS     mandatory
   DESCRIPTION
     "This attribute specifies the port identifier of the port on the designated 
      bridge, attached to the same lan as this port is attached to."
::= { vrPpSrBpStpOperEntry 7 }

vrPpSrBpForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { vrPpSrBpStpOperEntry 8 }

vrPpSrBpBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { vrPpSrBpStpOperEntry 9 }

vrPpSrBpDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { vrPpSrBpStpOperEntry 10 }

vrPpSrBpStatsTable OBJECT-TYPE
   SYNTAX     SEQUENCE OF VrPpSrBpStatsEntry
   ACCESS     not-accessible
   STATUS     mandatory
   DESCRIPTION
     "This group houses all the statistical attributes applicable to all types of 
      bridge ports and represents the common factor between them. These 
      attributes in part reflect the state of the bridge port."
::= { vrPpSrBp 19 }

vrPpSrBpStatsEntry OBJECT-TYPE
   SYNTAX     VrPpSrBpStatsEntry
   ACCESS     not-accessible
   STATUS     mandatory
   DESCRIPTION
     "An entry in the vrPpSrBpStatsTable."
   INDEX {
      vrIndex,
      vrPpIndex,
      vrPpSrBpIndex }
::= { vrPpSrBpStatsTable 1 }

VrPpSrBpStatsEntry ::= SEQUENCE {
   vrPpSrBpBadAbstractDiscards
      Counter32,
   vrPpSrBpTinygramFramesIn
      Counter32,
   vrPpSrBpTinygramFramesOut
      Counter32,
   vrPpSrBpInFilterDiscards
      Counter32,
   vrPpSrBpOutFilterDiscards
      Counter32 }

vrPpSrBpBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { vrPpSrBpStatsEntry 1 }

vrPpSrBpTinygramFramesIn OBJECT-TYPE
   SYNTAX     Counter32 
   ACCESS     read-only
   STATUS     mandatory
   DESCRIPTION
     "This attribute is indicative of the number of frames received on this 
      bridge port that used the tinygram compression scheme."
::= { vrPpSrBpStatsEntry 2 }

vrPpSrBpTinygramFramesOut OBJECT-TYPE
   SYNTAX     Counter32 
   ACCESS     read-only
   STATUS     mandatory
   DESCRIPTION
     "This attribute is indicative of the number of frames transmitted out this 
      bridge port that used the tinygram compression scheme."
::= { vrPpSrBpStatsEntry 3 }

vrPpSrBpInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { vrPpSrBpStatsEntry 4 }

vrPpSrBpOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { vrPpSrBpStatsEntry 5 }

vrPpSrBpSrProvTable OBJECT-TYPE
   SYNTAX     SEQUENCE OF VrPpSrBpSrProvEntry
   ACCESS     not-accessible
   STATUS     mandatory
   DESCRIPTION
     "This group contains all port specific, provisionable attributes associated 
      with SourceRouteBridge ports."
::= { vrPpSrBp 20 }

vrPpSrBpSrProvEntry OBJECT-TYPE
   SYNTAX     VrPpSrBpSrProvEntry
   ACCESS     not-accessible
   STATUS     mandatory
   DESCRIPTION
     "An entry in the vrPpSrBpSrProvTable."
   INDEX {
      vrIndex,
      vrPpIndex,
      vrPpSrBpIndex }
::= { vrPpSrBpSrProvTable 1 }

VrPpSrBpSrProvEntry ::= SEQUENCE {
   vrPpSrBpHopCount
      Unsigned32,
   vrPpSrBpExploreFrameTreatment
      INTEGER,
   vrPpSrBpLanId
      Unsigned32,
   vrPpSrBpInternalLanId
      Unsigned32,
   vrPpSrBpBridgeNum
      Unsigned32,
   vrPpSrBpLargestFrame
      Unsigned32,
   vrPpSrBpSteSpanMode
      INTEGER,
   vrPpSrBpAreRdLimit
      Unsigned32,
   vrPpSrBpSteRdLimit
      Unsigned32 }

vrPpSrBpHopCount OBJECT-TYPE
   SYNTAX     Unsigned32 (1..7)
   ACCESS     read-write
   STATUS     mandatory
   DESCRIPTION
     "This attribute specifies the maximum number of hops allowed in 
      Spanning Tree Explore and All Routes Explore frames. This value is one 
      less than the maximum number of route descriptors allowed in a source 
      route frame"
   DEFVAL     { 7 }
::= { vrPpSrBpSrProvEntry 1 }

vrPpSrBpExploreFrameTreatment OBJECT-TYPE
   SYNTAX     INTEGER  {
                 encap(0),
                 xlate(1) }
   ACCESS     read-write
   STATUS     mandatory
   DESCRIPTION
     "This attribute specifies whether or not explore frames received from 
      SourceRouteBridge ports will be sent to the SRTB-8209 translation or 
      the encapsulated SourceRouteBridge logic. This option is used only 
      when both the TbsrBridgePort and the SrtbBridgePort are provisioned 
      and enabled. 
      A value of Xlate implies that the explore frames will be sent to the Srtb 
      translation logic and a value of Encap implies that the frames will be 
      sent to the Encapsulated source route bridging logic."
   DEFVAL     { encap }
::= { vrPpSrBpSrProvEntry 2 }

vrPpSrBpLanId OBJECT-TYPE
   SYNTAX     Unsigned32 (0..4095)
   ACCESS     read-write
   STATUS     mandatory
   DESCRIPTION
     "This attribute specifies the identifier for the physical LAN that this port 
      is attached. All SourceRouteBridge ports are assigned to a physical LAN 
      and a logical internal LAN. 
      Current source route bridge implementations limit the lanId to a value in 
      the range 0 to 4095."
   DEFVAL     { 0 }
::= { vrPpSrBpSrProvEntry 3 }

vrPpSrBpInternalLanId OBJECT-TYPE
   SYNTAX     Unsigned32 (0..4095)
   ACCESS     read-write
   STATUS     mandatory
   DESCRIPTION
     "This attribute specifies the identifier for the internal logical LAN this 
      port is attached. All SourceRouteBridge ports are assigned to a physical 
      LAN and a logical internal LAN. 
      Current source route bridge implementations limit the lanId to a value in 
      the range 0 to 4095."
   DEFVAL     { 0 }
::= { vrPpSrBpSrProvEntry 4 }

vrPpSrBpBridgeNum OBJECT-TYPE
   SYNTAX     Unsigned32 (0..15)
   ACCESS     read-write
   STATUS     mandatory
   DESCRIPTION
     "This attribute specifies the value that is used to identify this bridge when 
      more than one bridge is used to span the same two LAN segments."
   DEFVAL     { 7 }
::= { vrPpSrBpSrProvEntry 5 }

vrPpSrBpLargestFrame OBJECT-TYPE
   SYNTAX     Unsigned32 (516 | 1470 | 2052 | 4399 | 8130 | 11407 | 17749)
   ACCESS     read-write
   STATUS     mandatory
   DESCRIPTION
     "This attribute specifies the maximum frame size (LLC and above) in 
      octets, allowed by this SourceRouteBridge port. This field is used to 
      determine whether a modification of the largest frame field of the 
      routing control field of the routing information field is warranted."
::= { vrPpSrBpSrProvEntry 6 }

vrPpSrBpSteSpanMode OBJECT-TYPE
   SYNTAX     INTEGER  {
                 autoSpan(1),
                 disabled(2),
                 forced(3) }
   ACCESS     read-write
   STATUS     mandatory
   DESCRIPTION
     "This attribute determines how this bridge port will react when presented 
      with a Spanning Tree Explore frame.
      If disabled, the Spanning Tree Explore frame is discarded regardless of 
      the value of stpPortState. 
      If the value of this attribute is forced, the Spanning Tree Explore frame 
      is forwarded regardless of the value of stpPortState. 
      autoSpan uses the stpPortState value to decide whether or not Spanning 
      Tree Explore frames should be forwarded out this bridge port. If the port 
      is in the forwarding state, the frame is received and transmitted 
      otherwise the frame is discarded."
   DEFVAL     { autoSpan }
::= { vrPpSrBpSrProvEntry 7 }

vrPpSrBpAreRdLimit OBJECT-TYPE
   SYNTAX     Unsigned32 (0..8)
   ACCESS     read-write
   STATUS     mandatory
   DESCRIPTION
     "This attribute specifies the number of route descriptors allowed in an All 
      Routes Explore frame received on a SourceRouteBridgePort or 
      SourceRouteTransparentBridgePort. Current source route bridge 
      implementations limit the areRdLimit to a value in the range 0 to 8."
   DEFVAL     { 8 }
::= { vrPpSrBpSrProvEntry 8 }

vrPpSrBpSteRdLimit OBJECT-TYPE
   SYNTAX     Unsigned32 (0..8)
   ACCESS     read-write
   STATUS     mandatory
   DESCRIPTION
     "This attribute specifies the number of route descriptors allowed in a 
      Spanning Tree Explore frame received on a SourceRouteBridgePort or 
      SourceRouteTransparentBridgePort. Current source route bridge 
      implementations limit the steRdLimit to a value in the range 0 to 8."
   DEFVAL     { 8 }
::= { vrPpSrBpSrProvEntry 9 }

vrPpSrBpSrStatsTable OBJECT-TYPE
   SYNTAX     SEQUENCE OF VrPpSrBpSrStatsEntry
   ACCESS     not-accessible
   STATUS     mandatory
   DESCRIPTION
     "This group contains all port specific statistical attributes associated with 
      SourceRouteBridge ports."
::= { vrPpSrBp 21 }

vrPpSrBpSrStatsEntry OBJECT-TYPE
   SYNTAX     VrPpSrBpSrStatsEntry
   ACCESS     not-accessible
   STATUS     mandatory
   DESCRIPTION
     "An entry in the vrPpSrBpSrStatsTable."
   INDEX {
      vrIndex,
      vrPpIndex,
      vrPpSrBpIndex }
::= { vrPpSrBpSrStatsTable 1 }

VrPpSrBpSrStatsEntry ::= SEQUENCE {
   vrPpSrBpSpecInFrames
      Counter32,
   vrPpSrBpSpecOutFrames
      Counter32,
   vrPpSrBpApeInFrames
      Counter32,
   vrPpSrBpApeOutFrames
      Counter32,
   vrPpSrBpSteInFrames
      Counter32,
   vrPpSrBpSteOutFrames
      Counter32,
   vrPpSrBpSegmentMismatchDiscards
      Counter32,
   vrPpSrBpDupSegmentDiscards
      Counter32,
   vrPpSrBpHopCountExceededDiscards
      Counter32,
   vrPpSrBpDupLanIdOrTreeErrors
      Counter32,
   vrPpSrBpLanIdMismatches
      Counter32,
   vrPpSrBpStaticDiscards
      Counter32,
   vrPpSrBpDynamicDiscards
      Counter32 }

vrPpSrBpSpecInFrames OBJECT-TYPE
   SYNTAX     Counter32 
   ACCESS     read-only
   STATUS     mandatory
   DESCRIPTION
     "This attribute specifies the number of specifically routed frames that 
      were received by this bridge port. A specifically routed frame has a route 
      descriptor, constructed by the originating host which details an explicit 
      route to the destination host. This counter will wrap to zero when it 
      exceeds its maximum."
::= { vrPpSrBpSrStatsEntry 1 }

vrPpSrBpSpecOutFrames OBJECT-TYPE
   SYNTAX     Counter32 
   ACCESS     read-only
   STATUS     mandatory
   DESCRIPTION
     "This attribute specifies the number of specifically routed frames that 
      were transmitted from this bridge port. This counter will wrap to zero 
      when it exceeds its maximum."
::= { vrPpSrBpSrStatsEntry 2 }

vrPpSrBpApeInFrames OBJECT-TYPE
   SYNTAX     Counter32 
   ACCESS     read-only
   STATUS     mandatory
   DESCRIPTION
     "This attribute specifies the number of All Path Explore frames received 
      on this bridge port. The All Path Explore frames are forwarded to all 
      SourceRouteBridge ports assigned to this bridge regardless of the port's 
      portStpStates. This counter will wrap to zero when it exceeds its 
      maximum."
::= { vrPpSrBpSrStatsEntry 3 }

vrPpSrBpApeOutFrames OBJECT-TYPE
   SYNTAX     Counter32 
   ACCESS     read-only
   STATUS     mandatory
   DESCRIPTION
     "This attribute specifies the number of All Path Explore frames 
      transmitted on this bridge port. The All Path Explore frames are 
      forwarded to all SourceRouteBridge ports assigned to this bridge 
      regardless of the port's portStpState state. This counter will wrap to zero 
      when it exceeds its maximum."
::= { vrPpSrBpSrStatsEntry 4 }

vrPpSrBpSteInFrames OBJECT-TYPE
   SYNTAX     Counter32 
   ACCESS     read-only
   STATUS     mandatory
   DESCRIPTION
     "This attribute specifies the number of Spanning Tree Explore frames 
      received on this bridge port. The Spanning Tree Explore frames are only 
      forwarded through bridge ports whose portStpState has a value of 
      forwarding. This counter will wrap to zero when it exceeds its 
      maximum."
::= { vrPpSrBpSrStatsEntry 5 }

vrPpSrBpSteOutFrames OBJECT-TYPE
   SYNTAX     Counter32 
   ACCESS     read-only
   STATUS     mandatory
   DESCRIPTION
     "This attribute specifies the number of Spanning Tree Frames transmitted 
      on this bridge port. This counter will wrap to zero when it exceeds its 
      maximum."
::= { vrPpSrBpSrStatsEntry 6 }

vrPpSrBpSegmentMismatchDiscards OBJECT-TYPE
   SYNTAX     Counter32 
   ACCESS     read-only
   STATUS     mandatory
   DESCRIPTION
     "This attribute specifies the number of All Routes Explore and Spanning 
      Tree Explore frames that were discarded due to an invalid next segment 
      value in the routing information field. This counter will wrap to zero 
      when it exceeds its maximum."
::= { vrPpSrBpSrStatsEntry 7 }

vrPpSrBpDupSegmentDiscards OBJECT-TYPE
   SYNTAX     Counter32 
   ACCESS     read-only
   STATUS     mandatory
   DESCRIPTION
     "This attribute specifies the number of frames discarded due to the 
      presence of a duplicate segment identifier in the route descriptor field 
      which may indicate a loop in the network topology. This counter will 
      wrap to zero when it exceeds its maximum."
::= { vrPpSrBpSrStatsEntry 8 }

vrPpSrBpHopCountExceededDiscards OBJECT-TYPE
   SYNTAX     Counter32 
   ACCESS     read-only
   STATUS     mandatory
   DESCRIPTION
     "This attribute specifies the number of All Routes Explore and Spanning 
      Tree Explore frames discarded by this bridge port due to a frame 
      exceeding the maximum size allowed for a route descriptor length. This 
      counter will wrap to zero when it exceeds its maximum."
::= { vrPpSrBpSrStatsEntry 9 }

vrPpSrBpDupLanIdOrTreeErrors OBJECT-TYPE
   SYNTAX     Counter32 
   ACCESS     read-only
   STATUS     mandatory
   DESCRIPTION
     "This attribute specifies the number frames received which contain 
      duplicate LAN IDs or Tree errors. This attribute is helpful in debugging 
      problems in networks which contain older IBM-SR bridges. This 
      counter will wrap to zero when it exceeds its maximum."
::= { vrPpSrBpSrStatsEntry 10 }

vrPpSrBpLanIdMismatches OBJECT-TYPE
   SYNTAX     Counter32 
   ACCESS     read-only
   STATUS     mandatory
   DESCRIPTION
     "This attributes counts the number of All Routes Explore or Spanning 
      Tree Explore frames that were discarded because the last LAN ID in the 
      routing information field did not equal the LAN ID. This counter will 
      wrap to zero when it exceeds its maximum."
::= { vrPpSrBpSrStatsEntry 11 }

vrPpSrBpStaticDiscards OBJECT-TYPE
   SYNTAX     Counter32 
   ACCESS     read-only
   STATUS     mandatory
   DESCRIPTION
     "This attribute is indicative of the number of explorer frames discarded 
      due to fact that the outbound SourceRouteBridge port was disabled or 
      deleted. This counter will wrap to zero when it exceeds its maximum."
::= { vrPpSrBpSrStatsEntry 12 }

vrPpSrBpDynamicDiscards OBJECT-TYPE
   SYNTAX     Counter32 
   ACCESS     read-only
   STATUS     mandatory
   DESCRIPTION
     "This attribute specifies the number of frames discarded due to receiving 
      a frame with a target LAN ID which did not match the internal LAN ID 
      of the receiving bridge port. This counter will wrap to zero when it 
      exceeds its maximum."
::= { vrPpSrBpSrStatsEntry 13 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

vrPpSrBpNs OBJECT IDENTIFIER ::= { vrPpSrBp 2 }



vrPpSrBpNsRowStatusTable OBJECT-TYPE
   SYNTAX     SEQUENCE OF VrPpSrBpNsRowStatusEntry
   ACCESS     not-accessible
   STATUS     mandatory
   DESCRIPTION
     "This entry controls the addition and deletion of 
      vrPpSrBpNs components."
::= { vrPpSrBpNs 1 }

vrPpSrBpNsRowStatusEntry OBJECT-TYPE
   SYNTAX     VrPpSrBpNsRowStatusEntry
   ACCESS     not-accessible
   STATUS     mandatory
   DESCRIPTION
     "A single entry in the table represents a single 
      vrPpSrBpNs component."
   INDEX {
      vrIndex,
      vrPpIndex,
      vrPpSrBpIndex,
      vrPpSrBpNsIndex }
::= { vrPpSrBpNsRowStatusTable 1 }

VrPpSrBpNsRowStatusEntry ::= SEQUENCE {
   vrPpSrBpNsRowStatus
      RowStatus,
   vrPpSrBpNsComponentName
      DisplayString,
   vrPpSrBpNsStorageType
      StorageType,
   vrPpSrBpNsIndex
      NonReplicated }

vrPpSrBpNsRowStatus OBJECT-TYPE
   SYNTAX     RowStatus 
   ACCESS     read-write
   STATUS     mandatory
   DESCRIPTION
     "This variable is used as the basis for SNMP naming of
      vrPpSrBpNs components.
      These components can be added and deleted."
::= { vrPpSrBpNsRowStatusEntry 1 }

vrPpSrBpNsComponentName OBJECT-TYPE
   SYNTAX     DisplayString 
   ACCESS     read-only
   STATUS     mandatory
   DESCRIPTION
     "This variable provides the component's string name for
      use with the ASCII Console Interface"
::= { vrPpSrBpNsRowStatusEntry 2 }

vrPpSrBpNsStorageType OBJECT-TYPE
   SYNTAX     StorageType 
   ACCESS     read-only
   STATUS     mandatory
   DESCRIPTION
     "This variable represents the storage type value for the
      vrPpSrBpNs tables."
::= { vrPpSrBpNsRowStatusEntry 4 }

vrPpSrBpNsIndex OBJECT-TYPE
   SYNTAX     NonReplicated 
   ACCESS     not-accessible
   STATUS     mandatory
   DESCRIPTION
     "This variable represents the index for the vrPpSrBpNs tables."
::= { vrPpSrBpNsRowStatusEntry 10 }

vrPpSrBpNsProvTable OBJECT-TYPE
   SYNTAX     SEQUENCE OF VrPpSrBpNsProvEntry
   ACCESS     not-accessible
   STATUS     mandatory
   DESCRIPTION
     "This group houses all the port specific provisionable attributes 
      associated with Ns. These attributes influence the application of filters to 
      incoming and outgoing frames."
::= { vrPpSrBpNs 10 }

vrPpSrBpNsProvEntry OBJECT-TYPE
   SYNTAX     VrPpSrBpNsProvEntry
   ACCESS     not-accessible
   STATUS     mandatory
   DESCRIPTION
     "An entry in the vrPpSrBpNsProvTable."
   INDEX {
      vrIndex,
      vrPpIndex,
      vrPpSrBpIndex,
      vrPpSrBpNsIndex }
::= { vrPpSrBpNsProvTable 1 }

VrPpSrBpNsProvEntry ::= SEQUENCE {
   vrPpSrBpNsIncomingFilter
      AsciiString,
   vrPpSrBpNsOutgoingFilter
      AsciiString }

vrPpSrBpNsIncomingFilter OBJECT-TYPE
   SYNTAX     AsciiString (SIZE (0..32))
   ACCESS     read-write
   STATUS     mandatory
   DESCRIPTION
     "This attribute specifies the name of the filter to be applied at the 
      incoming filter point."
::= { vrPpSrBpNsProvEntry 2 }

vrPpSrBpNsOutgoingFilter OBJECT-TYPE
   SYNTAX     AsciiString (SIZE (0..32))
   ACCESS     read-write
   STATUS     mandatory
   DESCRIPTION
     "This attribute specifies the name of the filter to be applied at the out 
      going filter point."
::= { vrPpSrBpNsProvEntry 3 }


-- Vr/<string> Pp/<string> SourceRouteTransparentBridgePort
-- This component represents a Source Route Transparent (SRT) bridge 
-- port. It contains all the attributes (provisionable and operational 
-- attributes) necessary for the operation of the bridge port. The SRT 
-- bridge port provides a mechanism to transmit and receive both source 
-- route and transparent bridge frames. In essence, the SRT bridging 
-- scheme defines a method for TB bridges to handle SR frames. SRT 
-- bridge ports participate in the transparent bridging spanning tree 
-- protocol.

vrPpSrtBp OBJECT IDENTIFIER ::= { vrPp 9 }



vrPpSrtBpRowStatusTable OBJECT-TYPE
   SYNTAX     SEQUENCE OF VrPpSrtBpRowStatusEntry
   ACCESS     not-accessible
   STATUS     mandatory
   DESCRIPTION
     "This entry controls the addition and deletion of 
      vrPpSrtBp components."
::= { vrPpSrtBp 1 }

vrPpSrtBpRowStatusEntry OBJECT-TYPE
   SYNTAX     VrPpSrtBpRowStatusEntry
   ACCESS     not-accessible
   STATUS     mandatory
   DESCRIPTION
     "A single entry in the table represents a single 
      vrPpSrtBp component."
   INDEX {
      vrIndex,
      vrPpIndex,
      vrPpSrtBpIndex }
::= { vrPpSrtBpRowStatusTable 1 }

VrPpSrtBpRowStatusEntry ::= SEQUENCE {
   vrPpSrtBpRowStatus
      RowStatus,
   vrPpSrtBpComponentName
      DisplayString,
   vrPpSrtBpStorageType
      StorageType,
   vrPpSrtBpIndex
      NonReplicated }

vrPpSrtBpRowStatus OBJECT-TYPE
   SYNTAX     RowStatus 
   ACCESS     read-write
   STATUS     mandatory
   DESCRIPTION
     "This variable is used as the basis for SNMP naming of
      vrPpSrtBp components.
      These components can be added and deleted."
::= { vrPpSrtBpRowStatusEntry 1 }

vrPpSrtBpComponentName OBJECT-TYPE
   SYNTAX     DisplayString 
   ACCESS     read-only
   STATUS     mandatory
   DESCRIPTION
     "This variable provides the component's string name for
      use with the ASCII Console Interface"
::= { vrPpSrtBpRowStatusEntry 2 }

vrPpSrtBpStorageType OBJECT-TYPE
   SYNTAX     StorageType 
   ACCESS     read-only
   STATUS     mandatory
   DESCRIPTION
     "This variable represents the storage type value for the
      vrPpSrtBp tables."
::= { vrPpSrtBpRowStatusEntry 4 }

vrPpSrtBpIndex OBJECT-TYPE
   SYNTAX     NonReplicated 
   ACCESS     not-accessible
   STATUS     mandatory
   DESCRIPTION
     "This variable represents the index for the vrPpSrtBp tables."
::= { vrPpSrtBpRowStatusEntry 10 }

vrPpSrtBpProvTable OBJECT-TYPE
   SYNTAX     SEQUENCE OF VrPpSrtBpProvEntry
   ACCESS     not-accessible
   STATUS     mandatory
   DESCRIPTION
     "This group houses all the provisionable attributes that belong to the this 
      group. This group of attributes is applicable to all types of bridge ports 
      and represent the common factor between them. These attributes 
      influence the working of a bridge port."
::= { vrPpSrtBp 10 }

vrPpSrtBpProvEntry OBJECT-TYPE
   SYNTAX     VrPpSrtBpProvEntry
   ACCESS     not-accessible
   STATUS     mandatory
   DESCRIPTION
     "An entry in the vrPpSrtBpProvTable."
   INDEX {
      vrIndex,
      vrPpIndex,
      vrPpSrtBpIndex }
::= { vrPpSrtBpProvTable 1 }

VrPpSrtBpProvEntry ::= SEQUENCE {
   vrPpSrtBpTranslateIpx
      INTEGER,
   vrPpSrtBpFragmentIp
      INTEGER,
   vrPpSrtBpServiceClass
      INTEGER,
   vrPpSrtBpConvertArpMacAddress
      INTEGER,
   vrPpSrtBpPortNum
      Unsigned32,
   vrPpSrtBpOutboundFrameMediaType
      INTEGER }

vrPpSrtBpTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { vrPpSrtBpProvEntry 1 }

vrPpSrtBpFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { vrPpSrtBpProvEntry 2 }

vrPpSrtBpServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { vrPpSrtBpProvEntry 3 }

vrPpSrtBpConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { vrPpSrtBpProvEntry 4 }

vrPpSrtBpPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { vrPpSrtBpProvEntry 5 }

vrPpSrtBpOutboundFrameMediaType OBJECT-TYPE
   SYNTAX     INTEGER  {
                 unaltered(1),
                 ethernetConv(2) }
   ACCESS     read-write
   STATUS     mandatory
   DESCRIPTION
     "This attribute specifies the media type the frame must be in before it is 
      to be forwarded over the outbound supported WAN Bridge Protocol 
      Port. The attribute only applies to outbound Bridge Protocol Port.
      
      For supported bridge ports, if the attribute value remains set to the 
      default value of unaltered then there will be no frame conversion. When 
      the value is set to the value ethernetConv then all frames being 
      forwarded out the outbound WAN Port will be converted to ethernet 
      before forwarding takes place. The only outbound WAN medias that 
      currently support conversion are: FR (Frame Relay) and VNS. All other 
      medias will fail the Bridge Port semantic check when attempts are made 
      to alter this attribute. 
      
      The following is an example of what the user may be able to do. Frames 
      originating from a Token Ring are to be flooded out onto another Token 
      Ring and a Frame Relay Port. The token ring Outbound port performs 
      no translation, yet the FR Port has the outboundFrameMediaType 
      attribute set to ethernetConv which results in the frame being translated 
      into Ethernet format from Token Ring format before Frame Relay does 
      its encapsulation and transmits over the FR port."
   DEFVAL     { unaltered }
::= { vrPpSrtBpProvEntry 6 }

vrPpSrtBpTbProvTable OBJECT-TYPE
   SYNTAX     SEQUENCE OF VrPpSrtBpTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { vrPpSrtBp 11 }

vrPpSrtBpTbProvEntry OBJECT-TYPE
   SYNTAX     VrPpSrtBpTbProvEntry
   ACCESS     not-accessible
   STATUS     mandatory
   DESCRIPTION
     "An entry in the vrPpSrtBpTbProvTable."
   INDEX {
      vrIndex,
      vrPpIndex,
      vrPpSrtBpIndex }
::= { vrPpSrtBpTbProvTable 1 }

VrPpSrtBpTbProvEntry ::= SEQUENCE {
   vrPpSrtBpSecureOption
      INTEGER }

vrPpSrtBpSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { vrPpSrtBpTbProvEntry 1 }

vrPpSrtBpStpProvTable OBJECT-TYPE
   SYNTAX     SEQUENCE OF VrPpSrtBpStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { vrPpSrtBp 12 }

vrPpSrtBpStpProvEntry OBJECT-TYPE
   SYNTAX     VrPpSrtBpStpProvEntry
   ACCESS     not-accessible
   STATUS     mandatory
   DESCRIPTION
     "An entry in the vrPpSrtBpStpProvTable."
   INDEX {
      vrIndex,
      vrPpIndex,
      vrPpSrtBpIndex }
::= { vrPpSrtBpStpProvTable 1 }

VrPpSrtBpStpProvEntry ::= SEQUENCE {
   vrPpSrtBpAdminStatus
      INTEGER,
   vrPpSrtBpPortStateStpControl
      INTEGER,
   vrPpSrtBpStpTypeProv
      INTEGER,
   vrPpSrtBpPortPriority
      Unsigned32,
   vrPpSrtBpPathCost
      Unsigned32,
   vrPpSrtBpPathCostMethod
      INTEGER }

vrPpSrtBpAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { vrPpSrtBpStpProvEntry 1 }

vrPpSrtBpPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { vrPpSrtBpStpProvEntry 2 }

vrPpSrtBpStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { vrPpSrtBpStpProvEntry 3 }

vrPpSrtBpPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { vrPpSrtBpStpProvEntry 4 }

vrPpSrtBpPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { vrPpSrtBpStpProvEntry 5 }

vrPpSrtBpPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { vrPpSrtBpStpProvEntry 6 }

vrPpSrtBpDIProvTable OBJECT-TYPE
   SYNTAX     SEQUENCE OF VrPpSrtBpDIProvEntry
   ACCESS     not-accessible
   STATUS     mandatory
   DESCRIPTION
     "This group houses all the provisionable, domain specific attributes for a 
      non-encapsulating bridge port."
::= { vrPpSrtBp 13 }

vrPpSrtBpDIProvEntry OBJECT-TYPE
   SYNTAX     VrPpSrtBpDIProvEntry
   ACCESS     not-accessible
   STATUS     mandatory
   DESCRIPTION
     "An entry in the vrPpSrtBpDIProvTable."
   INDEX {
      vrIndex,
      vrPpIndex,
      vrPpSrtBpIndex }
::= { vrPpSrtBpDIProvTable 1 }

VrPpSrtBpDIProvEntry ::= SEQUENCE {
   vrPpSrtBpDomainNum
      Unsigned32,
   vrPpSrtBpPreserveDomain
      INTEGER }

vrPpSrtBpDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { vrPpSrtBpDIProvEntry 1 }

vrPpSrtBpPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { vrPpSrtBpDIProvEntry 2 }

vrPpSrtBpStateTable OBJECT-TYPE
   SYNTAX     SEQUENCE OF VrPpSrtBpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpSrtBp 14 }

vrPpSrtBpStateEntry OBJECT-TYPE
   SYNTAX     VrPpSrtBpStateEntry
   ACCESS     not-accessible
   STATUS     mandatory
   DESCRIPTION
     "An entry in the vrPpSrtBpStateTable."
   INDEX {
      vrIndex,
      vrPpIndex,
      vrPpSrtBpIndex }
::= { vrPpSrtBpStateTable 1 }

VrPpSrtBpStateEntry ::= SEQUENCE {
   vrPpSrtBpAdminState
      INTEGER,
   vrPpSrtBpOperationalState
      INTEGER,
   vrPpSrtBpUsageState
      INTEGER }

vrPpSrtBpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpSrtBpStateEntry 1 }

vrPpSrtBpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpSrtBpStateEntry 2 }

vrPpSrtBpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpSrtBpStateEntry 3 }

vrPpSrtBpOperStatusTable OBJECT-TYPE
   SYNTAX     SEQUENCE OF VrPpSrtBpOperStatusEntry
   ACCESS     not-accessible
   STATUS     mandatory
   DESCRIPTION
     "This group includes the Operational Status attribute. This attribute 
      defines the current operational state of this component."
::= { vrPpSrtBp 15 }

vrPpSrtBpOperStatusEntry OBJECT-TYPE
   SYNTAX     VrPpSrtBpOperStatusEntry
   ACCESS     not-accessible
   STATUS     mandatory
   DESCRIPTION
     "An entry in the vrPpSrtBpOperStatusTable."
   INDEX {
      vrIndex,
      vrPpIndex,
      vrPpSrtBpIndex }
::= { vrPpSrtBpOperStatusTable 1 }

VrPpSrtBpOperStatusEntry ::= SEQUENCE {
   vrPpSrtBpSnmpOperStatus
      INTEGER }

vrPpSrtBpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpSrtBpOperStatusEntry 1 }

vrPpSrtBpOperTable OBJECT-TYPE
   SYNTAX     SEQUENCE OF VrPpSrtBpOperEntry
   ACCESS     not-accessible
   STATUS     mandatory
   DESCRIPTION
     "This group houses all the operational attributes belonging to the base 
      group. The base group of attributes is applicable to all types of bridge 
      ports and represent the common factor between them. These attributes in 
      part, reflect the state of a bridge port."
::= { vrPpSrtBp 16 }

vrPpSrtBpOperEntry OBJECT-TYPE
   SYNTAX     VrPpSrtBpOperEntry
   ACCESS     not-accessible
   STATUS     mandatory
   DESCRIPTION
     "An entry in the vrPpSrtBpOperTable."
   INDEX {
      vrIndex,
      vrPpIndex,
      vrPpSrtBpIndex }
::= { vrPpSrtBpOperTable 1 }

VrPpSrtBpOperEntry ::= SEQUENCE {
   vrPpSrtBpPortName
      AsciiString,
   vrPpSrtBpUpTime
      Unsigned32,
   vrPpSrtBpDownTime
      Unsigned32,
   vrPpSrtBpBridgingMode
      INTEGER,
   vrPpSrtBpBridgePortConfig
      INTEGER,
   vrPpSrtBpBridgePortType
      INTEGER,
   vrPpSrtBpIfIndex
      InterfaceIndex,
   vrPpSrtBpDelayExceededDiscards
      Counter32,
   vrPpSrtBpMtuExceededDiscards
      Counter32 }

vrPpSrtBpPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { vrPpSrtBpOperEntry 1 }

vrPpSrtBpUpTime OBJECT-TYPE
   SYNTAX     Unsigned32 (0..4294967295)
   ACCESS     read-only
   STATUS     mandatory
   DESCRIPTION
     "This attribute specifies the accumulated up time of this bridge port since 
      the last reset occurred."
   DEFVAL     { 0 }
::= { vrPpSrtBpOperEntry 3 }

vrPpSrtBpDownTime OBJECT-TYPE
   SYNTAX     Unsigned32 (0..4294967295)
   ACCESS     read-only
   STATUS     mandatory
   DESCRIPTION
     "This attribute specifies the accumulated down time of this bridge port 
      since the last reset occurred."
   DEFVAL     { 0 }
::= { vrPpSrtBpOperEntry 4 }

vrPpSrtBpBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { vrPpSrtBpOperEntry 5 }

vrPpSrtBpBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { vrPpSrtBpOperEntry 6 }

vrPpSrtBpBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { vrPpSrtBpOperEntry 7 }

vrPpSrtBpIfIndex OBJECT-TYPE
   SYNTAX     InterfaceIndex (1..65535)
   ACCESS     read-only
   STATUS     mandatory
   DESCRIPTION
     "This attribute specifies the index into the Interface Table where in 
      information about the media interface corresponding to the bridge port is 
      maintained."
::= { vrPpSrtBpOperEntry 8 }

vrPpSrtBpDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { vrPpSrtBpOperEntry 10 }

vrPpSrtBpMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { vrPpSrtBpOperEntry 11 }

vrPpSrtBpTbOperTable OBJECT-TYPE
   SYNTAX     SEQUENCE OF VrPpSrtBpTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { vrPpSrtBp 17 }

vrPpSrtBpTbOperEntry OBJECT-TYPE
   SYNTAX     VrPpSrtBpTbOperEntry
   ACCESS     not-accessible
   STATUS     mandatory
   DESCRIPTION
     "An entry in the vrPpSrtBpTbOperTable."
   INDEX {
      vrIndex,
      vrPpIndex,
      vrPpSrtBpIndex }
::= { vrPpSrtBpTbOperTable 1 }

VrPpSrtBpTbOperEntry ::= SEQUENCE {
   vrPpSrtBpMaxInfo
      Unsigned32,
   vrPpSrtBpBadVerifyDiscards
      Counter32,
   vrPpSrtBpUnicastNoMatches
      Counter32,
   vrPpSrtBpStaticEntryDiscards
      Counter32,
   vrPpSrtBpDynamicEntryDiscards
      Counter32,
   vrPpSrtBpLearningDiscards
      Counter32,
   vrPpSrtBpInDiscards
      Counter32,
   vrPpSrtBpInFrames
      Counter32,
   vrPpSrtBpOutFrames
      Counter32 }

vrPpSrtBpMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { vrPpSrtBpTbOperEntry 2 }

vrPpSrtBpBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { vrPpSrtBpTbOperEntry 3 }

vrPpSrtBpUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { vrPpSrtBpTbOperEntry 4 }

vrPpSrtBpStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { vrPpSrtBpTbOperEntry 5 }

vrPpSrtBpDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { vrPpSrtBpTbOperEntry 6 }

vrPpSrtBpLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { vrPpSrtBpTbOperEntry 7 }

vrPpSrtBpInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { vrPpSrtBpTbOperEntry 8 }

vrPpSrtBpInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { vrPpSrtBpTbOperEntry 9 }

vrPpSrtBpOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { vrPpSrtBpTbOperEntry 10 }

vrPpSrtBpStpOperTable OBJECT-TYPE
   SYNTAX     SEQUENCE OF VrPpSrtBpStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { vrPpSrtBp 18 }

vrPpSrtBpStpOperEntry OBJECT-TYPE
   SYNTAX     VrPpSrtBpStpOperEntry
   ACCESS     not-accessible
   STATUS     mandatory
   DESCRIPTION
     "An entry in the vrPpSrtBpStpOperTable."
   INDEX {
      vrIndex,
      vrPpIndex,
      vrPpSrtBpIndex }
::= { vrPpSrtBpStpOperTable 1 }

VrPpSrtBpStpOperEntry ::= SEQUENCE {
   vrPpSrtBpStpPortState
      INTEGER,
   vrPpSrtBpStpTypeOper
      INTEGER,
   vrPpSrtBpDesignatedCost
      Unsigned32,
   vrPpSrtBpPathCostOper
      Unsigned32,
   vrPpSrtBpDesignatedBridge
      BridgeId,
   vrPpSrtBpDesignatedPort
      Hex,
   vrPpSrtBpForwardTransitions
      Counter32,
   vrPpSrtBpBlockingDiscards
      Counter32,
   vrPpSrtBpDesignatedRoot
      BridgeId }

vrPpSrtBpStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { vrPpSrtBpStpOperEntry 2 }

vrPpSrtBpStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { vrPpSrtBpStpOperEntry 3 }

vrPpSrtBpDesignatedCost OBJECT-TYPE
   SYNTAX     Unsigned32 (0..4294967295)
   ACCESS     read-only
   STATUS     mandatory
   DESCRIPTION
     "This attribute specifies the path cost of the designated port of the lan 
      segment connected to the port."
::= { vrPpSrtBpStpOperEntry 4 }

vrPpSrtBpPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { vrPpSrtBpStpOperEntry 5 }

vrPpSrtBpDesignatedBridge OBJECT-TYPE
   SYNTAX     BridgeId (SIZE (8))
   ACCESS     read-only
   STATUS     mandatory
   DESCRIPTION
     "This attribute specifies the identifier of the bridge that this port considers 
      to be the designated bridge."
::= { vrPpSrtBpStpOperEntry 6 }

vrPpSrtBpDesignatedPort OBJECT-TYPE
   SYNTAX     Hex (0..65535)
   ACCESS     read-only
   STATUS     mandatory
   DESCRIPTION
     "This attribute specifies the port identifier of the port on the designated 
      bridge, attached to the same lan as this port is attached to."
::= { vrPpSrtBpStpOperEntry 7 }

vrPpSrtBpForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { vrPpSrtBpStpOperEntry 8 }

vrPpSrtBpBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { vrPpSrtBpStpOperEntry 9 }

vrPpSrtBpDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { vrPpSrtBpStpOperEntry 10 }

vrPpSrtBpStatsTable OBJECT-TYPE
   SYNTAX     SEQUENCE OF VrPpSrtBpStatsEntry
   ACCESS     not-accessible
   STATUS     mandatory
   DESCRIPTION
     "This group houses all the statistical attributes applicable to all types of 
      bridge ports and represents the common factor between them. These 
      attributes in part reflect the state of the bridge port."
::= { vrPpSrtBp 19 }

vrPpSrtBpStatsEntry OBJECT-TYPE
   SYNTAX     VrPpSrtBpStatsEntry
   ACCESS     not-accessible
   STATUS     mandatory
   DESCRIPTION
     "An entry in the vrPpSrtBpStatsTable."
   INDEX {
      vrIndex,
      vrPpIndex,
      vrPpSrtBpIndex }
::= { vrPpSrtBpStatsTable 1 }

VrPpSrtBpStatsEntry ::= SEQUENCE {
   vrPpSrtBpBadAbstractDiscards
      Counter32,
   vrPpSrtBpTinygramFramesIn
      Counter32,
   vrPpSrtBpTinygramFramesOut
      Counter32,
   vrPpSrtBpInFilterDiscards
      Counter32,
   vrPpSrtBpOutFilterDiscards
      Counter32 }

vrPpSrtBpBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { vrPpSrtBpStatsEntry 1 }

vrPpSrtBpTinygramFramesIn OBJECT-TYPE
   SYNTAX     Counter32 
   ACCESS     read-only
   STATUS     mandatory
   DESCRIPTION
     "This attribute is indicative of the number of frames received on this 
      bridge port that used the tinygram compression scheme."
::= { vrPpSrtBpStatsEntry 2 }

vrPpSrtBpTinygramFramesOut OBJECT-TYPE
   SYNTAX     Counter32 
   ACCESS     read-only
   STATUS     mandatory
   DESCRIPTION
     "This attribute is indicative of the number of frames transmitted out this 
      bridge port that used the tinygram compression scheme."
::= { vrPpSrtBpStatsEntry 3 }

vrPpSrtBpInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { vrPpSrtBpStatsEntry 4 }

vrPpSrtBpOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { vrPpSrtBpStatsEntry 5 }

vrPpSrtBpSrProvTable OBJECT-TYPE
   SYNTAX     SEQUENCE OF VrPpSrtBpSrProvEntry
   ACCESS     not-accessible
   STATUS     mandatory
   DESCRIPTION
     "This group contains all port specific, provisionable attributes associated 
      with SourceRouteBridge ports."
::= { vrPpSrtBp 20 }

vrPpSrtBpSrProvEntry OBJECT-TYPE
   SYNTAX     VrPpSrtBpSrProvEntry
   ACCESS     not-accessible
   STATUS     mandatory
   DESCRIPTION
     "An entry in the vrPpSrtBpSrProvTable."
   INDEX {
      vrIndex,
      vrPpIndex,
      vrPpSrtBpIndex }
::= { vrPpSrtBpSrProvTable 1 }

VrPpSrtBpSrProvEntry ::= SEQUENCE {
   vrPpSrtBpHopCount
      Unsigned32,
   vrPpSrtBpExploreFrameTreatment
      INTEGER,
   vrPpSrtBpLanId
      Unsigned32,
   vrPpSrtBpInternalLanId
      Unsigned32,
   vrPpSrtBpBridgeNum
      Unsigned32,
   vrPpSrtBpLargestFrame
      Unsigned32,
   vrPpSrtBpSteSpanMode
      INTEGER,
   vrPpSrtBpAreRdLimit
      Unsigned32,
   vrPpSrtBpSteRdLimit
      Unsigned32 }

vrPpSrtBpHopCount OBJECT-TYPE
   SYNTAX     Unsigned32 (1..7)
   ACCESS     read-write
   STATUS     mandatory
   DESCRIPTION
     "This attribute specifies the maximum number of hops allowed in 
      Spanning Tree Explore and All Routes Explore frames. This value is one 
      less than the maximum number of route descriptors allowed in a source 
      route frame"
   DEFVAL     { 7 }
::= { vrPpSrtBpSrProvEntry 1 }

vrPpSrtBpExploreFrameTreatment OBJECT-TYPE
   SYNTAX     INTEGER  {
                 encap(0),
                 xlate(1) }
   ACCESS     read-write
   STATUS     mandatory
   DESCRIPTION
     "This attribute specifies whether or not explore frames received from 
      SourceRouteBridge ports will be sent to the SRTB-8209 translation or 
      the encapsulated SourceRouteBridge logic. This option is used only 
      when both the TbsrBridgePort and the SrtbBridgePort are provisioned 
      and enabled. 
      A value of Xlate implies that the explore frames will be sent to the Srtb 
      translation logic and a value of Encap implies that the frames will be 
      sent to the Encapsulated source route bridging logic."
   DEFVAL     { encap }
::= { vrPpSrtBpSrProvEntry 2 }

vrPpSrtBpLanId OBJECT-TYPE
   SYNTAX     Unsigned32 (0..4095)
   ACCESS     read-write
   STATUS     mandatory
   DESCRIPTION
     "This attribute specifies the identifier for the physical LAN that this port 
      is attached. All SourceRouteBridge ports are assigned to a physical LAN 
      and a logical internal LAN. 
      Current source route bridge implementations limit the lanId to a value in 
      the range 0 to 4095."
   DEFVAL     { 0 }
::= { vrPpSrtBpSrProvEntry 3 }

vrPpSrtBpInternalLanId OBJECT-TYPE
   SYNTAX     Unsigned32 (0..4095)
   ACCESS     read-write
   STATUS     mandatory
   DESCRIPTION
     "This attribute specifies the identifier for the internal logical LAN this 
      port is attached. All SourceRouteBridge ports are assigned to a physical 
      LAN and a logical internal LAN. 
      Current source route bridge implementations limit the lanId to a value in 
      the range 0 to 4095."
   DEFVAL     { 0 }
::= { vrPpSrtBpSrProvEntry 4 }

vrPpSrtBpBridgeNum OBJECT-TYPE
   SYNTAX     Unsigned32 (0..15)
   ACCESS     read-write
   STATUS     mandatory
   DESCRIPTION
     "This attribute specifies the value that is used to identify this bridge when 
      more than one bridge is used to span the same two LAN segments."
   DEFVAL     { 7 }
::= { vrPpSrtBpSrProvEntry 5 }

vrPpSrtBpLargestFrame OBJECT-TYPE
   SYNTAX     Unsigned32 (516 | 1470 | 2052 | 4399 | 8130 | 11407 | 17749)
   ACCESS     read-write
   STATUS     mandatory
   DESCRIPTION
     "This attribute specifies the maximum frame size (LLC and above) in 
      octets, allowed by this SourceRouteBridge port. This field is used to 
      determine whether a modification of the largest frame field of the 
      routing control field of the routing information field is warranted."
::= { vrPpSrtBpSrProvEntry 6 }

vrPpSrtBpSteSpanMode OBJECT-TYPE
   SYNTAX     INTEGER  {
                 autoSpan(1),
                 disabled(2),
                 forced(3) }
   ACCESS     read-write
   STATUS     mandatory
   DESCRIPTION
     "This attribute determines how this bridge port will react when presented 
      with a Spanning Tree Explore frame.
      If disabled, the Spanning Tree Explore frame is discarded regardless of 
      the value of stpPortState. 
      If the value of this attribute is forced, the Spanning Tree Explore frame 
      is forwarded regardless of the value of stpPortState. 
      autoSpan uses the stpPortState value to decide whether or not Spanning 
      Tree Explore frames should be forwarded out this bridge port. If the port 
      is in the forwarding state, the frame is received and transmitted 
      otherwise the frame is discarded."
   DEFVAL     { autoSpan }
::= { vrPpSrtBpSrProvEntry 7 }

vrPpSrtBpAreRdLimit OBJECT-TYPE
   SYNTAX     Unsigned32 (0..8)
   ACCESS     read-write
   STATUS     mandatory
   DESCRIPTION
     "This attribute specifies the number of route descriptors allowed in an All 
      Routes Explore frame received on a SourceRouteBridgePort or 
      SourceRouteTransparentBridgePort. Current source route bridge 
      implementations limit the areRdLimit to a value in the range 0 to 8."
   DEFVAL     { 8 }
::= { vrPpSrtBpSrProvEntry 8 }

vrPpSrtBpSteRdLimit OBJECT-TYPE
   SYNTAX     Unsigned32 (0..8)
   ACCESS     read-write
   STATUS     mandatory
   DESCRIPTION
     "This attribute specifies the number of route descriptors allowed in a 
      Spanning Tree Explore frame received on a SourceRouteBridgePort or 
      SourceRouteTransparentBridgePort. Current source route bridge 
      implementations limit the steRdLimit to a value in the range 0 to 8."
   DEFVAL     { 8 }
::= { vrPpSrtBpSrProvEntry 9 }

vrPpSrtBpSrStatsTable OBJECT-TYPE
   SYNTAX     SEQUENCE OF VrPpSrtBpSrStatsEntry
   ACCESS     not-accessible
   STATUS     mandatory
   DESCRIPTION
     "This group contains all port specific statistical attributes associated with 
      SourceRouteBridge ports."
::= { vrPpSrtBp 21 }

vrPpSrtBpSrStatsEntry OBJECT-TYPE
   SYNTAX     VrPpSrtBpSrStatsEntry
   ACCESS     not-accessible
   STATUS     mandatory
   DESCRIPTION
     "An entry in the vrPpSrtBpSrStatsTable."
   INDEX {
      vrIndex,
      vrPpIndex,
      vrPpSrtBpIndex }
::= { vrPpSrtBpSrStatsTable 1 }

VrPpSrtBpSrStatsEntry ::= SEQUENCE {
   vrPpSrtBpSpecInFrames
      Counter32,
   vrPpSrtBpSpecOutFrames
      Counter32,
   vrPpSrtBpApeInFrames
      Counter32,
   vrPpSrtBpApeOutFrames
      Counter32,
   vrPpSrtBpSteInFrames
      Counter32,
   vrPpSrtBpSteOutFrames
      Counter32,
   vrPpSrtBpSegmentMismatchDiscards
      Counter32,
   vrPpSrtBpDupSegmentDiscards
      Counter32,
   vrPpSrtBpHopCountExceededDiscards
      Counter32,
   vrPpSrtBpDupLanIdOrTreeErrors
      Counter32,
   vrPpSrtBpLanIdMismatches
      Counter32,
   vrPpSrtBpStaticDiscards
      Counter32,
   vrPpSrtBpDynamicDiscards
      Counter32 }

vrPpSrtBpSpecInFrames OBJECT-TYPE
   SYNTAX     Counter32 
   ACCESS     read-only
   STATUS     mandatory
   DESCRIPTION
     "This attribute specifies the number of specifically routed frames that 
      were received by this bridge port. A specifically routed frame has a route 
      descriptor, constructed by the originating host which details an explicit 
      route to the destination host. This counter will wrap to zero when it 
      exceeds its maximum."
::= { vrPpSrtBpSrStatsEntry 1 }

vrPpSrtBpSpecOutFrames OBJECT-TYPE
   SYNTAX     Counter32 
   ACCESS     read-only
   STATUS     mandatory
   DESCRIPTION
     "This attribute specifies the number of specifically routed frames that 
      were transmitted from this bridge port. This counter will wrap to zero 
      when it exceeds its maximum."
::= { vrPpSrtBpSrStatsEntry 2 }

vrPpSrtBpApeInFrames OBJECT-TYPE
   SYNTAX     Counter32 
   ACCESS     read-only
   STATUS     mandatory
   DESCRIPTION
     "This attribute specifies the number of All Path Explore frames received 
      on this bridge port. The All Path Explore frames are forwarded to all 
      SourceRouteBridge ports assigned to this bridge regardless of the port's 
      portStpStates. This counter will wrap to zero when it exceeds its 
      maximum."
::= { vrPpSrtBpSrStatsEntry 3 }

vrPpSrtBpApeOutFrames OBJECT-TYPE
   SYNTAX     Counter32 
   ACCESS     read-only
   STATUS     mandatory
   DESCRIPTION
     "This attribute specifies the number of All Path Explore frames 
      transmitted on this bridge port. The All Path Explore frames are 
      forwarded to all SourceRouteBridge ports assigned to this bridge 
      regardless of the port's portStpState state. This counter will wrap to zero 
      when it exceeds its maximum."
::= { vrPpSrtBpSrStatsEntry 4 }

vrPpSrtBpSteInFrames OBJECT-TYPE
   SYNTAX     Counter32 
   ACCESS     read-only
   STATUS     mandatory
   DESCRIPTION
     "This attribute specifies the number of Spanning Tree Explore frames 
      received on this bridge port. The Spanning Tree Explore frames are only 
      forwarded through bridge ports whose portStpState has a value of 
      forwarding. This counter will wrap to zero when it exceeds its 
      maximum."
::= { vrPpSrtBpSrStatsEntry 5 }

vrPpSrtBpSteOutFrames OBJECT-TYPE
   SYNTAX     Counter32 
   ACCESS     read-only
   STATUS     mandatory
   DESCRIPTION
     "This attribute specifies the number of Spanning Tree Frames transmitted 
      on this bridge port. This counter will wrap to zero when it exceeds its 
      maximum."
::= { vrPpSrtBpSrStatsEntry 6 }

vrPpSrtBpSegmentMismatchDiscards OBJECT-TYPE
   SYNTAX     Counter32 
   ACCESS     read-only
   STATUS     mandatory
   DESCRIPTION
     "This attribute specifies the number of All Routes Explore and Spanning 
      Tree Explore frames that were discarded due to an invalid next segment 
      value in the routing information field. This counter will wrap to zero 
      when it exceeds its maximum."
::= { vrPpSrtBpSrStatsEntry 7 }

vrPpSrtBpDupSegmentDiscards OBJECT-TYPE
   SYNTAX     Counter32 
   ACCESS     read-only
   STATUS     mandatory
   DESCRIPTION
     "This attribute specifies the number of frames discarded due to the 
      presence of a duplicate segment identifier in the route descriptor field 
      which may indicate a loop in the network topology. This counter will 
      wrap to zero when it exceeds its maximum."
::= { vrPpSrtBpSrStatsEntry 8 }

vrPpSrtBpHopCountExceededDiscards OBJECT-TYPE
   SYNTAX     Counter32 
   ACCESS     read-only
   STATUS     mandatory
   DESCRIPTION
     "This attribute specifies the number of All Routes Explore and Spanning 
      Tree Explore frames discarded by this bridge port due to a frame 
      exceeding the maximum size allowed for a route descriptor length. This 
      counter will wrap to zero when it exceeds its maximum."
::= { vrPpSrtBpSrStatsEntry 9 }

vrPpSrtBpDupLanIdOrTreeErrors OBJECT-TYPE
   SYNTAX     Counter32 
   ACCESS     read-only
   STATUS     mandatory
   DESCRIPTION
     "This attribute specifies the number frames received which contain 
      duplicate LAN IDs or Tree errors. This attribute is helpful in debugging 
      problems in networks which contain older IBM-SR bridges. This 
      counter will wrap to zero when it exceeds its maximum."
::= { vrPpSrtBpSrStatsEntry 10 }

vrPpSrtBpLanIdMismatches OBJECT-TYPE
   SYNTAX     Counter32 
   ACCESS     read-only
   STATUS     mandatory
   DESCRIPTION
     "This attributes counts the number of All Routes Explore or Spanning 
      Tree Explore frames that were discarded because the last LAN ID in the 
      routing information field did not equal the LAN ID. This counter will 
      wrap to zero when it exceeds its maximum."
::= { vrPpSrtBpSrStatsEntry 11 }

vrPpSrtBpStaticDiscards OBJECT-TYPE
   SYNTAX     Counter32 
   ACCESS     read-only
   STATUS     mandatory
   DESCRIPTION
     "This attribute is indicative of the number of explorer frames discarded 
      due to fact that the outbound SourceRouteBridge port was disabled or 
      deleted. This counter will wrap to zero when it exceeds its maximum."
::= { vrPpSrtBpSrStatsEntry 12 }

vrPpSrtBpDynamicDiscards OBJECT-TYPE
   SYNTAX     Counter32 
   ACCESS     read-only
   STATUS     mandatory
   DESCRIPTION
     "This attribute specifies the number of frames discarded due to receiving 
      a frame with a target LAN ID which did not match the internal LAN ID 
      of the receiving bridge port. This counter will wrap to zero when it 
      exceeds its maximum."
::= { vrPpSrtBpSrStatsEntry 13 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

vrPpSrtBpNs OBJECT IDENTIFIER ::= { vrPpSrtBp 2 }



vrPpSrtBpNsRowStatusTable OBJECT-TYPE
   SYNTAX     SEQUENCE OF VrPpSrtBpNsRowStatusEntry
   ACCESS     not-accessible
   STATUS     mandatory
   DESCRIPTION
     "This entry controls the addition and deletion of 
      vrPpSrtBpNs components."
::= { vrPpSrtBpNs 1 }

vrPpSrtBpNsRowStatusEntry OBJECT-TYPE
   SYNTAX     VrPpSrtBpNsRowStatusEntry
   ACCESS     not-accessible
   STATUS     mandatory
   DESCRIPTION
     "A single entry in the table represents a single 
      vrPpSrtBpNs component."
   INDEX {
      vrIndex,
      vrPpIndex,
      vrPpSrtBpIndex,
      vrPpSrtBpNsIndex }
::= { vrPpSrtBpNsRowStatusTable 1 }

VrPpSrtBpNsRowStatusEntry ::= SEQUENCE {
   vrPpSrtBpNsRowStatus
      RowStatus,
   vrPpSrtBpNsComponentName
      DisplayString,
   vrPpSrtBpNsStorageType
      StorageType,
   vrPpSrtBpNsIndex
      NonReplicated }

vrPpSrtBpNsRowStatus OBJECT-TYPE
   SYNTAX     RowStatus 
   ACCESS     read-write
   STATUS     mandatory
   DESCRIPTION
     "This variable is used as the basis for SNMP naming of
      vrPpSrtBpNs components.
      These components can be added and deleted."
::= { vrPpSrtBpNsRowStatusEntry 1 }

vrPpSrtBpNsComponentName OBJECT-TYPE
   SYNTAX     DisplayString 
   ACCESS     read-only
   STATUS     mandatory
   DESCRIPTION
     "This variable provides the component's string name for
      use with the ASCII Console Interface"
::= { vrPpSrtBpNsRowStatusEntry 2 }

vrPpSrtBpNsStorageType OBJECT-TYPE
   SYNTAX     StorageType 
   ACCESS     read-only
   STATUS     mandatory
   DESCRIPTION
     "This variable represents the storage type value for the
      vrPpSrtBpNs tables."
::= { vrPpSrtBpNsRowStatusEntry 4 }

vrPpSrtBpNsIndex OBJECT-TYPE
   SYNTAX     NonReplicated 
   ACCESS     not-accessible
   STATUS     mandatory
   DESCRIPTION
     "This variable represents the index for the vrPpSrtBpNs tables."
::= { vrPpSrtBpNsRowStatusEntry 10 }

vrPpSrtBpNsProvTable OBJECT-TYPE
   SYNTAX     SEQUENCE OF VrPpSrtBpNsProvEntry
   ACCESS     not-accessible
   STATUS     mandatory
   DESCRIPTION
     "This group houses all the port specific provisionable attributes 
      associated with Ns. These attributes influence the application of filters to 
      incoming and outgoing frames."
::= { vrPpSrtBpNs 10 }

vrPpSrtBpNsProvEntry OBJECT-TYPE
   SYNTAX     VrPpSrtBpNsProvEntry
   ACCESS     not-accessible
   STATUS     mandatory
   DESCRIPTION
     "An entry in the vrPpSrtBpNsProvTable."
   INDEX {
      vrIndex,
      vrPpIndex,
      vrPpSrtBpIndex,
      vrPpSrtBpNsIndex }
::= { vrPpSrtBpNsProvTable 1 }

VrPpSrtBpNsProvEntry ::= SEQUENCE {
   vrPpSrtBpNsIncomingFilter
      AsciiString,
   vrPpSrtBpNsOutgoingFilter
      AsciiString }

vrPpSrtBpNsIncomingFilter OBJECT-TYPE
   SYNTAX     AsciiString (SIZE (0..32))
   ACCESS     read-write
   STATUS     mandatory
   DESCRIPTION
     "This attribute specifies the name of the filter to be applied at the 
      incoming filter point."
::= { vrPpSrtBpNsProvEntry 2 }

vrPpSrtBpNsOutgoingFilter OBJECT-TYPE
   SYNTAX     AsciiString (SIZE (0..32))
   ACCESS     read-write
   STATUS     mandatory
   DESCRIPTION
     "This attribute specifies the name of the filter to be applied at the out 
      going filter point."
::= { vrPpSrtBpNsProvEntry 3 }


-- Vr/<string> Pp/<string> SrseBridgePort
-- This component represents the access point for source route frames 
-- destined for the source route encapsulating logic. Source route 
-- encapsulated bridging enables source routed frames to be tunneled 
-- through a transparent bridge/source route transparent cloud in order to 
-- reach a remote source route network. This mechanism provides for 
-- virtual connectivity of source route networks across non source route 
-- networks. The SrseBridgePort essentially provides an access point for 
-- source route frames into this virtual connectivity. Note that the 
-- SrseBridgePort and the TbseBridgePort must be provisioned in the 
-- same provisioning session. Enabling/disabling the SrseBridgePort 
-- automatically enables/disables the TbseBridgePort.

vrPpSrse OBJECT IDENTIFIER ::= { vrPp 10 }



vrPpSrseRowStatusTable OBJECT-TYPE
   SYNTAX     SEQUENCE OF VrPpSrseRowStatusEntry
   ACCESS     not-accessible
   STATUS     mandatory
   DESCRIPTION
     "This entry controls the addition and deletion of 
      vrPpSrse components."
::= { vrPpSrse 1 }

vrPpSrseRowStatusEntry OBJECT-TYPE
   SYNTAX     VrPpSrseRowStatusEntry
   ACCESS     not-accessible
   STATUS     mandatory
   DESCRIPTION
     "A single entry in the table represents a single 
      vrPpSrse component."
   INDEX {
      vrIndex,
      vrPpIndex,
      vrPpSrseIndex }
::= { vrPpSrseRowStatusTable 1 }

VrPpSrseRowStatusEntry ::= SEQUENCE {
   vrPpSrseRowStatus
      RowStatus,
   vrPpSrseComponentName
      DisplayString,
   vrPpSrseStorageType
      StorageType,
   vrPpSrseIndex
      NonReplicated }

vrPpSrseRowStatus OBJECT-TYPE
   SYNTAX     RowStatus 
   ACCESS     read-write
   STATUS     mandatory
   DESCRIPTION
     "This variable is used as the basis for SNMP naming of
      vrPpSrse components.
      These components can be added and deleted."
::= { vrPpSrseRowStatusEntry 1 }

vrPpSrseComponentName OBJECT-TYPE
   SYNTAX     DisplayString 
   ACCESS     read-only
   STATUS     mandatory
   DESCRIPTION
     "This variable provides the component's string name for
      use with the ASCII Console Interface"
::= { vrPpSrseRowStatusEntry 2 }

vrPpSrseStorageType OBJECT-TYPE
   SYNTAX     StorageType 
   ACCESS     read-only
   STATUS     mandatory
   DESCRIPTION
     "This variable represents the storage type value for the
      vrPpSrse tables."
::= { vrPpSrseRowStatusEntry 4 }

vrPpSrseIndex OBJECT-TYPE
   SYNTAX     NonReplicated 
   ACCESS     not-accessible
   STATUS     mandatory
   DESCRIPTION
     "This variable represents the index for the vrPpSrse tables."
::= { vrPpSrseRowStatusEntry 10 }

vrPpSrseProvTable OBJECT-TYPE
   SYNTAX     SEQUENCE OF VrPpSrseProvEntry
   ACCESS     not-accessible
   STATUS     mandatory
   DESCRIPTION
     "This group houses all the provisionable attributes that belong to the this 
      group. This group of attributes is applicable to all types of bridge ports 
      and represent the common factor between them. These attributes 
      influence the working of a bridge port."
::= { vrPpSrse 10 }

vrPpSrseProvEntry OBJECT-TYPE
   SYNTAX     VrPpSrseProvEntry
   ACCESS     not-accessible
   STATUS     mandatory
   DESCRIPTION
     "An entry in the vrPpSrseProvTable."
   INDEX {
      vrIndex,
      vrPpIndex,
      vrPpSrseIndex }
::= { vrPpSrseProvTable 1 }

VrPpSrseProvEntry ::= SEQUENCE {
   vrPpSrseTranslateIpx
      INTEGER,
   vrPpSrseFragmentIp
      INTEGER,
   vrPpSrseServiceClass
      INTEGER,
   vrPpSrseConvertArpMacAddress
      INTEGER,
   vrPpSrsePortNum
      Unsigned32,
   vrPpSrseOutboundFrameMediaType
      INTEGER }

vrPpSrseTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { vrPpSrseProvEntry 1 }

vrPpSrseFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { vrPpSrseProvEntry 2 }

vrPpSrseServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { vrPpSrseProvEntry 3 }

vrPpSrseConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { vrPpSrseProvEntry 4 }

vrPpSrsePortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { vrPpSrseProvEntry 5 }

vrPpSrseOutboundFrameMediaType OBJECT-TYPE
   SYNTAX     INTEGER  {
                 unaltered(1),
                 ethernetConv(2) }
   ACCESS     read-write
   STATUS     mandatory
   DESCRIPTION
     "This attribute specifies the media type the frame must be in before it is 
      to be forwarded over the outbound supported WAN Bridge Protocol 
      Port. The attribute only applies to outbound Bridge Protocol Port.
      
      For supported bridge ports, if the attribute value remains set to the 
      default value of unaltered then there will be no frame conversion. When 
      the value is set to the value ethernetConv then all frames being 
      forwarded out the outbound WAN Port will be converted to ethernet 
      before forwarding takes place. The only outbound WAN medias that 
      currently support conversion are: FR (Frame Relay) and VNS. All other 
      medias will fail the Bridge Port semantic check when attempts are made 
      to alter this attribute. 
      
      The following is an example of what the user may be able to do. Frames 
      originating from a Token Ring are to be flooded out onto another Token 
      Ring and a Frame Relay Port. The token ring Outbound port performs 
      no translation, yet the FR Port has the outboundFrameMediaType 
      attribute set to ethernetConv which results in the frame being translated 
      into Ethernet format from Token Ring format before Frame Relay does 
      its encapsulation and transmits over the FR port."
   DEFVAL     { unaltered }
::= { vrPpSrseProvEntry 6 }

vrPpSrseStpProvTable OBJECT-TYPE
   SYNTAX     SEQUENCE OF VrPpSrseStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { vrPpSrse 12 }

vrPpSrseStpProvEntry OBJECT-TYPE
   SYNTAX     VrPpSrseStpProvEntry
   ACCESS     not-accessible
   STATUS     mandatory
   DESCRIPTION
     "An entry in the vrPpSrseStpProvTable."
   INDEX {
      vrIndex,
      vrPpIndex,
      vrPpSrseIndex }
::= { vrPpSrseStpProvTable 1 }

VrPpSrseStpProvEntry ::= SEQUENCE {
   vrPpSrseAdminStatus
      INTEGER,
   vrPpSrsePortStateStpControl
      INTEGER,
   vrPpSrseStpTypeProv
      INTEGER,
   vrPpSrsePortPriority
      Unsigned32,
   vrPpSrsePathCost
      Unsigned32,
   vrPpSrsePathCostMethod
      INTEGER }

vrPpSrseAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { vrPpSrseStpProvEntry 1 }

vrPpSrsePortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { vrPpSrseStpProvEntry 2 }

vrPpSrseStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { vrPpSrseStpProvEntry 3 }

vrPpSrsePortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { vrPpSrseStpProvEntry 4 }

vrPpSrsePathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { vrPpSrseStpProvEntry 5 }

vrPpSrsePathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { vrPpSrseStpProvEntry 6 }

vrPpSrseDIProvTable OBJECT-TYPE
   SYNTAX     SEQUENCE OF VrPpSrseDIProvEntry
   ACCESS     not-accessible
   STATUS     mandatory
   DESCRIPTION
     "This group houses all the provisionable, domain specific attributes for a 
      non-encapsulating bridge port."
::= { vrPpSrse 13 }

vrPpSrseDIProvEntry OBJECT-TYPE
   SYNTAX     VrPpSrseDIProvEntry
   ACCESS     not-accessible
   STATUS     mandatory
   DESCRIPTION
     "An entry in the vrPpSrseDIProvTable."
   INDEX {
      vrIndex,
      vrPpIndex,
      vrPpSrseIndex }
::= { vrPpSrseDIProvTable 1 }

VrPpSrseDIProvEntry ::= SEQUENCE {
   vrPpSrseDomainNum
      Unsigned32,
   vrPpSrsePreserveDomain
      INTEGER }

vrPpSrseDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { vrPpSrseDIProvEntry 1 }

vrPpSrsePreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { vrPpSrseDIProvEntry 2 }

vrPpSrseStateTable OBJECT-TYPE
   SYNTAX     SEQUENCE OF VrPpSrseStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpSrse 14 }

vrPpSrseStateEntry OBJECT-TYPE
   SYNTAX     VrPpSrseStateEntry
   ACCESS     not-accessible
   STATUS     mandatory
   DESCRIPTION
     "An entry in the vrPpSrseStateTable."
   INDEX {
      vrIndex,
      vrPpIndex,
      vrPpSrseIndex }
::= { vrPpSrseStateTable 1 }

VrPpSrseStateEntry ::= SEQUENCE {
   vrPpSrseAdminState
      INTEGER,
   vrPpSrseOperationalState
      INTEGER,
   vrPpSrseUsageState
      INTEGER }

vrPpSrseAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpSrseStateEntry 1 }

vrPpSrseOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpSrseStateEntry 2 }

vrPpSrseUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpSrseStateEntry 3 }

vrPpSrseOperStatusTable OBJECT-TYPE
   SYNTAX     SEQUENCE OF VrPpSrseOperStatusEntry
   ACCESS     not-accessible
   STATUS     mandatory
   DESCRIPTION
     "This group includes the Operational Status attribute. This attribute 
      defines the current operational state of this component."
::= { vrPpSrse 15 }

vrPpSrseOperStatusEntry OBJECT-TYPE
   SYNTAX     VrPpSrseOperStatusEntry
   ACCESS     not-accessible
   STATUS     mandatory
   DESCRIPTION
     "An entry in the vrPpSrseOperStatusTable."
   INDEX {
      vrIndex,
      vrPpIndex,
      vrPpSrseIndex }
::= { vrPpSrseOperStatusTable 1 }

VrPpSrseOperStatusEntry ::= SEQUENCE {
   vrPpSrseSnmpOperStatus
      INTEGER }

vrPpSrseSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpSrseOperStatusEntry 1 }

vrPpSrseOperTable OBJECT-TYPE
   SYNTAX     SEQUENCE OF VrPpSrseOperEntry
   ACCESS     not-accessible
   STATUS     mandatory
   DESCRIPTION
     "This group houses all the operational attributes belonging to the base 
      group. The base group of attributes is applicable to all types of bridge 
      ports and represent the common factor between them. These attributes in 
      part, reflect the state of a bridge port."
::= { vrPpSrse 16 }

vrPpSrseOperEntry OBJECT-TYPE
   SYNTAX     VrPpSrseOperEntry
   ACCESS     not-accessible
   STATUS     mandatory
   DESCRIPTION
     "An entry in the vrPpSrseOperTable."
   INDEX {
      vrIndex,
      vrPpIndex,
      vrPpSrseIndex }
::= { vrPpSrseOperTable 1 }

VrPpSrseOperEntry ::= SEQUENCE {
   vrPpSrsePortName
      AsciiString,
   vrPpSrseUpTime
      Unsigned32,
   vrPpSrseDownTime
      Unsigned32,
   vrPpSrseBridgingMode
      INTEGER,
   vrPpSrseBridgePortConfig
      INTEGER,
   vrPpSrseBridgePortType
      INTEGER,
   vrPpSrseIfIndex
      InterfaceIndex,
   vrPpSrseDelayExceededDiscards
      Counter32,
   vrPpSrseMtuExceededDiscards
      Counter32 }

vrPpSrsePortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { vrPpSrseOperEntry 1 }

vrPpSrseUpTime OBJECT-TYPE
   SYNTAX     Unsigned32 (0..4294967295)
   ACCESS     read-only
   STATUS     mandatory
   DESCRIPTION
     "This attribute specifies the accumulated up time of this bridge port since 
      the last reset occurred."
   DEFVAL     { 0 }
::= { vrPpSrseOperEntry 3 }

vrPpSrseDownTime OBJECT-TYPE
   SYNTAX     Unsigned32 (0..4294967295)
   ACCESS     read-only
   STATUS     mandatory
   DESCRIPTION
     "This attribute specifies the accumulated down time of this bridge port 
      since the last reset occurred."
   DEFVAL     { 0 }
::= { vrPpSrseOperEntry 4 }

vrPpSrseBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { vrPpSrseOperEntry 5 }

vrPpSrseBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { vrPpSrseOperEntry 6 }

vrPpSrseBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { vrPpSrseOperEntry 7 }

vrPpSrseIfIndex OBJECT-TYPE
   SYNTAX     InterfaceIndex (1..65535)
   ACCESS     read-only
   STATUS     mandatory
   DESCRIPTION
     "This attribute specifies the index into the Interface Table where in 
      information about the media interface corresponding to the bridge port is 
      maintained."
::= { vrPpSrseOperEntry 8 }

vrPpSrseDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { vrPpSrseOperEntry 10 }

vrPpSrseMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { vrPpSrseOperEntry 11 }

vrPpSrseStpOperTable OBJECT-TYPE
   SYNTAX     SEQUENCE OF VrPpSrseStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { vrPpSrse 18 }

vrPpSrseStpOperEntry OBJECT-TYPE
   SYNTAX     VrPpSrseStpOperEntry
   ACCESS     not-accessible
   STATUS     mandatory
   DESCRIPTION
     "An entry in the vrPpSrseStpOperTable."
   INDEX {
      vrIndex,
      vrPpIndex,
      vrPpSrseIndex }
::= { vrPpSrseStpOperTable 1 }

VrPpSrseStpOperEntry ::= SEQUENCE {
   vrPpSrseStpPortState
      INTEGER,
   vrPpSrseStpTypeOper
      INTEGER,
   vrPpSrseDesignatedCost
      Unsigned32,
   vrPpSrsePathCostOper
      Unsigned32,
   vrPpSrseDesignatedBridge
      BridgeId,
   vrPpSrseDesignatedPort
      Hex,
   vrPpSrseForwardTransitions
      Counter32,
   vrPpSrseBlockingDiscards
      Counter32,
   vrPpSrseDesignatedRoot
      BridgeId }

vrPpSrseStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { vrPpSrseStpOperEntry 2 }

vrPpSrseStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { vrPpSrseStpOperEntry 3 }

vrPpSrseDesignatedCost OBJECT-TYPE
   SYNTAX     Unsigned32 (0..4294967295)
   ACCESS     read-only
   STATUS     mandatory
   DESCRIPTION
     "This attribute specifies the path cost of the designated port of the lan 
      segment connected to the port."
::= { vrPpSrseStpOperEntry 4 }

vrPpSrsePathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { vrPpSrseStpOperEntry 5 }

vrPpSrseDesignatedBridge OBJECT-TYPE
   SYNTAX     BridgeId (SIZE (8))
   ACCESS     read-only
   STATUS     mandatory
   DESCRIPTION
     "This attribute specifies the identifier of the bridge that this port considers 
      to be the designated bridge."
::= { vrPpSrseStpOperEntry 6 }

vrPpSrseDesignatedPort OBJECT-TYPE
   SYNTAX     Hex (0..65535)
   ACCESS     read-only
   STATUS     mandatory
   DESCRIPTION
     "This attribute specifies the port identifier of the port on the designated 
      bridge, attached to the same lan as this port is attached to."
::= { vrPpSrseStpOperEntry 7 }

vrPpSrseForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { vrPpSrseStpOperEntry 8 }

vrPpSrseBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { vrPpSrseStpOperEntry 9 }

vrPpSrseDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { vrPpSrseStpOperEntry 10 }

vrPpSrseStatsTable OBJECT-TYPE
   SYNTAX     SEQUENCE OF VrPpSrseStatsEntry
   ACCESS     not-accessible
   STATUS     mandatory
   DESCRIPTION
     "This group houses all the statistical attributes applicable to all types of 
      bridge ports and represents the common factor between them. These 
      attributes in part reflect the state of the bridge port."
::= { vrPpSrse 19 }

vrPpSrseStatsEntry OBJECT-TYPE
   SYNTAX     VrPpSrseStatsEntry
   ACCESS     not-accessible
   STATUS     mandatory
   DESCRIPTION
     "An entry in the vrPpSrseStatsTable."
   INDEX {
      vrIndex,
      vrPpIndex,
      vrPpSrseIndex }
::= { vrPpSrseStatsTable 1 }

VrPpSrseStatsEntry ::= SEQUENCE {
   vrPpSrseBadAbstractDiscards
      Counter32,
   vrPpSrseTinygramFramesIn
      Counter32,
   vrPpSrseTinygramFramesOut
      Counter32,
   vrPpSrseInFilterDiscards
      Counter32,
   vrPpSrseOutFilterDiscards
      Counter32 }

vrPpSrseBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { vrPpSrseStatsEntry 1 }

vrPpSrseTinygramFramesIn OBJECT-TYPE
   SYNTAX     Counter32 
   ACCESS     read-only
   STATUS     mandatory
   DESCRIPTION
     "This attribute is indicative of the number of frames received on this 
      bridge port that used the tinygram compression scheme."
::= { vrPpSrseStatsEntry 2 }

vrPpSrseTinygramFramesOut OBJECT-TYPE
   SYNTAX     Counter32 
   ACCESS     read-only
   STATUS     mandatory
   DESCRIPTION
     "This attribute is indicative of the number of frames transmitted out this 
      bridge port that used the tinygram compression scheme."
::= { vrPpSrseStatsEntry 3 }

vrPpSrseInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { vrPpSrseStatsEntry 4 }

vrPpSrseOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { vrPpSrseStatsEntry 5 }

vrPpSrseSrProvTable OBJECT-TYPE
   SYNTAX     SEQUENCE OF VrPpSrseSrProvEntry
   ACCESS     not-accessible
   STATUS     mandatory
   DESCRIPTION
     "This group contains all port specific, provisionable attributes associated 
      with SourceRouteBridge ports."
::= { vrPpSrse 20 }

vrPpSrseSrProvEntry OBJECT-TYPE
   SYNTAX     VrPpSrseSrProvEntry
   ACCESS     not-accessible
   STATUS     mandatory
   DESCRIPTION
     "An entry in the vrPpSrseSrProvTable."
   INDEX {
      vrIndex,
      vrPpIndex,
      vrPpSrseIndex }
::= { vrPpSrseSrProvTable 1 }

VrPpSrseSrProvEntry ::= SEQUENCE {
   vrPpSrseHopCount
      Unsigned32,
   vrPpSrseExploreFrameTreatment
      INTEGER,
   vrPpSrseLanId
      Unsigned32,
   vrPpSrseInternalLanId
      Unsigned32,
   vrPpSrseBridgeNum
      Unsigned32,
   vrPpSrseLargestFrame
      Unsigned32,
   vrPpSrseSteSpanMode
      INTEGER,
   vrPpSrseAreRdLimit
      Unsigned32,
   vrPpSrseSteRdLimit
      Unsigned32 }

vrPpSrseHopCount OBJECT-TYPE
   SYNTAX     Unsigned32 (1..7)
   ACCESS     read-write
   STATUS     mandatory
   DESCRIPTION
     "This attribute specifies the maximum number of hops allowed in 
      Spanning Tree Explore and All Routes Explore frames. This value is one 
      less than the maximum number of route descriptors allowed in a source 
      route frame"
   DEFVAL     { 7 }
::= { vrPpSrseSrProvEntry 1 }

vrPpSrseExploreFrameTreatment OBJECT-TYPE
   SYNTAX     INTEGER  {
                 encap(0),
                 xlate(1) }
   ACCESS     read-write
   STATUS     mandatory
   DESCRIPTION
     "This attribute specifies whether or not explore frames received from 
      SourceRouteBridge ports will be sent to the SRTB-8209 translation or 
      the encapsulated SourceRouteBridge logic. This option is used only 
      when both the TbsrBridgePort and the SrtbBridgePort are provisioned 
      and enabled. 
      A value of Xlate implies that the explore frames will be sent to the Srtb 
      translation logic and a value of Encap implies that the frames will be 
      sent to the Encapsulated source route bridging logic."
   DEFVAL     { encap }
::= { vrPpSrseSrProvEntry 2 }

vrPpSrseLanId OBJECT-TYPE
   SYNTAX     Unsigned32 (0..4095)
   ACCESS     read-write
   STATUS     mandatory
   DESCRIPTION
     "This attribute specifies the identifier for the physical LAN that this port 
      is attached. All SourceRouteBridge ports are assigned to a physical LAN 
      and a logical internal LAN. 
      Current source route bridge implementations limit the lanId to a value in 
      the range 0 to 4095."
   DEFVAL     { 0 }
::= { vrPpSrseSrProvEntry 3 }

vrPpSrseInternalLanId OBJECT-TYPE
   SYNTAX     Unsigned32 (0..4095)
   ACCESS     read-write
   STATUS     mandatory
   DESCRIPTION
     "This attribute specifies the identifier for the internal logical LAN this 
      port is attached. All SourceRouteBridge ports are assigned to a physical 
      LAN and a logical internal LAN. 
      Current source route bridge implementations limit the lanId to a value in 
      the range 0 to 4095."
   DEFVAL     { 0 }
::= { vrPpSrseSrProvEntry 4 }

vrPpSrseBridgeNum OBJECT-TYPE
   SYNTAX     Unsigned32 (0..15)
   ACCESS     read-write
   STATUS     mandatory
   DESCRIPTION
     "This attribute specifies the value that is used to identify this bridge when 
      more than one bridge is used to span the same two LAN segments."
   DEFVAL     { 7 }
::= { vrPpSrseSrProvEntry 5 }

vrPpSrseLargestFrame OBJECT-TYPE
   SYNTAX     Unsigned32 (516 | 1470 | 2052 | 4399 | 8130 | 11407 | 17749)
   ACCESS     read-write
   STATUS     mandatory
   DESCRIPTION
     "This attribute specifies the maximum frame size (LLC and above) in 
      octets, allowed by this SourceRouteBridge port. This field is used to 
      determine whether a modification of the largest frame field of the 
      routing control field of the routing information field is warranted."
::= { vrPpSrseSrProvEntry 6 }

vrPpSrseSteSpanMode OBJECT-TYPE
   SYNTAX     INTEGER  {
                 autoSpan(1),
                 disabled(2),
                 forced(3) }
   ACCESS     read-write
   STATUS     mandatory
   DESCRIPTION
     "This attribute determines how this bridge port will react when presented 
      with a Spanning Tree Explore frame.
      If disabled, the Spanning Tree Explore frame is discarded regardless of 
      the value of stpPortState. 
      If the value of this attribute is forced, the Spanning Tree Explore frame 
      is forwarded regardless of the value of stpPortState. 
      autoSpan uses the stpPortState value to decide whether or not Spanning 
      Tree Explore frames should be forwarded out this bridge port. If the port 
      is in the forwarding state, the frame is received and transmitted 
      otherwise the frame is discarded."
   DEFVAL     { autoSpan }
::= { vrPpSrseSrProvEntry 7 }

vrPpSrseAreRdLimit OBJECT-TYPE
   SYNTAX     Unsigned32 (0..8)
   ACCESS     read-write
   STATUS     mandatory
   DESCRIPTION
     "This attribute specifies the number of route descriptors allowed in an All 
      Routes Explore frame received on a SourceRouteBridgePort or 
      SourceRouteTransparentBridgePort. Current source route bridge 
      implementations limit the areRdLimit to a value in the range 0 to 8."
   DEFVAL     { 8 }
::= { vrPpSrseSrProvEntry 8 }

vrPpSrseSteRdLimit OBJECT-TYPE
   SYNTAX     Unsigned32 (0..8)
   ACCESS     read-write
   STATUS     mandatory
   DESCRIPTION
     "This attribute specifies the number of route descriptors allowed in a 
      Spanning Tree Explore frame received on a SourceRouteBridgePort or 
      SourceRouteTransparentBridgePort. Current source route bridge 
      implementations limit the steRdLimit to a value in the range 0 to 8."
   DEFVAL     { 8 }
::= { vrPpSrseSrProvEntry 9 }

vrPpSrseSrStatsTable OBJECT-TYPE
   SYNTAX     SEQUENCE OF VrPpSrseSrStatsEntry
   ACCESS     not-accessible
   STATUS     mandatory
   DESCRIPTION
     "This group contains all port specific statistical attributes associated with 
      SourceRouteBridge ports."
::= { vrPpSrse 21 }

vrPpSrseSrStatsEntry OBJECT-TYPE
   SYNTAX     VrPpSrseSrStatsEntry
   ACCESS     not-accessible
   STATUS     mandatory
   DESCRIPTION
     "An entry in the vrPpSrseSrStatsTable."
   INDEX {
      vrIndex,
      vrPpIndex,
      vrPpSrseIndex }
::= { vrPpSrseSrStatsTable 1 }

VrPpSrseSrStatsEntry ::= SEQUENCE {
   vrPpSrseSpecInFrames
      Counter32,
   vrPpSrseSpecOutFrames
      Counter32,
   vrPpSrseApeInFrames
      Counter32,
   vrPpSrseApeOutFrames
      Counter32,
   vrPpSrseSteInFrames
      Counter32,
   vrPpSrseSteOutFrames
      Counter32,
   vrPpSrseSegmentMismatchDiscards
      Counter32,
   vrPpSrseDupSegmentDiscards
      Counter32,
   vrPpSrseHopCountExceededDiscards
      Counter32,
   vrPpSrseDupLanIdOrTreeErrors
      Counter32,
   vrPpSrseLanIdMismatches
      Counter32,
   vrPpSrseStaticDiscards
      Counter32,
   vrPpSrseDynamicDiscards
      Counter32 }

vrPpSrseSpecInFrames OBJECT-TYPE
   SYNTAX     Counter32 
   ACCESS     read-only
   STATUS     mandatory
   DESCRIPTION
     "This attribute specifies the number of specifically routed frames that 
      were received by this bridge port. A specifically routed frame has a route 
      descriptor, constructed by the originating host which details an explicit 
      route to the destination host. This counter will wrap to zero when it 
      exceeds its maximum."
::= { vrPpSrseSrStatsEntry 1 }

vrPpSrseSpecOutFrames OBJECT-TYPE
   SYNTAX     Counter32 
   ACCESS     read-only
   STATUS     mandatory
   DESCRIPTION
     "This attribute specifies the number of specifically routed frames that 
      were transmitted from this bridge port. This counter will wrap to zero 
      when it exceeds its maximum."
::= { vrPpSrseSrStatsEntry 2 }

vrPpSrseApeInFrames OBJECT-TYPE
   SYNTAX     Counter32 
   ACCESS     read-only
   STATUS     mandatory
   DESCRIPTION
     "This attribute specifies the number of All Path Explore frames received 
      on this bridge port. The All Path Explore frames are forwarded to all 
      SourceRouteBridge ports assigned to this bridge regardless of the port's 
      portStpStates. This counter will wrap to zero when it exceeds its 
      maximum."
::= { vrPpSrseSrStatsEntry 3 }

vrPpSrseApeOutFrames OBJECT-TYPE
   SYNTAX     Counter32 
   ACCESS     read-only
   STATUS     mandatory
   DESCRIPTION
     "This attribute specifies the number of All Path Explore frames 
      transmitted on this bridge port. The All Path Explore frames are 
      forwarded to all SourceRouteBridge ports assigned to this bridge 
      regardless of the port's portStpState state. This counter will wrap to zero 
      when it exceeds its maximum."
::= { vrPpSrseSrStatsEntry 4 }

vrPpSrseSteInFrames OBJECT-TYPE
   SYNTAX     Counter32 
   ACCESS     read-only
   STATUS     mandatory
   DESCRIPTION
     "This attribute specifies the number of Spanning Tree Explore frames 
      received on this bridge port. The Spanning Tree Explore frames are only 
      forwarded through bridge ports whose portStpState has a value of 
      forwarding. This counter will wrap to zero when it exceeds its 
      maximum."
::= { vrPpSrseSrStatsEntry 5 }

vrPpSrseSteOutFrames OBJECT-TYPE
   SYNTAX     Counter32 
   ACCESS     read-only
   STATUS     mandatory
   DESCRIPTION
     "This attribute specifies the number of Spanning Tree Frames transmitted 
      on this bridge port. This counter will wrap to zero when it exceeds its 
      maximum."
::= { vrPpSrseSrStatsEntry 6 }

vrPpSrseSegmentMismatchDiscards OBJECT-TYPE
   SYNTAX     Counter32 
   ACCESS     read-only
   STATUS     mandatory
   DESCRIPTION
     "This attribute specifies the number of All Routes Explore and Spanning 
      Tree Explore frames that were discarded due to an invalid next segment 
      value in the routing information field. This counter will wrap to zero 
      when it exceeds its maximum."
::= { vrPpSrseSrStatsEntry 7 }

vrPpSrseDupSegmentDiscards OBJECT-TYPE
   SYNTAX     Counter32 
   ACCESS     read-only
   STATUS     mandatory
   DESCRIPTION
     "This attribute specifies the number of frames discarded due to the 
      presence of a duplicate segment identifier in the route descriptor field 
      which may indicate a loop in the network topology. This counter will 
      wrap to zero when it exceeds its maximum."
::= { vrPpSrseSrStatsEntry 8 }

vrPpSrseHopCountExceededDiscards OBJECT-TYPE
   SYNTAX     Counter32 
   ACCESS     read-only
   STATUS     mandatory
   DESCRIPTION
     "This attribute specifies the number of All Routes Explore and Spanning 
      Tree Explore frames discarded by this bridge port due to a frame 
      exceeding the maximum size allowed for a route descriptor length. This 
      counter will wrap to zero when it exceeds its maximum."
::= { vrPpSrseSrStatsEntry 9 }

vrPpSrseDupLanIdOrTreeErrors OBJECT-TYPE
   SYNTAX     Counter32 
   ACCESS     read-only
   STATUS     mandatory
   DESCRIPTION
     "This attribute specifies the number frames received which contain 
      duplicate LAN IDs or Tree errors. This attribute is helpful in debugging 
      problems in networks which contain older IBM-SR bridges. This 
      counter will wrap to zero when it exceeds its maximum."
::= { vrPpSrseSrStatsEntry 10 }

vrPpSrseLanIdMismatches OBJECT-TYPE
   SYNTAX     Counter32 
   ACCESS     read-only
   STATUS     mandatory
   DESCRIPTION
     "This attributes counts the number of All Routes Explore or Spanning 
      Tree Explore frames that were discarded because the last LAN ID in the 
      routing information field did not equal the LAN ID. This counter will 
      wrap to zero when it exceeds its maximum."
::= { vrPpSrseSrStatsEntry 11 }

vrPpSrseStaticDiscards OBJECT-TYPE
   SYNTAX     Counter32 
   ACCESS     read-only
   STATUS     mandatory
   DESCRIPTION
     "This attribute is indicative of the number of explorer frames discarded 
      due to fact that the outbound SourceRouteBridge port was disabled or 
      deleted. This counter will wrap to zero when it exceeds its maximum."
::= { vrPpSrseSrStatsEntry 12 }

vrPpSrseDynamicDiscards OBJECT-TYPE
   SYNTAX     Counter32 
   ACCESS     read-only
   STATUS     mandatory
   DESCRIPTION
     "This attribute specifies the number of frames discarded due to receiving 
      a frame with a target LAN ID which did not match the internal LAN ID 
      of the receiving bridge port. This counter will wrap to zero when it 
      exceeds its maximum."
::= { vrPpSrseSrStatsEntry 13 }


-- Vr/<string> Pp/<string> TbseBridgePort
-- This component represents the access point or TB/SRT frames carrying 
-- a payload of a SR frame, into the SR encapsulation logic. After the 
-- encapsulated frame is stripped and the SR frame extracted, the extracted 
-- frame is handed down to regular SR bridging logic for further 
-- forwarding. The TbseBridgePort is the end point in the remote bridge 
-- unit with a MAC address, the TB/SRT encapsulated SR frames are 
-- directed to. This MAC address of a TbseBridgePort in the remote bridge 
-- unit, is learned and stored in the Lan Id Table (peerMACAddress) of the 
-- local bridge unit. Please note that the SrseBridgePort and the 
-- TbseBridgePort are always to be provisioned together. Enabling/
-- disabling the SrseBridgePort automatically enables/disables the 
-- TbseBridgePort.

vrPpTbse OBJECT IDENTIFIER ::= { vrPp 11 }



vrPpTbseRowStatusTable OBJECT-TYPE
   SYNTAX     SEQUENCE OF VrPpTbseRowStatusEntry
   ACCESS     not-accessible
   STATUS     mandatory
   DESCRIPTION
     "This entry controls the addition and deletion of 
      vrPpTbse components."
::= { vrPpTbse 1 }

vrPpTbseRowStatusEntry OBJECT-TYPE
   SYNTAX     VrPpTbseRowStatusEntry
   ACCESS     not-accessible
   STATUS     mandatory
   DESCRIPTION
     "A single entry in the table represents a single 
      vrPpTbse component."
   INDEX {
      vrIndex,
      vrPpIndex,
      vrPpTbseIndex }
::= { vrPpTbseRowStatusTable 1 }

VrPpTbseRowStatusEntry ::= SEQUENCE {
   vrPpTbseRowStatus
      RowStatus,
   vrPpTbseComponentName
      DisplayString,
   vrPpTbseStorageType
      StorageType,
   vrPpTbseIndex
      NonReplicated }

vrPpTbseRowStatus OBJECT-TYPE
   SYNTAX     RowStatus 
   ACCESS     read-write
   STATUS     mandatory
   DESCRIPTION
     "This variable is used as the basis for SNMP naming of
      vrPpTbse components.
      These components can be added and deleted."
::= { vrPpTbseRowStatusEntry 1 }

vrPpTbseComponentName OBJECT-TYPE
   SYNTAX     DisplayString 
   ACCESS     read-only
   STATUS     mandatory
   DESCRIPTION
     "This variable provides the component's string name for
      use with the ASCII Console Interface"
::= { vrPpTbseRowStatusEntry 2 }

vrPpTbseStorageType OBJECT-TYPE
   SYNTAX     StorageType 
   ACCESS     read-only
   STATUS     mandatory
   DESCRIPTION
     "This variable represents the storage type value for the
      vrPpTbse tables."
::= { vrPpTbseRowStatusEntry 4 }

vrPpTbseIndex OBJECT-TYPE
   SYNTAX     NonReplicated 
   ACCESS     not-accessible
   STATUS     mandatory
   DESCRIPTION
     "This variable represents the index for the vrPpTbse tables."
::= { vrPpTbseRowStatusEntry 10 }

vrPpTbseProvTable OBJECT-TYPE
   SYNTAX     SEQUENCE OF VrPpTbseProvEntry
   ACCESS     not-accessible
   STATUS     mandatory
   DESCRIPTION
     "This group houses all the provisionable attributes that belong to the this 
      group. This group of attributes is applicable to all types of bridge ports 
      and represent the common factor between them. These attributes 
      influence the working of a bridge port."
::= { vrPpTbse 10 }

vrPpTbseProvEntry OBJECT-TYPE
   SYNTAX     VrPpTbseProvEntry
   ACCESS     not-accessible
   STATUS     mandatory
   DESCRIPTION
     "An entry in the vrPpTbseProvTable."
   INDEX {
      vrIndex,
      vrPpIndex,
      vrPpTbseIndex }
::= { vrPpTbseProvTable 1 }

VrPpTbseProvEntry ::= SEQUENCE {
   vrPpTbseTranslateIpx
      INTEGER,
   vrPpTbseFragmentIp
      INTEGER,
   vrPpTbseServiceClass
      INTEGER,
   vrPpTbseConvertArpMacAddress
      INTEGER,
   vrPpTbsePortNum
      Unsigned32,
   vrPpTbseOutboundFrameMediaType
      INTEGER }

vrPpTbseTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { vrPpTbseProvEntry 1 }

vrPpTbseFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { vrPpTbseProvEntry 2 }

vrPpTbseServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { vrPpTbseProvEntry 3 }

vrPpTbseConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { vrPpTbseProvEntry 4 }

vrPpTbsePortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { vrPpTbseProvEntry 5 }

vrPpTbseOutboundFrameMediaType OBJECT-TYPE
   SYNTAX     INTEGER  {
                 unaltered(1),
                 ethernetConv(2) }
   ACCESS     read-write
   STATUS     mandatory
   DESCRIPTION
     "This attribute specifies the media type the frame must be in before it is 
      to be forwarded over the outbound supported WAN Bridge Protocol 
      Port. The attribute only applies to outbound Bridge Protocol Port.
      
      For supported bridge ports, if the attribute value remains set to the 
      default value of unaltered then there will be no frame conversion. When 
      the value is set to the value ethernetConv then all frames being 
      forwarded out the outbound WAN Port will be converted to ethernet 
      before forwarding takes place. The only outbound WAN medias that 
      currently support conversion are: FR (Frame Relay) and VNS. All other 
      medias will fail the Bridge Port semantic check when attempts are made 
      to alter this attribute. 
      
      The following is an example of what the user may be able to do. Frames 
      originating from a Token Ring are to be flooded out onto another Token 
      Ring and a Frame Relay Port. The token ring Outbound port performs 
      no translation, yet the FR Port has the outboundFrameMediaType 
      attribute set to ethernetConv which results in the frame being translated 
      into Ethernet format from Token Ring format before Frame Relay does 
      its encapsulation and transmits over the FR port."
   DEFVAL     { unaltered }
::= { vrPpTbseProvEntry 6 }

vrPpTbseTbProvTable OBJECT-TYPE
   SYNTAX     SEQUENCE OF VrPpTbseTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { vrPpTbse 11 }

vrPpTbseTbProvEntry OBJECT-TYPE
   SYNTAX     VrPpTbseTbProvEntry
   ACCESS     not-accessible
   STATUS     mandatory
   DESCRIPTION
     "An entry in the vrPpTbseTbProvTable."
   INDEX {
      vrIndex,
      vrPpIndex,
      vrPpTbseIndex }
::= { vrPpTbseTbProvTable 1 }

VrPpTbseTbProvEntry ::= SEQUENCE {
   vrPpTbseSecureOption
      INTEGER }

vrPpTbseSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { vrPpTbseTbProvEntry 1 }

vrPpTbseStpProvTable OBJECT-TYPE
   SYNTAX     SEQUENCE OF VrPpTbseStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { vrPpTbse 12 }

vrPpTbseStpProvEntry OBJECT-TYPE
   SYNTAX     VrPpTbseStpProvEntry
   ACCESS     not-accessible
   STATUS     mandatory
   DESCRIPTION
     "An entry in the vrPpTbseStpProvTable."
   INDEX {
      vrIndex,
      vrPpIndex,
      vrPpTbseIndex }
::= { vrPpTbseStpProvTable 1 }

VrPpTbseStpProvEntry ::= SEQUENCE {
   vrPpTbseAdminStatus
      INTEGER,
   vrPpTbsePortStateStpControl
      INTEGER,
   vrPpTbseStpTypeProv
      INTEGER,
   vrPpTbsePortPriority
      Unsigned32,
   vrPpTbsePathCost
      Unsigned32,
   vrPpTbsePathCostMethod
      INTEGER }

vrPpTbseAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { vrPpTbseStpProvEntry 1 }

vrPpTbsePortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { vrPpTbseStpProvEntry 2 }

vrPpTbseStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { vrPpTbseStpProvEntry 3 }

vrPpTbsePortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { vrPpTbseStpProvEntry 4 }

vrPpTbsePathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { vrPpTbseStpProvEntry 5 }

vrPpTbsePathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { vrPpTbseStpProvEntry 6 }

vrPpTbseDIProvTable OBJECT-TYPE
   SYNTAX     SEQUENCE OF VrPpTbseDIProvEntry
   ACCESS     not-accessible
   STATUS     mandatory
   DESCRIPTION
     "This group houses all the provisionable, domain specific attributes for a 
      non-encapsulating bridge port."
::= { vrPpTbse 13 }

vrPpTbseDIProvEntry OBJECT-TYPE
   SYNTAX     VrPpTbseDIProvEntry
   ACCESS     not-accessible
   STATUS     mandatory
   DESCRIPTION
     "An entry in the vrPpTbseDIProvTable."
   INDEX {
      vrIndex,
      vrPpIndex,
      vrPpTbseIndex }
::= { vrPpTbseDIProvTable 1 }

VrPpTbseDIProvEntry ::= SEQUENCE {
   vrPpTbseDomainNum
      Unsigned32,
   vrPpTbsePreserveDomain
      INTEGER }

vrPpTbseDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { vrPpTbseDIProvEntry 1 }

vrPpTbsePreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { vrPpTbseDIProvEntry 2 }

vrPpTbseStateTable OBJECT-TYPE
   SYNTAX     SEQUENCE OF VrPpTbseStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpTbse 14 }

vrPpTbseStateEntry OBJECT-TYPE
   SYNTAX     VrPpTbseStateEntry
   ACCESS     not-accessible
   STATUS     mandatory
   DESCRIPTION
     "An entry in the vrPpTbseStateTable."
   INDEX {
      vrIndex,
      vrPpIndex,
      vrPpTbseIndex }
::= { vrPpTbseStateTable 1 }

VrPpTbseStateEntry ::= SEQUENCE {
   vrPpTbseAdminState
      INTEGER,
   vrPpTbseOperationalState
      INTEGER,
   vrPpTbseUsageState
      INTEGER }

vrPpTbseAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpTbseStateEntry 1 }

vrPpTbseOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpTbseStateEntry 2 }

vrPpTbseUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpTbseStateEntry 3 }

vrPpTbseOperStatusTable OBJECT-TYPE
   SYNTAX     SEQUENCE OF VrPpTbseOperStatusEntry
   ACCESS     not-accessible
   STATUS     mandatory
   DESCRIPTION
     "This group includes the Operational Status attribute. This attribute 
      defines the current operational state of this component."
::= { vrPpTbse 15 }

vrPpTbseOperStatusEntry OBJECT-TYPE
   SYNTAX     VrPpTbseOperStatusEntry
   ACCESS     not-accessible
   STATUS     mandatory
   DESCRIPTION
     "An entry in the vrPpTbseOperStatusTable."
   INDEX {
      vrIndex,
      vrPpIndex,
      vrPpTbseIndex }
::= { vrPpTbseOperStatusTable 1 }

VrPpTbseOperStatusEntry ::= SEQUENCE {
   vrPpTbseSnmpOperStatus
      INTEGER }

vrPpTbseSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpTbseOperStatusEntry 1 }

vrPpTbseOperTable OBJECT-TYPE
   SYNTAX     SEQUENCE OF VrPpTbseOperEntry
   ACCESS     not-accessible
   STATUS     mandatory
   DESCRIPTION
     "This group houses all the operational attributes belonging to the base 
      group. The base group of attributes is applicable to all types of bridge 
      ports and represent the common factor between them. These attributes in 
      part, reflect the state of a bridge port."
::= { vrPpTbse 16 }

vrPpTbseOperEntry OBJECT-TYPE
   SYNTAX     VrPpTbseOperEntry
   ACCESS     not-accessible
   STATUS     mandatory
   DESCRIPTION
     "An entry in the vrPpTbseOperTable."
   INDEX {
      vrIndex,
      vrPpIndex,
      vrPpTbseIndex }
::= { vrPpTbseOperTable 1 }

VrPpTbseOperEntry ::= SEQUENCE {
   vrPpTbsePortName
      AsciiString,
   vrPpTbseUpTime
      Unsigned32,
   vrPpTbseDownTime
      Unsigned32,
   vrPpTbseBridgingMode
      INTEGER,
   vrPpTbseBridgePortConfig
      INTEGER,
   vrPpTbseBridgePortType
      INTEGER,
   vrPpTbseIfIndex
      InterfaceIndex,
   vrPpTbseDelayExceededDiscards
      Counter32,
   vrPpTbseMtuExceededDiscards
      Counter32 }

vrPpTbsePortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { vrPpTbseOperEntry 1 }

vrPpTbseUpTime OBJECT-TYPE
   SYNTAX     Unsigned32 (0..4294967295)
   ACCESS     read-only
   STATUS     mandatory
   DESCRIPTION
     "This attribute specifies the accumulated up time of this bridge port since 
      the last reset occurred."
   DEFVAL     { 0 }
::= { vrPpTbseOperEntry 3 }

vrPpTbseDownTime OBJECT-TYPE
   SYNTAX     Unsigned32 (0..4294967295)
   ACCESS     read-only
   STATUS     mandatory
   DESCRIPTION
     "This attribute specifies the accumulated down time of this bridge port 
      since the last reset occurred."
   DEFVAL     { 0 }
::= { vrPpTbseOperEntry 4 }

vrPpTbseBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { vrPpTbseOperEntry 5 }

vrPpTbseBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { vrPpTbseOperEntry 6 }

vrPpTbseBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { vrPpTbseOperEntry 7 }

vrPpTbseIfIndex OBJECT-TYPE
   SYNTAX     InterfaceIndex (1..65535)
   ACCESS     read-only
   STATUS     mandatory
   DESCRIPTION
     "This attribute specifies the index into the Interface Table where in 
      information about the media interface corresponding to the bridge port is 
      maintained."
::= { vrPpTbseOperEntry 8 }

vrPpTbseDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { vrPpTbseOperEntry 10 }

vrPpTbseMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { vrPpTbseOperEntry 11 }

vrPpTbseTbOperTable OBJECT-TYPE
   SYNTAX     SEQUENCE OF VrPpTbseTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { vrPpTbse 17 }

vrPpTbseTbOperEntry OBJECT-TYPE
   SYNTAX     VrPpTbseTbOperEntry
   ACCESS     not-accessible
   STATUS     mandatory
   DESCRIPTION
     "An entry in the vrPpTbseTbOperTable."
   INDEX {
      vrIndex,
      vrPpIndex,
      vrPpTbseIndex }
::= { vrPpTbseTbOperTable 1 }

VrPpTbseTbOperEntry ::= SEQUENCE {
   vrPpTbseMaxInfo
      Unsigned32,
   vrPpTbseBadVerifyDiscards
      Counter32,
   vrPpTbseUnicastNoMatches
      Counter32,
   vrPpTbseStaticEntryDiscards
      Counter32,
   vrPpTbseDynamicEntryDiscards
      Counter32,
   vrPpTbseLearningDiscards
      Counter32,
   vrPpTbseInDiscards
      Counter32,
   vrPpTbseInFrames
      Counter32,
   vrPpTbseOutFrames
      Counter32 }

vrPpTbseMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { vrPpTbseTbOperEntry 2 }

vrPpTbseBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { vrPpTbseTbOperEntry 3 }

vrPpTbseUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { vrPpTbseTbOperEntry 4 }

vrPpTbseStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { vrPpTbseTbOperEntry 5 }

vrPpTbseDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { vrPpTbseTbOperEntry 6 }

vrPpTbseLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { vrPpTbseTbOperEntry 7 }

vrPpTbseInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { vrPpTbseTbOperEntry 8 }

vrPpTbseInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { vrPpTbseTbOperEntry 9 }

vrPpTbseOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { vrPpTbseTbOperEntry 10 }

vrPpTbseStpOperTable OBJECT-TYPE
   SYNTAX     SEQUENCE OF VrPpTbseStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { vrPpTbse 18 }

vrPpTbseStpOperEntry OBJECT-TYPE
   SYNTAX     VrPpTbseStpOperEntry
   ACCESS     not-accessible
   STATUS     mandatory
   DESCRIPTION
     "An entry in the vrPpTbseStpOperTable."
   INDEX {
      vrIndex,
      vrPpIndex,
      vrPpTbseIndex }
::= { vrPpTbseStpOperTable 1 }

VrPpTbseStpOperEntry ::= SEQUENCE {
   vrPpTbseStpPortState
      INTEGER,
   vrPpTbseStpTypeOper
      INTEGER,
   vrPpTbseDesignatedCost
      Unsigned32,
   vrPpTbsePathCostOper
      Unsigned32,
   vrPpTbseDesignatedBridge
      BridgeId,
   vrPpTbseDesignatedPort
      Hex,
   vrPpTbseForwardTransitions
      Counter32,
   vrPpTbseBlockingDiscards
      Counter32,
   vrPpTbseDesignatedRoot
      BridgeId }

vrPpTbseStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { vrPpTbseStpOperEntry 2 }

vrPpTbseStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { vrPpTbseStpOperEntry 3 }

vrPpTbseDesignatedCost OBJECT-TYPE
   SYNTAX     Unsigned32 (0..4294967295)
   ACCESS     read-only
   STATUS     mandatory
   DESCRIPTION
     "This attribute specifies the path cost of the designated port of the lan 
      segment connected to the port."
::= { vrPpTbseStpOperEntry 4 }

vrPpTbsePathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { vrPpTbseStpOperEntry 5 }

vrPpTbseDesignatedBridge OBJECT-TYPE
   SYNTAX     BridgeId (SIZE (8))
   ACCESS     read-only
   STATUS     mandatory
   DESCRIPTION
     "This attribute specifies the identifier of the bridge that this port considers 
      to be the designated bridge."
::= { vrPpTbseStpOperEntry 6 }

vrPpTbseDesignatedPort OBJECT-TYPE
   SYNTAX     Hex (0..65535)
   ACCESS     read-only
   STATUS     mandatory
   DESCRIPTION
     "This attribute specifies the port identifier of the port on the designated 
      bridge, attached to the same lan as this port is attached to."
::= { vrPpTbseStpOperEntry 7 }

vrPpTbseForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { vrPpTbseStpOperEntry 8 }

vrPpTbseBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { vrPpTbseStpOperEntry 9 }

vrPpTbseDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { vrPpTbseStpOperEntry 10 }

vrPpTbseStatsTable OBJECT-TYPE
   SYNTAX     SEQUENCE OF VrPpTbseStatsEntry
   ACCESS     not-accessible
   STATUS     mandatory
   DESCRIPTION
     "This group houses all the statistical attributes applicable to all types of 
      bridge ports and represents the common factor between them. These 
      attributes in part reflect the state of the bridge port."
::= { vrPpTbse 19 }

vrPpTbseStatsEntry OBJECT-TYPE
   SYNTAX     VrPpTbseStatsEntry
   ACCESS     not-accessible
   STATUS     mandatory
   DESCRIPTION
     "An entry in the vrPpTbseStatsTable."
   INDEX {
      vrIndex,
      vrPpIndex,
      vrPpTbseIndex }
::= { vrPpTbseStatsTable 1 }

VrPpTbseStatsEntry ::= SEQUENCE {
   vrPpTbseBadAbstractDiscards
      Counter32,
   vrPpTbseTinygramFramesIn
      Counter32,
   vrPpTbseTinygramFramesOut
      Counter32,
   vrPpTbseInFilterDiscards
      Counter32,
   vrPpTbseOutFilterDiscards
      Counter32 }

vrPpTbseBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { vrPpTbseStatsEntry 1 }

vrPpTbseTinygramFramesIn OBJECT-TYPE
   SYNTAX     Counter32 
   ACCESS     read-only
   STATUS     mandatory
   DESCRIPTION
     "This attribute is indicative of the number of frames received on this 
      bridge port that used the tinygram compression scheme."
::= { vrPpTbseStatsEntry 2 }

vrPpTbseTinygramFramesOut OBJECT-TYPE
   SYNTAX     Counter32 
   ACCESS     read-only
   STATUS     mandatory
   DESCRIPTION
     "This attribute is indicative of the number of frames transmitted out this 
      bridge port that used the tinygram compression scheme."
::= { vrPpTbseStatsEntry 3 }

vrPpTbseInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { vrPpTbseStatsEntry 4 }

vrPpTbseOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { vrPpTbseStatsEntry 5 }


-- Vr/<string> Pp/<string> SrsgBridgePort
-- This component represents a controlled method to allow exchange of 
-- explorer frames between source route (SR) and source route transparent 
-- (SRT) networks.The SrsgBridgePort provides a cross over point for 
-- explorer frames from the source route network into the source route 
-- gating logic and vice-versa. The source route gating performs required 
-- verification before forwarding the frames into the source route 
-- transparent network.
-- The SrsgBridgePort participates in the source route spanning tree to 
-- eliminate possible loops caused by multiple active cross over points on 
-- multiple bridges and to provide for fault tolerance of these cross over 
-- points. While enabled, source route spanning tree BPDUs are sent 
-- across the source route transparent network, through this cross over 
-- point and the gating logic. Note that these explorer frames cross over 
-- based on the port's stpPortState.
-- All route explorer frames (ARE) are exchanged regardless of the 
-- stpPortState. 
-- Spanning tree explorer frames (STE) are exchanged only if stpPortState 
-- has a value of Forwarding.
-- If stpPortState has a value of Blocking STE frames will be sent out on 
-- bridge ports that are operating in the same mode, i.e. no exchange across 
-- SR and SRT networks takes place. Nevertheless, SR spanning tree 
-- BPDUs are still sent across the SRT network. Note that the 
-- SrsgBridgePort and the TbsgBridgePort must be provisioned during the 
-- same provisioning session as one cannot function without the other.

vrPpSrsg OBJECT IDENTIFIER ::= { vrPp 12 }



vrPpSrsgRowStatusTable OBJECT-TYPE
   SYNTAX     SEQUENCE OF VrPpSrsgRowStatusEntry
   ACCESS     not-accessible
   STATUS     mandatory
   DESCRIPTION
     "This entry controls the addition and deletion of 
      vrPpSrsg components."
::= { vrPpSrsg 1 }

vrPpSrsgRowStatusEntry OBJECT-TYPE
   SYNTAX     VrPpSrsgRowStatusEntry
   ACCESS     not-accessible
   STATUS     mandatory
   DESCRIPTION
     "A single entry in the table represents a single 
      vrPpSrsg component."
   INDEX {
      vrIndex,
      vrPpIndex,
      vrPpSrsgIndex }
::= { vrPpSrsgRowStatusTable 1 }

VrPpSrsgRowStatusEntry ::= SEQUENCE {
   vrPpSrsgRowStatus
      RowStatus,
   vrPpSrsgComponentName
      DisplayString,
   vrPpSrsgStorageType
      StorageType,
   vrPpSrsgIndex
      NonReplicated }

vrPpSrsgRowStatus OBJECT-TYPE
   SYNTAX     RowStatus 
   ACCESS     read-write
   STATUS     mandatory
   DESCRIPTION
     "This variable is used as the basis for SNMP naming of
      vrPpSrsg components.
      These components can be added and deleted."
::= { vrPpSrsgRowStatusEntry 1 }

vrPpSrsgComponentName OBJECT-TYPE
   SYNTAX     DisplayString 
   ACCESS     read-only
   STATUS     mandatory
   DESCRIPTION
     "This variable provides the component's string name for
      use with the ASCII Console Interface"
::= { vrPpSrsgRowStatusEntry 2 }

vrPpSrsgStorageType OBJECT-TYPE
   SYNTAX     StorageType 
   ACCESS     read-only
   STATUS     mandatory
   DESCRIPTION
     "This variable represents the storage type value for the
      vrPpSrsg tables."
::= { vrPpSrsgRowStatusEntry 4 }

vrPpSrsgIndex OBJECT-TYPE
   SYNTAX     NonReplicated 
   ACCESS     not-accessible
   STATUS     mandatory
   DESCRIPTION
     "This variable represents the index for the vrPpSrsg tables."
::= { vrPpSrsgRowStatusEntry 10 }

vrPpSrsgProvTable OBJECT-TYPE
   SYNTAX     SEQUENCE OF VrPpSrsgProvEntry
   ACCESS     not-accessible
   STATUS     mandatory
   DESCRIPTION
     "This group houses all the provisionable attributes that belong to the this 
      group. This group of attributes is applicable to all types of bridge ports 
      and represent the common factor between them. These attributes 
      influence the working of a bridge port."
::= { vrPpSrsg 10 }

vrPpSrsgProvEntry OBJECT-TYPE
   SYNTAX     VrPpSrsgProvEntry
   ACCESS     not-accessible
   STATUS     mandatory
   DESCRIPTION
     "An entry in the vrPpSrsgProvTable."
   INDEX {
      vrIndex,
      vrPpIndex,
      vrPpSrsgIndex }
::= { vrPpSrsgProvTable 1 }

VrPpSrsgProvEntry ::= SEQUENCE {
   vrPpSrsgTranslateIpx
      INTEGER,
   vrPpSrsgFragmentIp
      INTEGER,
   vrPpSrsgServiceClass
      INTEGER,
   vrPpSrsgConvertArpMacAddress
      INTEGER,
   vrPpSrsgPortNum
      Unsigned32,
   vrPpSrsgOutboundFrameMediaType
      INTEGER }

vrPpSrsgTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { vrPpSrsgProvEntry 1 }

vrPpSrsgFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { vrPpSrsgProvEntry 2 }

vrPpSrsgServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { vrPpSrsgProvEntry 3 }

vrPpSrsgConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { vrPpSrsgProvEntry 4 }

vrPpSrsgPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { vrPpSrsgProvEntry 5 }

vrPpSrsgOutboundFrameMediaType OBJECT-TYPE
   SYNTAX     INTEGER  {
                 unaltered(1),
                 ethernetConv(2) }
   ACCESS     read-write
   STATUS     mandatory
   DESCRIPTION
     "This attribute specifies the media type the frame must be in before it is 
      to be forwarded over the outbound supported WAN Bridge Protocol 
      Port. The attribute only applies to outbound Bridge Protocol Port.
      
      For supported bridge ports, if the attribute value remains set to the 
      default value of unaltered then there will be no frame conversion. When 
      the value is set to the value ethernetConv then all frames being 
      forwarded out the outbound WAN Port will be converted to ethernet 
      before forwarding takes place. The only outbound WAN medias that 
      currently support conversion are: FR (Frame Relay) and VNS. All other 
      medias will fail the Bridge Port semantic check when attempts are made 
      to alter this attribute. 
      
      The following is an example of what the user may be able to do. Frames 
      originating from a Token Ring are to be flooded out onto another Token 
      Ring and a Frame Relay Port. The token ring Outbound port performs 
      no translation, yet the FR Port has the outboundFrameMediaType 
      attribute set to ethernetConv which results in the frame being translated 
      into Ethernet format from Token Ring format before Frame Relay does 
      its encapsulation and transmits over the FR port."
   DEFVAL     { unaltered }
::= { vrPpSrsgProvEntry 6 }

vrPpSrsgStpProvTable OBJECT-TYPE
   SYNTAX     SEQUENCE OF VrPpSrsgStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { vrPpSrsg 12 }

vrPpSrsgStpProvEntry OBJECT-TYPE
   SYNTAX     VrPpSrsgStpProvEntry
   ACCESS     not-accessible
   STATUS     mandatory
   DESCRIPTION
     "An entry in the vrPpSrsgStpProvTable."
   INDEX {
      vrIndex,
      vrPpIndex,
      vrPpSrsgIndex }
::= { vrPpSrsgStpProvTable 1 }

VrPpSrsgStpProvEntry ::= SEQUENCE {
   vrPpSrsgAdminStatus
      INTEGER,
   vrPpSrsgPortStateStpControl
      INTEGER,
   vrPpSrsgStpTypeProv
      INTEGER,
   vrPpSrsgPortPriority
      Unsigned32,
   vrPpSrsgPathCost
      Unsigned32,
   vrPpSrsgPathCostMethod
      INTEGER }

vrPpSrsgAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { vrPpSrsgStpProvEntry 1 }

vrPpSrsgPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { vrPpSrsgStpProvEntry 2 }

vrPpSrsgStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { vrPpSrsgStpProvEntry 3 }

vrPpSrsgPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { vrPpSrsgStpProvEntry 4 }

vrPpSrsgPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { vrPpSrsgStpProvEntry 5 }

vrPpSrsgPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { vrPpSrsgStpProvEntry 6 }

vrPpSrsgDIProvTable OBJECT-TYPE
   SYNTAX     SEQUENCE OF VrPpSrsgDIProvEntry
   ACCESS     not-accessible
   STATUS     mandatory
   DESCRIPTION
     "This group houses all the provisionable, domain specific attributes for a 
      non-encapsulating bridge port."
::= { vrPpSrsg 13 }

vrPpSrsgDIProvEntry OBJECT-TYPE
   SYNTAX     VrPpSrsgDIProvEntry
   ACCESS     not-accessible
   STATUS     mandatory
   DESCRIPTION
     "An entry in the vrPpSrsgDIProvTable."
   INDEX {
      vrIndex,
      vrPpIndex,
      vrPpSrsgIndex }
::= { vrPpSrsgDIProvTable 1 }

VrPpSrsgDIProvEntry ::= SEQUENCE {
   vrPpSrsgDomainNum
      Unsigned32,
   vrPpSrsgPreserveDomain
      INTEGER }

vrPpSrsgDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { vrPpSrsgDIProvEntry 1 }

vrPpSrsgPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { vrPpSrsgDIProvEntry 2 }

vrPpSrsgStateTable OBJECT-TYPE
   SYNTAX     SEQUENCE OF VrPpSrsgStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpSrsg 14 }

vrPpSrsgStateEntry OBJECT-TYPE
   SYNTAX     VrPpSrsgStateEntry
   ACCESS     not-accessible
   STATUS     mandatory
   DESCRIPTION
     "An entry in the vrPpSrsgStateTable."
   INDEX {
      vrIndex,
      vrPpIndex,
      vrPpSrsgIndex }
::= { vrPpSrsgStateTable 1 }

VrPpSrsgStateEntry ::= SEQUENCE {
   vrPpSrsgAdminState
      INTEGER,
   vrPpSrsgOperationalState
      INTEGER,
   vrPpSrsgUsageState
      INTEGER }

vrPpSrsgAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpSrsgStateEntry 1 }

vrPpSrsgOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpSrsgStateEntry 2 }

vrPpSrsgUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpSrsgStateEntry 3 }

vrPpSrsgOperStatusTable OBJECT-TYPE
   SYNTAX     SEQUENCE OF VrPpSrsgOperStatusEntry
   ACCESS     not-accessible
   STATUS     mandatory
   DESCRIPTION
     "This group includes the Operational Status attribute. This attribute 
      defines the current operational state of this component."
::= { vrPpSrsg 15 }

vrPpSrsgOperStatusEntry OBJECT-TYPE
   SYNTAX     VrPpSrsgOperStatusEntry
   ACCESS     not-accessible
   STATUS     mandatory
   DESCRIPTION
     "An entry in the vrPpSrsgOperStatusTable."
   INDEX {
      vrIndex,
      vrPpIndex,
      vrPpSrsgIndex }
::= { vrPpSrsgOperStatusTable 1 }

VrPpSrsgOperStatusEntry ::= SEQUENCE {
   vrPpSrsgSnmpOperStatus
      INTEGER }

vrPpSrsgSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpSrsgOperStatusEntry 1 }

vrPpSrsgOperTable OBJECT-TYPE
   SYNTAX     SEQUENCE OF VrPpSrsgOperEntry
   ACCESS     not-accessible
   STATUS     mandatory
   DESCRIPTION
     "This group houses all the operational attributes belonging to the base 
      group. The base group of attributes is applicable to all types of bridge 
      ports and represent the common factor between them. These attributes in 
      part, reflect the state of a bridge port."
::= { vrPpSrsg 16 }

vrPpSrsgOperEntry OBJECT-TYPE
   SYNTAX     VrPpSrsgOperEntry
   ACCESS     not-accessible
   STATUS     mandatory
   DESCRIPTION
     "An entry in the vrPpSrsgOperTable."
   INDEX {
      vrIndex,
      vrPpIndex,
      vrPpSrsgIndex }
::= { vrPpSrsgOperTable 1 }

VrPpSrsgOperEntry ::= SEQUENCE {
   vrPpSrsgPortName
      AsciiString,
   vrPpSrsgUpTime
      Unsigned32,
   vrPpSrsgDownTime
      Unsigned32,
   vrPpSrsgBridgingMode
      INTEGER,
   vrPpSrsgBridgePortConfig
      INTEGER,
   vrPpSrsgBridgePortType
      INTEGER,
   vrPpSrsgIfIndex
      InterfaceIndex,
   vrPpSrsgDelayExceededDiscards
      Counter32,
   vrPpSrsgMtuExceededDiscards
      Counter32 }

vrPpSrsgPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { vrPpSrsgOperEntry 1 }

vrPpSrsgUpTime OBJECT-TYPE
   SYNTAX     Unsigned32 (0..4294967295)
   ACCESS     read-only
   STATUS     mandatory
   DESCRIPTION
     "This attribute specifies the accumulated up time of this bridge port since 
      the last reset occurred."
   DEFVAL     { 0 }
::= { vrPpSrsgOperEntry 3 }

vrPpSrsgDownTime OBJECT-TYPE
   SYNTAX     Unsigned32 (0..4294967295)
   ACCESS     read-only
   STATUS     mandatory
   DESCRIPTION
     "This attribute specifies the accumulated down time of this bridge port 
      since the last reset occurred."
   DEFVAL     { 0 }
::= { vrPpSrsgOperEntry 4 }

vrPpSrsgBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { vrPpSrsgOperEntry 5 }

vrPpSrsgBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { vrPpSrsgOperEntry 6 }

vrPpSrsgBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { vrPpSrsgOperEntry 7 }

vrPpSrsgIfIndex OBJECT-TYPE
   SYNTAX     InterfaceIndex (1..65535)
   ACCESS     read-only
   STATUS     mandatory
   DESCRIPTION
     "This attribute specifies the index into the Interface Table where in 
      information about the media interface corresponding to the bridge port is 
      maintained."
::= { vrPpSrsgOperEntry 8 }

vrPpSrsgDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { vrPpSrsgOperEntry 10 }

vrPpSrsgMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { vrPpSrsgOperEntry 11 }

vrPpSrsgStpOperTable OBJECT-TYPE
   SYNTAX     SEQUENCE OF VrPpSrsgStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { vrPpSrsg 18 }

vrPpSrsgStpOperEntry OBJECT-TYPE
   SYNTAX     VrPpSrsgStpOperEntry
   ACCESS     not-accessible
   STATUS     mandatory
   DESCRIPTION
     "An entry in the vrPpSrsgStpOperTable."
   INDEX {
      vrIndex,
      vrPpIndex,
      vrPpSrsgIndex }
::= { vrPpSrsgStpOperTable 1 }

VrPpSrsgStpOperEntry ::= SEQUENCE {
   vrPpSrsgStpPortState
      INTEGER,
   vrPpSrsgStpTypeOper
      INTEGER,
   vrPpSrsgDesignatedCost
      Unsigned32,
   vrPpSrsgPathCostOper
      Unsigned32,
   vrPpSrsgDesignatedBridge
      BridgeId,
   vrPpSrsgDesignatedPort
      Hex,
   vrPpSrsgForwardTransitions
      Counter32,
   vrPpSrsgBlockingDiscards
      Counter32,
   vrPpSrsgDesignatedRoot
      BridgeId }

vrPpSrsgStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { vrPpSrsgStpOperEntry 2 }

vrPpSrsgStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { vrPpSrsgStpOperEntry 3 }

vrPpSrsgDesignatedCost OBJECT-TYPE
   SYNTAX     Unsigned32 (0..4294967295)
   ACCESS     read-only
   STATUS     mandatory
   DESCRIPTION
     "This attribute specifies the path cost of the designated port of the lan 
      segment connected to the port."
::= { vrPpSrsgStpOperEntry 4 }

vrPpSrsgPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { vrPpSrsgStpOperEntry 5 }

vrPpSrsgDesignatedBridge OBJECT-TYPE
   SYNTAX     BridgeId (SIZE (8))
   ACCESS     read-only
   STATUS     mandatory
   DESCRIPTION
     "This attribute specifies the identifier of the bridge that this port considers 
      to be the designated bridge."
::= { vrPpSrsgStpOperEntry 6 }

vrPpSrsgDesignatedPort OBJECT-TYPE
   SYNTAX     Hex (0..65535)
   ACCESS     read-only
   STATUS     mandatory
   DESCRIPTION
     "This attribute specifies the port identifier of the port on the designated 
      bridge, attached to the same lan as this port is attached to."
::= { vrPpSrsgStpOperEntry 7 }

vrPpSrsgForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { vrPpSrsgStpOperEntry 8 }

vrPpSrsgBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { vrPpSrsgStpOperEntry 9 }

vrPpSrsgDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { vrPpSrsgStpOperEntry 10 }

vrPpSrsgStatsTable OBJECT-TYPE
   SYNTAX     SEQUENCE OF VrPpSrsgStatsEntry
   ACCESS     not-accessible
   STATUS     mandatory
   DESCRIPTION
     "This group houses all the statistical attributes applicable to all types of 
      bridge ports and represents the common factor between them. These 
      attributes in part reflect the state of the bridge port."
::= { vrPpSrsg 19 }

vrPpSrsgStatsEntry OBJECT-TYPE
   SYNTAX     VrPpSrsgStatsEntry
   ACCESS     not-accessible
   STATUS     mandatory
   DESCRIPTION
     "An entry in the vrPpSrsgStatsTable."
   INDEX {
      vrIndex,
      vrPpIndex,
      vrPpSrsgIndex }
::= { vrPpSrsgStatsTable 1 }

VrPpSrsgStatsEntry ::= SEQUENCE {
   vrPpSrsgBadAbstractDiscards
      Counter32,
   vrPpSrsgTinygramFramesIn
      Counter32,
   vrPpSrsgTinygramFramesOut
      Counter32,
   vrPpSrsgInFilterDiscards
      Counter32,
   vrPpSrsgOutFilterDiscards
      Counter32 }

vrPpSrsgBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { vrPpSrsgStatsEntry 1 }

vrPpSrsgTinygramFramesIn OBJECT-TYPE
   SYNTAX     Counter32 
   ACCESS     read-only
   STATUS     mandatory
   DESCRIPTION
     "This attribute is indicative of the number of frames received on this 
      bridge port that used the tinygram compression scheme."
::= { vrPpSrsgStatsEntry 2 }

vrPpSrsgTinygramFramesOut OBJECT-TYPE
   SYNTAX     Counter32 
   ACCESS     read-only
   STATUS     mandatory
   DESCRIPTION
     "This attribute is indicative of the number of frames transmitted out this 
      bridge port that used the tinygram compression scheme."
::= { vrPpSrsgStatsEntry 3 }

vrPpSrsgInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { vrPpSrsgStatsEntry 4 }

vrPpSrsgOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { vrPpSrsgStatsEntry 5 }

vrPpSrsgSrProvTable OBJECT-TYPE
   SYNTAX     SEQUENCE OF VrPpSrsgSrProvEntry
   ACCESS     not-accessible
   STATUS     mandatory
   DESCRIPTION
     "This group contains all port specific, provisionable attributes associated 
      with SourceRouteBridge ports."
::= { vrPpSrsg 20 }

vrPpSrsgSrProvEntry OBJECT-TYPE
   SYNTAX     VrPpSrsgSrProvEntry
   ACCESS     not-accessible
   STATUS     mandatory
   DESCRIPTION
     "An entry in the vrPpSrsgSrProvTable."
   INDEX {
      vrIndex,
      vrPpIndex,
      vrPpSrsgIndex }
::= { vrPpSrsgSrProvTable 1 }

VrPpSrsgSrProvEntry ::= SEQUENCE {
   vrPpSrsgHopCount
      Unsigned32,
   vrPpSrsgExploreFrameTreatment
      INTEGER,
   vrPpSrsgLanId
      Unsigned32,
   vrPpSrsgInternalLanId
      Unsigned32,
   vrPpSrsgBridgeNum
      Unsigned32,
   vrPpSrsgLargestFrame
      Unsigned32,
   vrPpSrsgSteSpanMode
      INTEGER,
   vrPpSrsgAreRdLimit
      Unsigned32,
   vrPpSrsgSteRdLimit
      Unsigned32 }

vrPpSrsgHopCount OBJECT-TYPE
   SYNTAX     Unsigned32 (1..7)
   ACCESS     read-write
   STATUS     mandatory
   DESCRIPTION
     "This attribute specifies the maximum number of hops allowed in 
      Spanning Tree Explore and All Routes Explore frames. This value is one 
      less than the maximum number of route descriptors allowed in a source 
      route frame"
   DEFVAL     { 7 }
::= { vrPpSrsgSrProvEntry 1 }

vrPpSrsgExploreFrameTreatment OBJECT-TYPE
   SYNTAX     INTEGER  {
                 encap(0),
                 xlate(1) }
   ACCESS     read-write
   STATUS     mandatory
   DESCRIPTION
     "This attribute specifies whether or not explore frames received from 
      SourceRouteBridge ports will be sent to the SRTB-8209 translation or 
      the encapsulated SourceRouteBridge logic. This option is used only 
      when both the TbsrBridgePort and the SrtbBridgePort are provisioned 
      and enabled. 
      A value of Xlate implies that the explore frames will be sent to the Srtb 
      translation logic and a value of Encap implies that the frames will be 
      sent to the Encapsulated source route bridging logic."
   DEFVAL     { encap }
::= { vrPpSrsgSrProvEntry 2 }

vrPpSrsgLanId OBJECT-TYPE
   SYNTAX     Unsigned32 (0..4095)
   ACCESS     read-write
   STATUS     mandatory
   DESCRIPTION
     "This attribute specifies the identifier for the physical LAN that this port 
      is attached. All SourceRouteBridge ports are assigned to a physical LAN 
      and a logical internal LAN. 
      Current source route bridge implementations limit the lanId to a value in 
      the range 0 to 4095."
   DEFVAL     { 0 }
::= { vrPpSrsgSrProvEntry 3 }

vrPpSrsgInternalLanId OBJECT-TYPE
   SYNTAX     Unsigned32 (0..4095)
   ACCESS     read-write
   STATUS     mandatory
   DESCRIPTION
     "This attribute specifies the identifier for the internal logical LAN this 
      port is attached. All SourceRouteBridge ports are assigned to a physical 
      LAN and a logical internal LAN. 
      Current source route bridge implementations limit the lanId to a value in 
      the range 0 to 4095."
   DEFVAL     { 0 }
::= { vrPpSrsgSrProvEntry 4 }

vrPpSrsgBridgeNum OBJECT-TYPE
   SYNTAX     Unsigned32 (0..15)
   ACCESS     read-write
   STATUS     mandatory
   DESCRIPTION
     "This attribute specifies the value that is used to identify this bridge when 
      more than one bridge is used to span the same two LAN segments."
   DEFVAL     { 7 }
::= { vrPpSrsgSrProvEntry 5 }

vrPpSrsgLargestFrame OBJECT-TYPE
   SYNTAX     Unsigned32 (516 | 1470 | 2052 | 4399 | 8130 | 11407 | 17749)
   ACCESS     read-write
   STATUS     mandatory
   DESCRIPTION
     "This attribute specifies the maximum frame size (LLC and above) in 
      octets, allowed by this SourceRouteBridge port. This field is used to 
      determine whether a modification of the largest frame field of the 
      routing control field of the routing information field is warranted."
::= { vrPpSrsgSrProvEntry 6 }

vrPpSrsgSteSpanMode OBJECT-TYPE
   SYNTAX     INTEGER  {
                 autoSpan(1),
                 disabled(2),
                 forced(3) }
   ACCESS     read-write
   STATUS     mandatory
   DESCRIPTION
     "This attribute determines how this bridge port will react when presented 
      with a Spanning Tree Explore frame.
      If disabled, the Spanning Tree Explore frame is discarded regardless of 
      the value of stpPortState. 
      If the value of this attribute is forced, the Spanning Tree Explore frame 
      is forwarded regardless of the value of stpPortState. 
      autoSpan uses the stpPortState value to decide whether or not Spanning 
      Tree Explore frames should be forwarded out this bridge port. If the port 
      is in the forwarding state, the frame is received and transmitted 
      otherwise the frame is discarded."
   DEFVAL     { autoSpan }
::= { vrPpSrsgSrProvEntry 7 }

vrPpSrsgAreRdLimit OBJECT-TYPE
   SYNTAX     Unsigned32 (0..8)
   ACCESS     read-write
   STATUS     mandatory
   DESCRIPTION
     "This attribute specifies the number of route descriptors allowed in an All 
      Routes Explore frame received on a SourceRouteBridgePort or 
      SourceRouteTransparentBridgePort. Current source route bridge 
      implementations limit the areRdLimit to a value in the range 0 to 8."
   DEFVAL     { 8 }
::= { vrPpSrsgSrProvEntry 8 }

vrPpSrsgSteRdLimit OBJECT-TYPE
   SYNTAX     Unsigned32 (0..8)
   ACCESS     read-write
   STATUS     mandatory
   DESCRIPTION
     "This attribute specifies the number of route descriptors allowed in a 
      Spanning Tree Explore frame received on a SourceRouteBridgePort or 
      SourceRouteTransparentBridgePort. Current source route bridge 
      implementations limit the steRdLimit to a value in the range 0 to 8."
   DEFVAL     { 8 }
::= { vrPpSrsgSrProvEntry 9 }

vrPpSrsgSrStatsTable OBJECT-TYPE
   SYNTAX     SEQUENCE OF VrPpSrsgSrStatsEntry
   ACCESS     not-accessible
   STATUS     mandatory
   DESCRIPTION
     "This group contains all port specific statistical attributes associated with 
      SourceRouteBridge ports."
::= { vrPpSrsg 21 }

vrPpSrsgSrStatsEntry OBJECT-TYPE
   SYNTAX     VrPpSrsgSrStatsEntry
   ACCESS     not-accessible
   STATUS     mandatory
   DESCRIPTION
     "An entry in the vrPpSrsgSrStatsTable."
   INDEX {
      vrIndex,
      vrPpIndex,
      vrPpSrsgIndex }
::= { vrPpSrsgSrStatsTable 1 }

VrPpSrsgSrStatsEntry ::= SEQUENCE {
   vrPpSrsgSpecInFrames
      Counter32,
   vrPpSrsgSpecOutFrames
      Counter32,
   vrPpSrsgApeInFrames
      Counter32,
   vrPpSrsgApeOutFrames
      Counter32,
   vrPpSrsgSteInFrames
      Counter32,
   vrPpSrsgSteOutFrames
      Counter32,
   vrPpSrsgSegmentMismatchDiscards
      Counter32,
   vrPpSrsgDupSegmentDiscards
      Counter32,
   vrPpSrsgHopCountExceededDiscards
      Counter32,
   vrPpSrsgDupLanIdOrTreeErrors
      Counter32,
   vrPpSrsgLanIdMismatches
      Counter32,
   vrPpSrsgStaticDiscards
      Counter32,
   vrPpSrsgDynamicDiscards
      Counter32 }

vrPpSrsgSpecInFrames OBJECT-TYPE
   SYNTAX     Counter32 
   ACCESS     read-only
   STATUS     mandatory
   DESCRIPTION
     "This attribute specifies the number of specifically routed frames that 
      were received by this bridge port. A specifically routed frame has a route 
      descriptor, constructed by the originating host which details an explicit 
      route to the destination host. This counter will wrap to zero when it 
      exceeds its maximum."
::= { vrPpSrsgSrStatsEntry 1 }

vrPpSrsgSpecOutFrames OBJECT-TYPE
   SYNTAX     Counter32 
   ACCESS     read-only
   STATUS     mandatory
   DESCRIPTION
     "This attribute specifies the number of specifically routed frames that 
      were transmitted from this bridge port. This counter will wrap to zero 
      when it exceeds its maximum."
::= { vrPpSrsgSrStatsEntry 2 }

vrPpSrsgApeInFrames OBJECT-TYPE
   SYNTAX     Counter32 
   ACCESS     read-only
   STATUS     mandatory
   DESCRIPTION
     "This attribute specifies the number of All Path Explore frames received 
      on this bridge port. The All Path Explore frames are forwarded to all 
      SourceRouteBridge ports assigned to this bridge regardless of the port's 
      portStpStates. This counter will wrap to zero when it exceeds its 
      maximum."
::= { vrPpSrsgSrStatsEntry 3 }

vrPpSrsgApeOutFrames OBJECT-TYPE
   SYNTAX     Counter32 
   ACCESS     read-only
   STATUS     mandatory
   DESCRIPTION
     "This attribute specifies the number of All Path Explore frames 
      transmitted on this bridge port. The All Path Explore frames are 
      forwarded to all SourceRouteBridge ports assigned to this bridge 
      regardless of the port's portStpState state. This counter will wrap to zero 
      when it exceeds its maximum."
::= { vrPpSrsgSrStatsEntry 4 }

vrPpSrsgSteInFrames OBJECT-TYPE
   SYNTAX     Counter32 
   ACCESS     read-only
   STATUS     mandatory
   DESCRIPTION
     "This attribute specifies the number of Spanning Tree Explore frames 
      received on this bridge port. The Spanning Tree Explore frames are only 
      forwarded through bridge ports whose portStpState has a value of 
      forwarding. This counter will wrap to zero when it exceeds its 
      maximum."
::= { vrPpSrsgSrStatsEntry 5 }

vrPpSrsgSteOutFrames OBJECT-TYPE
   SYNTAX     Counter32 
   ACCESS     read-only
   STATUS     mandatory
   DESCRIPTION
     "This attribute specifies the number of Spanning Tree Frames transmitted 
      on this bridge port. This counter will wrap to zero when it exceeds its 
      maximum."
::= { vrPpSrsgSrStatsEntry 6 }

vrPpSrsgSegmentMismatchDiscards OBJECT-TYPE
   SYNTAX     Counter32 
   ACCESS     read-only
   STATUS     mandatory
   DESCRIPTION
     "This attribute specifies the number of All Routes Explore and Spanning 
      Tree Explore frames that were discarded due to an invalid next segment 
      value in the routing information field. This counter will wrap to zero 
      when it exceeds its maximum."
::= { vrPpSrsgSrStatsEntry 7 }

vrPpSrsgDupSegmentDiscards OBJECT-TYPE
   SYNTAX     Counter32 
   ACCESS     read-only
   STATUS     mandatory
   DESCRIPTION
     "This attribute specifies the number of frames discarded due to the 
      presence of a duplicate segment identifier in the route descriptor field 
      which may indicate a loop in the network topology. This counter will 
      wrap to zero when it exceeds its maximum."
::= { vrPpSrsgSrStatsEntry 8 }

vrPpSrsgHopCountExceededDiscards OBJECT-TYPE
   SYNTAX     Counter32 
   ACCESS     read-only
   STATUS     mandatory
   DESCRIPTION
     "This attribute specifies the number of All Routes Explore and Spanning 
      Tree Explore frames discarded by this bridge port due to a frame 
      exceeding the maximum size allowed for a route descriptor length. This 
      counter will wrap to zero when it exceeds its maximum."
::= { vrPpSrsgSrStatsEntry 9 }

vrPpSrsgDupLanIdOrTreeErrors OBJECT-TYPE
   SYNTAX     Counter32 
   ACCESS     read-only
   STATUS     mandatory
   DESCRIPTION
     "This attribute specifies the number frames received which contain 
      duplicate LAN IDs or Tree errors. This attribute is helpful in debugging 
      problems in networks which contain older IBM-SR bridges. This 
      counter will wrap to zero when it exceeds its maximum."
::= { vrPpSrsgSrStatsEntry 10 }

vrPpSrsgLanIdMismatches OBJECT-TYPE
   SYNTAX     Counter32 
   ACCESS     read-only
   STATUS     mandatory
   DESCRIPTION
     "This attributes counts the number of All Routes Explore or Spanning 
      Tree Explore frames that were discarded because the last LAN ID in the 
      routing information field did not equal the LAN ID. This counter will 
      wrap to zero when it exceeds its maximum."
::= { vrPpSrsgSrStatsEntry 11 }

vrPpSrsgStaticDiscards OBJECT-TYPE
   SYNTAX     Counter32 
   ACCESS     read-only
   STATUS     mandatory
   DESCRIPTION
     "This attribute is indicative of the number of explorer frames discarded 
      due to fact that the outbound SourceRouteBridge port was disabled or 
      deleted. This counter will wrap to zero when it exceeds its maximum."
::= { vrPpSrsgSrStatsEntry 12 }

vrPpSrsgDynamicDiscards OBJECT-TYPE
   SYNTAX     Counter32 
   ACCESS     read-only
   STATUS     mandatory
   DESCRIPTION
     "This attribute specifies the number of frames discarded due to receiving 
      a frame with a target LAN ID which did not match the internal LAN ID 
      of the receiving bridge port. This counter will wrap to zero when it 
      exceeds its maximum."
::= { vrPpSrsgSrStatsEntry 13 }


-- Vr/<string> Pp/<string> TbsgBridgePort
-- This component represents a controlled way to allow exchange of 
-- explorer frames between SR and SRT networks.The TbsgBridgePort 
-- provides a cross over point for explorer frames from the source route 
-- gating logic into a SRT network and vice-versa. This port can and 
-- should be enabled / disabled through the SrsgBridgePort. This bridge 
-- port does not participate in the SR spanning tree protocol. Nevertheless, 
-- SR spanning tree BPDUs are still sent out across into the SRT network. 
-- Note that the SrsgBridgePort and the TbsgBridgePort should always be 
-- provisioned together, as one of these bridge ports cannot function 
-- without the other. 

vrPpTbsg OBJECT IDENTIFIER ::= { vrPp 13 }



vrPpTbsgRowStatusTable OBJECT-TYPE
   SYNTAX     SEQUENCE OF VrPpTbsgRowStatusEntry
   ACCESS     not-accessible
   STATUS     mandatory
   DESCRIPTION
     "This entry controls the addition and deletion of 
      vrPpTbsg components."
::= { vrPpTbsg 1 }

vrPpTbsgRowStatusEntry OBJECT-TYPE
   SYNTAX     VrPpTbsgRowStatusEntry
   ACCESS     not-accessible
   STATUS     mandatory
   DESCRIPTION
     "A single entry in the table represents a single 
      vrPpTbsg component."
   INDEX {
      vrIndex,
      vrPpIndex,
      vrPpTbsgIndex }
::= { vrPpTbsgRowStatusTable 1 }

VrPpTbsgRowStatusEntry ::= SEQUENCE {
   vrPpTbsgRowStatus
      RowStatus,
   vrPpTbsgComponentName
      DisplayString,
   vrPpTbsgStorageType
      StorageType,
   vrPpTbsgIndex
      NonReplicated }

vrPpTbsgRowStatus OBJECT-TYPE
   SYNTAX     RowStatus 
   ACCESS     read-write
   STATUS     mandatory
   DESCRIPTION
     "This variable is used as the basis for SNMP naming of
      vrPpTbsg components.
      These components can be added and deleted."
::= { vrPpTbsgRowStatusEntry 1 }

vrPpTbsgComponentName OBJECT-TYPE
   SYNTAX     DisplayString 
   ACCESS     read-only
   STATUS     mandatory
   DESCRIPTION
     "This variable provides the component's string name for
      use with the ASCII Console Interface"
::= { vrPpTbsgRowStatusEntry 2 }

vrPpTbsgStorageType OBJECT-TYPE
   SYNTAX     StorageType 
   ACCESS     read-only
   STATUS     mandatory
   DESCRIPTION
     "This variable represents the storage type value for the
      vrPpTbsg tables."
::= { vrPpTbsgRowStatusEntry 4 }

vrPpTbsgIndex OBJECT-TYPE
   SYNTAX     NonReplicated 
   ACCESS     not-accessible
   STATUS     mandatory
   DESCRIPTION
     "This variable represents the index for the vrPpTbsg tables."
::= { vrPpTbsgRowStatusEntry 10 }

vrPpTbsgProvTable OBJECT-TYPE
   SYNTAX     SEQUENCE OF VrPpTbsgProvEntry
   ACCESS     not-accessible
   STATUS     mandatory
   DESCRIPTION
     "This group houses all the provisionable attributes that belong to the this 
      group. This group of attributes is applicable to all types of bridge ports 
      and represent the common factor between them. These attributes 
      influence the working of a bridge port."
::= { vrPpTbsg 10 }

vrPpTbsgProvEntry OBJECT-TYPE
   SYNTAX     VrPpTbsgProvEntry
   ACCESS     not-accessible
   STATUS     mandatory
   DESCRIPTION
     "An entry in the vrPpTbsgProvTable."
   INDEX {
      vrIndex,
      vrPpIndex,
      vrPpTbsgIndex }
::= { vrPpTbsgProvTable 1 }

VrPpTbsgProvEntry ::= SEQUENCE {
   vrPpTbsgTranslateIpx
      INTEGER,
   vrPpTbsgFragmentIp
      INTEGER,
   vrPpTbsgServiceClass
      INTEGER,
   vrPpTbsgConvertArpMacAddress
      INTEGER,
   vrPpTbsgPortNum
      Unsigned32,
   vrPpTbsgOutboundFrameMediaType
      INTEGER }

vrPpTbsgTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { vrPpTbsgProvEntry 1 }

vrPpTbsgFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { vrPpTbsgProvEntry 2 }

vrPpTbsgServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { vrPpTbsgProvEntry 3 }

vrPpTbsgConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { vrPpTbsgProvEntry 4 }

vrPpTbsgPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { vrPpTbsgProvEntry 5 }

vrPpTbsgOutboundFrameMediaType OBJECT-TYPE
   SYNTAX     INTEGER  {
                 unaltered(1),
                 ethernetConv(2) }
   ACCESS     read-write
   STATUS     mandatory
   DESCRIPTION
     "This attribute specifies the media type the frame must be in before it is 
      to be forwarded over the outbound supported WAN Bridge Protocol 
      Port. The attribute only applies to outbound Bridge Protocol Port.
      
      For supported bridge ports, if the attribute value remains set to the 
      default value of unaltered then there will be no frame conversion. When 
      the value is set to the value ethernetConv then all frames being 
      forwarded out the outbound WAN Port will be converted to ethernet 
      before forwarding takes place. The only outbound WAN medias that 
      currently support conversion are: FR (Frame Relay) and VNS. All other 
      medias will fail the Bridge Port semantic check when attempts are made 
      to alter this attribute. 
      
      The following is an example of what the user may be able to do. Frames 
      originating from a Token Ring are to be flooded out onto another Token 
      Ring and a Frame Relay Port. The token ring Outbound port performs 
      no translation, yet the FR Port has the outboundFrameMediaType 
      attribute set to ethernetConv which results in the frame being translated 
      into Ethernet format from Token Ring format before Frame Relay does 
      its encapsulation and transmits over the FR port."
   DEFVAL     { unaltered }
::= { vrPpTbsgProvEntry 6 }

vrPpTbsgTbProvTable OBJECT-TYPE
   SYNTAX     SEQUENCE OF VrPpTbsgTbProvEntry
   ACCESS     not-accessible
   STATUS     mandatory
   DESCRIPTION
     "This group houses all the port specific provisionable attributes that 
      belong to the Tb group. The Tb group is only applicable bridge port 
      types that operate in the TB mode. These attributes in part influence the 
      working of a bridge port operating in the TB mode."
::= { vrPpTbsg 11 }

vrPpTbsgTbProvEntry OBJECT-TYPE
   SYNTAX     VrPpTbsgTbProvEntry
   ACCESS     not-accessible
   STATUS     mandatory
   DESCRIPTION
     "An entry in the vrPpTbsgTbProvTable."
   INDEX {
      vrIndex,
      vrPpIndex,
      vrPpTbsgIndex }
::= { vrPpTbsgTbProvTable 1 }

VrPpTbsgTbProvEntry ::= SEQUENCE {
   vrPpTbsgSecureOption
      INTEGER }

vrPpTbsgSecureOption OBJECT-TYPE
   SYNTAX     INTEGER  {
                 disabled(0),
                 enabled(1) }
   ACCESS     read-write
   STATUS     mandatory
   DESCRIPTION
     "This attribute specifies whether the port secure feature is enabled. The 
      secure feature, if enabled causes the following things to happen:
      a) disallows dynamic learning,
      b) disallows frames to be forwarded that do not satisfy the following 
      condition: the mac address of the source should be found in the 
      forwarding table and the destination mac address of the frame should 
      also be found in the forwarding table. In addition to this, the port the 
      frame was received on should figure as the in port, given the destination 
      mac address found in the frame. 
      c) disallows frames to be forwarded if the allowed to go port map for the 
      destination mac address is empty. 
      This feature in effect allows the user to choose the hosts that can 
      generate traffic and the hosts that can receive traffic through this bridge 
      unit."
   DEFVAL     { disabled }
::= { vrPpTbsgTbProvEntry 1 }

vrPpTbsgStpProvTable OBJECT-TYPE
   SYNTAX     SEQUENCE OF VrPpTbsgStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { vrPpTbsg 12 }

vrPpTbsgStpProvEntry OBJECT-TYPE
   SYNTAX     VrPpTbsgStpProvEntry
   ACCESS     not-accessible
   STATUS     mandatory
   DESCRIPTION
     "An entry in the vrPpTbsgStpProvTable."
   INDEX {
      vrIndex,
      vrPpIndex,
      vrPpTbsgIndex }
::= { vrPpTbsgStpProvTable 1 }

VrPpTbsgStpProvEntry ::= SEQUENCE {
   vrPpTbsgAdminStatus
      INTEGER,
   vrPpTbsgPortStateStpControl
      INTEGER,
   vrPpTbsgStpTypeProv
      INTEGER,
   vrPpTbsgPortPriority
      Unsigned32,
   vrPpTbsgPathCost
      Unsigned32,
   vrPpTbsgPathCostMethod
      INTEGER }

vrPpTbsgAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { vrPpTbsgStpProvEntry 1 }

vrPpTbsgPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { vrPpTbsgStpProvEntry 2 }

vrPpTbsgStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { vrPpTbsgStpProvEntry 3 }

vrPpTbsgPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { vrPpTbsgStpProvEntry 4 }

vrPpTbsgPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { vrPpTbsgStpProvEntry 5 }

vrPpTbsgPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { vrPpTbsgStpProvEntry 6 }

vrPpTbsgDIProvTable OBJECT-TYPE
   SYNTAX     SEQUENCE OF VrPpTbsgDIProvEntry
   ACCESS     not-accessible
   STATUS     mandatory
   DESCRIPTION
     "This group houses all the provisionable, domain specific attributes for a 
      non-encapsulating bridge port."
::= { vrPpTbsg 13 }

vrPpTbsgDIProvEntry OBJECT-TYPE
   SYNTAX     VrPpTbsgDIProvEntry
   ACCESS     not-accessible
   STATUS     mandatory
   DESCRIPTION
     "An entry in the vrPpTbsgDIProvTable."
   INDEX {
      vrIndex,
      vrPpIndex,
      vrPpTbsgIndex }
::= { vrPpTbsgDIProvTable 1 }

VrPpTbsgDIProvEntry ::= SEQUENCE {
   vrPpTbsgDomainNum
      Unsigned32,
   vrPpTbsgPreserveDomain
      INTEGER }

vrPpTbsgDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { vrPpTbsgDIProvEntry 1 }

vrPpTbsgPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { vrPpTbsgDIProvEntry 2 }

vrPpTbsgStateTable OBJECT-TYPE
   SYNTAX     SEQUENCE OF VrPpTbsgStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpTbsg 14 }

vrPpTbsgStateEntry OBJECT-TYPE
   SYNTAX     VrPpTbsgStateEntry
   ACCESS     not-accessible
   STATUS     mandatory
   DESCRIPTION
     "An entry in the vrPpTbsgStateTable."
   INDEX {
      vrIndex,
      vrPpIndex,
      vrPpTbsgIndex }
::= { vrPpTbsgStateTable 1 }

VrPpTbsgStateEntry ::= SEQUENCE {
   vrPpTbsgAdminState
      INTEGER,
   vrPpTbsgOperationalState
      INTEGER,
   vrPpTbsgUsageState
      INTEGER }

vrPpTbsgAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpTbsgStateEntry 1 }

vrPpTbsgOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpTbsgStateEntry 2 }

vrPpTbsgUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpTbsgStateEntry 3 }

vrPpTbsgOperStatusTable OBJECT-TYPE
   SYNTAX     SEQUENCE OF VrPpTbsgOperStatusEntry
   ACCESS     not-accessible
   STATUS     mandatory
   DESCRIPTION
     "This group includes the Operational Status attribute. This attribute 
      defines the current operational state of this component."
::= { vrPpTbsg 15 }

vrPpTbsgOperStatusEntry OBJECT-TYPE
   SYNTAX     VrPpTbsgOperStatusEntry
   ACCESS     not-accessible
   STATUS     mandatory
   DESCRIPTION
     "An entry in the vrPpTbsgOperStatusTable."
   INDEX {
      vrIndex,
      vrPpIndex,
      vrPpTbsgIndex }
::= { vrPpTbsgOperStatusTable 1 }

VrPpTbsgOperStatusEntry ::= SEQUENCE {
   vrPpTbsgSnmpOperStatus
      INTEGER }

vrPpTbsgSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpTbsgOperStatusEntry 1 }

vrPpTbsgOperTable OBJECT-TYPE
   SYNTAX     SEQUENCE OF VrPpTbsgOperEntry
   ACCESS     not-accessible
   STATUS     mandatory
   DESCRIPTION
     "This group houses all the operational attributes belonging to the base 
      group. The base group of attributes is applicable to all types of bridge 
      ports and represent the common factor between them. These attributes in 
      part, reflect the state of a bridge port."
::= { vrPpTbsg 16 }

vrPpTbsgOperEntry OBJECT-TYPE
   SYNTAX     VrPpTbsgOperEntry
   ACCESS     not-accessible
   STATUS     mandatory
   DESCRIPTION
     "An entry in the vrPpTbsgOperTable."
   INDEX {
      vrIndex,
      vrPpIndex,
      vrPpTbsgIndex }
::= { vrPpTbsgOperTable 1 }

VrPpTbsgOperEntry ::= SEQUENCE {
   vrPpTbsgPortName
      AsciiString,
   vrPpTbsgUpTime
      Unsigned32,
   vrPpTbsgDownTime
      Unsigned32,
   vrPpTbsgBridgingMode
      INTEGER,
   vrPpTbsgBridgePortConfig
      INTEGER,
   vrPpTbsgBridgePortType
      INTEGER,
   vrPpTbsgIfIndex
      InterfaceIndex,
   vrPpTbsgDelayExceededDiscards
      Counter32,
   vrPpTbsgMtuExceededDiscards
      Counter32 }

vrPpTbsgPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { vrPpTbsgOperEntry 1 }

vrPpTbsgUpTime OBJECT-TYPE
   SYNTAX     Unsigned32 (0..4294967295)
   ACCESS     read-only
   STATUS     mandatory
   DESCRIPTION
     "This attribute specifies the accumulated up time of this bridge port since 
      the last reset occurred."
   DEFVAL     { 0 }
::= { vrPpTbsgOperEntry 3 }

vrPpTbsgDownTime OBJECT-TYPE
   SYNTAX     Unsigned32 (0..4294967295)
   ACCESS     read-only
   STATUS     mandatory
   DESCRIPTION
     "This attribute specifies the accumulated down time of this bridge port 
      since the last reset occurred."
   DEFVAL     { 0 }
::= { vrPpTbsgOperEntry 4 }

vrPpTbsgBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { vrPpTbsgOperEntry 5 }

vrPpTbsgBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { vrPpTbsgOperEntry 6 }

vrPpTbsgBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { vrPpTbsgOperEntry 7 }

vrPpTbsgIfIndex OBJECT-TYPE
   SYNTAX     InterfaceIndex (1..65535)
   ACCESS     read-only
   STATUS     mandatory
   DESCRIPTION
     "This attribute specifies the index into the Interface Table where in 
      information about the media interface corresponding to the bridge port is 
      maintained."
::= { vrPpTbsgOperEntry 8 }

vrPpTbsgDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { vrPpTbsgOperEntry 10 }

vrPpTbsgMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { vrPpTbsgOperEntry 11 }

vrPpTbsgTbOperTable OBJECT-TYPE
   SYNTAX     SEQUENCE OF VrPpTbsgTbOperEntry
   ACCESS     not-accessible
   STATUS     mandatory
   DESCRIPTION
     "This group houses all the port specific operational attributes that belong 
      to the Tb group. This group also houses all the port specific statistical 
      attributes that belong to the Tb group. The Tb group is only applicable 
      bridge port types that operate in the TB mode. These attributes reflect 
      the state of a bridge port operating in the TB mode"
::= { vrPpTbsg 17 }

vrPpTbsgTbOperEntry OBJECT-TYPE
   SYNTAX     VrPpTbsgTbOperEntry
   ACCESS     not-accessible
   STATUS     mandatory
   DESCRIPTION
     "An entry in the vrPpTbsgTbOperTable."
   INDEX {
      vrIndex,
      vrPpIndex,
      vrPpTbsgIndex }
::= { vrPpTbsgTbOperTable 1 }

VrPpTbsgTbOperEntry ::= SEQUENCE {
   vrPpTbsgMaxInfo
      Unsigned32,
   vrPpTbsgBadVerifyDiscards
      Counter32,
   vrPpTbsgUnicastNoMatches
      Counter32,
   vrPpTbsgStaticEntryDiscards
      Counter32,
   vrPpTbsgDynamicEntryDiscards
      Counter32,
   vrPpTbsgLearningDiscards
      Counter32,
   vrPpTbsgInDiscards
      Counter32,
   vrPpTbsgInFrames
      Counter32,
   vrPpTbsgOutFrames
      Counter32 }

vrPpTbsgMaxInfo OBJECT-TYPE
   SYNTAX     Unsigned32 (0..4294967295)
   ACCESS     read-only
   STATUS     mandatory
   DESCRIPTION
     "This attribute specifies the maximum size of the information field in a 
      TB frame. This excludes the header field."
   DEFVAL     { 0 }
::= { vrPpTbsgTbOperEntry 2 }

vrPpTbsgBadVerifyDiscards OBJECT-TYPE
   SYNTAX     Counter32 
   ACCESS     read-only
   STATUS     mandatory
   DESCRIPTION
     "This attribute is indicative of the number of incoming frames that were 
      discarded because:
      a) the value of the secureOption attribute was set to on and 
      b) it is not allowed to receive frames originating from the mac address 
      found in the source address field of the frame (source mac address look 
      up in the forwarding table failed.) on this bridge port.
      c) for the destination mac address found in the frame, the port the frame 
      was received on does not appear as in port in the corresponding static 
      table entry.
      Permission to receive frames from a mac address is granted via the static 
      table entries.
      This attribute, badVerifyDiscards, is directly influenced by:
      1. secureOption and 
      2. the static table entries.
      This counter wraps around its maximum value of 4294967295."
::= { vrPpTbsgTbOperEntry 3 }

vrPpTbsgUnicastNoMatches OBJECT-TYPE
   SYNTAX     Counter32 
   ACCESS     read-only
   STATUS     mandatory
   DESCRIPTION
     "This attribute is indicative of the number frames discarded because the 
      MAC address found in the destination field did not match the local MAC 
      address of the bridge port. This counter is only applicable for the 
      protocols that are being routed currently.This counter wraps around its 
      maximum value of 4294967295."
::= { vrPpTbsgTbOperEntry 4 }

vrPpTbsgStaticEntryDiscards OBJECT-TYPE
   SYNTAX     Counter32 
   ACCESS     read-only
   STATUS     mandatory
   DESCRIPTION
     "This attribute is indicative of the number of frames that were discarded 
      because of the following two reasons: 
      a) there was no entry for the 'allowed to go' field in the static table 
      entry, where the input port is this bridge port.
      b) for spanning tree bpdus that are locally processed.
      This counter wraps around its maximum value of 4294967295.
      It might prove useful to check the static table entry corresponding to the 
      bridge port in question, if this counter consistently displays a high value.
      Ideally this counter should be as low as possible."
::= { vrPpTbsgTbOperEntry 5 }

vrPpTbsgDynamicEntryDiscards OBJECT-TYPE
   SYNTAX     Counter32 
   ACCESS     read-only
   STATUS     mandatory
   DESCRIPTION
     "This attribute is indicative of the number of incoming frames that 
      a) were discarded because of the fact that the bridge port, the frame is to 
      go out of matches the bridge port it came in from or 
      b) if the stp port state of the out port is not forwarding. 
      This counter wraps around its maximum value of 4294967295."
::= { vrPpTbsgTbOperEntry 6 }

vrPpTbsgLearningDiscards OBJECT-TYPE
   SYNTAX     Counter32 
   ACCESS     read-only
   STATUS     mandatory
   DESCRIPTION
     "This attribute is indicative of the number of frames that were discarded 
      while this bridge port was in a state other than the forwarding state. 
      While in learning state the frame is discarded after the information from 
      its header is learnt. This counter wraps around its maximum value of 
      4294967295."
::= { vrPpTbsgTbOperEntry 7 }

vrPpTbsgInDiscards OBJECT-TYPE
   SYNTAX     Counter32 
   ACCESS     read-only
   STATUS     mandatory
   DESCRIPTION
     "This attribute is indicative of the number of frames that were received by 
      this bridge port and were discarded by the forwarding process. This 
      includes frames that could have been discarded due to filtering. A 
      repidly increasing value for this attribute could indicate a shrtage of 
      resource in terms of memory needed to process the incoming frames. 
      More memory can be provisioned through the VirtualRouter's memory 
      manager."
::= { vrPpTbsgTbOperEntry 8 }

vrPpTbsgInFrames OBJECT-TYPE
   SYNTAX     Counter32 
   ACCESS     read-only
   STATUS     mandatory
   DESCRIPTION
     "This attribute is indicative of the number of frames that have been 
      received by this port from its segment. Note that a frame received on this 
      bridge port is counted if and only if it can be processed by the bridge 
      logic contained in this bridge unit, a protocol that can be processed by 
      the bridge logic. This counter wraps around its maximum value of 
      4294967295."
::= { vrPpTbsgTbOperEntry 9 }

vrPpTbsgOutFrames OBJECT-TYPE
   SYNTAX     Counter32 
   ACCESS     read-only
   STATUS     mandatory
   DESCRIPTION
     "This attribute is indicative of the number of frames that have been 
      transmitted out this bridge port. Note that frame transmitted out this 
      bridge port is counted if and only if it is for a protocol being processed 
      by the bridge unit. This also includes management frames.This counter 
      wraps around its maximum value of 4294967295."
::= { vrPpTbsgTbOperEntry 10 }

vrPpTbsgStpOperTable OBJECT-TYPE
   SYNTAX     SEQUENCE OF VrPpTbsgStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { vrPpTbsg 18 }

vrPpTbsgStpOperEntry OBJECT-TYPE
   SYNTAX     VrPpTbsgStpOperEntry
   ACCESS     not-accessible
   STATUS     mandatory
   DESCRIPTION
     "An entry in the vrPpTbsgStpOperTable."
   INDEX {
      vrIndex,
      vrPpIndex,
      vrPpTbsgIndex }
::= { vrPpTbsgStpOperTable 1 }

VrPpTbsgStpOperEntry ::= SEQUENCE {
   vrPpTbsgStpPortState
      INTEGER,
   vrPpTbsgStpTypeOper
      INTEGER,
   vrPpTbsgDesignatedCost
      Unsigned32,
   vrPpTbsgPathCostOper
      Unsigned32,
   vrPpTbsgDesignatedBridge
      BridgeId,
   vrPpTbsgDesignatedPort
      Hex,
   vrPpTbsgForwardTransitions
      Counter32,
   vrPpTbsgBlockingDiscards
      Counter32,
   vrPpTbsgDesignatedRoot
      BridgeId }

vrPpTbsgStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { vrPpTbsgStpOperEntry 2 }

vrPpTbsgStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { vrPpTbsgStpOperEntry 3 }

vrPpTbsgDesignatedCost OBJECT-TYPE
   SYNTAX     Unsigned32 (0..4294967295)
   ACCESS     read-only
   STATUS     mandatory
   DESCRIPTION
     "This attribute specifies the path cost of the designated port of the lan 
      segment connected to the port."
::= { vrPpTbsgStpOperEntry 4 }

vrPpTbsgPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { vrPpTbsgStpOperEntry 5 }

vrPpTbsgDesignatedBridge OBJECT-TYPE
   SYNTAX     BridgeId (SIZE (8))
   ACCESS     read-only
   STATUS     mandatory
   DESCRIPTION
     "This attribute specifies the identifier of the bridge that this port considers 
      to be the designated bridge."
::= { vrPpTbsgStpOperEntry 6 }

vrPpTbsgDesignatedPort OBJECT-TYPE
   SYNTAX     Hex (0..65535)
   ACCESS     read-only
   STATUS     mandatory
   DESCRIPTION
     "This attribute specifies the port identifier of the port on the designated 
      bridge, attached to the same lan as this port is attached to."
::= { vrPpTbsgStpOperEntry 7 }

vrPpTbsgForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { vrPpTbsgStpOperEntry 8 }

vrPpTbsgBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { vrPpTbsgStpOperEntry 9 }

vrPpTbsgDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { vrPpTbsgStpOperEntry 10 }

vrPpTbsgStatsTable OBJECT-TYPE
   SYNTAX     SEQUENCE OF VrPpTbsgStatsEntry
   ACCESS     not-accessible
   STATUS     mandatory
   DESCRIPTION
     "This group houses all the statistical attributes applicable to all types of 
      bridge ports and represents the common factor between them. These 
      attributes in part reflect the state of the bridge port."
::= { vrPpTbsg 19 }

vrPpTbsgStatsEntry OBJECT-TYPE
   SYNTAX     VrPpTbsgStatsEntry
   ACCESS     not-accessible
   STATUS     mandatory
   DESCRIPTION
     "An entry in the vrPpTbsgStatsTable."
   INDEX {
      vrIndex,
      vrPpIndex,
      vrPpTbsgIndex }
::= { vrPpTbsgStatsTable 1 }

VrPpTbsgStatsEntry ::= SEQUENCE {
   vrPpTbsgBadAbstractDiscards
      Counter32,
   vrPpTbsgTinygramFramesIn
      Counter32,
   vrPpTbsgTinygramFramesOut
      Counter32,
   vrPpTbsgInFilterDiscards
      Counter32,
   vrPpTbsgOutFilterDiscards
      Counter32 }

vrPpTbsgBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { vrPpTbsgStatsEntry 1 }

vrPpTbsgTinygramFramesIn OBJECT-TYPE
   SYNTAX     Counter32 
   ACCESS     read-only
   STATUS     mandatory
   DESCRIPTION
     "This attribute is indicative of the number of frames received on this 
      bridge port that used the tinygram compression scheme."
::= { vrPpTbsgStatsEntry 2 }

vrPpTbsgTinygramFramesOut OBJECT-TYPE
   SYNTAX     Counter32 
   ACCESS     read-only
   STATUS     mandatory
   DESCRIPTION
     "This attribute is indicative of the number of frames transmitted out this 
      bridge port that used the tinygram compression scheme."
::= { vrPpTbsgStatsEntry 3 }

vrPpTbsgInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { vrPpTbsgStatsEntry 4 }

vrPpTbsgOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { vrPpTbsgStatsEntry 5 }


-- Vr/<string> Pp/<string> ClusterSrBridgePort
-- This component represents the functionality called Cluster Bridging. 
-- Cluster Bridging allows for MAC frames, carrying packets belonging a 
-- certain network protocol, to be bridged and routed at the same time. 
-- Also, it provides for a convenient way to manage the entire cluster of 
-- LANs, using a single attachment point to the cluster of LANs, the 
-- Cluster Bridge Port. To realize these features, the network protocol(s) 
-- should also be provisioned on same port as the Cluster Bridge Port. 
-- ClusterSrBridgePort represents a cluster of Sr LANs. 

vrPpSrcl OBJECT IDENTIFIER ::= { vrPp 14 }



vrPpSrclRowStatusTable OBJECT-TYPE
   SYNTAX     SEQUENCE OF VrPpSrclRowStatusEntry
   ACCESS     not-accessible
   STATUS     mandatory
   DESCRIPTION
     "This entry controls the addition and deletion of 
      vrPpSrcl components."
::= { vrPpSrcl 1 }

vrPpSrclRowStatusEntry OBJECT-TYPE
   SYNTAX     VrPpSrclRowStatusEntry
   ACCESS     not-accessible
   STATUS     mandatory
   DESCRIPTION
     "A single entry in the table represents a single 
      vrPpSrcl component."
   INDEX {
      vrIndex,
      vrPpIndex,
      vrPpSrclIndex }
::= { vrPpSrclRowStatusTable 1 }

VrPpSrclRowStatusEntry ::= SEQUENCE {
   vrPpSrclRowStatus
      RowStatus,
   vrPpSrclComponentName
      DisplayString,
   vrPpSrclStorageType
      StorageType,
   vrPpSrclIndex
      NonReplicated }

vrPpSrclRowStatus OBJECT-TYPE
   SYNTAX     RowStatus 
   ACCESS     read-write
   STATUS     mandatory
   DESCRIPTION
     "This variable is used as the basis for SNMP naming of
      vrPpSrcl components.
      These components can be added and deleted."
::= { vrPpSrclRowStatusEntry 1 }

vrPpSrclComponentName OBJECT-TYPE
   SYNTAX     DisplayString 
   ACCESS     read-only
   STATUS     mandatory
   DESCRIPTION
     "This variable provides the component's string name for
      use with the ASCII Console Interface"
::= { vrPpSrclRowStatusEntry 2 }

vrPpSrclStorageType OBJECT-TYPE
   SYNTAX     StorageType 
   ACCESS     read-only
   STATUS     mandatory
   DESCRIPTION
     "This variable represents the storage type value for the
      vrPpSrcl tables."
::= { vrPpSrclRowStatusEntry 4 }

vrPpSrclIndex OBJECT-TYPE
   SYNTAX     NonReplicated 
   ACCESS     not-accessible
   STATUS     mandatory
   DESCRIPTION
     "This variable represents the index for the vrPpSrcl tables."
::= { vrPpSrclRowStatusEntry 10 }

vrPpSrclProvTable OBJECT-TYPE
   SYNTAX     SEQUENCE OF VrPpSrclProvEntry
   ACCESS     not-accessible
   STATUS     mandatory
   DESCRIPTION
     "This group houses all the provisionable attributes that belong to the this 
      group. This group of attributes is applicable to all types of bridge ports 
      and represent the common factor between them. These attributes 
      influence the working of a bridge port."
::= { vrPpSrcl 10 }

vrPpSrclProvEntry OBJECT-TYPE
   SYNTAX     VrPpSrclProvEntry
   ACCESS     not-accessible
   STATUS     mandatory
   DESCRIPTION
     "An entry in the vrPpSrclProvTable."
   INDEX {
      vrIndex,
      vrPpIndex,
      vrPpSrclIndex }
::= { vrPpSrclProvTable 1 }

VrPpSrclProvEntry ::= SEQUENCE {
   vrPpSrclTranslateIpx
      INTEGER,
   vrPpSrclFragmentIp
      INTEGER,
   vrPpSrclServiceClass
      INTEGER,
   vrPpSrclConvertArpMacAddress
      INTEGER,
   vrPpSrclPortNum
      Unsigned32,
   vrPpSrclOutboundFrameMediaType
      INTEGER }

vrPpSrclTranslateIpx OBJECT-TYPE
   SYNTAX     INTEGER  {
                 off(0),
                 ieee8023(1),
                 ethernet(2),
                 snap(3),
                 sap(4) }
   ACCESS     read-write
   STATUS     mandatory
   DESCRIPTION
     "This attribute specifies the type of translation to be performed on frames 
      carrying IPX packets. Ethernet frames carrying IPX payload could be 
      translated to IEEE 802.3 frames (with the same IPX payload) or vice-
      versa. The main reason to do so is to allow the bridge unit to 
      consistently forward one type of frames carrying IPX packets. 
      Translations can be turned off altogether in which case the IPX frames 
      will pass through the bridge unit unchanged."
   DEFVAL     { off }
::= { vrPpSrclProvEntry 1 }

vrPpSrclFragmentIp OBJECT-TYPE
   SYNTAX     INTEGER  {
                 off(0),
                 on(1) }
   ACCESS     read-write
   STATUS     mandatory
   DESCRIPTION
     "This attribute specifies if or not outbound frames carrying IP datagrams 
      should be fragmented to conform to message transfer unit (mtu) sizes 
      dictated by the media."
   DEFVAL     { off }
::= { vrPpSrclProvEntry 2 }

vrPpSrclServiceClass OBJECT-TYPE
   SYNTAX     INTEGER  {
                 ordered(0),
                 notOrdered(1) }
   ACCESS     read-write
   STATUS     mandatory
   DESCRIPTION
     "This attribute specifies if the frames should be ordered or not before they 
      are transmitted through a bridge port. 
      If this attribute has a value of ordered the received frames are ordered as 
      in the original message, before they are transmitted out through a bridge 
      port. 
      If it has a value of notOrdered, received then frames pass through the 
      bridge unit in the order they are received. This feature can be used over 
      multiple telecommunication links to increase data flow.
      Please note that this attribute only affects link protocols and is 
      ineffective with lan media."
   DEFVAL     { notOrdered }
::= { vrPpSrclProvEntry 3 }

vrPpSrclConvertArpMacAddress OBJECT-TYPE
   SYNTAX     INTEGER  {
                 off(0),
                 on(1) }
   ACCESS     read-write
   STATUS     mandatory
   DESCRIPTION
     "This attribute is indicative of the state of the MAC address format 
      conversion process for ARP/RARP frames. The MAC addresses may be 
      translated if need be from a canonical format to a non-canonical format, 
      based on the needs of the associated media.
      If this attribute is set to a value of on then all Mac addresses will 
      converted if need be to suit the format of mac address, the outgoing 
      media will support. 
      If this attribute is set to a value of off no such conversion takes place."
   DEFVAL     { off }
::= { vrPpSrclProvEntry 4 }

vrPpSrclPortNum OBJECT-TYPE
   SYNTAX     Unsigned32 (0..255)
   ACCESS     read-only
   STATUS     mandatory
   DESCRIPTION
     "This attribute is indicative of the unique number assigned to the bridge 
      port. It is used for SNMP management of this bridge port and in 
      spanning tree as an identifier this bridge port.
      Notes regarding portNum:
      
      Escape routines exist for initializing, copying, and deleting port 
      numbers. This is necessary because SNMP requires a unique port 
      instance identifier. The initPortNum escape routine sets the port number 
      to a value in the range 1-255 for this purpose. The setCopiedPortNum 
      escape routine exists to maintain the uniqueness of the port number in 
      cases when one port is copied to another. When a bridge port is deleted, 
      the releasePortNum escape routine places the port number being 
      released into a pending deletion state. This is because the port number 
      cannot be re-allocated until the port is truely deleted in the current view. 
      This is necessary since there is no guarantee of order when processing 
      changes to multiple protocol ports so without the pending deletion state, 
      the same port number could be temporarily assigned to two ports for a 
      short period of time.
      
      The portNum is set as component critical since bridging also uses the 
      port number as a key for indexing into its data structures. If a port is 
      deleted then re-added under the same protocol port, CAS treats the 
      change as a SET to the portNum attribute."
   DEFVAL     { 0 }
::= { vrPpSrclProvEntry 5 }

vrPpSrclOutboundFrameMediaType OBJECT-TYPE
   SYNTAX     INTEGER  {
                 unaltered(1),
                 ethernetConv(2) }
   ACCESS     read-write
   STATUS     mandatory
   DESCRIPTION
     "This attribute specifies the media type the frame must be in before it is 
      to be forwarded over the outbound supported WAN Bridge Protocol 
      Port. The attribute only applies to outbound Bridge Protocol Port.
      
      For supported bridge ports, if the attribute value remains set to the 
      default value of unaltered then there will be no frame conversion. When 
      the value is set to the value ethernetConv then all frames being 
      forwarded out the outbound WAN Port will be converted to ethernet 
      before forwarding takes place. The only outbound WAN medias that 
      currently support conversion are: FR (Frame Relay) and VNS. All other 
      medias will fail the Bridge Port semantic check when attempts are made 
      to alter this attribute. 
      
      The following is an example of what the user may be able to do. Frames 
      originating from a Token Ring are to be flooded out onto another Token 
      Ring and a Frame Relay Port. The token ring Outbound port performs 
      no translation, yet the FR Port has the outboundFrameMediaType 
      attribute set to ethernetConv which results in the frame being translated 
      into Ethernet format from Token Ring format before Frame Relay does 
      its encapsulation and transmits over the FR port."
   DEFVAL     { unaltered }
::= { vrPpSrclProvEntry 6 }

vrPpSrclStpProvTable OBJECT-TYPE
   SYNTAX     SEQUENCE OF VrPpSrclStpProvEntry
   ACCESS     not-accessible
   STATUS     mandatory
   DESCRIPTION
     "This group houses all the port specific provisionable attributes that 
      belong to the Stp group. The Stp group is applicable to all the bridge 
      ports that participate in the spanning tree protocol. These attributes 
      influence the participation of the bridge port in the spanning tree 
      protocol."
::= { vrPpSrcl 12 }

vrPpSrclStpProvEntry OBJECT-TYPE
   SYNTAX     VrPpSrclStpProvEntry
   ACCESS     not-accessible
   STATUS     mandatory
   DESCRIPTION
     "An entry in the vrPpSrclStpProvTable."
   INDEX {
      vrIndex,
      vrPpIndex,
      vrPpSrclIndex }
::= { vrPpSrclStpProvTable 1 }

VrPpSrclStpProvEntry ::= SEQUENCE {
   vrPpSrclAdminStatus
      INTEGER,
   vrPpSrclPortStateStpControl
      INTEGER,
   vrPpSrclStpTypeProv
      INTEGER,
   vrPpSrclPortPriority
      Unsigned32,
   vrPpSrclPathCost
      Unsigned32,
   vrPpSrclPathCostMethod
      INTEGER }

vrPpSrclAdminStatus OBJECT-TYPE
   SYNTAX     INTEGER  {
                 up(1),
                 down(2) }
   ACCESS     read-write
   STATUS     mandatory
   DESCRIPTION
     "This attribute defines the current administrative state for this component. 
      enabled indicates that the component is available for operation. disabled 
      indicates the component is unavailable for operation."
   DEFVAL     { up }
::= { vrPpSrclStpProvEntry 1 }

vrPpSrclPortStateStpControl OBJECT-TYPE
   SYNTAX     INTEGER  {
                 off(0),
                 on(1) }
   ACCESS     read-write
   STATUS     mandatory
   DESCRIPTION
     "This attribute specifies whether or not spanning tree protocol state for 
      this bridge port is controlled by the spanning tree protocol. In essence it 
      indicates the participation of this bridge port in the spanning tree 
      protocol, by accepting and acting on received bridge protocol data units 
      and by sending out the same. 
      on signifies that this bridge port's spanning tree port state is controlled 
      by the spanning tree protocol. 
      A value of off signifies that the spanning tree port state of this bridge 
      port is unaffected by the spanning tree protocol. This in effect puts the 
      bridge port out of reach of the spanning tree protocol and in the 
      forwarding state. Care should be taken while assigning a value of off to 
      this attribute, as this might cause network loops. Please do not set this 
      attribute to off unless you are absolutely sure about the effect of such an 
      action on your network topology."
   DEFVAL     { on }
::= { vrPpSrclStpProvEntry 2 }

vrPpSrclStpTypeProv OBJECT-TYPE
   SYNTAX     INTEGER  {
                 dec(2),
                 ieee8021(3) }
   ACCESS     read-write
   STATUS     mandatory
   DESCRIPTION
     "This attribute specifies the type of spanning tree protocol the port is 
      participating in. A bridge port could participate in either the ieee8021 
      spanning tree protocol or the dec spanning tree protocol. If the value of 
      the attribute protocolSpec in the SpanningTreeProtocol component, 
      provisioned under the TransparentBridge component is in conflict with 
      the value of this attribute, the value of the protocolSpec attribute will 
      prevail. Prevailing stp type is reflected in the value of the attribute 
      stpTypeOper."
   DEFVAL     { ieee8021 }
::= { vrPpSrclStpProvEntry 3 }

vrPpSrclPortPriority OBJECT-TYPE
   SYNTAX     Unsigned32 (0..65535)
   ACCESS     read-write
   STATUS     mandatory
   DESCRIPTION
     "This attribute specifies the value for port priority, which is contained in 
      the first octet of the port identifier. Valid values are as follows:
      1) 0..255 for stp type DEC and 
      2) 0..65535 for stp type IEEE."
   DEFVAL     { 128 }
::= { vrPpSrclStpProvEntry 4 }

vrPpSrclPathCost OBJECT-TYPE
   SYNTAX     Unsigned32 (1..65535)
   ACCESS     read-write
   STATUS     mandatory
   DESCRIPTION
     "This attribute specifies the contribution of this port, to all the paths to the 
      root bridge that include this port. Please note that the value of the 
      attribute pathCostMethod is applied only when the value of the attribute 
      pathCostMethod is set to on and is ignored if otherwise."
   DEFVAL     { 10 }
::= { vrPpSrclStpProvEntry 5 }

vrPpSrclPathCostMethod OBJECT-TYPE
   SYNTAX     INTEGER  {
                 off(1),
                 dec(2),
                 ieee8021(3) }
   ACCESS     read-write
   STATUS     mandatory
   DESCRIPTION
     "This attribute specifies the method used by the bridging logic, to 
      calculate the path cost to the bridge considered to be the root bridge in 
      the spanning tree topology. This attribute should be set to off before 
      attempting to provision a value for pathCostProv."
   DEFVAL     { ieee8021 }
::= { vrPpSrclStpProvEntry 6 }

vrPpSrclDIProvTable OBJECT-TYPE
   SYNTAX     SEQUENCE OF VrPpSrclDIProvEntry
   ACCESS     not-accessible
   STATUS     mandatory
   DESCRIPTION
     "This group houses all the provisionable, domain specific attributes for a 
      non-encapsulating bridge port."
::= { vrPpSrcl 13 }

vrPpSrclDIProvEntry OBJECT-TYPE
   SYNTAX     VrPpSrclDIProvEntry
   ACCESS     not-accessible
   STATUS     mandatory
   DESCRIPTION
     "An entry in the vrPpSrclDIProvTable."
   INDEX {
      vrIndex,
      vrPpIndex,
      vrPpSrclIndex }
::= { vrPpSrclDIProvTable 1 }

VrPpSrclDIProvEntry ::= SEQUENCE {
   vrPpSrclDomainNum
      Unsigned32,
   vrPpSrclPreserveDomain
      INTEGER }

vrPpSrclDomainNum OBJECT-TYPE
   SYNTAX     Unsigned32 (1..4294967293)
   ACCESS     read-write
   STATUS     mandatory
   DESCRIPTION
     "This attribute specifies the domain number associated with this bridge 
      port. Domain numbers are used for confining frames to a domain. 
      Domain based filtering provides a complete segregation of traffic based 
      on domain number associated with frames. There can exist only sixteen 
      domains when a spanning tree is desired specific to each domain. When 
      there is only a single spanning tree spanning all the domains the 
      maximum number of domains possible are 4294967293.
      This attribute is of no relevance when associated with backbone bridge 
      port. Its value is ignored in such a situation."
   DEFVAL     { 1 }
::= { vrPpSrclDIProvEntry 1 }

vrPpSrclPreserveDomain OBJECT-TYPE
   SYNTAX     INTEGER  {
                 off(0),
                 on(1) }
   ACCESS     read-write
   STATUS     mandatory
   DESCRIPTION
     "This attribute specifies if the domain information should be preserved or 
      embedded in the frame header. This attribute applies only to backbone 
      ports and does not affect the access bridge ports. By setting this attribute 
      to a value of on, domain information could be preserved in frames being 
      tunnelled across the a backbone, so that this information can be 
      deciphered at the other end of the backbone tunnel. This preserves the 
      integrity of the domains thus preventing domain breaches while 
      tunnelling frames across backbone network. 
      If the value of this attribute is set to off then domain information is not 
      preserved in the header of the frames tunnelling through the backbone. 
      This eliminates the overhead incurred to preserve domain information 
      across the backbone while tunnelling frames across it.
      Preserve domain is relevant when used in conjunction with the following 
      media: FDDI, ATM MPE, Frame Relay and PPP. It is ignored when 
      used with other types of media."
::= { vrPpSrclDIProvEntry 2 }

vrPpSrclStateTable OBJECT-TYPE
   SYNTAX     SEQUENCE OF VrPpSrclStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpSrcl 14 }

vrPpSrclStateEntry OBJECT-TYPE
   SYNTAX     VrPpSrclStateEntry
   ACCESS     not-accessible
   STATUS     mandatory
   DESCRIPTION
     "An entry in the vrPpSrclStateTable."
   INDEX {
      vrIndex,
      vrPpIndex,
      vrPpSrclIndex }
::= { vrPpSrclStateTable 1 }

VrPpSrclStateEntry ::= SEQUENCE {
   vrPpSrclAdminState
      INTEGER,
   vrPpSrclOperationalState
      INTEGER,
   vrPpSrclUsageState
      INTEGER }

vrPpSrclAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpSrclStateEntry 1 }

vrPpSrclOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpSrclStateEntry 2 }

vrPpSrclUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpSrclStateEntry 3 }

vrPpSrclOperStatusTable OBJECT-TYPE
   SYNTAX     SEQUENCE OF VrPpSrclOperStatusEntry
   ACCESS     not-accessible
   STATUS     mandatory
   DESCRIPTION
     "This group includes the Operational Status attribute. This attribute 
      defines the current operational state of this component."
::= { vrPpSrcl 15 }

vrPpSrclOperStatusEntry OBJECT-TYPE
   SYNTAX     VrPpSrclOperStatusEntry
   ACCESS     not-accessible
   STATUS     mandatory
   DESCRIPTION
     "An entry in the vrPpSrclOperStatusTable."
   INDEX {
      vrIndex,
      vrPpIndex,
      vrPpSrclIndex }
::= { vrPpSrclOperStatusTable 1 }

VrPpSrclOperStatusEntry ::= SEQUENCE {
   vrPpSrclSnmpOperStatus
      INTEGER }

vrPpSrclSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpSrclOperStatusEntry 1 }

vrPpSrclOperTable OBJECT-TYPE
   SYNTAX     SEQUENCE OF VrPpSrclOperEntry
   ACCESS     not-accessible
   STATUS     mandatory
   DESCRIPTION
     "This group houses all the operational attributes belonging to the base 
      group. The base group of attributes is applicable to all types of bridge 
      ports and represent the common factor between them. These attributes in 
      part, reflect the state of a bridge port."
::= { vrPpSrcl 16 }

vrPpSrclOperEntry OBJECT-TYPE
   SYNTAX     VrPpSrclOperEntry
   ACCESS     not-accessible
   STATUS     mandatory
   DESCRIPTION
     "An entry in the vrPpSrclOperTable."
   INDEX {
      vrIndex,
      vrPpIndex,
      vrPpSrclIndex }
::= { vrPpSrclOperTable 1 }

VrPpSrclOperEntry ::= SEQUENCE {
   vrPpSrclPortName
      AsciiString,
   vrPpSrclUpTime
      Unsigned32,
   vrPpSrclDownTime
      Unsigned32,
   vrPpSrclBridgingMode
      INTEGER,
   vrPpSrclBridgePortConfig
      INTEGER,
   vrPpSrclBridgePortType
      INTEGER,
   vrPpSrclIfIndex
      InterfaceIndex,
   vrPpSrclDelayExceededDiscards
      Counter32,
   vrPpSrclMtuExceededDiscards
      Counter32 }

vrPpSrclPortName OBJECT-TYPE
   SYNTAX     AsciiString (SIZE (4..29))
   ACCESS     read-only
   STATUS     mandatory
   DESCRIPTION
     "The attribute portName is a string of the form 'BridgePortName-i', 
      where BridgePortName is the abbreviation of the corresponding bridge 
      port and i is the instance identifier of the ProtocolPort, the bridge port is 
      provisioned under. For example a TransparentBridgePort provisioned 
      under ProtocolPort/myport would have a name TBP-myport."
::= { vrPpSrclOperEntry 1 }

vrPpSrclUpTime OBJECT-TYPE
   SYNTAX     Unsigned32 (0..4294967295)
   ACCESS     read-only
   STATUS     mandatory
   DESCRIPTION
     "This attribute specifies the accumulated up time of this bridge port since 
      the last reset occurred."
   DEFVAL     { 0 }
::= { vrPpSrclOperEntry 3 }

vrPpSrclDownTime OBJECT-TYPE
   SYNTAX     Unsigned32 (0..4294967295)
   ACCESS     read-only
   STATUS     mandatory
   DESCRIPTION
     "This attribute specifies the accumulated down time of this bridge port 
      since the last reset occurred."
   DEFVAL     { 0 }
::= { vrPpSrclOperEntry 4 }

vrPpSrclBridgingMode OBJECT-TYPE
   SYNTAX     INTEGER  {
                 unknown(1),
                 tb(2),
                 sr(3),
                 srt(4) }
   ACCESS     read-only
   STATUS     mandatory
   DESCRIPTION
     "This attribute specifies the mode of bridging this port can support. It in 
      turn implies the format of frames, this bridge port can process and 
      forward."
::= { vrPpSrclOperEntry 5 }

vrPpSrclBridgePortConfig OBJECT-TYPE
   SYNTAX     INTEGER  {
                 access(1),
                 backbone(2) }
   ACCESS     read-only
   STATUS     mandatory
   DESCRIPTION
     "This attribute specifies the bridge port's configuration. It indicates if the 
      bridge port is operating as an access port or as a backbone port. An 
      access bridge port does not encapsulate a MAC frame and does not 
      preserve domain information in the encapsulation, whereas a backbone 
      bridge port encapsulates the MAC frame and optionally preserves 
      domain information in the encapsulated frame.A backbone bridge port 
      is typically used to transport frames across a high bandwidth backbone 
      network to another bridge unit for further processing/forwarding of the 
      frame."
::= { vrPpSrclOperEntry 6 }

vrPpSrclBridgePortType OBJECT-TYPE
   SYNTAX     INTEGER  {
                 ethernetBridgePort(0),
                 tokenRingBridgePort(1),
                 fddiBridgePort(2),
                 tokenBusBridgePort(3),
                 fddiEncapsulatingBridgePort(4),
                 vnsBridgePort(5),
                 frameRelayBridgePort(6),
                 pppBridgePort(7),
                 smdsBridgePort(8),
                 vcpBridgePort(9),
                 x25BridgePort(10),
                 srEncapSrBridgePort(11),
                 srEncapTbBridgePort(12),
                 sourceGateSrBridgePort(13),
                 sourceGateTbBridgePort(14),
                 srtbBridgePort(15),
                 tbsrBridgePort(16),
                 clusterSrBridgePort(17),
                 clusterTbBridgePort(18),
                 unknown(19),
                 atmMpeBridgePort(20),
                 snaDlrBridgePort(21),
                 lanEmulationClientEthernet(22) }
   ACCESS     read-only
   STATUS     mandatory
   DESCRIPTION
     "This attribute specifies the type of bridge port that was provisioned. It 
      takes into consideration the bridgingMode, bridgePortConfig and the 
      media the bridge port is linked to before branding a bridge port."
::= { vrPpSrclOperEntry 7 }

vrPpSrclIfIndex OBJECT-TYPE
   SYNTAX     InterfaceIndex (1..65535)
   ACCESS     read-only
   STATUS     mandatory
   DESCRIPTION
     "This attribute specifies the index into the Interface Table where in 
      information about the media interface corresponding to the bridge port is 
      maintained."
::= { vrPpSrclOperEntry 8 }

vrPpSrclDelayExceededDiscards OBJECT-TYPE
   SYNTAX     Counter32 
   ACCESS     read-only
   STATUS     mandatory
   DESCRIPTION
     "This attribute is indicative of the number of frames that were discarded 
      because the time taken to process these frames exceeded the transit 
      delay allowed for this bridge unit. This attribute is not supported by 
      bridging and will always have a value of 0."
::= { vrPpSrclOperEntry 10 }

vrPpSrclMtuExceededDiscards OBJECT-TYPE
   SYNTAX     Counter32 
   ACCESS     read-only
   STATUS     mandatory
   DESCRIPTION
     "This attribute is indicative of the number of frames discarded because 
      the size of the out bound frame exceeded the message transfer unit (mtu) 
      allowed for the bridge port. Note that this counter only refers to the 
      outbound frames for this bridge port. This counter wraps around its 
      maximum value of 4294967295.
      This counter is influenced by the attribute fragmentIp. This counter is 
      incremented when the a frame larger than the mtu allowed is 
      encountered and cannot be fragmented. If this counter is increasing 
      steadily, it might be useful to set the value of the attribute fragmentIp to 
      a value of on."
::= { vrPpSrclOperEntry 11 }

vrPpSrclStpOperTable OBJECT-TYPE
   SYNTAX     SEQUENCE OF VrPpSrclStpOperEntry
   ACCESS     not-accessible
   STATUS     mandatory
   DESCRIPTION
     "This group houses all the port specific operational attributes that belong 
      to the Stp group. The Stp group is applicable to all the bridge ports that 
      participate in the spanning tree protocol. These attributes reflect the state 
      of the bridge port's participation in the spanning tree protocol."
::= { vrPpSrcl 18 }

vrPpSrclStpOperEntry OBJECT-TYPE
   SYNTAX     VrPpSrclStpOperEntry
   ACCESS     not-accessible
   STATUS     mandatory
   DESCRIPTION
     "An entry in the vrPpSrclStpOperTable."
   INDEX {
      vrIndex,
      vrPpIndex,
      vrPpSrclIndex }
::= { vrPpSrclStpOperTable 1 }

VrPpSrclStpOperEntry ::= SEQUENCE {
   vrPpSrclStpPortState
      INTEGER,
   vrPpSrclStpTypeOper
      INTEGER,
   vrPpSrclDesignatedCost
      Unsigned32,
   vrPpSrclPathCostOper
      Unsigned32,
   vrPpSrclDesignatedBridge
      BridgeId,
   vrPpSrclDesignatedPort
      Hex,
   vrPpSrclForwardTransitions
      Counter32,
   vrPpSrclBlockingDiscards
      Counter32,
   vrPpSrclDesignatedRoot
      BridgeId }

vrPpSrclStpPortState OBJECT-TYPE
   SYNTAX     INTEGER  {
                 disabled(1),
                 blocking(2),
                 listening(3),
                 learning(4),
                 forwarding(5),
                 broken(6) }
   ACCESS     read-only
   STATUS     mandatory
   DESCRIPTION
     "This attribute specifies the spanning tree protocol state of the bridge 
      port."
   DEFVAL     { disabled }
::= { vrPpSrclStpOperEntry 2 }

vrPpSrclStpTypeOper OBJECT-TYPE
   SYNTAX     INTEGER  {
                 none(0),
                 dec(2),
                 ieee8021(3) }
   ACCESS     read-only
   STATUS     mandatory
   DESCRIPTION
     "This attribute specifies the type of spanning tree protocol the port is 
      participating in. A bridge port could participate in either the ieee8021 
      spanning tree protocol or the dec spanning tree protocol."
   DEFVAL     { ieee8021 }
::= { vrPpSrclStpOperEntry 3 }

vrPpSrclDesignatedCost OBJECT-TYPE
   SYNTAX     Unsigned32 (0..4294967295)
   ACCESS     read-only
   STATUS     mandatory
   DESCRIPTION
     "This attribute specifies the path cost of the designated port of the lan 
      segment connected to the port."
::= { vrPpSrclStpOperEntry 4 }

vrPpSrclPathCostOper OBJECT-TYPE
   SYNTAX     Unsigned32 (1..65535)
   ACCESS     read-only
   STATUS     mandatory
   DESCRIPTION
     "This attribute specifies the contribution of this port, to all the paths to the 
      root bridge that include this port. This attribute pathCostOper will track 
      the value of the attribute pathCostProv when the value of the attribute 
      pathCostMethod is set of off."
::= { vrPpSrclStpOperEntry 5 }

vrPpSrclDesignatedBridge OBJECT-TYPE
   SYNTAX     BridgeId (SIZE (8))
   ACCESS     read-only
   STATUS     mandatory
   DESCRIPTION
     "This attribute specifies the identifier of the bridge that this port considers 
      to be the designated bridge."
::= { vrPpSrclStpOperEntry 6 }

vrPpSrclDesignatedPort OBJECT-TYPE
   SYNTAX     Hex (0..65535)
   ACCESS     read-only
   STATUS     mandatory
   DESCRIPTION
     "This attribute specifies the port identifier of the port on the designated 
      bridge, attached to the same lan as this port is attached to."
::= { vrPpSrclStpOperEntry 7 }

vrPpSrclForwardTransitions OBJECT-TYPE
   SYNTAX     Counter32 
   ACCESS     read-only
   STATUS     mandatory
   DESCRIPTION
     "This attribute is indicative of the number of times this bridge port 
      transitioned from the learning state to the forwarding state. This 
      counter wraps around its maximum value of 4294967295.
      A rapidly increasing value might be indicative of an unstable spanning 
      tree topology."
::= { vrPpSrclStpOperEntry 8 }

vrPpSrclBlockingDiscards OBJECT-TYPE
   SYNTAX     Counter32 
   ACCESS     read-only
   STATUS     mandatory
   DESCRIPTION
     "This attribute is indicative of the number of incoming frames that were 
      discarded because the bridge port was in the blocking state. This counter 
      wraps around its maximum value of 4294967295."
::= { vrPpSrclStpOperEntry 9 }

vrPpSrclDesignatedRoot OBJECT-TYPE
   SYNTAX     BridgeId (SIZE (8))
   ACCESS     read-only
   STATUS     mandatory
   DESCRIPTION
     "This attribute specifies the bridge identifier of the bridge recorded as the 
      root bridge, in the configuration BPDUs sent out by the designated 
      bridge on the segment to which the port is attached."
::= { vrPpSrclStpOperEntry 10 }

vrPpSrclStatsTable OBJECT-TYPE
   SYNTAX     SEQUENCE OF VrPpSrclStatsEntry
   ACCESS     not-accessible
   STATUS     mandatory
   DESCRIPTION
     "This group houses all the statistical attributes applicable to all types of 
      bridge ports and represents the common factor between them. These 
      attributes in part reflect the state of the bridge port."
::= { vrPpSrcl 19 }

vrPpSrclStatsEntry OBJECT-TYPE
   SYNTAX     VrPpSrclStatsEntry
   ACCESS     not-accessible
   STATUS     mandatory
   DESCRIPTION
     "An entry in the vrPpSrclStatsTable."
   INDEX {
      vrIndex,
      vrPpIndex,
      vrPpSrclIndex }
::= { vrPpSrclStatsTable 1 }

VrPpSrclStatsEntry ::= SEQUENCE {
   vrPpSrclBadAbstractDiscards
      Counter32,
   vrPpSrclTinygramFramesIn
      Counter32,
   vrPpSrclTinygramFramesOut
      Counter32,
   vrPpSrclInFilterDiscards
      Counter32,
   vrPpSrclOutFilterDiscards
      Counter32 }

vrPpSrclBadAbstractDiscards OBJECT-TYPE
   SYNTAX     Counter32 
   ACCESS     read-only
   STATUS     mandatory
   DESCRIPTION
     "This attribute is indicative of the number of frames that were discarded 
      because the data that was abstracted, from frames coming in through this 
      bridge port, did not conform to the format expected by the bridge 
      logic.This counter wraps around its maximum value of 4294967295."
::= { vrPpSrclStatsEntry 1 }

vrPpSrclTinygramFramesIn OBJECT-TYPE
   SYNTAX     Counter32 
   ACCESS     read-only
   STATUS     mandatory
   DESCRIPTION
     "This attribute is indicative of the number of frames received on this 
      bridge port that used the tinygram compression scheme."
::= { vrPpSrclStatsEntry 2 }

vrPpSrclTinygramFramesOut OBJECT-TYPE
   SYNTAX     Counter32 
   ACCESS     read-only
   STATUS     mandatory
   DESCRIPTION
     "This attribute is indicative of the number of frames transmitted out this 
      bridge port that used the tinygram compression scheme."
::= { vrPpSrclStatsEntry 3 }

vrPpSrclInFilterDiscards OBJECT-TYPE
   SYNTAX     Counter32 
   ACCESS     read-only
   STATUS     mandatory
   DESCRIPTION
     "This attribute is indicative of the number of frames discarded at the in 
      filter point. This includes 
      a) frames discarded due to application of the filter defined with PCF for 
      the in filter point and
      b) the frames discarded due to domain based filtering at the in filter 
      point. This counter wraps around its maximum value of 4294967295."
::= { vrPpSrclStatsEntry 4 }

vrPpSrclOutFilterDiscards OBJECT-TYPE
   SYNTAX     Counter32 
   ACCESS     read-only
   STATUS     mandatory
   DESCRIPTION
     "This attribute is indicative of the number of frames discarded at the out 
      filter point. This includes:
      a) frames discarded due to application of the filter defined with PCF for 
      the out filter point and
      b) the frames discarded due to domain based filtering at the out filter 
      point. This counter wraps around its maximum value of 4294967295."
::= { vrPpSrclStatsEntry 5 }

vrPpSrclSrProvTable OBJECT-TYPE
   SYNTAX     SEQUENCE OF VrPpSrclSrProvEntry
   ACCESS     not-accessible
   STATUS     mandatory
   DESCRIPTION
     "This group contains all port specific, provisionable attributes associated 
      with SourceRouteBridge ports."
::= { vrPpSrcl 20 }

vrPpSrclSrProvEntry OBJECT-TYPE
   SYNTAX     VrPpSrclSrProvEntry
   ACCESS     not-accessible
   STATUS     mandatory
   DESCRIPTION
     "An entry in the vrPpSrclSrProvTable."
   INDEX {
      vrIndex,
      vrPpIndex,
      vrPpSrclIndex }
::= { vrPpSrclSrProvTable 1 }

VrPpSrclSrProvEntry ::= SEQUENCE {
   vrPpSrclHopCount
      Unsigned32,
   vrPpSrclExploreFrameTreatment
      INTEGER,
   vrPpSrclLanId
      Unsigned32,
   vrPpSrclInternalLanId
      Unsigned32,
   vrPpSrclBridgeNum
      Unsigned32,
   vrPpSrclLargestFrame
      Unsigned32,
   vrPpSrclSteSpanMode
      INTEGER,
   vrPpSrclAreRdLimit
      Unsigned32,
   vrPpSrclSteRdLimit
      Unsigned32 }

vrPpSrclHopCount OBJECT-TYPE
   SYNTAX     Unsigned32 (1..7)
   ACCESS     read-write
   STATUS     mandatory
   DESCRIPTION
     "This attribute specifies the maximum number of hops allowed in 
      Spanning Tree Explore and All Routes Explore frames. This value is one 
      less than the maximum number of route descriptors allowed in a source 
      route frame"
   DEFVAL     { 7 }
::= { vrPpSrclSrProvEntry 1 }

vrPpSrclExploreFrameTreatment OBJECT-TYPE
   SYNTAX     INTEGER  {
                 encap(0),
                 xlate(1) }
   ACCESS     read-write
   STATUS     mandatory
   DESCRIPTION
     "This attribute specifies whether or not explore frames received from 
      SourceRouteBridge ports will be sent to the SRTB-8209 translation or 
      the encapsulated SourceRouteBridge logic. This option is used only 
      when both the TbsrBridgePort and the SrtbBridgePort are provisioned 
      and enabled. 
      A value of Xlate implies that the explore frames will be sent to the Srtb 
      translation logic and a value of Encap implies that the frames will be 
      sent to the Encapsulated source route bridging logic."
   DEFVAL     { encap }
::= { vrPpSrclSrProvEntry 2 }

vrPpSrclLanId OBJECT-TYPE
   SYNTAX     Unsigned32 (0..4095)
   ACCESS     read-write
   STATUS     mandatory
   DESCRIPTION
     "This attribute specifies the identifier for the physical LAN that this port 
      is attached. All SourceRouteBridge ports are assigned to a physical LAN 
      and a logical internal LAN. 
      Current source route bridge implementations limit the lanId to a value in 
      the range 0 to 4095."
   DEFVAL     { 0 }
::= { vrPpSrclSrProvEntry 3 }

vrPpSrclInternalLanId OBJECT-TYPE
   SYNTAX     Unsigned32 (0..4095)
   ACCESS     read-write
   STATUS     mandatory
   DESCRIPTION
     "This attribute specifies the identifier for the internal logical LAN this 
      port is attached. All SourceRouteBridge ports are assigned to a physical 
      LAN and a logical internal LAN. 
      Current source route bridge implementations limit the lanId to a value in 
      the range 0 to 4095."
   DEFVAL     { 0 }
::= { vrPpSrclSrProvEntry 4 }

vrPpSrclBridgeNum OBJECT-TYPE
   SYNTAX     Unsigned32 (0..15)
   ACCESS     read-write
   STATUS     mandatory
   DESCRIPTION
     "This attribute specifies the value that is used to identify this bridge when 
      more than one bridge is used to span the same two LAN segments."
   DEFVAL     { 7 }
::= { vrPpSrclSrProvEntry 5 }

vrPpSrclLargestFrame OBJECT-TYPE
   SYNTAX     Unsigned32 (516 | 1470 | 2052 | 4399 | 8130 | 11407 | 17749)
   ACCESS     read-write
   STATUS     mandatory
   DESCRIPTION
     "This attribute specifies the maximum frame size (LLC and above) in 
      octets, allowed by this SourceRouteBridge port. This field is used to 
      determine whether a modification of the largest frame field of the 
      routing control field of the routing information field is warranted."
::= { vrPpSrclSrProvEntry 6 }

vrPpSrclSteSpanMode OBJECT-TYPE
   SYNTAX     INTEGER  {
                 autoSpan(1),
                 disabled(2),
                 forced(3) }
   ACCESS     read-write
   STATUS     mandatory
   DESCRIPTION
     "This attribute determines how this bridge port will react when presented 
      with a Spanning Tree Explore frame.
      If disabled, the Spanning Tree Explore frame is discarded regardless of 
      the value of stpPortState. 
      If the value of this attribute is forced, the Spanning Tree Explore frame 
      is forwarded regardless of the value of stpPortState. 
      autoSpan uses the stpPortState value to decide whether or not Spanning 
      Tree Explore frames should be forwarded out this bridge port. If the port 
      is in the forwarding state, the frame is received and transmitted 
      otherwise the frame is discarded."
   DEFVAL     { autoSpan }
::= { vrPpSrclSrProvEntry 7 }

vrPpSrclAreRdLimit OBJECT-TYPE
   SYNTAX     Unsigned32 (0..8)
   ACCESS     read-write
   STATUS     mandatory
   DESCRIPTION
     "This attribute specifies the number of route descriptors allowed in an All 
      Routes Explore frame received on a SourceRouteBridgePort or 
      SourceRouteTransparentBridgePort. Current source route bridge 
      implementations limit the areRdLimit to a value in the range 0 to 8."
   DEFVAL     { 8 }
::= { vrPpSrclSrProvEntry 8 }

vrPpSrclSteRdLimit OBJECT-TYPE
   SYNTAX     Unsigned32 (0..8)
   ACCESS     read-write
   STATUS     mandatory
   DESCRIPTION
     "This attribute specifies the number of route descriptors allowed in a 
      Spanning Tree Explore frame received on a SourceRouteBridgePort or 
      SourceRouteTransparentBridgePort. Current source route bridge 
      implementations limit the steRdLimit to a value in the range 0 to 8."
   DEFVAL     { 8 }
::= { vrPpSrclSrProvEntry 9 }

vrPpSrclSrStatsTable OBJECT-TYPE
   SYNTAX     SEQUENCE OF VrPpSrclSrStatsEntry
   ACCESS     not-accessible
   STATUS     mandatory
   DESCRIPTION
     "This group contains all port specific statistical attributes associated with 
      SourceRouteBridge ports."
::= { vrPpSrcl 21 }

vrPpSrclSrStatsEntry OBJECT-TYPE
   SYNTAX     VrPpSrclSrStatsEntry
   ACCESS     not-accessible
   STATUS     mandatory
   DESCRIPTION
     "An entry in the vrPpSrclSrStatsTable."
   INDEX {
      vrIndex,
      vrPpIndex,
      vrPpSrclIndex }
::= { vrPpSrclSrStatsTable 1 }

VrPpSrclSrStatsEntry ::= SEQUENCE {
   vrPpSrclSpecInFrames
      Counter32,
   vrPpSrclSpecOutFrames
      Counter32,
   vrPpSrclApeInFrames
      Counter32,
   vrPpSrclApeOutFrames
      Counter32,
   vrPpSrclSteInFrames
      Counter32,
   vrPpSrclSteOutFrames
      Counter32,
   vrPpSrclSegmentMismatchDiscards
      Counter32,
   vrPpSrclDupSegmentDiscards
      Counter32,
   vrPpSrclHopCountExceededDiscards
      Counter32,
   vrPpSrclDupLanIdOrTreeErrors
      Counter32,
   vrPpSrclLanIdMismatches
      Counter32,
   vrPpSrclStaticDiscards
      Counter32,
   vrPpSrclDynamicDiscards
      Counter32 }

vrPpSrclSpecInFrames OBJECT-TYPE
   SYNTAX     Counter32 
   ACCESS     read-only
   STATUS     mandatory
   DESCRIPTION
     "This attribute specifies the number of specifically routed frames that 
      were received by this bridge port. A specifically routed frame has a route 
      descriptor, constructed by the originating host which details an explicit 
      route to the destination host. This counter will wrap to zero when it 
      exceeds its maximum."
::= { vrPpSrclSrStatsEntry 1 }

vrPpSrclSpecOutFrames OBJECT-TYPE
   SYNTAX     Counter32 
   ACCESS     read-only
   STATUS     mandatory
   DESCRIPTION
     "This attribute specifies the number of specifically routed frames that 
      were transmitted from this bridge port. This counter will wrap to zero 
      when it exceeds its maximum."
::= { vrPpSrclSrStatsEntry 2 }

vrPpSrclApeInFrames OBJECT-TYPE
   SYNTAX     Counter32 
   ACCESS     read-only
   STATUS     mandatory
   DESCRIPTION
     "This attribute specifies the number of All Path Explore frames received 
      on this bridge port. The All Path Explore frames are forwarded to all 
      SourceRouteBridge ports assigned to this bridge regardless of the port's 
      portStpStates. This counter will wrap to zero when it exceeds its 
      maximum."
::= { vrPpSrclSrStatsEntry 3 }

vrPpSrclApeOutFrames OBJECT-TYPE
   SYNTAX     Counter32 
   ACCESS     read-only
   STATUS     mandatory
   DESCRIPTION
     "This attribute specifies the number of All Path Explore frames 
      transmitted on this bridge port. The All Path Explore frames are 
      forwarded to all SourceRouteBridge ports assigned to this bridge 
      regardless of the port's portStpState state. This counter will wrap to zero 
      when it exceeds its maximum."
::= { vrPpSrclSrStatsEntry 4 }

vrPpSrclSteInFrames OBJECT-TYPE
   SYNTAX     Counter32 
   ACCESS     read-only
   STATUS     mandatory
   DESCRIPTION
     "This attribute specifies the number of Spanning Tree Explore frames 
      received on this bridge port. The Spanning Tree Explore frames are only 
      forwarded through bridge ports whose portStpState has a value of 
      forwarding. This counter will wrap to zero when it exceeds its 
      maximum."
::= { vrPpSrclSrStatsEntry 5 }

vrPpSrclSteOutFrames OBJECT-TYPE
   SYNTAX     Counter32 
   ACCESS     read-only
   STATUS     mandatory
   DESCRIPTION
     "This attribute specifies the number of Spanning Tree Frames transmitted 
      on this bridge port. This counter will wrap to zero when it exceeds its 
      maximum."
::= { vrPpSrclSrStatsEntry 6 }

vrPpSrclSegmentMismatchDiscards OBJECT-TYPE
   SYNTAX     Counter32 
   ACCESS     read-only
   STATUS     mandatory
   DESCRIPTION
     "This attribute specifies the number of All Routes Explore and Spanning 
      Tree Explore frames that were discarded due to an invalid next segment 
      value in the routing information field. This counter will wrap to zero 
      when it exceeds its maximum."
::= { vrPpSrclSrStatsEntry 7 }

vrPpSrclDupSegmentDiscards OBJECT-TYPE
   SYNTAX     Counter32 
   ACCESS     read-only
   STATUS     mandatory
   DESCRIPTION
     "This attribute specifies the number of frames discarded due to the 
      presence of a duplicate segment identifier in the route descriptor field 
      which may indicate a loop in the network topology. This counter will 
      wrap to zero when it exceeds its maximum."
::= { vrPpSrclSrStatsEntry 8 }

vrPpSrclHopCountExceededDiscards OBJECT-TYPE
   SYNTAX     Counter32 
   ACCESS     read-only
   STATUS     mandatory
   DESCRIPTION
     "This attribute specifies the number of All Routes Explore and Spanning 
      Tree Explore frames discarded by this bridge port due to a frame 
      exceeding the maximum size allowed for a route descriptor length. This 
      counter will wrap to zero when it exceeds its maximum."
::= { vrPpSrclSrStatsEntry 9 }

vrPpSrclDupLanIdOrTreeErrors OBJECT-TYPE
   SYNTAX     Counter32 
   ACCESS     read-only
   STATUS     mandatory
   DESCRIPTION
     "This attribute specifies the number frames received which contain 
      duplicate LAN IDs or Tree errors. This attribute is helpful in debugging 
      problems in networks which contain older IBM-SR bridges. This 
      counter will wrap to zero when it exceeds its maximum."
::= { vrPpSrclSrStatsEntry 10 }

vrPpSrclLanIdMismatches OBJECT-TYPE
   SYNTAX     Counter32 
   ACCESS     read-only
   STATUS     mandatory
   DESCRIPTION
     "This attributes counts the number of All Routes Explore or Spanning 
      Tree Explore frames that were discarded because the last LAN ID in the 
      routing information field did not equal the LAN ID. This counter will 
      wrap to zero when it exceeds its maximum."
::= { vrPpSrclSrStatsEntry 11 }

vrPpSrclStaticDiscards OBJECT-TYPE
   SYNTAX     Counter32 
   ACCESS     read-only
   STATUS     mandatory
   DESCRIPTION
     "This attribute is indicative of the number of explorer frames discarded 
      due to fact that the outbound SourceRouteBridge port was disabled or 
      deleted. This counter will wrap to zero when it exceeds its maximum."
::= { vrPpSrclSrStatsEntry 12 }

vrPpSrclDynamicDiscards OBJECT-TYPE
   SYNTAX     Counter32 
   ACCESS     read-only
   STATUS     mandatory
   DESCRIPTION
     "This attribute specifies the number of frames discarded due to receiving 
      a frame with a target LAN ID which did not match the internal LAN ID 
      of the receiving bridge port. This counter will wrap to zero when it 
      exceeds its maximum."
::= { vrPpSrclSrStatsEntry 13 }


-- Vr/<string> Pp/<string> TransparentBridgePort NetSentry
-- This component represents the Ns functionality that can be applied to a 
-- bridge port. It contains all the attribute groups (provisionable) that are 
-- necessary for the application of Ns functionality to a bridge port. In 
-- essence, it allows for the definition of filters, at the incoming and 
-- outgoing points, specific to the interface represented by this bridge port. 

vrPpSrclNs OBJECT IDENTIFIER ::= { vrPpSrcl 2 }



vrPpSrclNsRowStatusTable OBJECT-TYPE
   SYNTAX     SEQUENCE OF VrPpSrclNsRowStatusEntry
   ACCESS     not-accessible
   STATUS     mandatory
   DESCRIPTION
     "This entry controls the addition and deletion of 
      vrPpSrclNs components."
::= { vrPpSrclNs 1 }

vrPpSrclNsRowStatusEntry OBJECT-TYPE
   SYNTAX     VrPpSrclNsRowStatusEntry
   ACCESS     not-accessible
   STATUS     mandatory
   DESCRIPTION
     "A single entry in the table represents a single 
      vrPpSrclNs component."
   INDEX {
      vrIndex,
      vrPpIndex,
      vrPpSrclIndex,
      vrPpSrclNsIndex }
::= { vrPpSrclNsRowStatusTable 1 }

VrPpSrclNsRowStatusEntry ::= SEQUENCE {
   vrPpSrclNsRowStatus
      RowStatus,
   vrPpSrclNsComponentName
      DisplayString,
   vrPpSrclNsStorageType
      StorageType,
   vrPpSrclNsIndex
      NonReplicated }

vrPpSrclNsRowStatus OBJECT-TYPE
   SYNTAX     RowStatus 
   ACCESS     read-write
   STATUS     mandatory
   DESCRIPTION
     "This variable is used as the basis for SNMP naming of
      vrPpSrclNs components.
      These components can be added and deleted."
::= { vrPpSrclNsRowStatusEntry 1 }

vrPpSrclNsComponentName OBJECT-TYPE
   SYNTAX     DisplayString 
   ACCESS     read-only
   STATUS     mandatory
   DESCRIPTION
     "This variable provides the component's string name for
      use with the ASCII Console Interface"
::= { vrPpSrclNsRowStatusEntry 2 }

vrPpSrclNsStorageType OBJECT-TYPE
   SYNTAX     StorageType 
   ACCESS     read-only
   STATUS     mandatory
   DESCRIPTION
     "This variable represents the storage type value for the
      vrPpSrclNs tables."
::= { vrPpSrclNsRowStatusEntry 4 }

vrPpSrclNsIndex OBJECT-TYPE
   SYNTAX     NonReplicated 
   ACCESS     not-accessible
   STATUS     mandatory
   DESCRIPTION
     "This variable represents the index for the vrPpSrclNs tables."
::= { vrPpSrclNsRowStatusEntry 10 }

vrPpSrclNsProvTable OBJECT-TYPE
   SYNTAX     SEQUENCE OF VrPpSrclNsProvEntry
   ACCESS     not-accessible
   STATUS     mandatory
   DESCRIPTION
     "This group houses all the port specific provisionable attributes 
      associated with Ns. These attributes influence the application of filters to 
      incoming and outgoing frames."
::= { vrPpSrclNs 10 }

vrPpSrclNsProvEntry OBJECT-TYPE
   SYNTAX     VrPpSrclNsProvEntry
   ACCESS     not-accessible
   STATUS     mandatory
   DESCRIPTION
     "An entry in the vrPpSrclNsProvTable."
   INDEX {
      vrIndex,
      vrPpIndex,
      vrPpSrclIndex,
      vrPpSrclNsIndex }
::= { vrPpSrclNsProvTable 1 }

VrPpSrclNsProvEntry ::= SEQUENCE {
   vrPpSrclNsIncomingFilter
      AsciiString,
   vrPpSrclNsOutgoingFilter
      AsciiString }

vrPpSrclNsIncomingFilter OBJECT-TYPE
   SYNTAX     AsciiString (SIZE (0..32))
   ACCESS     read-write
   STATUS     mandatory
   DESCRIPTION
     "This attribute specifies the name of the filter to be applied at the 
      incoming filter point."
::= { vrPpSrclNsProvEntry 2 }

vrPpSrclNsOutgoingFilter OBJECT-TYPE
   SYNTAX     AsciiString (SIZE (0..32))
   ACCESS     read-write
   STATUS     mandatory
   DESCRIPTION
     "This attribute specifies the name of the filter to be applied at the out 
      going filter point."
::= { vrPpSrclNsProvEntry 3 }


-- Vr/<string> Bridge 
-- This component represents the bridge logic, and all the associated 
-- attribute groups. All the various functions provided by bridging are 
-- encompassed by this component. 

vrBr OBJECT IDENTIFIER ::= { vr 5 }



vrBrRowStatusTable OBJECT-TYPE
   SYNTAX     SEQUENCE OF VrBrRowStatusEntry
   ACCESS     not-accessible
   STATUS     mandatory
   DESCRIPTION
     "This entry controls the addition and deletion of 
      vrBr components."
::= { vrBr 1 }

vrBrRowStatusEntry OBJECT-TYPE
   SYNTAX     VrBrRowStatusEntry
   ACCESS     not-accessible
   STATUS     mandatory
   DESCRIPTION
     "A single entry in the table represents a single 
      vrBr component."
   INDEX {
      vrIndex,
      vrBrIndex }
::= { vrBrRowStatusTable 1 }

VrBrRowStatusEntry ::= SEQUENCE {
   vrBrRowStatus
      RowStatus,
   vrBrComponentName
      DisplayString,
   vrBrStorageType
      StorageType,
   vrBrIndex
      NonReplicated }

vrBrRowStatus OBJECT-TYPE
   SYNTAX     RowStatus 
   ACCESS     read-write
   STATUS     mandatory
   DESCRIPTION
     "This variable is used as the basis for SNMP naming of
      vrBr components.
      These components can be added and deleted."
::= { vrBrRowStatusEntry 1 }

vrBrComponentName OBJECT-TYPE
   SYNTAX     DisplayString 
   ACCESS     read-only
   STATUS     mandatory
   DESCRIPTION
     "This variable provides the component's string name for
      use with the ASCII Console Interface"
::= { vrBrRowStatusEntry 2 }

vrBrStorageType OBJECT-TYPE
   SYNTAX     StorageType 
   ACCESS     read-only
   STATUS     mandatory
   DESCRIPTION
     "This variable represents the storage type value for the
      vrBr tables."
::= { vrBrRowStatusEntry 4 }

vrBrIndex OBJECT-TYPE
   SYNTAX     NonReplicated 
   ACCESS     not-accessible
   STATUS     mandatory
   DESCRIPTION
     "This variable represents the index for the vrBr tables."
::= { vrBrRowStatusEntry 10 }

vrBrAdminControlTable OBJECT-TYPE
   SYNTAX     SEQUENCE OF VrBrAdminControlEntry
   ACCESS     not-accessible
   STATUS     mandatory
   DESCRIPTION
     "This group includes the Administrative Control attribute. This attribute 
      defines the current administrative state of this component."
::= { vrBr 10 }

vrBrAdminControlEntry OBJECT-TYPE
   SYNTAX     VrBrAdminControlEntry
   ACCESS     not-accessible
   STATUS     mandatory
   DESCRIPTION
     "An entry in the vrBrAdminControlTable."
   INDEX {
      vrIndex,
      vrBrIndex }
::= { vrBrAdminControlTable 1 }

VrBrAdminControlEntry ::= SEQUENCE {
   vrBrAdminStatus
      INTEGER }

vrBrAdminStatus OBJECT-TYPE
   SYNTAX     INTEGER  {
                 up(1),
                 down(2) }
   ACCESS     read-write
   STATUS     mandatory
   DESCRIPTION
     "This attribute defines the current administrative status for 
      thiscomponent. 
      enabled indicates that the component is available for operation. 
      disabled indicates the component is unavailable for operation. The 
      application preserves all previously received provisioning data, all 
      writable operational data and all counters. Please note that all learnt data 
      are lost. The bridge application is not available for operation while in 
      this state."
   DEFVAL     { up }
::= { vrBrAdminControlEntry 1 }

vrBrStateTable OBJECT-TYPE
   SYNTAX     SEQUENCE OF VrBrStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrBr 12 }

vrBrStateEntry OBJECT-TYPE
   SYNTAX     VrBrStateEntry
   ACCESS     not-accessible
   STATUS     mandatory
   DESCRIPTION
     "An entry in the vrBrStateTable."
   INDEX {
      vrIndex,
      vrBrIndex }
::= { vrBrStateTable 1 }

VrBrStateEntry ::= SEQUENCE {
   vrBrAdminState
      INTEGER,
   vrBrOperationalState
      INTEGER,
   vrBrUsageState
      INTEGER }

vrBrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrBrStateEntry 1 }

vrBrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrBrStateEntry 2 }

vrBrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrBrStateEntry 3 }

vrBrOperStatusTable OBJECT-TYPE
   SYNTAX     SEQUENCE OF VrBrOperStatusEntry
   ACCESS     not-accessible
   STATUS     mandatory
   DESCRIPTION
     "This group includes the Operational Status attribute. This attribute 
      defines the current operational state of this component."
::= { vrBr 13 }

vrBrOperStatusEntry OBJECT-TYPE
   SYNTAX     VrBrOperStatusEntry
   ACCESS     not-accessible
   STATUS     mandatory
   DESCRIPTION
     "An entry in the vrBrOperStatusTable."
   INDEX {
      vrIndex,
      vrBrIndex }
::= { vrBrOperStatusTable 1 }

VrBrOperStatusEntry ::= SEQUENCE {
   vrBrSnmpOperStatus
      INTEGER }

vrBrSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrBrOperStatusEntry 1 }

vrBrOperTable OBJECT-TYPE
   SYNTAX     SEQUENCE OF VrBrOperEntry
   ACCESS     not-accessible
   STATUS     mandatory
   DESCRIPTION
     "This group houses all the operational attributes applicable to bridging, 
      those components that are global in nature and are not port specific."
::= { vrBr 14 }

vrBrOperEntry OBJECT-TYPE
   SYNTAX     VrBrOperEntry
   ACCESS     not-accessible
   STATUS     mandatory
   DESCRIPTION
     "An entry in the vrBrOperTable."
   INDEX {
      vrIndex,
      vrBrIndex }
::= { vrBrOperTable 1 }

VrBrOperEntry ::= SEQUENCE {
   vrBrBridgeAddress
      MacAddress,
   vrBrNumPorts
      Gauge32,
   vrBrType
      INTEGER }

vrBrBridgeAddress OBJECT-TYPE
   SYNTAX     MacAddress (SIZE (6))
   ACCESS     read-only
   STATUS     mandatory
   DESCRIPTION
     "This attribute represents the Mac address for the bridge. This address is 
      used when this bridge must be referred to in a unique manner. It is used 
      to form the bridge identifier, used by the spanning tree protocol, by 
      concatenating it with the attribute bridgePriority under the component 
      SpanningTreeProtocol."
::= { vrBrOperEntry 1 }

vrBrNumPorts OBJECT-TYPE
   SYNTAX     Gauge32 (0..255)
   ACCESS     read-only
   STATUS     mandatory
   DESCRIPTION
     "This attribute is indicative of the number of ports this bridge controls. In 
      other words, it is a count of the number of bridge ports provisioned."
::= { vrBrOperEntry 2 }

vrBrType OBJECT-TYPE
   SYNTAX     INTEGER  {
                 unknown(1),
                 transparentOnly(2),
                 sourceRouteOnly(3),
                 srt(4) }
   ACCESS     read-only
   STATUS     mandatory
   DESCRIPTION
     "This attribute is indicative of the capability of this bridge unit in terms of 
      types of bridging it can handle."
::= { vrBrOperEntry 3 }

-- 
-- *** THIS SUBTREE CURRENTLY NOT IMPLEMENTED ***
-- 

-- Vr/<string> Bridge PortTableEntry/<Decimal>,<string>,mode
-- This component is one of a group of similar components that forms a 
-- table. This table houses all the bridge ports provisioned and the 
-- corresponding domains they belong to. This table can be used as a 
-- central place to access all the information about bridge ports and the 
-- domains associated with these bridge ports. There can exist only sixteen 
-- domains when a spanning tree is desired specific to each domain. When 
-- there is only a single spanning tree spanning all the domains the 
-- maximum number of domains possible are 4294967293.

vrBrPte OBJECT IDENTIFIER ::= { vrBr 2 }



vrBrPteRowStatusTable OBJECT-TYPE
   SYNTAX     SEQUENCE OF VrBrPteRowStatusEntry
   ACCESS     not-accessible
   STATUS     mandatory
   DESCRIPTION
     "*** THIS TABLE CURRENTLY NOT IMPLEMENTED ***

      This entry controls the addition and deletion of 
      vrBrPte components."
::= { vrBrPte 1 }

vrBrPteRowStatusEntry OBJECT-TYPE
   SYNTAX     VrBrPteRowStatusEntry
   ACCESS     not-accessible
   STATUS     mandatory
   DESCRIPTION
     "A single entry in the table represents a single 
      vrBrPte component."
   INDEX {
      vrIndex,
      vrBrIndex,
      vrBrPteDomainNumIndex,
      vrBrPtePortNameIndex,
      vrBrPteModeIndex }
::= { vrBrPteRowStatusTable 1 }

VrBrPteRowStatusEntry ::= SEQUENCE {
   vrBrPteRowStatus
      RowStatus,
   vrBrPteComponentName
      DisplayString,
   vrBrPteStorageType
      StorageType,
   vrBrPteDomainNumIndex
      Integer32,
   vrBrPtePortNameIndex
      AsciiStringIndex,
   vrBrPteModeIndex
      INTEGER }

vrBrPteRowStatus OBJECT-TYPE
   SYNTAX     RowStatus 
   ACCESS     read-only
   STATUS     mandatory
   DESCRIPTION
     "This variable is used as the basis for SNMP naming of
      vrBrPte components.
      These components cannot be added nor deleted."
::= { vrBrPteRowStatusEntry 1 }

vrBrPteComponentName OBJECT-TYPE
   SYNTAX     DisplayString 
   ACCESS     read-only
   STATUS     mandatory
   DESCRIPTION
     "This variable provides the component's string name for
      use with the ASCII Console Interface"
::= { vrBrPteRowStatusEntry 2 }

vrBrPteStorageType OBJECT-TYPE
   SYNTAX     StorageType 
   ACCESS     read-only
   STATUS     mandatory
   DESCRIPTION
     "This variable represents the storage type value for the
      vrBrPte tables."
::= { vrBrPteRowStatusEntry 4 }

vrBrPteDomainNumIndex OBJECT-TYPE
   SYNTAX     Integer32 (1..268435455)
   ACCESS     not-accessible
   STATUS     mandatory
   DESCRIPTION
     "This variable represents an index for the vrBrPte tables."
::= { vrBrPteRowStatusEntry 10 }

vrBrPtePortNameIndex OBJECT-TYPE
   SYNTAX     AsciiStringIndex (SIZE (0..29))
   ACCESS     not-accessible
   STATUS     mandatory
   DESCRIPTION
     "This variable represents an index for the vrBrPte tables."
::= { vrBrPteRowStatusEntry 11 }

vrBrPteModeIndex OBJECT-TYPE
   SYNTAX     INTEGER  {
                 tb(2),
                 sr(3),
                 srt(4) }
   ACCESS     not-accessible
   STATUS     mandatory
   DESCRIPTION
     "This variable represents an index for the vrBrPte tables."
::= { vrBrPteRowStatusEntry 12 }

vrBrPteOperTable OBJECT-TYPE
   SYNTAX     SEQUENCE OF VrBrPteOperEntry
   ACCESS     not-accessible
   STATUS     mandatory
   DESCRIPTION
     "*** THIS TABLE CURRENTLY NOT IMPLEMENTED ***

      This group houses all the operational attributes belonging to the 
      PortTableEntry component."
::= { vrBrPte 10 }

vrBrPteOperEntry OBJECT-TYPE
   SYNTAX     VrBrPteOperEntry
   ACCESS     not-accessible
   STATUS     mandatory
   DESCRIPTION
     "An entry in the vrBrPteOperTable."
   INDEX {
      vrIndex,
      vrBrIndex,
      vrBrPteDomainNumIndex,
      vrBrPtePortNameIndex,
      vrBrPteModeIndex }
::= { vrBrPteOperTable 1 }

VrBrPteOperEntry ::= SEQUENCE {
   vrBrPteMacType
      INTEGER,
   vrBrPteStpState
      INTEGER,
   vrBrPteStpType
      INTEGER,
   vrBrPteFilterPoints
      INTEGER,
   vrBrPtePortPointsTo
      INTEGER }

vrBrPteMacType OBJECT-TYPE
   SYNTAX     INTEGER  {
                 ethernet(0),
                 tokenRing(1),
                 fddiBridgePort(2),
                 tokenBus(3),
                 fddiEncapsulating(4),
                 vns(5),
                 frameRelay(6),
                 ppp(7),
                 smds(8),
                 vcp(9),
                 x25(10),
                 srEncapSr(11),
                 srEncapTb(12),
                 sourceGateSr(13),
                 sourceGateTb(14),
                 srtb(15),
                 tbsr(16),
                 clusterSr(17),
                 clusterTb(18),
                 unknown(19),
                 atmMpe(20),
                 snaDlr(21),
                 lecEthernet(22) }
   ACCESS     read-only
   STATUS     mandatory
   DESCRIPTION
     "This attribute is indicative of the Mac type of the bridge port is 
      associated with."
::= { vrBrPteOperEntry 1 }

vrBrPteStpState OBJECT-TYPE
   SYNTAX     INTEGER  {
                 disabled(1),
                 blocking(2),
                 listening(3),
                 learning(4),
                 forwarding(5),
                 broken(6) }
   ACCESS     read-only
   STATUS     mandatory
   DESCRIPTION
     "This attribute is indicative of the stp state of the bridge port."
   DEFVAL     { disabled }
::= { vrBrPteOperEntry 2 }

vrBrPteStpType OBJECT-TYPE
   SYNTAX     INTEGER  {
                 unknown(1),
                 dec(2),
                 ieee8021(3) }
   ACCESS     read-only
   STATUS     mandatory
   DESCRIPTION
     "This attribute specifies the type of the spanning tree protocol this bridge 
      port is participating in."
   DEFVAL     { ieee8021 }
::= { vrBrPteOperEntry 3 }

vrBrPteFilterPoints OBJECT-TYPE
   SYNTAX     INTEGER  {
                 in(1),
                 out(2),
                 inOut(3),
                 none(4) }
   ACCESS     read-only
   STATUS     mandatory
   DESCRIPTION
     "This attribute in indicative of the points where filtering is active 
      currently."
   DEFVAL     { none }
::= { vrBrPteOperEntry 4 }

vrBrPtePortPointsTo OBJECT-TYPE
   SYNTAX     INTEGER  {
                 none(1),
                 rootBridge(2),
                 designatedBridge(3) }
   ACCESS     read-only
   STATUS     mandatory
   DESCRIPTION
     "This attribute in indicative of the fact if this bridge port leads to the root 
      bridge of the spanning tree topology or if leads to the designated bridge 
      of the lan segment the bridge port is attached to."
   DEFVAL     { none }
::= { vrBrPteOperEntry 5 }

vrBrPteSpOperTable OBJECT-TYPE
   SYNTAX     SEQUENCE OF VrBrPteSpOperEntry
   ACCESS     not-accessible
   STATUS     mandatory
   DESCRIPTION
     "*** THIS TABLE CURRENTLY NOT IMPLEMENTED ***

      This group contains all the attributes associated with the source route 
      portion of the port table."
::= { vrBrPte 11 }

vrBrPteSpOperEntry OBJECT-TYPE
   SYNTAX     VrBrPteSpOperEntry
   ACCESS     not-accessible
   STATUS     mandatory
   DESCRIPTION
     "An entry in the vrBrPteSpOperTable."
   INDEX {
      vrIndex,
      vrBrIndex,
      vrBrPteDomainNumIndex,
      vrBrPtePortNameIndex,
      vrBrPteModeIndex }
::= { vrBrPteSpOperTable 1 }

VrBrPteSpOperEntry ::= SEQUENCE {
   vrBrPteLanId
      Unsigned32,
   vrBrPteInternalLanId
      Unsigned32,
   vrBrPteBridgeNum
      Unsigned32 }

vrBrPteLanId OBJECT-TYPE
   SYNTAX     Unsigned32 (0..4095 | 65535)
   ACCESS     read-only
   STATUS     mandatory
   DESCRIPTION
     "This attribute identifies the lan identifier the bridge port is attached to. 
      LAN ID is a part of the route descriptor used when source route 
      bridging.
      Note that the value 0 is used by some applications for special test cases 
      and the value 65535 signifies that no lanId is assigned to this port."
::= { vrBrPteSpOperEntry 1 }

vrBrPteInternalLanId OBJECT-TYPE
   SYNTAX     Unsigned32 (0..4095 | 65535)
   ACCESS     read-only
   STATUS     mandatory
   DESCRIPTION
     "This attribute contains the internal or logical LAN to which a port is 
      attached. All source bridge ports have an associated physical LAN 
      segment and logical internal LAN segment.
      Note that the value 0 is used by some applications for special test cases 
      and the value 65535 signifies that no internalLanId is assigned to this 
      port."
::= { vrBrPteSpOperEntry 2 }

vrBrPteBridgeNum OBJECT-TYPE
   SYNTAX     Unsigned32 (0..15 | 65535)
   ACCESS     read-only
   STATUS     mandatory
   DESCRIPTION
     "This attribute specifies the number assigned to the bridge associated 
      with this LAN ID table entry. The bridge number is a part of the route 
      descriptor of a source routed frame. Note that the value 0 is used by 
      some applications for special test cases and the value 65535 signifies 
      that no bridgeNum is assigned to this port."
::= { vrBrPteSpOperEntry 3 }


-- Vr/<string> Bridge NetSentry 
-- This component represents the net sentry facility as applicable to 
-- bridging. It serves to allow the user to provision filter names that are 
-- applicable at the first, the last filter, the localIn and the localOut points 
-- and also the filter apply table. 

vrBrNs OBJECT IDENTIFIER ::= { vrBr 3 }



vrBrNsRowStatusTable OBJECT-TYPE
   SYNTAX     SEQUENCE OF VrBrNsRowStatusEntry
   ACCESS     not-accessible
   STATUS     mandatory
   DESCRIPTION
     "This entry controls the addition and deletion of 
      vrBrNs components."
::= { vrBrNs 1 }

vrBrNsRowStatusEntry OBJECT-TYPE
   SYNTAX     VrBrNsRowStatusEntry
   ACCESS     not-accessible
   STATUS     mandatory
   DESCRIPTION
     "A single entry in the table represents a single 
      vrBrNs component."
   INDEX {
      vrIndex,
      vrBrIndex,
      vrBrNsIndex }
::= { vrBrNsRowStatusTable 1 }

VrBrNsRowStatusEntry ::= SEQUENCE {
   vrBrNsRowStatus
      RowStatus,
   vrBrNsComponentName
      DisplayString,
   vrBrNsStorageType
      StorageType,
   vrBrNsIndex
      NonReplicated }

vrBrNsRowStatus OBJECT-TYPE
   SYNTAX     RowStatus 
   ACCESS     read-write
   STATUS     mandatory
   DESCRIPTION
     "This variable is used as the basis for SNMP naming of
      vrBrNs components.
      These components can be added and deleted."
::= { vrBrNsRowStatusEntry 1 }

vrBrNsComponentName OBJECT-TYPE
   SYNTAX     DisplayString 
   ACCESS     read-only
   STATUS     mandatory
   DESCRIPTION
     "This variable provides the component's string name for
      use with the ASCII Console Interface"
::= { vrBrNsRowStatusEntry 2 }

vrBrNsStorageType OBJECT-TYPE
   SYNTAX     StorageType 
   ACCESS     read-only
   STATUS     mandatory
   DESCRIPTION
     "This variable represents the storage type value for the
      vrBrNs tables."
::= { vrBrNsRowStatusEntry 4 }

vrBrNsIndex OBJECT-TYPE
   SYNTAX     NonReplicated 
   ACCESS     not-accessible
   STATUS     mandatory
   DESCRIPTION
     "This variable represents the index for the vrBrNs tables."
::= { vrBrNsRowStatusEntry 10 }

vrBrNsProvTable OBJECT-TYPE
   SYNTAX     SEQUENCE OF VrBrNsProvEntry
   ACCESS     not-accessible
   STATUS     mandatory
   DESCRIPTION
     "This group houses all the provisionable attributes applicable to the 
      packet control facility. These attributes are global attributes and are not 
      port specific."
::= { vrBrNs 10 }

vrBrNsProvEntry OBJECT-TYPE
   SYNTAX     VrBrNsProvEntry
   ACCESS     not-accessible
   STATUS     mandatory
   DESCRIPTION
     "An entry in the vrBrNsProvTable."
   INDEX {
      vrIndex,
      vrBrIndex,
      vrBrNsIndex }
::= { vrBrNsProvTable 1 }

VrBrNsProvEntry ::= SEQUENCE {
   vrBrNsFirstFilter
      AsciiString,
   vrBrNsLastFilter
      AsciiString }

vrBrNsFirstFilter OBJECT-TYPE
   SYNTAX     AsciiString (SIZE (0..32))
   ACCESS     read-write
   STATUS     mandatory
   DESCRIPTION
     "This attribute specifies the name of the filter to be applied at the first 
      filter point."
::= { vrBrNsProvEntry 1 }

vrBrNsLastFilter OBJECT-TYPE
   SYNTAX     AsciiString (SIZE (0..32))
   ACCESS     read-write
   STATUS     mandatory
   DESCRIPTION
     "This attribute specifies the name of the filter that is to be applied at the 
      last filter point."
::= { vrBrNsProvEntry 2 }


-- Vr/<string> Bridge NetSentry ApplyTableEntry/<Decimal> 
-- This component, represents an entry in the filter apply table. The filter 
-- apply table is used to specifically filter frames, based on a frame's 
-- origin, its destination, and the domain associated with the frame. A filter 
-- name is specified in the entry, which is applied to a frame if the match 
-- criteria is satisfied. 
-- When the attribute direction has the value to, a match in the filter table 
-- requires the firstMACAddress anded with the firstMACAddressMask to 
-- match the source MAC address in the frame, the secondMACAddress 
-- anded with the secondMACAddressMask to match the destination MAC 
-- address in the frame, and the domainNum to match the domain number 
-- associated with the frame.
-- When the direction has the value from, a match in the filter table 
-- requires the firstMACAddress anded with the firstMACAddressMask to 
-- match the destination MAC address in the frame, the 
-- secondMACAddress anded with the secondMACAddressMask to match 
-- the source MAC address in the frame, and the domainNum to match the 
-- domain number associated with the frame.
-- When the direction has the value toFrom, a match in the filter table 
-- requires the firstMACAddress anded with the firstMACAddressMask to 
-- match the source/destination MAC address in the frame, the 
-- secondMACAddress anded with the secondMACAddressMask to match 
-- the destination/source MAC address in the frame, and the domainNum to 
-- match the domain number associated with the frame. 

vrBrNsAte OBJECT IDENTIFIER ::= { vrBrNs 2 }



vrBrNsAteRowStatusTable OBJECT-TYPE
   SYNTAX     SEQUENCE OF VrBrNsAteRowStatusEntry
   ACCESS     not-accessible
   STATUS     mandatory
   DESCRIPTION
     "This entry controls the addition and deletion of 
      vrBrNsAte components."
::= { vrBrNsAte 1 }

vrBrNsAteRowStatusEntry OBJECT-TYPE
   SYNTAX     VrBrNsAteRowStatusEntry
   ACCESS     not-accessible
   STATUS     mandatory
   DESCRIPTION
     "A single entry in the table represents a single 
      vrBrNsAte component."
   INDEX {
      vrIndex,
      vrBrIndex,
      vrBrNsIndex,
      vrBrNsAteEntryNumberIndex }
::= { vrBrNsAteRowStatusTable 1 }

VrBrNsAteRowStatusEntry ::= SEQUENCE {
   vrBrNsAteRowStatus
      RowStatus,
   vrBrNsAteComponentName
      DisplayString,
   vrBrNsAteStorageType
      StorageType,
   vrBrNsAteEntryNumberIndex
      Integer32 }

vrBrNsAteRowStatus OBJECT-TYPE
   SYNTAX     RowStatus 
   ACCESS     read-write
   STATUS     mandatory
   DESCRIPTION
     "This variable is used as the basis for SNMP naming of
      vrBrNsAte components.
      These components can be added and deleted."
::= { vrBrNsAteRowStatusEntry 1 }

vrBrNsAteComponentName OBJECT-TYPE
   SYNTAX     DisplayString 
   ACCESS     read-only
   STATUS     mandatory
   DESCRIPTION
     "This variable provides the component's string name for
      use with the ASCII Console Interface"
::= { vrBrNsAteRowStatusEntry 2 }

vrBrNsAteStorageType OBJECT-TYPE
   SYNTAX     StorageType 
   ACCESS     read-only
   STATUS     mandatory
   DESCRIPTION
     "This variable represents the storage type value for the
      vrBrNsAte tables."
::= { vrBrNsAteRowStatusEntry 4 }

vrBrNsAteEntryNumberIndex OBJECT-TYPE
   SYNTAX     Integer32 (0..255)
   ACCESS     not-accessible
   STATUS     mandatory
   DESCRIPTION
     "This variable represents the index for the vrBrNsAte tables."
::= { vrBrNsAteRowStatusEntry 10 }

vrBrNsAteProvTable OBJECT-TYPE
   SYNTAX     SEQUENCE OF VrBrNsAteProvEntry
   ACCESS     not-accessible
   STATUS     mandatory
   DESCRIPTION
     "This group houses all the attributes that together form an apply table 
      entry. These fields of an apply table entry are used as match criteria, 
      which when satisfied results in the application of the named filter to the 
      frame."
::= { vrBrNsAte 10 }

vrBrNsAteProvEntry OBJECT-TYPE
   SYNTAX     VrBrNsAteProvEntry
   ACCESS     not-accessible
   STATUS     mandatory
   DESCRIPTION
     "An entry in the vrBrNsAteProvTable."
   INDEX {
      vrIndex,
      vrBrIndex,
      vrBrNsIndex,
      vrBrNsAteEntryNumberIndex }
::= { vrBrNsAteProvTable 1 }

VrBrNsAteProvEntry ::= SEQUENCE {
   vrBrNsAteDomainNum
      Unsigned32,
   vrBrNsAteFirstMacAddress
      MacAddress,
   vrBrNsAteFirstMacAddressMask
      MacAddress,
   vrBrNsAteSecondMacAddress
      MacAddress,
   vrBrNsAteSecondMacAddressMask
      MacAddress,
   vrBrNsAteDirection
      INTEGER,
   vrBrNsAteFilterName
      AsciiString }

vrBrNsAteDomainNum OBJECT-TYPE
   SYNTAX     Unsigned32 (0..4294967293)
   ACCESS     read-write
   STATUS     mandatory
   DESCRIPTION
     "This attribute specifies the domain number associated with a frame, that 
      would qualify it partly, for a match in the apply table. The domain 
      number provisioned will form a part of the match criteria only if it is not 
      provisioned with a wild card value of 0. If the wild card character is 
      specified, any domain number will satisfy the match criteria, in effect 
      loosing domain number as a qualifier in the match criteria."
   DEFVAL     { 0 }
::= { vrBrNsAteProvEntry 1 }

vrBrNsAteFirstMacAddress OBJECT-TYPE
   SYNTAX     MacAddress (SIZE (6))
   ACCESS     read-write
   STATUS     mandatory
   DESCRIPTION
     "This attribute specifies the MAC address to be anded with the 
      firstMACAddressMask, and the result compared with-
      a) The source MAC address in a frame when the attribute direction has a 
      value of to,
      b) The destination MAC address in a frame when the attribute direction 
      has a value of from,
      c) Source / Destination address in a frame when the attribute direction 
      has a value of toFrom, as a part of finding a match in the bridge filter 
      apply table."
   DEFVAL     { '000000000000'H }
::= { vrBrNsAteProvEntry 2 }

vrBrNsAteFirstMacAddressMask OBJECT-TYPE
   SYNTAX     MacAddress (SIZE (6))
   ACCESS     read-write
   STATUS     mandatory
   DESCRIPTION
     "This attribute specifies the mask which is anded with the attribute 
      firstMACAddress. The result is then compared with- 
      a) The source MAC address in a frame when the attribute direction has a 
      value of to,
      b) The destination MAC address in a frame when the attribute direction 
      has a value of from, 
      c) Source / Destination address in a frame when the attribute direction 
      has a value of toFrom, as a part of finding a match in the bridge filter 
      apply table."
   DEFVAL     { 'ffffffffffff'H }
::= { vrBrNsAteProvEntry 3 }

vrBrNsAteSecondMacAddress OBJECT-TYPE
   SYNTAX     MacAddress (SIZE (6))
   ACCESS     read-write
   STATUS     mandatory
   DESCRIPTION
     "This attribute specifies the MAC address to be anded with the 
      secondMACAddressMask, and the result compared with- 
      a) The destination MAC address in a frame when the attribute direction 
      has a value of to, 
      b) The source MAC address in a frame when the attribute direction has a 
      value of from,
      c) Destination/Source address in a frame when the attribute direction has 
      a value of toFrom, as a part of finding a match in the bridge filter apply 
      table."
   DEFVAL     { '000000000000'H }
::= { vrBrNsAteProvEntry 4 }

vrBrNsAteSecondMacAddressMask OBJECT-TYPE
   SYNTAX     MacAddress (SIZE (6))
   ACCESS     read-write
   STATUS     mandatory
   DESCRIPTION
     "This attribute specifies the mask which is anded with the attribute 
      secondMACAddress. The result is then compared with-
      a) The destination MAC address in a frame when the attribute direction 
      has a value of to, 
      b) The source MAC address in a frame when the attribute direction has a 
      value of from, 
      c) Destination/Source address in a frame when the attribute direction has 
      a value of toFrom, as a part of finding a match in the bridge filter apply 
      table."
   DEFVAL     { 'ffffffffffff'H }
::= { vrBrNsAteProvEntry 5 }

vrBrNsAteDirection OBJECT-TYPE
   SYNTAX     INTEGER  {
                 to(0),
                 from(1),
                 toFrom(2) }
   ACCESS     read-write
   STATUS     mandatory
   DESCRIPTION
     "This attribute specifies the direction of frame flow. It is used to 
      appropriately compare the result of logically anding MAC address, 
      MACAddressMask pairs, with the source /destination MAC address 
      fields in a frame, as a part of the match finding process. 
      When this attribute has value of to, the firstMACAddress is logically 
      anded with the firstMACAddressMask and the result compared with the 
      source MAC address in a frame and the secondMACAddress logically 
      anded with the secondMACAddressMask and compared with the 
      destination MAC address. 
      When this attribute has a value of from, the firstMACAddress is 
      logically anded with the firstMACAddressMask and the result compared 
      with the destinationMAC address in a frame and the 
      secondMACAddress logically anded with the secondMACAddressMask 
      and compared with the sourceMAC addressin the frame, as a part of 
      finding a match in the bridge filter apply table entry."
   DEFVAL     { toFrom }
::= { vrBrNsAteProvEntry 6 }

vrBrNsAteFilterName OBJECT-TYPE
   SYNTAX     AsciiString (SIZE (0..32))
   ACCESS     read-write
   STATUS     mandatory
   DESCRIPTION
     "This attribute specifies the name of the filter to be applied to the frame, 
      if it satisfies the match criteria mentioned in the bridge filter apply table 
      entry."
::= { vrBrNsAteProvEntry 7 }


-- Vr/<string> Bridge TransparentBridge
-- This component houses all the global bridge attribute groups necessary 
-- for the operation of a transparent bridge.

vrBrTb OBJECT IDENTIFIER ::= { vrBr 4 }



vrBrTbRowStatusTable OBJECT-TYPE
   SYNTAX     SEQUENCE OF VrBrTbRowStatusEntry
   ACCESS     not-accessible
   STATUS     mandatory
   DESCRIPTION
     "This entry controls the addition and deletion of 
      vrBrTb components."
::= { vrBrTb 1 }

vrBrTbRowStatusEntry OBJECT-TYPE
   SYNTAX     VrBrTbRowStatusEntry
   ACCESS     not-accessible
   STATUS     mandatory
   DESCRIPTION
     "A single entry in the table represents a single 
      vrBrTb component."
   INDEX {
      vrIndex,
      vrBrIndex,
      vrBrTbIndex }
::= { vrBrTbRowStatusTable 1 }

VrBrTbRowStatusEntry ::= SEQUENCE {
   vrBrTbRowStatus
      RowStatus,
   vrBrTbComponentName
      DisplayString,
   vrBrTbStorageType
      StorageType,
   vrBrTbIndex
      NonReplicated }

vrBrTbRowStatus OBJECT-TYPE
   SYNTAX     RowStatus 
   ACCESS     read-write
   STATUS     mandatory
   DESCRIPTION
     "This variable is used as the basis for SNMP naming of
      vrBrTb components.
      These components can be added and deleted."
::= { vrBrTbRowStatusEntry 1 }

vrBrTbComponentName OBJECT-TYPE
   SYNTAX     DisplayString 
   ACCESS     read-only
   STATUS     mandatory
   DESCRIPTION
     "This variable provides the component's string name for
      use with the ASCII Console Interface"
::= { vrBrTbRowStatusEntry 2 }

vrBrTbStorageType OBJECT-TYPE
   SYNTAX     StorageType 
   ACCESS     read-only
   STATUS     mandatory
   DESCRIPTION
     "This variable represents the storage type value for the
      vrBrTb tables."
::= { vrBrTbRowStatusEntry 4 }

vrBrTbIndex OBJECT-TYPE
   SYNTAX     NonReplicated 
   ACCESS     not-accessible
   STATUS     mandatory
   DESCRIPTION
     "This variable represents the index for the vrBrTb tables."
::= { vrBrTbRowStatusEntry 10 }

vrBrTbProvTable OBJECT-TYPE
   SYNTAX     SEQUENCE OF VrBrTbProvEntry
   ACCESS     not-accessible
   STATUS     mandatory
   DESCRIPTION
     "This group houses all the provisionable attributes applicable to a 
      transparent bridge, those attributes that are global and are not port 
      specific."
::= { vrBrTb 10 }

vrBrTbProvEntry OBJECT-TYPE
   SYNTAX     VrBrTbProvEntry
   ACCESS     not-accessible
   STATUS     mandatory
   DESCRIPTION
     "An entry in the vrBrTbProvTable."
   INDEX {
      vrIndex,
      vrBrIndex,
      vrBrTbIndex }
::= { vrBrTbProvTable 1 }

VrBrTbProvEntry ::= SEQUENCE {
   vrBrTbFwdTableNumEntries
      Unsigned32,
   vrBrTbAgingTime
      Unsigned32 }

vrBrTbFwdTableNumEntries OBJECT-TYPE
   SYNTAX     Unsigned32 (0..65535)
   ACCESS     read-write
   STATUS     mandatory
   DESCRIPTION
     "This attribute specifies the number of entries that can exist in the 
      transparent bridge forwarding table. This attribute provides a way to 
      control the resources allocated to forwarding table. This attribute will 
      prove to be very useful while attempting to fine tune the resource 
      allocated to the various types of tables to suit the network configuration. 
      Please understand that this attribute tbFwdTableNumEntries is 
      influenced by the memory management scheme provided by the 
      VirtualRouter and is by no means independent of the same. It is 
      important to understand the network configuration in terms of number 
      and types of bridge ports provisioned before attempting to fine tune this 
      attribute.The following attributes can be used as feedback to fine tune 
      this attribute:
      a) attribute totalForwardingTableEntries under the TransparentBridge 
      component,
      b) attribute numFtEntriesFree under the TransparentBridge 
      component,
      c) attribute numFtEntriesDenied under the TransparentBridge 
      component"
   DEFVAL     { 500 }
::= { vrBrTbProvEntry 1 }

vrBrTbAgingTime OBJECT-TYPE
   SYNTAX     Unsigned32 (10..1000000)
   ACCESS     read-write
   STATUS     mandatory
   DESCRIPTION
     "This attribute specifies the time period used in seconds, to age out 
      dynamically learned entries in the forwarding table. The aging time can 
      change, triggered by a spanning tree topology change. The operational 
      value of the aging time is reflected in the attribute agingTimeOper under 
      the SpanningTreeProtocol component."
   DEFVAL     { 300 }
::= { vrBrTbProvEntry 2 }

vrBrTbStatsTable OBJECT-TYPE
   SYNTAX     SEQUENCE OF VrBrTbStatsEntry
   ACCESS     not-accessible
   STATUS     mandatory
   DESCRIPTION
     "This group houses all the statistical attributes for a transparent bridge, 
      those attributes that are global in nature and are not port specific."
::= { vrBrTb 11 }

vrBrTbStatsEntry OBJECT-TYPE
   SYNTAX     VrBrTbStatsEntry
   ACCESS     not-accessible
   STATUS     mandatory
   DESCRIPTION
     "An entry in the vrBrTbStatsTable."
   INDEX {
      vrIndex,
      vrBrIndex,
      vrBrTbIndex }
::= { vrBrTbStatsTable 1 }

VrBrTbStatsEntry ::= SEQUENCE {
   vrBrTbLearnedEntryDiscards
      Counter32,
   vrBrTbTotalForwardingTableEntries
      Counter32,
   vrBrTbNumFtEntriesFree
      Gauge32,
   vrBrTbNumFtEntriesDenied
      Counter32 }

vrBrTbLearnedEntryDiscards OBJECT-TYPE
   SYNTAX     Counter32 
   ACCESS     read-only
   STATUS     mandatory
   DESCRIPTION
     "This attribute represents the number of entries that might have been 
      learned but have been discarded due to lack of space to store them in the 
      forwarding table. This counter is not supported currently by the bridging 
      platform and will always return a value of 0 in response to any queries."
::= { vrBrTbStatsEntry 1 }

vrBrTbTotalForwardingTableEntries OBJECT-TYPE
   SYNTAX     Counter32 
   ACCESS     read-only
   STATUS     mandatory
   DESCRIPTION
     "This attribute specifies the total number of TB forwarding table entries. 
      This includes static forwarding table entries and dynamic forwarding 
      table entries. 
      This attribute is influenced by the attribute tbFwdTableNumEntries, 
      which is a provisionable attribute. 
      If the value is consistently approaching the value of the attribute 
      tbFwdTableNumEntries, it is advisable to increase the value provisioned 
      for tbFwdTableNumEntries. It indicates a potential shortage of 
      forwarding table entries in the future. 
      This attribute is inversely proportional in value to the attribute 
      numFtEntriesFree.
      This counter wraps around its maximum value of 4294967295."
::= { vrBrTbStatsEntry 2 }

vrBrTbNumFtEntriesFree OBJECT-TYPE
   SYNTAX     Gauge32 (0..4294967295)
   ACCESS     read-only
   STATUS     mandatory
   DESCRIPTION
     "This attribute is indicative of the number of TB forwarding table entries 
      free. These entries could be used by static entries or by dynamic entries. 
      This counter wraps around its maximum value of 4294967295.
      A consistently high value for this attribute indicates that there is a 
      resource surplus here, in terms of the memory requirements of the 
      forwarding table. This surplus could be utilized elsewhere if need be. 
      The value of this attributes directly influenced by the value of the 
      attribute tbFwdTableNumEntries."
   DEFVAL     { 0 }
::= { vrBrTbStatsEntry 3 }

vrBrTbNumFtEntriesDenied OBJECT-TYPE
   SYNTAX     Counter32 
   ACCESS     read-only
   STATUS     mandatory
   DESCRIPTION
     "This attribute is indicative of the number of instances wherein TB table 
      entry was unavailable. These entries could have been denied for static 
      entries or for dynamic entries. This counter wraps around its maximum 
      value of 4294967295. 
      If this counter consistently shows a high value, it is indicative of a 
      resource shortage in terms of memory required to support the increase in 
      the number of forwarding table entries. To rectify this resource shortage, 
      increase the number of forwarding table entries through the provisioned 
      attribute tbFwdTableEntries under the Bridge component. This counter 
      should ideally be as low as possible."
::= { vrBrTbStatsEntry 4 }


-- Vr/<string> Br Tb Stp/<Decimal>
-- Vr/<string> Br Sr Stp/<Decimal>
-- This component represents the Spanning Tree Protocol for the bridge. 
-- Bridges in a network use the Spanning Tree Protocol to provide a loop 
-- free, fault tolerant network topology. As there may be a need for 
-- multiple domains in the network, bridging allows provisioning of 
-- domain specific spanning tree instances.
-- Individual spanning tree instances are indexed using the domain number. 
-- The domain numbers assigned are only unique to the bridge type so 
-- domain numbers may be shared between TransparentBridge and 
-- SourceRouteBridge.
-- Note that only 16 instances of this component are allowed and includes 
-- the backbone spanning tree instance.
-- The instance identifier of the SpanningTreeProtocol component is 
-- significant as it is indicative of the domain that spanning tree instance 
-- governs.

vrBrTbStp OBJECT IDENTIFIER ::= { vrBrTb 2 }



vrBrTbStpRowStatusTable OBJECT-TYPE
   SYNTAX     SEQUENCE OF VrBrTbStpRowStatusEntry
   ACCESS     not-accessible
   STATUS     mandatory
   DESCRIPTION
     "This entry controls the addition and deletion of 
      vrBrTbStp components."
::= { vrBrTbStp 1 }

vrBrTbStpRowStatusEntry OBJECT-TYPE
   SYNTAX     VrBrTbStpRowStatusEntry
   ACCESS     not-accessible
   STATUS     mandatory
   DESCRIPTION
     "A single entry in the table represents a single 
      vrBrTbStp component."
   INDEX {
      vrIndex,
      vrBrIndex,
      vrBrTbIndex,
      vrBrTbStpIndex }
::= { vrBrTbStpRowStatusTable 1 }

VrBrTbStpRowStatusEntry ::= SEQUENCE {
   vrBrTbStpRowStatus
      RowStatus,
   vrBrTbStpComponentName
      DisplayString,
   vrBrTbStpStorageType
      StorageType,
   vrBrTbStpIndex
      Integer32 }

vrBrTbStpRowStatus OBJECT-TYPE
   SYNTAX     RowStatus 
   ACCESS     read-write
   STATUS     mandatory
   DESCRIPTION
     "This variable is used as the basis for SNMP naming of
      vrBrTbStp components.
      These components can be added and deleted."
::= { vrBrTbStpRowStatusEntry 1 }

vrBrTbStpComponentName OBJECT-TYPE
   SYNTAX     DisplayString 
   ACCESS     read-only
   STATUS     mandatory
   DESCRIPTION
     "This variable provides the component's string name for
      use with the ASCII Console Interface"
::= { vrBrTbStpRowStatusEntry 2 }

vrBrTbStpStorageType OBJECT-TYPE
   SYNTAX     StorageType 
   ACCESS     read-only
   STATUS     mandatory
   DESCRIPTION
     "This variable represents the storage type value for the
      vrBrTbStp tables."
::= { vrBrTbStpRowStatusEntry 4 }

vrBrTbStpIndex OBJECT-TYPE
   SYNTAX     Integer32 (1..268435455)
   ACCESS     not-accessible
   STATUS     mandatory
   DESCRIPTION
     "This variable represents the index for the vrBrTbStp tables."
::= { vrBrTbStpRowStatusEntry 10 }

vrBrTbStpProvTable OBJECT-TYPE
   SYNTAX     SEQUENCE OF VrBrTbStpProvEntry
   ACCESS     not-accessible
   STATUS     mandatory
   DESCRIPTION
     "This group houses all the provisionable attributes that are applicable to 
      the spanning tree protocol. These are global attributes and not port 
      specific attributes. These attributes have a direct impact on the way this 
      bridge participates in the spanning tree protocol."
::= { vrBrTbStp 10 }

vrBrTbStpProvEntry OBJECT-TYPE
   SYNTAX     VrBrTbStpProvEntry
   ACCESS     not-accessible
   STATUS     mandatory
   DESCRIPTION
     "An entry in the vrBrTbStpProvTable."
   INDEX {
      vrIndex,
      vrBrIndex,
      vrBrTbIndex,
      vrBrTbStpIndex }
::= { vrBrTbStpProvTable 1 }

VrBrTbStpProvEntry ::= SEQUENCE {
   vrBrTbStpStpMode
      INTEGER,
   vrBrTbStpProtocolSpec
      INTEGER,
   vrBrTbStpPriority
      Unsigned32,
   vrBrTbStpBridgeMaxAge
      Unsigned32,
   vrBrTbStpBridgeHelloTime
      Unsigned32,
   vrBrTbStpBridgeForwardDelay
      Unsigned32 }

vrBrTbStpStpMode OBJECT-TYPE
   SYNTAX     INTEGER  {
                 access(1),
                 backbone(2) }
   ACCESS     read-write
   STATUS     mandatory
   DESCRIPTION
     "This attribute determines if this stp instance is to act as the stp instance 
      for the backbone or an stp instance for a non-backbone media 
      configuration. There can exist only one Backbone stp instance per 
      virtual router. If the attribute domainStpTbState is set to a value on and 
      Backbone bridge ports have been provisioned, there should exist a 
      Backbone stp instance. Please note that it is not permissible to assign the 
      instance identifier of this stp instance as domain number of any access 
      bridge port. In case of stp instances that are non-Backbone, the instance 
      identifier is indicative of the domain number the stp is operational in."
   DEFVAL     { access }
::= { vrBrTbStpProvEntry 1 }

vrBrTbStpProtocolSpec OBJECT-TYPE
   SYNTAX     INTEGER  {
                 both(1),
                 dec(2),
                 ieee8021d(3) }
   ACCESS     read-write
   STATUS     mandatory
   DESCRIPTION
     "This attribute specifies the type of spanning tree protocols that are in 
      operation in the bridge. This means that this bridge participates in the 
      types spanning tree protocol indicated by this attribute."
   DEFVAL     { ieee8021d }
::= { vrBrTbStpProvEntry 2 }

vrBrTbStpPriority OBJECT-TYPE
   SYNTAX     Unsigned32 (0..65535)
   ACCESS     read-write
   STATUS     mandatory
   DESCRIPTION
     "This attribute is used to construct the bridgeId. It forms the first two 
      octets of the bridgeId and the remaining 6 octets are made up of the 
      bridgeMACAddress. The priority also determines the root bridge of the 
      spanning tree topology. Manipulating this attribute might lead to a 
      change in the spanning tree topology."
   DEFVAL     { 32768 }
::= { vrBrTbStpProvEntry 3 }

vrBrTbStpBridgeMaxAge OBJECT-TYPE
   SYNTAX     Unsigned32 (600..4000)
   ACCESS     read-write
   STATUS     mandatory
   DESCRIPTION
     "The maximum age of spanning tree protocol information learned from 
      the network on any bridge port before it is discarded. This value is used 
      by this bridge and all the other bridges, when this bridge is the root 
      bridge of the spanning tree topology. The following relationships are 
      enforced as required by the IEEE 802.1d standards document.
      2 *(bridgeForwardDelay -1.0seconds) >= bridgeMaxAge, 
      bridgeMaxAge >= 2 * bridgeHelloTime + 1.0 seconds.
      DESCRIPTION"
   DEFVAL     { 2000 }
::= { vrBrTbStpProvEntry 4 }

vrBrTbStpBridgeHelloTime OBJECT-TYPE
   SYNTAX     Unsigned32 (100..1000)
   ACCESS     read-write
   STATUS     mandatory
   DESCRIPTION
     "This attribute specifies the time interval between the transmission of 
      configuration BPDUs on any bridge port when this bridge becomes the 
      root bridge. This attribute value is also used by all the other bridges in 
      the Spanning Tree while this bridge is the root. 
      The following relationship is enforced as required by the IEEE 802.1d 
      standards document. 
      bridgeMaxAge >= 2 * bridgeHelloTime + 1.0 seconds."
   DEFVAL     { 200 }
::= { vrBrTbStpProvEntry 5 }

vrBrTbStpBridgeForwardDelay OBJECT-TYPE
   SYNTAX     Unsigned32 (400..3000)
   ACCESS     read-write
   STATUS     mandatory
   DESCRIPTION
     "This attribute specifies how fast a bridge port changes its STP state 
      while progressing towards the forwarding state. It is also used as 
      agingTime to age dynamic entries in the forwarding table once a 
      topology change is detected. This attribute is used by all the bridges 
      participating in the spanning tree protocol, when this bridge is the root 
      bridge.
      The following relationship is enforced as required by the IEEE 802.1d 
      standards document. 
      2 *(bridgeForwardDelay -1.0sconds) >= bridgeMaxAge."
   DEFVAL     { 1500 }
::= { vrBrTbStpProvEntry 6 }

vrBrTbStpOperTable OBJECT-TYPE
   SYNTAX     SEQUENCE OF VrBrTbStpOperEntry
   ACCESS     not-accessible
   STATUS     mandatory
   DESCRIPTION
     "This group houses all the operational, spanning tree protocol attributes. 
      These attributes are applicable in a global manner and are not specific to 
      a bridge port."
::= { vrBrTbStp 11 }

vrBrTbStpOperEntry OBJECT-TYPE
   SYNTAX     VrBrTbStpOperEntry
   ACCESS     not-accessible
   STATUS     mandatory
   DESCRIPTION
     "An entry in the vrBrTbStpOperTable."
   INDEX {
      vrIndex,
      vrBrIndex,
      vrBrTbIndex,
      vrBrTbStpIndex }
::= { vrBrTbStpOperTable 1 }

VrBrTbStpOperEntry ::= SEQUENCE {
   vrBrTbStpBridgeId
      BridgeId,
   vrBrTbStpRootPortName
      AsciiString,
   vrBrTbStpTimeSinceTopologyChange
      Unsigned32,
   vrBrTbStpTopologyChangeDetect
      INTEGER,
   vrBrTbStpTopologyChanges
      Counter32,
   vrBrTbStpDesignatedRoot
      BridgeId,
   vrBrTbStpRootCost
      Unsigned32,
   vrBrTbStpMaxAge
      Unsigned32,
   vrBrTbStpAgingTimeOper
      Unsigned32,
   vrBrTbStpHelloTime
      Unsigned32,
   vrBrTbStpHoldTime
      Unsigned32,
   vrBrTbStpFwdDelay
      Unsigned32 }

vrBrTbStpBridgeId OBJECT-TYPE
   SYNTAX     BridgeId (SIZE (8))
   ACCESS     read-only
   STATUS     mandatory
   DESCRIPTION
     "This attribute specifies the identifier value of this bridge, which serves to 
      uniquely represent this bridge in the spanning tree topology. Thus, a 
      bridgeId is unique only in the spanning tree instance the bridge in 
      participating in. If multiple domain spanning trees exist then the same 
      bridgeId can be re-used across these spanning tree instances."
::= { vrBrTbStpOperEntry 1 }

vrBrTbStpRootPortName OBJECT-TYPE
   SYNTAX     AsciiString (SIZE (4..29))
   ACCESS     read-only
   STATUS     mandatory
   DESCRIPTION
     "This attribute specifies the name of the bridge port that offers the lowest 
      cost route to the root bridge of the spanning tree topology.The attribute 
      rootPortName is a string of the form 'BridgePortName-i', where 
      BridgePortName is the abbreviation of the corresponding bridge port 
      and i is the instance identifier of the ProtocolPort, the bridge port is 
      provisioned under. For example a TransparentBridgePort provisioned 
      under ProtocolPort/myport would have a name TBP-myport. 
      If multiple instances of spanning tree are operational, then there will 
      exist a rootPortName value for each instance of the spanning tree 
      running, and is applicable to that instance alone."
::= { vrBrTbStpOperEntry 2 }

vrBrTbStpTimeSinceTopologyChange OBJECT-TYPE
   SYNTAX     Unsigned32 (0..4294967295)
   ACCESS     read-only
   STATUS     mandatory
   DESCRIPTION
     "This attribute specifies the time since a spanning tree topology change 
      was detected by this bridge."
   DEFVAL     { 0 }
::= { vrBrTbStpOperEntry 3 }

vrBrTbStpTopologyChangeDetect OBJECT-TYPE
   SYNTAX     INTEGER  {
                 false(0),
                 true(1) }
   ACCESS     read-only
   STATUS     mandatory
   DESCRIPTION
     "This attribute specifies whether or not a topology change was detected. 
      This flag is set when a bpdu with the topology detect flag set is received 
      from the root bridge. If this bridge is the root bridge this flag is set on 
      receipt of a topology change notification bpdu. It is reset after a fixed 
      length of time."
   DEFVAL     { false }
::= { vrBrTbStpOperEntry 4 }

vrBrTbStpTopologyChanges OBJECT-TYPE
   SYNTAX     Counter32 
   ACCESS     read-only
   STATUS     mandatory
   DESCRIPTION
     "This attribute is indicative of the number of topology changes detected 
      by this bridge since the last bridge reset. This counter wraps around its 
      maximum value of 4294967295."
::= { vrBrTbStpOperEntry 5 }

vrBrTbStpDesignatedRoot OBJECT-TYPE
   SYNTAX     BridgeId (SIZE (8))
   ACCESS     read-only
   STATUS     mandatory
   DESCRIPTION
     "This attribute specifies the identifier of the bridge that this bridge treats 
      as the root of the spanning tree topology. The root of the spanning tree 
      topology is chosen through exchange."
::= { vrBrTbStpOperEntry 6 }

vrBrTbStpRootCost OBJECT-TYPE
   SYNTAX     Unsigned32 (1..65535)
   ACCESS     read-only
   STATUS     mandatory
   DESCRIPTION
     "This attribute specifies the cost of the path to the root as seen by this 
      bridge."
::= { vrBrTbStpOperEntry 8 }

vrBrTbStpMaxAge OBJECT-TYPE
   SYNTAX     Unsigned32 (600..4000)
   ACCESS     read-only
   STATUS     mandatory
   DESCRIPTION
     "This attribute specifies the maximum age of the spanning tree protocol 
      info learnt from a port, before it is discarded."
   DEFVAL     { 2000 }
::= { vrBrTbStpOperEntry 9 }

vrBrTbStpAgingTimeOper OBJECT-TYPE
   SYNTAX     Unsigned32 (10..1000000)
   ACCESS     read-only
   STATUS     mandatory
   DESCRIPTION
     "This attribute specifies the time period used in seconds, to age out 
      dynamically learned entries in the forwarding table. The aging time is 
      specific to a spanning tree protocol instance running. A value for the 
      aging time of the current instance of the spanning tree protocol can be 
      provisioned through the attribute agingTime under the InwBrTb 
      component. The agingTimeOper attribute assumes the value of the 
      bridgeForwardDelay while a topology change is in progress. This is 
      done to facilitate quick aging out of the learned entries that might have 
      become obsolete due to a spanning tree topology change."
   DEFVAL     { 300 }
::= { vrBrTbStpOperEntry 10 }

vrBrTbStpHelloTime OBJECT-TYPE
   SYNTAX     Unsigned32 (100..1000)
   ACCESS     read-only
   STATUS     mandatory
   DESCRIPTION
     "This attribute specifies the time interval between the transmission of the 
      configuration BPDUs. This value is obtained from the root bridge of the 
      spanning tree topology, through bridge protocol data units. This value 
      should be the value assigned to the attribute bridgeHelloTime of the root 
      bridge."
   DEFVAL     { 200 }
::= { vrBrTbStpOperEntry 11 }

vrBrTbStpHoldTime OBJECT-TYPE
   SYNTAX     Unsigned32 (100)
   ACCESS     read-only
   STATUS     mandatory
   DESCRIPTION
     "This attribute specifies the interval of time which no more than two 
      BPDUs should be sent."
   DEFVAL     { 100 }
::= { vrBrTbStpOperEntry 12 }

vrBrTbStpFwdDelay OBJECT-TYPE
   SYNTAX     Unsigned32 (400..3000)
   ACCESS     read-only
   STATUS     mandatory
   DESCRIPTION
     "This attribute specifies how much time a port spends in any state while 
      progressing towards the forwarding state. It is also used to age out 
      learned entries while a topology change is in progress.This value should 
      be the value assigned to the attribute bridgefwdDelay of the root bridge."
   DEFVAL     { 1500 }
::= { vrBrTbStpOperEntry 13 }


-- Vr/<string> Br Tb StaticTableEntry/address, receivePort 
-- This component represents an entry in the transparent bridging static 
-- forwarding table. A static table is used to store provisioned forwarding 
-- entries. Entries in the static table indicate the output ports, a frame is 
-- allowed to go out of, if it was received on receivePort and if its 
-- destination MAC address field matched address. A collection of such 
-- entries form the static forwarding table. 

vrBrTbSte OBJECT IDENTIFIER ::= { vrBrTb 3 }



vrBrTbSteRowStatusTable OBJECT-TYPE
   SYNTAX     SEQUENCE OF VrBrTbSteRowStatusEntry
   ACCESS     not-accessible
   STATUS     mandatory
   DESCRIPTION
     "This entry controls the addition and deletion of 
      vrBrTbSte components."
::= { vrBrTbSte 1 }

vrBrTbSteRowStatusEntry OBJECT-TYPE
   SYNTAX     VrBrTbSteRowStatusEntry
   ACCESS     not-accessible
   STATUS     mandatory
   DESCRIPTION
     "A single entry in the table represents a single 
      vrBrTbSte component."
   INDEX {
      vrIndex,
      vrBrIndex,
      vrBrTbIndex,
      vrBrTbSteAddressIndex,
      vrBrTbSteReceivePortIndex }
::= { vrBrTbSteRowStatusTable 1 }

VrBrTbSteRowStatusEntry ::= SEQUENCE {
   vrBrTbSteRowStatus
      RowStatus,
   vrBrTbSteComponentName
      DisplayString,
   vrBrTbSteStorageType
      StorageType,
   vrBrTbSteAddressIndex
      DashedHexString,
   vrBrTbSteReceivePortIndex
      AsciiStringIndex }

vrBrTbSteRowStatus OBJECT-TYPE
   SYNTAX     RowStatus 
   ACCESS     read-write
   STATUS     mandatory
   DESCRIPTION
     "This variable is used as the basis for SNMP naming of
      vrBrTbSte components.
      These components can be added and deleted."
::= { vrBrTbSteRowStatusEntry 1 }

vrBrTbSteComponentName OBJECT-TYPE
   SYNTAX     DisplayString 
   ACCESS     read-only
   STATUS     mandatory
   DESCRIPTION
     "This variable provides the component's string name for
      use with the ASCII Console Interface"
::= { vrBrTbSteRowStatusEntry 2 }

vrBrTbSteStorageType OBJECT-TYPE
   SYNTAX     StorageType 
   ACCESS     read-only
   STATUS     mandatory
   DESCRIPTION
     "This variable represents the storage type value for the
      vrBrTbSte tables."
::= { vrBrTbSteRowStatusEntry 4 }

vrBrTbSteAddressIndex OBJECT-TYPE
   SYNTAX     DashedHexString (SIZE (6))
   ACCESS     not-accessible
   STATUS     mandatory
   DESCRIPTION
     "This variable represents an index for the vrBrTbSte tables."
::= { vrBrTbSteRowStatusEntry 10 }

vrBrTbSteReceivePortIndex OBJECT-TYPE
   SYNTAX     AsciiStringIndex (SIZE (1..29))
   ACCESS     not-accessible
   STATUS     mandatory
   DESCRIPTION
     "This variable represents an index for the vrBrTbSte tables."
::= { vrBrTbSteRowStatusEntry 11 }

vrBrTbSteProvTable OBJECT-TYPE
   SYNTAX     SEQUENCE OF VrBrTbSteProvEntry
   ACCESS     not-accessible
   STATUS     mandatory
   DESCRIPTION
     "This group houses all the fields of a static table entry. All these attributes 
      can be provisioned by the user. Multiple such static table entries together 
      form the static forwarding table."
::= { vrBrTbSte 10 }

vrBrTbSteProvEntry OBJECT-TYPE
   SYNTAX     VrBrTbSteProvEntry
   ACCESS     not-accessible
   STATUS     mandatory
   DESCRIPTION
     "An entry in the vrBrTbSteProvTable."
   INDEX {
      vrIndex,
      vrBrIndex,
      vrBrTbIndex,
      vrBrTbSteAddressIndex,
      vrBrTbSteReceivePortIndex }
::= { vrBrTbSteProvTable 1 }

VrBrTbSteProvEntry ::= SEQUENCE {
   vrBrTbSteStatus
      INTEGER }

vrBrTbSteStatus OBJECT-TYPE
   SYNTAX     INTEGER  {
                 permanent(3) }
   ACCESS     read-write
   STATUS     mandatory
   DESCRIPTION
     "This attribute specifies the longevity of an entry in the static table. 
      Please note that currently only a value of permanent is supported."
   DEFVAL     { permanent }
::= { vrBrTbSteProvEntry 1 }

vrBrTbSteAtgtTable OBJECT-TYPE
   SYNTAX     SEQUENCE OF VrBrTbSteAtgtEntry
   ACCESS     not-accessible
   STATUS     mandatory
   DESCRIPTION
     "This port map specifies the out bridge ports a MAC frame with address 
      in its destination MAC address field, originating from receivePort, can 
      go out of. 
      The allowedToGoTo attribute is a set of strings where in each string is 
      of the form 'BridgePortName-i', where BridgePortName is the 
      abbreviation of the corresponding TB or SRT bridge port and i is the 
      instance identifier of the ProtocolPort, the bridge port is provisioned 
      under. Multiple strings can be specified on the same set command. Each 
      string in the list is space separated. An '*' in place of the i indicates 
      that regardless of the protocol port instance, all bridge ports with name 
      BridgePortName should be included in the allowedToGoTo. 
      In cases where there are multiple bridge ports provisioned under a 
      protocol port, (e.g. pseudo bridge ports) each bridge port name must be 
      specified in the form of strings, as indicated above. Please note that this 
      attribute allowedToGoTo cannot contain any of the following bridge 
      ports in part: SrBP, Srtb, Srsg, Tbsg, Srse, Srcl, FddiESr."
::= { vrBrTbSte 271 }

vrBrTbSteAtgtEntry OBJECT-TYPE
   SYNTAX     VrBrTbSteAtgtEntry
   ACCESS     not-accessible
   STATUS     mandatory
   DESCRIPTION
     "An entry in the vrBrTbSteAtgtTable."
   INDEX {
      vrIndex,
      vrBrIndex,
      vrBrTbIndex,
      vrBrTbSteAddressIndex,
      vrBrTbSteReceivePortIndex,
      vrBrTbSteAtgtValue }
::= { vrBrTbSteAtgtTable 1 }

VrBrTbSteAtgtEntry ::= SEQUENCE {
   vrBrTbSteAtgtValue
      AsciiString,
   vrBrTbSteAtgtRowStatus
      RowStatus }

vrBrTbSteAtgtValue OBJECT-TYPE
   SYNTAX     AsciiString (SIZE (4..29))
   ACCESS     read-write
   STATUS     mandatory
   DESCRIPTION
     "This variable represents both the value and the index for the
      vrBrTbSteAtgtTable."
::= { vrBrTbSteAtgtEntry 1 }

vrBrTbSteAtgtRowStatus OBJECT-TYPE
   SYNTAX     RowStatus 
   ACCESS     write-only
   STATUS     mandatory
   DESCRIPTION
     "This variable is used to control the addition and deletion 
      of individual values of the vrBrTbSteAtgtTable."
::= { vrBrTbSteAtgtEntry 2 }

-- 
-- *** THIS SUBTREE CURRENTLY NOT IMPLEMENTED ***
-- 

-- Vr/<string> Br Tb FowardTableEntry/address, domainNum
-- This component represents an entry in the transparent bridge forwarding 
-- table. Entries in this table serve to map a destination MAC address to a 
-- port in the bridge. Essentially, entries are learned and aged in this table. 
-- This means that entries that are not frequently used, are purged. The 
-- agingTime is a provisionable attribute under the TransparentBridge 
-- component. Other fields in this table are informative in nature. A 
-- collection of such entries constitutes a transparent bridge forwarding 
-- table. There can exist only sixteen domains when a spanning tree is 
-- desired specific to each domain. When there is only a single spanning 
-- tree spanning all the domains, the maximum number of domains 
-- possible are 4294967293.

vrBrTbFte OBJECT IDENTIFIER ::= { vrBrTb 4 }



vrBrTbFteRowStatusTable OBJECT-TYPE
   SYNTAX     SEQUENCE OF VrBrTbFteRowStatusEntry
   ACCESS     not-accessible
   STATUS     mandatory
   DESCRIPTION
     "*** THIS TABLE CURRENTLY NOT IMPLEMENTED ***

      This entry controls the addition and deletion of 
      vrBrTbFte components."
::= { vrBrTbFte 1 }

vrBrTbFteRowStatusEntry OBJECT-TYPE
   SYNTAX     VrBrTbFteRowStatusEntry
   ACCESS     not-accessible
   STATUS     mandatory
   DESCRIPTION
     "A single entry in the table represents a single 
      vrBrTbFte component."
   INDEX {
      vrIndex,
      vrBrIndex,
      vrBrTbIndex,
      vrBrTbFteAddressIndex,
      vrBrTbFteDomainNumIndex }
::= { vrBrTbFteRowStatusTable 1 }

VrBrTbFteRowStatusEntry ::= SEQUENCE {
   vrBrTbFteRowStatus
      RowStatus,
   vrBrTbFteComponentName
      DisplayString,
   vrBrTbFteStorageType
      StorageType,
   vrBrTbFteAddressIndex
      DashedHexString,
   vrBrTbFteDomainNumIndex
      Integer32 }

vrBrTbFteRowStatus OBJECT-TYPE
   SYNTAX     RowStatus 
   ACCESS     read-only
   STATUS     mandatory
   DESCRIPTION
     "This variable is used as the basis for SNMP naming of
      vrBrTbFte components.
      These components cannot be added nor deleted."
::= { vrBrTbFteRowStatusEntry 1 }

vrBrTbFteComponentName OBJECT-TYPE
   SYNTAX     DisplayString 
   ACCESS     read-only
   STATUS     mandatory
   DESCRIPTION
     "This variable provides the component's string name for
      use with the ASCII Console Interface"
::= { vrBrTbFteRowStatusEntry 2 }

vrBrTbFteStorageType OBJECT-TYPE
   SYNTAX     StorageType 
   ACCESS     read-only
   STATUS     mandatory
   DESCRIPTION
     "This variable represents the storage type value for the
      vrBrTbFte tables."
::= { vrBrTbFteRowStatusEntry 4 }

vrBrTbFteAddressIndex OBJECT-TYPE
   SYNTAX     DashedHexString (SIZE (6))
   ACCESS     not-accessible
   STATUS     mandatory
   DESCRIPTION
     "This variable represents an index for the vrBrTbFte tables."
::= { vrBrTbFteRowStatusEntry 10 }

vrBrTbFteDomainNumIndex OBJECT-TYPE
   SYNTAX     Integer32 (1..268435455)
   ACCESS     not-accessible
   STATUS     mandatory
   DESCRIPTION
     "This variable represents an index for the vrBrTbFte tables."
::= { vrBrTbFteRowStatusEntry 11 }

vrBrTbFteOperTable OBJECT-TYPE
   SYNTAX     SEQUENCE OF VrBrTbFteOperEntry
   ACCESS     not-accessible
   STATUS     mandatory
   DESCRIPTION
     "*** THIS TABLE CURRENTLY NOT IMPLEMENTED ***

      This group houses all the attributes that form the fields of a forwarding 
      table entry. Multiple such forwarding table entries put together form the 
      forwarding table. These attributes reflect the state of the transparent 
      bridge forwarding table."
::= { vrBrTbFte 10 }

vrBrTbFteOperEntry OBJECT-TYPE
   SYNTAX     VrBrTbFteOperEntry
   ACCESS     not-accessible
   STATUS     mandatory
   DESCRIPTION
     "An entry in the vrBrTbFteOperTable."
   INDEX {
      vrIndex,
      vrBrIndex,
      vrBrTbIndex,
      vrBrTbFteAddressIndex,
      vrBrTbFteDomainNumIndex }
::= { vrBrTbFteOperTable 1 }

VrBrTbFteOperEntry ::= SEQUENCE {
   vrBrTbFtePort
      AsciiString,
   vrBrTbFteAgeOfEntry
      Gauge32,
   vrBrTbFtePeerAddressInfo
      BridgeId,
   vrBrTbFteStatus
      INTEGER }

vrBrTbFtePort OBJECT-TYPE
   SYNTAX     AsciiString (SIZE (4..29))
   ACCESS     read-only
   STATUS     mandatory
   DESCRIPTION
     "This attribute is the port name through which the address was learnt. 
      This implies that the frames that are destined for a station whose MAC 
      address is the same as the address, will be forwarded through the bridge 
      port indicated by the attribute port.
      The attribute port is a string of the form 'BridgePortName-i', where 
      BridgePortName is the abbreviation of the corresponding bridge port 
      and i is the instance identifier of the ProtocolPort, the bridge port is 
      provisioned under. For example a TransparentBridgePort provisioned 
      under ProtocolPort/myport would have a name TBP-myport."
::= { vrBrTbFteOperEntry 3 }

vrBrTbFteAgeOfEntry OBJECT-TYPE
   SYNTAX     Gauge32 (0..1000000)
   ACCESS     read-only
   STATUS     mandatory
   DESCRIPTION
     "This attribute specifies the age of the forwarding table entry. This is used 
      to purge entries that have not been used for a certain period of time. This 
      feature is to ensure that only the recently used entries are kept in the 
      forwarding table. The time period for aging entries can be provisioned 
      through the attribute agingTime under the component 
      TransparentBridge."
::= { vrBrTbFteOperEntry 4 }

vrBrTbFtePeerAddressInfo OBJECT-TYPE
   SYNTAX     BridgeId (SIZE (8))
   ACCESS     read-only
   STATUS     mandatory
   DESCRIPTION
     "This attribute represents the learned peer address information. This 
      address is used to essentially tunnel frames to a peer bridge unit across a 
      network or a backbone. The tunneled frame is then appropriately 
      processed by the peer bridge unit. Fddi encapsulated bridging using 
      FddiETb bridge port and Source route encapsulated bridging using 
      SrseBridgePort & TbseBridgePort are examples of instances where this 
      attribute peerAddressInfo is used."
::= { vrBrTbFteOperEntry 5 }

vrBrTbFteStatus OBJECT-TYPE
   SYNTAX     INTEGER  {
                 learned(3) }
   ACCESS     read-only
   STATUS     mandatory
   DESCRIPTION
     "This attribute represents the status of the forwarding table entry. A value 
      of learned indicates that the entry was learned and cached from the 
      network. Please note that a only a value of learned is currently 
      supported."
   DEFVAL     { learned }
::= { vrBrTbFteOperEntry 6 }

-- 
-- *** THIS SUBTREE CURRENTLY NOT IMPLEMENTED ***
-- 

-- Vr/<string> Br Tb NcFowardTableEntry/address, domainNum
-- This component represents an entry in the transparent bridge forwarding 
-- table. This component is identical to ForwardTableEntry except the 
-- MAC address portion of the index of this component is in non-canonical 
-- form.

vrBrTbNcFte OBJECT IDENTIFIER ::= { vrBrTb 5 }



vrBrTbNcFteRowStatusTable OBJECT-TYPE
   SYNTAX     SEQUENCE OF VrBrTbNcFteRowStatusEntry
   ACCESS     not-accessible
   STATUS     mandatory
   DESCRIPTION
     "*** THIS TABLE CURRENTLY NOT IMPLEMENTED ***

      This entry controls the addition and deletion of 
      vrBrTbNcFte components."
::= { vrBrTbNcFte 1 }

vrBrTbNcFteRowStatusEntry OBJECT-TYPE
   SYNTAX     VrBrTbNcFteRowStatusEntry
   ACCESS     not-accessible
   STATUS     mandatory
   DESCRIPTION
     "A single entry in the table represents a single 
      vrBrTbNcFte component."
   INDEX {
      vrIndex,
      vrBrIndex,
      vrBrTbIndex,
      vrBrTbNcFteAddressIndex,
      vrBrTbNcFteDomainNumIndex }
::= { vrBrTbNcFteRowStatusTable 1 }

VrBrTbNcFteRowStatusEntry ::= SEQUENCE {
   vrBrTbNcFteRowStatus
      RowStatus,
   vrBrTbNcFteComponentName
      DisplayString,
   vrBrTbNcFteStorageType
      StorageType,
   vrBrTbNcFteAddressIndex
      DashedHexString,
   vrBrTbNcFteDomainNumIndex
      Integer32 }

vrBrTbNcFteRowStatus OBJECT-TYPE
   SYNTAX     RowStatus 
   ACCESS     read-only
   STATUS     mandatory
   DESCRIPTION
     "This variable is used as the basis for SNMP naming of
      vrBrTbNcFte components.
      These components cannot be added nor deleted."
::= { vrBrTbNcFteRowStatusEntry 1 }

vrBrTbNcFteComponentName OBJECT-TYPE
   SYNTAX     DisplayString 
   ACCESS     read-only
   STATUS     mandatory
   DESCRIPTION
     "This variable provides the component's string name for
      use with the ASCII Console Interface"
::= { vrBrTbNcFteRowStatusEntry 2 }

vrBrTbNcFteStorageType OBJECT-TYPE
   SYNTAX     StorageType 
   ACCESS     read-only
   STATUS     mandatory
   DESCRIPTION
     "This variable represents the storage type value for the
      vrBrTbNcFte tables."
::= { vrBrTbNcFteRowStatusEntry 4 }

vrBrTbNcFteAddressIndex OBJECT-TYPE
   SYNTAX     DashedHexString (SIZE (6))
   ACCESS     not-accessible
   STATUS     mandatory
   DESCRIPTION
     "This variable represents an index for the vrBrTbNcFte tables."
::= { vrBrTbNcFteRowStatusEntry 10 }

vrBrTbNcFteDomainNumIndex OBJECT-TYPE
   SYNTAX     Integer32 (1..268435455)
   ACCESS     not-accessible
   STATUS     mandatory
   DESCRIPTION
     "This variable represents an index for the vrBrTbNcFte tables."
::= { vrBrTbNcFteRowStatusEntry 11 }

vrBrTbNcFteOperTable OBJECT-TYPE
   SYNTAX     SEQUENCE OF VrBrTbNcFteOperEntry
   ACCESS     not-accessible
   STATUS     mandatory
   DESCRIPTION
     "*** THIS TABLE CURRENTLY NOT IMPLEMENTED ***

      This group houses all the attributes that form the fields of a forwarding 
      table entry. Multiple such forwarding table entries put together form the 
      forwarding table. These attributes reflect the state of the transparent 
      bridge forwarding table."
::= { vrBrTbNcFte 10 }

vrBrTbNcFteOperEntry OBJECT-TYPE
   SYNTAX     VrBrTbNcFteOperEntry
   ACCESS     not-accessible
   STATUS     mandatory
   DESCRIPTION
     "An entry in the vrBrTbNcFteOperTable."
   INDEX {
      vrIndex,
      vrBrIndex,
      vrBrTbIndex,
      vrBrTbNcFteAddressIndex,
      vrBrTbNcFteDomainNumIndex }
::= { vrBrTbNcFteOperTable 1 }

VrBrTbNcFteOperEntry ::= SEQUENCE {
   vrBrTbNcFtePort
      AsciiString,
   vrBrTbNcFteAgeOfEntry
      Gauge32,
   vrBrTbNcFtePeerAddressInfo
      BridgeId,
   vrBrTbNcFteStatus
      INTEGER }

vrBrTbNcFtePort OBJECT-TYPE
   SYNTAX     AsciiString (SIZE (4..29))
   ACCESS     read-only
   STATUS     mandatory
   DESCRIPTION
     "This attribute is the port name through which the address was learnt. 
      This implies that the frames that are destined for a station whose MAC 
      address is the same as the address, will be forwarded through the bridge 
      port indicated by the attribute port.
      The attribute port is a string of the form 'BridgePortName-i', where 
      BridgePortName is the abbreviation of the corresponding bridge port 
      and i is the instance identifier of the ProtocolPort, the bridge port is 
      provisioned under. For example a TransparentBridgePort provisioned 
      under ProtocolPort/myport would have a name TBP-myport."
::= { vrBrTbNcFteOperEntry 3 }

vrBrTbNcFteAgeOfEntry OBJECT-TYPE
   SYNTAX     Gauge32 (0..1000000)
   ACCESS     read-only
   STATUS     mandatory
   DESCRIPTION
     "This attribute specifies the age of the forwarding table entry. This is used 
      to purge entries that have not been used for a certain period of time. This 
      feature is to ensure that only the recently used entries are kept in the 
      forwarding table. The time period for aging entries can be provisioned 
      through the attribute agingTime under the component 
      TransparentBridge."
::= { vrBrTbNcFteOperEntry 4 }

vrBrTbNcFtePeerAddressInfo OBJECT-TYPE
   SYNTAX     BridgeId (SIZE (8))
   ACCESS     read-only
   STATUS     mandatory
   DESCRIPTION
     "This attribute represents the learned peer address information. This 
      address is used to essentially tunnel frames to a peer bridge unit across a 
      network or a backbone. The tunneled frame is then appropriately 
      processed by the peer bridge unit. Fddi encapsulated bridging using 
      FddiETb bridge port and Source route encapsulated bridging using 
      SrseBridgePort & TbseBridgePort are examples of instances where this 
      attribute peerAddressInfo is used."
::= { vrBrTbNcFteOperEntry 5 }

vrBrTbNcFteStatus OBJECT-TYPE
   SYNTAX     INTEGER  {
                 learned(3) }
   ACCESS     read-only
   STATUS     mandatory
   DESCRIPTION
     "This attribute represents the status of the forwarding table entry. A value 
      of learned indicates that the entry was learned and cached from the 
      network. Please note that a only a value of learned is currently 
      supported."
   DEFVAL     { learned }
::= { vrBrTbNcFteOperEntry 6 }


-- Vr/<string> Br SourceRouteBridge
-- This component represents the source route bridging scheme described 
-- in various IEEE documents. Source routing is a scheme whereby most 
-- of the routing decisions are made by the originating host. The bridge 
-- merely forwards frames based upon the route descriptor fields found in 
-- the individual frames. 
-- Source route bridges also process explorer frames traversing the 
-- network. The spanning tree protocol is (optionally) used to prevent loops 
-- and the duplication of explorer frames.

vrBrSrb OBJECT IDENTIFIER ::= { vrBr 5 }



vrBrSrbRowStatusTable OBJECT-TYPE
   SYNTAX     SEQUENCE OF VrBrSrbRowStatusEntry
   ACCESS     not-accessible
   STATUS     mandatory
   DESCRIPTION
     "This entry controls the addition and deletion of 
      vrBrSrb components."
::= { vrBrSrb 1 }

vrBrSrbRowStatusEntry OBJECT-TYPE
   SYNTAX     VrBrSrbRowStatusEntry
   ACCESS     not-accessible
   STATUS     mandatory
   DESCRIPTION
     "A single entry in the table represents a single 
      vrBrSrb component."
   INDEX {
      vrIndex,
      vrBrIndex,
      vrBrSrbIndex }
::= { vrBrSrbRowStatusTable 1 }

VrBrSrbRowStatusEntry ::= SEQUENCE {
   vrBrSrbRowStatus
      RowStatus,
   vrBrSrbComponentName
      DisplayString,
   vrBrSrbStorageType
      StorageType,
   vrBrSrbIndex
      NonReplicated }

vrBrSrbRowStatus OBJECT-TYPE
   SYNTAX     RowStatus 
   ACCESS     read-write
   STATUS     mandatory
   DESCRIPTION
     "This variable is used as the basis for SNMP naming of
      vrBrSrb components.
      These components can be added and deleted."
::= { vrBrSrbRowStatusEntry 1 }

vrBrSrbComponentName OBJECT-TYPE
   SYNTAX     DisplayString 
   ACCESS     read-only
   STATUS     mandatory
   DESCRIPTION
     "This variable provides the component's string name for
      use with the ASCII Console Interface"
::= { vrBrSrbRowStatusEntry 2 }

vrBrSrbStorageType OBJECT-TYPE
   SYNTAX     StorageType 
   ACCESS     read-only
   STATUS     mandatory
   DESCRIPTION
     "This variable represents the storage type value for the
      vrBrSrb tables."
::= { vrBrSrbRowStatusEntry 4 }

vrBrSrbIndex OBJECT-TYPE
   SYNTAX     NonReplicated 
   ACCESS     not-accessible
   STATUS     mandatory
   DESCRIPTION
     "This variable represents the index for the vrBrSrb tables."
::= { vrBrSrbRowStatusEntry 10 }

vrBrSrbProvTable OBJECT-TYPE
   SYNTAX     SEQUENCE OF VrBrSrbProvEntry
   ACCESS     not-accessible
   STATUS     mandatory
   DESCRIPTION
     "This group contains all provisionable attributes associated with source 
      route bridging. These attributes are global in nature as opposed to port 
      specific."
::= { vrBrSrb 10 }

vrBrSrbProvEntry OBJECT-TYPE
   SYNTAX     VrBrSrbProvEntry
   ACCESS     not-accessible
   STATUS     mandatory
   DESCRIPTION
     "An entry in the vrBrSrbProvTable."
   INDEX {
      vrIndex,
      vrBrIndex,
      vrBrSrbIndex }
::= { vrBrSrbProvTable 1 }

VrBrSrbProvEntry ::= SEQUENCE {
   vrBrSrbLanIdTableNumEntries
      Unsigned32,
   vrBrSrbAgingTime
      Unsigned32,
   vrBrSrbBridgeLfMode
      INTEGER }

vrBrSrbLanIdTableNumEntries OBJECT-TYPE
   SYNTAX     Unsigned32 (500..65535)
   ACCESS     read-write
   STATUS     mandatory
   DESCRIPTION
     "This attribute specifies the maximum number of entries in the LAN ID 
      table. This attribute provides a way to control the resources allocated to 
      the LAN ID table. The lanIdTableNumEntries value depends upon the 
      VirtualRouter attribute bridgingMaxHeapSpace and the number of 
      source route bridge ports provisioned for this SourceRouteBridge.
      
      Consider the following attributes of the SourceRouteBridge component 
      when adjusting this number:
      - totalLanIdTableEntries
      - numLanIdTEntriesFree
      - numLanIdTEntriesDenied"
   DEFVAL     { 500 }
::= { vrBrSrbProvEntry 1 }

vrBrSrbAgingTime OBJECT-TYPE
   SYNTAX     Unsigned32 (10..1000000)
   ACCESS     read-write
   STATUS     mandatory
   DESCRIPTION
     "This attribute specifies the time period used in seconds, to age out 
      dynamically learned entries in the forwarding table. The aging time can 
      change, triggered by a spanning tree topology change. The operational 
      value of the aging time is reflected in the attribute agingTimeOper under 
      the SpanningTreeProtocol component."
   DEFVAL     { 300 }
::= { vrBrSrbProvEntry 2 }

vrBrSrbBridgeLfMode OBJECT-TYPE
   SYNTAX     INTEGER  {
                 mode3(1),
                 mode6(2) }
   ACCESS     read-only
   STATUS     mandatory
   DESCRIPTION
     "This attribute indicates whether the bridge operates using the older 3-bit 
      length negotiation field or the newer 6-bit length field in the routing 
      information field. Only the 3-bit field is supported at this time."
   DEFVAL     { mode3 }
::= { vrBrSrbProvEntry 3 }

vrBrSrbStatsTable OBJECT-TYPE
   SYNTAX     SEQUENCE OF VrBrSrbStatsEntry
   ACCESS     not-accessible
   STATUS     mandatory
   DESCRIPTION
     "This group contains all statistical attributes associated with the 
      SourceRouteBridge. These attributes are global in nature as opposed to 
      port specific."
::= { vrBrSrb 11 }

vrBrSrbStatsEntry OBJECT-TYPE
   SYNTAX     VrBrSrbStatsEntry
   ACCESS     not-accessible
   STATUS     mandatory
   DESCRIPTION
     "An entry in the vrBrSrbStatsTable."
   INDEX {
      vrIndex,
      vrBrIndex,
      vrBrSrbIndex }
::= { vrBrSrbStatsTable 1 }

VrBrSrbStatsEntry ::= SEQUENCE {
   vrBrSrbTotalLanIdTableEntries
      Counter32,
   vrBrSrbNumLanIdtEntriesFree
      Counter32,
   vrBrSrbNumLanIdtEntriesDenied
      Counter32 }

vrBrSrbTotalLanIdTableEntries OBJECT-TYPE
   SYNTAX     Counter32 
   ACCESS     read-only
   STATUS     mandatory
   DESCRIPTION
     "This attribute specifies the total number of LAN ID Table entries. The 
      total includes both static and dynamic entries. The value is limited by 
      the attribute lanIdTableNumEntries, a provisionable attribute. If the 
      value is consistently approaching the value of lanIdTableNumEntries it 
      is advisable to increase the value provisioned for lanIdTableNumEntries."
::= { vrBrSrbStatsEntry 1 }

vrBrSrbNumLanIdtEntriesFree OBJECT-TYPE
   SYNTAX     Counter32 
   ACCESS     read-only
   STATUS     mandatory
   DESCRIPTION
     "This attribute specifies the number of LanIdTable entries that are 
      available for use. A consistently high value indicates a resource surplus 
      in terms of memory requirements for the bridge. This surplus could be 
      utilized elsewhere if need be. The value of this attribute is directly 
      influenced by the value of the lanIdTableNumEntries."
::= { vrBrSrbStatsEntry 2 }

vrBrSrbNumLanIdtEntriesDenied OBJECT-TYPE
   SYNTAX     Counter32 
   ACCESS     read-only
   STATUS     mandatory
   DESCRIPTION
     "This attribute indicates the number of instances where an entry was not 
      placed in the LanIdTable due to the lack of free entries. A rapid increase 
      indicates a shortage of free entries. To reduce the shortage increase the 
      provisioned lanIdTableNumEntries value."
::= { vrBrSrbStatsEntry 3 }


-- Vr/<string> Br Tb Stp/<Decimal>
-- Vr/<string> Br Sr Stp/<Decimal>
-- This component represents the Spanning Tree Protocol for the bridge. 
-- Bridges in a network use the Spanning Tree Protocol to provide a loop 
-- free, fault tolerant network topology. As there may be a need for 
-- multiple domains in the network, bridging allows provisioning of 
-- domain specific spanning tree instances.
-- Individual spanning tree instances are indexed using the domain number. 
-- The domain numbers assigned are only unique to the bridge type so 
-- domain numbers may be shared between TransparentBridge and 
-- SourceRouteBridge.
-- Note that only 16 instances of this component are allowed and includes 
-- the backbone spanning tree instance.
-- The instance identifier of the SpanningTreeProtocol component is 
-- significant as it is indicative of the domain that spanning tree instance 
-- governs.

vrBrSrbStp OBJECT IDENTIFIER ::= { vrBrSrb 2 }



vrBrSrbStpRowStatusTable OBJECT-TYPE
   SYNTAX     SEQUENCE OF VrBrSrbStpRowStatusEntry
   ACCESS     not-accessible
   STATUS     mandatory
   DESCRIPTION
     "This entry controls the addition and deletion of 
      vrBrSrbStp components."
::= { vrBrSrbStp 1 }

vrBrSrbStpRowStatusEntry OBJECT-TYPE
   SYNTAX     VrBrSrbStpRowStatusEntry
   ACCESS     not-accessible
   STATUS     mandatory
   DESCRIPTION
     "A single entry in the table represents a single 
      vrBrSrbStp component."
   INDEX {
      vrIndex,
      vrBrIndex,
      vrBrSrbIndex,
      vrBrSrbStpIndex }
::= { vrBrSrbStpRowStatusTable 1 }

VrBrSrbStpRowStatusEntry ::= SEQUENCE {
   vrBrSrbStpRowStatus
      RowStatus,
   vrBrSrbStpComponentName
      DisplayString,
   vrBrSrbStpStorageType
      StorageType,
   vrBrSrbStpIndex
      Integer32 }

vrBrSrbStpRowStatus OBJECT-TYPE
   SYNTAX     RowStatus 
   ACCESS     read-write
   STATUS     mandatory
   DESCRIPTION
     "This variable is used as the basis for SNMP naming of
      vrBrSrbStp components.
      These components can be added and deleted."
::= { vrBrSrbStpRowStatusEntry 1 }

vrBrSrbStpComponentName OBJECT-TYPE
   SYNTAX     DisplayString 
   ACCESS     read-only
   STATUS     mandatory
   DESCRIPTION
     "This variable provides the component's string name for
      use with the ASCII Console Interface"
::= { vrBrSrbStpRowStatusEntry 2 }

vrBrSrbStpStorageType OBJECT-TYPE
   SYNTAX     StorageType 
   ACCESS     read-only
   STATUS     mandatory
   DESCRIPTION
     "This variable represents the storage type value for the
      vrBrSrbStp tables."
::= { vrBrSrbStpRowStatusEntry 4 }

vrBrSrbStpIndex OBJECT-TYPE
   SYNTAX     Integer32 (1..268435455)
   ACCESS     not-accessible
   STATUS     mandatory
   DESCRIPTION
     "This variable represents the index for the vrBrSrbStp tables."
::= { vrBrSrbStpRowStatusEntry 10 }

vrBrSrbStpProvTable OBJECT-TYPE
   SYNTAX     SEQUENCE OF VrBrSrbStpProvEntry
   ACCESS     not-accessible
   STATUS     mandatory
   DESCRIPTION
     "This group houses all the provisionable attributes that are applicable to 
      the spanning tree protocol. These are global attributes and not port 
      specific attributes. These attributes have a direct impact on the way this 
      bridge participates in the spanning tree protocol."
::= { vrBrSrbStp 10 }

vrBrSrbStpProvEntry OBJECT-TYPE
   SYNTAX     VrBrSrbStpProvEntry
   ACCESS     not-accessible
   STATUS     mandatory
   DESCRIPTION
     "An entry in the vrBrSrbStpProvTable."
   INDEX {
      vrIndex,
      vrBrIndex,
      vrBrSrbIndex,
      vrBrSrbStpIndex }
::= { vrBrSrbStpProvTable 1 }

VrBrSrbStpProvEntry ::= SEQUENCE {
   vrBrSrbStpStpMode
      INTEGER,
   vrBrSrbStpProtocolSpec
      INTEGER,
   vrBrSrbStpPriority
      Unsigned32,
   vrBrSrbStpBridgeMaxAge
      Unsigned32,
   vrBrSrbStpBridgeHelloTime
      Unsigned32,
   vrBrSrbStpBridgeForwardDelay
      Unsigned32 }

vrBrSrbStpStpMode OBJECT-TYPE
   SYNTAX     INTEGER  {
                 access(1),
                 backbone(2) }
   ACCESS     read-write
   STATUS     mandatory
   DESCRIPTION
     "This attribute determines if this stp instance is to act as the stp instance 
      for the backbone or an stp instance for a non-backbone media 
      configuration. There can exist only one Backbone stp instance per 
      virtual router. If the attribute domainStpTbState is set to a value on and 
      Backbone bridge ports have been provisioned, there should exist a 
      Backbone stp instance. Please note that it is not permissible to assign the 
      instance identifier of this stp instance as domain number of any access 
      bridge port. In case of stp instances that are non-Backbone, the instance 
      identifier is indicative of the domain number the stp is operational in."
   DEFVAL     { access }
::= { vrBrSrbStpProvEntry 1 }

vrBrSrbStpProtocolSpec OBJECT-TYPE
   SYNTAX     INTEGER  {
                 both(1),
                 dec(2),
                 ieee8021d(3) }
   ACCESS     read-write
   STATUS     mandatory
   DESCRIPTION
     "This attribute specifies the type of spanning tree protocols that are in 
      operation in the bridge. This means that this bridge participates in the 
      types spanning tree protocol indicated by this attribute."
   DEFVAL     { ieee8021d }
::= { vrBrSrbStpProvEntry 2 }

vrBrSrbStpPriority OBJECT-TYPE
   SYNTAX     Unsigned32 (0..65535)
   ACCESS     read-write
   STATUS     mandatory
   DESCRIPTION
     "This attribute is used to construct the bridgeId. It forms the first two 
      octets of the bridgeId and the remaining 6 octets are made up of the 
      bridgeMACAddress. The priority also determines the root bridge of the 
      spanning tree topology. Manipulating this attribute might lead to a 
      change in the spanning tree topology."
   DEFVAL     { 32768 }
::= { vrBrSrbStpProvEntry 3 }

vrBrSrbStpBridgeMaxAge OBJECT-TYPE
   SYNTAX     Unsigned32 (600..4000)
   ACCESS     read-write
   STATUS     mandatory
   DESCRIPTION
     "The maximum age of spanning tree protocol information learned from 
      the network on any bridge port before it is discarded. This value is used 
      by this bridge and all the other bridges, when this bridge is the root 
      bridge of the spanning tree topology. The following relationships are 
      enforced as required by the IEEE 802.1d standards document.
      2 *(bridgeForwardDelay -1.0seconds) >= bridgeMaxAge, 
      bridgeMaxAge >= 2 * bridgeHelloTime + 1.0 seconds.
      DESCRIPTION"
   DEFVAL     { 2000 }
::= { vrBrSrbStpProvEntry 4 }

vrBrSrbStpBridgeHelloTime OBJECT-TYPE
   SYNTAX     Unsigned32 (100..1000)
   ACCESS     read-write
   STATUS     mandatory
   DESCRIPTION
     "This attribute specifies the time interval between the transmission of 
      configuration BPDUs on any bridge port when this bridge becomes the 
      root bridge. This attribute value is also used by all the other bridges in 
      the Spanning Tree while this bridge is the root. 
      The following relationship is enforced as required by the IEEE 802.1d 
      standards document. 
      bridgeMaxAge >= 2 * bridgeHelloTime + 1.0 seconds."
   DEFVAL     { 200 }
::= { vrBrSrbStpProvEntry 5 }

vrBrSrbStpBridgeForwardDelay OBJECT-TYPE
   SYNTAX     Unsigned32 (400..3000)
   ACCESS     read-write
   STATUS     mandatory
   DESCRIPTION
     "This attribute specifies how fast a bridge port changes its STP state 
      while progressing towards the forwarding state. It is also used as 
      agingTime to age dynamic entries in the forwarding table once a 
      topology change is detected. This attribute is used by all the bridges 
      participating in the spanning tree protocol, when this bridge is the root 
      bridge.
      The following relationship is enforced as required by the IEEE 802.1d 
      standards document. 
      2 *(bridgeForwardDelay -1.0sconds) >= bridgeMaxAge."
   DEFVAL     { 1500 }
::= { vrBrSrbStpProvEntry 6 }

vrBrSrbStpOperTable OBJECT-TYPE
   SYNTAX     SEQUENCE OF VrBrSrbStpOperEntry
   ACCESS     not-accessible
   STATUS     mandatory
   DESCRIPTION
     "This group houses all the operational, spanning tree protocol attributes. 
      These attributes are applicable in a global manner and are not specific to 
      a bridge port."
::= { vrBrSrbStp 11 }

vrBrSrbStpOperEntry OBJECT-TYPE
   SYNTAX     VrBrSrbStpOperEntry
   ACCESS     not-accessible
   STATUS     mandatory
   DESCRIPTION
     "An entry in the vrBrSrbStpOperTable."
   INDEX {
      vrIndex,
      vrBrIndex,
      vrBrSrbIndex,
      vrBrSrbStpIndex }
::= { vrBrSrbStpOperTable 1 }

VrBrSrbStpOperEntry ::= SEQUENCE {
   vrBrSrbStpBridgeId
      BridgeId,
   vrBrSrbStpRootPortName
      AsciiString,
   vrBrSrbStpTimeSinceTopologyChange
      Unsigned32,
   vrBrSrbStpTopologyChangeDetect
      INTEGER,
   vrBrSrbStpTopologyChanges
      Counter32,
   vrBrSrbStpDesignatedRoot
      BridgeId,
   vrBrSrbStpRootCost
      Unsigned32,
   vrBrSrbStpMaxAge
      Unsigned32,
   vrBrSrbStpAgingTimeOper
      Unsigned32,
   vrBrSrbStpHelloTime
      Unsigned32,
   vrBrSrbStpHoldTime
      Unsigned32,
   vrBrSrbStpFwdDelay
      Unsigned32 }

vrBrSrbStpBridgeId OBJECT-TYPE
   SYNTAX     BridgeId (SIZE (8))
   ACCESS     read-only
   STATUS     mandatory
   DESCRIPTION
     "This attribute specifies the identifier value of this bridge, which serves to 
      uniquely represent this bridge in the spanning tree topology. Thus, a 
      bridgeId is unique only in the spanning tree instance the bridge in 
      participating in. If multiple domain spanning trees exist then the same 
      bridgeId can be re-used across these spanning tree instances."
::= { vrBrSrbStpOperEntry 1 }

vrBrSrbStpRootPortName OBJECT-TYPE
   SYNTAX     AsciiString (SIZE (4..29))
   ACCESS     read-only
   STATUS     mandatory
   DESCRIPTION
     "This attribute specifies the name of the bridge port that offers the lowest 
      cost route to the root bridge of the spanning tree topology.The attribute 
      rootPortName is a string of the form 'BridgePortName-i', where 
      BridgePortName is the abbreviation of the corresponding bridge port 
      and i is the instance identifier of the ProtocolPort, the bridge port is 
      provisioned under. For example a TransparentBridgePort provisioned 
      under ProtocolPort/myport would have a name TBP-myport. 
      If multiple instances of spanning tree are operational, then there will 
      exist a rootPortName value for each instance of the spanning tree 
      running, and is applicable to that instance alone."
::= { vrBrSrbStpOperEntry 2 }

vrBrSrbStpTimeSinceTopologyChange OBJECT-TYPE
   SYNTAX     Unsigned32 (0..4294967295)
   ACCESS     read-only
   STATUS     mandatory
   DESCRIPTION
     "This attribute specifies the time since a spanning tree topology change 
      was detected by this bridge."
   DEFVAL     { 0 }
::= { vrBrSrbStpOperEntry 3 }

vrBrSrbStpTopologyChangeDetect OBJECT-TYPE
   SYNTAX     INTEGER  {
                 false(0),
                 true(1) }
   ACCESS     read-only
   STATUS     mandatory
   DESCRIPTION
     "This attribute specifies whether or not a topology change was detected. 
      This flag is set when a bpdu with the topology detect flag set is received 
      from the root bridge. If this bridge is the root bridge this flag is set on 
      receipt of a topology change notification bpdu. It is reset after a fixed 
      length of time."
   DEFVAL     { false }
::= { vrBrSrbStpOperEntry 4 }

vrBrSrbStpTopologyChanges OBJECT-TYPE
   SYNTAX     Counter32 
   ACCESS     read-only
   STATUS     mandatory
   DESCRIPTION
     "This attribute is indicative of the number of topology changes detected 
      by this bridge since the last bridge reset. This counter wraps around its 
      maximum value of 4294967295."
::= { vrBrSrbStpOperEntry 5 }

vrBrSrbStpDesignatedRoot OBJECT-TYPE
   SYNTAX     BridgeId (SIZE (8))
   ACCESS     read-only
   STATUS     mandatory
   DESCRIPTION
     "This attribute specifies the identifier of the bridge that this bridge treats 
      as the root of the spanning tree topology. The root of the spanning tree 
      topology is chosen through exchange."
::= { vrBrSrbStpOperEntry 6 }

vrBrSrbStpRootCost OBJECT-TYPE
   SYNTAX     Unsigned32 (1..65535)
   ACCESS     read-only
   STATUS     mandatory
   DESCRIPTION
     "This attribute specifies the cost of the path to the root as seen by this 
      bridge."
::= { vrBrSrbStpOperEntry 8 }

vrBrSrbStpMaxAge OBJECT-TYPE
   SYNTAX     Unsigned32 (600..4000)
   ACCESS     read-only
   STATUS     mandatory
   DESCRIPTION
     "This attribute specifies the maximum age of the spanning tree protocol 
      info learnt from a port, before it is discarded."
   DEFVAL     { 2000 }
::= { vrBrSrbStpOperEntry 9 }

vrBrSrbStpAgingTimeOper OBJECT-TYPE
   SYNTAX     Unsigned32 (10..1000000)
   ACCESS     read-only
   STATUS     mandatory
   DESCRIPTION
     "This attribute specifies the time period used in seconds, to age out 
      dynamically learned entries in the forwarding table. The aging time is 
      specific to a spanning tree protocol instance running. A value for the 
      aging time of the current instance of the spanning tree protocol can be 
      provisioned through the attribute agingTime under the InwBrTb 
      component. The agingTimeOper attribute assumes the value of the 
      bridgeForwardDelay while a topology change is in progress. This is 
      done to facilitate quick aging out of the learned entries that might have 
      become obsolete due to a spanning tree topology change."
   DEFVAL     { 300 }
::= { vrBrSrbStpOperEntry 10 }

vrBrSrbStpHelloTime OBJECT-TYPE
   SYNTAX     Unsigned32 (100..1000)
   ACCESS     read-only
   STATUS     mandatory
   DESCRIPTION
     "This attribute specifies the time interval between the transmission of the 
      configuration BPDUs. This value is obtained from the root bridge of the 
      spanning tree topology, through bridge protocol data units. This value 
      should be the value assigned to the attribute bridgeHelloTime of the root 
      bridge."
   DEFVAL     { 200 }
::= { vrBrSrbStpOperEntry 11 }

vrBrSrbStpHoldTime OBJECT-TYPE
   SYNTAX     Unsigned32 (100)
   ACCESS     read-only
   STATUS     mandatory
   DESCRIPTION
     "This attribute specifies the interval of time which no more than two 
      BPDUs should be sent."
   DEFVAL     { 100 }
::= { vrBrSrbStpOperEntry 12 }

vrBrSrbStpFwdDelay OBJECT-TYPE
   SYNTAX     Unsigned32 (400..3000)
   ACCESS     read-only
   STATUS     mandatory
   DESCRIPTION
     "This attribute specifies how much time a port spends in any state while 
      progressing towards the forwarding state. It is also used to age out 
      learned entries while a topology change is in progress.This value should 
      be the value assigned to the attribute bridgefwdDelay of the root bridge."
   DEFVAL     { 1500 }
::= { vrBrSrbStpOperEntry 13 }

-- 
-- *** THIS SUBTREE CURRENTLY NOT IMPLEMENTED ***
-- 

-- Vr/<string> Br Srb LanIdTableEntry/lanId, domainNum
-- This component represents an entry in the LAN ID Table. The LAN ID 
-- Table is used by the SourceRouteBridge logic to associate a particular 
-- bridge port with a LAN ID found in the route descriptor field of a source 
-- route frame. Static entries reference bridge ports local to the bridge.

vrBrSrbLte OBJECT IDENTIFIER ::= { vrBrSrb 3 }



vrBrSrbLteRowStatusTable OBJECT-TYPE
   SYNTAX     SEQUENCE OF VrBrSrbLteRowStatusEntry
   ACCESS     not-accessible
   STATUS     mandatory
   DESCRIPTION
     "*** THIS TABLE CURRENTLY NOT IMPLEMENTED ***

      This entry controls the addition and deletion of 
      vrBrSrbLte components."
::= { vrBrSrbLte 1 }

vrBrSrbLteRowStatusEntry OBJECT-TYPE
   SYNTAX     VrBrSrbLteRowStatusEntry
   ACCESS     not-accessible
   STATUS     mandatory
   DESCRIPTION
     "A single entry in the table represents a single 
      vrBrSrbLte component."
   INDEX {
      vrIndex,
      vrBrIndex,
      vrBrSrbIndex,
      vrBrSrbLteLanIdIndex,
      vrBrSrbLteDomainNumIndex }
::= { vrBrSrbLteRowStatusTable 1 }

VrBrSrbLteRowStatusEntry ::= SEQUENCE {
   vrBrSrbLteRowStatus
      RowStatus,
   vrBrSrbLteComponentName
      DisplayString,
   vrBrSrbLteStorageType
      StorageType,
   vrBrSrbLteLanIdIndex
      Integer32,
   vrBrSrbLteDomainNumIndex
      Integer32 }

vrBrSrbLteRowStatus OBJECT-TYPE
   SYNTAX     RowStatus 
   ACCESS     read-only
   STATUS     mandatory
   DESCRIPTION
     "This variable is used as the basis for SNMP naming of
      vrBrSrbLte components.
      These components cannot be added nor deleted."
::= { vrBrSrbLteRowStatusEntry 1 }

vrBrSrbLteComponentName OBJECT-TYPE
   SYNTAX     DisplayString 
   ACCESS     read-only
   STATUS     mandatory
   DESCRIPTION
     "This variable provides the component's string name for
      use with the ASCII Console Interface"
::= { vrBrSrbLteRowStatusEntry 2 }

vrBrSrbLteStorageType OBJECT-TYPE
   SYNTAX     StorageType 
   ACCESS     read-only
   STATUS     mandatory
   DESCRIPTION
     "This variable represents the storage type value for the
      vrBrSrbLte tables."
::= { vrBrSrbLteRowStatusEntry 4 }

vrBrSrbLteLanIdIndex OBJECT-TYPE
   SYNTAX     Integer32 (0..4095 | 65535)
   ACCESS     not-accessible
   STATUS     mandatory
   DESCRIPTION
     "This variable represents an index for the vrBrSrbLte tables."
::= { vrBrSrbLteRowStatusEntry 10 }

vrBrSrbLteDomainNumIndex OBJECT-TYPE
   SYNTAX     Integer32 (1..268435455)
   ACCESS     not-accessible
   STATUS     mandatory
   DESCRIPTION
     "This variable represents an index for the vrBrSrbLte tables."
::= { vrBrSrbLteRowStatusEntry 11 }

vrBrSrbLteOperTable OBJECT-TYPE
   SYNTAX     SEQUENCE OF VrBrSrbLteOperEntry
   ACCESS     not-accessible
   STATUS     mandatory
   DESCRIPTION
     "*** THIS TABLE CURRENTLY NOT IMPLEMENTED ***

      This group contains all the fields of a LAN ID Table entry."
::= { vrBrSrbLte 10 }

vrBrSrbLteOperEntry OBJECT-TYPE
   SYNTAX     VrBrSrbLteOperEntry
   ACCESS     not-accessible
   STATUS     mandatory
   DESCRIPTION
     "An entry in the vrBrSrbLteOperTable."
   INDEX {
      vrIndex,
      vrBrIndex,
      vrBrSrbIndex,
      vrBrSrbLteLanIdIndex,
      vrBrSrbLteDomainNumIndex }
::= { vrBrSrbLteOperTable 1 }

VrBrSrbLteOperEntry ::= SEQUENCE {
   vrBrSrbLtePortName
      AsciiString,
   vrBrSrbLteAgeOfEntry
      Unsigned32,
   vrBrSrbLtePeerMACAddress
      DashedHexString,
   vrBrSrbLteTypeOfEntry
      INTEGER }

vrBrSrbLtePortName OBJECT-TYPE
   SYNTAX     AsciiString (SIZE (4..29))
   ACCESS     read-only
   STATUS     mandatory
   DESCRIPTION
     "This attribute specifies the name of the bridge port the frame should be 
      forwarded through to reach the desired Lan. In the case where the 
      desired Lan is across a TB/SRT cloud, this entry would have the name 
      of the SrSeBridgePort. 
      The attribute portName is a string of the form 'BridgePortName-i', 
      where BridgePortName is the abbreviation of the corresponding bridge 
      port and i is the instance identifier of the ProtocolPort the bridge port is 
      provisioned under. For example a SourceRouteBridgePort provisioned 
      under ProtocolPort/MyPort would have a name SrBP-MyPort. Please 
      note that the attribute portName cannot have a value of TBP, FddiETb, 
      Tbse, Tbcl, Tbsr, Srsg, Tbsg.
      DESCRIPTION"
::= { vrBrSrbLteOperEntry 1 }

vrBrSrbLteAgeOfEntry OBJECT-TYPE
   SYNTAX     Unsigned32 (0..4294967295)
   ACCESS     read-only
   STATUS     mandatory
   DESCRIPTION
     "This attribute specifies the age of this entry in seconds."
::= { vrBrSrbLteOperEntry 2 }

vrBrSrbLtePeerMACAddress OBJECT-TYPE
   SYNTAX     DashedHexString (SIZE (6))
   ACCESS     read-only
   STATUS     mandatory
   DESCRIPTION
     "This attribute specifies the MAC address of a bridge unit found across an 
      transparent bridge/source route transparent network whose LAN ID is 
      referenced by the attribute lanId. The peerMACAddress for static entries 
      will be all zeroes."
::= { vrBrSrbLteOperEntry 3 }

vrBrSrbLteTypeOfEntry OBJECT-TYPE
   SYNTAX     INTEGER  {
                 static(0),
                 dynamic(1) }
   ACCESS     read-only
   STATUS     mandatory
   DESCRIPTION
     "This attribute specifies the type of the LAN ID table entry. LAN ID table 
      entries may be either static or dynamic. Dynamic entries imply that to 
      reach the desired LAN source route frames need to be tunneled through 
      a TB/SRT network, to another bridge unit which is attached to the LAN. 
      These entries have a peerMACAddress associated with them and may be 
      removed through the aging mechanism of the LAN ID table. Static 
      entries on the other hand contain information about LANs that may be 
      reached directly through bridge ports attached to the bridge. They are 
      not aged and do not have a peerMACAddress associated with them."
::= { vrBrSrbLteOperEntry 4 }


-- ClusterBridge
-- The ClusterBridge component represents 
-- one ClusterBridge application. It allows a set 
-- of bridged ports to be treated as one routed 
-- port.

cB OBJECT IDENTIFIER ::= { components 103 }



cBRowStatusTable OBJECT-TYPE
   SYNTAX     SEQUENCE OF CBRowStatusEntry
   ACCESS     not-accessible
   STATUS     mandatory
   DESCRIPTION
     "This entry controls the addition and deletion of 
      cB components."
::= { cB 1 }

cBRowStatusEntry OBJECT-TYPE
   SYNTAX     CBRowStatusEntry
   ACCESS     not-accessible
   STATUS     mandatory
   DESCRIPTION
     "A single entry in the table represents a single 
      cB component."
   INDEX {
      cBIndex }
::= { cBRowStatusTable 1 }

CBRowStatusEntry ::= SEQUENCE {
   cBRowStatus
      RowStatus,
   cBComponentName
      DisplayString,
   cBStorageType
      StorageType,
   cBIndex
      NonReplicated }

cBRowStatus OBJECT-TYPE
   SYNTAX     RowStatus 
   ACCESS     read-write
   STATUS     mandatory
   DESCRIPTION
     "This variable is used as the basis for SNMP naming of
      cB components.
      These components can be added and deleted."
::= { cBRowStatusEntry 1 }

cBComponentName OBJECT-TYPE
   SYNTAX     DisplayString 
   ACCESS     read-only
   STATUS     mandatory
   DESCRIPTION
     "This variable provides the component's string name for
      use with the ASCII Console Interface"
::= { cBRowStatusEntry 2 }

cBStorageType OBJECT-TYPE
   SYNTAX     StorageType 
   ACCESS     read-only
   STATUS     mandatory
   DESCRIPTION
     "This variable represents the storage type value for the
      cB tables."
::= { cBRowStatusEntry 4 }

cBIndex OBJECT-TYPE
   SYNTAX     NonReplicated 
   ACCESS     not-accessible
   STATUS     mandatory
   DESCRIPTION
     "This variable represents the index for the cB tables."
::= { cBRowStatusEntry 10 }

cBAdminControlTable OBJECT-TYPE
   SYNTAX     SEQUENCE OF CBAdminControlEntry
   ACCESS     not-accessible
   STATUS     mandatory
   DESCRIPTION
     "This group includes the Administrative Control attribute. This attribute 
      defines the current administrative state of this component."
::= { cB 10 }

cBAdminControlEntry OBJECT-TYPE
   SYNTAX     CBAdminControlEntry
   ACCESS     not-accessible
   STATUS     mandatory
   DESCRIPTION
     "An entry in the cBAdminControlTable."
   INDEX {
      cBIndex }
::= { cBAdminControlTable 1 }

CBAdminControlEntry ::= SEQUENCE {
   cBSnmpAdminStatus
      INTEGER }

cBSnmpAdminStatus OBJECT-TYPE
   SYNTAX     INTEGER  {
                 up(1),
                 down(2),
                 testing(3) }
   ACCESS     read-write
   STATUS     obsolete
   DESCRIPTION
     "The desired state of the interface. The up state indicates the interface is 
      operational and packet forwarding is allowed. The down state indicates 
      the interface is not operational and packet forwarding is unavailable. 
      The testing state indicates that no operational packets can be passed."
   DEFVAL     { up }
::= { cBAdminControlEntry 1 }

cBIfEntryTable OBJECT-TYPE
   SYNTAX     SEQUENCE OF CBIfEntryEntry
   ACCESS     not-accessible
   STATUS     mandatory
   DESCRIPTION
     "This group contains the provisionable attributes for the ifEntry."
::= { cB 11 }

cBIfEntryEntry OBJECT-TYPE
   SYNTAX     CBIfEntryEntry
   ACCESS     not-accessible
   STATUS     mandatory
   DESCRIPTION
     "An entry in the cBIfEntryTable."
   INDEX {
      cBIndex }
::= { cBIfEntryTable 1 }

CBIfEntryEntry ::= SEQUENCE {
   cBIfAdminStatus
      INTEGER,
   cBIfIndex
      InterfaceIndex }

cBIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { cBIfEntryEntry 1 }

cBIfIndex OBJECT-TYPE
   SYNTAX     InterfaceIndex (1..65535)
   ACCESS     read-only
   STATUS     mandatory
   DESCRIPTION
     "This is the index for the IfEntry. Its value is automatically initialized 
      during the provisioning process."
::= { cBIfEntryEntry 2 }

cBMpTable OBJECT-TYPE
   SYNTAX     SEQUENCE OF CBMpEntry
   ACCESS     not-accessible
   STATUS     mandatory
   DESCRIPTION
     "This group contains the base provisioning data for the media base 
      component."
::= { cB 12 }

cBMpEntry OBJECT-TYPE
   SYNTAX     CBMpEntry
   ACCESS     not-accessible
   STATUS     mandatory
   DESCRIPTION
     "An entry in the cBMpTable."
   INDEX {
      cBIndex }
::= { cBMpTable 1 }

CBMpEntry ::= SEQUENCE {
   cBLinkToProtocolPort
      Link }

cBLinkToProtocolPort OBJECT-TYPE
   SYNTAX     Link 
   ACCESS     read-write
   STATUS     mandatory
   DESCRIPTION
     "This attribute specifies the ProtocolPort to which this interface is 
      linked to. The protocol port is the logical interface to the network. 
      The protocol port component describes the logical characteristics of 
      this interface."
::= { cBMpEntry 1 }

cBOperTable OBJECT-TYPE
   SYNTAX     SEQUENCE OF CBOperEntry
   ACCESS     not-accessible
   STATUS     mandatory
   DESCRIPTION
     "This group includes the operational attibutes 
      which are specific to the ClusterBridge 
      component."
::= { cB 13 }

cBOperEntry OBJECT-TYPE
   SYNTAX     CBOperEntry
   ACCESS     not-accessible
   STATUS     mandatory
   DESCRIPTION
     "An entry in the cBOperTable."
   INDEX {
      cBIndex }
::= { cBOperTable 1 }

CBOperEntry ::= SEQUENCE {
   cBMacAddress
      MacAddress }

cBMacAddress OBJECT-TYPE
   SYNTAX     MacAddress (SIZE (6))
   ACCESS     read-only
   STATUS     mandatory
   DESCRIPTION
     "The medium access controller (MAC) address is 
      an address that is only recognized by one station 
      on the attached bus. This address is automatically 
      assigned by the system."
::= { cBOperEntry 1 }

cBStateTable OBJECT-TYPE
   SYNTAX     SEQUENCE OF CBStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { cB 14 }

cBStateEntry OBJECT-TYPE
   SYNTAX     CBStateEntry
   ACCESS     not-accessible
   STATUS     mandatory
   DESCRIPTION
     "An entry in the cBStateTable."
   INDEX {
      cBIndex }
::= { cBStateTable 1 }

CBStateEntry ::= SEQUENCE {
   cBAdminState
      INTEGER,
   cBOperationalState
      INTEGER,
   cBUsageState
      INTEGER }

cBAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { cBStateEntry 1 }

cBOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { cBStateEntry 2 }

cBUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { cBStateEntry 3 }

cBOperStatusTable OBJECT-TYPE
   SYNTAX     SEQUENCE OF CBOperStatusEntry
   ACCESS     not-accessible
   STATUS     mandatory
   DESCRIPTION
     "This group includes the Operational Status attribute. This attribute 
      defines the current operational state of this component."
::= { cB 15 }

cBOperStatusEntry OBJECT-TYPE
   SYNTAX     CBOperStatusEntry
   ACCESS     not-accessible
   STATUS     mandatory
   DESCRIPTION
     "An entry in the cBOperStatusTable."
   INDEX {
      cBIndex }
::= { cBOperStatusTable 1 }

CBOperStatusEntry ::= SEQUENCE {
   cBSnmpOperStatus
      INTEGER }

cBSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { cBOperStatusEntry 1 }


-- PseudoBridge
-- The PseudoBridge component represents 
-- one PseudoBridge application.

pB OBJECT IDENTIFIER ::= { components 104 }



pBRowStatusTable OBJECT-TYPE
   SYNTAX     SEQUENCE OF PBRowStatusEntry
   ACCESS     not-accessible
   STATUS     mandatory
   DESCRIPTION
     "This entry controls the addition and deletion of 
      pB components."
::= { pB 1 }

pBRowStatusEntry OBJECT-TYPE
   SYNTAX     PBRowStatusEntry
   ACCESS     not-accessible
   STATUS     mandatory
   DESCRIPTION
     "A single entry in the table represents a single 
      pB component."
   INDEX {
      pBIndex }
::= { pBRowStatusTable 1 }

PBRowStatusEntry ::= SEQUENCE {
   pBRowStatus
      RowStatus,
   pBComponentName
      DisplayString,
   pBStorageType
      StorageType,
   pBIndex
      NonReplicated }

pBRowStatus OBJECT-TYPE
   SYNTAX     RowStatus 
   ACCESS     read-write
   STATUS     mandatory
   DESCRIPTION
     "This variable is used as the basis for SNMP naming of
      pB components.
      These components can be added and deleted."
::= { pBRowStatusEntry 1 }

pBComponentName OBJECT-TYPE
   SYNTAX     DisplayString 
   ACCESS     read-only
   STATUS     mandatory
   DESCRIPTION
     "This variable provides the component's string name for
      use with the ASCII Console Interface"
::= { pBRowStatusEntry 2 }

pBStorageType OBJECT-TYPE
   SYNTAX     StorageType 
   ACCESS     read-only
   STATUS     mandatory
   DESCRIPTION
     "This variable represents the storage type value for the
      pB tables."
::= { pBRowStatusEntry 4 }

pBIndex OBJECT-TYPE
   SYNTAX     NonReplicated 
   ACCESS     not-accessible
   STATUS     mandatory
   DESCRIPTION
     "This variable represents the index for the pB tables."
::= { pBRowStatusEntry 10 }

pBAdminControlTable OBJECT-TYPE
   SYNTAX     SEQUENCE OF PBAdminControlEntry
   ACCESS     not-accessible
   STATUS     mandatory
   DESCRIPTION
     "This group includes the Administrative Control attribute. This attribute 
      defines the current administrative state of this component."
::= { pB 10 }

pBAdminControlEntry OBJECT-TYPE
   SYNTAX     PBAdminControlEntry
   ACCESS     not-accessible
   STATUS     mandatory
   DESCRIPTION
     "An entry in the pBAdminControlTable."
   INDEX {
      pBIndex }
::= { pBAdminControlTable 1 }

PBAdminControlEntry ::= SEQUENCE {
   pBSnmpAdminStatus
      INTEGER }

pBSnmpAdminStatus OBJECT-TYPE
   SYNTAX     INTEGER  {
                 up(1),
                 down(2),
                 testing(3) }
   ACCESS     read-write
   STATUS     obsolete
   DESCRIPTION
     "The desired state of the interface. The up state indicates the interface is 
      operational and packet forwarding is allowed. The down state indicates 
      the interface is not operational and packet forwarding is unavailable. 
      The testing state indicates that no operational packets can be passed."
   DEFVAL     { up }
::= { pBAdminControlEntry 1 }

pBIfEntryTable OBJECT-TYPE
   SYNTAX     SEQUENCE OF PBIfEntryEntry
   ACCESS     not-accessible
   STATUS     mandatory
   DESCRIPTION
     "This group contains the provisionable attributes for the ifEntry."
::= { pB 11 }

pBIfEntryEntry OBJECT-TYPE
   SYNTAX     PBIfEntryEntry
   ACCESS     not-accessible
   STATUS     mandatory
   DESCRIPTION
     "An entry in the pBIfEntryTable."
   INDEX {
      pBIndex }
::= { pBIfEntryTable 1 }

PBIfEntryEntry ::= SEQUENCE {
   pBIfAdminStatus
      INTEGER,
   pBIfIndex
      InterfaceIndex }

pBIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { pBIfEntryEntry 1 }

pBIfIndex OBJECT-TYPE
   SYNTAX     InterfaceIndex (1..65535)
   ACCESS     read-only
   STATUS     mandatory
   DESCRIPTION
     "This is the index for the IfEntry. Its value is automatically initialized 
      during the provisioning process."
::= { pBIfEntryEntry 2 }

pBMpTable OBJECT-TYPE
   SYNTAX     SEQUENCE OF PBMpEntry
   ACCESS     not-accessible
   STATUS     mandatory
   DESCRIPTION
     "This group contains the base provisioning data for the media base 
      component."
::= { pB 12 }

pBMpEntry OBJECT-TYPE
   SYNTAX     PBMpEntry
   ACCESS     not-accessible
   STATUS     mandatory
   DESCRIPTION
     "An entry in the pBMpTable."
   INDEX {
      pBIndex }
::= { pBMpTable 1 }

PBMpEntry ::= SEQUENCE {
   pBLinkToProtocolPort
      Link }

pBLinkToProtocolPort OBJECT-TYPE
   SYNTAX     Link 
   ACCESS     read-write
   STATUS     mandatory
   DESCRIPTION
     "This attribute specifies the ProtocolPort to which this interface is 
      linked to. The protocol port is the logical interface to the network. 
      The protocol port component describes the logical characteristics of 
      this interface."
::= { pBMpEntry 1 }

pBOperTable OBJECT-TYPE
   SYNTAX     SEQUENCE OF PBOperEntry
   ACCESS     not-accessible
   STATUS     mandatory
   DESCRIPTION
     "This group includes the operational attibutes 
      which are specific to the PseudoBridge 
      component."
::= { pB 13 }

pBOperEntry OBJECT-TYPE
   SYNTAX     PBOperEntry
   ACCESS     not-accessible
   STATUS     mandatory
   DESCRIPTION
     "An entry in the pBOperTable."
   INDEX {
      pBIndex }
::= { pBOperTable 1 }

PBOperEntry ::= SEQUENCE {
   pBMacAddress
      HexString }

pBMacAddress OBJECT-TYPE
   SYNTAX     HexString (SIZE (6))
   ACCESS     read-only
   STATUS     mandatory
   DESCRIPTION
     "The medium access controller (MAC) address is an address that is 
      only recognized by one station on the attached 
      bus. This address is automatically assigned by the 
      system."
::= { pBOperEntry 1 }

pBStateTable OBJECT-TYPE
   SYNTAX     SEQUENCE OF PBStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { pB 14 }

pBStateEntry OBJECT-TYPE
   SYNTAX     PBStateEntry
   ACCESS     not-accessible
   STATUS     mandatory
   DESCRIPTION
     "An entry in the pBStateTable."
   INDEX {
      pBIndex }
::= { pBStateTable 1 }

PBStateEntry ::= SEQUENCE {
   pBAdminState
      INTEGER,
   pBOperationalState
      INTEGER,
   pBUsageState
      INTEGER }

pBAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { pBStateEntry 1 }

pBOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { pBStateEntry 2 }

pBUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { pBStateEntry 3 }

pBOperStatusTable OBJECT-TYPE
   SYNTAX     SEQUENCE OF PBOperStatusEntry
   ACCESS     not-accessible
   STATUS     mandatory
   DESCRIPTION
     "This group includes the Operational Status attribute. This attribute 
      defines the current operational state of this component."
::= { pB 15 }

pBOperStatusEntry OBJECT-TYPE
   SYNTAX     PBOperStatusEntry
   ACCESS     not-accessible
   STATUS     mandatory
   DESCRIPTION
     "An entry in the pBOperStatusTable."
   INDEX {
      pBIndex }
::= { pBOperStatusTable 1 }

PBOperStatusEntry ::= SEQUENCE {
   pBSnmpOperStatus
      INTEGER }

pBSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { pBOperStatusEntry 1 }




-- 
-- Version and Compliance statements
-- 



-- Object-Group Statement:
-- A list of all current accessible leaf objects.

-- OBJECTS { vrPpTbseStpTypeOper,
--           vrBrTbStpFwdDelay,
--           vrPpSrtBpRowStatus,
--           vrPpSrseDesignatedBridge,
--           vrPpSrseHopCountExceededDiscards,
--           vrPpFddiETBPreserveDomain,
--           vrPpSrtBpHopCount,
--           vrPpTbclNsIncomingFilter,
--           vrPpSrsgBridgePortConfig,
--           vrPpTbclDesignatedBridge,
--           vrBrNsLastFilter,
--           vrPpTbpSnmpOperStatus,
--           vrPpTbsgDelayExceededDiscards,
--           vrPpSrtBpLargestFrame,
--           vrPpTbpIfIndex,
--           vrPpFddiETBConvertArpMacAddress,
--           vrPpSrseMtuExceededDiscards,
--           vrBrTbStpStorageType,
--           vrPpTbpStpTypeProv,
--           vrPpSrtBpTinygramFramesIn,
--           vrPpSrBpBridgePortConfig,
--           vrPpSrclNsComponentName,
--           vrPpTbpDomainNum,
--           vrPpSrsgBridgePortType,
--           vrPpTbseDesignatedBridge,
--           vrBrTbFteComponentName,
--           vrPpSrseDomainNum,
--           vrPpSrBpTranslateIpx,
--           vrPpSrclUpTime,
--           vrPpTbsgBridgingMode,
--           vrPpSrBpDupSegmentDiscards,
--           pBIfAdminStatus,
--           vrPpFddiETBSnmpOperStatus,
--           cBMacAddress,
--           vrPpFddiETBIfIndex,
--           vrPpTbclUnicastNoMatches,
--           vrPpSrtBpDesignatedPort,
--           vrPpFddiETBStpTypeProv,
--           vrPpSrsgInternalLanId,
--           vrPpSrsgUsageState,
--           vrPpTbseDelayExceededDiscards,
--           vrPpSrsgPortPriority,
--           vrPpTbsgSecureOption,
--           vrBrPtePortPointsTo,
--           vrPpFddiETBDomainNum,
--           vrPpSrBpPortNum,
--           vrPpSrseAreRdLimit,
--           vrPpSrclPortPriority,
--           vrPpSrtBpDynamicDiscards,
--           vrPpTbpRowStatus,
--           vrPpSrtBpDesignatedRoot,
--           vrPpTbclDownTime,
--           vrPpSrseBridgePortType,
--           vrPpSrsgDupLanIdOrTreeErrors,
--           vrPpSrclComponentName,
--           vrPpTbsgTranslateIpx,
--           vrPpTbseBridgingMode,
--           vrPpTbpNsRowStatus,
--           vrPpSrseOutFilterDiscards,
--           vrPpSrBpUsageState,
--           vrPpSrclDesignatedRoot,
--           vrPpTbsgForwardTransitions,
--           vrBrTbStpComponentName,
--           vrPpTbpTinygramFramesIn,
--           vrPpTbclPortName,
--           vrBrPteStpState,
--           vrBrTbAgingTime,
--           vrPpSrsePortPriority,
--           vrBrSrbStpBridgeId,
--           vrPpFddiETBRowStatus,
--           vrPpSrclLanId,
--           vrPpSrclDupSegmentDiscards,
--           vrPpSrBpApeInFrames,
--           vrPpSrsgFragmentIp,
--           vrPpTbclMtuExceededDiscards,
--           vrPpSrtBpBadAbstractDiscards,
--           vrBrPteStorageType,
--           vrPpSrtBpPortNum,
--           vrPpTbpOperationalState,
--           vrPpSrtBpDupLanIdOrTreeErrors,
--           vrPpFddiETBNsRowStatus,
--           vrBrSrbLteStorageType,
--           pBComponentName,
--           vrPpTbpDesignatedPort,
--           vrPpTbsgDesignatedPort,
--           vrPpTbseTranslateIpx,
--           vrPpFddiETBTinygramFramesIn,
--           vrPpTbclBridgePortConfig,
--           vrPpFddiETBStpTypeOper,
--           vrPpTbseSecureOption,
--           vrPpTbclTinygramFramesOut,
--           vrPpSrBpHopCountExceededDiscards,
--           vrPpSrtBpDesignatedBridge,
--           vrPpSrsgSegmentMismatchDiscards,
--           vrPpTbsgInFilterDiscards,
--           vrPpSrclNsRowStatus,
--           vrPpSrclSteOutFrames,
--           vrPpTbclServiceClass,
--           vrPpSrseInternalLanId,
--           vrPpSrtBpSteInFrames,
--           vrPpFddiETBOperationalState,
--           vrPpSrsgStorageType,
--           cBSnmpOperStatus,
--           vrBrPteLanId,
--           vrPpSrseFragmentIp,
--           vrPpFddiETBDesignatedPort,
--           vrPpSrclUsageState,
--           vrPpTbsgInDiscards,
--           vrPpSrsgStpPortState,
--           vrBrSrbLtePortName,
--           vrBrSrbStpTopologyChangeDetect,
--           vrPpSrsgApeOutFrames,
--           vrPpSrseForwardTransitions,
--           vrPpSrtBpDomainNum,
--           vrPpSrseStpTypeProv,
--           vrPpSrtBpUnicastNoMatches,
--           vrPpSrsgAdminState,
--           vrPpTbclBadVerifyDiscards,
--           vrPpSrseSegmentMismatchDiscards,
--           vrPpTbseInFilterDiscards,
--           cBIfAdminStatus,
--           vrPpTbsgPreserveDomain,
--           vrPpSrBpStaticDiscards,
--           vrPpSrtBpSpecOutFrames,
--           vrPpTbclDesignatedCost,
--           vrPpSrsePortStateStpControl,
--           pBStorageType,
--           vrPpTbsePathCostOper,
--           vrPpTbsePreserveDomain,
--           vrPpTbclStpTypeOper,
--           vrBrPteRowStatus,
--           vrPpSrclSteRdLimit,
--           vrPpSrtBpBridgeNum,
--           vrPpSrtBpDownTime,
--           vrBrTbNumFtEntriesDenied,
--           vrPpSrsgOutboundFrameMediaType,
--           vrPpTbpNsIncomingFilter,
--           vrPpTbclBadAbstractDiscards,
--           vrPpTbpDesignatedBridge,
--           vrPpSrsgSpecInFrames,
--           vrPpSrsgConvertArpMacAddress,
--           vrPpSrclTranslateIpx,
--           vrPpSrseApeOutFrames,
--           vrPpSrclMtuExceededDiscards,
--           vrPpSrclStpTypeProv,
--           vrPpTbsgBridgePortConfig,
--           vrPpSrBpOutFilterDiscards,
--           vrPpFddiETBPortNum,
--           vrPpSrsgDelayExceededDiscards,
--           vrPpSrtBpPortName,
--           vrPpTbseBridgePortConfig,
--           vrBrTbStpBridgeId,
--           vrPpSrtBpStaticDiscards,
--           vrPpTbsgInFrames,
--           vrBrAdminStatus,
--           pBOperationalState,
--           vrPpTbsgOutFilterDiscards,
--           vrPpSrBpPortPriority,
--           vrPpSrclBridgingMode,
--           vrBrTbComponentName,
--           vrPpFddiETBNsIncomingFilter,
--           vrPpSrsgRowStatus,
--           vrPpFddiETBDesignatedBridge,
--           vrPpSrtBpStpTypeOper,
--           pBSnmpOperStatus,
--           vrPpTbsgUsageState,
--           vrPpSrsgBlockingDiscards,
--           vrPpSrseOutboundFrameMediaType,
--           vrPpTbpUnicastNoMatches,
--           vrPpSrsgSteSpanMode,
--           vrPpSrseConvertArpMacAddress,
--           vrPpTbpOutboundFrameMediaType,
--           vrBrSrbStpHoldTime,
--           vrPpSrclPathCostMethod,
--           vrPpSrtBpTinygramFramesOut,
--           vrPpSrclSteInFrames,
--           vrPpTbsgOutboundFrameMediaType,
--           vrPpSrsgStaticDiscards,
--           vrPpSrBpNsOutgoingFilter,
--           vrBrTbStpBridgeForwardDelay,
--           vrPpFddiETBStpPortState,
--           vrPpSrclExploreFrameTreatment,
--           vrPpTbseDynamicEntryDiscards,
--           vrPpTbseInFrames,
--           vrPpSrclBridgePortType,
--           vrPpTbpDownTime,
--           vrBrSrbStpBridgeMaxAge,
--           vrPpSrBpInternalLanId,
--           vrBrSrbStpTimeSinceTopologyChange,
--           vrPpSrsgServiceClass,
--           vrPpFddiETBUnicastNoMatches,
--           vrPpTbclBridgingMode,
--           vrBrTbFteStorageType,
--           vrPpSrclOutFilterDiscards,
--           vrPpSrBpAreRdLimit,
--           vrPpSrsgTinygramFramesIn,
--           vrPpSrseBlockingDiscards,
--           vrBrTbStpDesignatedRoot,
--           vrPpTbpPathCost,
--           vrBrPteStpType,
--           vrPpTbclDelayExceededDiscards,
--           vrPpTbclSecureOption,
--           vrPpSrBpForwardTransitions,
--           vrPpSrtBpBadVerifyDiscards,
--           vrPpFddiETBDownTime,
--           vrPpSrBpLanId,
--           vrBrTbSteAtgtValue,
--           vrPpSrclAdminStatus,
--           vrPpSrBpSegmentMismatchDiscards,
--           vrPpSrclHopCount,
--           vrPpSrtBpDesignatedCost,
--           vrPpSrsgPathCostMethod,
--           vrPpSrclDynamicDiscards,
--           vrPpSrBpPortStateStpControl,
--           vrPpSrseStpPortState,
--           vrPpSrseServiceClass,
--           vrPpSrBpStorageType,
--           vrPpFddiETBPathCost,
--           vrBrSrbStpFwdDelay,
--           vrPpTbpTinygramFramesOut,
--           vrPpSrsgDesignatedRoot,
--           vrBrTbStpBridgeHelloTime,
--           pBRowStatus,
--           vrPpSrclInternalLanId,
--           vrPpSrBpNsStorageType,
--           vrPpTbsgDynamicEntryDiscards,
--           vrPpTbclComponentName,
--           vrBrAdminState,
--           vrPpSrBpApeOutFrames,
--           vrPpTbseMtuExceededDiscards,
--           vrPpSrBpAdminState,
--           vrBrSrbStpBridgeForwardDelay,
--           vrPpTbclNsComponentName,
--           vrPpFddiETBPortName,
--           vrPpTbclPreserveDomain,
--           vrBrSrbTotalLanIdTableEntries,
--           vrPpFddiETBTinygramFramesOut,
--           vrPpSrclStpTypeOper,
--           vrPpSrsgBadAbstractDiscards,
--           vrPpSrtBpSteRdLimit,
--           vrPpSrsgTranslateIpx,
--           vrPpSrsePathCost,
--           vrPpSrseStorageType,
--           vrBrPteBridgeNum,
--           vrPpSrclSegmentMismatchDiscards,
--           vrPpTbclInFilterDiscards,
--           vrPpSrBpOutboundFrameMediaType,
--           vrPpFddiETBOutFrames,
--           vrPpSrtBpDelayExceededDiscards,
--           vrPpSrsgPreserveDomain,
--           vrBrTbFteStatus,
--           vrPpSrtBpSteOutFrames,
--           vrPpSrBpConvertArpMacAddress,
--           vrPpTbpDesignatedCost,
--           vrPpTbclPathCostOper,
--           vrPpSrsgForwardTransitions,
--           vrPpTbpStpTypeOper,
--           vrPpTbclNsRowStatus,
--           vrPpSrclSpecInFrames,
--           vrPpSrclBadAbstractDiscards,
--           vrPpTbclUsageState,
--           vrPpSrsgExploreFrameTreatment,
--           vrPpTbseBridgePortType,
--           vrPpSrclHopCountExceededDiscards,
--           vrPpSrseUpTime,
--           vrPpSrtBpBridgingMode,
--           vrPpFddiETBBadVerifyDiscards,
--           vrPpSrclApeOutFrames,
--           vrPpSrseLanId,
--           vrPpSrseAdminStatus,
--           vrBrNumPorts,
--           vrBrSrbStpPriority,
--           vrPpTbseOutFilterDiscards,
--           vrPpSrclAdminState,
--           vrPpSrBpDesignatedCost,
--           vrPpSrBpBlockingDiscards,
--           vrBrTbNumFtEntriesFree,
--           vrPpSrsgSnmpOperStatus,
--           vrPpSrsePreserveDomain,
--           vrPpSrsgIfIndex,
--           vrPpSrtBpSecureOption,
--           vrPpSrseTinygramFramesOut,
--           vrPpTbsePortPriority,
--           cBLinkToProtocolPort,
--           vrPpSrsgStpTypeProv,
--           vrBrPteComponentName,
--           vrBrTbStpAgingTimeOper,
--           vrPpTbsgFragmentIp,
--           vrBrNsAteSecondMacAddress,
--           vrPpSrsgDomainNum,
--           vrPpSrclOutboundFrameMediaType,
--           vrPpSrclDomainNum,
--           vrPpSrseExploreFrameTreatment,
--           vrBrSrbStpAgingTimeOper,
--           vrPpSrBpMtuExceededDiscards,
--           vrPpSrclConvertArpMacAddress,
--           vrPpSrBpStpPortState,
--           vrPpTbpDelayExceededDiscards,
--           vrPpSrBpServiceClass,
--           vrPpSrsgStpTypeOper,
--           vrPpTbsgPortPriority,
--           vrPpSrtBpInDiscards,
--           vrPpSrtBpSpecInFrames,
--           vrPpTbseLearningDiscards,
--           vrPpSrseSnmpOperStatus,
--           vrPpTbclInFrames,
--           vrPpSrtBpComponentName,
--           vrPpSrseIfIndex,
--           vrBrSrbAgingTime,
--           vrPpTbsgPortStateStpControl,
--           vrPpTbsgPortNum,
--           vrPpSrseSpecInFrames,
--           vrPpTbsgStorageType,
--           vrBrNsAteFirstMacAddress,
--           vrPpTbpBridgingMode,
--           vrPpSrBpPreserveDomain,
--           vrPpTbseFragmentIp,
--           vrPpSrtBpNsComponentName,
--           vrPpFddiETBDelayExceededDiscards,
--           vrPpSrclBlockingDiscards,
--           vrPpSrsgHopCount,
--           vrBrSrbLteComponentName,
--           vrPpSrsgTinygramFramesOut,
--           vrPpSrBpPathCostMethod,
--           vrBrPteFilterPoints,
--           vrPpSrtBpNsStorageType,
--           vrPpTbsgStaticEntryDiscards,
--           vrPpSrsgLargestFrame,
--           vrPpTbseForwardTransitions,
--           vrPpTbpSecureOption,
--           vrPpTbpComponentName,
--           vrBrSrbRowStatus,
--           vrPpSrtBpInFilterDiscards,
--           vrPpTbsgAdminState,
--           vrPpSrtBpSteSpanMode,
--           vrPpTbseOutFrames,
--           vrBrSrbStpRowStatus,
--           vrPpSrtBpPathCost,
--           vrPpSrseLanIdMismatches,
--           vrPpFddiETBBridgingMode,
--           vrPpTbsgMaxInfo,
--           vrPpSrtBpPathCostOper,
--           vrPpTbsePortStateStpControl,
--           vrPpSrclStpPortState,
--           vrPpTbseUnicastNoMatches,
--           vrPpSrclServiceClass,
--           vrBrSrbLanIdTableNumEntries,
--           vrPpTbseStorageType,
--           vrBrSrbStpRootCost,
--           pBLinkToProtocolPort,
--           vrPpSrseRowStatus,
--           vrPpSrsgOperationalState,
--           vrBrNsFirstFilter,
--           vrPpSrseHopCount,
--           vrPpFddiETBSecureOption,
--           vrPpSrtBpOperationalState,
--           vrPpSrsgDesignatedPort,
--           vrPpSrclPortStateStpControl,
--           vrPpSrBpUpTime,
--           vrBrNsComponentName,
--           vrPpTbseStaticEntryDiscards,
--           vrPpSrseLargestFrame,
--           vrPpSrBpBadAbstractDiscards,
--           vrPpSrBpAdminStatus,
--           vrBrSrbStpProtocolSpec,
--           vrPpSrtBpBridgePortConfig,
--           vrPpTbseAdminState,
--           vrPpSrseTinygramFramesIn,
--           vrPpSrtBpSegmentMismatchDiscards,
--           vrBrTbFtePeerAddressInfo,
--           vrPpFddiETBTranslateIpx,
--           vrPpTbclStpTypeProv,
--           vrPpTbpNsComponentName,
--           vrPpTbseMaxInfo,
--           vrBrComponentName,
--           pBMacAddress,
--           vrPpSrtBpDupSegmentDiscards,
--           vrPpSrsgBridgeNum,
--           vrBrTbSteStorageType,
--           vrPpSrBpPortName,
--           vrPpSrsgSteOutFrames,
--           vrBrPteInternalLanId,
--           vrPpSrseOperationalState,
--           vrBrTbStorageType,
--           vrPpFddiETBComponentName,
--           vrPpTbseOutboundFrameMediaType,
--           vrPpTbpInFilterDiscards,
--           vrPpSrBpExploreFrameTreatment,
--           vrPpSrseDesignatedPort,
--           vrBrTbNcFtePort,
--           vrPpSrclIfIndex,
--           vrPpTbseConvertArpMacAddress,
--           vrBrTbNcFteAgeOfEntry,
--           vrPpSrsgDupSegmentDiscards,
--           vrPpFddiETBDesignatedRoot,
--           vrPpTbpPathCostOper,
--           vrPpFddiETBNsComponentName,
--           vrPpSrclAreRdLimit,
--           vrBrTbStpProtocolSpec,
--           vrPpSrtBpInFrames,
--           vrBrTbFtePort,
--           vrPpSrBpSnmpOperStatus,
--           vrPpTbclBridgePortType,
--           vrPpSrseDesignatedRoot,
--           vrPpSrBpIfIndex,
--           vrPpTbpAdminStatus,
--           vrPpTbsgStpPortState,
--           vrPpSrBpStpTypeProv,
--           vrPpFddiETBInFilterDiscards,
--           vrPpSrtBpUsageState,
--           vrBrSrbStpDesignatedRoot,
--           vrBrNsAteRowStatus,
--           vrPpTbclOutFilterDiscards,
--           vrPpTbclDynamicEntryDiscards,
--           vrPpSrsgLanIdMismatches,
--           vrPpSrBpDomainNum,
--           vrPpTbseBlockingDiscards,
--           vrBrUsageState,
--           vrPpFddiETBPathCostOper,
--           vrPpSrclPreserveDomain,
--           vrPpTbsgPathCostOper,
--           vrPpTbclPortPriority,
--           vrPpSrtBpApeInFrames,
--           vrBrNsAteDirection,
--           vrPpSrseSteSpanMode,
--           cBIfIndex,
--           vrBrTbLearnedEntryDiscards,
--           vrPpSrseBridgePortConfig,
--           vrPpSrtBpNsRowStatus,
--           vrPpTbseUsageState,
--           vrBrSrbLtePeerMACAddress,
--           vrPpSrBpLanIdMismatches,
--           vrPpSrsePortNum,
--           vrPpTbsgPathCostMethod,
--           vrPpSrseDupLanIdOrTreeErrors,
--           vrPpTbseStpPortState,
--           vrBrRowStatus,
--           vrPpTbseServiceClass,
--           vrPpFddiETBBridgePortConfig,
--           vrPpSrtBpHopCountExceededDiscards,
--           vrPpTbseComponentName,
--           vrPpSrBpRowStatus,
--           vrPpTbclNsOutgoingFilter,
--           vrPpTbclLearningDiscards,
--           vrPpSrBpHopCount,
--           vrPpSrclSnmpOperStatus,
--           vrBrNsRowStatus,
--           vrPpSrsgHopCountExceededDiscards,
--           vrPpTbpInFrames,
--           vrPpSrsgSpecOutFrames,
--           vrPpSrtBpMtuExceededDiscards,
--           vrBrTbStpMaxAge,
--           vrPpSrBpLargestFrame,
--           vrPpTbsgMtuExceededDiscards,
--           vrPpSrseSteInFrames,
--           vrPpSrBpSpecInFrames,
--           vrPpSrclInFilterDiscards,
--           vrPpTbclFragmentIp,
--           vrPpSrBpTinygramFramesIn,
--           vrPpTbpUsageState,
--           vrPpTbsgStpTypeOper,
--           vrPpSrsgDownTime,
--           vrBrNsAteFilterName,
--           vrPpSrseSteOutFrames,
--           vrPpTbsePathCostMethod,
--           cBComponentName,
--           vrPpTbsgUpTime,
--           pBAdminState,
--           vrBrOperationalState,
--           vrPpTbclForwardTransitions,
--           vrPpTbsgAdminStatus,
--           vrPpFddiETBInFrames,
--           vrBrTbSteComponentName,
--           vrBrNsAteDomainNum,
--           vrPpSrBpOperationalState,
--           vrPpTbclOutFrames,
--           vrBrType,
--           vrPpSrsgPathCost,
--           vrPpSrclLanIdMismatches,
--           vrPpSrtBpDynamicEntryDiscards,
--           vrPpSrBpDesignatedPort,
--           vrPpSrclPortName,
--           vrPpSrseSpecOutFrames,
--           vrPpTbclPortStateStpControl,
--           vrPpFddiETBUsageState,
--           vrPpSrclPathCostOper,
--           vrBrSrbStpTopologyChanges,
--           vrPpTbclStorageType,
--           vrPpSrBpBridgePortType,
--           vrPpSrBpPathCost,
--           vrPpSrseBridgeNum,
--           vrPpSrtBpBridgePortType,
--           vrPpSrseDownTime,
--           vrPpSrBpDynamicDiscards,
--           vrPpSrBpDesignatedRoot,
--           vrPpTbclNsStorageType,
--           vrPpTbseUpTime,
--           vrPpTbpAdminState,
--           vrPpTbclStaticEntryDiscards,
--           vrPpTbsgBadAbstractDiscards,
--           vrPpSrtBpOutFilterDiscards,
--           vrPpTbseAdminStatus,
--           vrPpTbpMtuExceededDiscards,
--           vrBrTbStpTimeSinceTopologyChange,
--           vrPpTbclAdminState,
--           vrPpTbpBadVerifyDiscards,
--           vrPpTbsgServiceClass,
--           vrPpTbclRowStatus,
--           vrPpSrsePortName,
--           vrPpTbsgSnmpOperStatus,
--           vrPpSrtBpPortPriority,
--           vrPpTbclMaxInfo,
--           vrPpSrsgSteInFrames,
--           vrPpSrclDownTime,
--           vrPpSrclPathCost,
--           vrBrSrbLteAgeOfEntry,
--           vrPpTbsgStpTypeProv,
--           vrPpTbpPortName,
--           vrPpSrBpSteSpanMode,
--           vrPpSrsgPortStateStpControl,
--           vrPpTbsePortName,
--           vrPpTbsgDomainNum,
--           vrPpTbclOutboundFrameMediaType,
--           vrPpSrsgPortNum,
--           vrPpFddiETBMtuExceededDiscards,
--           vrPpSrclDesignatedPort,
--           vrPpSrBpDupLanIdOrTreeErrors,
--           vrPpTbclConvertArpMacAddress,
--           vrPpSrsgUpTime,
--           vrPpTbpDynamicEntryDiscards,
--           vrBrSrbComponentName,
--           cBStorageType,
--           vrBrTbFteAgeOfEntry,
--           vrPpSrtBpNsOutgoingFilter,
--           vrPpSrtBpLearningDiscards,
--           vrBrBridgeAddress,
--           vrPpSrBpNsIncomingFilter,
--           vrBrTbStpHoldTime,
--           vrPpSrBpDesignatedBridge,
--           vrPpTbseSnmpOperStatus,
--           vrBrSrbStpComponentName,
--           vrPpSrtBpInternalLanId,
--           vrPpTbseIfIndex,
--           vrPpTbpBridgePortType,
--           vrBrNsStorageType,
--           vrPpTbseStpTypeProv,
--           vrPpTbpTranslateIpx,
--           vrPpSrBpSteInFrames,
--           cBAdminState,
--           vrPpTbsgRowStatus,
--           vrPpTbpOutFilterDiscards,
--           vrPpFddiETBDynamicEntryDiscards,
--           vrPpTbclBlockingDiscards,
--           vrPpTbsgIfIndex,
--           vrBrTbTotalForwardingTableEntries,
--           vrPpSrclPortNum,
--           vrBrStorageType,
--           vrPpSrtBpForwardTransitions,
--           vrPpTbsgComponentName,
--           vrPpTbpPortPriority,
--           vrPpSrtBpStpTypeProv,
--           vrPpTbsgDesignatedCost,
--           vrPpSrtBpOutFrames,
--           vrPpFddiETBBridgePortType,
--           vrPpTbsgTinygramFramesIn,
--           vrPpSrtBpNsIncomingFilter,
--           vrPpSrtBpFragmentIp,
--           vrPpSrclRowStatus,
--           vrPpSrtBpPortStateStpControl,
--           vrPpSrseDesignatedCost,
--           vrPpSrsgAdminStatus,
--           vrPpSrBpSpecOutFrames,
--           vrPpFddiETBOutFilterDiscards,
--           vrPpSrtBpStorageType,
--           vrPpSrseStpTypeOper,
--           vrBrSrbLteRowStatus,
--           vrPpSrsgDynamicDiscards,
--           vrPpSrsgSteRdLimit,
--           vrPpSrBpNsRowStatus,
--           vrPpTbseRowStatus,
--           vrPpTbseBadAbstractDiscards,
--           vrPpSrBpBridgeNum,
--           vrPpFddiETBPortPriority,
--           vrPpSrBpDownTime,
--           vrPpTbpLearningDiscards,
--           vrPpTbpNsOutgoingFilter,
--           vrPpFddiETBAdminState,
--           vrPpSrtBpStaticEntryDiscards,
--           vrPpSrtBpApeOutFrames,
--           vrPpSrclDesignatedBridge,
--           vrPpFddiETBDesignatedCost,
--           vrPpSrtBpAreRdLimit,
--           vrPpSrBpInFilterDiscards,
--           vrPpSrtBpAdminState,
--           vrBrSrbBridgeLfMode,
--           vrPpSrseAdminState,
--           vrPpTbclInDiscards,
--           vrPpTbseTinygramFramesIn,
--           vrPpTbpFragmentIp,
--           vrPpSrtBpMaxInfo,
--           vrBrTbSteAtgtRowStatus,
--           vrPpSrclNsStorageType,
--           vrPpTbclPathCostMethod,
--           vrBrTbNcFteComponentName,
--           vrPpFddiETBNsOutgoingFilter,
--           vrPpSrsgBridgingMode,
--           vrPpFddiETBLearningDiscards,
--           vrPpTbpForwardTransitions,
--           vrPpSrseSteRdLimit,
--           vrPpSrtBpOutboundFrameMediaType,
--           vrPpTbseOperationalState,
--           vrPpSrclStorageType,
--           vrBrSrbNumLanIdtEntriesDenied,
--           vrPpTbpOutFrames,
--           vrBrSrbStpRootPortName,
--           vrPpSrtBpConvertArpMacAddress,
--           vrPpTbseDesignatedPort,
--           vrPpSrseDelayExceededDiscards,
--           vrPpSrclSpecOutFrames,
--           vrBrNsAteFirstMacAddressMask,
--           vrPpFddiETBFragmentIp,
--           vrPpTbpPortStateStpControl,
--           vrPpTbseDomainNum,
--           vrPpSrBpTinygramFramesOut,
--           vrPpTbpStorageType,
--           vrBrSrbStpBridgeHelloTime,
--           vrPpSrclBridgeNum,
--           vrPpSrclFragmentIp,
--           vrPpFddiETBForwardTransitions,
--           vrPpTbseDesignatedRoot,
--           vrPpTbseInDiscards,
--           vrPpTbclUpTime,
--           vrPpTbpNsStorageType,
--           vrPpSrclTinygramFramesIn,
--           vrPpSrseBridgingMode,
--           vrPpTbpStaticEntryDiscards,
--           vrPpTbclAdminStatus,
--           vrPpSrsgDesignatedCost,
--           vrPpSrtBpBlockingDiscards,
--           vrBrTbStpRootPortName,
--           vrPpSrclBridgePortConfig,
--           vrPpFddiETBPortStateStpControl,
--           vrPpTbsgDesignatedBridge,
--           vrPpTbseDesignatedCost,
--           vrPpSrclStaticDiscards,
--           vrPpFddiETBStorageType,
--           vrBrNsAteSecondMacAddressMask,
--           vrPpSrsgComponentName,
--           vrPpTbpMaxInfo,
--           cBUsageState,
--           vrBrTbStpStpMode,
--           vrBrTbFwdTableNumEntries,
--           vrBrTbNcFtePeerAddressInfo,
--           pBIfIndex,
--           vrBrTbSteRowStatus,
--           vrPpSrclSteSpanMode,
--           vrPpFddiETBNsStorageType,
--           vrPpSrseDynamicDiscards,
--           vrPpFddiETBStaticEntryDiscards,
--           vrPpTbsePortNum,
--           vrPpSrtBpStpPortState,
--           vrPpSrtBpServiceClass,
--           vrBrNsAteStorageType,
--           vrPpSrseTranslateIpx,
--           vrPpTbpConvertArpMacAddress,
--           vrPpSrBpStpTypeOper,
--           vrPpSrsgPortName,
--           vrPpSrclTinygramFramesOut,
--           vrPpFddiETBMaxInfo,
--           vrPpSrsgInFilterDiscards,
--           vrPpSrsgDesignatedBridge,
--           vrPpTbpDesignatedRoot,
--           vrBrTbStpHelloTime,
--           vrPpTbclSnmpOperStatus,
--           vrPpSrclOperationalState,
--           vrPpTbsgUnicastNoMatches,
--           vrPpTbclIfIndex,
--           vrPpSrseComponentName,
--           vrPpSrclNsOutgoingFilter,
--           vrPpSrsgPathCostOper,
--           vrBrTbNcFteRowStatus,
--           vrPpSrtBpTranslateIpx,
--           vrPpFddiETBOutboundFrameMediaType,
--           vrBrTbStpPriority,
--           vrPpTbclDomainNum,
--           vrPpSrtBpPathCostMethod,
--           vrPpTbsgDownTime,
--           vrPpTbpBlockingDiscards,
--           vrPpTbsgLearningDiscards,
--           vrPpSrsgLanId,
--           vrPpTbclStpPortState,
--           vrPpTbsgBlockingDiscards,
--           vrPpTbpPortNum,
--           vrPpSrsgOutFilterDiscards,
--           vrPpTbpBridgePortConfig,
--           vrPpSrBpSteRdLimit,
--           vrPpSrclLargestFrame,
--           vrPpSrseInFilterDiscards,
--           vrBrSrbNumLanIdtEntriesFree,
--           vrPpTbsgPathCost,
--           vrPpSrBpSteOutFrames,
--           vrPpSrclForwardTransitions,
--           vrPpSrclDesignatedCost,
--           vrPpSrBpDelayExceededDiscards,
--           vrPpSrsePathCostOper,
--           vrPpTbpStpPortState,
--           vrPpFddiETBBlockingDiscards,
--           vrPpTbpServiceClass,
--           vrBrTbNcFteStatus,
--           vrBrSrbStpMaxAge,
--           vrPpSrBpFragmentIp,
--           vrPpSrsgAreRdLimit,
--           vrPpTbseDownTime,
--           vrBrSrbLteTypeOfEntry,
--           vrPpSrtBpUpTime,
--           vrBrSrbStpStorageType,
--           vrPpTbsgConvertArpMacAddress,
--           vrPpSrtBpLanId,
--           vrPpSrtBpAdminStatus,
--           vrPpSrBpBridgingMode,
--           vrBrTbNcFteStorageType,
--           vrPpTbsgTinygramFramesOut,
--           vrBrSnmpOperStatus,
--           vrPpSrclDupLanIdOrTreeErrors,
--           vrPpTbclTinygramFramesIn,
--           vrPpTbpInDiscards,
--           vrPpSrtBpPreserveDomain,
--           vrPpTbsePathCost,
--           vrPpFddiETBServiceClass,
--           vrBrNsAteComponentName,
--           vrBrSrbStpStpMode,
--           vrPpTbpPathCostMethod,
--           vrPpSrseDupSegmentDiscards,
--           vrBrTbStpRowStatus,
--           vrPpTbsgBridgePortType,
--           vrPpTbclTranslateIpx,
--           vrPpTbclOperationalState,
--           vrPpSrtBpExploreFrameTreatment,
--           cBRowStatus,
--           vrPpSrclNsIncomingFilter,
--           vrBrTbStpTopologyChangeDetect,
--           vrPpTbclDesignatedPort,
--           vrPpSrclDelayExceededDiscards,
--           vrBrTbRowStatus,
--           vrPpTbclPathCost,
--           vrPpFddiETBInDiscards,
--           vrBrSrbStpHelloTime,
--           vrPpSrsgApeInFrames,
--           vrPpTbseTinygramFramesOut,
--           vrPpSrseStaticDiscards,
--           vrPpFddiETBPathCostMethod,
--           vrBrTbStpRootCost,
--           vrPpSrtBpSnmpOperStatus,
--           vrPpTbsgBadVerifyDiscards,
--           vrBrTbSteStatus,
--           vrPpSrtBpIfIndex,
--           vrPpTbclDesignatedRoot,
--           vrPpSrclApeInFrames,
--           vrPpSrBpComponentName,
--           vrBrPteMacType,
--           vrPpTbpUpTime,
--           vrPpSrsePathCostMethod,
--           vrPpTbsgPortName,
--           vrPpTbpBadAbstractDiscards,
--           vrPpSrseUsageState,
--           vrPpTbsgDesignatedRoot,
--           vrPpFddiETBBadAbstractDiscards,
--           vrPpSrBpNsComponentName,
--           vrBrTbStpTopologyChanges,
--           vrBrTbFteRowStatus,
--           vrPpTbpPreserveDomain,
--           vrBrTbStpBridgeMaxAge,
--           vrPpSrsgMtuExceededDiscards,
--           vrPpSrseBadAbstractDiscards,
--           vrPpTbsgOutFrames,
--           vrPpSrseApeInFrames,
--           vrBrSrbStorageType,
--           vrPpTbseBadVerifyDiscards,
--           cBOperationalState,
--           vrPpSrtBpLanIdMismatches,
--           vrPpFddiETBUpTime,
--           vrPpTbsgOperationalState,
--           pBUsageState,
--           vrPpTbclPortNum,
--           vrPpFddiETBAdminStatus,
--           vrPpSrBpPathCostOper }
-- STATUS  mandatory
-- DESCRIPTION
--   "A list of all current accessible leaf objects."

bridgeGroup OBJECT IDENTIFIER ::= { bridgeMIB 1 }
bridgeGroupBE OBJECT IDENTIFIER ::= { bridgeGroup 5 }
bridgeGroupBE01 OBJECT IDENTIFIER ::= { bridgeGroupBE 2 }
bridgeGroupBE01A OBJECT IDENTIFIER ::= { bridgeGroupBE01 2 }



-- Agent-Capabilities Statement:

-- PRODUCT-RELEASE "Passport Release 7.0 Bridge."
-- STATUS          mandatory
-- DESCRIPTION     "Bridge MIB: MIB Version BE01A,
--                  Software Version BG00S4C."
-- SUPPORTS        Nortel-Magellan-Passport-BridgeMIB
--    INCLUDES     { bridgeGroupBE01A }
--    rfc1493 (Bridge)
-- 
-- SUPPORTS RFC1493-MIB
--    INCLUDES          { dot1dBase, dot1dStp, dot1dTp, dot1dStatic }
--       
--    variations for dot1dBase group
--     
--    VARIATION		dot1dBasePortCircuit
--       ACCESS		not-implemented
--       DESCRIPTION	"Inapplicable" 
--         
--    VARIATION		dot1dBasePortDelayExceededDiscards
--       ACCESS		not-implemented
--       DESCRIPTION	"Not supported"

bridgeCapabilities OBJECT IDENTIFIER ::= { bridgeMIB 3 }
bridgeCapabilitiesBE OBJECT IDENTIFIER ::= { bridgeCapabilities 5 }
bridgeCapabilitiesBE01 OBJECT IDENTIFIER ::= { bridgeCapabilitiesBE 2 }
bridgeCapabilitiesBE01A OBJECT IDENTIFIER ::= { bridgeCapabilitiesBE01 2 }





END
