BAS-IP-MIB DEFINITIONS ::= BEGIN

IMPORTS
	MODULE-IDENTITY, OBJECT-TYPE, 
	IpAddress						FROM SNMPv2-SMI
	RowStatus						FROM SNMPv2-TC
	IANAifType						FROM IANAifType-MIB
	basExtIp, BasChassisId,
	BasSlotId, BasInterfaceId,
        BasCardClass,	   
	BasLogicalPortId				FROM BAS-MIB;


basIpMib MODULE-IDENTITY
	LAST-UPDATED "9810071415Z"
	ORGANIZATION "Broadband Access Systems"
	CONTACT-INFO
		" Tech Support
		  Broadband Access Systems
		  201 Forest Street
		  Marlboro, MA  01752
		  U.S.A.
		  
		  508-485-8200
		  support@basystems.com"
	DESCRIPTION
		"This module defines extensions to the IP
		 MIB objects for Broadband Access Systems."
	::= { basExtIp 1 }


basIp			OBJECT IDENTIFIER ::= { basIpMib 1 }


-- the IP address table

basIpAddrTable OBJECT-TYPE
	SYNTAX		SEQUENCE OF BasIpAddrEntry
	MAX-ACCESS	not-accessible
	STATUS		current
	DESCRIPTION
		"The table of addressing information relevant to this
		 entity's IP addresses."
	::= { basIp 1 }

basIpAddrEntry OBJECT-TYPE
    SYNTAX		BasIpAddrEntry
    MAX-ACCESS	not-accessible
    STATUS		current
    DESCRIPTION
		"The addressing information for one of this entity's IP addresses."
    INDEX      { basIpAdEntChassis, basIpAdEntSlot, basIpAdEntIf,
				 basIpAdEntLPort, basIpAdEntAddr }
    ::= { basIpAddrTable 1 }

BasIpAddrEntry ::= SEQUENCE {
		basIpAdEntChassis					BasChassisId,
		basIpAdEntSlot						BasSlotId,
		basIpAdEntIf						BasInterfaceId,
		basIpAdEntLPort						BasLogicalPortId,
        basIpAdEntAddr							IpAddress,
        basIpAdEntIfIndex						INTEGER,
        basIpAdEntNetMask						IpAddress,
        basIpAdEntBcastAddr						INTEGER,
        basIpAdEntReasmMaxSize						INTEGER,
	basIpAdEntStatus						RowStatus,
	basIpAdEntCardType						BasCardClass,
        basIpAdEntPriority                                              INTEGER
    }


basIpAdEntChassis OBJECT-TYPE
	SYNTAX		BasChassisId
	MAX-ACCESS	not-accessible
	STATUS		current
	DESCRIPTION
		"The BAS Chassis ID of the Route Server."
	::= { basIpAddrEntry 1 }

basIpAdEntSlot OBJECT-TYPE
	SYNTAX		BasSlotId
	MAX-ACCESS	not-accessible
	STATUS		current
	DESCRIPTION
		"The BAS Slot ID of the Route Server."
	::= { basIpAddrEntry 2 }

basIpAdEntIf OBJECT-TYPE
	SYNTAX		BasInterfaceId
	MAX-ACCESS	not-accessible
	STATUS		current
	DESCRIPTION
		"The BAS interface ID of the Route Server."
	::= { basIpAddrEntry 3 }

basIpAdEntLPort OBJECT-TYPE
	SYNTAX		BasLogicalPortId
	MAX-ACCESS	not-accessible
	STATUS		current
	DESCRIPTION
		"The BAS logical port ID of the Route Server."
	::= { basIpAddrEntry 4 }

basIpAdEntAddr OBJECT-TYPE
    SYNTAX		IpAddress
    MAX-ACCESS	read-create
    STATUS		current
    DESCRIPTION
		"The IP address to which this entry's addressing information
		 pertains."
    ::= { basIpAddrEntry 5 }

basIpAdEntIfIndex OBJECT-TYPE
    SYNTAX		INTEGER (1..2147483647)
    MAX-ACCESS	read-create
    STATUS		current
    DESCRIPTION
		"The index value which uniquely identifies the interface to
		 which this entry is applicable.  The interface identified by
		 a particular value of this index is the same interface as
		 identified by the same value of RFC 1573's ifIndex."
    ::= { basIpAddrEntry 6 }

basIpAdEntNetMask OBJECT-TYPE
    SYNTAX		IpAddress
    MAX-ACCESS	read-create
    STATUS		current
    DESCRIPTION
		"The subnet mask associated with the IP address of this
		 entry.  The value of the mask is an IP address with all the
		 network bits set to 1 and all the hosts bits set to 0."
    ::= { basIpAddrEntry 7 }

basIpAdEntBcastAddr OBJECT-TYPE
    SYNTAX		INTEGER(0..1)
    MAX-ACCESS	read-create
    STATUS		current
    DESCRIPTION
		"The value of the least-significant bit in the IP broadcast
		 address used for sending datagrams on the (logical)
		 interface associated with the IP address of this entry.  For
		 example, when the Internet standard all-ones broadcast
		 address is used, the value will be 1.  This value applies to
		 both the subnet and network broadcasts addresses used by the
		 entity on this (logical) interface."
    ::= { basIpAddrEntry 8 }

basIpAdEntReasmMaxSize OBJECT-TYPE
    SYNTAX		INTEGER (0..65535)
    MAX-ACCESS	read-only
    STATUS		current
    DESCRIPTION
		"The size of the largest IP datagram which this entity can
		 re-assemble from incoming IP fragmented datagrams received
		 on this interface."
    ::= { basIpAddrEntry 9 }

basIpAdEntStatus OBJECT-TYPE
	SYNTAX		RowStatus
	MAX-ACCESS	read-create
	STATUS		current
	DESCRIPTION
		"The row status object used to create and delete a 
		 conceptual row according to RowStatus conventions."
	::= { basIpAddrEntry 10 }

basIpAdEntCardType OBJECT-TYPE
    SYNTAX		BasCardClass
    MAX-ACCESS		read-only
    STATUS		current
    DESCRIPTION
        "The card type inserted in a particular slot"
    ::= { basIpAddrEntry 11 }

basIpAdEntPriority OBJECT-TYPE
    SYNTAX		INTEGER (0..100)
    MAX-ACCESS		read-write
    STATUS		current
    DESCRIPTION
        "IP address priority, 1 = primary, 2 and above secondary.
        Cannot be set to 0."
    ::= { basIpAddrEntry 12 }


END
