--			Ascend mibloadselect MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBLOADSELECT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibloadSelectProfile  OBJECT IDENTIFIER ::= { configuration 92}

	-- The mibloadSelectProfile table
	--
	-- This table contains parameters for the mibloadSelectProfile profile
	--

    mibloadSelectProfileTable	OBJECT-TYPE
	SYNTAX		SEQUENCE OF MibloadSelectProfileEntry
	ACCESS		not-accessible
	STATUS		mandatory
	DESCRIPTION	"A list of mibloadSelectProfile profile entries."
	::= { mibloadSelectProfile 1 }

    mibloadSelectProfileEntry	OBJECT-TYPE
	SYNTAX		MibloadSelectProfileEntry
	ACCESS		not-accessible
	STATUS		mandatory
	DESCRIPTION	"A mibloadSelectProfile entry containing objects that
			 maps to the parameters of mibloadSelectProfile profile."
	INDEX		{ loadSelectProfile-Index-o }
	::= { mibloadSelectProfileTable 1 }

    MibloadSelectProfileEntry ::=
	SEQUENCE {
	    loadSelectProfile-Index-o
		INTEGER,
	    loadSelectProfile-UnknownCards
		INTEGER,
	    loadSelectProfile-Sr
		INTEGER,
	    loadSelectProfile-Sr2
		INTEGER,
	    loadSelectProfile-Apxsr
		INTEGER,
	    loadSelectProfile-o8t1
		INTEGER,
	    loadSelectProfile-o8e1
		INTEGER,
	    loadSelectProfile-T3
		INTEGER,
	    loadSelectProfile-Stm0
		INTEGER,
	    loadSelectProfile-Pctfit
		INTEGER,
	    loadSelectProfile-Pctfie
		INTEGER,
	    loadSelectProfile-Clpmt
		INTEGER,
	    loadSelectProfile-Clpme
		INTEGER,
	    loadSelectProfile-o24t1
		INTEGER,
	    loadSelectProfile-o24e1
		INTEGER,
	    loadSelectProfile-Cln
		INTEGER,
	    loadSelectProfile-Alpmt
		INTEGER,
	    loadSelectProfile-Alpme
		INTEGER,
	    loadSelectProfile-Ut1
		INTEGER,
	    loadSelectProfile-Ue1
		INTEGER,
	    loadSelectProfile-Uds3
		INTEGER,
	    loadSelectProfile-Ds3Atm
		INTEGER,
	    loadSelectProfile-AtmHse
		INTEGER,
	    loadSelectProfile-Enet2
		INTEGER,
	    loadSelectProfile-Enet3
		INTEGER,
	    loadSelectProfile-Enet3nd
		INTEGER,
	    loadSelectProfile-EtherDual
		INTEGER,
	    loadSelectProfile-SrsEther
		INTEGER,
	    loadSelectProfile-EnetHse
		INTEGER,
	    loadSelectProfile-Apxenet
		INTEGER,
	    loadSelectProfile-MdmV34
		INTEGER,
	    loadSelectProfile-Mdm56k
		INTEGER,
	    loadSelectProfile-Amdm
		INTEGER,
	    loadSelectProfile-Anmdm
		INTEGER,
	    loadSelectProfile-Csmx
		INTEGER,
	    loadSelectProfile-Madd
		INTEGER,
	    loadSelectProfile-Csm3v
		INTEGER,
	    loadSelectProfile-Madd3
		INTEGER,
	    loadSelectProfile-Hdlc2
		INTEGER,
	    loadSelectProfile-Hdlc2ec
		INTEGER,
	    loadSelectProfile-Swan
		INTEGER,
	    loadSelectProfile-Hssi
		INTEGER,
	    loadSelectProfile-Idsl
		INTEGER,
	    loadSelectProfile-Capadsl
		INTEGER,
	    loadSelectProfile-Dmtadsl
		INTEGER,
	    loadSelectProfile-Sdsl
		INTEGER,
	    loadSelectProfile-Sdsl70d
		INTEGER,
	    loadSelectProfile-Sdsl70v
		INTEGER,
	    loadSelectProfile-Oc3Atm
		INTEGER,
	    loadSelectProfile-SdslAtm
		INTEGER,
	    loadSelectProfile-AlDmtadslAtm
		INTEGER,
	    loadSelectProfile-SdslAtmV2
		INTEGER,
	    loadSelectProfile-DadslAtm24
		INTEGER,
	    loadSelectProfile-GliteAtm48
		INTEGER,
	    loadSelectProfile-Hdsl2
		INTEGER,
	    loadSelectProfile-AnnexbDmtadsl
		INTEGER,
	    loadSelectProfile-T1000
		INTEGER,
	    loadSelectProfile-Ima
		INTEGER,
	    loadSelectProfile-Stngr32Idsl
		INTEGER,
	    loadSelectProfile-o40DmtAdsl
		INTEGER,
	    loadSelectProfile-o48DmtAdsl
		INTEGER,
	    loadSelectProfile-o72Shdsl
		INTEGER,
	    loadSelectProfile-o72CtDmtAdsl
		INTEGER,
	    loadSelectProfile-o32DmtAslam
		INTEGER,
	    loadSelectProfile-Vdsl
		INTEGER,
	    loadSelectProfile-Ds3Atm2
		INTEGER,
	    loadSelectProfile-E3Atm
		INTEGER,
	    loadSelectProfile-Oc3Atm2
		INTEGER,
	    loadSelectProfile-Vpn
		INTEGER,
	    loadSelectProfile-Swan2
		INTEGER,
	    loadSelectProfile-Action-o
		INTEGER
	}

    loadSelectProfile-Index-o	OBJECT-TYPE
	SYNTAX	INTEGER
	ACCESS	read-only
	STATUS	mandatory
	DESCRIPTION	""
	::= { mibloadSelectProfileEntry 1 }

    loadSelectProfile-UnknownCards	OBJECT-TYPE
	SYNTAX	INTEGER {
		    auto (1),
		    load (2),
		    skip (3)
		}
	ACCESS	read-write
	STATUS	mandatory
	DESCRIPTION	"Controls whether code images for card models which the current software load doesn't know of should be stored in Flash"
	::= { mibloadSelectProfileEntry 2 }

    loadSelectProfile-Sr	OBJECT-TYPE
	SYNTAX	INTEGER {
		    auto (1),
		    load (2),
		    skip (3)
		}
	ACCESS	read-write
	STATUS	mandatory
	DESCRIPTION	"Controls whether code images for the SHELF-CONTROLER card should be stored in Flash"
	::= { mibloadSelectProfileEntry 3 }

    loadSelectProfile-Sr2	OBJECT-TYPE
	SYNTAX	INTEGER {
		    auto (1),
		    load (2),
		    skip (3)
		}
	ACCESS	read-write
	STATUS	mandatory
	DESCRIPTION	"Controls whether code images for the SHELF-CONTROLER-2 card should be stored in Flash"
	::= { mibloadSelectProfileEntry 4 }

    loadSelectProfile-Apxsr	OBJECT-TYPE
	SYNTAX	INTEGER {
		    auto (1),
		    load (2),
		    skip (3)
		}
	ACCESS	read-write
	STATUS	mandatory
	DESCRIPTION	"Controls whether code images for the APX-SHELF-CONTROLER card should be stored in Flash"
	::= { mibloadSelectProfileEntry 5 }

    loadSelectProfile-o8t1	OBJECT-TYPE
	SYNTAX	INTEGER {
		    auto (1),
		    load (2),
		    skip (3)
		}
	ACCESS	read-write
	STATUS	mandatory
	DESCRIPTION	"Controls whether code images for T1 cards should be stored in Flash"
	::= { mibloadSelectProfileEntry 6 }

    loadSelectProfile-o8e1	OBJECT-TYPE
	SYNTAX	INTEGER {
		    auto (1),
		    load (2),
		    skip (3)
		}
	ACCESS	read-write
	STATUS	mandatory
	DESCRIPTION	"Controls whether code images for E1 cards should be stored in Flash"
	::= { mibloadSelectProfileEntry 7 }

    loadSelectProfile-T3	OBJECT-TYPE
	SYNTAX	INTEGER {
		    auto (1),
		    load (2),
		    skip (3)
		}
	ACCESS	read-write
	STATUS	mandatory
	DESCRIPTION	"Controls whether code images for T3 cards should be stored in Flash"
	::= { mibloadSelectProfileEntry 8 }

    loadSelectProfile-Stm0	OBJECT-TYPE
	SYNTAX	INTEGER {
		    auto (1),
		    load (2),
		    skip (3)
		}
	ACCESS	read-write
	STATUS	mandatory
	DESCRIPTION	"Controls whether code images for STM-0 cards should be stored in Flash"
	::= { mibloadSelectProfileEntry 9 }

    loadSelectProfile-Pctfit	OBJECT-TYPE
	SYNTAX	INTEGER {
		    auto (1),
		    load (2),
		    skip (3)
		}
	ACCESS	read-write
	STATUS	mandatory
	DESCRIPTION	"Controls whether code images for PCTFI T1 cards should be stored in Flash"
	::= { mibloadSelectProfileEntry 10 }

    loadSelectProfile-Pctfie	OBJECT-TYPE
	SYNTAX	INTEGER {
		    auto (1),
		    load (2),
		    skip (3)
		}
	ACCESS	read-write
	STATUS	mandatory
	DESCRIPTION	"Controls whether code images for PCTFI E1 cards should be stored in Flash"
	::= { mibloadSelectProfileEntry 11 }

    loadSelectProfile-Clpmt	OBJECT-TYPE
	SYNTAX	INTEGER {
		    auto (1),
		    load (2),
		    skip (3)
		}
	ACCESS	read-write
	STATUS	mandatory
	DESCRIPTION	"Controls whether code images for APX CLPM for T1 should be stored in Flash"
	::= { mibloadSelectProfileEntry 12 }

    loadSelectProfile-Clpme	OBJECT-TYPE
	SYNTAX	INTEGER {
		    auto (1),
		    load (2),
		    skip (3)
		}
	ACCESS	read-write
	STATUS	mandatory
	DESCRIPTION	"Controls whether code images for the APX CLPM for E1 should be stored in Flash"
	::= { mibloadSelectProfileEntry 13 }

    loadSelectProfile-o24t1	OBJECT-TYPE
	SYNTAX	INTEGER {
		    auto (1),
		    load (2),
		    skip (3)
		}
	ACCESS	read-write
	STATUS	mandatory
	DESCRIPTION	"Controls whether code images for 24 port T1 cards should be stored in Flash"
	::= { mibloadSelectProfileEntry 64 }

    loadSelectProfile-o24e1	OBJECT-TYPE
	SYNTAX	INTEGER {
		    auto (1),
		    load (2),
		    skip (3)
		}
	ACCESS	read-write
	STATUS	mandatory
	DESCRIPTION	"Controls whether code images for 24 port E1 cards should be stored in Flash"
	::= { mibloadSelectProfileEntry 65 }

    loadSelectProfile-Cln	OBJECT-TYPE
	SYNTAX	INTEGER {
		    auto (1),
		    load (2),
		    skip (3)
		}
	ACCESS	read-write
	STATUS	mandatory
	DESCRIPTION	"Controls whether code images for APX 1K Channelized line type cards should be stored in Flash. cln include 2ds3 and 3ds3 cards."
	::= { mibloadSelectProfileEntry 72 }

    loadSelectProfile-Alpmt	OBJECT-TYPE
	SYNTAX	INTEGER {
		    auto (1),
		    load (2),
		    skip (3)
		}
	ACCESS	read-write
	STATUS	mandatory
	DESCRIPTION	"Controls whether code images for the APX ALPM for T1 should be stored in Flash"
	::= { mibloadSelectProfileEntry 75 }

    loadSelectProfile-Alpme	OBJECT-TYPE
	SYNTAX	INTEGER {
		    auto (1),
		    load (2),
		    skip (3)
		}
	ACCESS	read-write
	STATUS	mandatory
	DESCRIPTION	"Controls whether code images for the APX ALPM for E1 should be stored in Flash"
	::= { mibloadSelectProfileEntry 76 }

    loadSelectProfile-Ut1	OBJECT-TYPE
	SYNTAX	INTEGER {
		    auto (1),
		    load (2),
		    skip (3)
		}
	ACCESS	read-write
	STATUS	mandatory
	DESCRIPTION	"Controls whether code images for UT1 cards should be stored in Flash"
	::= { mibloadSelectProfileEntry 14 }

    loadSelectProfile-Ue1	OBJECT-TYPE
	SYNTAX	INTEGER {
		    auto (1),
		    load (2),
		    skip (3)
		}
	ACCESS	read-write
	STATUS	mandatory
	DESCRIPTION	"Controls whether code images for UE1 cards should be stored in Flash"
	::= { mibloadSelectProfileEntry 15 }

    loadSelectProfile-Uds3	OBJECT-TYPE
	SYNTAX	INTEGER {
		    auto (1),
		    load (2),
		    skip (3)
		}
	ACCESS	read-write
	STATUS	mandatory
	DESCRIPTION	"Controls whether code images for UDS3 cards should be stored in Flash"
	::= { mibloadSelectProfileEntry 16 }

    loadSelectProfile-Ds3Atm	OBJECT-TYPE
	SYNTAX	INTEGER {
		    auto (1),
		    load (2),
		    skip (3)
		}
	ACCESS	read-write
	STATUS	mandatory
	DESCRIPTION	"Controls whether code images for DS3-ATM cards should be stored in Flash"
	::= { mibloadSelectProfileEntry 17 }

    loadSelectProfile-AtmHse	OBJECT-TYPE
	SYNTAX	INTEGER {
		    auto (1),
		    load (2),
		    skip (3)
		}
	ACCESS	read-write
	STATUS	mandatory
	DESCRIPTION	"Controls whether code images for ATM HSE cards should be stored in Flash"
	::= { mibloadSelectProfileEntry 68 }

    loadSelectProfile-Enet2	OBJECT-TYPE
	SYNTAX	INTEGER {
		    auto (1),
		    load (2),
		    skip (3)
		}
	ACCESS	read-write
	STATUS	mandatory
	DESCRIPTION	"Controls whether code images for ETHERNET2 cards should be stored in Flash"
	::= { mibloadSelectProfileEntry 19 }

    loadSelectProfile-Enet3	OBJECT-TYPE
	SYNTAX	INTEGER {
		    auto (1),
		    load (2),
		    skip (3)
		}
	ACCESS	read-write
	STATUS	mandatory
	DESCRIPTION	"Controls whether code images for ETHERNET3 cards should be stored in Flash"
	::= { mibloadSelectProfileEntry 20 }

    loadSelectProfile-Enet3nd	OBJECT-TYPE
	SYNTAX	INTEGER {
		    auto (1),
		    load (2),
		    skip (3)
		}
	ACCESS	read-write
	STATUS	mandatory
	DESCRIPTION	"Controls whether code images for ETHERNET3ND cards should be stored in Flash"
	::= { mibloadSelectProfileEntry 21 }

    loadSelectProfile-EtherDual	OBJECT-TYPE
	SYNTAX	INTEGER {
		    auto (1),
		    load (2),
		    skip (3)
		}
	ACCESS	read-write
	STATUS	mandatory
	DESCRIPTION	"Controls whether code images for DUAL 10/100 ETHERNET cards should be stored in Flash"
	::= { mibloadSelectProfileEntry 22 }

    loadSelectProfile-SrsEther	OBJECT-TYPE
	SYNTAX	INTEGER {
		    auto (1),
		    load (2),
		    skip (3)
		}
	ACCESS	read-write
	STATUS	mandatory
	DESCRIPTION	"Controls whether code images for SRS ETHERNET cards should be stored in Flash"
	::= { mibloadSelectProfileEntry 23 }

    loadSelectProfile-EnetHse	OBJECT-TYPE
	SYNTAX	INTEGER {
		    auto (1),
		    load (2),
		    skip (3)
		}
	ACCESS	read-write
	STATUS	mandatory
	DESCRIPTION	"Controls whether code images for HS ETHERNET card should be stored in Flash"
	::= { mibloadSelectProfileEntry 69 }

    loadSelectProfile-Apxenet	OBJECT-TYPE
	SYNTAX	INTEGER {
		    auto (1),
		    load (2),
		    skip (3)
		}
	ACCESS	read-write
	STATUS	mandatory
	DESCRIPTION	"Controls whether code images for APXENET card should be stored in flash"
	::= { mibloadSelectProfileEntry 82 }

    loadSelectProfile-MdmV34	OBJECT-TYPE
	SYNTAX	INTEGER {
		    auto (1),
		    load (2),
		    skip (3)
		}
	ACCESS	read-write
	STATUS	mandatory
	DESCRIPTION	"Controls whether code images for MODEM cards should be stored in Flash"
	::= { mibloadSelectProfileEntry 24 }

    loadSelectProfile-Mdm56k	OBJECT-TYPE
	SYNTAX	INTEGER {
		    auto (1),
		    load (2),
		    skip (3)
		}
	ACCESS	read-write
	STATUS	mandatory
	DESCRIPTION	"Controls whether code images for OBSOLETE MODEM-56K cards should be stored in Flash"
	::= { mibloadSelectProfileEntry 25 }

    loadSelectProfile-Amdm	OBJECT-TYPE
	SYNTAX	INTEGER {
		    auto (1),
		    load (2),
		    skip (3)
		}
	ACCESS	read-write
	STATUS	mandatory
	DESCRIPTION	"Controls whether code images for OBSOLETE ANALOG MODEM cards should be stored in Flash"
	::= { mibloadSelectProfileEntry 26 }

    loadSelectProfile-Anmdm	OBJECT-TYPE
	SYNTAX	INTEGER {
		    auto (1),
		    load (2),
		    skip (3)
		}
	ACCESS	read-write
	STATUS	mandatory
	DESCRIPTION	"Controls whether code images for OBSOLETE analog modem cards should be stored in Flash. Replaced by amdm."
	::= { mibloadSelectProfileEntry 27 }

    loadSelectProfile-Csmx	OBJECT-TYPE
	SYNTAX	INTEGER {
		    auto (1),
		    load (2),
		    skip (3)
		}
	ACCESS	read-write
	STATUS	mandatory
	DESCRIPTION	"Controls whether code images for CSMX cards should be stored in Flash"
	::= { mibloadSelectProfileEntry 28 }

    loadSelectProfile-Madd	OBJECT-TYPE
	SYNTAX	INTEGER {
		    auto (1),
		    load (2),
		    skip (3)
		}
	ACCESS	read-write
	STATUS	mandatory
	DESCRIPTION	"Controls whether code images for MADD cards should be stored in Flash"
	::= { mibloadSelectProfileEntry 29 }

    loadSelectProfile-Csm3v	OBJECT-TYPE
	SYNTAX	INTEGER {
		    auto (1),
		    load (2),
		    skip (3)
		}
	ACCESS	read-write
	STATUS	mandatory
	DESCRIPTION	"Controls whether code images for CSM3V cards should be stored in Flash"
	::= { mibloadSelectProfileEntry 30 }

    loadSelectProfile-Madd3	OBJECT-TYPE
	SYNTAX	INTEGER {
		    auto (1),
		    load (2),
		    skip (3)
		}
	ACCESS	read-write
	STATUS	mandatory
	DESCRIPTION	"Controls whether code images for MADD3 cards should be stored in Flash"
	::= { mibloadSelectProfileEntry 31 }

    loadSelectProfile-Hdlc2	OBJECT-TYPE
	SYNTAX	INTEGER {
		    auto (1),
		    load (2),
		    skip (3)
		}
	ACCESS	read-write
	STATUS	mandatory
	DESCRIPTION	"Controls whether code images for HDLC2 cards should be stored in Flash"
	::= { mibloadSelectProfileEntry 33 }

    loadSelectProfile-Hdlc2ec	OBJECT-TYPE
	SYNTAX	INTEGER {
		    auto (1),
		    load (2),
		    skip (3)
		}
	ACCESS	read-write
	STATUS	mandatory
	DESCRIPTION	"Controls whether code images for HDLC2EC cards should be stored in Flash"
	::= { mibloadSelectProfileEntry 34 }

    loadSelectProfile-Swan	OBJECT-TYPE
	SYNTAX	INTEGER {
		    auto (1),
		    load (2),
		    skip (3)
		}
	ACCESS	read-write
	STATUS	mandatory
	DESCRIPTION	"Controls whether code images for SWAN cards should be stored in Flash"
	::= { mibloadSelectProfileEntry 35 }

    loadSelectProfile-Hssi	OBJECT-TYPE
	SYNTAX	INTEGER {
		    auto (1),
		    load (2),
		    skip (3)
		}
	ACCESS	read-write
	STATUS	mandatory
	DESCRIPTION	"Controls whether code images for HSSI cards should be stored in Flash"
	::= { mibloadSelectProfileEntry 36 }

    loadSelectProfile-Idsl	OBJECT-TYPE
	SYNTAX	INTEGER {
		    auto (1),
		    load (2),
		    skip (3)
		}
	ACCESS	read-write
	STATUS	mandatory
	DESCRIPTION	"Controls whether code images for IDSL cards should be stored in Flash"
	::= { mibloadSelectProfileEntry 37 }

    loadSelectProfile-Capadsl	OBJECT-TYPE
	SYNTAX	INTEGER {
		    auto (1),
		    load (2),
		    skip (3)
		}
	ACCESS	read-write
	STATUS	mandatory
	DESCRIPTION	"Controls whether code images for CAP-ADSL cards should be stored in Flash"
	::= { mibloadSelectProfileEntry 38 }

    loadSelectProfile-Dmtadsl	OBJECT-TYPE
	SYNTAX	INTEGER {
		    auto (1),
		    load (2),
		    skip (3)
		}
	ACCESS	read-write
	STATUS	mandatory
	DESCRIPTION	"Controls whether code images for DMT-ADSL cards should be stored in Flash"
	::= { mibloadSelectProfileEntry 39 }

    loadSelectProfile-Sdsl	OBJECT-TYPE
	SYNTAX	INTEGER {
		    auto (1),
		    load (2),
		    skip (3)
		}
	ACCESS	read-write
	STATUS	mandatory
	DESCRIPTION	"Controls whether code images for SDSL cards should be stored in Flash"
	::= { mibloadSelectProfileEntry 40 }

    loadSelectProfile-Sdsl70d	OBJECT-TYPE
	SYNTAX	INTEGER {
		    auto (1),
		    load (2),
		    skip (3)
		}
	ACCESS	read-write
	STATUS	mandatory
	DESCRIPTION	"Controls whether code images for SDSL70D cards should be stored in Flash"
	::= { mibloadSelectProfileEntry 41 }

    loadSelectProfile-Sdsl70v	OBJECT-TYPE
	SYNTAX	INTEGER {
		    auto (1),
		    load (2),
		    skip (3)
		}
	ACCESS	read-write
	STATUS	mandatory
	DESCRIPTION	"Controls whether code images for SDSL70V cards should be stored in Flash"
	::= { mibloadSelectProfileEntry 42 }

    loadSelectProfile-Oc3Atm	OBJECT-TYPE
	SYNTAX	INTEGER {
		    auto (1),
		    load (2),
		    skip (3)
		}
	ACCESS	read-write
	STATUS	mandatory
	DESCRIPTION	"Controls whether code images for OC3-ATM cards should be stored in Flash"
	::= { mibloadSelectProfileEntry 43 }

    loadSelectProfile-SdslAtm	OBJECT-TYPE
	SYNTAX	INTEGER {
		    auto (1),
		    load (2),
		    skip (3)
		}
	ACCESS	read-write
	STATUS	mandatory
	DESCRIPTION	"Controls whether code images for SDSL-ATM cards should be stored in Flash"
	::= { mibloadSelectProfileEntry 44 }

    loadSelectProfile-AlDmtadslAtm	OBJECT-TYPE
	SYNTAX	INTEGER {
		    auto (1),
		    load (2),
		    skip (3)
		}
	ACCESS	read-write
	STATUS	mandatory
	DESCRIPTION	"Controls whether code images for DMT-ADSL-ATM cards should be stored in Flash"
	::= { mibloadSelectProfileEntry 45 }

    loadSelectProfile-SdslAtmV2	OBJECT-TYPE
	SYNTAX	INTEGER {
		    auto (1),
		    load (2),
		    skip (3)
		}
	ACCESS	read-write
	STATUS	mandatory
	DESCRIPTION	"Controls whether code images for SDSL-ATM-V2 cards should be stored in Flash"
	::= { mibloadSelectProfileEntry 46 }

    loadSelectProfile-DadslAtm24	OBJECT-TYPE
	SYNTAX	INTEGER {
		    auto (1),
		    load (2),
		    skip (3)
		}
	ACCESS	read-write
	STATUS	mandatory
	DESCRIPTION	"Controls whether code images for 24 port DMT-ADSL-ATM cards should be stored in Flash"
	::= { mibloadSelectProfileEntry 47 }

    loadSelectProfile-GliteAtm48	OBJECT-TYPE
	SYNTAX	INTEGER {
		    auto (1),
		    load (2),
		    skip (3)
		}
	ACCESS	read-write
	STATUS	mandatory
	DESCRIPTION	"Controls whether code images for 48 port GLITE-DMT-ATM cards should be stored in Flash"
	::= { mibloadSelectProfileEntry 48 }

    loadSelectProfile-Hdsl2	OBJECT-TYPE
	SYNTAX	INTEGER {
		    auto (1),
		    load (2),
		    skip (3)
		}
	ACCESS	read-write
	STATUS	mandatory
	DESCRIPTION	"Controls whether code images for 32 port HDSL2 cards should be stored in Flash"
	::= { mibloadSelectProfileEntry 49 }

    loadSelectProfile-AnnexbDmtadsl	OBJECT-TYPE
	SYNTAX	INTEGER {
		    auto (1),
		    load (2),
		    skip (3)
		}
	ACCESS	read-write
	STATUS	mandatory
	DESCRIPTION	"Controls whether code images for 12 port ANNEX B DMT-ADSL-ATM cards should be stored in Flash"
	::= { mibloadSelectProfileEntry 50 }

    loadSelectProfile-T1000	OBJECT-TYPE
	SYNTAX	INTEGER {
		    auto (1),
		    load (2),
		    skip (3)
		}
	ACCESS	read-write
	STATUS	mandatory
	DESCRIPTION	"Controls whether code images for STNGR_T1000 cards should be stored in Flash"
	::= { mibloadSelectProfileEntry 51 }

    loadSelectProfile-Ima	OBJECT-TYPE
	SYNTAX	INTEGER {
		    auto (1),
		    load (2),
		    skip (3)
		}
	ACCESS	read-write
	STATUS	mandatory
	DESCRIPTION	"Controls whether code images for 24-port/8-port IMA_T1/IMA_E1 cards should be stored in Flash"
	::= { mibloadSelectProfileEntry 52 }

    loadSelectProfile-Stngr32Idsl	OBJECT-TYPE
	SYNTAX	INTEGER {
		    auto (1),
		    load (2),
		    skip (3)
		}
	ACCESS	read-write
	STATUS	mandatory
	DESCRIPTION	"Controls whether code images for STINGER 32 port IDSL cards should be stored in Flash"
	::= { mibloadSelectProfileEntry 53 }

    loadSelectProfile-o40DmtAdsl	OBJECT-TYPE
	SYNTAX	INTEGER {
		    auto (1),
		    load (2),
		    skip (3)
		}
	ACCESS	read-write
	STATUS	mandatory
	DESCRIPTION	"Controls whether code images for 40 port Annex A/C DMT-ATM cards should be stored in Flash"
	::= { mibloadSelectProfileEntry 54 }

    loadSelectProfile-o48DmtAdsl	OBJECT-TYPE
	SYNTAX	INTEGER {
		    auto (1),
		    load (2),
		    skip (3)
		}
	ACCESS	read-write
	STATUS	mandatory
	DESCRIPTION	"Controls whether code images for 48 port Annex A/B/C DMT-ATM cards should be stored in Flash"
	::= { mibloadSelectProfileEntry 55 }

    loadSelectProfile-o72Shdsl	OBJECT-TYPE
	SYNTAX	INTEGER {
		    auto (1),
		    load (2),
		    skip (3)
		}
	ACCESS	read-write
	STATUS	mandatory
	DESCRIPTION	"Controls whether code images for 72 port SHDSL cards should be stored in Flash"
	::= { mibloadSelectProfileEntry 62 }

    loadSelectProfile-o72CtDmtAdsl	OBJECT-TYPE
	SYNTAX	INTEGER {
		    auto (1),
		    load (2),
		    skip (3)
		}
	ACCESS	read-write
	STATUS	mandatory
	DESCRIPTION	"Controls whether code images for 72 port CT DMT-ATM cards should be stored in Flash"
	::= { mibloadSelectProfileEntry 77 }

    loadSelectProfile-o32DmtAslam	OBJECT-TYPE
	SYNTAX	INTEGER {
		    auto (1),
		    load (2),
		    skip (3)
		}
	ACCESS	read-write
	STATUS	mandatory
	DESCRIPTION	"Controls whether code images for 32 port ASLAM cards should be stored in Flash"
	::= { mibloadSelectProfileEntry 70 }

    loadSelectProfile-Vdsl	OBJECT-TYPE
	SYNTAX	INTEGER {
		    auto (1),
		    load (2),
		    skip (3)
		}
	ACCESS	read-write
	STATUS	mandatory
	DESCRIPTION	"Controls whether code images for 24 port VDSL cards should be stored in Flash"
	::= { mibloadSelectProfileEntry 71 }

    loadSelectProfile-Ds3Atm2	OBJECT-TYPE
	SYNTAX	INTEGER {
		    auto (1),
		    load (2),
		    skip (3)
		}
	ACCESS	read-write
	STATUS	mandatory
	DESCRIPTION	"Controls whether code images for DS3-ATM2 cards should be stored in Flash"
	::= { mibloadSelectProfileEntry 56 }

    loadSelectProfile-E3Atm	OBJECT-TYPE
	SYNTAX	INTEGER {
		    auto (1),
		    load (2),
		    skip (3)
		}
	ACCESS	read-write
	STATUS	mandatory
	DESCRIPTION	"Controls whether code images for E3-ATM cards should be stored in Flash"
	::= { mibloadSelectProfileEntry 57 }

    loadSelectProfile-Oc3Atm2	OBJECT-TYPE
	SYNTAX	INTEGER {
		    auto (1),
		    load (2),
		    skip (3)
		}
	ACCESS	read-write
	STATUS	mandatory
	DESCRIPTION	"Controls whether code images for OC3-ATM2 cards should be stored in Flash"
	::= { mibloadSelectProfileEntry 58 }

    loadSelectProfile-Vpn	OBJECT-TYPE
	SYNTAX	INTEGER {
		    auto (1),
		    load (2),
		    skip (3)
		}
	ACCESS	read-write
	STATUS	mandatory
	DESCRIPTION	"Controls whether code images for VPN cards should be stored in Flash"
	::= { mibloadSelectProfileEntry 59 }

    loadSelectProfile-Swan2	OBJECT-TYPE
	SYNTAX	INTEGER {
		    auto (1),
		    load (2),
		    skip (3)
		}
	ACCESS	read-write
	STATUS	mandatory
	DESCRIPTION	"Controls whether code images for SWAN version 2 cards should be stored in Flash"
	::= { mibloadSelectProfileEntry 60 }

    loadSelectProfile-Action-o	OBJECT-TYPE
	SYNTAX	INTEGER {
		    noAction (1),
		    createProfile (2),
		    deleteProfile (3)
		}
	ACCESS	read-write
	STATUS	mandatory
	DESCRIPTION	""
	::= { mibloadSelectProfileEntry 61 }

END
