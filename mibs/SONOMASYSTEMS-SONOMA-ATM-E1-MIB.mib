-- |**********************************************************************|
 -- | Copyright 1998 - Sonoma Systems, Inc. Marina del Rey, CA 90292       |
 -- |    Unpublished software - All rights reserved.                       |
 -- |                                                                      |
 -- | The information in this software is subject to change without notice |
 -- | and should not be construed as a commitment by Sonoma Systems, Inc.  |
 -- |                                                                      |
 -- | Sonoma Systems, Inc. assumes no responsibility for the use or        |
 -- | reliability of its software on equipment which is not supplied by    |
 -- | Sonoma Systems, Inc.                                                 |
 -- |                                                                      |
 -- | This software is furnished under a license and may be copied only    |
 -- | under the terms of that license and with the inclusion of this       |
 -- | notice. This software, or any other copies thereof, may not be       |
 -- | provided or otherwise made available to any other person except to   |
 -- | one who agrees to these license terms. Title to and ownership of the |
 -- | software shall at all times remain with Sonoma Systems, Inc.         |
 -- |**********************************************************************|
 --
 -- Sonoma Systems Inc.,
 -- 4640 Admiralty Way, Suite #600,
 -- Marina Del Rey,
 -- California 90292-6695.
 --
 -- Web : www.sonoma-systems.com
 -- Phone:  310.827.8000
 --
 -- NAME        : e1mib.def
 --
 -- DESCRIPTION : This is the MIB for the Sonoma ATM/E1 interface.
 --
 -- ARCHIVE : $Archive:   M:\pvcs\pvcsproj\sonoma3\src\mib\e1mib.dev  $
 -- REVISION: $Revision:   1.4  $
 -- AUTHOR  : $Author:   FREEVE  $
 -- DATE    : $Date:   Nov 13 1998 10:33:26  $

      SONOMASYSTEMS-SONOMA-ATM-E1-MIB DEFINITIONS ::= BEGIN

      IMPORTS
        Counter
        FROM RFC1155-SMI
        OBJECT-TYPE
        FROM RFC-1212
        sonomaATM
        FROM SONOMASYSTEMS-SONOMA-MIB;

    --  This MIB module uses the extended OBJECT-TYPE macro as
    --  defined in [14];
    --
    -- Hierarchy for these groups
    -- enterprises OBJECT IDENTIFIER ::= { private 4 }
    -- sonomaSystems OBJECT IDENTIFIER ::= {  enterprises 2926 }
    -- sonomaSeries OBJECT IDENTIFIER ::= { sonomaSystems 25 }
    -- sonomaATM OBJECT IDENTIFIER ::= { sonomaSeries 7 }
    sonomaE1ATMAdapterGroup OBJECT IDENTIFIER ::= { sonomaATM 6 }
        
      --   Sonoma E1 ATM Adapter Specific Group MIB groups
      atmE1ConfGroup OBJECT IDENTIFIER ::= { sonomaE1ATMAdapterGroup 1 }
      atmE1StatsGroup OBJECT IDENTIFIER ::= { sonomaE1ATMAdapterGroup 2 }

    -- Sonoma E1 ATM Adapter Specific Group MIB groups

    -- This group contains all informat specificly for
    -- Sonoma Systems E1 adapter. It includes the configuration and
    -- some statistics information

    --  atmE1ConfGroup

    atmE1ConfPhyTable  OBJECT-TYPE
        SYNTAX  SEQUENCE OF AtmE1ConfPhyEntry
        ACCESS  not-accessible
        STATUS  mandatory
        DESCRIPTION
            "A table of physical layer configuration for the E1
         interface"
        ::= { atmE1ConfGroup 1 }

    atmE1ConfPhyEntry  OBJECT-TYPE
        SYNTAX  AtmE1ConfPhyEntry
        ACCESS  not-accessible
        STATUS  mandatory
        DESCRIPTION
          "A entry in the table, containing information about the
           physical layer of a E1 interface"
        INDEX  { atmE1ConfPhysIndex }
        ::= { atmE1ConfPhyTable 1 }
    
    AtmE1ConfPhyEntry ::= SEQUENCE {
      atmE1ConfPhysIndex     INTEGER,
      atmE1ConfLoopback      INTEGER,
      atmE1ConfTxClockSelect   INTEGER,
      atmE1ConfFillerCells   INTEGER
    }

    atmE1ConfPhysIndex   OBJECT-TYPE
        SYNTAX  INTEGER
        ACCESS  read-only
        STATUS  mandatory
        DESCRIPTION
            "The physical interface index."
        ::= { atmE1ConfPhyEntry 1 }   

    atmE1ConfLoopback OBJECT-TYPE
        SYNTAX  INTEGER { 
                        disabled(1),
                        internal(2), 
                        external(3)
                        }
        ACCESS  read-write
        STATUS  mandatory
        DESCRIPTION
            "This object is used to modify the state of internal
             loopback...."
          DEFVAL { disabled }
        ::= { atmE1ConfPhyEntry 2 }

    atmE1ConfTxClockSelect OBJECT-TYPE
        SYNTAX  INTEGER {
                        internal(1), 
                        recovered(2) 
                        } 
        ACCESS  read-write
        STATUS  mandatory
        DESCRIPTION
            "Configure the transmit clock."
            DEFVAL { internal }
        ::= { atmE1ConfPhyEntry 3 }

    atmE1ConfFillerCells OBJECT-TYPE
        SYNTAX  INTEGER { 
			unassigned(1), 
			idle(2)
			}
        ACCESS  read-write
        STATUS  mandatory
        DESCRIPTION
            "This parameter indicates the type of filler cells to send
             when there are no data cells."
            DEFVAL { unassigned }
        ::= { atmE1ConfPhyEntry 4 }

    --  atmE1StatsGroup

    atmE1StatsTable  OBJECT-TYPE
        SYNTAX  SEQUENCE OF AtmE1StatsEntry
        ACCESS  not-accessible
        STATUS  mandatory
        DESCRIPTION
            "A table of physical layer statistics information for the E1 
         interface"
        ::= { atmE1StatsGroup 1 }

    atmE1StatsEntry  OBJECT-TYPE
        SYNTAX  AtmE1StatsEntry
        ACCESS  not-accessible
        STATUS  mandatory
        DESCRIPTION
          "A entry in the table, containing information about the
           physical layer of a E1 interface"
        INDEX  { atmE1StatsPhysIndex }
        ::= { atmE1StatsTable 1 }
    
    AtmE1StatsEntry ::= SEQUENCE {
      atmE1StatsPhysIndex      INTEGER,
      atmE1StatsNoSignals      Counter,
      atmE1StatsRAIDetects     Counter,
      atmE1StatsFASErrors      Counter,
      atmE1StatsCVErrors       Counter,
      atmE1StatsCRCErrors      Counter,
      atmE1StatsEBitErrors     Counter,
      atmE1StatsSyncLossCount  Counter,
      atmE1StatsHECErrors      Counter,
      atmE1StatsSignalLoss       INTEGER,
      atmE1StatsRAIDetect        INTEGER,
      atmE1StatsSyncLoss          INTEGER,
      atmE1StatsTxClockLoss         INTEGER,
      atmE1StatsClearCounters     INTEGER
    }

    atmE1StatsPhysIndex  OBJECT-TYPE
        SYNTAX  INTEGER
        ACCESS  read-only
        STATUS  mandatory
        DESCRIPTION
            "The physical interface index."
        ::= { atmE1StatsEntry 1 }  

    atmE1StatsNoSignals  OBJECT-TYPE
        SYNTAX  Counter
        ACCESS  read-only
        STATUS  mandatory
        DESCRIPTION
            "No signal error counter."
        ::= { atmE1StatsEntry 2 }

    atmE1StatsRAIDetects  OBJECT-TYPE
        SYNTAX  Counter
        ACCESS  read-only
        STATUS  mandatory
        DESCRIPTION
            "RAI Detect counter."
        ::= {atmE1StatsEntry 3 }
    
    atmE1StatsFASErrors  OBJECT-TYPE
        SYNTAX  Counter
        ACCESS  read-only
        STATUS  mandatory
        DESCRIPTION
            "FAS (Frame Alignment Signal) error counter."
        ::= { atmE1StatsEntry 4 }

    atmE1StatsCVErrors  OBJECT-TYPE
        SYNTAX  Counter
        ACCESS  read-only
        STATUS  mandatory
        DESCRIPTION
            "CV (Code Violation) error counter."
        ::= { atmE1StatsEntry 5 }

    atmE1StatsCRCErrors  OBJECT-TYPE
        SYNTAX  Counter
        ACCESS  read-only
        STATUS  mandatory
        DESCRIPTION
            "CRC4 error counter."
        ::= { atmE1StatsEntry 6 }

    atmE1StatsEBitErrors  OBJECT-TYPE
        SYNTAX  Counter
        ACCESS  read-only
        STATUS  mandatory
        DESCRIPTION
            "E-Bit (FEBE) error counter."
        ::= { atmE1StatsEntry 7 }

    atmE1StatsSyncLossCount  OBJECT-TYPE
        SYNTAX  Counter
        ACCESS  read-only
        STATUS  mandatory
        DESCRIPTION
            "Sync Loss counter."
        ::= { atmE1StatsEntry 8 }

    atmE1StatsHECErrors  OBJECT-TYPE
        SYNTAX  Counter
        ACCESS  read-only
        STATUS  mandatory
        DESCRIPTION
            "HEC error counter."
        ::= { atmE1StatsEntry 9 }

    atmE1StatsSignalLoss  OBJECT-TYPE
        SYNTAX  INTEGER {
                        true (1), 
                        false (2)
                        }
        ACCESS  read-only
        STATUS  mandatory
        DESCRIPTION
            "Signal loss indication."
        ::= { atmE1StatsEntry 10 }

    atmE1StatsRAIDetect  OBJECT-TYPE
        SYNTAX  INTEGER {
                        true (1), 
                        false (2)
                        }
        ACCESS  read-only
        STATUS  mandatory
        DESCRIPTION
            "RAI indication."
        ::= { atmE1StatsEntry 11 }


    atmE1StatsSyncLoss  OBJECT-TYPE
        SYNTAX  INTEGER {
                        true (1), 
                        false (2)
                        }
        ACCESS  read-only
        STATUS  mandatory
        DESCRIPTION
            "Loss of sync indication."
        ::= { atmE1StatsEntry 12 }

    atmE1StatsTxClockLoss  OBJECT-TYPE
        SYNTAX  INTEGER {
                        true (1), 
                        false (2)
                        }
        ACCESS  read-only
        STATUS  mandatory
        DESCRIPTION
            "Loss of transmit clock indication."
        ::= { atmE1StatsEntry 13 }

    atmE1StatsClearCounters  OBJECT-TYPE
        SYNTAX  INTEGER {
                        true (1), 
                        false (2)
                        }
        ACCESS  read-write
        STATUS  mandatory
        DESCRIPTION
            "Clear all counters in this group ONLY."
        DEFVAL { false }
        ::= { atmE1StatsEntry 14 }

END
