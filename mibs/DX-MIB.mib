-- *****************************************************************************
--
--                 eTrust Directory r8.1 (1278)
--
-- Copyright 1997, 1998, 1999, 2000 Computer Associates International, 
-- Incorporated.
--
-- THIS SOFTWARE AND DOCUMENTATION IS PROVIDED "AS IS" AND COMPUTER ASSOCIATES 
-- INT, INC. GRANTS NO WARRANTIES, EXPRESS OR IMPLIED, BY STATUE OR OTHERWISE,
-- REGARDING THE SOFTWARE AND ANY RELATED MATERIALS. IN NO EVENT SHALL
-- COMPUTER ASSOCIATES INT INC. BE LIABLE FOR ANY INCIDENTAL, CONSEQUENTIAL,
-- SPECIAL, EXEMPLARY OR PUNITIVE DAMAGES, (INCLUDING WITHOUT LIMITATION LOST
-- DATA, LOST PROFITS, LOST SAVINGS, OR LOSS OF GOODWILL) OF ANY KIND OR
-- NATURE, WHETHER SUCH LIABILITY IS ASSERTED ON THE BASIS OF CONTRACT OR
-- TORT (INCLUDING NEGLIGENCE OR STRICT LIABILITY).
-- 
-- This eTrust Directory specific Management Information Base is provided to
-- assist with integration of Directory with SNMP management software. It may 
-- be updated anytime without notice. It will however be compatible with the 
-- DXserver version it is packaged with. Care will however be taken to provide 
-- backward compatibility.
--
-- The OID for enterprises is 1.3.6.1.4.1
--
-- *****************************************************************************

DX-MIB DEFINITIONS ::= BEGIN
IMPORTS
    OBJECT-TYPE, MODULE-IDENTITY,
    Counter32, Gauge32,
        enterprises
    FROM SNMPv2-SMI;

dxMIB MODULE-IDENTITY
    LAST-UPDATED "200511081536Z"
    ORGANIZATION
        "Computer Associates Intl.
         http://www.ca.com"
    CONTACT-INFO
        "ComputerAssociatesCustomerSupport@ca.com"
    DESCRIPTION
        "This module contains eTrust Directory-specific SNMP information."
    REVISION "200511081536Z"
    DESCRIPTION
        "SNMPv2-compliant release."
::= { eTrustDirectory 21 }

-- Define the arc where the DXmib information will be stored
eTrustDirectory OBJECT IDENTIFIER ::= { enterprises 3327 }

-- **************************************************************
-- MultiWrite Monitoring MIB 
-- **************************************************************

dx-MULTIWRITE-MIB OBJECT IDENTIFIER ::= { dxMIB 1 }

    dxMWTable OBJECT-TYPE
        SYNTAX SEQUENCE OF DxMWEntry
        MAX-ACCESS not-accessible
        STATUS current
        DESCRIPTION
          " The table holding information relating to the
            MW status of remote DSAs."
        ::= {dx-MULTIWRITE-MIB 1}

    dxMWEntry OBJECT-TYPE
        SYNTAX DxMWEntry
        MAX-ACCESS not-accessible
        STATUS current
        DESCRIPTION
          " Entry containing information relating to the
            MW status of remote DSAs."
        INDEX { dxMWIndex }
        ::= { dxMWTable 1 }

    DxMWEntry ::= SEQUENCE {

-- Entries containing information for each remote DSA the current DSA 
-- is multi-writing to.

        dxMWIndex
            INTEGER,
        dxRemoteDsaName
            OCTET STRING,
        dxMWQueueLength
            Gauge32,
        dxMWStatus
            INTEGER,
        dxMWPendingRemote
            Gauge32,
        dxMWConfirmedLocal
            Gauge32
    }

    dxMWIndex  OBJECT-TYPE
        SYNTAX INTEGER (1..2147483647)
        MAX-ACCESS not-accessible
        STATUS current
        DESCRIPTION
          " Create a unique key to identify rows of MW information"
        ::= {dxMWEntry 1}

    dxRemoteDsaName OBJECT-TYPE
        SYNTAX OCTET STRING
        MAX-ACCESS read-only
        STATUS current
        DESCRIPTION
          " Name of the current Remote DSA"
        ::= {dxMWEntry 2}

    dxMWQueueLength OBJECT-TYPE
        SYNTAX Gauge32
        MAX-ACCESS read-only
        STATUS current
        DESCRIPTION
          " The number of currently MWs outstanding"
        ::= {dxMWEntry 3}

    dxMWStatus OBJECT-TYPE
        SYNTAX INTEGER
        {
            internal-error(0),
            ok(1),
            failed(2),
            failed-no-dsa(3),
            non-existent(4),
            recovering(5),
            disp-failed(6),
            wait-disp(7),
            q-purged(8),
            failed-sent(9)
        }
        MAX-ACCESS read-only
        STATUS current
        DESCRIPTION
          " Status of MW queue. The meaning of the statuses are as follows:
            internal-error - An internal error has occurred.
            ok             - MW is functioning correctly.
            failed         - The MW DSA is not contactable. Update will be 
                             queued. The uncontactable DSA needs attention.
            failed-no-dsa  - MW Update failed. Knowledge of DSA lost.
            non-existent   - Waiting for DISP but knowledge of DSA lost.
            recovering     - MW DSA has been contacted and being updated.
            disp-failed    - A failure occurred during DISP. The cause of this
                             needs to be resolved before MW will continue.
            wait-disp      - Waiting for DISP to complete before MWing.
            q-purged       - MW queue was purged and MW to the DSA disabled.
            failed-sent    - Have sent an update to a previously uncontactable
                             DSA and waiting on a response."
        ::= {dxMWEntry 4}

    dxMWPendingRemote OBJECT-TYPE
        SYNTAX Gauge32
        MAX-ACCESS read-only
        STATUS current
        DESCRIPTION
          " Gauge of pending remote MW operations"
        ::= {dxMWEntry 5}

    dxMWConfirmedLocal OBJECT-TYPE
        SYNTAX Gauge32
        MAX-ACCESS read-only
        STATUS current
        DESCRIPTION
          " Gauge of queued MW operations that have been applied locally."
            ::= {dxMWEntry 6}

-- **************************************************************
-- DSA Statistics Monitoring MIB 
-- **************************************************************

dx-STATISTICS-MIB OBJECT IDENTIFIER ::= { dxMIB 2 }

    dxStatsAssocs OBJECT-TYPE
        SYNTAX Gauge32
        MAX-ACCESS read-only
        STATUS current
        DESCRIPTION
            " The current number of associations"
        ::= {dx-STATISTICS-MIB 1}

    dxStatsNilCredit OBJECT-TYPE
        SYNTAX Counter32
        MAX-ACCESS read-only
        STATUS current
        DESCRIPTION
            " The number of times flow control was applied to any association"
        ::= {dx-STATISTICS-MIB 2}

    dxStatsNoTicks OBJECT-TYPE
        SYNTAX Gauge32
        MAX-ACCESS read-only
        STATUS current
        DESCRIPTION
            " The number of times in the last minute processing did not occur
              NOTE: This requires stats logging/tracing to enable"
        ::= {dx-STATISTICS-MIB 3}

    dxStatsQueue OBJECT-TYPE
        SYNTAX Gauge32
        MAX-ACCESS read-only
        STATUS current
        DESCRIPTION
            " The number of outstanding operations"
        ::= {dx-STATISTICS-MIB 4}

    dxStatsBusy OBJECT-TYPE
        SYNTAX Gauge32
        MAX-ACCESS read-only
        STATUS current
        DESCRIPTION
            " The percentage of time in the last minute the DSA was busy
              NOTE: This requires stats logging/tracing to enable"
        ::= {dx-STATISTICS-MIB 5}

    dxStatsOps OBJECT-TYPE
        SYNTAX Counter32
        MAX-ACCESS read-only
        STATUS current
        DESCRIPTION
            " The total number of operations processed since DSA was started"
        ::= {dx-STATISTICS-MIB 6}

    dxStatsEntries OBJECT-TYPE
        SYNTAX Counter32
        MAX-ACCESS read-only
        STATUS current
        DESCRIPTION
            " The total number of entries returned since DSA was started"
        ::= {dx-STATISTICS-MIB 7}

    dxStatsMWQ OBJECT-TYPE
        SYNTAX Gauge32
        MAX-ACCESS read-only
        STATUS current
        DESCRIPTION
            " The number of queued multiwrite operations"
        ::= {dx-STATISTICS-MIB 8}

-- **************************************************************
-- DxCache Monitoring MIB 
-- **************************************************************

dx-CACHE-MIB OBJECT IDENTIFIER ::= { dxMIB 3 }

    dxCacheStatus OBJECT-TYPE
        SYNTAX INTEGER
        {
            internal-error(0),
            cache-disabled(1),
            cache-building(2),
            cache-ok(3),
            cache-dirty(4)
        }
        MAX-ACCESS read-only
        STATUS current
        DESCRIPTION
          " Status of DxCache. The meaning of the statuses are as follows:
            internal-error - An internal error has occurred.
            cache-disabled - DxCache is disabled (see trace log if unexpected):
                             - Not turned on
                             - Had a problem loading
                             - Had a problem during an entry update
                             - Has exceeded the maximum configured size
                             - Machine has run out of memory
                             - etc etc
            cache-building - DxCache is currently loading information from the
                             backend.
            cache-ok       - DxCache is up and running.
            cache-dirty    - The DSA has received a DISP update. DxCache will be
                             refreshed"
        ::= {dx-CACHE-MIB 1}

    dxCacheSize OBJECT-TYPE
        SYNTAX Gauge32
        MAX-ACCESS read-only
        STATUS current
        DESCRIPTION
            " Memory in (mb) currently being used by DxCache."
        ::= {dx-CACHE-MIB 2}

    dxCacheSearchHits OBJECT-TYPE
        SYNTAX Counter32
        MAX-ACCESS read-only
        STATUS current
        DESCRIPTION
            " Number of search requests serviced by DxCache."
        ::= {dx-CACHE-MIB 3}

    dxCacheSearchMisses OBJECT-TYPE
        SYNTAX Counter32
        MAX-ACCESS read-only
        STATUS current
        DESCRIPTION
            " Number of search requests going through to the backend."
        ::= {dx-CACHE-MIB 4}

    dxCacheSequentialScans OBJECT-TYPE
        SYNTAX Counter32
        MAX-ACCESS read-only
        STATUS current
        DESCRIPTION
            " Number of searches requiring a sequential scan of the cache."
        ::= {dx-CACHE-MIB 5}
END
