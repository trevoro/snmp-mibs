-- Copyright 2003 hP, Inc.
-- All rights reserved.
-- Copyright message need to be updated

    HP-PROCURVE-420-PRIVATE-MIB 

    DEFINITIONS ::= BEGIN
  
    IMPORTS
        ifIndex                                 FROM RFC1213-MIB
        mgmt, Counter, IpAddress, enterprises   FROM RFC1155-SMI
       Integer32, Counter32, OBJECT-TYPE                    FROM SNMPv2-SMI
    ;
    PhysAddress 
        ::= OCTET STRING
    Guage32   
        ::= Counter
    MacAddress  
        ::= OCTET STRING
    DisplayString  
        ::= OCTET STRING
    TruthValue  ::=
        INTEGER { false(2), true(1) }

-- Before we get the private mib OID from hP, using the accton OID instead

    hP                          OBJECT IDENTIFIER ::= { enterprises 11 }
    wireless                    OBJECT IDENTIFIER ::= { hP 2 }
    enterprise                  OBJECT IDENTIFIER ::= { wireless 3 }
    accessPoint                 OBJECT IDENTIFIER ::= { enterprise 7 }
    proCurve                    OBJECT IDENTIFIER ::= { accessPoint 11 }
    hPProCuve420                OBJECT IDENTIFIER ::= { proCurve 37 }
 
-- accton AP OBJECT IDs Groups

    enterpriseApSys             OBJECT IDENTIFIER ::= { hPProCuve420 1 }
    enterpriseApLineMgnt        OBJECT IDENTIFIER ::= { hPProCuve420 2 }
    enterpriseApPortMgnt        OBJECT IDENTIFIER ::= { hPProCuve420 3 }
    enterpriseApFileTransferMgt OBJECT IDENTIFIER ::= { hPProCuve420 4 }
    enterpriseApResetMgt        OBJECT IDENTIFIER ::= { hPProCuve420 5 }
    enterpriseApIpMgt           OBJECT IDENTIFIER ::= { hPProCuve420 6 }
    enterpriseAPdot11           OBJECT IDENTIFIER ::= { hPProCuve420 7 }


-- ****************************************************************************************
--  enterpriseApSys - Standard Mib elements
-- ****************************************************************************************
swHardwareVer OBJECT-TYPE
        SYNTAX      DisplayString (SIZE(0..20))
        ACCESS      read-only
        STATUS      mandatory
        DESCRIPTION "Hardware version of the main board."
        ::= { enterpriseApSys 1 }

swBootRomVer OBJECT-TYPE
        SYNTAX      DisplayString (SIZE(0..20))
        ACCESS      read-only
        STATUS      mandatory
        DESCRIPTION "Boot ROM code version of the main board."
        ::= { enterpriseApSys 2 }

swOpCodeVer OBJECT-TYPE
        SYNTAX      DisplayString (SIZE(0..20))
        ACCESS      read-only
        STATUS      mandatory
        DESCRIPTION "Operation code version of the main board."
        ::= { enterpriseApSys 3 }

swCountryCode OBJECT-TYPE
        SYNTAX      DisplayString (SIZE(2))
        ACCESS      read-write
        STATUS      mandatory
        DESCRIPTION "Country code of the AP.  
AL-ALBANIA,     DZ-ALGERIA,     AR-ARGENTINA,   AM-ARMENIA,     AU-AUSTRALIA,   AT-AUSTRIA,     AZ-AZERBAIJAN,
BH-BAHRAIN,     BY-BELARUS,     BE-BELGIUM,     BZ-BELIZE,      BO-BOLVIA,      BR-BRAZIL,      BN-BRUNEI_DARUSSALAM, 
BG-BULGARIA,    CA-CANADA,      CL-CHILE,       CN-CHINA,       CO-COLOMBIA,    CR-COSTA_RICA,  HR-CROATIA,
CY-CYPRUS,      CZ-CZECH_REPUBLIC,              DK-DENMARK,     DO-DOMINICAN_REPUBLIC,          EC-ECUADOR, 
EG-EGYPT,       EE-ESTONIA,     FI-FINLAND,     FR-FRANCE,      GE-GEORGIA,     DE-GERMANY,     GR-GREECE, 
GT-GUATEMALA,   HK-HONG_KONG,   HU-HUNGARY,     IS-ICELAND,     IN-INDIA,       ID-INDONESIA,   IR-IRAN, 
IE-IRELAND,     IL-ISRAEL,      IT-ITALY,       JP-JAPAN,       JO-JORDAN,      KZ-KAZAKHSTAN,  KP-NORTH_KOREA, 
KR-KOREA_REPUBLIC,              KW-KUWAIT,      LV-LATVIA,      LB-LEBANON,     LI-LIECHTENSTEIN, 
LT-LITHUANIA,   LU-LUXEMBOURG,  MO-MACAU,       MK-MACEDONIA,   MY-MALAYSIA,    MX-MEXICO,      MC-MONACO, 
MA-MOROCCO,     NA-NORTH_AMERICA, NL-NETHERLANDS, NZ-NEW_ZEALAND, NO-NORWAY,      OM-OMAN,        PK-PAKISTAN,    
PA-PANAMA,      PE-PERU,        PH-PHILIPPINES, PL-POLAND,      PT-PORTUGAL,    PR-PUERTO_RICO, QA-QATAR,       
RO-ROMANIA,     RU-RUSSIA,      SA-SAUDI_ARABIA, SG-SINGAPORE,  SK-SLOVAK_REPUBLIC,             SI-SLOVENIA,    
ZA-SOUTH_AFRICA, ES-SPAIN,       SE-SWEDEN,      CH-SWITZERLAND, SY-SYRIA,       TW-TAIWAN,      TH-THAILAND,    
TR-TURKEY,      UA-UKRAINE,     AE-UNITED_ARAB_EMIRATES,        GB-UNITED_KINGDOM,              US-UNITED_STATES, 
UY-URUGUAY,     VE-VENEZUELA,   VN-VIETNAM"
        ::= { enterpriseApSys 4 }
-- ****************************************************************************************
--  enterpriseApLine  AP Line elements
-- ****************************************************************************************
lineTable OBJECT-TYPE
        SYNTAX      SEQUENCE OF LineEntry
        ACCESS      not-accessible
        STATUS      mandatory
        DESCRIPTION "Table of descriptive and status information about
                     configuration of each RS-232 line in this system"
        ::= { enterpriseApLineMgnt 1 }

lineEntry OBJECT-TYPE
        SYNTAX      LineEntry
        ACCESS      not-accessible
        STATUS      mandatory
        DESCRIPTION "An entry in the table, containing information
                     about configuration in one RS232 line of the Access Point."
        INDEX       { lineIndex }
        ::= { lineTable 1 }

LineEntry ::= SEQUENCE
{
    lineIndex                Integer32,
    lineDataBits             Integer32,
    lineParity               INTEGER,
    lineSpeed                Integer32,
    lineStopBits             Integer32
}

lineIndex OBJECT-TYPE
        SYNTAX      Integer32
        ACCESS      not-accessible
        STATUS      mandatory
        DESCRIPTION "This is defined as RS-232 index."
        ::= { lineEntry 1 }

lineDataBits OBJECT-TYPE
        SYNTAX      Integer32
        ACCESS      read-only
        STATUS      mandatory
        DESCRIPTION "This is defined as number of data bits for the RS232 interface."
        ::= { lineEntry 2 }


lineParity OBJECT-TYPE
        SYNTAX      INTEGER
                    {
                        none(99),
                        odd(1),
                        even(2)
                    }
        ACCESS      read-only
        STATUS      mandatory
        DESCRIPTION "This is defined as parity of the RS232 interface."
        ::= { lineEntry 3 }

lineSpeed OBJECT-TYPE
        SYNTAX      Integer32
        ACCESS      read-only
        STATUS      mandatory
        DESCRIPTION "This is defined as the speed of the RS-232 interface."
        ::= { lineEntry 4 }

lineStopBits OBJECT-TYPE
        SYNTAX      Integer32
        ACCESS      read-only
        STATUS      mandatory
        DESCRIPTION "This is defined as the number of stop bits for the RS-232 interface."
        ::= { lineEntry 5 }


-- ****************************************************************************************
--  enterpriseApPortMgnt - Port Mib elements
-- ****************************************************************************************
portTable OBJECT-TYPE
        SYNTAX      SEQUENCE OF PortEntry
        ACCESS      not-accessible
        STATUS      mandatory
        DESCRIPTION "Table of descriptive and status information about
                     configuration of each switch port (including expansion slot)
                     in this system. This table also contains information
                     about each trunk (similar to Cisco's EtherChannel)."
        ::= { enterpriseApPortMgnt 1 }

portEntry OBJECT-TYPE
        SYNTAX      PortEntry
        ACCESS      not-accessible
        STATUS      mandatory
        DESCRIPTION "An entry in the table, containing information
                     about configuration in one switch port of the switch."
        INDEX       { portIndex }
        ::= { portTable 1 }

PortEntry ::= SEQUENCE
{
    portIndex                Integer32,
    portName                 DisplayString,
    portType                 INTEGER,
    portSpeedDpxCfg          INTEGER,
    portFlowCtrlCfg          INTEGER,
    portCapabilities         INTEGER,
    portAutonegotiation      INTEGER,
    portSpeedDpxStatus       INTEGER,
    portFlowCtrlStatus       INTEGER
}

portIndex OBJECT-TYPE
        SYNTAX      Integer32
        ACCESS      not-accessible
        STATUS      mandatory
        DESCRIPTION "This is defined as ifIndex in the IF-MIB."
        ::= { portEntry 1 }

portName OBJECT-TYPE
        SYNTAX      DisplayString (SIZE(0..64))
        ACCESS      read-only
        STATUS      mandatory
        DESCRIPTION "Indicates the port name. This is same as 
                     ifAlias in the IF-MIB (RFC2863 or later)."
        ::= { portEntry 2 }

portType OBJECT-TYPE
        SYNTAX      INTEGER
                    {
                        other(1),
                        hundredBaseTX(2),
                        hundredBaseFX(3),
                        thousandBaseSX(4),
                        thousandBaseLX(5),
                        thousandBaseT(6),
                        thousandBaseGBIC(7),
                        thousandBaseMiniGBIC(8)
                    }
        ACCESS      read-only
        STATUS      mandatory
        DESCRIPTION "Indicates the port type."
        ::= { portEntry 3 }

portSpeedDpxCfg OBJECT-TYPE
        SYNTAX      INTEGER
                    {
                        auto(1),
                        halfDuplex10(2),
                        fullDuplex10(3),
                        halfDuplex100(4),
                        fullDuplex100(5),
                        halfDuplex1000(6),
                        fullDuplex1000(7)
                    }
        ACCESS      read-only
        STATUS      mandatory
        DESCRIPTION "Set the port speed and duplex mode as follows:
                         halfDuplex10(2)    - 10Mbps and half duplex mode
                         fullDuplex10(3)    - 10Mbps and full duplex mode
                         halfDuplex100(4)   - 100Mbps and half duplex mode
                         fullDuplex100(5)   - 100Mbps and full duplex mode
                         halfDuplex1000(6)  - 1000Mbps and half duplex mode
                         fullDuplex1000(7)  - 1000Mbps and full duplex mode
                     hundredBaseTX port can be set as
                         halfDuplex10(2)
                         fullDuplex10(3)
                         halfDuplex100(4)
                         fullDuplex100(5)
                     hundredBaseFX port can be set as
                         halfDuplex100(4)
                         fullDuplex100(5)
                     thousandBaseSX port can be set as
                         halfDuplex1000(6)
                         fullDuplex1000(7)
                     The actual operating speed and duplex of the port
                     is given by portSpeedDpxStatus."
        DEFVAL      { halfDuplex10 }
        ::= { portEntry 4 }

portFlowCtrlCfg OBJECT-TYPE
        SYNTAX      INTEGER
                    {
                        enabled(1),
                        disabled(2),
                        backPressure(3),
                        dot3xFlowControl(4)
                    }
        ACCESS      read-only
        STATUS      mandatory
        DESCRIPTION "(1) Flow control mechanism is enabled.
                         If the port type is hundredBaseTX or thousandBaseSX:
                         When the port is operating in halfDuplex mode, the
                         port uses backPressure flow control mechanism. When
                         the port is operating in fullDuplex mode, the port
                         uses IEEE 802.3x flow control mechanism.
                         If the port type is hundredBaseFX:
                         When the port is operating in halfDuplex mode, the
                         port uses backPressure flow control mechanism. When
                         the port is operating in fullDuplex mode, Flow
                         control mechanism will not function.
                     (2) Flow control mechanism is disabled.
                     (3) Flow control mechanism is backPressure.
                         when the port is in fullDuplex mode.This flow control
                         mechanism will not function.
                     (4) Flow control mechanism is IEEE 802.3x flow control.
                         when the port is in halfDuplex mode.This flow control
                         mechanism will not function.
                     hundredBaseTX and thousandBaseSX port can be set as:
                         enabled(1),
                         disabled(2),
                         backPressure(3),
                         dot3xFlowControl(4).
                     hundredBaseFX port can be set as:
                         enabled(1),
                         disabled(2),
                         backPressure(3).
                     The actual flow control mechanism is used given by
                     portFlowCtrlStatus."
        DEFVAL      { enabled }
        ::= { portEntry 5 }

portCapabilities OBJECT-TYPE
        SYNTAX      INTEGER
                    {
                        portCap10half(99),
                        portCap10full(1),
                        portCap100half(2),
                        portCap100full(3),
                        portCap1000half(4),
                        portCap1000full(5),
                        reserved6(6),
                        reserved7(7),
                        reserved8(8),
                        reserved9(9),
                        reserved10(10),
                        reserved11(11),
                        reserved12(12),
                        reserved13(13),
                        portCapSym(14),
                        portCapFlowCtrl(15)
                    }
        ACCESS      read-only
        STATUS      mandatory
        DESCRIPTION "Port capabilities."
        ::= { portEntry 6 }

portAutonegotiation OBJECT-TYPE
        SYNTAX      INTEGER
                    {
                        enabled(1),
                        disabled(2)
                    }
        ACCESS      read-only
        STATUS      mandatory
        DESCRIPTION "Whether autonegotiation is enabled."
        ::= { portEntry 7 }
                        
portSpeedDpxStatus OBJECT-TYPE
        SYNTAX      INTEGER
                    {
                        error(1),
                        halfDuplex10(2),
                        fullDuplex10(3),
                        halfDuplex100(4),
                        fullDuplex100(5),
                        halfDuplex1000(6),
                        fullDuplex1000(7)
                    }
        ACCESS      read-only
        STATUS      mandatory
        DESCRIPTION "The operating speed and duplex mode of the
                     switched port. If this index is a trunk,
                     the speed is the speed of its individual members.
                     If this index is a trunk and the result
                     is inconsistent among its member ports, this value is
                     error(1)."
        ::= { portEntry 8 }

portFlowCtrlStatus OBJECT-TYPE
        SYNTAX      INTEGER
                    {
                        error(1),
                        backPressure(2),
                        dot3xFlowControl(3),
                        none(4)
                    }
        ACCESS      read-only
        STATUS      mandatory
        DESCRIPTION "(2) BackPressure flow control machanism is used.
                     (3) IEEE 802.3 flow control machanism is used.
                     (4) Flow control mechanism is disabled.
                     If this index is a trunk and the result
                     is inconsistent among its member ports, this value is
                     error(1)."
        ::= { portEntry 9 }

-- ****************************************************************************************
--  enterpriseApTftpMgt - File Transfer Mib elements
-- ****************************************************************************************

transferStart  OBJECT-TYPE
    SYNTAX     INTEGER {
                  go(1),
                  nogo(2)
               }
    ACCESS     read-write
    STATUS     mandatory
    DESCRIPTION
        "Set to go(1) to start a transfer."
    ::= { enterpriseApFileTransferMgt 1 }

transferType  OBJECT-TYPE
    SYNTAX     INTEGER {
                  ftp(1),
                  tftp(2)
               }
    ACCESS     read-write
    STATUS     mandatory
    DESCRIPTION
        "Type of file to transfer."
    ::= { enterpriseApFileTransferMgt 2 }

fileType  OBJECT-TYPE
    SYNTAX     INTEGER {
                  opcode(1),
                  config(2)
               }
    ACCESS     read-write
    STATUS     mandatory
    DESCRIPTION
        "Type of file to transfer."
    ::= { enterpriseApFileTransferMgt 3 }

srcFile  OBJECT-TYPE
    SYNTAX     DisplayString (SIZE(0..127))
    ACCESS     read-write
    STATUS     mandatory
    DESCRIPTION
        "The source file name for TFTP transfer when a
        transfer is next requested via this MIB.  This value is set to
        the zero length string when no file name has been specified."
    ::= { enterpriseApFileTransferMgt 4 }

destFile  OBJECT-TYPE
    SYNTAX     DisplayString (SIZE(0..127))
    ACCESS     read-write
    STATUS     mandatory
    DESCRIPTION
        "The destination file name for TFTP transfer when a
        transfer is next requested via this MIB.  This value is set to
        the zero length string when no file name has been specified."
    ::= { enterpriseApFileTransferMgt 5 }

fileServer  OBJECT-TYPE
    SYNTAX     IpAddress
    ACCESS     read-write
    STATUS     mandatory
    DESCRIPTION
        "The IP address of the TFTP server for transfer
        when a download is next requested via this MIB.
        This value is set to `0.0.0.0' when no IP address has been
        specified."
    ::= { enterpriseApFileTransferMgt 6 }

userName  OBJECT-TYPE
    SYNTAX     DisplayString (SIZE(0..127))
    ACCESS     read-write
    STATUS     mandatory
    DESCRIPTION
        "The username specified for an FTP Transfer."
    ::= { enterpriseApFileTransferMgt 7 }

password  OBJECT-TYPE
    SYNTAX     DisplayString (SIZE(0..127))
    ACCESS     read-write
    STATUS     mandatory
    DESCRIPTION
        "The password specified for an FTP Transfer."
    ::= { enterpriseApFileTransferMgt 8 }

-- ****************************************************************************************
--  enterpriseApResetMgt - Reset Mib elements
-- ****************************************************************************************

restartOpCodeFile OBJECT-TYPE
        SYNTAX      DisplayString (SIZE(0..32))
        ACCESS      read-write
        STATUS      mandatory
        DESCRIPTION "Name of op-code file for start-up."
        ::= { enterpriseApResetMgt 1 }

restartControl  OBJECT-TYPE
    SYNTAX     INTEGER {
                    running(1),
                    warmBoot(2),
                    coldBoot(3)
              }
    ACCESS     read-write
    STATUS     mandatory
    DESCRIPTION
        "Setting this object to warmBoot(2) causes the device to
        restart the application software with current configuration
        parameters saved in non-volatile memory.  Setting this
        object to coldBoot(3) causes the device to reinitialize
        configuration parameters in non-volatile memory to default
        values and restart the application software.  When the device
        is running normally, this variable has a value of
        running(1)."
    ::= { enterpriseApResetMgt 2 }


-- ****************************************************************************************
--  enterpriseApIpMgnt - Ip Mib elements
-- ****************************************************************************************

netConfigIPAddress  OBJECT-TYPE
    SYNTAX     IpAddress
    ACCESS     read-write
    STATUS     mandatory
    DESCRIPTION
        "The IP address of this Net interface.  The default value
        for this object is 0.0.0.0.  If either the netConfigIPAddress
        or netConfigSubnetMask are 0.0.0.0, then when the device
        boots, it may use DHCP to try to figure out what these
        values should be. If DHCP fails, before the device
        can talk on the network, this value must be configured
        (e.g., through a terminal attached to the device)."
    ::= { enterpriseApIpMgt 1 }

netConfigSubnetMask  OBJECT-TYPE
    SYNTAX     IpAddress
    ACCESS     read-write
    STATUS     mandatory
    DESCRIPTION
        "The subnet mask of this Net interface.  The default value
        for this object is 0.0.0.0.  If either the netConfigIPAddress
        or netConfigSubnetMask are 0.0.0.0, then when the device
        boots, it may use DHCP to try to figure out what these
        values should be. If DHCP fails, before the device
        can talk on the network, this value must be configured
        (e.g., through a terminal attached to the device)."
    ::= { enterpriseApIpMgt 2 }

netDefaultGateway  OBJECT-TYPE
    SYNTAX     IpAddress
    ACCESS     read-write
    STATUS     mandatory
    DESCRIPTION
        "The IP Address of the default gateway.  If this value is
        undefined or unknown, it shall have the value 0.0.0.0."
    ::= { enterpriseApIpMgt 3 }

ipHttpState OBJECT-TYPE
    SYNTAX     INTEGER
               {
                   enabled(1),
                   disabled(2)
               }
    ACCESS     read-write
    STATUS     mandatory
    DESCRIPTION
        "Whether HTTP is enabled."
    ::= { enterpriseApIpMgt 4 }

ipHttpPort OBJECT-TYPE
    SYNTAX     INTEGER
    ACCESS     read-write
    STATUS     mandatory
    DESCRIPTION
        "The port number for HTTP."
    ::= { enterpriseApIpMgt 5 }

-- ****************************************************************************************
--  enterpriseAPdot11 - 802.11 MIB elements 
-- ****************************************************************************************

hpdot11StationConfigTable OBJECT-TYPE
        SYNTAX      SEQUENCE OF Hpdot11StationConfigEntry
        ACCESS      not-accessible
        STATUS      mandatory
        DESCRIPTION "Table of descriptive and status information about
                     configuration of each radio of the AP."
        ::= { enterpriseAPdot11 1 }

hpdot11StationConfigEntry OBJECT-TYPE
        SYNTAX      Hpdot11StationConfigEntry
        ACCESS      not-accessible
        STATUS      mandatory
        DESCRIPTION "An entry in the table, containing information
                     about configuration in one radio of the AP."
        INDEX       { hpdot11portIndex }
        ::= { hpdot11StationConfigTable 1 }

Hpdot11StationConfigEntry ::= SEQUENCE
{
    hpdot11portIndex                            Integer32,
    hpdot11DesiredSSID                      OCTET STRING,
    hpdot11BeaconPeriod                     INTEGER,
    hpdot11DTIMPeriod                           INTEGER,
    hpdot11OperationalRateSet                   INTEGER,
    hpdot11AuthenticationAlgorithm          INTEGER
}

hpdot11portIndex OBJECT-TYPE
        SYNTAX      Integer32
        ACCESS      not-accessible
        STATUS      mandatory
        DESCRIPTION "Radio index of the AP."
        ::= { hpdot11StationConfigEntry 1 }

hpdot11DesiredSSID OBJECT-TYPE
        SYNTAX OCTET STRING (SIZE(0..32))
        ACCESS read-write
        STATUS mandatory
        DESCRIPTION
            "This attribute reflects the Service Set ID used
            in the DesiredSSID parameter of the most recent
            MLME_Scan.request. This value may be modified
            by an external management entity and used by the
            local SME to make decisions about the Scanning process."

    ::= { hpdot11StationConfigEntry 2 }

hpdot11BeaconPeriod OBJECT-TYPE
        SYNTAX INTEGER (20..1000)
        ACCESS read-write
        STATUS mandatory
        DESCRIPTION
            "This attribute shall specify the number of ms that a
            station shall use for scheduling Beacon transmissions.
            This value is transmitted in Beacon and Probe Response
            frames."

    ::= { hpdot11StationConfigEntry 3 }

hpdot11DTIMPeriod OBJECT-TYPE
        SYNTAX INTEGER(1..255)
        ACCESS read-write
        STATUS mandatory
        DESCRIPTION
            "This attribute shall specify the number of beacon
            intervals that shall elapse between transmission of
            Beacons frames containing a TIM element whose DTIM
            Count field is 0. This value is transmitted in
            the DTIM Period field of Beacon frames."

    ::= { hpdot11StationConfigEntry 4 }

hpdot11OperationalRateSet OBJECT-TYPE
        SYNTAX INTEGER (1..108)
        ACCESS read-write
        STATUS mandatory
        DESCRIPTION
            "This attribute shall specify the set of data rates
            at which the station may transmit data. Each octet
            contains a value representing a rate. Each rate
            shall be within the range from 2 to 127,
            corresponding to data rates in increments of
            500 kb/s from 1 Mbit/s to 63.5 Mbit/s, and shall be
            supported (as indicated in the supported rates
            table) for receiving data. This value is reported in
            transmitted Beacon, Probe Request, Probe Response,
            Association Request, Association Response,
            Reassociation Request, and Reassociation Response
            frames, and is used to determine whether a BSS
            with which the station desires to synchronize is
            suitable. It is also used when starting a BSS,
            as specified in 10.3."

    ::= { hpdot11StationConfigEntry 5 }

hpdot11AuthenticationAlgorithm OBJECT-TYPE
        SYNTAX INTEGER { openSystem (1), sharedKey (2) }
        ACCESS read-write
        STATUS mandatory
        DESCRIPTION
            "This attribute shall be a set of all the authentication
            algorithms supported by the STAs. The following are the
            default values and the associated algorithm.
                Value = 1: Open System
                Value = 2: Shared Key"

    ::= {  hpdot11StationConfigEntry 6 }

-- **********************************************************************
-- * End of dot11StationConfig TABLE
-- **********************************************************************   

-- **********************************************************************
-- * hpdot11PrivacyEntry TABLE
-- **********************************************************************   

hpdot11PrivacyTable OBJECT-TYPE
        SYNTAX      SEQUENCE OF Hpdot11PrivacyEntry
        ACCESS      not-accessible
        STATUS      mandatory
        DESCRIPTION "Table of descriptive and status information about
                     configuration of each radio of the AP."
        ::= { enterpriseAPdot11 2 }

hpdot11PrivacyEntry OBJECT-TYPE
        SYNTAX      Hpdot11PrivacyEntry
        ACCESS      not-accessible
        STATUS      mandatory
        DESCRIPTION "An entry in the table, containing information
                     about configuration in one radio of the AP."
        INDEX       { hpdot11PrivacyportIndex }
        ::= { hpdot11PrivacyTable 1 }

Hpdot11PrivacyEntry ::= SEQUENCE
{
    hpdot11PrivacyportIndex                 Integer32,
    hpdot11PrivacyInvoked                       INTEGER,
    hpdot11WEPDefaultKeyID                  INTEGER,
    hpdot11WEPKeyMappingLength              INTEGER
}

hpdot11PrivacyportIndex OBJECT-TYPE
        SYNTAX      Integer32
        ACCESS      not-accessible
        STATUS      mandatory
        DESCRIPTION "Radio index of the AP."
        ::= { hpdot11PrivacyEntry 1 }

hpdot11PrivacyInvoked   OBJECT-TYPE
        SYNTAX      INTEGER
                    {
                        true(1),
                        false(2)
                    }       
        ACCESS read-write
        STATUS mandatory

        DESCRIPTION
            "When this attribute is true, it shall indicate that the IEEE
            802.11 WEP mechanism is used for transmitting frames of type
            Data. The default value of this attribute shall be false."
        ::= { hpdot11PrivacyEntry 2 }

hpdot11WEPDefaultKeyID OBJECT-TYPE
        SYNTAX INTEGER (0..3)
        ACCESS read-write
        STATUS mandatory
        DESCRIPTION
            "This attribute shall indicate the use of the first,
            second, or third element of the WEPDefaultKeys
            array when set to values of zero, one, or two(the 
            fourth are reserved for dynamic key). The
            default value of this attribute shall be 0."
        REFERENCE "ISO/IEC 8802-11:1999, 8.3.2"
    ::= { hpdot11PrivacyEntry 3 }

hpdot11WEPKeyMappingLength OBJECT-TYPE
        SYNTAX INTEGER (10..2147483647)
        ACCESS read-write
        STATUS mandatory
        DESCRIPTION
            "The maximum number of tuples that dot11WEPKeyMappings can hold."
        REFERENCE "ISO/IEC 8802-11:1999, 8.3.2"
    ::= { hpdot11PrivacyEntry 4 }

-- **********************************************************************
-- * End of dot11Privacy TABLE
-- **********************************************************************

-- MAC Attributes

hpdot11mac                      OBJECT IDENTIFIER ::= { enterpriseAPdot11 3 }

-- **********************************************************************
-- * dot11OperationTable TABLE
-- **********************************************************************
hpdot11OperationTable OBJECT-TYPE
        SYNTAX      SEQUENCE OF Hpdot11OperationEntry
        ACCESS      not-accessible
       STATUS      mandatory
       DESCRIPTION "Table of descriptive and status information about
                    configuration of each radio of the AP."
       ::= { hpdot11mac 1 }

hpdot11OperationEntry OBJECT-TYPE
      SYNTAX      Hpdot11OperationEntry
      ACCESS        not-accessible
      STATUS      mandatory
      DESCRIPTION "An entry in the table, containing information
                   about configuration in one radio of the AP."
      INDEX       { hpdot11OperationIndex }
       ::= { hpdot11OperationTable 1 }
        
Hpdot11OperationEntry ::= SEQUENCE
{
   hpdot11OperationIndex                    Integer32,
   hpdot11RTSThreshold                      INTEGER,
   hpdot11FragmentationThreshold    INTEGER
}

hpdot11OperationIndex OBJECT-TYPE
        SYNTAX      Integer32
        ACCESS      not-accessible
        STATUS      mandatory
        DESCRIPTION "Radio index of the AP."
        ::= { hpdot11OperationEntry 1 }
        

hpdot11RTSThreshold OBJECT-TYPE
        SYNTAX INTEGER (0..2347)
        ACCESS read-write
        STATUS mandatory
        DESCRIPTION
            "This attribute shall indicate the number of octets in an MPDU,
            below which an RTS/CTS handshake shall not be performed. An
            RTS/CTS handshake shall be performed at the beginning of any
            frame exchange sequence where the MPDU is of type Data or
            Management, the MPDU has an individual address in the Address1
            field, and the length of the MPDU is greater than
            this threshold. (For additional details, refer to Table 21 in
            9.7.) Setting this attribute to be larger than the maximum
            MSDU size shall have the effect of turning off the RTS/CTS
            handshake for frames of Data or Management type transmitted by
            this STA. Setting this attribute to zero shall have the effect
            of turning on the RTS/CTS handshake for all frames of Data or
            Management type transmitted by this STA. The default value of
            this attribute shall be 2347."

    ::= { hpdot11OperationEntry 2 }

hpdot11FragmentationThreshold OBJECT-TYPE
        SYNTAX INTEGER (256..2346)
        ACCESS read-write
        STATUS mandatory
        DESCRIPTION
            "This attribute shall specify the mandatory maximum size, in
            octets, of the MPDU that may be delivered to the PHY. An MSDU
            shall be broken into fragments if its size exceeds the value
            of this attribute after adding MAC headers and trailers. An
            MSDU or MMPDU shall be fragmented when the resulting frame has
            an individual address in the Address1 field, and the length of
            the frame is larger than this threshold. The default value
            for this attribute shall be the lesser of 2346 or the
            aMPDUMaxLength of the attached PHY and shall never exceed the
            lesser of 2346 or the aMPDUMaxLength of the attached PHY. The
            value of this attribute shall never be less than 256."

    ::= { hpdot11OperationEntry 3 }


-- **********************************************************************
-- * End of dot11OperationTable TABLE
-- **********************************************************************

-- PHY Attributes

   hpdot11phy                       OBJECT IDENTIFIER ::= { enterpriseAPdot11 4 }

-- **********************************************************************
-- * dot11PhyOperationEntry TABLE
-- **********************************************************************
hpdot11PhyOperationTable OBJECT-TYPE
        SYNTAX      SEQUENCE OF Hpdot11PhyOperationEntry
        ACCESS      not-accessible
        STATUS      mandatory
        DESCRIPTION "Table of descriptive and status information about
                     configuration of each radio of the AP."
        ::= { hpdot11phy 1 }

hpdot11PhyOperationEntry OBJECT-TYPE
        SYNTAX      Hpdot11PhyOperationEntry
        ACCESS      not-accessible
        STATUS      mandatory
        DESCRIPTION "An entry in the table, containing information
                     about configuration in one radio of the AP."
        INDEX       { hpdot11Index }
        ::= { hpdot11PhyOperationTable 1 }

Hpdot11PhyOperationEntry ::= SEQUENCE
{
    hpdot11Index                            Integer32,
    hpdot11CurrentChannel                   INTEGER,
    hpdot11TurboModeEnabled             INTEGER,
    hpdot11PreambleLength                   INTEGER
}

hpdot11Index OBJECT-TYPE
        SYNTAX      Integer32
        ACCESS      not-accessible
        STATUS      mandatory
        DESCRIPTION "Radio index of the AP."
        ::= { hpdot11PhyOperationEntry 1 }

hpdot11CurrentChannel OBJECT-TYPE
        SYNTAX INTEGER
        ACCESS read-write
        STATUS mandatory
        DESCRIPTION
            "The current operating frequency channel of the network"

    ::= { hpdot11PhyOperationEntry 2 }


hpdot11TurboModeEnabled OBJECT-TYPE
        SYNTAX INTEGER
           {
            none(99),
            on(1),
            off(2)
           }
        ACCESS read-only
        STATUS mandatory
        DESCRIPTION
            "This attribute, when true, shall indicate that the 
            propietory turbo mode option is enabled. The default value of
            this attribute shall be false."

    ::= { hpdot11PhyOperationEntry 3 }


hpdot11PreambleLength OBJECT-TYPE
        SYNTAX INTEGER
            {
            short(1),
            long(2)
          }
        ACCESS read-write
        STATUS mandatory
        DESCRIPTION
            "This attribute determines whether or not a short or a long
            preamble is used to delineate 802.11 frames."

    ::= { hpdot11PhyOperationEntry 4 }

-- **********************************************************************
-- * End of dot11PhyOperationEntry TABLE
-- **********************************************************************

-- **********************************************************************
-- * dot11AuthenticationEntry TABLE
-- **********************************************************************
hpdot11AuthenticationEntry                      OBJECT IDENTIFIER ::= { enterpriseAPdot11 5 }

hpdot118021xSupport OBJECT-TYPE
        SYNTAX TruthValue
        ACCESS read-write
        STATUS mandatory
        DESCRIPTION
            "This attribute, when true(1), indicates that the Enterprise
            Access Point supports the 802.1x authentication algorithm."

    ::= { hpdot11AuthenticationEntry 1 }

hpdot118021xRequired OBJECT-TYPE
        SYNTAX TruthValue
        ACCESS read-write
        STATUS mandatory
        DESCRIPTION
            "This attribute, when true(1), indicates that the Enterprise
            Access Point requires successful 802.1x authentication              
            for any clients accessing the network."

    ::= { hpdot11AuthenticationEntry 2 }


-- **********************************************************************
-- * End of dot11Authentication TABLE
-- **********************************************************************

-- **********************************************************************
-- * dot11AuthenticationServer TABLE
-- **********************************************************************

hpdot11AuthenticationServerTable OBJECT-TYPE
        SYNTAX      SEQUENCE OF Hpdot11AuthenticationServerEntry
        ACCESS      not-accessible
        STATUS      mandatory
        DESCRIPTION "Table of descriptive and status information about
                     configuration of each authentication server."
        ::= { enterpriseAPdot11 6 }

hpdot11AuthenticationServerEntry OBJECT-TYPE
        SYNTAX      Hpdot11AuthenticationServerEntry
        ACCESS      not-accessible
        STATUS      mandatory
        DESCRIPTION "An entry in the table, containing information
                     about configuration in one radio of the AP."
        INDEX       { hpdot11serverIndex }
        ::= { hpdot11AuthenticationServerTable 1 }

Hpdot11AuthenticationServerEntry ::= SEQUENCE
{
    hpdot11serverIndex                      Integer32,
    hpdot11AuthenticationServer             IpAddress,
    hpdot11AuthenticationPort                   INTEGER,
    hpdot11AuthenticationKey                    DisplayString,
    hpdot11AuthenticationRetransmit         INTEGER,
    hpdot11AuthenticationTimeout                INTEGER
}

hpdot11serverIndex OBJECT-TYPE
        SYNTAX      Integer32
        ACCESS      not-accessible
        STATUS      mandatory
        DESCRIPTION "Radio index of the AP."
        ::= { hpdot11AuthenticationServerEntry 1 }


hpdot11AuthenticationServer OBJECT-TYPE
        SYNTAX IpAddress
        ACCESS read-write
        STATUS mandatory
        DESCRIPTION
            "This values indicates the IP address of the 
            authentication server."

    ::= { hpdot11AuthenticationServerEntry 2 }

hpdot11AuthenticationPort OBJECT-TYPE
        SYNTAX INTEGER (1024..65535)
        ACCESS read-write
        STATUS mandatory
        DESCRIPTION
            "This values indicates the UDP Port used by the primary
            authentication server."

    ::= { hpdot11AuthenticationServerEntry 3 }

hpdot11AuthenticationKey OBJECT-TYPE
        SYNTAX DisplayString (SIZE(0..20))
        ACCESS read-write
        STATUS mandatory
        DESCRIPTION
            "This values indicates the shared key used by the 
            authentication server."

    ::= { hpdot11AuthenticationServerEntry 4 }

hpdot11AuthenticationRetransmit OBJECT-TYPE
        SYNTAX INTEGER (1..30)
        ACCESS read-write
        STATUS mandatory
        DESCRIPTION
            "This values indicates the retransmit timer length used by the 
            authentication server."

    ::= { hpdot11AuthenticationServerEntry 5 }

hpdot11AuthenticationTimeout OBJECT-TYPE
        SYNTAX INTEGER (1..60)
        ACCESS read-write
        STATUS mandatory
        DESCRIPTION
            "This values indicates the Timeout value(sec) used by the 
            authentication server."

    ::= { hpdot11AuthenticationServerEntry 6 }


-- **********************************************************************
-- * End of dot11AuthenticationServer TABLE
-- **********************************************************************

-- **********************************************************************
-- * dot11FilteringTable TABLE
-- **********************************************************************

hpdot11FilterTable OBJECT-TYPE
        SYNTAX      SEQUENCE OF Hpdot11FilterEntry
        ACCESS      not-accessible
        STATUS      mandatory
        DESCRIPTION "Table of status information about
                     each configured MAC Address Filtering Entry."
        ::= { enterpriseAPdot11 7 }

hpdot11FilterEntry OBJECT-TYPE
        SYNTAX      Hpdot11FilterEntry
        ACCESS      not-accessible
        STATUS      mandatory
        DESCRIPTION "An entry in the table, containing information
                     about configuration in one radio of the AP."
        INDEX       { hpdot11FilterIndex }
        ::= { hpdot11FilterTable 1 }

Hpdot11FilterEntry ::= SEQUENCE
{
    hpdot11FilterIndex                        Integer32,
    hpdot11FilterAddress                      PhysAddress,
    hpdot11FilterStatus                       INTEGER
}

hpdot11FilterIndex OBJECT-TYPE
        SYNTAX      Integer32
        ACCESS      not-accessible
        STATUS      mandatory
        DESCRIPTION "Filter index."
        ::= { hpdot11FilterEntry 1 }


hpdot11FilterAddress OBJECT-TYPE
        SYNTAX PhysAddress
        ACCESS read-write
        STATUS mandatory
        DESCRIPTION
            "This values indicates the MAC address of the 
            filter entry."
    ::= { hpdot11FilterEntry 2 }

hpdot11FilterStatus OBJECT-TYPE
        SYNTAX INTEGER
                   {
                allowed(30),
                denied(31)
               }

        ACCESS read-write
        STATUS mandatory
        DESCRIPTION
            "This values indicates the Status of the filter entry.
             Ifallowed, the client is allowed access to the network.
             If disallowed, the no frames will be forwarded to the 
             network from the client."

    ::= { hpdot11FilterEntry 3 }
    
  hpdot11smt                    OBJECT IDENTIFIER ::= { enterpriseAPdot11 8 }

-- 
-- **********************************************************************
-- *    WEP Default Keys Table 11g
-- **********************************************************************
  hpdot11WEPDefaultKeys11g OBJECT IDENTIFIER ::= { hpdot11smt 1 }
  
        hpdot11WEPDefaultKeys11gTable OBJECT-TYPE
            SYNTAX SEQUENCE OF Hpdot11WEPDefaultKeys11gEntry
            MAX-ACCESS not-accessible
            STATUS mandatory
            DESCRIPTION
                "Conceptual table for WEP default keys.  This table shall
                contain the four WEP default secret key values
                corresponding to the four possible KeyID values.  The WEP
                default secret keys are logically WRITE-ONLY.  Attempts to
                read the entries in this table shall return unsuccessful
                status and values of null or zero.  The default value of
                each WEP default key shall be null."
            REFERENCE
                "IEEE Std 802.11-1997, 8.3.2"
            ::= { hpdot11WEPDefaultKeys11g 1 }
        
        hpdot11WEPDefaultKeys11gEntry OBJECT-TYPE
            SYNTAX Hpdot11WEPDefaultKeys11gEntry
            MAX-ACCESS not-accessible
            STATUS mandatory
            DESCRIPTION
                "An Entry (conceptual row) in the WEP Default Keys Table.
                
                ifIndex - Each 802.11 interface is represented by an
                ifEntry.  Interface tables in this MIB module are indexed
                by ifIndex."
            INDEX { dot11WEPDefaultKey11gLength }
            ::= { hpdot11WEPDefaultKeys11gTable 1 }
        
        Hpdot11WEPDefaultKeys11gEntry ::=
            SEQUENCE { 
                hpdot11WEPDefaultKey11gLength       INTEGER,
                hpdot11WEPDefaultKey11gIndex      INTEGER,
                hpdot11WEPDefaultKey11gValue      OCTET STRING
             }

        hpdot11WEPDefaultKey11gLength OBJECT-TYPE
            SYNTAX INTEGER
                {
                sixtyFour(64),
                oneHundredTwentyEight(128),
                oneHundredFiftyTwo(152)
                }
            MAX-ACCESS read-write
            STATUS mandatory
            DESCRIPTION
                "A 40(64)-bits [5 octets WEP], 104(128)-bits [13 octets] or 128(152)-bits [16 octets]"
            DEFVAL { oneHundredTwentyEight }
            ::= { hpdot11WEPDefaultKeys11gEntry 1 }
        
        hpdot11WEPDefaultKey11gIndex OBJECT-TYPE
            SYNTAX INTEGER (1..4)
            MAX-ACCESS not-accessible
            STATUS mandatory
            DESCRIPTION
                "The auxiliary variable used to identify instances
                of the columnar objects in the WEP Default Keys Table.
                The value of this variable is equal to the WEPDefaultKeyID + 1"
            ::= { hpdot11WEPDefaultKeys11gEntry 2 }
        
        
        hpdot11WEPDefaultKey11gValue OBJECT-TYPE
            SYNTAX OCTET STRING (SIZE (1..32))
            MAX-ACCESS read-write
            STATUS mandatory
            DESCRIPTION
                "A 40(64)-bits [5 octets WEP] or 104(128)-bits [13 octets] 
                 default secret key value."
            ::= { hpdot11WEPDefaultKeys11gEntry 3 }
            
END
