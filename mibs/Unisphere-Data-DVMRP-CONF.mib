-- *****************************************************************************
-- Unisphere-Data-DVMRP-CONF
--
-- SNMP Agent Capabilities definitions for the DVMRP MIBs.
--
-- Copyright (c) 2001 Unisphere Networks, Inc.  All rights reserved.
-- *****************************************************************************

Unisphere-Data-DVMRP-CONF DEFINITIONS ::= BEGIN

IMPORTS
    MODULE-IDENTITY
        FROM SNMPv2-SMI
    AGENT-CAPABILITIES
        FROM SNMPv2-CONF
    usDataAgents
        FROM Unisphere-Data-Agents
    uxdDvmrpGeneralGroup, uxdDvmrpInterfaceGroup, uxdDvmrpInterfaceLocalAddress,
    uxdDvmrpInterfaceMetric, uxdDvmrpInterfaceInterfaceKey,
    uxdDvmrpInterfaceInterfaceKeyVersion, uxdDvmrpNeighborGroup,
    uxdDvmrpRoutingGroup, uxdDvmrpSecurityGroup, uxdDvmrpTreeGroup
        FROM DVMRP-STD-MIB-UNI
    usdDvmrpBaseGroup, usdDvmrpAclDistNbrGroup, usdDvmrpInterfaceGroup,
    usdDvmrpSourceGroup
        FROM Unisphere-Data-DVMRP-MIB;

usdDvmrpAgent MODULE-IDENTITY
    LAST-UPDATED "200111302024Z"  -- 30-Nov-01 03:24 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the DVMRP component of the SNMP
        agent in the Unisphere Routing Switch family of products."
    -- Revision History
    REVISION    "200111302024Z"  -- 30-Nov-01 03:24 PM EST  - RX 3.2
    DESCRIPTION
        "The initial release of this management information module."
    ::= { usDataAgents 12 }

usdDvmrpAgentV1 AGENT-CAPABILITIES
    PRODUCT-RELEASE
        "Version 1 of the DVMRP component of the Unisphere Routing Switch SNMP
        agent.  This version of the DVMRP component is supported in the
        Unisphere RX 3.0 and subsequent system releases."
    STATUS      current
    DESCRIPTION
        "The MIBs supported by the SNMP agent for the DVMRP application in the
        Unisphere Routing Switch."
    SUPPORTS    DVMRP-STD-MIB-UNI
        INCLUDES  {
            uxdDvmrpGeneralGroup,
            uxdDvmrpInterfaceGroup,
            uxdDvmrpNeighborGroup,
            uxdDvmrpRoutingGroup,
            uxdDvmrpSecurityGroup,
            uxdDvmrpTreeGroup }
        VARIATION   uxdDvmrpInterfaceLocalAddress
            ACCESS      read-only
            DESCRIPTION
                "This object's value is assigned by the RX system.  Therefore,
                it must not be supplied when creating an interface and cannot be
                modified via SNMP.
                It is read as the IP address assigned to the interface or the IP
                address associated with the loopback interface for an unnumbered
                interface."
        VARIATION   uxdDvmrpInterfaceMetric
            DESCRIPTION
                "The RX system supports both a metric in and a metric out; this
                object is used to manage metric in; to manage metric out see
                Unisphere-Data-DVMRP-MIB.usdDvmrpInterfaceMetricOffsetOut."
        VARIATION   uxdDvmrpInterfaceInterfaceKey
            ACCESS      not-implemented
            DESCRIPTION
                "This object is not supported on the RX system.  Therefore, it
                must not be supplied when creating an interface."
        VARIATION   uxdDvmrpInterfaceInterfaceKeyVersion
            ACCESS      not-implemented
            DESCRIPTION
                "This object is not supported on the RX system.  Therefore, it
                must not be supplied when creating an interface."
    SUPPORTS    Unisphere-Data-DVMRP-MIB
        INCLUDES  {
            usdDvmrpBaseGroup,
            usdDvmrpAclDistNbrGroup,
            usdDvmrpInterfaceGroup,
            usdDvmrpSourceGroup }
    ::= { usdDvmrpAgent 1 }

END
