AISLCALIAS-MIB DEFINITIONS ::= BEGIN

IMPORTS
	MODULE-IDENTITY, OBJECT-TYPE, enterprises
			FROM SNMPv2-SMI
	TruthValue, RowStatus
			FROM SNMPv2-TC
	DisplayString
			FROM RFC1213-MIB;

	aii OBJECT IDENTIFIER ::= {enterprises 539}

aiSLCAlias MODULE-IDENTITY
	LAST-UPDATED "9909141600Z"
	ORGANIZATION "Applied Innovation Inc."
	CONTACT-INFO "Engineering MIB Administrator
		      Postal: Applied Innovation Inc.
		              5800 Innovation Drive
                              Dublin, Ohio 43017-3271

                      Tel:    614-798-2000
                      Fax:    614-798-1770
                      Email:  snmp@aiinet.com"
	DESCRIPTION "MIB module for SLCs with alias translation ability."
	::= {aii 22}

--=========================================================================

aiSLCAliasTable OBJECT-TYPE
	SYNTAX		SEQUENCE OF AISLCAliasEntry
        MAX-ACCESS	not-accessible
	STATUS		current
	DESCRIPTION
		"Table of aliases stored in the SLC, indexed by alias name.
		Rows are managed with the SNMPv2 RowStatus mechanism.
		All strings in this table may be up to 300 characters long,
		except the description, which may be up to 80."
	::= {aiSLCAlias 1}

aiSLCAliasEntry OBJECT-TYPE
	SYNTAX		AISLCAliasEntry
	MAX-ACCESS	not-accessible
	STATUS		current
	DESCRIPTION	"Entry of aiSLCAliasTable."
	INDEX		{IMPLIED aislcaliAliasName}
	::= {aiSLCAliasTable 1}

AISLCAliasEntry ::= SEQUENCE {
	aislcaliAliasName	DisplayString,
	aislcaliRowStatus	RowStatus,
	aislcaliDescription	DisplayString,
	aislcaliDestination	DisplayString,
	aislcaliShowInDestMenu	TruthValue,
	aislcaliCallingAddr	DisplayString,
	aislcaliCalledAddr	DisplayString,
	aislcaliCallData	DisplayString,
	aislcaliCallingProto	DisplayString,
	aislcaliCalledProto	DisplayString,
	aislcaliAppString	DisplayString,
	aislcaliAltRoute	DisplayString
}

aislcaliAliasName OBJECT-TYPE
	SYNTAX		DisplayString
	MAX-ACCESS	read-only
	STATUS		current
	DESCRIPTION	"Name of the alias to which this table row applies.
			Maximum length is 255 characters."
	::= {aiSLCAliasEntry 1}

aislcaliRowStatus OBJECT-TYPE
	SYNTAX		RowStatus
	MAX-ACCESS	read-create
	STATUS		current
	DESCRIPTION	"Status of this row, as defined by SNMPv2."
	DEFVAL      	{active}
	::= {aiSLCAliasEntry 2}

aislcaliDescription OBJECT-TYPE
	SYNTAX		DisplayString (SIZE (0..80))
	MAX-ACCESS	read-create
	STATUS		current
	DESCRIPTION	"Textual description of this alias.
			Maximum length is 80 characters."
	::= {aiSLCAliasEntry 3}

aislcaliDestination OBJECT-TYPE
	SYNTAX		DisplayString
	MAX-ACCESS	read-create
	STATUS		current
	DESCRIPTION	"Destination of this alias.
			Maximum length is 255 characters."
	::= {aiSLCAliasEntry 4}

aislcaliShowInDestMenu OBJECT-TYPE
	SYNTAX		TruthValue
	MAX-ACCESS	read-create
	STATUS		current
	DESCRIPTION	"Show this alias in the destination menu."
	::= {aiSLCAliasEntry 5}

aislcaliCallingAddr OBJECT-TYPE
	SYNTAX		DisplayString
	MAX-ACCESS	read-create
	STATUS		current
	DESCRIPTION	"Address of the entity calling this alias.
			Maximum length is 255 characters."
	::= {aiSLCAliasEntry 6}

aislcaliCalledAddr OBJECT-TYPE
	SYNTAX		DisplayString
	MAX-ACCESS	read-create
	STATUS		current
	DESCRIPTION	"Address called by this alias.
			Maximum length is 255 characters."
	::= {aiSLCAliasEntry 7}

aislcaliCallData OBJECT-TYPE
	SYNTAX		DisplayString
	MAX-ACCESS	read-create
	STATUS		current
	DESCRIPTION	"String used for SLC-dependent features.
			Maximum length is 255 characters."
	::= {aiSLCAliasEntry 8}

aislcaliCallingProto OBJECT-TYPE
	SYNTAX		DisplayString
	MAX-ACCESS	read-create
	STATUS		current
	DESCRIPTION	"Protocol used by the entity calling this alias.
			Maximum length is 255 characters."
	::= {aiSLCAliasEntry 9}

aislcaliCalledProto OBJECT-TYPE
	SYNTAX		DisplayString
	MAX-ACCESS	read-create
	STATUS		current
	DESCRIPTION	"Protocol used for a call placed by this alias.
			Maximum length is 255 characters."
	::= {aiSLCAliasEntry 10}

aislcaliAppString OBJECT-TYPE
	SYNTAX		DisplayString
	MAX-ACCESS	read-create
	STATUS		current
	DESCRIPTION	"String used for SLC-dependent features.
			Maximum length is 255 characters."
	::= {aiSLCAliasEntry 11}

aislcaliAltRoute OBJECT-TYPE
	SYNTAX		DisplayString
	MAX-ACCESS	read-create
	STATUS		current
	DESCRIPTION	"Name of an alternative alias the SLC can use.
			Maximum length is 255 characters."
	::= {aiSLCAliasEntry 12}

--=========================================================================

END
