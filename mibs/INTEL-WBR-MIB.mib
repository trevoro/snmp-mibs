INTEL-WBR-MIB DEFINITIONS ::= BEGIN

-- Copyright (C) 1997 Intel Corporation. All rights reserved.
--
-- WAN Bridging MIB, 02-05-1997
--
-- This mib is a proprietary extension to the RFC 1493 Bridge MIB.
--
-- Change History:
-- 97-05-02 Initial version
-- 97-04-06 Spelling errors, descriptions & enums corrected
-- 97-04-10 added counters for Total
--

IMPORTS
        Counter, TimeTicks      FROM RFC1155-SMI
        mib2ext                 FROM INTEL-GEN-MIB
        OBJECT-TYPE             FROM RFC-1212;

wbr                     OBJECT IDENTIFIER ::= { mib2ext 25 }
wbrBase                 OBJECT IDENTIFIER ::= { wbr 1 }
wbrStp                  OBJECT IDENTIFIER ::= { wbr 2 }
wbrTp                   OBJECT IDENTIFIER ::= { wbr 3 }

wbrBaseLastConfigTime OBJECT-TYPE
    SYNTAX TimeTicks
    ACCESS read-only
    STATUS mandatory
    DESCRIPTION "Time of last change in bridge configuration"
    ::= { wbrBase 1 }

wbrBaseBridging OBJECT-TYPE
    SYNTAX INTEGER { disabled(1), enabled(2) }
    ACCESS read-only
    STATUS mandatory
    DESCRIPTION "Is Bridging (except of IP/IPX) enabled - 'Enabled' or 'Disabled'"
    ::= { wbrBase 2 }

wbrBaseBridgingIP OBJECT-TYPE
    SYNTAX INTEGER { disabled(1), enabled(2) }
    ACCESS read-only
    STATUS mandatory
    DESCRIPTION "Is Bridging of IP traffic Enabled - 'Enabled' or 'Disabled'"
    ::= { wbrBase 3 }

wbrBaseBridgingIPX OBJECT-TYPE
    SYNTAX INTEGER { disabled(1), enabled(2) }
    ACCESS read-only
    STATUS mandatory
    DESCRIPTION "Is Bridging of IPX traffic Enabled - 'Enabled' or 'Disabled'"
    ::= { wbrBase 4 }

wbrStpBridgeAgeingTime OBJECT-TYPE
    SYNTAX INTEGER
    ACCESS read-only
    STATUS mandatory
    DESCRIPTION "The Ageing Time configured for this Bridge"
    ::= { wbrStp 1 }

wbrStpBridgeIsRoot OBJECT-TYPE
    SYNTAX INTEGER { no(1), yes(2) }
    ACCESS read-only
    STATUS mandatory
    DESCRIPTION "Is this Bridge the Root Bridge - 'Yes' or 'No'"
    ::= { wbrStp 2 }

wbrStpRxBPDUs OBJECT-TYPE
    SYNTAX Counter
    ACCESS read-only
    STATUS mandatory
    DESCRIPTION "Total number of BPDUs packets received"
    ::= { wbrStp 3 }

wbrStpTxBPDUs OBJECT-TYPE
    SYNTAX Counter
    ACCESS read-only
    STATUS mandatory
    DESCRIPTION "Total number of BPDUs packets transmitted"
    ::= { wbrStp 4 }

wbrStpTxBPDUsFailed OBJECT-TYPE
    SYNTAX Counter
    ACCESS read-only
    STATUS mandatory
    DESCRIPTION "Total number of BPDUs packets unsuccessfully transmitted"
    ::= { wbrStp 5 }

wbrStpRxSpoofBPDUs OBJECT-TYPE
    SYNTAX Counter
    ACCESS read-only
    STATUS mandatory
    DESCRIPTION "Total number of BPDUs packets spoofed instead of received"
    ::= { wbrStp 6 }

wbrStpTxSpoofBPDUs OBJECT-TYPE
    SYNTAX Counter
    ACCESS read-only
    STATUS mandatory
    DESCRIPTION "Total number of BPDUs packets spoofed instead of transmitted"
    ::= { wbrStp 7 }

wbrStpTxSpoofFailed OBJECT-TYPE
    SYNTAX Counter
    ACCESS read-only
    STATUS mandatory
    DESCRIPTION "Total number of spoofing protocol packets unsuccessfully
                 transmitted"
    ::= { wbrStp 8 }

wbrStpTxSpoofData OBJECT-TYPE
    SYNTAX Counter
    ACCESS read-only
    STATUS mandatory
    DESCRIPTION "Total number of packets spoofed instead of transmitted"
    ::= { wbrStp 9 }

wbrStpLinkTable OBJECT-TYPE
    SYNTAX SEQUENCE OF WbrStpLinkEntry
    ACCESS not-accessible
    STATUS mandatory
    DESCRIPTION "A table that contains port-specific information
                 for the Spanning Tree Protocol."
    ::= { wbrStp 10 }

wbrStpLinkEntry OBJECT-TYPE
    SYNTAX WbrStpLinkEntry
    ACCESS not-accessible
    STATUS mandatory
    DESCRIPTION ""
    INDEX { wbrStpLinkIfIndex }
    ::= { wbrStpLinkTable 1 }

WbrStpLinkEntry ::= SEQUENCE {
                        wbrStpLinkIfIndex
                           INTEGER,
                        wbrStpLinkRxProtocolBytes
                           Counter,
                        wbrStpLinkTxProtocolBytes
                           Counter,
                        wbrStpLinkRxBPDUs
                           Counter,
                        wbrStpLinkTxBPDUs
                           Counter,
                        wbrStpLinkTxBPDUsFailed
                           Counter,
                        wbrStpLinkRxSpoofBPDUs
                           Counter,
                        wbrStpLinkTxSpoofBPDUs
                           Counter,
                        wbrStpLinkTxSpoofFailed
                           Counter,
                        wbrStpLinkTxSpoofData
                           Counter,
                        wbrStpLinkSPTStatus
                           OCTET STRING,
                        wbrStpLinkConfigBPDUPending
                           INTEGER,
                        wbrStpLinkTopologyChangeAck
                           INTEGER,
                        wbrStpLinkConfigBPDUAgeActive
                           INTEGER,
                        wbrStpLinkConfigBPDUAge
                           INTEGER,
                        wbrStpLinkBPDUSpoofing
                           OCTET STRING,
                        wbrStpLinkNonBPDUSpoofing
                           OCTET STRING,
                        wbrStpLinkSpoofing
                           INTEGER
                        }

wbrStpLinkIfIndex OBJECT-TYPE
    SYNTAX INTEGER
    ACCESS read-only
    STATUS mandatory
    DESCRIPTION "Link Index"
    ::= { wbrStpLinkEntry 1 }

wbrStpLinkRxProtocolBytes OBJECT-TYPE
    SYNTAX Counter
    ACCESS read-only
    STATUS mandatory
    DESCRIPTION "BPDUs bytes received"
    ::= { wbrStpLinkEntry 2 }

wbrStpLinkTxProtocolBytes OBJECT-TYPE
    SYNTAX Counter
    ACCESS read-only
    STATUS mandatory
    DESCRIPTION "BPDU bytes transmitted"
    ::= { wbrStpLinkEntry 3 }

wbrStpLinkRxBPDUs OBJECT-TYPE
    SYNTAX Counter
    ACCESS read-only
    STATUS mandatory
    DESCRIPTION "Number of BPDUs packets received"
    ::= { wbrStpLinkEntry 4 }

wbrStpLinkTxBPDUs OBJECT-TYPE
    SYNTAX Counter
    ACCESS read-only
    STATUS mandatory
    DESCRIPTION "Number of BPDUs packets transmitted"
    ::= { wbrStpLinkEntry 5 }

wbrStpLinkTxBPDUsFailed OBJECT-TYPE
    SYNTAX Counter
    ACCESS read-only
    STATUS mandatory
    DESCRIPTION "Number of BPDUs packets unsuccessfully transmitted
                 from the link"
    ::= { wbrStpLinkEntry 6 }

wbrStpLinkRxSpoofBPDUs OBJECT-TYPE
    SYNTAX Counter
    ACCESS read-only
    STATUS mandatory
    DESCRIPTION "Number of BPDUs packets spoofed instead of received on link"
    ::= { wbrStpLinkEntry 7 }

wbrStpLinkTxSpoofBPDUs OBJECT-TYPE
    SYNTAX Counter
    ACCESS read-only
    STATUS mandatory
    DESCRIPTION "Number of BPDUs packets spoofed instead of transmitted on link"
    ::= { wbrStpLinkEntry 8 }

wbrStpLinkTxSpoofFailed OBJECT-TYPE
    SYNTAX Counter
    ACCESS read-only
    STATUS mandatory
    DESCRIPTION "Number of spoofing protocol packets unsuccessfully
                 transmitted from the link"
    ::= { wbrStpLinkEntry 9 }

wbrStpLinkTxSpoofData OBJECT-TYPE
    SYNTAX Counter
    ACCESS read-only
    STATUS mandatory
    DESCRIPTION "Number of packets spoofed instead of transmitted on link"
    ::= { wbrStpLinkEntry 10 }

wbrStpLinkSPTStatus OBJECT-TYPE
    SYNTAX OCTET STRING (SIZE(30))
    ACCESS read-only
    STATUS mandatory
    DESCRIPTION "Status for Spanning Tree Link"
    ::= { wbrStpLinkEntry 11 }

wbrStpLinkConfigBPDUPending OBJECT-TYPE
    SYNTAX INTEGER { no(1), yes(2) }
    ACCESS read-only
    STATUS mandatory
    DESCRIPTION "Whether a Configuration BPDU packet is to
                 be forwarded to the Bridges on the Designated
                 ports (via Configuration BPDUs) - 'Yes' or 'No'"
    ::= { wbrStpLinkEntry 12 }

wbrStpLinkTopologyChangeAck OBJECT-TYPE
    SYNTAX INTEGER { no(1), yes(2) }
    ACCESS read-only
    STATUS mandatory
    DESCRIPTION "Determines if the configuration change is
                 to be forwarded to the Bridges on the Designated
                 Ports (via Configuration BPDUs) - 'Yes' or 'No'"
    ::= { wbrStpLinkEntry 13 }

wbrStpLinkConfigBPDUAgeActive OBJECT-TYPE
    SYNTAX INTEGER { no(1), yes(2) }
    ACCESS read-only
    STATUS mandatory
    DESCRIPTION "Whether ConfigBPDUAge is active/valid for
                 monitoring. If not active then ConfigBPDUAge is undefined
                 i.e. 'Not Active'"
    ::= { wbrStpLinkEntry 14 }

wbrStpLinkConfigBPDUAge OBJECT-TYPE
    SYNTAX INTEGER
    ACCESS read-only
    STATUS mandatory
    DESCRIPTION "The age of the information within the last
                 Configuration BPDU packet received from the
                 Designated Bridge"
    ::= { wbrStpLinkEntry 15 }

wbrStpLinkBPDUSpoofing OBJECT-TYPE
    SYNTAX OCTET STRING (SIZE(14))
    ACCESS read-only
    STATUS mandatory
    DESCRIPTION "Whether Configuration BPDU packets are
                 spoofed - 'Yes' or 'Not Active'"
    ::= { wbrStpLinkEntry 16 }

wbrStpLinkNonBPDUSpoofing OBJECT-TYPE
    SYNTAX OCTET STRING (SIZE(14))
    ACCESS read-only
    STATUS mandatory
    DESCRIPTION "Whether Non-BPDU packets are spoofed -
                  'Yes' or 'Not Active'"
    ::= { wbrStpLinkEntry 17 }

wbrStpLinkSpoofing OBJECT-TYPE
    SYNTAX INTEGER { disabled(1), enabled(2) }
    ACCESS read-only
    STATUS mandatory
    DESCRIPTION "If Spoofing is enabled in Setup"
    ::= { wbrStpLinkEntry 18 }

wbrTpRxPackets OBJECT-TYPE
    SYNTAX Counter
    ACCESS read-only
    STATUS mandatory
    DESCRIPTION "Total number of bridged packets
                 (non BPDU packets) received"
    ::= { wbrTp 1 }

wbrTpTxPackets OBJECT-TYPE
    SYNTAX Counter
    ACCESS read-only
    STATUS mandatory
    DESCRIPTION "Total number of bridged packets
                 (non BPDU packets) transmitted"
    ::= { wbrTp 2 }

wbrTpTxFailed OBJECT-TYPE
    SYNTAX Counter
    ACCESS read-only
    STATUS mandatory
    DESCRIPTION "Total number of packets that the
                 router failed to transmit"
    ::= { wbrTp 3 }

wbrTpRxRejUnknown OBJECT-TYPE
    SYNTAX Counter
    ACCESS read-only
    STATUS mandatory
    DESCRIPTION "Total number of unknown Unicast packets
                 received which were discarded due to exceeding
                 the maximum number of unknown Unicast packets
                 (5 within 5 seconds for the entire Bridge)"
    ::= { wbrTp 4 }

wbrTpRxRejTotal OBJECT-TYPE
    SYNTAX Counter
    ACCESS read-only
    STATUS mandatory
    DESCRIPTION "Total number of valid frames received
                 which were rejected (i.e., filtered)
                 by the Forwarding Process"
    ::= { wbrTp 5 }

wbrTpRxInvalid OBJECT-TYPE
    SYNTAX Counter
    ACCESS read-only
    STATUS mandatory
    DESCRIPTION "Total number of erroneous packets received"
    ::= { wbrTp 6 }

wbrTpRejUnicast OBJECT-TYPE
    SYNTAX Counter
    ACCESS read-only
    STATUS mandatory
    DESCRIPTION "Total number of packets received
                 which were rejected by the Unicast Destination
                 Forwarding Table"
    ::= { wbrTp 7 }

wbrTpRejDefaultUnicast OBJECT-TYPE
    SYNTAX Counter
    ACCESS read-only
    STATUS mandatory
    DESCRIPTION "Total number of packets received
                 which were rejected by the Default Action of the
                 Unicast Destination Forwarding Table"
    ::= { wbrTp 8 }

wbrTpRejMulticast OBJECT-TYPE
    SYNTAX Counter
    ACCESS read-only
    STATUS mandatory
    DESCRIPTION "Total number of packets received
                 which were rejected by the Multicast Destination
                 Forwarding Table"
    ::= { wbrTp 9 }

wbrTpRejDefaultMulticast OBJECT-TYPE
    SYNTAX Counter
    ACCESS read-only
    STATUS mandatory
    DESCRIPTION "Total number of packets received
                 which were rejected by the Default Action of
                 the Multicast Destination Forwarding Table"
    ::= { wbrTp 10 }

wbrTpRejSource OBJECT-TYPE
    SYNTAX Counter
    ACCESS read-only
    STATUS mandatory
    DESCRIPTION "Total number of packets received
                 which were rejected by the Source Forwarding Table"
    ::= { wbrTp 11 }

wbrTpRejDefaultSource OBJECT-TYPE
    SYNTAX Counter
    ACCESS read-only
    STATUS mandatory
    DESCRIPTION "Total number of packets received
                 which were rejected by the Default Action of the
                 Source Forwarding Table"
    ::= { wbrTp 12 }

wbrTpRejType OBJECT-TYPE
    SYNTAX Counter
    ACCESS read-only
    STATUS mandatory
    DESCRIPTION "Total number of packets received
                 which were rejected by the Type Forwarding Table"
    ::= { wbrTp 13 }

wbrTpRejDefaultType OBJECT-TYPE
    SYNTAX Counter
    ACCESS read-only
    STATUS mandatory
    DESCRIPTION "Total number of packets received
                 which were rejected by the Default Action of the
                 Type Forwarding Table"
    ::= { wbrTp 14 }

wbrTpLinkTable OBJECT-TYPE
    SYNTAX SEQUENCE OF WbrTpLinkEntry
    ACCESS not-accessible
    STATUS mandatory
    DESCRIPTION "A table that contains information about every
                 port that is associated with this transparent
                 bridge."
    ::= { wbrTp 15 }

wbrTpLinkEntry OBJECT-TYPE
    SYNTAX WbrTpLinkEntry
    ACCESS not-accessible
    STATUS mandatory
    DESCRIPTION ""
    INDEX { wbrTpLinkIfIndex }
    ::= { wbrTpLinkTable 1 }

WbrTpLinkEntry ::= SEQUENCE {
                        wbrTpLinkIfIndex
                           INTEGER,
                        wbrTpLinkRxOtherBytes
                           Counter,
                        wbrTpLinkTxOtherBytes
                           Counter,
                        wbrTpLinkRxRejectedBytes
                           Counter,
                        wbrTpLinkTxRejectedBytes
                           Counter,
                        wbrTpLinkRxRejUnknown
                           Counter,
                        wbrTpLinkRxInvalid
                           Counter,
                        wbrTpLinkTxFailed
                           Counter,
                        wbrTpLinkRxRejUnicast
                           Counter,
                        wbrTpLinkRxRejMulticast
                           Counter,
                        wbrTpLinkRxRejSource
                           Counter,
                        wbrTpLinkRxRejType
                           Counter,
                        wbrTpLinkRxRejDefaultUnicast
                           Counter,
                        wbrTpLinkRxRejDefaultMulticast
                           Counter,
                        wbrTpLinkRxRejDefaultSource
                           Counter,
                        wbrTpLinkRxRejDefaultType
                           Counter
                        }

wbrTpLinkIfIndex OBJECT-TYPE
    SYNTAX INTEGER
    ACCESS read-only
    STATUS mandatory
    DESCRIPTION "Link Index"
    ::= { wbrTpLinkEntry 1 }

wbrTpLinkRxOtherBytes OBJECT-TYPE
    SYNTAX Counter
    ACCESS read-only
    STATUS mandatory
    DESCRIPTION "Non-BPDU bytes received"
    ::= { wbrTpLinkEntry 2 }

wbrTpLinkTxOtherBytes OBJECT-TYPE
    SYNTAX Counter
    ACCESS read-only
    STATUS mandatory
    DESCRIPTION "Non-BPDU bytes transmitted"
    ::= { wbrTpLinkEntry 3 }

wbrTpLinkRxRejectedBytes OBJECT-TYPE
    SYNTAX Counter
    ACCESS read-only
    STATUS mandatory
    DESCRIPTION "Number of non-BPDU bytes received on this
                 link which were rejected"
    ::= { wbrTpLinkEntry 4 }

wbrTpLinkTxRejectedBytes OBJECT-TYPE
    SYNTAX Counter
    ACCESS read-only
    STATUS mandatory
    DESCRIPTION "Number of non-BPDU bytes to be transmitted
                 on this link which were rejected"
    ::= { wbrTpLinkEntry 5 }

wbrTpLinkRxRejUnknown OBJECT-TYPE
    SYNTAX Counter
    ACCESS read-only
    STATUS mandatory
    DESCRIPTION "Number of unknown Unicast packets received
                 on the link which were discarded due to exceeding
                 the maximum number of unknown Unicast packets
                 (5 within 5 seconds for the entire Bridge)"
    ::= { wbrTpLinkEntry 6 }

wbrTpLinkRxInvalid OBJECT-TYPE
    SYNTAX Counter
    ACCESS read-only
    STATUS mandatory
    DESCRIPTION "Number of erroneous packets received"
    ::= { wbrTpLinkEntry 7 }

wbrTpLinkTxFailed OBJECT-TYPE
    SYNTAX Counter
    ACCESS read-only
    STATUS mandatory
    DESCRIPTION "Number of non-BPDU packets unsuccessfully
                 transmitted from the link"
    ::= { wbrTpLinkEntry 8 }

wbrTpLinkRxRejUnicast OBJECT-TYPE
    SYNTAX Counter
    ACCESS read-only
    STATUS mandatory
    DESCRIPTION "Number of packets received on this link
                 which were rejected by the Unicast Destination
                 Forwarding Table"
    ::= { wbrTpLinkEntry 9 }

wbrTpLinkRxRejMulticast OBJECT-TYPE
    SYNTAX Counter
    ACCESS read-only
    STATUS mandatory
    DESCRIPTION "Number of packets received on this link
                 which were rejected by the Multicast Destination
                 Forwarding Table"
    ::= { wbrTpLinkEntry 10 }

wbrTpLinkRxRejSource OBJECT-TYPE
    SYNTAX Counter
    ACCESS read-only
    STATUS mandatory
    DESCRIPTION "Number of packets received on this link which
                 were rejected by the Source Forwarding Table"
    ::= { wbrTpLinkEntry 11 }

wbrTpLinkRxRejType OBJECT-TYPE
    SYNTAX Counter
    ACCESS read-only
    STATUS mandatory
    DESCRIPTION "Number of packets received on this link which
                 were rejected by the Type Forwarding Table"
    ::= { wbrTpLinkEntry 12 }

wbrTpLinkRxRejDefaultUnicast OBJECT-TYPE
    SYNTAX Counter
    ACCESS read-only
    STATUS mandatory
    DESCRIPTION "Number of packets received on this link
                 which were rejected by the Default Action of the
                 Unicast Destination Forwarding Table"
    ::= { wbrTpLinkEntry 13 }

wbrTpLinkRxRejDefaultMulticast OBJECT-TYPE
    SYNTAX Counter
    ACCESS read-only
    STATUS mandatory
    DESCRIPTION "Number of packets received on this link
                 which were rejected by the Default Action of
                 the Multicast Destination Forwarding Table"
    ::= { wbrTpLinkEntry 14 }

wbrTpLinkRxRejDefaultSource OBJECT-TYPE
    SYNTAX Counter
    ACCESS read-only
    STATUS mandatory
    DESCRIPTION "Number of packets received on this link
                 which were rejected by the Default Action of the
                 Source Forwarding Table"
    ::= { wbrTpLinkEntry 15 }

wbrTpLinkRxRejDefaultType OBJECT-TYPE
    SYNTAX Counter
    ACCESS read-only
    STATUS mandatory
    DESCRIPTION "Number of packets received on this link
                 which were rejected by the Default Action of the
                 Type Forwarding Table"
    ::= { wbrTpLinkEntry 16 }

END
