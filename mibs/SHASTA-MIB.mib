-- $Id: SHASTA-MIB.my,v 1.2.34.1.2.1 2000/05/26 01:54:39 stevea Exp $
SHASTA-MIB DEFINITIONS ::= BEGIN

IMPORTS
	enterprises
		FROM RFC1155-SMI
	OBJECT-IDENTITY, MODULE-IDENTITY, OBJECT-TYPE, NOTIFICATION-TYPE,
	ObjectName, Integer32, Counter32, snmpModules
                  FROM SNMPv2-SMI
	TruthValue, DisplayString, TestAndIncr, TimeStamp
                  FROM SNMPv2-TC
	MODULE-COMPLIANCE, OBJECT-GROUP
                  FROM SNMPv2-CONF;

shasta MODULE-IDENTITY
        LAST-UPDATED "9907140000Z"
	ORGANIZATION	"Nortel Networks
			 Shasta IP Services Business Unit"
	CONTACT-INFO	"
			 Nortel Networks
			 Shasta IP Services Business Unit
			 Customer Service

		 Postal: 2305 Mission College Boulevard
		 	 Mailstop SC9-C1200
                         Santa Clara, CA 94054
                         USA
 
                 Tel: +1 408 855-3800

		 E-mail: support@shastanets.com"

        DESCRIPTION
                "The Structure of Management Information for the
                 Shasta Networks enterprise."
        REVISION      "9901100000Z"
        DESCRIPTION
                "Initial version of this MIB module."
        ::= { enterprises 3199 }   -- assigned by IANA

shastaMgmt OBJECT-IDENTITY
        STATUS  current
        DESCRIPTION
                "shastaMgmt is the main subtree for new mib development."
        ::= { shasta 1 }

shastaExperiment OBJECT-IDENTITY
        STATUS  current
        DESCRIPTION
                "shastaExperiment provides a root object identifier
                from which experimental MIBs may be temporarily
                based.  MIBs are typicially based here if they
                fall in one of two categories
                1) are IETF work-in-process MIBs which have not
                been assigned a permanent object identifier by
                the IANA.
                2) are shasta work-in-process which has not been
                assigned a permanent object identifier by the
                shasat assigned number authority, typicially because
                the mib is not ready for deployment.
 
                NOTE WELL:  support for MIBs in the shastaExperiment
                subtree will be deleted when a permanent object
                identifier assignment is made."
        ::= { shasta 10 }
END
