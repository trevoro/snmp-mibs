Nortel-Magellan-Passport-IpCosMIB
DEFINITIONS ::= BEGIN



IMPORTS

      OBJECT-TYPE
   FROM RFC-1212

      IpAddress
   FROM RFC1155-SMI

      passportMIBs
   FROM Nortel-Magellan-Passport-UsefulDefinitionsMIB

      DisplayString,
      StorageType,
      RowStatus,
      Integer32,
      Unsigned32
   FROM Nortel-Magellan-Passport-StandardTextualConventionsMIB

      Hex,
      NonReplicated,
      Link,
      AsciiStringIndex
   FROM Nortel-Magellan-Passport-TextualConventionsMIB

      vrIpIndex,
      vrIp
   FROM Nortel-Magellan-Passport-IpMIB

      vrIndex
   FROM Nortel-Magellan-Passport-VirtualRouterMIB;




-- LAST-UPDATED   "0003280000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     IpCos Enterprise MIB."

ipCosMIB OBJECT IDENTIFIER ::= { passportMIBs 162 }










-- Vr/<string> Ip CosPolicyGroup/<string>
-- The CosPolicyGroup component represents a set of policies, which 
-- may be associated with a specific IpPort or may be used as the 
-- default policy of the Virtual Router.
-- 
-- The instance value is represented by an arbitrary text string of at 
-- most 20 characters. The intention is to allow the operator to assign a 
-- meaningful name for easier reference.

vrIpPg OBJECT IDENTIFIER ::= { vrIp 20 }



vrIpPgRowStatusTable OBJECT-TYPE
   SYNTAX     SEQUENCE OF VrIpPgRowStatusEntry
   ACCESS     not-accessible
   STATUS     mandatory
   DESCRIPTION
     "This entry controls the addition and deletion of 
      vrIpPg components."
::= { vrIpPg 1 }

vrIpPgRowStatusEntry OBJECT-TYPE
   SYNTAX     VrIpPgRowStatusEntry
   ACCESS     not-accessible
   STATUS     mandatory
   DESCRIPTION
     "A single entry in the table represents a single 
      vrIpPg component."
   INDEX {
      vrIndex,
      vrIpIndex,
      vrIpPgIndex }
::= { vrIpPgRowStatusTable 1 }

VrIpPgRowStatusEntry ::= SEQUENCE {
   vrIpPgRowStatus
      RowStatus,
   vrIpPgComponentName
      DisplayString,
   vrIpPgStorageType
      StorageType,
   vrIpPgIndex
      AsciiStringIndex }

vrIpPgRowStatus OBJECT-TYPE
   SYNTAX     RowStatus 
   ACCESS     read-write
   STATUS     mandatory
   DESCRIPTION
     "This variable is used as the basis for SNMP naming of
      vrIpPg components.
      These components can be added and deleted."
::= { vrIpPgRowStatusEntry 1 }

vrIpPgComponentName OBJECT-TYPE
   SYNTAX     DisplayString 
   ACCESS     read-only
   STATUS     mandatory
   DESCRIPTION
     "This variable provides the component's string name for
      use with the ASCII Console Interface"
::= { vrIpPgRowStatusEntry 2 }

vrIpPgStorageType OBJECT-TYPE
   SYNTAX     StorageType 
   ACCESS     read-only
   STATUS     mandatory
   DESCRIPTION
     "This variable represents the storage type value for the
      vrIpPg tables."
::= { vrIpPgRowStatusEntry 4 }

vrIpPgIndex OBJECT-TYPE
   SYNTAX     AsciiStringIndex (SIZE (1..20))
   ACCESS     not-accessible
   STATUS     mandatory
   DESCRIPTION
     "This variable represents the index for the vrIpPg tables."
::= { vrIpPgRowStatusEntry 10 }

vrIpPgUsersTable OBJECT-TYPE
   SYNTAX     SEQUENCE OF VrIpPgUsersEntry
   ACCESS     not-accessible
   STATUS     mandatory
   DESCRIPTION
     "This attribute specifies a list of components that are using this 
      CosPolicyGroup."
::= { vrIpPg 432 }

vrIpPgUsersEntry OBJECT-TYPE
   SYNTAX     VrIpPgUsersEntry
   ACCESS     not-accessible
   STATUS     mandatory
   DESCRIPTION
     "An entry in the vrIpPgUsersTable."
   INDEX {
      vrIndex,
      vrIpIndex,
      vrIpPgIndex,
      vrIpPgUsersValue }
::= { vrIpPgUsersTable 1 }

VrIpPgUsersEntry ::= SEQUENCE {
   vrIpPgUsersValue
      Link,
   vrIpPgUsersRowStatus
      RowStatus }

vrIpPgUsersValue OBJECT-TYPE
   SYNTAX     Link 
   ACCESS     read-write
   STATUS     mandatory
   DESCRIPTION
     "This variable represents both the value and the index for the
      vrIpPgUsersTable."
::= { vrIpPgUsersEntry 1 }

vrIpPgUsersRowStatus OBJECT-TYPE
   SYNTAX     RowStatus 
   ACCESS     write-only
   STATUS     mandatory
   DESCRIPTION
     "This variable is used to control the addition and deletion 
      of individual values of the vrIpPgUsersTable."
::= { vrIpPgUsersEntry 2 }


-- Vr/<string> Ip Pg/<string> Policy/<string>
-- The Policy component defines a policy to be applied on a per virtual 
-- router or per IpPort basis. A policy is defined by two sets of 
-- parameters:
-- 
-- 1. The criteria specifying when the policy is to be applied. These 
-- criteria are defined by the Policy subcomponents: TosMap  and 
-- IpAddrLayer4Flow.
-- 
-- 2. The actions or results when the policy is applied. These actions 
-- or results are defined as subcomponents of CosPolicyGroup, and 
-- are referenced by attributes under the Policy component. Currently 
-- the CosTreatment component is the only component of this type.
-- 
-- The instance value is represented by an arbitrary text string of at 
-- most 20 characters. The intention is to allow operator to assign 
-- meaningful name for easier reference.

vrIpPgPolicy OBJECT IDENTIFIER ::= { vrIpPg 2 }



vrIpPgPolicyRowStatusTable OBJECT-TYPE
   SYNTAX     SEQUENCE OF VrIpPgPolicyRowStatusEntry
   ACCESS     not-accessible
   STATUS     mandatory
   DESCRIPTION
     "This entry controls the addition and deletion of 
      vrIpPgPolicy components."
::= { vrIpPgPolicy 1 }

vrIpPgPolicyRowStatusEntry OBJECT-TYPE
   SYNTAX     VrIpPgPolicyRowStatusEntry
   ACCESS     not-accessible
   STATUS     mandatory
   DESCRIPTION
     "A single entry in the table represents a single 
      vrIpPgPolicy component."
   INDEX {
      vrIndex,
      vrIpIndex,
      vrIpPgIndex,
      vrIpPgPolicyIndex }
::= { vrIpPgPolicyRowStatusTable 1 }

VrIpPgPolicyRowStatusEntry ::= SEQUENCE {
   vrIpPgPolicyRowStatus
      RowStatus,
   vrIpPgPolicyComponentName
      DisplayString,
   vrIpPgPolicyStorageType
      StorageType,
   vrIpPgPolicyIndex
      AsciiStringIndex }

vrIpPgPolicyRowStatus OBJECT-TYPE
   SYNTAX     RowStatus 
   ACCESS     read-write
   STATUS     mandatory
   DESCRIPTION
     "This variable is used as the basis for SNMP naming of
      vrIpPgPolicy components.
      These components can be added and deleted."
::= { vrIpPgPolicyRowStatusEntry 1 }

vrIpPgPolicyComponentName OBJECT-TYPE
   SYNTAX     DisplayString 
   ACCESS     read-only
   STATUS     mandatory
   DESCRIPTION
     "This variable provides the component's string name for
      use with the ASCII Console Interface"
::= { vrIpPgPolicyRowStatusEntry 2 }

vrIpPgPolicyStorageType OBJECT-TYPE
   SYNTAX     StorageType 
   ACCESS     read-only
   STATUS     mandatory
   DESCRIPTION
     "This variable represents the storage type value for the
      vrIpPgPolicy tables."
::= { vrIpPgPolicyRowStatusEntry 4 }

vrIpPgPolicyIndex OBJECT-TYPE
   SYNTAX     AsciiStringIndex (SIZE (1..20))
   ACCESS     not-accessible
   STATUS     mandatory
   DESCRIPTION
     "This variable represents the index for the vrIpPgPolicy tables."
::= { vrIpPgPolicyRowStatusEntry 10 }

vrIpPgPolicyProvTable OBJECT-TYPE
   SYNTAX     SEQUENCE OF VrIpPgPolicyProvEntry
   ACCESS     not-accessible
   STATUS     mandatory
   DESCRIPTION
     "This group contains the provisionable attributes for the Policy 
      component."
::= { vrIpPgPolicy 10 }

vrIpPgPolicyProvEntry OBJECT-TYPE
   SYNTAX     VrIpPgPolicyProvEntry
   ACCESS     not-accessible
   STATUS     mandatory
   DESCRIPTION
     "An entry in the vrIpPgPolicyProvTable."
   INDEX {
      vrIndex,
      vrIpIndex,
      vrIpPgIndex,
      vrIpPgPolicyIndex }
::= { vrIpPgPolicyProvTable 1 }

VrIpPgPolicyProvEntry ::= SEQUENCE {
   vrIpPgPolicyCosTreatmentIndex
      Unsigned32 }

vrIpPgPolicyCosTreatmentIndex OBJECT-TYPE
   SYNTAX     Unsigned32 (0..3)
   ACCESS     read-write
   STATUS     mandatory
   DESCRIPTION
     "This attribute specifies the Class Of Service (COS) treatment a 
      packet receives if this policy applies. If the value of this attribute is 
      set to n, then the COS treatment is defined by the CosTreatment/n 
      component of the same CosPolicyGroup."
   DEFVAL     { 0 }
::= { vrIpPgPolicyProvEntry 1 }


-- Vr/<string> Ip Pg/<string> Policy/<string> TosMap
-- The TosMap component is one of several ways to define the 
-- matching criteria for which a Policy is deemed applicable.
-- 
-- The TosMap component allows the operator to provision a list of 
-- Type Of service (TOS) byte values. Incoming packets are deemed to 
-- match this policy if the TOS byte matches any one of those in the 
-- list.
-- 
-- The operator is provided with the flexibility to define which bits in 
-- the TOS byte are to be matched by setting the tosMask attribute 
-- under the CosTreatment component.

vrIpPgPolicyTosMap OBJECT IDENTIFIER ::= { vrIpPgPolicy 2 }



vrIpPgPolicyTosMapRowStatusTable OBJECT-TYPE
   SYNTAX     SEQUENCE OF VrIpPgPolicyTosMapRowStatusEntry
   ACCESS     not-accessible
   STATUS     mandatory
   DESCRIPTION
     "This entry controls the addition and deletion of 
      vrIpPgPolicyTosMap components."
::= { vrIpPgPolicyTosMap 1 }

vrIpPgPolicyTosMapRowStatusEntry OBJECT-TYPE
   SYNTAX     VrIpPgPolicyTosMapRowStatusEntry
   ACCESS     not-accessible
   STATUS     mandatory
   DESCRIPTION
     "A single entry in the table represents a single 
      vrIpPgPolicyTosMap component."
   INDEX {
      vrIndex,
      vrIpIndex,
      vrIpPgIndex,
      vrIpPgPolicyIndex,
      vrIpPgPolicyTosMapIndex }
::= { vrIpPgPolicyTosMapRowStatusTable 1 }

VrIpPgPolicyTosMapRowStatusEntry ::= SEQUENCE {
   vrIpPgPolicyTosMapRowStatus
      RowStatus,
   vrIpPgPolicyTosMapComponentName
      DisplayString,
   vrIpPgPolicyTosMapStorageType
      StorageType,
   vrIpPgPolicyTosMapIndex
      NonReplicated }

vrIpPgPolicyTosMapRowStatus OBJECT-TYPE
   SYNTAX     RowStatus 
   ACCESS     read-write
   STATUS     mandatory
   DESCRIPTION
     "This variable is used as the basis for SNMP naming of
      vrIpPgPolicyTosMap components.
      These components can be added and deleted."
::= { vrIpPgPolicyTosMapRowStatusEntry 1 }

vrIpPgPolicyTosMapComponentName OBJECT-TYPE
   SYNTAX     DisplayString 
   ACCESS     read-only
   STATUS     mandatory
   DESCRIPTION
     "This variable provides the component's string name for
      use with the ASCII Console Interface"
::= { vrIpPgPolicyTosMapRowStatusEntry 2 }

vrIpPgPolicyTosMapStorageType OBJECT-TYPE
   SYNTAX     StorageType 
   ACCESS     read-only
   STATUS     mandatory
   DESCRIPTION
     "This variable represents the storage type value for the
      vrIpPgPolicyTosMap tables."
::= { vrIpPgPolicyTosMapRowStatusEntry 4 }

vrIpPgPolicyTosMapIndex OBJECT-TYPE
   SYNTAX     NonReplicated 
   ACCESS     not-accessible
   STATUS     mandatory
   DESCRIPTION
     "This variable represents the index for the vrIpPgPolicyTosMap tables."
::= { vrIpPgPolicyTosMapRowStatusEntry 10 }

vrIpPgPolicyTosMapOperTable OBJECT-TYPE
   SYNTAX     SEQUENCE OF VrIpPgPolicyTosMapOperEntry
   ACCESS     not-accessible
   STATUS     mandatory
   DESCRIPTION
     "This group contains the operational attributes for the TosMap and 
      the IpAddrLayer4Flow component."
::= { vrIpPgPolicyTosMap 11 }

vrIpPgPolicyTosMapOperEntry OBJECT-TYPE
   SYNTAX     VrIpPgPolicyTosMapOperEntry
   ACCESS     not-accessible
   STATUS     mandatory
   DESCRIPTION
     "An entry in the vrIpPgPolicyTosMapOperTable."
   INDEX {
      vrIndex,
      vrIpIndex,
      vrIpPgIndex,
      vrIpPgPolicyIndex,
      vrIpPgPolicyTosMapIndex }
::= { vrIpPgPolicyTosMapOperTable 1 }

VrIpPgPolicyTosMapOperEntry ::= SEQUENCE {
   vrIpPgPolicyTosMapCos
      Unsigned32 }

vrIpPgPolicyTosMapCos OBJECT-TYPE
   SYNTAX     Unsigned32 (0..3)
   ACCESS     read-only
   STATUS     mandatory
   DESCRIPTION
     "This attribute indicates the Class Of Service (COS) with which a 
      packet receives if this policy applies. The value of this attribute is 
      derived from the cos attribute of the referenced CosTreatment of the 
      Policy."
::= { vrIpPgPolicyTosMapOperEntry 1 }

vrIpPgPolicyTosMapTosTable OBJECT-TYPE
   SYNTAX     SEQUENCE OF VrIpPgPolicyTosMapTosEntry
   ACCESS     not-accessible
   STATUS     mandatory
   DESCRIPTION
     "This attribute specifies a list of TOS byte values. An incoming 
      packet is considered to match this policy if its masked TOS byte 
      matches a value in the list. The TOS byte of the incoming packet is 
      anded with the tosMask attribute of the referenced CosTreatment 
      component before the comparison is done.
      
      This attribute must contain at least one TOS byte value, otherwise a 
      semantic check error is generated."
::= { vrIpPgPolicyTosMap 434 }

vrIpPgPolicyTosMapTosEntry OBJECT-TYPE
   SYNTAX     VrIpPgPolicyTosMapTosEntry
   ACCESS     not-accessible
   STATUS     mandatory
   DESCRIPTION
     "An entry in the vrIpPgPolicyTosMapTosTable."
   INDEX {
      vrIndex,
      vrIpIndex,
      vrIpPgIndex,
      vrIpPgPolicyIndex,
      vrIpPgPolicyTosMapIndex,
      vrIpPgPolicyTosMapTosValue }
::= { vrIpPgPolicyTosMapTosTable 1 }

VrIpPgPolicyTosMapTosEntry ::= SEQUENCE {
   vrIpPgPolicyTosMapTosValue
      Integer32,
   vrIpPgPolicyTosMapTosRowStatus
      RowStatus }

vrIpPgPolicyTosMapTosValue OBJECT-TYPE
   SYNTAX     Integer32 (0..255)
   ACCESS     read-write
   STATUS     mandatory
   DESCRIPTION
     "This variable represents both the value and the index for the
      vrIpPgPolicyTosMapTosTable."
::= { vrIpPgPolicyTosMapTosEntry 1 }

vrIpPgPolicyTosMapTosRowStatus OBJECT-TYPE
   SYNTAX     RowStatus 
   ACCESS     write-only
   STATUS     mandatory
   DESCRIPTION
     "This variable is used to control the addition and deletion 
      of individual values of the vrIpPgPolicyTosMapTosTable."
::= { vrIpPgPolicyTosMapTosEntry 2 }


-- Vr/<string> Ip Pg/<string> Policy/<string> IpAddrLayer4Flow/n
-- The IpAddrLayer4Flow component is one of several ways to define 
-- the matching criteria for which a Policy is deemed applicable.
-- 
-- The IpAddrLayer4Flow component allows the operator to 
-- distinguish a flow based on:
-- 1. IP address or range of IP addresses; and/or
-- 2. Layer 4 (transport) protocol; and
-- 3. Optionally for TCP and UDP, one can further specify the port 
-- number or range of port numbers.
-- 
-- When both IP address and port number are defined, the matching is 
-- as follows:
-- 1. The provisioned IP address and port number is matched against 
-- the destination IP address and destination TCP/UDP port number of 
-- the incoming packet. If the match fails, then
-- 2. The provisioned IP address and port number is matched against 
-- the source IP address and src TCP/UDP port number.

vrIpPgPolicyIpAddrLayer4Flow OBJECT IDENTIFIER ::= { vrIpPgPolicy 3 }



vrIpPgPolicyIpAddrLayer4FlowRowStatusTable OBJECT-TYPE
   SYNTAX     SEQUENCE OF VrIpPgPolicyIpAddrLayer4FlowRowStatusEntry
   ACCESS     not-accessible
   STATUS     mandatory
   DESCRIPTION
     "This entry controls the addition and deletion of 
      vrIpPgPolicyIpAddrLayer4Flow components."
::= { vrIpPgPolicyIpAddrLayer4Flow 1 }

vrIpPgPolicyIpAddrLayer4FlowRowStatusEntry OBJECT-TYPE
   SYNTAX     VrIpPgPolicyIpAddrLayer4FlowRowStatusEntry
   ACCESS     not-accessible
   STATUS     mandatory
   DESCRIPTION
     "A single entry in the table represents a single 
      vrIpPgPolicyIpAddrLayer4Flow component."
   INDEX {
      vrIndex,
      vrIpIndex,
      vrIpPgIndex,
      vrIpPgPolicyIndex,
      vrIpPgPolicyIpAddrLayer4FlowIndex }
::= { vrIpPgPolicyIpAddrLayer4FlowRowStatusTable 1 }

VrIpPgPolicyIpAddrLayer4FlowRowStatusEntry ::= SEQUENCE {
   vrIpPgPolicyIpAddrLayer4FlowRowStatus
      RowStatus,
   vrIpPgPolicyIpAddrLayer4FlowComponentName
      DisplayString,
   vrIpPgPolicyIpAddrLayer4FlowStorageType
      StorageType,
   vrIpPgPolicyIpAddrLayer4FlowIndex
      Integer32 }

vrIpPgPolicyIpAddrLayer4FlowRowStatus OBJECT-TYPE
   SYNTAX     RowStatus 
   ACCESS     read-write
   STATUS     mandatory
   DESCRIPTION
     "This variable is used as the basis for SNMP naming of
      vrIpPgPolicyIpAddrLayer4Flow components.
      These components can be added and deleted."
::= { vrIpPgPolicyIpAddrLayer4FlowRowStatusEntry 1 }

vrIpPgPolicyIpAddrLayer4FlowComponentName OBJECT-TYPE
   SYNTAX     DisplayString 
   ACCESS     read-only
   STATUS     mandatory
   DESCRIPTION
     "This variable provides the component's string name for
      use with the ASCII Console Interface"
::= { vrIpPgPolicyIpAddrLayer4FlowRowStatusEntry 2 }

vrIpPgPolicyIpAddrLayer4FlowStorageType OBJECT-TYPE
   SYNTAX     StorageType 
   ACCESS     read-only
   STATUS     mandatory
   DESCRIPTION
     "This variable represents the storage type value for the
      vrIpPgPolicyIpAddrLayer4Flow tables."
::= { vrIpPgPolicyIpAddrLayer4FlowRowStatusEntry 4 }

vrIpPgPolicyIpAddrLayer4FlowIndex OBJECT-TYPE
   SYNTAX     Integer32 (0..1023)
   ACCESS     not-accessible
   STATUS     mandatory
   DESCRIPTION
     "This variable represents the index for the vrIpPgPolicyIpAddrLayer4Flow tables."
::= { vrIpPgPolicyIpAddrLayer4FlowRowStatusEntry 10 }

vrIpPgPolicyIpAddrLayer4FlowProvTable OBJECT-TYPE
   SYNTAX     SEQUENCE OF VrIpPgPolicyIpAddrLayer4FlowProvEntry
   ACCESS     not-accessible
   STATUS     mandatory
   DESCRIPTION
     "This group contains the provisionable attributes for any flow related 
      component which has prefix and prefix length as its parameters."
::= { vrIpPgPolicyIpAddrLayer4Flow 10 }

vrIpPgPolicyIpAddrLayer4FlowProvEntry OBJECT-TYPE
   SYNTAX     VrIpPgPolicyIpAddrLayer4FlowProvEntry
   ACCESS     not-accessible
   STATUS     mandatory
   DESCRIPTION
     "An entry in the vrIpPgPolicyIpAddrLayer4FlowProvTable."
   INDEX {
      vrIndex,
      vrIpIndex,
      vrIpPgIndex,
      vrIpPgPolicyIndex,
      vrIpPgPolicyIpAddrLayer4FlowIndex }
::= { vrIpPgPolicyIpAddrLayer4FlowProvTable 1 }

VrIpPgPolicyIpAddrLayer4FlowProvEntry ::= SEQUENCE {
   vrIpPgPolicyIpAddrLayer4FlowPrefix
      IpAddress,
   vrIpPgPolicyIpAddrLayer4FlowPrefixLength
      Unsigned32 }

vrIpPgPolicyIpAddrLayer4FlowPrefix OBJECT-TYPE
   SYNTAX     IpAddress 
   ACCESS     read-write
   STATUS     mandatory
   DESCRIPTION
     "This attribute specifies the IP address prefix, source or destination 
      IP address, of which the policy applies. The matching of actual 
      address to the prefix is done in conjunction with the prefixLength 
      attribute. A prefix length of 0 means any IP address."
   DEFVAL     { '00000000'H }  -- "0.0.0.0"
::= { vrIpPgPolicyIpAddrLayer4FlowProvEntry 1 }

vrIpPgPolicyIpAddrLayer4FlowPrefixLength OBJECT-TYPE
   SYNTAX     Unsigned32 (0..32)
   ACCESS     read-write
   STATUS     mandatory
   DESCRIPTION
     "This attribute specifies the number of most significant bits of the IP 
      address that are to be matched with the prefix. A prefix length of 0 
      means any IP address."
   DEFVAL     { 0 }
::= { vrIpPgPolicyIpAddrLayer4FlowProvEntry 2 }

vrIpPgPolicyIpAddrLayer4FlowProtoProvisionedTable OBJECT-TYPE
   SYNTAX     SEQUENCE OF VrIpPgPolicyIpAddrLayer4FlowProtoProvisionedEntry
   ACCESS     not-accessible
   STATUS     mandatory
   DESCRIPTION
     "This group contains the provisionable attributes for any flow related 
      component which has layer 4 (transport) protocol and port number 
      as its parameters."
::= { vrIpPgPolicyIpAddrLayer4Flow 11 }

vrIpPgPolicyIpAddrLayer4FlowProtoProvisionedEntry OBJECT-TYPE
   SYNTAX     VrIpPgPolicyIpAddrLayer4FlowProtoProvisionedEntry
   ACCESS     not-accessible
   STATUS     mandatory
   DESCRIPTION
     "An entry in the vrIpPgPolicyIpAddrLayer4FlowProtoProvisionedTable."
   INDEX {
      vrIndex,
      vrIpIndex,
      vrIpPgIndex,
      vrIpPgPolicyIndex,
      vrIpPgPolicyIpAddrLayer4FlowIndex }
::= { vrIpPgPolicyIpAddrLayer4FlowProtoProvisionedTable 1 }

VrIpPgPolicyIpAddrLayer4FlowProtoProvisionedEntry ::= SEQUENCE {
   vrIpPgPolicyIpAddrLayer4FlowProtocol
      INTEGER }

vrIpPgPolicyIpAddrLayer4FlowProtocol OBJECT-TYPE
   SYNTAX     INTEGER  {
                 icmp(1),
                 tcp(6),
                 udp(17) }
   ACCESS     read-write
   STATUS     mandatory
   DESCRIPTION
     "This attribute specifies the layer 4 (transport) protocol to which the 
      policy applies."
   DEFVAL     { tcp }
::= { vrIpPgPolicyIpAddrLayer4FlowProtoProvisionedEntry 1 }

vrIpPgPolicyIpAddrLayer4FlowOperTable OBJECT-TYPE
   SYNTAX     SEQUENCE OF VrIpPgPolicyIpAddrLayer4FlowOperEntry
   ACCESS     not-accessible
   STATUS     mandatory
   DESCRIPTION
     "This group contains the operational attributes for the TosMap and 
      the IpAddrLayer4Flow component."
::= { vrIpPgPolicyIpAddrLayer4Flow 12 }

vrIpPgPolicyIpAddrLayer4FlowOperEntry OBJECT-TYPE
   SYNTAX     VrIpPgPolicyIpAddrLayer4FlowOperEntry
   ACCESS     not-accessible
   STATUS     mandatory
   DESCRIPTION
     "An entry in the vrIpPgPolicyIpAddrLayer4FlowOperTable."
   INDEX {
      vrIndex,
      vrIpIndex,
      vrIpPgIndex,
      vrIpPgPolicyIndex,
      vrIpPgPolicyIpAddrLayer4FlowIndex }
::= { vrIpPgPolicyIpAddrLayer4FlowOperTable 1 }

VrIpPgPolicyIpAddrLayer4FlowOperEntry ::= SEQUENCE {
   vrIpPgPolicyIpAddrLayer4FlowCos
      Unsigned32 }

vrIpPgPolicyIpAddrLayer4FlowCos OBJECT-TYPE
   SYNTAX     Unsigned32 (0..3)
   ACCESS     read-only
   STATUS     mandatory
   DESCRIPTION
     "This attribute indicates the Class Of Service (COS) with which a 
      packet receives if this policy applies. The value of this attribute is 
      derived from the cos attribute of the referenced CosTreatment of the 
      Policy."
::= { vrIpPgPolicyIpAddrLayer4FlowOperEntry 1 }

vrIpPgPolicyIpAddrLayer4FlowPortNumberRangeTable OBJECT-TYPE
   SYNTAX     SEQUENCE OF VrIpPgPolicyIpAddrLayer4FlowPortNumberRangeEntry
   ACCESS     not-accessible
   STATUS     mandatory
   DESCRIPTION
     "This attribute specifies the TCP or UDP port number or range of 
      port numbers of which the policy applies. The port numbers 
      specified here are used to match the source or destination port 
      number of any incoming packet. The exact matching algorithm is 
      defined by the flow component that uses this attribute group.
      
      To specify a port number to match, just enter the value. To specify a 
      range of port numbers to match, enter the lower and upper bound of 
      the range. The order in which the lower and upper bound are 
      entered does not matter.
      
      Not setting this attribute or setting the port number to 0 means any 
      port number."
::= { vrIpPgPolicyIpAddrLayer4Flow 435 }

vrIpPgPolicyIpAddrLayer4FlowPortNumberRangeEntry OBJECT-TYPE
   SYNTAX     VrIpPgPolicyIpAddrLayer4FlowPortNumberRangeEntry
   ACCESS     not-accessible
   STATUS     mandatory
   DESCRIPTION
     "An entry in the vrIpPgPolicyIpAddrLayer4FlowPortNumberRangeTable."
   INDEX {
      vrIndex,
      vrIpIndex,
      vrIpPgIndex,
      vrIpPgPolicyIndex,
      vrIpPgPolicyIpAddrLayer4FlowIndex,
      vrIpPgPolicyIpAddrLayer4FlowPortNumberRangeValue }
::= { vrIpPgPolicyIpAddrLayer4FlowPortNumberRangeTable 1 }

VrIpPgPolicyIpAddrLayer4FlowPortNumberRangeEntry ::= SEQUENCE {
   vrIpPgPolicyIpAddrLayer4FlowPortNumberRangeValue
      Integer32,
   vrIpPgPolicyIpAddrLayer4FlowPortNumberRangeRowStatus
      RowStatus }

vrIpPgPolicyIpAddrLayer4FlowPortNumberRangeValue OBJECT-TYPE
   SYNTAX     Integer32 (0..65535)
   ACCESS     read-write
   STATUS     mandatory
   DESCRIPTION
     "This variable represents both the value and the index for the
      vrIpPgPolicyIpAddrLayer4FlowPortNumberRangeTable."
::= { vrIpPgPolicyIpAddrLayer4FlowPortNumberRangeEntry 1 }

vrIpPgPolicyIpAddrLayer4FlowPortNumberRangeRowStatus OBJECT-TYPE
   SYNTAX     RowStatus 
   ACCESS     write-only
   STATUS     mandatory
   DESCRIPTION
     "This variable is used to control the addition and deletion 
      of individual values of the vrIpPgPolicyIpAddrLayer4FlowPortNumberRangeTable."
::= { vrIpPgPolicyIpAddrLayer4FlowPortNumberRangeEntry 2 }


-- Vr/<string> Ip Pg/<string> CosTreatment/n
-- The CosTreatment represents a Class of Service (COS) treatment a 
-- packet receives when any Policy referencing it is deemed 
-- applicable. A Policy is referencing this component if its 
-- cosTreatmentIndex attribute contains the instance value of this 
-- component.
-- 
-- Four instances of this component, index 0, 1, 2 and 3 respectively, 
-- are created automatically when the parent CosPolicyGroup 
-- component is added. These 4 CosTreatment component represents 
-- the 4 COSs that are currently supported.
-- 
-- When multiple policies, such as TosMap and IpAddrLayer4Flow 
-- are deemed applicable to a packet, the ultimate COS treatment the 
-- packet receives is determined in the following fashion:
-- 
-- 1. The packet's COS is initialized to be the media's assigned COS. 
-- For media type FrameRelayDte, the media COS is based on the 
-- receiving DLCI's ipCos. For Vns, the media COS is based on the 
-- mapping from discard and emission priority in the Vns header to 
-- QosP. For all other media, the media COS is the linked IpPort 
-- assignedQos.
-- 
-- 2. Subsequently, if the IpPort has a TosMap policy provisioned, the 
-- packet's COS is updated if there is a match.
-- 
-- 3. Finally, if the IpPort has one or more IpAddrLayer4Flow policies 
-- provisioned, the packet's COS is updated if there is a match.

vrIpPgCosTreatment OBJECT IDENTIFIER ::= { vrIpPg 3 }



vrIpPgCosTreatmentRowStatusTable OBJECT-TYPE
   SYNTAX     SEQUENCE OF VrIpPgCosTreatmentRowStatusEntry
   ACCESS     not-accessible
   STATUS     mandatory
   DESCRIPTION
     "This entry controls the addition and deletion of 
      vrIpPgCosTreatment components."
::= { vrIpPgCosTreatment 1 }

vrIpPgCosTreatmentRowStatusEntry OBJECT-TYPE
   SYNTAX     VrIpPgCosTreatmentRowStatusEntry
   ACCESS     not-accessible
   STATUS     mandatory
   DESCRIPTION
     "A single entry in the table represents a single 
      vrIpPgCosTreatment component."
   INDEX {
      vrIndex,
      vrIpIndex,
      vrIpPgIndex,
      vrIpPgCosTreatmentIndex }
::= { vrIpPgCosTreatmentRowStatusTable 1 }

VrIpPgCosTreatmentRowStatusEntry ::= SEQUENCE {
   vrIpPgCosTreatmentRowStatus
      RowStatus,
   vrIpPgCosTreatmentComponentName
      DisplayString,
   vrIpPgCosTreatmentStorageType
      StorageType,
   vrIpPgCosTreatmentIndex
      Integer32 }

vrIpPgCosTreatmentRowStatus OBJECT-TYPE
   SYNTAX     RowStatus 
   ACCESS     read-write
   STATUS     mandatory
   DESCRIPTION
     "This variable is used as the basis for SNMP naming of
      vrIpPgCosTreatment components.
      These components can be added."
::= { vrIpPgCosTreatmentRowStatusEntry 1 }

vrIpPgCosTreatmentComponentName OBJECT-TYPE
   SYNTAX     DisplayString 
   ACCESS     read-only
   STATUS     mandatory
   DESCRIPTION
     "This variable provides the component's string name for
      use with the ASCII Console Interface"
::= { vrIpPgCosTreatmentRowStatusEntry 2 }

vrIpPgCosTreatmentStorageType OBJECT-TYPE
   SYNTAX     StorageType 
   ACCESS     read-only
   STATUS     mandatory
   DESCRIPTION
     "This variable represents the storage type value for the
      vrIpPgCosTreatment tables."
::= { vrIpPgCosTreatmentRowStatusEntry 4 }

vrIpPgCosTreatmentIndex OBJECT-TYPE
   SYNTAX     Integer32 (0..3)
   ACCESS     not-accessible
   STATUS     mandatory
   DESCRIPTION
     "This variable represents the index for the vrIpPgCosTreatment tables."
::= { vrIpPgCosTreatmentRowStatusEntry 10 }

vrIpPgCosTreatmentProvTable OBJECT-TYPE
   SYNTAX     SEQUENCE OF VrIpPgCosTreatmentProvEntry
   ACCESS     not-accessible
   STATUS     mandatory
   DESCRIPTION
     "This group contains the provisionable attributes for the 
      CosTreatment component."
::= { vrIpPgCosTreatment 10 }

vrIpPgCosTreatmentProvEntry OBJECT-TYPE
   SYNTAX     VrIpPgCosTreatmentProvEntry
   ACCESS     not-accessible
   STATUS     mandatory
   DESCRIPTION
     "An entry in the vrIpPgCosTreatmentProvTable."
   INDEX {
      vrIndex,
      vrIpIndex,
      vrIpPgIndex,
      vrIpPgCosTreatmentIndex }
::= { vrIpPgCosTreatmentProvTable 1 }

VrIpPgCosTreatmentProvEntry ::= SEQUENCE {
   vrIpPgCosTreatmentCos
      Unsigned32,
   vrIpPgCosTreatmentSetTosByte
      INTEGER,
   vrIpPgCosTreatmentTos
      Hex,
   vrIpPgCosTreatmentTosMask
      Hex,
   vrIpPgCosTreatmentEmissionPriority
      Unsigned32,
   vrIpPgCosTreatmentDiscardPriority
      Unsigned32 }

vrIpPgCosTreatmentCos OBJECT-TYPE
   SYNTAX     Unsigned32 (0..3)
   ACCESS     read-only
   STATUS     mandatory
   DESCRIPTION
     "This attribute specifies the Class Of Service (COS) with which a 
      packet would be forwarded when this COS treatment is selected."
::= { vrIpPgCosTreatmentProvEntry 1 }

vrIpPgCosTreatmentSetTosByte OBJECT-TYPE
   SYNTAX     INTEGER  {
                 no(0),
                 yes(1) }
   ACCESS     read-write
   STATUS     mandatory
   DESCRIPTION
     "This attribute specifies whether the router would change the Type 
      Of Service (TOS) byte of packets when this COS treatment is 
      selected. If set to yes, the TOS byte is changed based on the value of 
      tos and tosMask."
   DEFVAL     { no }
::= { vrIpPgCosTreatmentProvEntry 3 }

vrIpPgCosTreatmentTos OBJECT-TYPE
   SYNTAX     Hex (0..255)
   ACCESS     read-write
   STATUS     mandatory
   DESCRIPTION
     "This attribute specifies the value of the Type Of Service (TOS) byte 
      with which packets are updated when this COS treatment is 
      selected. This attribute is ignored if setTosByte is set to no. The 
      actual TOS byte of the packet is updated based on the tos and 
      tosMask attribute using the following formula:
      
      New TOS = ( Original TOS & ~tosMask ) | ( tos & tosMask )
      
      For example:
      
      Original TOS byte: hex 8A (10001010 in binary)
      tos attribute: hex 12 (00010010 in binary)
      tosMask attribute: hex 3F (00111111 in binary)
      
      The changed TOS byte would be: hex 92 (10010010 in binary)."
   DEFVAL     { 0 }
::= { vrIpPgCosTreatmentProvEntry 4 }

vrIpPgCosTreatmentTosMask OBJECT-TYPE
   SYNTAX     Hex (1..255)
   ACCESS     read-write
   STATUS     mandatory
   DESCRIPTION
     "This attribute specifies the Type Of Service (TOS) bit mask with 
      which the packets are examined and updated when this COS 
      treatment is selected. The mask specifies which bits within the 
      original TOS byte are to be examined or updated by the router.
      
      When the setTosByte is set to yes, this attribute is used in 
      conjunction with the tos attribute to determine how the TOS byte is 
      updated using the following formula:
      
      New TOS = ( Original TOS & ~tosMask ) | ( tos & tosMask )
      
      For example:
      
      Original TOS byte: hex 8A (10001010 in binary)
      tos attribute: hex 12 (00010010 in binary)
      tosMask attribute: hex 3F (00111111 in binary)
      
      The changed TOS byte would be: hex 92 (10010010 in binary).
      
      When the TosMap component is provisioned under this Policy, this 
      attribute is used in conjunction with the tos attribute of the TosMap 
      component when packets are examined for matching TOS bits.
      
      By default, this attribute is set to the value of hex FC, i.e. bits 0-5 of 
      the TOS byte ( differentiated services codepoint bits) are eligible to 
      be examined and updated.
      
      When either the setTosByte is set to yes, or when the TosMap 
      component is provisioned, a zero tosMask is considered invalid,"
   DEFVAL     { 252 }
::= { vrIpPgCosTreatmentProvEntry 5 }

vrIpPgCosTreatmentEmissionPriority OBJECT-TYPE
   SYNTAX     Unsigned32 (1..8)
   ACCESS     read-write
   STATUS     mandatory
   DESCRIPTION
     "This attribute specifies the emission  priority to be assigned to 
      packets when this CoS Treatment is selected. The use of the 
      emission priority is egress media specific. This attribute can take a 
      value from 1 to 8. 1 is treated as the highest priority and 8 the 
      lowest. Some egress media support fewer then 8 emission prioritie. 
      For these media the values which correspond to emission priorities 
      lower then the lowest supported priority are treated as the lowest 
      priority. For instance, if a media supports two priorities, high and 
      normal, a vlaue of 1 corresponds to high priority and values of 2 to 
      8 correspond to normal priority."
   DEFVAL     { 2 }
::= { vrIpPgCosTreatmentProvEntry 6 }

vrIpPgCosTreatmentDiscardPriority OBJECT-TYPE
   SYNTAX     Unsigned32 (0 | 1..3)
   ACCESS     read-write
   STATUS     mandatory
   DESCRIPTION
     "This attribute specifies the discard  priority to be assigned to packets 
      when this CoS Treatment is selected.

      VALUES (

      0 = unChanged

      )"
   DEFVAL     { 0 }
::= { vrIpPgCosTreatmentProvEntry 7 }




-- 
-- Version and Compliance statements
-- 



-- Object-Group Statement:
-- A list of all current accessible leaf objects.

-- OBJECTS { vrIpPgPolicyIpAddrLayer4FlowCos,
--           vrIpPgPolicyTosMapTosValue,
--           vrIpPgPolicyIpAddrLayer4FlowComponentName,
--           vrIpPgCosTreatmentRowStatus,
--           vrIpPgPolicyIpAddrLayer4FlowProtocol,
--           vrIpPgPolicyIpAddrLayer4FlowPortNumberRangeRowStatus,
--           vrIpPgPolicyTosMapCos,
--           vrIpPgUsersRowStatus,
--           vrIpPgCosTreatmentDiscardPriority,
--           vrIpPgPolicyTosMapComponentName,
--           vrIpPgPolicyIpAddrLayer4FlowPrefixLength,
--           vrIpPgCosTreatmentEmissionPriority,
--           vrIpPgPolicyStorageType,
--           vrIpPgStorageType,
--           vrIpPgCosTreatmentTosMask,
--           vrIpPgPolicyTosMapStorageType,
--           vrIpPgPolicyIpAddrLayer4FlowPortNumberRangeValue,
--           vrIpPgUsersValue,
--           vrIpPgPolicyCosTreatmentIndex,
--           vrIpPgCosTreatmentCos,
--           vrIpPgCosTreatmentComponentName,
--           vrIpPgRowStatus,
--           vrIpPgCosTreatmentStorageType,
--           vrIpPgCosTreatmentTos,
--           vrIpPgPolicyIpAddrLayer4FlowRowStatus,
--           vrIpPgPolicyRowStatus,
--           vrIpPgPolicyIpAddrLayer4FlowStorageType,
--           vrIpPgPolicyTosMapTosRowStatus,
--           vrIpPgPolicyIpAddrLayer4FlowPrefix,
--           vrIpPgPolicyTosMapRowStatus,
--           vrIpPgCosTreatmentSetTosByte,
--           vrIpPgComponentName,
--           vrIpPgPolicyComponentName }
-- STATUS  mandatory
-- DESCRIPTION
--   "A list of all current accessible leaf objects."

ipCosGroup OBJECT IDENTIFIER ::= { ipCosMIB 1 }
ipCosGroupBG OBJECT IDENTIFIER ::= { ipCosGroup 7 }
ipCosGroupBG00 OBJECT IDENTIFIER ::= { ipCosGroupBG 1 }
ipCosGroupBG00A OBJECT IDENTIFIER ::= { ipCosGroupBG00 2 }



-- Agent-Capabilities Statement:

-- PRODUCT-RELEASE "Passport Release 7.0 IpCos."
-- STATUS          mandatory
-- DESCRIPTION     "IpCos MIB: MIB Version BG00A,
--                  Software Version BG00S4C."
-- SUPPORTS        Nortel-Magellan-Passport-IpCosMIB
--    INCLUDES     { ipCosGroupBG00A }

ipCosCapabilities OBJECT IDENTIFIER ::= { ipCosMIB 3 }
ipCosCapabilitiesBG OBJECT IDENTIFIER ::= { ipCosCapabilities 7 }
ipCosCapabilitiesBG00 OBJECT IDENTIFIER ::= { ipCosCapabilitiesBG 1 }
ipCosCapabilitiesBG00A OBJECT IDENTIFIER ::= { ipCosCapabilitiesBG00 2 }





END
