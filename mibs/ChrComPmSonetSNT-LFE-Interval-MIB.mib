ChrComPmSonetSNT-LFE-Interval-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComPmSonet				FROM  Chromatis-MIB
	chrComIfifIndex					FROM  ChrComIfifTable-MIB
	TruthValue				FROM  ChrTyp-MIB
	Gauge32				FROM  SNMPv2-SMI;

-- chrComPmSonetSNT-LFE-Interval Table

chrComPmSonetSNT-LFE-IntervalTable		OBJECT-TYPE
	SYNTAX		SEQUENCE OF ChrComPmSonetSNT-LFE-IntervalEntry
	MAX-ACCESS	not-accessible
	STATUS		current
	DESCRIPTION
	""
	::= { chrComPmSonet 8}

chrComPmSonetSNT-LFE-IntervalEntry		OBJECT-TYPE
	SYNTAX		ChrComPmSonetSNT-LFE-IntervalEntry
	MAX-ACCESS	not-accessible
	STATUS		current
	DESCRIPTION
	""
	INDEX  {  chrComIfifIndex, chrComPmSonetIntervalNumber }

--DEFAULT  get-function-async  MNIL_GetRoutine
--DEFAULT  set-function-async  MNIL_SetRoutine
--DEFAULT  next-function-async MNIL_NextRoutine
--DEFAULT  test-function-async MNIL_TestRoutine
--DEFAULT  cookie "SNT-LFE-Interval"
	::= { chrComPmSonetSNT-LFE-IntervalTable  1 }

ChrComPmSonetSNT-LFE-IntervalEntry  ::=
	SEQUENCE  {
	chrComPmSonetIntervalNumber		Unsigned32	(1..32),
	chrComPmSonetSuspectedInterval	TruthValue,
	chrComPmSonetElapsedTime		Unsigned32	(0..4294967295),
	chrComPmSonetSuppressedIntrvls	Gauge32			(0..4294967295),
	chrComPmSonetES			Gauge32			(0..4294967295),
	chrComPmSonetSES			Gauge32			(0..4294967295),
	chrComPmSonetCV			Gauge32			(0..4294967295),
	chrComPmSonetUAS			Gauge32			(0..4294967295)
}

chrComPmSonetIntervalNumber 	OBJECT-TYPE
	SYNTAX		Unsigned32	(1..32)
	MAX-ACCESS 	read-only
	STATUS 		current
	DESCRIPTION
	""
	::= { chrComPmSonetSNT-LFE-IntervalEntry  1 }

chrComPmSonetSuspectedInterval 	OBJECT-TYPE
	SYNTAX		TruthValue
	MAX-ACCESS 	read-only
	STATUS 		current
	DESCRIPTION
	""
	::= { chrComPmSonetSNT-LFE-IntervalEntry  2 }

chrComPmSonetElapsedTime 	OBJECT-TYPE
	SYNTAX		Unsigned32	(0..4294967295)
	MAX-ACCESS 	read-only
	STATUS 		current
	DESCRIPTION
	""
	::= { chrComPmSonetSNT-LFE-IntervalEntry  3 }

chrComPmSonetSuppressedIntrvls 	OBJECT-TYPE
	SYNTAX		Gauge32			(0..4294967295)
	MAX-ACCESS 	read-only
	STATUS 		current
	DESCRIPTION
	""
	::= { chrComPmSonetSNT-LFE-IntervalEntry  4 }

chrComPmSonetES 	OBJECT-TYPE
	SYNTAX		Gauge32			(0..4294967295)
	MAX-ACCESS 	read-only
	STATUS 		current
	DESCRIPTION
	""
	::= { chrComPmSonetSNT-LFE-IntervalEntry  5 }

chrComPmSonetSES 	OBJECT-TYPE
	SYNTAX		Gauge32			(0..4294967295)
	MAX-ACCESS 	read-only
	STATUS 		current
	DESCRIPTION
	""
	::= { chrComPmSonetSNT-LFE-IntervalEntry  6 }

chrComPmSonetCV 	OBJECT-TYPE
	SYNTAX		Gauge32			(0..4294967295)
	MAX-ACCESS 	read-only
	STATUS 		current
	DESCRIPTION
	""
	::= { chrComPmSonetSNT-LFE-IntervalEntry  7 }

chrComPmSonetUAS 	OBJECT-TYPE
	SYNTAX		Gauge32			(0..4294967295)
	MAX-ACCESS 	read-only
	STATUS 		current
	DESCRIPTION
	""
	::= { chrComPmSonetSNT-LFE-IntervalEntry  8 }


END
