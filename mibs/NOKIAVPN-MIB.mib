NOKIAVPN-MIB DEFINITIONS ::= BEGIN

IMPORTS
        MODULE-IDENTITY, OBJECT-IDENTITY, enterprises
		FROM SNMPv2-SMI
	nokiaVPN
		FROM NOKIA-OID-REGISTRATION-MIB;


nokiaVPNProducts OBJECT-IDENTITY
        STATUS  current
        DESCRIPTION
                "Products"
        ::= { nokiaVPN 1 }


nokiaVPNMgmt OBJECT-IDENTITY
        STATUS  current
        DESCRIPTION
                "Management"
        ::= { nokiaVPN 2 }

nokiaVPNExperiment OBJECT-IDENTITY
        STATUS  current
        DESCRIPTION
                "Experiment provides a root object identifier
                from which experimental mibs may be temporarily
                based.  mibs are typicially based here if they
                fall in one of two categories
                1) are IETF work-in-process mibs which have not
                   been assigned a permanent object identifier by
                   the IANA.
                2) are Network Alchemy work-in-process which has 
		   not been assigned a permanent object identifier 
		   by the Network Alchemy assigned number authority, 
		   typicially because the MIB is not ready for deployment.

                NOTE WELL:  support for MIBs in the nokiaVPNExperiment
                subtree will be deleted when a permanent object
                identifier assignment is made."
        ::= { nokiaVPN 3 }

nokiaVPNAdmin OBJECT-IDENTITY
        STATUS  current
        DESCRIPTION
                "Reserved for administratively assigned
                OBJECT IDENTIFIERS, i.e. those not associated with MIB
                objects"
        ::= { nokiaVPN 4 }

nokiaVPNModules OBJECT-IDENTITY
        STATUS  current
        DESCRIPTION
                "Provides a root object identifier
                from which MODULE-IDENTITY values may be assigned."
        ::= { nokiaVPN 5 }

nokiaVPNTraps OBJECT-IDENTITY
        STATUS  current
        DESCRIPTION
                "All the traps common to Nokia VPN fall under here."
        ::= { nokiaVPN 6 }

ipsec  OBJECT-IDENTITY  
	STATUS current
	DESCRIPTION "IPSEC (statistics) MIB"
	::= { nokiaVPNMgmt 1 }

vpn  OBJECT-IDENTITY  
	STATUS current
	DESCRIPTION "VPN (L2TP/PPTP tunnel statistics) MIB"
	::= { nokiaVPNMgmt 2 }

config  OBJECT-IDENTITY  
	STATUS current
	DESCRIPTION "General configuration MIB"
	::= { nokiaVPNMgmt 3 }

--
-- Hardware products
--

nokiaHardwareUnknown OBJECT-IDENTITY
        STATUS  current
        DESCRIPTION
                "Unknown hardware."
        ::= { nokiaVPNProducts 1 }

nokiaCryptoCluster500 OBJECT-IDENTITY
        STATUS  current
        DESCRIPTION
                "CryptoCluster 500."
        ::= { nokiaVPNProducts 4 }

nokiaCryptoCluster5010 OBJECT-IDENTITY
        STATUS  current
        DESCRIPTION
                "CryptoCluster 5010."
        ::= { nokiaVPNProducts 5 }

nokiaCryptoCluster501 OBJECT-IDENTITY
        STATUS  current
        DESCRIPTION
                "CryptoCluster 501."
        ::= { nokiaVPNProducts 8 }

nokiaCryptoCluster5000 OBJECT-IDENTITY
        STATUS  current
        DESCRIPTION
                "CryptoCluster 5000."
        ::= { nokiaVPNProducts 10 }

nokiaCryptoCluster2500 OBJECT-IDENTITY
        STATUS  current
        DESCRIPTION
                "CryptoCluster 2500."
        ::= { nokiaVPNProducts 11 }

nokiaCryptoCluster2501 OBJECT-IDENTITY
        STATUS  current
        DESCRIPTION
                "CryptoCluster 2501."
        ::= { nokiaVPNProducts 12 }

nokiaCryptoCluster5200 OBJECT-IDENTITY
        STATUS  current
        DESCRIPTION
                "CryptoCluster 5200."
        ::= { nokiaVPNProducts 15 }

nokiaCryptoCluster5205 OBJECT-IDENTITY
        STATUS  current
        DESCRIPTION
                "CryptoCluster 5205."
        ::= { nokiaVPNProducts 16 }

nokiaCA200 OBJECT-IDENTITY
        STATUS  current
        DESCRIPTION
                "CA200."
        ::= { nokiaVPNProducts 18 }

nokiaCA600 OBJECT-IDENTITY
        STATUS  current
        DESCRIPTION
                "CA600."
        ::= { nokiaVPNProducts 19 }

nokiaCryptoCluster100 OBJECT-IDENTITY
        STATUS  current
        DESCRIPTION
                "CryptoCluster."
        ::= { nokiaVPNProducts 20 }

END
