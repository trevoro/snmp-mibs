TERAWAVE-teraWlinkAtm-MIB DEFINITIONS ::= BEGIN
        -- Created by sml2mib compiler 
        IMPORTS

 enterprises,  OBJECT-TYPE,  Counter,  Gauge,  TimeTicks
        FROM RFC1155-SMI
		 Counter32 FROM SNMPv2-SMI;

terawave OBJECT IDENTIFIER ::=  { enterprises 4513 }

teraWaveLinkGroup OBJECT IDENTIFIER ::=  { terawave 6 }

     -- teraWlinkAtm

teraWlinkAtm OBJECT-TYPE
     SYNTAX SEQUENCE OF TeraWlinkAtmEntryType
     ACCESS not-accessible
     STATUS mandatory
     DESCRIPTION
          " table teraWlinkAtm"
     ::= { teraWaveLinkGroup 1 }

teraWlinkAtmEntry OBJECT-TYPE
          SYNTAX TeraWlinkAtmEntryType
          ACCESS not-accessible
          STATUS mandatory
          DESCRIPTION
               " table entry teraWlinkAtmEntry "
          INDEX {                   teraWlinkAtmIndex }
     ::= { teraWlinkAtm 1 }

TeraWlinkAtmEntryType ::= SEQUENCE {
          teraWlinkAtmIndex   
             INTEGER (1..5),
          uTOPIACellDrops   
             Counter32,
          misinsertedCells   
             Counter32,
          f4SegCells   
             Counter32,
          f4EndToEndCells   
             Counter32,
          f5SegCells   
             Counter32,
          f5EndToEndCells   
             Counter32,
          misinsertedOAMCells   
             Counter32
}

teraWlinkAtmIndex OBJECT-TYPE
          SYNTAX INTEGER (1..5)
          ACCESS read-only
          STATUS mandatory
          DESCRIPTION
               ""
          ::= { teraWlinkAtmEntry 1 }

uTOPIACellDrops OBJECT-TYPE
          SYNTAX Counter32
          ACCESS read-only
          STATUS mandatory
          DESCRIPTION
               ""
          ::= { teraWlinkAtmEntry 2 }

misinsertedCells OBJECT-TYPE
          SYNTAX Counter32
          ACCESS read-only
          STATUS mandatory
          DESCRIPTION
               ""
          ::= { teraWlinkAtmEntry 3 }

f4SegCells OBJECT-TYPE
          SYNTAX Counter32
          ACCESS read-only
          STATUS mandatory
          DESCRIPTION
               ""
          ::= { teraWlinkAtmEntry 4 }

f4EndToEndCells OBJECT-TYPE
          SYNTAX Counter32
          ACCESS read-only
          STATUS mandatory
          DESCRIPTION
               ""
          ::= { teraWlinkAtmEntry 5 }

f5SegCells OBJECT-TYPE
          SYNTAX Counter32
          ACCESS read-only
          STATUS mandatory
          DESCRIPTION
               ""
          ::= { teraWlinkAtmEntry 6 }

f5EndToEndCells OBJECT-TYPE
          SYNTAX Counter32
          ACCESS read-only
          STATUS mandatory
          DESCRIPTION
               ""
          ::= { teraWlinkAtmEntry 7 }

misinsertedOAMCells OBJECT-TYPE
          SYNTAX Counter32
          ACCESS read-only
          STATUS mandatory
          DESCRIPTION
               ""
          ::= { teraWlinkAtmEntry 8 }

END
