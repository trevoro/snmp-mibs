--			Ascend mibfrmrl MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBFRMRL-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmfrProfile  OBJECT IDENTIFIER ::= { configuration 78}
    mibframeRelayProfile  OBJECT IDENTIFIER ::= { configuration 2}

	-- The mibmfrProfile table
	--
	-- This table contains parameters for the mibmfrProfile profile
	--

    mibmfrProfileTable	OBJECT-TYPE
	SYNTAX		SEQUENCE OF MibmfrProfileEntry
	ACCESS		not-accessible
	STATUS		mandatory
	DESCRIPTION	"A list of mibmfrProfile profile entries."
	::= { mibmfrProfile 1 }

    mibmfrProfileEntry	OBJECT-TYPE
	SYNTAX		MibmfrProfileEntry
	ACCESS		not-accessible
	STATUS		mandatory
	DESCRIPTION	"A mibmfrProfile entry containing objects that
			 maps to the parameters of mibmfrProfile profile."
	INDEX		{ mfrProfile-MfrBundleName }
	::= { mibmfrProfileTable 1 }

    MibmfrProfileEntry ::=
	SEQUENCE {
	    mfrProfile-MfrBundleName
		DisplayString,
	    mfrProfile-Active
		INTEGER,
	    mfrProfile-MfrBundleType
		INTEGER,
	    mfrProfile-MaxBundleMembers
		INTEGER,
	    mfrProfile-MinBandwidth
		INTEGER,
	    mfrProfile-Action-o
		INTEGER
	}

    mfrProfile-MfrBundleName	OBJECT-TYPE
	SYNTAX	DisplayString
	ACCESS	read-only
	STATUS	mandatory
	DESCRIPTION	"Name of the multi-link frame-relay profile."
	::= { mibmfrProfileEntry 1 }

    mfrProfile-Active	OBJECT-TYPE
	SYNTAX	INTEGER {
		    no (1),
		    yes (2)
		}
	ACCESS	read-write
	STATUS	mandatory
	DESCRIPTION	"Indicates whether this profile is to be included in the mfrv table."
	::= { mibmfrProfileEntry 2 }

    mfrProfile-MfrBundleType	OBJECT-TYPE
	SYNTAX	INTEGER {
		    mfrDte (1)
		}
	ACCESS	read-write
	STATUS	mandatory
	DESCRIPTION	"Type of MFR bundling to be used, currently only DTE_DTE supported."
	::= { mibmfrProfileEntry 3 }

    mfrProfile-MaxBundleMembers	OBJECT-TYPE
	SYNTAX	INTEGER
	ACCESS	read-write
	STATUS	mandatory
	DESCRIPTION	"The maximum number of links allowed on this bundle."
	::= { mibmfrProfileEntry 4 }

    mfrProfile-MinBandwidth	OBJECT-TYPE
	SYNTAX	INTEGER
	ACCESS	read-write
	STATUS	mandatory
	DESCRIPTION	"The minimum bandwidth allowed for an active bundle."
	::= { mibmfrProfileEntry 5 }

    mfrProfile-Action-o	OBJECT-TYPE
	SYNTAX	INTEGER {
		    noAction (1),
		    createProfile (2),
		    deleteProfile (3)
		}
	ACCESS	read-write
	STATUS	mandatory
	DESCRIPTION	""
	::= { mibmfrProfileEntry 6 }


	-- The mibframeRelayProfile table
	--
	-- This table contains parameters for the mibframeRelayProfile profile
	--

    mibframeRelayProfileTable	OBJECT-TYPE
	SYNTAX		SEQUENCE OF MibframeRelayProfileEntry
	ACCESS		not-accessible
	STATUS		mandatory
	DESCRIPTION	"A list of mibframeRelayProfile profile entries."
	::= { mibframeRelayProfile 1 }

    mibframeRelayProfileEntry	OBJECT-TYPE
	SYNTAX		MibframeRelayProfileEntry
	ACCESS		not-accessible
	STATUS		mandatory
	DESCRIPTION	"A mibframeRelayProfile entry containing objects that
			 maps to the parameters of mibframeRelayProfile profile."
	INDEX		{ frameRelayProfile-FrName }
	::= { mibframeRelayProfileTable 1 }

    MibframeRelayProfileEntry ::=
	SEQUENCE {
	    frameRelayProfile-FrName
		DisplayString,
	    frameRelayProfile-Active
		INTEGER,
	    frameRelayProfile-NailedUpGroup
		INTEGER,
	    frameRelayProfile-NailedMode
		INTEGER,
	    frameRelayProfile-CalledNumberType
		INTEGER,
	    frameRelayProfile-SwitchedCallType
		INTEGER,
	    frameRelayProfile-PhoneNumber
		DisplayString,
	    frameRelayProfile-BillingNumber
		DisplayString,
	    frameRelayProfile-TransitNumber
		DisplayString,
	    frameRelayProfile-CallByCallId
		INTEGER,
	    frameRelayProfile-LinkMgmt
		INTEGER,
	    frameRelayProfile-LinkType
		INTEGER,
	    frameRelayProfile-N391Val
		INTEGER,
	    frameRelayProfile-N392Val
		INTEGER,
	    frameRelayProfile-N393Val
		INTEGER,
	    frameRelayProfile-T391Val
		INTEGER,
	    frameRelayProfile-T392Val
		INTEGER,
	    frameRelayProfile-oMRU
		INTEGER,
	    frameRelayProfile-DceN392Val
		INTEGER,
	    frameRelayProfile-DceN393Val
		INTEGER,
	    frameRelayProfile-LinkMgmtDlci
		INTEGER,
	    frameRelayProfile-MfrBundleName
		DisplayString,
	    frameRelayProfile-Frf5Options-Enable
		INTEGER,
	    frameRelayProfile-Frf5Options-Vpi
		INTEGER,
	    frameRelayProfile-Frf5Options-Vci
		INTEGER,
	    frameRelayProfile-Frf5Options-Shaper
		INTEGER,
	    frameRelayProfile-SvcOptions-Enabled
		INTEGER,
	    frameRelayProfile-SvcOptions-FrAddress
		DisplayString,
	    frameRelayProfile-FastPathEnabled
		INTEGER,
	    frameRelayProfile-Action-o
		INTEGER
	}

    frameRelayProfile-FrName	OBJECT-TYPE
	SYNTAX	DisplayString
	ACCESS	read-only
	STATUS	mandatory
	DESCRIPTION	"Name of the frame-relay profile."
	::= { mibframeRelayProfileEntry 1 }

    frameRelayProfile-Active	OBJECT-TYPE
	SYNTAX	INTEGER {
		    no (1),
		    yes (2)
		}
	ACCESS	read-write
	STATUS	mandatory
	DESCRIPTION	"Indicates whether this profile is to be included in the frame relay table."
	::= { mibframeRelayProfileEntry 2 }

    frameRelayProfile-NailedUpGroup	OBJECT-TYPE
	SYNTAX	INTEGER
	ACCESS	read-write
	STATUS	mandatory
	DESCRIPTION	"nailed group number."
	::= { mibframeRelayProfileEntry 3 }

    frameRelayProfile-NailedMode	OBJECT-TYPE
	SYNTAX	INTEGER {
		    off (1),
		    ft1 (2),
		    ft1Mpp (3),
		    bri (4),
		    ft1Bo (5),
		    dChan (6),
		    aodi (7),
		    megamax (8)
		}
	ACCESS	read-write
	STATUS	mandatory
	DESCRIPTION	"Specifies whether it is a nailed or switched link."
	::= { mibframeRelayProfileEntry 4 }

    frameRelayProfile-CalledNumberType	OBJECT-TYPE
	SYNTAX	INTEGER
	ACCESS	read-write
	STATUS	mandatory
	DESCRIPTION	"The 'type' of number given in the field 'phone-number' -- national, international, etc.."
	::= { mibframeRelayProfileEntry 5 }

    frameRelayProfile-SwitchedCallType	OBJECT-TYPE
	SYNTAX	INTEGER {
		    voice (1),
		    n-56kRestricted (2),
		    n-64kClear (3),
		    n-64kRestricted (4),
		    n-56kClear (5),
		    n-384kRestricted (6),
		    n-384kClear (7),
		    n-1536kClear (8),
		    n-1536kRestricted (9),
		    n-128kClear (10),
		    n-192kClear (11),
		    n-256kClear (12),
		    n-320kClear (13),
		    dws384Clear (14),
		    n-448Clear (15),
		    n-512Clear (16),
		    n-576Clear (17),
		    n-640Clear (18),
		    n-704Clear (19),
		    n-768Clear (20),
		    n-832Clear (21),
		    n-896Clear (22),
		    n-960Clear (23),
		    n-1024Clear (24),
		    n-1088Clear (25),
		    n-1152Clear (26),
		    n-1216Clear (27),
		    n-1280Clear (28),
		    n-1344Clear (29),
		    n-1408Clear (30),
		    n-1472Clear (31),
		    n-1600Clear (32),
		    n-1664Clear (33),
		    n-1728Clear (34),
		    n-1792Clear (35),
		    n-1856Clear (36),
		    n-1920Clear (37),
		    x30RestrictedBearer (39),
		    v110ClearBearer (40),
		    n-64kX30Restricted (41),
		    n-56kV110Clear (42),
		    modem (43),
		    atmodem (44),
		    n-2456kV110 (46),
		    n-4856kV110 (47),
		    n-9656kV110 (48),
		    n-19256kV110 (49),
		    n-38456kV110 (50),
		    n-2456krV110 (51),
		    n-4856krV110 (52),
		    n-9656krV110 (53),
		    n-19256krV110 (54),
		    n-38456krV110 (55),
		    n-2464kV110 (56),
		    n-4864kV110 (57),
		    n-9664kV110 (58),
		    n-19264kV110 (59),
		    n-38464kV110 (60),
		    n-2464krV110 (61),
		    n-4864krV110 (62),
		    n-9664krV110 (63),
		    n-19264krV110 (64),
		    n-38464krV110 (65),
		    v32 (66),
		    phs64k (67),
		    voiceOverIp (68),
		    atmSvc (70),
		    frameRelaySvc (71),
		    vpnTunnel (72),
		    wormarq (73),
		    n-14456kV110 (74),
		    n-28856kV110 (75),
		    n-14456krV110 (76),
		    n-28856krV110 (77),
		    n-14464kV110 (78),
		    n-28864kV110 (79),
		    n-14464krV110 (80),
		    n-28864krV110 (81),
		    modem31khzAudio (82),
		    x25Svc (83),
		    n-144kClear (255),
		    iptoip (263)
		}
	ACCESS	read-write
	STATUS	mandatory
	DESCRIPTION	"Type of bearer channel capability to set up for each switched call in the session."
	::= { mibframeRelayProfileEntry 6 }

    frameRelayProfile-PhoneNumber	OBJECT-TYPE
	SYNTAX	DisplayString
	ACCESS	read-write
	STATUS	mandatory
	DESCRIPTION	"The phonenumber of the named host."
	::= { mibframeRelayProfileEntry 7 }

    frameRelayProfile-BillingNumber	OBJECT-TYPE
	SYNTAX	DisplayString
	ACCESS	read-write
	STATUS	mandatory
	DESCRIPTION	"A number used for billing purposes."
	::= { mibframeRelayProfileEntry 8 }

    frameRelayProfile-TransitNumber	OBJECT-TYPE
	SYNTAX	DisplayString
	ACCESS	read-write
	STATUS	mandatory
	DESCRIPTION	"The string for use in the 'transit network ie' for PRI calling when going through a LEC."
	::= { mibframeRelayProfileEntry 9 }

    frameRelayProfile-CallByCallId	OBJECT-TYPE
	SYNTAX	INTEGER
	ACCESS	read-write
	STATUS	mandatory
	DESCRIPTION	"Id for the call-by-call signalling for PRI."
	::= { mibframeRelayProfileEntry 11 }

    frameRelayProfile-LinkMgmt	OBJECT-TYPE
	SYNTAX	INTEGER {
		    none (1),
		    ansiT1617d (2),
		    ccittQ933a (3)
		}
	ACCESS	read-write
	STATUS	mandatory
	DESCRIPTION	"Link Management Interface to use on this link."
	::= { mibframeRelayProfileEntry 10 }

    frameRelayProfile-LinkType	OBJECT-TYPE
	SYNTAX	INTEGER {
		    dte (1),
		    dce (2),
		    nni (3)
		}
	ACCESS	read-write
	STATUS	mandatory
	DESCRIPTION	"Datalink link management type (DTE, DCE, or NNI)."
	::= { mibframeRelayProfileEntry 12 }

    frameRelayProfile-N391Val	OBJECT-TYPE
	SYNTAX	INTEGER
	ACCESS	read-write
	STATUS	mandatory
	DESCRIPTION	"Interval for requesting status report."
	::= { mibframeRelayProfileEntry 13 }

    frameRelayProfile-N392Val	OBJECT-TYPE
	SYNTAX	INTEGER
	ACCESS	read-write
	STATUS	mandatory
	DESCRIPTION	"Error threshold count."
	::= { mibframeRelayProfileEntry 14 }

    frameRelayProfile-N393Val	OBJECT-TYPE
	SYNTAX	INTEGER
	ACCESS	read-write
	STATUS	mandatory
	DESCRIPTION	"Monitered events count."
	::= { mibframeRelayProfileEntry 15 }

    frameRelayProfile-T391Val	OBJECT-TYPE
	SYNTAX	INTEGER
	ACCESS	read-write
	STATUS	mandatory
	DESCRIPTION	"Timer for link integrity verification."
	::= { mibframeRelayProfileEntry 16 }

    frameRelayProfile-T392Val	OBJECT-TYPE
	SYNTAX	INTEGER
	ACCESS	read-write
	STATUS	mandatory
	DESCRIPTION	"Timer for status enquiry."
	::= { mibframeRelayProfileEntry 17 }

    frameRelayProfile-oMRU	OBJECT-TYPE
	SYNTAX	INTEGER
	ACCESS	read-write
	STATUS	mandatory
	DESCRIPTION	"Maximum Receive Unit, i.e. the largest frame we will accept."
	::= { mibframeRelayProfileEntry 18 }

    frameRelayProfile-DceN392Val	OBJECT-TYPE
	SYNTAX	INTEGER
	ACCESS	read-write
	STATUS	mandatory
	DESCRIPTION	"Error threshold count."
	::= { mibframeRelayProfileEntry 19 }

    frameRelayProfile-DceN393Val	OBJECT-TYPE
	SYNTAX	INTEGER
	ACCESS	read-write
	STATUS	mandatory
	DESCRIPTION	"Monitered events count."
	::= { mibframeRelayProfileEntry 20 }

    frameRelayProfile-LinkMgmtDlci	OBJECT-TYPE
	SYNTAX	INTEGER {
		    dlci0 (1),
		    dlci1023 (1024)
		}
	ACCESS	read-write
	STATUS	mandatory
	DESCRIPTION	"Dlci number to use for link management (0 or 1023)."
	::= { mibframeRelayProfileEntry 21 }

    frameRelayProfile-MfrBundleName	OBJECT-TYPE
	SYNTAX	DisplayString
	ACCESS	read-write
	STATUS	mandatory
	DESCRIPTION	"Name of the multi-link frame-relay profile."
	::= { mibframeRelayProfileEntry 24 }

    frameRelayProfile-Frf5Options-Enable	OBJECT-TYPE
	SYNTAX	INTEGER {
		    no (1),
		    yes (2)
		}
	ACCESS	read-write
	STATUS	mandatory
	DESCRIPTION	"Enable or disable the FRF.5."
	::= { mibframeRelayProfileEntry 27 }

    frameRelayProfile-Frf5Options-Vpi	OBJECT-TYPE
	SYNTAX	INTEGER
	ACCESS	read-write
	STATUS	mandatory
	DESCRIPTION	"The VPI of this connection."
	::= { mibframeRelayProfileEntry 28 }

    frameRelayProfile-Frf5Options-Vci	OBJECT-TYPE
	SYNTAX	INTEGER
	ACCESS	read-write
	STATUS	mandatory
	DESCRIPTION	"The VCI of this connection."
	::= { mibframeRelayProfileEntry 29 }

    frameRelayProfile-Frf5Options-Shaper	OBJECT-TYPE
	SYNTAX	INTEGER
	ACCESS	read-write
	STATUS	mandatory
	DESCRIPTION	"Assigned Traffic shaper to this connection."
	::= { mibframeRelayProfileEntry 30 }

    frameRelayProfile-SvcOptions-Enabled	OBJECT-TYPE
	SYNTAX	INTEGER {
		    no (1),
		    yes (2)
		}
	ACCESS	read-write
	STATUS	mandatory
	DESCRIPTION	"Frame Relay signalling is enabled on ths link."
	::= { mibframeRelayProfileEntry 25 }

    frameRelayProfile-SvcOptions-FrAddress	OBJECT-TYPE
	SYNTAX	DisplayString
	ACCESS	read-write
	STATUS	mandatory
	DESCRIPTION	"Frame Relay Link SVC address."
	::= { mibframeRelayProfileEntry 26 }

    frameRelayProfile-FastPathEnabled	OBJECT-TYPE
	SYNTAX	INTEGER {
		    no (1),
		    yes (2)
		}
	ACCESS	read-write
	STATUS	mandatory
	DESCRIPTION	"Set if this frame relay link will be used to carry voice packets destined to this tnt."
	::= { mibframeRelayProfileEntry 31 }

    frameRelayProfile-Action-o	OBJECT-TYPE
	SYNTAX	INTEGER {
		    noAction (1),
		    createProfile (2),
		    deleteProfile (3)
		}
	ACCESS	read-write
	STATUS	mandatory
	DESCRIPTION	""
	::= { mibframeRelayProfileEntry 22 }

END
