--

-- Copyright (c) 1993 Chipcom Corporation.  All Rights Reserved.
--
-- Reproduction of this document is authorized on condition that this
-- copyright notice is included.  This SNMP MIB Specification
-- embodies proprietary intellectual property.  The copyright
-- retains all title and ownership in the specification, including any
-- revisions. 
--
-- It is the intent to encourage the widespread use of this
-- specification in connection with the management of our
-- products. The copyright grants vendor, end-users, and other interested
-- parties a non-exclusive license to use this specification in
-- connection with the management of our products.
--
-- This specification is supplied "AS IS," and no
-- warranty, either express or implied, as to the use, operation,
-- condition, or performance of the specification, is made.
--
-- Copyright text courtesy of Dave Perkins.
--
-- The right to change this MIB without notification is retained.
--


--
-- If you have any questions about this MIB, please call your
-- Technical Support Center, or call 1-800-228-6840.
--

--
-- MIB Version Information:
--
-- Version     Description
------------------------------------------------------------------
--   v1.0      Initial version of the chipmib02 branch.
--   v2.0      Version tracking initiated.
--   v2.1      Version release with TRMM v.2.10
--
-- 

--
-- Agents supporting this MIB:
--	Ethernet Management Module, Software rev: v3.2
--	Ethernet to Ethernet Bridge Module, Software Rev: v2.12
--	Ethernet to Ethernet Bridge Box, Software Rev: v2.12
--	Token Ring Management Module, Software Rev: v2.1
--	Ethernet Interconnect Module, Software Rev: v1.0
--


CHIPCONC-MIB DEFINITIONS ::= BEGIN

IMPORTS
	enterprises, NetworkAddress, IpAddress,
	Counter, Gauge, TimeTicks, DisplayString
		FROM RFC1155-SMI
	OBJECT-TYPE
		FROM RFC-1212;

-- All representations of MAC addresses in this MIB Module use,
-- as a textual convention (i.e. this convention does not affect
-- their encoding), the data type:

MacAddress ::= OCTET STRING (SIZE (6))    -- a 6 octet address in
                                          -- the "canonical" order
-- defined by IEEE 802.1a, i.e., as if it were transmitted least
-- significant bit first, even though 802.5 (in contrast to other
-- 802.x protocols) requires MAC addresses to be transmitted most
-- significant bit first.
--
-- 16-bit addresses, if needed, are represented by setting their
-- upper 4 octets to all 0's, i.e., AAFF would be represented
-- as 00000000AAFF.


chipcom     	OBJECT IDENTIFIER ::= { enterprises 49 }

chipmib02 	OBJECT IDENTIFIER ::= { chipcom 2 }

--
-- Top level groups
--

chipGen    	OBJECT IDENTIFIER ::= { chipmib02 1 }
chipEcho   	OBJECT IDENTIFIER ::= { chipmib02 2 }
chipProducts   	OBJECT IDENTIFIER ::= { chipmib02 3 }
chipExperiment  OBJECT IDENTIFIER ::= { chipmib02 4 }
chipTTY	        OBJECT IDENTIFIER ::= { chipmib02 5 }
chipTFTP	OBJECT IDENTIFIER ::= { chipmib02 6 }
chipDownload	OBJECT IDENTIFIER ::= { chipmib02 7 }


--
-- Product specific branches.  Also used for sysObjectID.
--

online        	OBJECT IDENTIFIER ::= { chipProducts 1 }
oebm 	      	OBJECT IDENTIFIER ::= { chipProducts 2 }

midnight      	OBJECT IDENTIFIER ::= { chipProducts 3 }
workGroupHub    OBJECT IDENTIFIER ::= { chipProducts 4 }

emm		OBJECT IDENTIFIER ::= { chipProducts 5 }
chipBridge	OBJECT IDENTIFIER ::= { chipProducts 6 }
trmm		OBJECT IDENTIFIER ::= { chipProducts 7 }
fmm		OBJECT IDENTIFIER ::= { chipProducts 8 }
focus1		OBJECT IDENTIFIER ::= { chipProducts 9 }
oeim    	OBJECT IDENTIFIER ::= { chipProducts 10 }





--
-- Experimental Branches
--
-- When RFCs are still in the experimental stage, the MIB
-- is incorporated under the enterprise experimental branch
-- so that changes in the experimental MIB do not affect
-- the released product.  
--
-- As the RFC becomes standard and support is provided by the agents,
-- the support under this branch will be moved to the appropriate
-- standard branch.  That is, the support under this branch
-- for the MIB in question will be removed.
--

chipExpTokenRing OBJECT IDENTIFIER ::= { chipExperiment 1 }
dot1dBridge	OBJECT IDENTIFIER ::= { chipExperiment 14 }

dot5		OBJECT IDENTIFIER ::= { chipExpTokenRing 1}

--
-- ONline Groups 
--

olAgents   	OBJECT IDENTIFIER ::= { online   1 }
olConc    	OBJECT IDENTIFIER ::= { online   2 }
olEnv     	OBJECT IDENTIFIER ::= { online   3 }
olModules 	OBJECT IDENTIFIER ::= { online   4 }
olNets   	OBJECT IDENTIFIER ::= { online   5 }
olGroups   	OBJECT IDENTIFIER ::= { online   6 }
olAlarm   	OBJECT IDENTIFIER ::= { online   7 }

--
-- Value added module attributes 
--

olSpecMods	OBJECT IDENTIFIER ::= { olModules 4 }

--
-- A node for each module type  :
--

ol50nnMCTL  	OBJECT IDENTIFIER ::= { olSpecMods 3 }
ol51nnMMGT  	OBJECT IDENTIFIER ::= { olSpecMods 4 }
ol51nnMFIB  	OBJECT IDENTIFIER ::= { olSpecMods 5 }
ol51nnMUTP  	OBJECT IDENTIFIER ::= { olSpecMods 6 }
ol51nnMTP   	OBJECT IDENTIFIER ::= { olSpecMods 7 }
ol51nnMBNC  	OBJECT IDENTIFIER ::= { olSpecMods 8 }
ol51nnBEE   	OBJECT IDENTIFIER ::= { olSpecMods 9 }
ol51nnRES   	OBJECT IDENTIFIER ::= { olSpecMods 10 }
ol51nnREE   	OBJECT IDENTIFIER ::= { olSpecMods 11 }
ol51nnMAUIF 	OBJECT IDENTIFIER ::= { olSpecMods 12 }
ol51nnMAUIM 	OBJECT IDENTIFIER ::= { olSpecMods 13 }
ol5208MTP   	OBJECT IDENTIFIER ::= { olSpecMods 14 }
ol51nnMFP   	OBJECT IDENTIFIER ::= { olSpecMods 15 }
ol51nnMFBP  	OBJECT IDENTIFIER ::= { olSpecMods 16 }
ol51nnMTPL  	OBJECT IDENTIFIER ::= { olSpecMods 17 }
ol51nnMTPPL 	OBJECT IDENTIFIER ::= { olSpecMods 18 }
ol52nnMTP   	OBJECT IDENTIFIER ::= { olSpecMods 19 }
ol52nnMFR   	OBJECT IDENTIFIER ::= { olSpecMods 20 }
ol51nnMTS   	OBJECT IDENTIFIER ::= { olSpecMods 21 }
ol51nnMFL   	OBJECT IDENTIFIER ::= { olSpecMods 22 }
ol50nnMRCTL 	OBJECT IDENTIFIER ::= { olSpecMods 23 }
ol51nnMFB   	OBJECT IDENTIFIER ::= { olSpecMods 24 }
ol53nnMMGT  	OBJECT IDENTIFIER ::= { olSpecMods 25 }
ol53nnMFBMIC	OBJECT IDENTIFIER ::= { olSpecMods 26 }
ol53nnMFIBST	OBJECT IDENTIFIER ::= { olSpecMods 27 }
ol53nnMSTP  	OBJECT IDENTIFIER ::= { olSpecMods 28 }
ol51nnMTPCL 	OBJECT IDENTIFIER ::= { olSpecMods 29 }
ol52nnBTT 	OBJECT IDENTIFIER ::= { olSpecMods 30 }
ol51nnIx 	OBJECT IDENTIFIER ::= { olSpecMods 31 }
ol52nnMMGT  	OBJECT IDENTIFIER ::= { olSpecMods 32 }
ol50nnMHCTL 	OBJECT IDENTIFIER ::= { olSpecMods 33 }













--
-- Networking groups
--

olNet		OBJECT IDENTIFIER ::= { olNets 1 }
olEnet		OBJECT IDENTIFIER ::= { olNets 2 }
olTRnet 	OBJECT IDENTIFIER ::= { olNets 3 }
olFDDInet 	OBJECT IDENTIFIER ::= { olNets 4 }


--
-- Workgroup Hub
--

hubSysGroup        OBJECT IDENTIFIER ::= { workGroupHub 1 }
hardwareGroup      OBJECT IDENTIFIER ::= { workGroupHub 2 }
softwareGroup      OBJECT IDENTIFIER ::= { workGroupHub 3 }
hubGroup           OBJECT IDENTIFIER ::= { workGroupHub 4 }
boardGroup         OBJECT IDENTIFIER ::= { workGroupHub 5 }
portGroup          OBJECT IDENTIFIER ::= { workGroupHub 6 }
alarmGroup         OBJECT IDENTIFIER ::= { workGroupHub 7 }


--
-- Threshold group
--

olThresh	OBJECT IDENTIFIER ::= { olAlarm 1 }

olThreshControl	OBJECT IDENTIFIER ::= { olThresh 1 }



-- The ONline Concentrator Groups:
-- 
-- The following groups are specific to the Concentrator product family.
--

-- The olAgents Group:

-- This group is mandatory for all agents that exist in the concentrator.
--
-- The master management module(s) indicate all of the other SNMP agents
-- present in the concentrator.  The olAgents group is also used
-- by each agent to indicate his own agent status, whether master or not.
--

olAgentsMySlot OBJECT-TYPE
	SYNTAX INTEGER
	ACCESS read-only
	STATUS mandatory
	DESCRIPTION
		"The slot id of this agent."
	::= { olAgents 1 }

olAgentsMasterReset OBJECT-TYPE
	SYNTAX  INTEGER {
		noReset(1),
		reset(2)
		}
	ACCESS read-write
	STATUS mandatory
	DESCRIPTION
		"Resetting mastership causes a new mastership election to 
		occur. The agent with the highest mastership priority will
		become the new master.  If there is more than one agent
		with the highest priority, the selection between
		those agents will be arbritrary."
	::= { olAgents 2 }
	
olAgentsTable OBJECT-TYPE
	SYNTAX  SEQUENCE OF OlAgentsEntry
	ACCESS  not-accessible
	STATUS  mandatory
	DESCRIPTION
		"A table of agents in the concentrator as seen by
		this agent.  A master will see all the agents; a slave
		will only see itself."
	::= { olAgents 3 }

olAgentsEntry OBJECT-TYPE
	SYNTAX  OlAgentsEntry
	ACCESS  not-accessible
	STATUS  mandatory
	DESCRIPTION
		"A profile of an agent within the concentrator."
	INDEX 	{ olAgentsSlotIndex }
	::= { olAgentsTable 1 }

OlAgentsEntry ::=
	SEQUENCE {
		olAgentsSlotIndex
			INTEGER,
		olAgentsStationAddr
			OCTET STRING,	
		olAgentsIpAddress
			IpAddress,
		olAgentsMasterStatus
			INTEGER,
		olAgentsMasterPriority
			INTEGER

		}

olAgentsSlotIndex OBJECT-TYPE
	SYNTAX  INTEGER
	ACCESS	read-only
	STATUS	mandatory
	DESCRIPTION
		"The slot number that identifies the referenced agent."
	::= { olAgentsEntry 1 }

olAgentsStationAddr OBJECT-TYPE
	SYNTAX	OCTET STRING (SIZE(6))
	ACCESS	read-only
	STATUS	mandatory
	DESCRIPTION
		"The unique identifier for this agent.  Often this
		is the value of ifPhysAddress for the first interface."
	::= { olAgentsEntry 2 }

olAgentsIpAddress OBJECT-TYPE
	SYNTAX 	IpAddress
	ACCESS	read-only
	STATUS	mandatory
	DESCRIPTION
		"An IP Address that can be used to communicate to 
		this agent.  Note, this object's value may change
		as the agent switches to different sub-networks."
	::= { olAgentsEntry 3 }

olAgentsMasterStatus OBJECT-TYPE
	SYNTAX INTEGER {
		master(1),
		non-master(2), -- slave
		electing(3)
		}
	ACCESS read-only
	STATUS mandatory
	DESCRIPTION
		"The mastership status of this agent."
	::= { olAgentsEntry 4 }

olAgentsMasterPriority OBJECT-TYPE
	SYNTAX INTEGER {
		one(1), 	-- lowest
		two(2),
		three(3),
		four(4),
		five(5),
		six(6),
		seven(7),
		eight(8),
		nine(9),
		ten(10),	-- highest
		never(11)
		}	
	ACCESS read-write
	STATUS mandatory
	DESCRIPTION
		"The mastership priority of this agent.  Ten is the
		highest and one is the lowest.  Never means will not
		be able become master.  Some agents do not have the 
		capability to become master (the etherent to ethernet bridge, 
		e.g.) and setting those agents to a value other than 
		never(11) will generate an invalid value error.  Priority is
		only used when an election occurs.  Mastership is not
		pre-emptive; use the reset mastership command 
		(olAgentsMasterReset)."
	::= { olAgentsEntry 5 } 


			

-- The olConc Group:

-- This group is mandatory for all devices that are acting as a concentrator
-- master.
--
-- The olConc group contains information and control relative to 
-- the concentrator.
--

olConcType OBJECT-TYPE
	SYNTAX INTEGER {
		online-seventeen-slot(1),
		online-six-slot(2),
		online-six-slot-ft(3),   -- 6 slot with flag board
	        online-six-slot-hc(4),   -- 6-slot with hidden controller
		online-six-slot-ft-hc(5) -- 6-slot with both



	}
	ACCESS read-only
	STATUS mandatory
	DESCRIPTION
		"This object identifies the type of concentrator represented
		by this agent."
	::= { olConc 1 }


olConcReset OBJECT-TYPE
	SYNTAX INTEGER {
		noReset(1),
		reset(2)
		}
	ACCESS read-write
	STATUS mandatory
	DESCRIPTION
		"Setting this value to reset(2) causes this concentrator to
		reset. "
	::= { olConc 2 }


olConcNumSlots OBJECT-TYPE
	SYNTAX INTEGER
	ACCESS read-only
	STATUS mandatory
	DESCRIPTION
		"The number of slots in this concentrator.  Note, that
		if a hidden controller is present, the number of slots
		is one more than the number of payload slots (six-slot-hc
		will report 7 slots, for example). The hidden controller
		does not actually occupy a main slot in the 6-slot
		concentrator, but it will report itself as slot 7."
	::= { olConc 3 }

olConcProfile OBJECT-TYPE
	SYNTAX OCTET STRING (SIZE(1..3))
	ACCESS read-only
	STATUS mandatory
	DESCRIPTION
		"A bit string where the least significant bit corresponds to
		slot 1.  A '1' in the bit indicates that a module is present
		in that slot.  The number of octets provided is based on 
		the olConcNumSlots value divided by 8.  Any extra bits
		(for example, bits 18-24 for 17 slots) are meaningless.  

		For example, the string 0x01 0xFF 0xFF would represent 
		a full 17 slot concentrator."
	::= { olConc 4 }

-- The olEnv Group

-- This group represents the concentrator's environment.  It is available
-- from agents that are acting as a concentrator master.

olEnvTempStatus OBJECT-TYPE
	SYNTAX INTEGER {
		okay(1),
		extremeTemp(2)
		}
	ACCESS read-only
	STATUS mandatory
	DESCRIPTION
		"The overall temperature status for this concentrator.
		This object's value is an aggregate of all the temperature
		probes in the concentrator, such that, when at least one probe
		reports	extreme temperature, this object will have the value
		extremeTemp(2)."
	::= { olEnv 1 }

olEnvPSCapacity OBJECT-TYPE
	SYNTAX INTEGER
	ACCESS read-only
	STATUS mandatory
	DESCRIPTION
		"The total capacity of power supplies for this concentrator."
	::= { olEnv 2 }

olEnvPSTable OBJECT-TYPE
	SYNTAX SEQUENCE OF OlEnvPSEntry
	ACCESS not-accessible
	STATUS mandatory
	DESCRIPTION
		"A table that contains information about each potential
		power supply in the concentrator."
	::= { olEnv 3 }


olEnvPSEntry OBJECT-TYPE
	SYNTAX OlEnvPSEntry
	ACCESS not-accessible
	STATUS mandatory
	DESCRIPTION
		"A list of of information for each power supply in the
		concentrator."
	INDEX { olEnvPSIndex }
	::= { olEnvPSTable 1 }

OlEnvPSEntry ::=
	SEQUENCE {
		olEnvPSIndex
			INTEGER,
		olEnvPSAdminState
			INTEGER,
		olEnvPSOperStatus
			INTEGER
		}

olEnvPSIndex OBJECT-TYPE
	SYNTAX INTEGER
	ACCESS read-only
	STATUS mandatory
	DESCRIPTION
		"Identifies the power supply for which this entry contains
		power supply information.  For systems with the
		primary and backup power supply (as opposed to
		the N+1 design), index 1 refers to the primary, 
		and index 2 refers to the backup. "
	::= { olEnvPSEntry 1 }

olEnvPSAdminState OBJECT-TYPE
	SYNTAX INTEGER {
		activate(1),
		standby(2)
		}
	ACCESS read-write
	STATUS mandatory
	DESCRIPTION
		"The current desired state of the power supply.  A power
		supply in standby does not provide power to the concentrator."
	::= { olEnvPSEntry 2 }

olEnvPSOperStatus OBJECT-TYPE
	SYNTAX INTEGER {
		active(1),
		standby(2),
		faulty(3),
		not-installed(4)
		}
	ACCESS read-only
	STATUS mandatory
	DESCRIPTION
		"The current operational state of the power supply.  A power
		supply in standby does not provide power to the concentrator."
	::= { olEnvPSEntry 3 }

olEnvFanStatus OBJECT-TYPE
	SYNTAX INTEGER {
		okay(1),
		faulty(3),
		not-installed(4),
		unknown(5)
		}
	ACCESS read-only
	STATUS mandatory
	DESCRIPTION
		"The overall status of the fan(s)."
	::= { olEnv 4 }




-- The olModules group

-- This group represents the information as seen by what is currently known
-- as the concentrator master.  If the module is not a master, this group
-- is not represented.  These tables have dynamic instances, that is, 
-- if the module does not exist in the concentrator, the tables are empty.
-- No excess information is presented.
--


olModTable	 OBJECT-TYPE
	SYNTAX SEQUENCE OF OlModEntry
	ACCESS not-accessible
	STATUS mandatory
	DESCRIPTION
		"A table that contains generic information about every
		module that is present within the concentrator.

		"
	::= { olModules 1 }

olModEntry OBJECT-TYPE
	SYNTAX OlModEntry
	ACCESS not-accessible
	STATUS mandatory
	DESCRIPTION
		"A list of information for each module in the concentrator.

		"
	INDEX { olModSlotIndex }
	::= { olModTable 1 }

OlModEntry ::=
	SEQUENCE {
		olModSlotIndex
			INTEGER,
		olModType
			INTEGER,
		olModClass
			INTEGER,
		olModDescr
			DisplayString,
		olModVersion
			DisplayString,
		olModVendor
			INTEGER,
		olModResetModule
			INTEGER,
		olModConfigToDips
			INTEGER, 
		olModConfigured
			INTEGER,
		olModNetwork
			INTEGER,
		olModNetworkType
			INTEGER,
		olModStatus
			INTEGER,
		olModNumPorts
			INTEGER,
		olModNumTrunks
			INTEGER

		}

olModSlotIndex OBJECT-TYPE
	SYNTAX INTEGER
	ACCESS read-only
	STATUS mandatory
	DESCRIPTION
		"The unique slot number of this module.  Its value ranges
		between 1 and olConcNumSlots and remains constant at
		least from one re-initialization of the entity's network
		management system to the next re-initialization."
	::= { olModEntry 1 }

olModType OBJECT-TYPE
	SYNTAX INTEGER {
		module-unmanageable(1), -- not manageable 
		module-unknown(2),	-- only generically manageable
		module-50nnM-CTL(3),	-- Controller 
		module-51nnM-MGT(4),	-- Ethernet Management
		module-51nnM-FIB(5),	-- Ethernet Fiber
		module-51nnM-UTP(6),	-- Ethernet 10BASE-T
		module-51nnM-TP(7),	-- Ethernet 10BASE-T
		module-51nnM-BNC(8),	-- Ethernet BNC
		module-51nnB-EE(9),	-- OEBM
		module-51nnR-ES(10),	-- Cisco Serial
		module-51nnR-EE(11),	-- Cisco Ethernet
		module-51nnM-AUIF(12),	-- Ethernet AUI Female
		module-51nnM-AUIM(13),	-- Ethernet AUI Male
		module-5208M-TP(14),	-- Token Ring 8-port MAU module
		module-51nnM-FP(15),	-- Ethernet Fiber port switching
		module-51nnM-FBP(16),	-- Ethernet 10BASE-F port switching
		module-51nnM-TPL(17),	-- Ethernet 10BASE-T
		module-51nnM-TPPL(18),  -- Ethernet 10BASE-T port switching
		module-52nnM-TP(19),    -- Token Ring Media Module
		module-52nnM-FR(20),	-- Token Ring FiberOptic Repeater
		module-51nnM-TS(21),	-- Ethernet Terminal Server
		module-51nnM-FL(22),	-- Ethernet FOIRL
		module-50nnM-RCTL(23),	-- Redundant Controller 
		module-51nnM-FB(24),	-- Ethernet 10BASE-F 
                module-53nnM-MGT(25),   -- FDDI managment module (FMM) 
                module-53nnM-FBMIC(26), -- FDDI media w/ ANSI MIC conn.
                module-53nnM-FIBST(27), -- FDDI media w/ ST conn.      
                module-53nnM-STP(28),   -- FDDI over copper
		module-51nnM-TPCL(29), 	-- Ethernet 10BASE-T per-connector
		module-52nnB-TT(30), 	-- Token Ring Bridge
		module-51nnI-x(31), 	-- Ethernet Interconnect Module
		module-52nnM-MGT(32),	-- Token Ring Management
		module-50nnM-HCTL(33)	-- Hidden Controller 











		}
	ACCESS read-only
	STATUS mandatory
	DESCRIPTION
		"The unique type identifier for this module.  This type
		is used to identify the branch in olSpecMods (see below).

		module-unmanageable(1) means that only the following
		objects are valid for this module:
	
			olModSlotIndex			
			olModClass
			olModVersion
			olModVendor
			olModReset
			olModConfigToDips
			olModConfigured

		module-unknown(2) means that all the generic attributes
		are manageable, but there is no olSpecMods branch
		for this module as viewed by this agent."
		::= { olModEntry 2 }

olModClass OBJECT-TYPE
	SYNTAX INTEGER {
		controller(1),
		ethernet-mgmt(2),
		ethernet-media(3),
		ethernet-interconnect(4),
		ethernet-portswitching-media(5),
		token-ring-media(6),
		terminal-server(7),
                fddi-media(8),
		token-ring-mgmt(9),
		ethernet-connswitching-media(10),
		token-ring-interconnect(11),
		fddi-mgmt(12)


		}
	ACCESS read-only
	STATUS mandatory
	DESCRIPTION
		"The class of this module.  Generally speaking, this
		object indicates the kind of module.  Specifically,
		the class identifier specifies the internal representation
		of the module's managed information base."
	::= { olModEntry 3 }

olModDescr OBJECT-TYPE
	SYNTAX DisplayString (SIZE(1..128))
	ACCESS read-only
	STATUS mandatory
	DESCRIPTION
		"A textual string containing information about the module."
	::= { olModEntry 4 }

olModVersion OBJECT-TYPE
	SYNTAX DisplayString (SIZE(1..32))
	ACCESS read-only
	STATUS mandatory
	DESCRIPTION
		"The software version number of this module.  "
	::= { olModEntry 5 }

olModVendor OBJECT-TYPE
	SYNTAX INTEGER {
		chipcom(1),
		cisco(2),
		pilkington(3),
		datability(5),
		ibm(6),
		raycom(7),
		retix(8),
		intellicom(9)
		}
	ACCESS read-only
	STATUS mandatory
	DESCRIPTION
		"The actual manufacturer of this board."
	::= { olModEntry 6 }

olModResetModule OBJECT-TYPE
	SYNTAX INTEGER {
		noReset(1),
		reset(2)
		}
	ACCESS read-write
	STATUS mandatory
	DESCRIPTION
		"Setting this object to reset(2) causes this module to reset."
	::= { olModEntry 7 }

olModConfigToDips OBJECT-TYPE
	SYNTAX INTEGER {
		noConfigure(1),
		configure(2)
		}
	ACCESS read-write
	STATUS mandatory
	DESCRIPTION
		"Setting this object to configure(2) causes this module to 
		configure based on the dip switch settings."
	::= { olModEntry 8 }

olModConfigured OBJECT-TYPE
	SYNTAX INTEGER {
		notConfigured(1),
		configured(2)
		}
	ACCESS read-only
	STATUS mandatory
	DESCRIPTION
		"This object indicates whether this module has already been
		configured.  An unconfigured module is configured to a safe
		state where the network is isolated and the ports are 
		disabled."
	::= { olModEntry 9 }


olModNetwork OBJECT-TYPE
	SYNTAX INTEGER {
		other(1),
		isolated(2),
		port-switching(3),
		front-panel(5),
		ethernet-1(6),		
		ethernet-2(7),
		ethernet-3(8),
		token-ring-1(9),
		token-ring-2(10),
		token-ring-3(11),
		token-ring-4(12),
		token-ring-5(13),
		token-ring-6(14),
		token-ring-7(15),
		fddi-1(16),
		fddi-2(17),
		fddi-3(18),
		fddi-4(19),
		per-connector(20),
		isolated-1(21),		-- for modules with multiple
		isolated-2(22)		-- isolated networks within the module

		}
	ACCESS read-write
	STATUS mandatory
	DESCRIPTION
		"The network that this module is attached to.  If the
		value is other(1) or port-switching(3), setting this object
		to a different value will generate the invalidData error.

		If the value is port-switching(3), manage the networks via
		the olPortNetwork object.

		The value per-connector(20) is returned if the managed 
 		module is a per-connector switchable and the connectors are on 
		different networks.  The connector networks are managed 
		by the objects defined in the olSpecMods branch 
		specified for this module.

		Modules and ports on the same network intercommunicate.
		Setting the module to isolated(2) (or other isolated values), 
		removes this module from the backplane.

		Setting this module to a value that is not the same 
		protocol type will return an invalidData error.

		Setting this module to a value that it does not support
		will return an invalidData error."
	::= { olModEntry 10 }

olModNetworkType OBJECT-TYPE
	SYNTAX INTEGER {
		other(1),	    -- other only
		port-switching(3),  -- use olPortNetwork
		ethernet(5),	    -- ethernet 1-3 or 1-8, isolated 
		token-ring(6),      -- token-ring 1-7, isolated
		fddi(7), 	    -- fddi 1-4, isolated
		serial(8)           -- front or isolated only
		}
	ACCESS read-only
	STATUS mandatory
	DESCRIPTION
		"The network type of this module.  port-switching(3)
		means that the network type differs depending on the 
		port (like the router module). The network type reflects
		the valid values for olModNetwork."
	::= { olModEntry 11 }

olModStatus OBJECT-TYPE
	SYNTAX INTEGER {
		okay(1),
 		fatalError(10),
                booting(20),
                partial-failure(21)
		}
	ACCESS read-only
	STATUS mandatory
	DESCRIPTION
		"The module's status."
	::= { olModEntry 12 }

olModNumPorts OBJECT-TYPE
	SYNTAX INTEGER
	ACCESS read-only
	STATUS mandatory
	DESCRIPTION
		"The number of ports on this module.  Note, ports may be 
		physical ports like 10BASE-T ports, or logical, like 
		the bridge module ports."
	::= { olModEntry 13 }

olModNumTrunks OBJECT-TYPE
	SYNTAX INTEGER
	ACCESS read-only
	STATUS mandatory
	DESCRIPTION
		"The number of trunks on this module.  Note, trunks
		are links that are, by definition, backbone connections.
		Examples of trunks are ring in and ring out ports for
		token ring, and the connections for rings to the backplane."
	::= { olModEntry 14 }



	
--
-- Generic Port Table
--

olPortTable OBJECT-TYPE
	SYNTAX SEQUENCE OF OlPortEntry
	ACCESS not-accessible
	STATUS mandatory
	DESCRIPTION
		"A table that contains generic information about
		each port on each module present within the concentrator."
	::= { olModules 2 }

olPortEntry OBJECT-TYPE
	SYNTAX OlPortEntry
	ACCESS not-accessible
	STATUS mandatory
	DESCRIPTION
		"A list of information about each port in the
		concentrator."
	INDEX { olPortSlotIndex, olPortIndex }
	::= { olPortTable 1}

OlPortEntry ::=
	SEQUENCE {
		olPortSlotIndex
			INTEGER,
		olPortIndex
			INTEGER,
		olPortType
			INTEGER,
		olPortConnector
			INTEGER,
		olPortStatus
			INTEGER,
		olPortAdminState
			INTEGER,
		olPortNetwork
			INTEGER,
		olPortNetworkType
			INTEGER



		}

olPortSlotIndex OBJECT-TYPE
	SYNTAX INTEGER
	ACCESS read-only
	STATUS mandatory
	DESCRIPTION
		"The slot number of this port's module."
	::= { olPortEntry 1 }

olPortIndex OBJECT-TYPE
	SYNTAX INTEGER
	ACCESS read-only
	STATUS mandatory
	DESCRIPTION
		"The port number of this port within this module."
	::= { olPortEntry 2 }

olPortType OBJECT-TYPE
	SYNTAX INTEGER {
		logical(1),	-- oebm's ports for example
		media(2), 	-- normal ports
		virtual(5)	-- oets'  ports for example
		}
	ACCESS read-only
	STATUS mandatory
	DESCRIPTION
		"The type of port.  logical(1) is used to manage
		port resources that may not map directly to physical
		connections.  The OEBM, for example, has two logical
		ports, although those two ports can be assigned to
		different combinations of four physical connections.
		media(2) refers to ports such as those on the 10BASE-T
		module. "
	::= { olPortEntry 3 }
		
		
olPortConnector OBJECT-TYPE
	SYNTAX INTEGER {
		backPlane(1),	-- connects directly to backplane
		bnc(2),		-- thinnet
		faui(3),	-- female aui
		maui(4),	-- male aui
		fiber(5),	-- fiber connector
		db-50(6),	-- serial port
		telco(7),	-- 50 pin connector
		rj45(8),	-- unshielded
		rj45S(9),	-- shielded
		db-9(10),	-- 9 pin connector
		virtual(11),	-- e.g. terminal server port
                fddi-lc(12),    -- low cost connector   
                fddi-st(13),    -- ST type connector    
		fddi-mic(14)	-- MIC connector
		}
	ACCESS read-only
	STATUS mandatory
	DESCRIPTION
		"The connector type of this port."
	::= { olPortEntry 4 }

olPortStatus OBJECT-TYPE
	SYNTAX INTEGER {
		okay(1),
		linkFailure(2),
		jabber(3),
		remoteLinkFailure(4),
		remoteJabber(5),
		invalidData(6),
		lowLight(7),
		fifoOverrun(8),
		fifoUnderrun(9),
		fatalError(10),
		partition(11),
		mjlp(12),
		noCable(13),
		noSquelch(14),
		noPhantom(15),
	        okay-standby(19),
                off(22),                
                connecting(23),
                backup-link(24),
		security-breach(25),
		unknownStatus(26),
		beacon(27),
		wireFault(28),
		macRemoved(29),
		notInserted(30),
		speedMismatch(31)
		}
	ACCESS read-only
	STATUS mandatory
	DESCRIPTION
		"The status of this port."
	::= { olPortEntry 5 }

olPortAdminState OBJECT-TYPE
	SYNTAX INTEGER {
		enabled(1),	      -- only valid value for class 2&4 modules
		disabled(2),
		redundant-primary(3), -- use olSpecMods to set
		redundant-backup(4),  -- redundancy buddys
		redundant-rfs(5),     -- used by FOIRL only 
		local(6),	      -- terminal server only
		remote(7),	      -- terminal server only
		remote-diagnostics(8),
		unknown(9)
		}
	ACCESS read-write
	STATUS mandatory
	DESCRIPTION
		"The desired state of this port.  Setting a port to be
		redundant-primary(3) or redundant-backup requires that the
		buddy slot and buddy port also be set to valid values
		(see appropriate olSpecMods objects).  If the 
		values associated with the redundant buddys
		are not valid, a genError will be returned.  If the port
		is already redundant, an invalid set may result in both
		ports being disabled."
	::= { olPortEntry 6 }

olPortNetwork OBJECT-TYPE
	SYNTAX INTEGER {
		other(1),
		isolated(2),
		per-module(4),
		front-panel(5),
		ethernet-1(6),
		ethernet-2(7),
		ethernet-3(8),
		token-ring-1(9),
		token-ring-2(10),
		token-ring-3(11),
		token-ring-4(12),
		token-ring-5(13),
		token-ring-6(14),
		token-ring-7(15),
		fddi-1(16),
		fddi-2(17),
		fddi-3(18),
		fddi-4(19),
		per-connector(20),
		isolated-1(21),		-- for modules with multiple
		isolated-2(22)		-- isolated networks within the module

		}
	ACCESS read-write
	STATUS mandatory
	DESCRIPTION
		"The network that this port is attached to.

		If the value of olPortNetwork is per-module(4),
		then use the olModNetwork to manage this port.
		Setting olPortNetwork to a different value in this
		case will generate the invalidData error.

		Setting this port to a value that is not the same protocol 
		type will return invalidData error.  front-panel(5) is used for 
		modules that have a logical port and a physical front 
		connection. An example of this is the Eth2Eth Bridge module.

		Setting this port to a value that it does not support will
		generate an invalidData error."
	::= { olPortEntry 7 }
		
olPortNetworkType OBJECT-TYPE
	SYNTAX INTEGER {
		other(1),	-- other only
		ethernet(5),    -- ethernet 1-3, isolated
		token-ring(6),  -- token ring 1 - 7, isolated
		fddi(7), 	    -- fddi 1-4, isolated
		serial(8)          -- front or isolated only
		}
	ACCESS read-only
	STATUS mandatory
	DESCRIPTION
		"The network type of this port.  The type reflects the
		valid values for olPortNetwork. "
	::= { olPortEntry 8 }



--
-- Trunk Table
-- 

olTrunkTable OBJECT-TYPE
	SYNTAX SEQUENCE OF OlTrunkEntry
	ACCESS not-accessible
	STATUS mandatory
	DESCRIPTION
		"A table that contains generic information about
		each trunk on each module present within the concentrator."
	::= { olModules 3 }

olTrunkEntry OBJECT-TYPE
	SYNTAX OlTrunkEntry
	ACCESS not-accessible
	STATUS mandatory
	DESCRIPTION
		"A list of information about each trunk in the
		concentrator."
	INDEX { olTrunkSlotIndex, olTrunkIndex }
	::= { olTrunkTable 1}

OlTrunkEntry ::=
	SEQUENCE {
		olTrunkSlotIndex
			INTEGER,
		olTrunkIndex
			INTEGER,
		olTrunkType
			INTEGER,
		olTrunkConnector
			INTEGER,
		olTrunkStatus
			INTEGER,
		olTrunkAdminState
			INTEGER,
		olTrunkWrapState
			INTEGER,
		olTrunkNeighbor
			INTEGER
		}

olTrunkSlotIndex OBJECT-TYPE
	SYNTAX INTEGER
	ACCESS read-only
	STATUS mandatory
	DESCRIPTION
		"The slot number of this trunk's module."
	::= { olTrunkEntry 1 }

olTrunkIndex OBJECT-TYPE
	SYNTAX INTEGER
	ACCESS read-only
	STATUS mandatory
	DESCRIPTION
		"The trunk number of this trunk."
	::= { olTrunkEntry 2 }

olTrunkType OBJECT-TYPE
	SYNTAX INTEGER {
		other(1),
		ringIn(3),	-- ring access trunks
		ringOut(4),
		backplaneIn(6), -- backplane access
		backplaneOut(7)
		}
	ACCESS read-only
	STATUS mandatory
	DESCRIPTION
		"The type of trunk. ringIn(3) and ringOut(4) refer to special
		trunks on the token ring protocol type modules."
	::= { olTrunkEntry 3 }
		
		
olTrunkConnector OBJECT-TYPE
	SYNTAX INTEGER {
		backplane(1),
		fiber(5),	-- 
		rj45S(9)	-- shielded
		}
	ACCESS read-only
	STATUS mandatory
	DESCRIPTION
		"The connector type of this trunk."
	::= { olTrunkEntry 4 }

olTrunkStatus OBJECT-TYPE
	SYNTAX INTEGER {
		okay(1),
		linkFailure(2),
		fatalError(10),
		noCable(13),
		noSquelch(14),
		lostLock(16),
		upstreamNeighborLost(17),
		invalidConfig(18),
                beacon(27),
                wireFault(28)
		}
	ACCESS read-only
	STATUS mandatory
	DESCRIPTION
		"The status of this trunk."
	::= { olTrunkEntry 5 }

olTrunkAdminState OBJECT-TYPE
	SYNTAX INTEGER {
		enabled(1),
		disabled(2)
		}
	ACCESS read-write
	STATUS mandatory
	DESCRIPTION
		"The desired state of this trunk.  Enabling a trunk allows
		the trunk to pass network traffic."
	::= { olTrunkEntry 6 }

olTrunkWrapState OBJECT-TYPE
	SYNTAX INTEGER {
		wrapped(1),
		unwrapped(2)
		}
	ACCESS read-only
	STATUS mandatory
	DESCRIPTION
		"The wrap state of this trunk.  A trunk can wrap in 
		response to a network event such as a break in
		the cable."
	::= { olTrunkEntry 7 }	

olTrunkNeighbor OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		external(255)
		}
	ACCESS read-only
	STATUS mandatory
	DESCRIPTION
		"The upstream or downstream neighbor of the trunk."
	::= { olTrunkEntry 8 }	




--
-- olModSummary
--
-- This group was designed to enhance the performance of retrievals of 
-- module related information.  It is specifically targeted for use by
-- closely designed management applications.  It is NOT designed for use 
-- by off the shelf applications and is documented here only for completeness.
-- 
-- The summary group encodes the module information into an octet string
-- that includes the values of each object in the module, port and trunk
-- tables.  This allows fast retrieval of a large amount of information
-- within no more that 17 Get operations, rather than utilizing 17 operations
-- (max) for the modules, and 17 x Number of Ports (max) for the port 
-- information, and 17 x Number of Trunks (max) for the trunk information.
--
-- Users should be aware that this table requires the application to 
-- parse out information and therefore, applications should be sensitive to 
-- the positioning of information within the summary string.
--



olModSummaryTable OBJECT-TYPE
	SYNTAX SEQUENCE OF OlModSummaryEntry
	ACCESS not-accessible
	STATUS mandatory
	DESCRIPTION
		"A table of condensed module information."
	::= { olModules 5 }

olModSummaryEntry OBJECT-TYPE
	SYNTAX OlModSummaryEntry
	ACCESS not-accessible
	STATUS mandatory
	DESCRIPTION
		"A summary of all the generic and value added information
		associated with this module."
	INDEX { olModSummarySlotIndex }
	::= { olModSummaryTable 1 }

OlModSummaryEntry ::= 
	SEQUENCE {
		olModSummarySlotIndex
			INTEGER,
		olModSummaryInfo
			OCTET STRING
		}

olModSummarySlotIndex OBJECT-TYPE
	SYNTAX INTEGER
	ACCESS read-only
	STATUS mandatory
	DESCRIPTION
		"The slot number of this module that this summary
		pertains to."
	::= { olModSummaryEntry 1 }

olModSummaryInfo OBJECT-TYPE
	SYNTAX OCTET STRING (SIZE(0..512))
	ACCESS read-only
	STATUS mandatory
	DESCRIPTION
		"A summary of all information relating to this module in 
		condensed format.  The condensed format is only as large
		as needed to hence the largest value which usually is one
		octet.  The TCP port for the terminal server, however,
		uses 4 octets.

		The summary consists of a header, a module portion, a port
		portion, and a trunk portion.  Each portion consists of 
		generic information and module specific information. 
		For example, the module information consists of the 
		olModTable entry for this slot and the olSpecMods module
		table information for this module type for this slot.


		---------------------------------------------------
		The header consists of the following octets:
			Version of structure : 1

			Number of octets in generic module 
			Number of octets in specific module
			Number of octets in generic port
			Number of octets in specific port
			Number of octets in generic trunk
			Number of octets in specific trunk

		The format of the data portion is as follows:
		
			Some of the olModTable:
				olModType
				olModClass
				olModDescr
				olModVersion
				olModNetwork
				olModNetworkType
				olModStatus

				olModNumPorts
				olModNumTrunks

			olSpecMods module table (for this module)
				Not including slot number.

		For each port:
			Some of the olPortTable:
				olPortType
				olPortConnector
				olPortStatus  
				olPortAdminState
				olPortNetwork
				olPortNetworkType
	
			olSpecMods port table (for this port's module)
				Not including slot and port number.

		For each trunk:
			Some of the olTrunkTable:
				olTrunkType
				olTrunkConnector
				olTrunkStatus
				olTrunkAdminState
				olTrunkWrapState
				olTrunkNeighbor

			olSpecMods trunk table (for this trunk's module)
				Not including slot and trunk number.



		In all of the above, the index for all of these tables
		is condensed out of the summary. "
	::= { olModSummaryEntry 2 }






-- The olGroups group

-- These objects define ports which have been assigned to groups and actions
-- which can be performed on the groups.  To add ports to a group, 
-- olGroupSetAction should be set to add-ports(1) and the port(s) defined
-- by olGroupSetSlotIndex and olGroupSetPortIndex will be added to the group 
-- olGroupSetGroupID, if the port exists and is not a logical port.  To remove 
-- ports from a group, olGroupSetAction should be set to delete-ports(2) and 
-- the port(s) defined by olGroupSetSlotIndex and olGroupSetPortIndex will be 
-- removed from the group olGroupSetGroupID.   To change the admin state of 
-- all ports in the group, olGroupSetAction should be set to 
-- set-admin-state(3) and the ports in group olGroupSetGroupID will be set 
-- to the state defined in olGroupSetAdminState.

olGroupPortTable OBJECT-TYPE
	SYNTAX SEQUENCE OF OlGroupPortEntry
	ACCESS not-accessible
	STATUS mandatory
	DESCRIPTION
		"A list of groups that each port is in. Each port can
		can be in 0, 1, or many groups."
	::= { olGroups 1 }

olGroupPortEntry OBJECT-TYPE
	SYNTAX OlGroupPortEntry
	ACCESS not-accessible
	STATUS mandatory
	DESCRIPTION
		"The groups corresponding to a particular port."
	INDEX { olGroupPortSlotIndex, olGroupPortIndex }
	::= { olGroupPortTable 1 }

OlGroupPortEntry ::=
	SEQUENCE {
		olGroupPortSlotIndex
			INTEGER,
		olGroupPortIndex
			INTEGER,
		olGroupPortGroupID
			OCTET STRING
		}

olGroupPortSlotIndex OBJECT-TYPE
	SYNTAX INTEGER 
	ACCESS read-only
	STATUS mandatory
	DESCRIPTION
		"The slot number that contains this port."
	::= { olGroupPortEntry 1 }

olGroupPortIndex OBJECT-TYPE
	SYNTAX INTEGER 
	ACCESS read-only
	STATUS mandatory
	DESCRIPTION
		"The port number within this slot. Logical ports
		can not be put into groups."
	::= { olGroupPortEntry 2 }

olGroupPortGroupID OBJECT-TYPE
	SYNTAX OCTET STRING (SIZE(0..8))
	ACCESS read-only
	STATUS mandatory
	DESCRIPTION
		"The group(s) to which the port has been assigned." 
	::= { olGroupPortEntry 3 }


olGroupSummaryTable OBJECT-TYPE
	SYNTAX SEQUENCE OF OlGroupSummaryEntry
	ACCESS not-accessible
	STATUS mandatory
	DESCRIPTION
		"A table of condensed group information listing all the ports
		in each group."
	::= { olGroups 2 }

olGroupSummaryEntry OBJECT-TYPE
	SYNTAX OlGroupSummaryEntry
	ACCESS not-accessible
	STATUS mandatory
	DESCRIPTION
		"The summary of all the ports in a particular group."
	INDEX { olGroupSummaryGroupID, olGroupSummaryIndex }
	::= { olGroupSummaryTable 1 }

OlGroupSummaryEntry ::=
	SEQUENCE {
		olGroupSummaryGroupID
			INTEGER,
		olGroupSummaryIndex
			INTEGER,
		olGroupSummaryPorts
			OCTET STRING
		}

olGroupSummaryGroupID OBJECT-TYPE
	SYNTAX INTEGER {
		group-1(1),
		group-2(2),
		group-3(3),
		group-4(4),
		group-5(5),
		group-6(6),
		group-7(7),
		group-8(8)
		}
	ACCESS read-only
	STATUS mandatory
	DESCRIPTION
		"The group to which the ports have been assigned. A port
		can be in one or more groups."
	::= { olGroupSummaryEntry 1 }

olGroupSummaryIndex OBJECT-TYPE
	SYNTAX INTEGER
	ACCESS read-only
	STATUS mandatory
	DESCRIPTION 
		"The index into the summary array. Up to 256 ports will be shown
		in olGroupSummaryPorts for each value in this entry."
	::= { olGroupSummaryEntry 2 }

olGroupSummaryPorts OBJECT-TYPE
	SYNTAX OCTET STRING (SIZE(0..1400))
	ACCESS read-only
	STATUS mandatory
	DESCRIPTION 
		"A condensed list of all the ports in this group. The summary
		is in the format: Slotx PortX SlotY PortY ..."
	::= { olGroupSummaryEntry 3 }		 

		
olGroupSet	OBJECT IDENTIFIER ::= { olGroups 3 }


olGroupSetAction OBJECT-TYPE
	SYNTAX INTEGER {
		add-ports(1),
		clear-ports(2),
		set-admin-state(3)
	}
	ACCESS read-write
	STATUS mandatory
	DESCRIPTION
		"This object specifies the action that we apply on
		 a group. add-ports(1) adds port(s) to a group, 
		 clear-ports(2) clears (delete) port(s) from a group,
		 and set-admin-state sets the Admin State of 
		 the group."
	::= { olGroupSet 1 }


olGroupSetGroupID OBJECT-TYPE
	SYNTAX INTEGER {
		group-1(1),
		group-2(2),
		group-3(3),
		group-4(4),
		group-5(5),
		group-6(6),
		group-7(7),
		group-8(8),
		all-groups(255) -- only valid for olGroupSetAction of 
 				-- clear-ports(2)
		}
	ACCESS read-write
	STATUS mandatory
	DESCRIPTION
		"A group index that uniquely identifies this group. A port
		can be in zero, one, or more groups."
	::= { olGroupSet 2 }


olGroupSetSlotIndex OBJECT-TYPE
	SYNTAX INTEGER 
	ACCESS read-write
	STATUS mandatory
	DESCRIPTION
		"This object specifies the slot number of the port(s) that 
		are to be added/cleared to/from the group. This object should 
		be set whenever add-ports(1) or clear-ports(2) are selected 
		for olGroupSetAction.  Value 254 refers to all non-existing 
		ports, and value 255 refers to all slots which are only valid 
		when olGroupSetAction is clear-ports(2)."
 	::= { olGroupSet 3 }

olGroupSetPortIndex OBJECT-TYPE
	SYNTAX INTEGER 
	ACCESS read-write
	STATUS mandatory
	DESCRIPTION
		"This object specifies the port number of the port(s) that 
		are to be added/cleared to/from the group. This object should 
		be set whenever add-ports(1) or clear-ports(2) are selected 
		for olGroupSetAction. Value 255 refers to all ports."
	::= { olGroupSet 4 }


olGroupSetAdminState OBJECT-TYPE
	SYNTAX INTEGER {
		enabled(1),
		disabled(2)
	}
	ACCESS read-write
	STATUS mandatory
	DESCRIPTION
		"This object specifies the Admin State that all the ports in 
		the group defined by olGroupSetGroupID should be set to. 
		This object should be set whenever set-admin-state(3) is 
		selected for olGroupSetAction."
	::= { olGroupSet 5 }


--  Threshold Group

--	This group provides access to agent thresholding.
--	If the agent does not support thresholding, then
--	olThreshTable will have no entries.


olThreshTotalEntries OBJECT-TYPE
  SYNTAX INTEGER
  ACCESS read-only
  STATUS mandatory
  DESCRIPTION
	"The number of entries currently in olThreshTable."
    ::= { olThreshControl 1 }

olThreshMaxEntries OBJECT-TYPE
  SYNTAX INTEGER
  ACCESS read-only
  STATUS mandatory
  DESCRIPTION
	"The maximum number of entries in olThreshTable supported by
	this agent."
    ::= { olThreshControl 2 }

olThreshLastCreatedIndex OBJECT-TYPE
  SYNTAX INTEGER
  ACCESS read-only
  STATUS mandatory
  DESCRIPTION
	"The index of the last entry in olThreshTable created via index 255
	(see olThreshMode).  If none, this value will be zero."
    ::= { olThreshControl 3 }

olThreshAllMode OBJECT-TYPE
        SYNTAX INTEGER {
                enable(1),
                disable(2),
		clear(3)
                }
        ACCESS read-write
        STATUS mandatory
        DESCRIPTION
                "Provides the management station with a convenient way to set
		olThreshMode for all of the entries in ThreshTable.
		Setting olThreshAllMode to enable(1) or disable(2)
		will not cause new entries to be created; this
		will only affect entries that have presiously been created.
		Getting olThreshAllMode will always yield clear(3)."
        ::= { olThreshControl 4 }

olThreshTable OBJECT-TYPE
    SYNTAX SEQUENCE OF OlThreshEntry
    ACCESS not-accessible
    STATUS mandatory
    DESCRIPTION
	"A list of thresholding entries."
    ::= { olThresh 2 }

olThreshEntry OBJECT-TYPE
    SYNTAX OlThreshEntry
    ACCESS not-accessible
    STATUS mandatory
    DESCRIPTION
	"A collection of variables for controlling and monitoring a
	specific threshold."
    INDEX { olThreshIndex }
    ::= { olThreshTable 1 }

OlThreshEntry ::= SEQUENCE {
    olThreshIndex		INTEGER,
    olThreshMode		INTEGER,
    olThreshDescription		DisplayString,
    olThreshObjectIdentifier	OBJECT IDENTIFIER,
    olThreshStatCategory	INTEGER,
    olThreshStatType		INTEGER,
    olThreshStatNetID		INTEGER,
    olThreshStatSlotIndex	INTEGER,
    olThreshStatPortIndex	INTEGER,
    olThreshStatStationAddr	MacAddress,
    olThreshInterval		INTEGER,
    olThreshCondition		INTEGER,
    olThreshValue		INTEGER,
    olThreshCurrentValue	INTEGER,
    olThreshStatus		INTEGER,
    olThreshTimeSinceLastTriggered	TimeTicks,
    olThreshActionType		INTEGER,
    olThreshActionData		INTEGER,
    olThreshActionPriority	INTEGER
}

olThreshIndex OBJECT-TYPE
  SYNTAX INTEGER
  ACCESS read-only
  STATUS mandatory
  DESCRIPTION
	"An index that uniquely identifies an entry in
	the olThresh table.  The number of entries in olTRThreshTable
	is olThreshTotalEntries.  A new entry is created when a value is
	written to any object within the entry.  An entry is removed when 
	olThreshMode is set to clear(3).
	Index 255 references a 'pseudo entry' that allows
	the management station to create a new entry without having to 
	search for a clear entry.
	When olThreshMode for entry 255 is set to disable or enable, 
	if there is no available (clear) entry, then the SNMP set-response will
	indicate a bad value error, otherwise the agent does the following:
	    - set the value of olThreshLastCreatedIndex to the index
		of the available entry
	    - copy the values currently in entry 255 to the available entry
	    - clear out entry 255."
  ::= { olThreshEntry 1 }

olThreshMode OBJECT-TYPE
        SYNTAX INTEGER {
                enable(1),
                disable(2),
		clear(3)
                }
        ACCESS read-write
        STATUS mandatory
        DESCRIPTION
                "The mode for this threshold.
		enable(1) indicates that this entry
		is in use and thresholding will be done.
		disable(2) indicates that this entry
		is in use but will no thresholding will be done.
		Setting olThreshMode to clear(3)  will cause this entry to be
		removed from the table."
--      DEFVAL {disable(2)}
        ::= { olThreshEntry 2 }

olThreshDescription OBJECT-TYPE
        SYNTAX DisplayString (SIZE(0..40))
        ACCESS read-write
        STATUS mandatory
        DESCRIPTION
		"Description of the threshold to be sent with the
		chipAboveThreshold trap."
        ::= { olThreshEntry 3 }

olThreshObjectIdentifier OBJECT-TYPE
        SYNTAX OBJECT IDENTIFIER
        ACCESS read-write
        STATUS mandatory
        DESCRIPTION
                "The object identifier that specifies the statistic to be
		thresholded.  The statistic to be thresholded can be 
		specified either by setting olThreshObjectIdentifier
		or by setting values of the olThreshStat group of variables.
		When olThreshObjectIdentifier is set, the agent changes
		the values of the olThreshStat group of variables
		to refer to the new statistic to be thresholded.
		Similarly, when a olThreshStat variable is set, the agent
		changes olThreshObjectIdentifier to refer to the new statistic
		to be thresholded.  A null object identifier (0.0) is used
		when no statistic is specified."
        ::= { olThreshEntry 4 }

olThreshStatCategory OBJECT-TYPE
        SYNTAX INTEGER {
		other(1),
		network(2),
		port(3),
		station(4)
	}
        ACCESS read-write
        STATUS mandatory
        DESCRIPTION
                "Specifies the category of statistic to be thresholded.
		When olThreshStatCategory is network(2) or station(4),
		olThreshStatNetID may also be specified.
		When olThreshStatCategory is station(4),
		olThreshStatStation must be specified.
		When olThreshStatCategory is port(3), olThreshStatSlotIndex
		and olThreshStatPortIndex must be specified."

--      DEFVAL {network(2)}
        ::= { olThreshEntry 5 }

olThreshStatType OBJECT-TYPE
        SYNTAX INTEGER {
		other(1),
		frames(2),
		octets(3),
		broadcast-frames(4),
		multicast-frames(5),
		error-frames(6),
		tr-net-soft-errors(7),
		tr-net-hard-errors(8)
	}
        ACCESS read-write
        STATUS mandatory
        DESCRIPTION
                "Specifies the type of statistic to be thresholded.
		error-frames(6) is valid only when olThreshStatCategory is
		port(3) or station(4).  tr-net-soft-errors(7) or
		tr-net-hard-errors(8) is valid only when olThreshStatCategory
		is network(2).  Note that tr-net-soft-errors(7) and 
		tr-net-hard-errors(8) refer to dot5StatsSoftErrors
		and dot5StatsHardErrors, respectively.  The other choices
		refer for items in the olTRTraf tables."
--      DEFVAL {frames(2)}
        ::= { olThreshEntry 6 }

olThreshStatNetID OBJECT-TYPE
        SYNTAX INTEGER {
		other(1),
		isolated(2),
		token-ring-1(9),
		token-ring-2(10),
		token-ring-3(11),
		token-ring-4(12),
		token-ring-5(13),
		token-ring-6(14),
		token-ring-7(15),
		agent-network(255)
	}
        ACCESS read-write
        STATUS mandatory
        DESCRIPTION
                "When olThreshStatCategory is network(2) or station(4),
		specifies the network of statistic to be thresholded.  
		If the agent is capable of collecting statistics only for
		the network that it is attached to, olThreshStatNetID can
		be set to agent-network(255); the agent will change
		olThreshStatNetID to reflect the network that the agent
		is currently attached to.  If olThreshStatType is
		tr-net-soft-errors(7) or tr-net-hard-errors(8) the
		agent will change olThreshStatNetID to other(1)."
--      DEFVAL {agent-network(255)}
        ::= { olThreshEntry 7 }

olThreshStatSlotIndex OBJECT-TYPE
        SYNTAX INTEGER
        ACCESS read-write
        STATUS mandatory
        DESCRIPTION
                "When olThreshStatCategory is port(3), specifies the
		slot index of the port of statistic to be thresholded."
        ::= { olThreshEntry 8 }

olThreshStatPortIndex OBJECT-TYPE
        SYNTAX INTEGER
        ACCESS read-write
        STATUS mandatory
        DESCRIPTION
                "When olThreshStatCategory is port(3), specifies the
		port index of the port of statistic to be thresholded."
        ::= { olThreshEntry 9 }

olThreshStatStationAddr OBJECT-TYPE
        SYNTAX MacAddress
        ACCESS read-write
        STATUS mandatory
        DESCRIPTION
                "When olThreshStatCategory is station(4), specifies the
		MAC address of the station of statistic to be thresholded."
        ::= { olThreshEntry 10 }

olThreshInterval OBJECT-TYPE
        SYNTAX INTEGER
        ACCESS read-write
        STATUS mandatory
        DESCRIPTION
                "Specifies the length of the thresholding period in seconds.
		Minimum length is 5 seconds; maximum is 86400 seconds
		(24 hours)."
--      DEFVAL {60}
        ::= { olThreshEntry 11 }

olThreshCondition OBJECT-TYPE
        SYNTAX INTEGER {
		delta-above(1)
	}
        ACCESS read-write
        STATUS mandatory
        DESCRIPTION
                "Specifies the type of conditional comparison for the
		threshold."
--	  Possible future values for olThreshCondition: delta-below,
--	  absolute-above, absolute-below
--      DEFVAL {delta-above(1)}
        ::= { olThreshEntry 12 }

olThreshValue OBJECT-TYPE
        SYNTAX INTEGER
        ACCESS read-write
        STATUS mandatory
        DESCRIPTION
            "At the end of each thresholding interval (olThreshInterval
	    seconds), olThreshCurrentValue is compared against
	    olThreshValue (unsigned).
	    When olThreshType is delta-above(1):
		If olThreshStatus is valid(4), and olThreshCurrentValue is
		above olThreshValue, and olThreshMode is enabled,
		then a chipAboveThreshold trap will be sent.
		Another chipAboveThreshold trap will not be sent until
		olThreshCurrentValue drops to less than or equal to
		olThreshValue and then again exceeds it."
--      DEFVAL { 0 }
        ::= { olThreshEntry 13 }

olThreshCurrentValue OBJECT-TYPE
        SYNTAX INTEGER
        ACCESS read-only
        STATUS mandatory
        DESCRIPTION
	    "When olThreshType is delta-exceed(1):
		The most recent delta value of olThreshStatObjectIdentifier
		(i.e. value of olThreshStatObjectIdentifier at the end of
		the interval minus the value of olThreshStatObjectIdentifier
		at the beginning of the interval).
	    If olThreshStatus is not valid(4), olThreshCurrentValue will be 0."
        ::= { olThreshEntry 14 }

olThreshStatus OBJECT-TYPE
        SYNTAX INTEGER {
		no-statistic-specified(1),
		statistic-not-accessible(2),
		not-yet-available(3),
		valid(4)
	}
        ACCESS read-only
        STATUS mandatory
        DESCRIPTION
	    "When olThreshType is delta-exceed(1):
		If olThreshStatObjectIdentifier has not yet been specified,
		olThreshStatus will be no-statistic-specified(1).
		If the first interval has not yet completed,
		olThreshStatus will be not-yet-available(2).
		If object referenced by olThreshStatObjectIdentifier is not
		accessible, olThreshStatus will be not-accessible(3).
		Otherwise olThreshStatus will be valid(4)."
        ::= { olThreshEntry 15 }

olThreshTimeSinceLastTriggered OBJECT-TYPE
  SYNTAX TimeTicks
  ACCESS read-only
  STATUS mandatory
  DESCRIPTION
	"Time in TimeTicks that has elapsed since a chipAboveThreshold trap 
	associated with this ThreshEntry was last sent.
	If never sent, this value shall be zero."
    ::= { olThreshEntry 16 }

olThreshActionType OBJECT-TYPE
        SYNTAX INTEGER {
		trap-only(1)
	}
        ACCESS read-write
        STATUS mandatory
        DESCRIPTION
		"The action to be performed when the threshold is triggered."
--	  Possible future olThreshActionTypes: log, execute-script
--      DEFVAL {trap-only(1)}
    ::= { olThreshEntry 17 }

olThreshActionData OBJECT-TYPE
        SYNTAX INTEGER
        ACCESS read-write
        STATUS mandatory
        DESCRIPTION
		"Additional information to be sent with the
		chipAboveThreshold trap.  Provided for use by the
		network management station (NMS) - not interpreted by
		the agent.  A network management station (NMS)
		could use olThreshActionData to specify an action to be
		performed by the NMS when the chipAboveThreshold trap
		is received."
--	  Possible future use: specify which script to execute
    ::= { olThreshEntry 18 }

olThreshActionPriority OBJECT-TYPE
        SYNTAX INTEGER {
		low(1),
		medium(2),
		high(3)
	}
        ACCESS read-write
        STATUS mandatory
        DESCRIPTION
		"The priority for this entry.  Provided for use by the
		network management station (NMS) - not interpreted by
		the agent."
--      DEFVAL {low(1)}
    ::= { olThreshEntry 19 }




END
