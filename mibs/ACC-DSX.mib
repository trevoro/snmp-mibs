ACC-DSX DEFINITIONS ::= BEGIN

    IMPORTS
	 OBJECT-TYPE FROM RFC1155-SMI
                        accTrapLogSeqNum FROM ACC-SYSTEM
	accBRG FROM ACC-MIB;


-- Companding Mode
    accDsx OBJECT IDENTIFIER ::= { accBRG 90 }
    accDsxParmTable OBJECT IDENTIFIER ::= { accDsx 1 }
    accDsxParmEntry OBJECT IDENTIFIER ::= { accDsxParmTable 1 }
        accPstnDs1InCompandMode OBJECT-TYPE
            SYNTAX INTEGER {
                ulaw (1),
                alaw (2)
            }
            ACCESS read-write
            STATUS mandatory
            DESCRIPTION
              " DS1 interface companding mode."
            ::= { accDsxParmEntry 1 }

END
