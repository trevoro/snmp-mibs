Nortel-Magellan-Passport-MgmtInterfacesMIB
DEFINITIONS ::= BEGIN



IMPORTS

      OBJECT-TYPE
   FROM RFC-1212

      IpAddress
   FROM RFC1155-SMI

      components,
      passportMIBs
   FROM Nortel-Magellan-Passport-UsefulDefinitionsMIB

      RowPointer,
      DisplayString,
      StorageType,
      RowStatus,
      Integer32,
      Unsigned32
   FROM Nortel-Magellan-Passport-StandardTextualConventionsMIB

      AsciiString,
      NonReplicated,
      AsciiStringIndex
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     MgmtInterfaces Enterprise MIB."

mgmtInterfacesMIB OBJECT IDENTIFIER ::= { passportMIBs 15 }










-- Nmis
-- The Network Management Interface System (NMIS) is the 
-- collection of software Interfaces on Passport provided to administer 
-- the Passport. NMIS offers Telnet (server and client) and FTP 
-- (server) access, a directly-connected Local Operator capability, and 
-- a proprietary FMIP Interface for use by Magellan NMS.
-- The Nmis component is a placeholder component to collect all the 
-- Network Management Interface components below it.

nmis OBJECT IDENTIFIER ::= { components 17 }



nmisRowStatusTable OBJECT-TYPE
   SYNTAX     SEQUENCE OF NmisRowStatusEntry
   ACCESS     not-accessible
   STATUS     mandatory
   DESCRIPTION
     "This entry controls the addition and deletion of 
      nmis components."
::= { nmis 1 }

nmisRowStatusEntry OBJECT-TYPE
   SYNTAX     NmisRowStatusEntry
   ACCESS     not-accessible
   STATUS     mandatory
   DESCRIPTION
     "A single entry in the table represents a single 
      nmis component."
   INDEX {
      nmisIndex }
::= { nmisRowStatusTable 1 }

NmisRowStatusEntry ::= SEQUENCE {
   nmisRowStatus
      RowStatus,
   nmisComponentName
      DisplayString,
   nmisStorageType
      StorageType,
   nmisIndex
      NonReplicated }

nmisRowStatus OBJECT-TYPE
   SYNTAX     RowStatus 
   ACCESS     read-only
   STATUS     mandatory
   DESCRIPTION
     "This variable is used as the basis for SNMP naming of
      nmis components.
      These components cannot be added nor deleted."
::= { nmisRowStatusEntry 1 }

nmisComponentName OBJECT-TYPE
   SYNTAX     DisplayString 
   ACCESS     read-only
   STATUS     mandatory
   DESCRIPTION
     "This variable provides the component's string name for
      use with the ASCII Console Interface"
::= { nmisRowStatusEntry 2 }

nmisStorageType OBJECT-TYPE
   SYNTAX     StorageType 
   ACCESS     read-only
   STATUS     mandatory
   DESCRIPTION
     "This variable represents the storage type value for the
      nmis tables."
::= { nmisRowStatusEntry 4 }

nmisIndex OBJECT-TYPE
   SYNTAX     NonReplicated 
   ACCESS     not-accessible
   STATUS     mandatory
   DESCRIPTION
     "This variable represents the index for the nmis tables."
::= { nmisRowStatusEntry 10 }


-- Nmis Local
-- This network management interface is supported on the V.24 DCE 
-- port on the Control Processors. A VT-100 ASCII terminal must be 
-- connected to the V.24 DCE port to log in to the Local Operator 
-- Interface. The Local Operator Interface is otherwise identical to the 
-- Telnet operator interface.

nmisLocal OBJECT IDENTIFIER ::= { nmis 2 }



nmisLocalRowStatusTable OBJECT-TYPE
   SYNTAX     SEQUENCE OF NmisLocalRowStatusEntry
   ACCESS     not-accessible
   STATUS     mandatory
   DESCRIPTION
     "This entry controls the addition and deletion of 
      nmisLocal components."
::= { nmisLocal 1 }

nmisLocalRowStatusEntry OBJECT-TYPE
   SYNTAX     NmisLocalRowStatusEntry
   ACCESS     not-accessible
   STATUS     mandatory
   DESCRIPTION
     "A single entry in the table represents a single 
      nmisLocal component."
   INDEX {
      nmisIndex,
      nmisLocalIndex }
::= { nmisLocalRowStatusTable 1 }

NmisLocalRowStatusEntry ::= SEQUENCE {
   nmisLocalRowStatus
      RowStatus,
   nmisLocalComponentName
      DisplayString,
   nmisLocalStorageType
      StorageType,
   nmisLocalIndex
      NonReplicated }

nmisLocalRowStatus OBJECT-TYPE
   SYNTAX     RowStatus 
   ACCESS     read-only
   STATUS     mandatory
   DESCRIPTION
     "This variable is used as the basis for SNMP naming of
      nmisLocal components.
      These components cannot be added nor deleted."
::= { nmisLocalRowStatusEntry 1 }

nmisLocalComponentName OBJECT-TYPE
   SYNTAX     DisplayString 
   ACCESS     read-only
   STATUS     mandatory
   DESCRIPTION
     "This variable provides the component's string name for
      use with the ASCII Console Interface"
::= { nmisLocalRowStatusEntry 2 }

nmisLocalStorageType OBJECT-TYPE
   SYNTAX     StorageType 
   ACCESS     read-only
   STATUS     mandatory
   DESCRIPTION
     "This variable represents the storage type value for the
      nmisLocal tables."
::= { nmisLocalRowStatusEntry 4 }

nmisLocalIndex OBJECT-TYPE
   SYNTAX     NonReplicated 
   ACCESS     not-accessible
   STATUS     mandatory
   DESCRIPTION
     "This variable represents the index for the nmisLocal tables."
::= { nmisLocalRowStatusEntry 10 }

nmisLocalStateTable OBJECT-TYPE
   SYNTAX     SEQUENCE OF NmisLocalStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { nmisLocal 10 }

nmisLocalStateEntry OBJECT-TYPE
   SYNTAX     NmisLocalStateEntry
   ACCESS     not-accessible
   STATUS     mandatory
   DESCRIPTION
     "An entry in the nmisLocalStateTable."
   INDEX {
      nmisIndex,
      nmisLocalIndex }
::= { nmisLocalStateTable 1 }

NmisLocalStateEntry ::= SEQUENCE {
   nmisLocalAdminState
      INTEGER,
   nmisLocalOperationalState
      INTEGER,
   nmisLocalUsageState
      INTEGER }

nmisLocalAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { nmisLocalStateEntry 1 }

nmisLocalOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { nmisLocalStateEntry 2 }

nmisLocalUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { nmisLocalStateEntry 3 }

nmisLocalOperTable OBJECT-TYPE
   SYNTAX     SEQUENCE OF NmisLocalOperEntry
   ACCESS     not-accessible
   STATUS     mandatory
   DESCRIPTION
     "This group contains the operational attributes for an NMIS 
      manager. This group is common to all NMIS managers."
::= { nmisLocal 11 }

nmisLocalOperEntry OBJECT-TYPE
   SYNTAX     NmisLocalOperEntry
   ACCESS     not-accessible
   STATUS     mandatory
   DESCRIPTION
     "An entry in the nmisLocalOperTable."
   INDEX {
      nmisIndex,
      nmisLocalIndex }
::= { nmisLocalOperTable 1 }

NmisLocalOperEntry ::= SEQUENCE {
   nmisLocalMaxAllowedSessions
      Unsigned32,
   nmisLocalActiveSessions
      Unsigned32 }

nmisLocalMaxAllowedSessions OBJECT-TYPE
   SYNTAX     Unsigned32 (2..35)
   ACCESS     read-only
   STATUS     mandatory
   DESCRIPTION
     "This attribute indicates the maximum number of simultaneous 
      sessions the manager will allow."
::= { nmisLocalOperEntry 1 }

nmisLocalActiveSessions OBJECT-TYPE
   SYNTAX     Unsigned32 (0..35)
   ACCESS     read-only
   STATUS     mandatory
   DESCRIPTION
     "This attribute indicates the number of simultaneous sessions 
      currently active under the manager. Note that there may be fewer  
      Session components than what is shown here, since an active 
      session could be in the midst of logging in and may not yet be fully 
      up."
::= { nmisLocalOperEntry 2 }


-- Nmis Local Session/n
-- This Session component supports a single local operator logged in 
-- to a V.24 DCE port of a control processor.

nmisLocalSession OBJECT IDENTIFIER ::= { nmisLocal 2 }



nmisLocalSessionRowStatusTable OBJECT-TYPE
   SYNTAX     SEQUENCE OF NmisLocalSessionRowStatusEntry
   ACCESS     not-accessible
   STATUS     mandatory
   DESCRIPTION
     "This entry controls the addition and deletion of 
      nmisLocalSession components."
::= { nmisLocalSession 1 }

nmisLocalSessionRowStatusEntry OBJECT-TYPE
   SYNTAX     NmisLocalSessionRowStatusEntry
   ACCESS     not-accessible
   STATUS     mandatory
   DESCRIPTION
     "A single entry in the table represents a single 
      nmisLocalSession component."
   INDEX {
      nmisIndex,
      nmisLocalIndex,
      nmisLocalSessionIndex }
::= { nmisLocalSessionRowStatusTable 1 }

NmisLocalSessionRowStatusEntry ::= SEQUENCE {
   nmisLocalSessionRowStatus
      RowStatus,
   nmisLocalSessionComponentName
      DisplayString,
   nmisLocalSessionStorageType
      StorageType,
   nmisLocalSessionIndex
      Integer32 }

nmisLocalSessionRowStatus OBJECT-TYPE
   SYNTAX     RowStatus 
   ACCESS     read-only
   STATUS     mandatory
   DESCRIPTION
     "This variable is used as the basis for SNMP naming of
      nmisLocalSession components.
      These components cannot be added nor deleted."
::= { nmisLocalSessionRowStatusEntry 1 }

nmisLocalSessionComponentName OBJECT-TYPE
   SYNTAX     DisplayString 
   ACCESS     read-only
   STATUS     mandatory
   DESCRIPTION
     "This variable provides the component's string name for
      use with the ASCII Console Interface"
::= { nmisLocalSessionRowStatusEntry 2 }

nmisLocalSessionStorageType OBJECT-TYPE
   SYNTAX     StorageType 
   ACCESS     read-only
   STATUS     mandatory
   DESCRIPTION
     "This variable represents the storage type value for the
      nmisLocalSession tables."
::= { nmisLocalSessionRowStatusEntry 4 }

nmisLocalSessionIndex OBJECT-TYPE
   SYNTAX     Integer32 (1..2)
   ACCESS     not-accessible
   STATUS     mandatory
   DESCRIPTION
     "This variable represents the index for the nmisLocalSession tables."
::= { nmisLocalSessionRowStatusEntry 10 }

nmisLocalSessionOperTable OBJECT-TYPE
   SYNTAX     SEQUENCE OF NmisLocalSessionOperEntry
   ACCESS     not-accessible
   STATUS     mandatory
   DESCRIPTION
     "This group contains the operational attributes for a Local session."
::= { nmisLocalSession 10 }

nmisLocalSessionOperEntry OBJECT-TYPE
   SYNTAX     NmisLocalSessionOperEntry
   ACCESS     not-accessible
   STATUS     mandatory
   DESCRIPTION
     "An entry in the nmisLocalSessionOperTable."
   INDEX {
      nmisIndex,
      nmisLocalIndex,
      nmisLocalSessionIndex }
::= { nmisLocalSessionOperTable 1 }

NmisLocalSessionOperEntry ::= SEQUENCE {
   nmisLocalSessionUserid
      AsciiString,
   nmisLocalSessionDataStreams
      OCTET STRING,
   nmisLocalSessionHostCard
      RowPointer,
   nmisLocalSessionScreenWidth
      Unsigned32 }

nmisLocalSessionUserid OBJECT-TYPE
   SYNTAX     AsciiString (SIZE (8))
   ACCESS     read-only
   STATUS     mandatory
   DESCRIPTION
     "This attribute indicates the Userid logged in to the Session."
::= { nmisLocalSessionOperEntry 1 }

nmisLocalSessionDataStreams OBJECT-TYPE
   SYNTAX     OCTET STRING (SIZE (1))
   ACCESS     read-write
   STATUS     mandatory
   DESCRIPTION
     "This attribute indicates which data streams will be transmitted back 
      to the operator through this session. Only a userid with a command 
      impact of system administration may register for logs.

      Description of bits:
      notused0(0)
      alarm(1)
      log(2)
      debug(3)
      scn(4)"
::= { nmisLocalSessionOperEntry 2 }

nmisLocalSessionHostCard OBJECT-TYPE
   SYNTAX     RowPointer 
   ACCESS     read-only
   STATUS     mandatory
   DESCRIPTION
     "This attribute holds the component name of the host control 
      processor Card servicing the local operator session."
::= { nmisLocalSessionOperEntry 3 }

nmisLocalSessionScreenWidth OBJECT-TYPE
   SYNTAX     Unsigned32 (79..2000)
   ACCESS     read-write
   STATUS     mandatory
   DESCRIPTION
     "This attribute indicates the maximum width (in characters) of 
      operator command responses. Beyond this maximum, responses are 
      either truncated or wrapped onto the next line, as appropriate.
      
      Asynchronous responses, such as alarms, are always displayed 
      using a 79 character width."
   DEFVAL     { 79 }
::= { nmisLocalSessionOperEntry 4 }


-- Nmis Telnet
-- Passport supports both the Telnet server and client. The Session 
-- subcomponent corresponds to the server connection, while the 
-- Session's Client subcomponent corresponds to the client 
-- connection. The server (that is, the network management interface) 
-- is accessed from a remote computer using the Telnet protocol. The 
-- Telnet operator interface is otherwise identical to the local operator 
-- interface. Each server can set up a single client connection. Note 
-- that Telnet clients are accessible only from a Telnet session, not 
-- from Local, FMIP, or FTP sessions.

nmisTelnet OBJECT IDENTIFIER ::= { nmis 3 }



nmisTelnetRowStatusTable OBJECT-TYPE
   SYNTAX     SEQUENCE OF NmisTelnetRowStatusEntry
   ACCESS     not-accessible
   STATUS     mandatory
   DESCRIPTION
     "This entry controls the addition and deletion of 
      nmisTelnet components."
::= { nmisTelnet 1 }

nmisTelnetRowStatusEntry OBJECT-TYPE
   SYNTAX     NmisTelnetRowStatusEntry
   ACCESS     not-accessible
   STATUS     mandatory
   DESCRIPTION
     "A single entry in the table represents a single 
      nmisTelnet component."
   INDEX {
      nmisIndex,
      nmisTelnetIndex }
::= { nmisTelnetRowStatusTable 1 }

NmisTelnetRowStatusEntry ::= SEQUENCE {
   nmisTelnetRowStatus
      RowStatus,
   nmisTelnetComponentName
      DisplayString,
   nmisTelnetStorageType
      StorageType,
   nmisTelnetIndex
      NonReplicated }

nmisTelnetRowStatus OBJECT-TYPE
   SYNTAX     RowStatus 
   ACCESS     read-only
   STATUS     mandatory
   DESCRIPTION
     "This variable is used as the basis for SNMP naming of
      nmisTelnet components.
      These components cannot be added nor deleted."
::= { nmisTelnetRowStatusEntry 1 }

nmisTelnetComponentName OBJECT-TYPE
   SYNTAX     DisplayString 
   ACCESS     read-only
   STATUS     mandatory
   DESCRIPTION
     "This variable provides the component's string name for
      use with the ASCII Console Interface"
::= { nmisTelnetRowStatusEntry 2 }

nmisTelnetStorageType OBJECT-TYPE
   SYNTAX     StorageType 
   ACCESS     read-only
   STATUS     mandatory
   DESCRIPTION
     "This variable represents the storage type value for the
      nmisTelnet tables."
::= { nmisTelnetRowStatusEntry 4 }

nmisTelnetIndex OBJECT-TYPE
   SYNTAX     NonReplicated 
   ACCESS     not-accessible
   STATUS     mandatory
   DESCRIPTION
     "This variable represents the index for the nmisTelnet tables."
::= { nmisTelnetRowStatusEntry 10 }

nmisTelnetStateTable OBJECT-TYPE
   SYNTAX     SEQUENCE OF NmisTelnetStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { nmisTelnet 10 }

nmisTelnetStateEntry OBJECT-TYPE
   SYNTAX     NmisTelnetStateEntry
   ACCESS     not-accessible
   STATUS     mandatory
   DESCRIPTION
     "An entry in the nmisTelnetStateTable."
   INDEX {
      nmisIndex,
      nmisTelnetIndex }
::= { nmisTelnetStateTable 1 }

NmisTelnetStateEntry ::= SEQUENCE {
   nmisTelnetAdminState
      INTEGER,
   nmisTelnetOperationalState
      INTEGER,
   nmisTelnetUsageState
      INTEGER }

nmisTelnetAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { nmisTelnetStateEntry 1 }

nmisTelnetOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { nmisTelnetStateEntry 2 }

nmisTelnetUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { nmisTelnetStateEntry 3 }

nmisTelnetOperTable OBJECT-TYPE
   SYNTAX     SEQUENCE OF NmisTelnetOperEntry
   ACCESS     not-accessible
   STATUS     mandatory
   DESCRIPTION
     "This group contains the operational attributes for an NMIS 
      manager. This group is common to all NMIS managers."
::= { nmisTelnet 11 }

nmisTelnetOperEntry OBJECT-TYPE
   SYNTAX     NmisTelnetOperEntry
   ACCESS     not-accessible
   STATUS     mandatory
   DESCRIPTION
     "An entry in the nmisTelnetOperTable."
   INDEX {
      nmisIndex,
      nmisTelnetIndex }
::= { nmisTelnetOperTable 1 }

NmisTelnetOperEntry ::= SEQUENCE {
   nmisTelnetMaxAllowedSessions
      Unsigned32,
   nmisTelnetActiveSessions
      Unsigned32 }

nmisTelnetMaxAllowedSessions OBJECT-TYPE
   SYNTAX     Unsigned32 (2..35)
   ACCESS     read-only
   STATUS     mandatory
   DESCRIPTION
     "This attribute indicates the maximum number of simultaneous 
      sessions the manager will allow."
::= { nmisTelnetOperEntry 1 }

nmisTelnetActiveSessions OBJECT-TYPE
   SYNTAX     Unsigned32 (0..35)
   ACCESS     read-only
   STATUS     mandatory
   DESCRIPTION
     "This attribute indicates the number of simultaneous sessions 
      currently active under the manager. Note that there may be fewer  
      Session components than what is shown here, since an active 
      session could be in the midst of logging in and may not yet be fully 
      up."
::= { nmisTelnetOperEntry 2 }


-- Nmis Telnet Session/n
-- This  component supports a single remote Telnet operator logged in 
-- using the Telnet protocol. Optionally, a single outgoing Telnet client 
-- connection can be established from here.

nmisTelnetSession OBJECT IDENTIFIER ::= { nmisTelnet 2 }



nmisTelnetSessionRowStatusTable OBJECT-TYPE
   SYNTAX     SEQUENCE OF NmisTelnetSessionRowStatusEntry
   ACCESS     not-accessible
   STATUS     mandatory
   DESCRIPTION
     "This entry controls the addition and deletion of 
      nmisTelnetSession components."
::= { nmisTelnetSession 1 }

nmisTelnetSessionRowStatusEntry OBJECT-TYPE
   SYNTAX     NmisTelnetSessionRowStatusEntry
   ACCESS     not-accessible
   STATUS     mandatory
   DESCRIPTION
     "A single entry in the table represents a single 
      nmisTelnetSession component."
   INDEX {
      nmisIndex,
      nmisTelnetIndex,
      nmisTelnetSessionIndex }
::= { nmisTelnetSessionRowStatusTable 1 }

NmisTelnetSessionRowStatusEntry ::= SEQUENCE {
   nmisTelnetSessionRowStatus
      RowStatus,
   nmisTelnetSessionComponentName
      DisplayString,
   nmisTelnetSessionStorageType
      StorageType,
   nmisTelnetSessionIndex
      Integer32 }

nmisTelnetSessionRowStatus OBJECT-TYPE
   SYNTAX     RowStatus 
   ACCESS     read-only
   STATUS     mandatory
   DESCRIPTION
     "This variable is used as the basis for SNMP naming of
      nmisTelnetSession components.
      These components cannot be added nor deleted."
::= { nmisTelnetSessionRowStatusEntry 1 }

nmisTelnetSessionComponentName OBJECT-TYPE
   SYNTAX     DisplayString 
   ACCESS     read-only
   STATUS     mandatory
   DESCRIPTION
     "This variable provides the component's string name for
      use with the ASCII Console Interface"
::= { nmisTelnetSessionRowStatusEntry 2 }

nmisTelnetSessionStorageType OBJECT-TYPE
   SYNTAX     StorageType 
   ACCESS     read-only
   STATUS     mandatory
   DESCRIPTION
     "This variable represents the storage type value for the
      nmisTelnetSession tables."
::= { nmisTelnetSessionRowStatusEntry 4 }

nmisTelnetSessionIndex OBJECT-TYPE
   SYNTAX     Integer32 (1..8)
   ACCESS     not-accessible
   STATUS     mandatory
   DESCRIPTION
     "This variable represents the index for the nmisTelnetSession tables."
::= { nmisTelnetSessionRowStatusEntry 10 }

nmisTelnetSessionOperTable OBJECT-TYPE
   SYNTAX     SEQUENCE OF NmisTelnetSessionOperEntry
   ACCESS     not-accessible
   STATUS     mandatory
   DESCRIPTION
     "This group contains the operational attributes for a Telnet session."
::= { nmisTelnetSession 10 }

nmisTelnetSessionOperEntry OBJECT-TYPE
   SYNTAX     NmisTelnetSessionOperEntry
   ACCESS     not-accessible
   STATUS     mandatory
   DESCRIPTION
     "An entry in the nmisTelnetSessionOperTable."
   INDEX {
      nmisIndex,
      nmisTelnetIndex,
      nmisTelnetSessionIndex }
::= { nmisTelnetSessionOperTable 1 }

NmisTelnetSessionOperEntry ::= SEQUENCE {
   nmisTelnetSessionUserid
      AsciiString,
   nmisTelnetSessionDataStreams
      OCTET STRING,
   nmisTelnetSessionRemoteIpAddr
      IpAddress,
   nmisTelnetSessionRemoteTcpPort
      Unsigned32,
   nmisTelnetSessionScreenWidth
      Unsigned32 }

nmisTelnetSessionUserid OBJECT-TYPE
   SYNTAX     AsciiString (SIZE (8))
   ACCESS     read-only
   STATUS     mandatory
   DESCRIPTION
     "This attribute indicates the userid logged in to the session."
::= { nmisTelnetSessionOperEntry 1 }

nmisTelnetSessionDataStreams OBJECT-TYPE
   SYNTAX     OCTET STRING (SIZE (1))
   ACCESS     read-write
   STATUS     mandatory
   DESCRIPTION
     "This attribute indicates which data streams (alarm, debug, log, scn) 
      will be transmitted back to the operator through this session. Only a 
      userid with a command impact of system administration may 
      register for logs.
      
      When a client connection is up through this interface, all of the 
      values are turned off. This means that this data is discarded when 
      the session has a Telnet client connection set up.
      
      When the client connection terminates, the data which was being 
      received prior to the client being set up is requested again.

      Description of bits:
      notused0(0)
      alarm(1)
      log(2)
      debug(3)
      scn(4)"
::= { nmisTelnetSessionOperEntry 2 }

nmisTelnetSessionRemoteIpAddr OBJECT-TYPE
   SYNTAX     IpAddress 
   ACCESS     read-only
   STATUS     mandatory
   DESCRIPTION
     "This attribute indicates the IP address of the remote device 
      connected to the session."
::= { nmisTelnetSessionOperEntry 3 }

nmisTelnetSessionRemoteTcpPort OBJECT-TYPE
   SYNTAX     Unsigned32 (0..65535)
   ACCESS     read-only
   STATUS     mandatory
   DESCRIPTION
     "This attribute indicates the TCP port number of the Telnet client 
      being used on the remote device connected to the session."
::= { nmisTelnetSessionOperEntry 4 }

nmisTelnetSessionScreenWidth OBJECT-TYPE
   SYNTAX     Unsigned32 (79..2000)
   ACCESS     read-write
   STATUS     mandatory
   DESCRIPTION
     "This attribute indicates the maximum width (in characters) of 
      operator command responses. Beyond this maximum, responses are 
      either truncated or wrapped onto the next line, as appropriate.
      
      Asynchronous responses, such as alarms, are always displayed 
      using a 79 character width."
   DEFVAL     { 79 }
::= { nmisTelnetSessionOperEntry 5 }


-- Nmis Telnet Session/n Client
-- This component represents a client connection to a remote node 
-- through this session. The client connection is established by 
-- invoking the Telnet command of a Vr component.

nmisTelnetSessionClient OBJECT IDENTIFIER ::= { nmisTelnetSession 2 }



nmisTelnetSessionClientRowStatusTable OBJECT-TYPE
   SYNTAX     SEQUENCE OF NmisTelnetSessionClientRowStatusEntry
   ACCESS     not-accessible
   STATUS     mandatory
   DESCRIPTION
     "This entry controls the addition and deletion of 
      nmisTelnetSessionClient components."
::= { nmisTelnetSessionClient 1 }

nmisTelnetSessionClientRowStatusEntry OBJECT-TYPE
   SYNTAX     NmisTelnetSessionClientRowStatusEntry
   ACCESS     not-accessible
   STATUS     mandatory
   DESCRIPTION
     "A single entry in the table represents a single 
      nmisTelnetSessionClient component."
   INDEX {
      nmisIndex,
      nmisTelnetIndex,
      nmisTelnetSessionIndex,
      nmisTelnetSessionClientIndex }
::= { nmisTelnetSessionClientRowStatusTable 1 }

NmisTelnetSessionClientRowStatusEntry ::= SEQUENCE {
   nmisTelnetSessionClientRowStatus
      RowStatus,
   nmisTelnetSessionClientComponentName
      DisplayString,
   nmisTelnetSessionClientStorageType
      StorageType,
   nmisTelnetSessionClientIndex
      NonReplicated }

nmisTelnetSessionClientRowStatus OBJECT-TYPE
   SYNTAX     RowStatus 
   ACCESS     read-only
   STATUS     mandatory
   DESCRIPTION
     "This variable is used as the basis for SNMP naming of
      nmisTelnetSessionClient components.
      These components cannot be added nor deleted."
::= { nmisTelnetSessionClientRowStatusEntry 1 }

nmisTelnetSessionClientComponentName OBJECT-TYPE
   SYNTAX     DisplayString 
   ACCESS     read-only
   STATUS     mandatory
   DESCRIPTION
     "This variable provides the component's string name for
      use with the ASCII Console Interface"
::= { nmisTelnetSessionClientRowStatusEntry 2 }

nmisTelnetSessionClientStorageType OBJECT-TYPE
   SYNTAX     StorageType 
   ACCESS     read-only
   STATUS     mandatory
   DESCRIPTION
     "This variable represents the storage type value for the
      nmisTelnetSessionClient tables."
::= { nmisTelnetSessionClientRowStatusEntry 4 }

nmisTelnetSessionClientIndex OBJECT-TYPE
   SYNTAX     NonReplicated 
   ACCESS     not-accessible
   STATUS     mandatory
   DESCRIPTION
     "This variable represents the index for the nmisTelnetSessionClient tables."
::= { nmisTelnetSessionClientRowStatusEntry 10 }

nmisTelnetSessionClientOperTable OBJECT-TYPE
   SYNTAX     SEQUENCE OF NmisTelnetSessionClientOperEntry
   ACCESS     not-accessible
   STATUS     mandatory
   DESCRIPTION
     "This group contains the operational attributes for a Telnet client."
::= { nmisTelnetSessionClient 10 }

nmisTelnetSessionClientOperEntry OBJECT-TYPE
   SYNTAX     NmisTelnetSessionClientOperEntry
   ACCESS     not-accessible
   STATUS     mandatory
   DESCRIPTION
     "An entry in the nmisTelnetSessionClientOperTable."
   INDEX {
      nmisIndex,
      nmisTelnetIndex,
      nmisTelnetSessionIndex,
      nmisTelnetSessionClientIndex }
::= { nmisTelnetSessionClientOperTable 1 }

NmisTelnetSessionClientOperEntry ::= SEQUENCE {
   nmisTelnetSessionClientVirtualRouter
      RowPointer,
   nmisTelnetSessionClientRemoteIpAddr
      IpAddress,
   nmisTelnetSessionClientRemoteTcpPort
      Unsigned32 }

nmisTelnetSessionClientVirtualRouter OBJECT-TYPE
   SYNTAX     RowPointer 
   ACCESS     read-only
   STATUS     mandatory
   DESCRIPTION
     "This attribute indicates the VR instance that determines which 
      address space the remoteIpAddr belongs to."
::= { nmisTelnetSessionClientOperEntry 1 }

nmisTelnetSessionClientRemoteIpAddr OBJECT-TYPE
   SYNTAX     IpAddress 
   ACCESS     read-only
   STATUS     mandatory
   DESCRIPTION
     "This attribute indicates the IP address of the remote side of the 
      client connection."
::= { nmisTelnetSessionClientOperEntry 2 }

nmisTelnetSessionClientRemoteTcpPort OBJECT-TYPE
   SYNTAX     Unsigned32 (0..65535)
   ACCESS     read-only
   STATUS     mandatory
   DESCRIPTION
     "This attribute indicates the TCP port number of the remote side of 
      the client connection."
::= { nmisTelnetSessionClientOperEntry 3 }


-- Nmis Fmip
-- This network management interface is accessed by a Magellan 
-- NMS calling the Passport for management purposes, using the 
-- proprietary FMIP protocol.

nmisFmip OBJECT IDENTIFIER ::= { nmis 4 }



nmisFmipRowStatusTable OBJECT-TYPE
   SYNTAX     SEQUENCE OF NmisFmipRowStatusEntry
   ACCESS     not-accessible
   STATUS     mandatory
   DESCRIPTION
     "This entry controls the addition and deletion of 
      nmisFmip components."
::= { nmisFmip 1 }

nmisFmipRowStatusEntry OBJECT-TYPE
   SYNTAX     NmisFmipRowStatusEntry
   ACCESS     not-accessible
   STATUS     mandatory
   DESCRIPTION
     "A single entry in the table represents a single 
      nmisFmip component."
   INDEX {
      nmisIndex,
      nmisFmipIndex }
::= { nmisFmipRowStatusTable 1 }

NmisFmipRowStatusEntry ::= SEQUENCE {
   nmisFmipRowStatus
      RowStatus,
   nmisFmipComponentName
      DisplayString,
   nmisFmipStorageType
      StorageType,
   nmisFmipIndex
      NonReplicated }

nmisFmipRowStatus OBJECT-TYPE
   SYNTAX     RowStatus 
   ACCESS     read-only
   STATUS     mandatory
   DESCRIPTION
     "This variable is used as the basis for SNMP naming of
      nmisFmip components.
      These components cannot be added nor deleted."
::= { nmisFmipRowStatusEntry 1 }

nmisFmipComponentName OBJECT-TYPE
   SYNTAX     DisplayString 
   ACCESS     read-only
   STATUS     mandatory
   DESCRIPTION
     "This variable provides the component's string name for
      use with the ASCII Console Interface"
::= { nmisFmipRowStatusEntry 2 }

nmisFmipStorageType OBJECT-TYPE
   SYNTAX     StorageType 
   ACCESS     read-only
   STATUS     mandatory
   DESCRIPTION
     "This variable represents the storage type value for the
      nmisFmip tables."
::= { nmisFmipRowStatusEntry 4 }

nmisFmipIndex OBJECT-TYPE
   SYNTAX     NonReplicated 
   ACCESS     not-accessible
   STATUS     mandatory
   DESCRIPTION
     "This variable represents the index for the nmisFmip tables."
::= { nmisFmipRowStatusEntry 10 }

nmisFmipStateTable OBJECT-TYPE
   SYNTAX     SEQUENCE OF NmisFmipStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { nmisFmip 10 }

nmisFmipStateEntry OBJECT-TYPE
   SYNTAX     NmisFmipStateEntry
   ACCESS     not-accessible
   STATUS     mandatory
   DESCRIPTION
     "An entry in the nmisFmipStateTable."
   INDEX {
      nmisIndex,
      nmisFmipIndex }
::= { nmisFmipStateTable 1 }

NmisFmipStateEntry ::= SEQUENCE {
   nmisFmipAdminState
      INTEGER,
   nmisFmipOperationalState
      INTEGER,
   nmisFmipUsageState
      INTEGER }

nmisFmipAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { nmisFmipStateEntry 1 }

nmisFmipOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { nmisFmipStateEntry 2 }

nmisFmipUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { nmisFmipStateEntry 3 }

nmisFmipOperTable OBJECT-TYPE
   SYNTAX     SEQUENCE OF NmisFmipOperEntry
   ACCESS     not-accessible
   STATUS     mandatory
   DESCRIPTION
     "This group contains the operational attributes for an NMIS 
      manager. This group is common to all NMIS managers."
::= { nmisFmip 11 }

nmisFmipOperEntry OBJECT-TYPE
   SYNTAX     NmisFmipOperEntry
   ACCESS     not-accessible
   STATUS     mandatory
   DESCRIPTION
     "An entry in the nmisFmipOperTable."
   INDEX {
      nmisIndex,
      nmisFmipIndex }
::= { nmisFmipOperTable 1 }

NmisFmipOperEntry ::= SEQUENCE {
   nmisFmipMaxAllowedSessions
      Unsigned32,
   nmisFmipActiveSessions
      Unsigned32 }

nmisFmipMaxAllowedSessions OBJECT-TYPE
   SYNTAX     Unsigned32 (2..35)
   ACCESS     read-only
   STATUS     mandatory
   DESCRIPTION
     "This attribute indicates the maximum number of simultaneous 
      sessions the manager will allow."
::= { nmisFmipOperEntry 1 }

nmisFmipActiveSessions OBJECT-TYPE
   SYNTAX     Unsigned32 (0..35)
   ACCESS     read-only
   STATUS     mandatory
   DESCRIPTION
     "This attribute indicates the number of simultaneous sessions 
      currently active under the manager. Note that there may be fewer  
      Session components than what is shown here, since an active 
      session could be in the midst of logging in and may not yet be fully 
      up."
::= { nmisFmipOperEntry 2 }


-- Nmis Fmip Session/n
-- This Session component supports a single FMIP connection from a 
-- remote Magellan NMS.

nmisFmipSession OBJECT IDENTIFIER ::= { nmisFmip 2 }



nmisFmipSessionRowStatusTable OBJECT-TYPE
   SYNTAX     SEQUENCE OF NmisFmipSessionRowStatusEntry
   ACCESS     not-accessible
   STATUS     mandatory
   DESCRIPTION
     "This entry controls the addition and deletion of 
      nmisFmipSession components."
::= { nmisFmipSession 1 }

nmisFmipSessionRowStatusEntry OBJECT-TYPE
   SYNTAX     NmisFmipSessionRowStatusEntry
   ACCESS     not-accessible
   STATUS     mandatory
   DESCRIPTION
     "A single entry in the table represents a single 
      nmisFmipSession component."
   INDEX {
      nmisIndex,
      nmisFmipIndex,
      nmisFmipSessionIndex }
::= { nmisFmipSessionRowStatusTable 1 }

NmisFmipSessionRowStatusEntry ::= SEQUENCE {
   nmisFmipSessionRowStatus
      RowStatus,
   nmisFmipSessionComponentName
      DisplayString,
   nmisFmipSessionStorageType
      StorageType,
   nmisFmipSessionIndex
      Integer32 }

nmisFmipSessionRowStatus OBJECT-TYPE
   SYNTAX     RowStatus 
   ACCESS     read-only
   STATUS     mandatory
   DESCRIPTION
     "This variable is used as the basis for SNMP naming of
      nmisFmipSession components.
      These components cannot be added nor deleted."
::= { nmisFmipSessionRowStatusEntry 1 }

nmisFmipSessionComponentName OBJECT-TYPE
   SYNTAX     DisplayString 
   ACCESS     read-only
   STATUS     mandatory
   DESCRIPTION
     "This variable provides the component's string name for
      use with the ASCII Console Interface"
::= { nmisFmipSessionRowStatusEntry 2 }

nmisFmipSessionStorageType OBJECT-TYPE
   SYNTAX     StorageType 
   ACCESS     read-only
   STATUS     mandatory
   DESCRIPTION
     "This variable represents the storage type value for the
      nmisFmipSession tables."
::= { nmisFmipSessionRowStatusEntry 4 }

nmisFmipSessionIndex OBJECT-TYPE
   SYNTAX     Integer32 (1..35)
   ACCESS     not-accessible
   STATUS     mandatory
   DESCRIPTION
     "This variable represents the index for the nmisFmipSession tables."
::= { nmisFmipSessionRowStatusEntry 10 }

nmisFmipSessionOperTable OBJECT-TYPE
   SYNTAX     SEQUENCE OF NmisFmipSessionOperEntry
   ACCESS     not-accessible
   STATUS     mandatory
   DESCRIPTION
     "This group contains the operational attributes for an FMIP session."
::= { nmisFmipSession 10 }

nmisFmipSessionOperEntry OBJECT-TYPE
   SYNTAX     NmisFmipSessionOperEntry
   ACCESS     not-accessible
   STATUS     mandatory
   DESCRIPTION
     "An entry in the nmisFmipSessionOperTable."
   INDEX {
      nmisIndex,
      nmisFmipIndex,
      nmisFmipSessionIndex }
::= { nmisFmipSessionOperTable 1 }

NmisFmipSessionOperEntry ::= SEQUENCE {
   nmisFmipSessionUserid
      AsciiString,
   nmisFmipSessionDataStreams
      OCTET STRING,
   nmisFmipSessionRemoteIpAddr
      IpAddress,
   nmisFmipSessionRemoteTcpPort
      Unsigned32,
   nmisFmipSessionScreenWidth
      Unsigned32 }

nmisFmipSessionUserid OBJECT-TYPE
   SYNTAX     AsciiString (SIZE (8))
   ACCESS     read-only
   STATUS     mandatory
   DESCRIPTION
     "This attribute indicates the userid logged in to the session."
::= { nmisFmipSessionOperEntry 1 }

nmisFmipSessionDataStreams OBJECT-TYPE
   SYNTAX     OCTET STRING (SIZE (1))
   ACCESS     read-write
   STATUS     mandatory
   DESCRIPTION
     "This attribute indicates which data streams will be transmitted back 
      to the operator through this session. Only a userid with a command 
      impact of system administration may register for logs.

      Description of bits:
      notused0(0)
      alarm(1)
      log(2)
      debug(3)
      scn(4)"
::= { nmisFmipSessionOperEntry 2 }

nmisFmipSessionRemoteIpAddr OBJECT-TYPE
   SYNTAX     IpAddress 
   ACCESS     read-only
   STATUS     mandatory
   DESCRIPTION
     "This attribute indicates the IP address of the remote device 
      connected to the session."
::= { nmisFmipSessionOperEntry 3 }

nmisFmipSessionRemoteTcpPort OBJECT-TYPE
   SYNTAX     Unsigned32 (0..65535)
   ACCESS     read-only
   STATUS     mandatory
   DESCRIPTION
     "This attribute indicates the TCP port number of the FMIP client 
      being used on the remote device connected to the session."
::= { nmisFmipSessionOperEntry 4 }

nmisFmipSessionScreenWidth OBJECT-TYPE
   SYNTAX     Unsigned32 (79..2000)
   ACCESS     read-write
   STATUS     mandatory
   DESCRIPTION
     "This attribute indicates the maximum width (in characters) of 
      operator command responses. Beyond this maximum, responses are 
      either truncated or wrapped onto the next line, as appropriate.
      
      Asynchronous responses, such as alarms, are always displayed 
      using a 79 character width."
   DEFVAL     { 79 }
::= { nmisFmipSessionOperEntry 5 }


-- Nmis Ftp
-- This network management interface is accessed from a remote 
-- computer using the FTP protocol.

nmisFtp OBJECT IDENTIFIER ::= { nmis 5 }



nmisFtpRowStatusTable OBJECT-TYPE
   SYNTAX     SEQUENCE OF NmisFtpRowStatusEntry
   ACCESS     not-accessible
   STATUS     mandatory
   DESCRIPTION
     "This entry controls the addition and deletion of 
      nmisFtp components."
::= { nmisFtp 1 }

nmisFtpRowStatusEntry OBJECT-TYPE
   SYNTAX     NmisFtpRowStatusEntry
   ACCESS     not-accessible
   STATUS     mandatory
   DESCRIPTION
     "A single entry in the table represents a single 
      nmisFtp component."
   INDEX {
      nmisIndex,
      nmisFtpIndex }
::= { nmisFtpRowStatusTable 1 }

NmisFtpRowStatusEntry ::= SEQUENCE {
   nmisFtpRowStatus
      RowStatus,
   nmisFtpComponentName
      DisplayString,
   nmisFtpStorageType
      StorageType,
   nmisFtpIndex
      NonReplicated }

nmisFtpRowStatus OBJECT-TYPE
   SYNTAX     RowStatus 
   ACCESS     read-only
   STATUS     mandatory
   DESCRIPTION
     "This variable is used as the basis for SNMP naming of
      nmisFtp components.
      These components cannot be added nor deleted."
::= { nmisFtpRowStatusEntry 1 }

nmisFtpComponentName OBJECT-TYPE
   SYNTAX     DisplayString 
   ACCESS     read-only
   STATUS     mandatory
   DESCRIPTION
     "This variable provides the component's string name for
      use with the ASCII Console Interface"
::= { nmisFtpRowStatusEntry 2 }

nmisFtpStorageType OBJECT-TYPE
   SYNTAX     StorageType 
   ACCESS     read-only
   STATUS     mandatory
   DESCRIPTION
     "This variable represents the storage type value for the
      nmisFtp tables."
::= { nmisFtpRowStatusEntry 4 }

nmisFtpIndex OBJECT-TYPE
   SYNTAX     NonReplicated 
   ACCESS     not-accessible
   STATUS     mandatory
   DESCRIPTION
     "This variable represents the index for the nmisFtp tables."
::= { nmisFtpRowStatusEntry 10 }

nmisFtpStateTable OBJECT-TYPE
   SYNTAX     SEQUENCE OF NmisFtpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { nmisFtp 10 }

nmisFtpStateEntry OBJECT-TYPE
   SYNTAX     NmisFtpStateEntry
   ACCESS     not-accessible
   STATUS     mandatory
   DESCRIPTION
     "An entry in the nmisFtpStateTable."
   INDEX {
      nmisIndex,
      nmisFtpIndex }
::= { nmisFtpStateTable 1 }

NmisFtpStateEntry ::= SEQUENCE {
   nmisFtpAdminState
      INTEGER,
   nmisFtpOperationalState
      INTEGER,
   nmisFtpUsageState
      INTEGER }

nmisFtpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { nmisFtpStateEntry 1 }

nmisFtpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { nmisFtpStateEntry 2 }

nmisFtpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { nmisFtpStateEntry 3 }

nmisFtpOperTable OBJECT-TYPE
   SYNTAX     SEQUENCE OF NmisFtpOperEntry
   ACCESS     not-accessible
   STATUS     mandatory
   DESCRIPTION
     "This group contains the operational attributes for an NMIS 
      manager. This group is common to all NMIS managers."
::= { nmisFtp 11 }

nmisFtpOperEntry OBJECT-TYPE
   SYNTAX     NmisFtpOperEntry
   ACCESS     not-accessible
   STATUS     mandatory
   DESCRIPTION
     "An entry in the nmisFtpOperTable."
   INDEX {
      nmisIndex,
      nmisFtpIndex }
::= { nmisFtpOperTable 1 }

NmisFtpOperEntry ::= SEQUENCE {
   nmisFtpMaxAllowedSessions
      Unsigned32,
   nmisFtpActiveSessions
      Unsigned32 }

nmisFtpMaxAllowedSessions OBJECT-TYPE
   SYNTAX     Unsigned32 (2..35)
   ACCESS     read-only
   STATUS     mandatory
   DESCRIPTION
     "This attribute indicates the maximum number of simultaneous 
      sessions the manager will allow."
::= { nmisFtpOperEntry 1 }

nmisFtpActiveSessions OBJECT-TYPE
   SYNTAX     Unsigned32 (0..35)
   ACCESS     read-only
   STATUS     mandatory
   DESCRIPTION
     "This attribute indicates the number of simultaneous sessions 
      currently active under the manager. Note that there may be fewer  
      Session components than what is shown here, since an active 
      session could be in the midst of logging in and may not yet be fully 
      up."
::= { nmisFtpOperEntry 2 }


-- Nmis Ftp Session/n
-- This component supports a single remote FTP client logged in using 
-- the FTP protocol.

nmisFtpSession OBJECT IDENTIFIER ::= { nmisFtp 2 }



nmisFtpSessionRowStatusTable OBJECT-TYPE
   SYNTAX     SEQUENCE OF NmisFtpSessionRowStatusEntry
   ACCESS     not-accessible
   STATUS     mandatory
   DESCRIPTION
     "This entry controls the addition and deletion of 
      nmisFtpSession components."
::= { nmisFtpSession 1 }

nmisFtpSessionRowStatusEntry OBJECT-TYPE
   SYNTAX     NmisFtpSessionRowStatusEntry
   ACCESS     not-accessible
   STATUS     mandatory
   DESCRIPTION
     "A single entry in the table represents a single 
      nmisFtpSession component."
   INDEX {
      nmisIndex,
      nmisFtpIndex,
      nmisFtpSessionIndex }
::= { nmisFtpSessionRowStatusTable 1 }

NmisFtpSessionRowStatusEntry ::= SEQUENCE {
   nmisFtpSessionRowStatus
      RowStatus,
   nmisFtpSessionComponentName
      DisplayString,
   nmisFtpSessionStorageType
      StorageType,
   nmisFtpSessionIndex
      Integer32 }

nmisFtpSessionRowStatus OBJECT-TYPE
   SYNTAX     RowStatus 
   ACCESS     read-only
   STATUS     mandatory
   DESCRIPTION
     "This variable is used as the basis for SNMP naming of
      nmisFtpSession components.
      These components cannot be added nor deleted."
::= { nmisFtpSessionRowStatusEntry 1 }

nmisFtpSessionComponentName OBJECT-TYPE
   SYNTAX     DisplayString 
   ACCESS     read-only
   STATUS     mandatory
   DESCRIPTION
     "This variable provides the component's string name for
      use with the ASCII Console Interface"
::= { nmisFtpSessionRowStatusEntry 2 }

nmisFtpSessionStorageType OBJECT-TYPE
   SYNTAX     StorageType 
   ACCESS     read-only
   STATUS     mandatory
   DESCRIPTION
     "This variable represents the storage type value for the
      nmisFtpSession tables."
::= { nmisFtpSessionRowStatusEntry 4 }

nmisFtpSessionIndex OBJECT-TYPE
   SYNTAX     Integer32 (1..16)
   ACCESS     not-accessible
   STATUS     mandatory
   DESCRIPTION
     "This variable represents the index for the nmisFtpSession tables."
::= { nmisFtpSessionRowStatusEntry 10 }

nmisFtpSessionOperTable OBJECT-TYPE
   SYNTAX     SEQUENCE OF NmisFtpSessionOperEntry
   ACCESS     not-accessible
   STATUS     mandatory
   DESCRIPTION
     "This group contains the operational attributes for an FTP session."
::= { nmisFtpSession 10 }

nmisFtpSessionOperEntry OBJECT-TYPE
   SYNTAX     NmisFtpSessionOperEntry
   ACCESS     not-accessible
   STATUS     mandatory
   DESCRIPTION
     "An entry in the nmisFtpSessionOperTable."
   INDEX {
      nmisIndex,
      nmisFtpIndex,
      nmisFtpSessionIndex }
::= { nmisFtpSessionOperTable 1 }

NmisFtpSessionOperEntry ::= SEQUENCE {
   nmisFtpSessionUserid
      AsciiString,
   nmisFtpSessionRemoteIpAddr
      IpAddress,
   nmisFtpSessionRemoteTcpPort
      Unsigned32 }

nmisFtpSessionUserid OBJECT-TYPE
   SYNTAX     AsciiString (SIZE (8))
   ACCESS     read-only
   STATUS     mandatory
   DESCRIPTION
     "This attribute indicates the userid logged in to the session."
::= { nmisFtpSessionOperEntry 1 }

nmisFtpSessionRemoteIpAddr OBJECT-TYPE
   SYNTAX     IpAddress 
   ACCESS     read-only
   STATUS     mandatory
   DESCRIPTION
     "This attribute indicates the IP address of the remote device 
      connected to the session."
::= { nmisFtpSessionOperEntry 2 }

nmisFtpSessionRemoteTcpPort OBJECT-TYPE
   SYNTAX     Unsigned32 (0..65535)
   ACCESS     read-only
   STATUS     mandatory
   DESCRIPTION
     "This attribute indicates the TCP port number of the FTP control 
      connection being used on the remote device connected to the 
      session."
::= { nmisFtpSessionOperEntry 3 }


-- AccessControl
-- The AccessControl component performs security validation to 
-- restrict access to a Passport module. AccessControl ensures that 
-- only authorized remote devices can log in to the Network 
-- Management Interfaces for management purposes.
-- The AccessControl component is a placeholder to collect all the 
-- Userid and IpAccess components below it.

ac OBJECT IDENTIFIER ::= { components 18 }



acRowStatusTable OBJECT-TYPE
   SYNTAX     SEQUENCE OF AcRowStatusEntry
   ACCESS     not-accessible
   STATUS     mandatory
   DESCRIPTION
     "This entry controls the addition and deletion of 
      ac components."
::= { ac 1 }

acRowStatusEntry OBJECT-TYPE
   SYNTAX     AcRowStatusEntry
   ACCESS     not-accessible
   STATUS     mandatory
   DESCRIPTION
     "A single entry in the table represents a single 
      ac component."
   INDEX {
      acIndex }
::= { acRowStatusTable 1 }

AcRowStatusEntry ::= SEQUENCE {
   acRowStatus
      RowStatus,
   acComponentName
      DisplayString,
   acStorageType
      StorageType,
   acIndex
      NonReplicated }

acRowStatus OBJECT-TYPE
   SYNTAX     RowStatus 
   ACCESS     read-write
   STATUS     mandatory
   DESCRIPTION
     "This variable is used as the basis for SNMP naming of
      ac components.
      These components can be added."
::= { acRowStatusEntry 1 }

acComponentName OBJECT-TYPE
   SYNTAX     DisplayString 
   ACCESS     read-only
   STATUS     mandatory
   DESCRIPTION
     "This variable provides the component's string name for
      use with the ASCII Console Interface"
::= { acRowStatusEntry 2 }

acStorageType OBJECT-TYPE
   SYNTAX     StorageType 
   ACCESS     read-only
   STATUS     mandatory
   DESCRIPTION
     "This variable represents the storage type value for the
      ac tables."
::= { acRowStatusEntry 4 }

acIndex OBJECT-TYPE
   SYNTAX     NonReplicated 
   ACCESS     not-accessible
   STATUS     mandatory
   DESCRIPTION
     "This variable represents the index for the ac tables."
::= { acRowStatusEntry 10 }

acProvTable OBJECT-TYPE
   SYNTAX     SEQUENCE OF AcProvEntry
   ACCESS     not-accessible
   STATUS     mandatory
   DESCRIPTION
     "This group contains the provisionable attributes which apply to the 
      overall access of the the node."
::= { ac 10 }

acProvEntry OBJECT-TYPE
   SYNTAX     AcProvEntry
   ACCESS     not-accessible
   STATUS     mandatory
   DESCRIPTION
     "An entry in the acProvTable."
   INDEX {
      acIndex }
::= { acProvTable 1 }

AcProvEntry ::= SEQUENCE {
   acPublicKeyAuth
      OCTET STRING }

acPublicKeyAuth OBJECT-TYPE
   SYNTAX     OCTET STRING (SIZE (1))
   ACCESS     read-write
   STATUS     mandatory
   DESCRIPTION
     "This attribute indicates whether Telnet sessions require a public key 
      exchange in order to log in to the node. FMIP sessions always 
      require a public key exchange for login authentication.

      Description of bits:
      telnet(0)"
::= { acProvEntry 1 }


-- AccessControl Userid/<string>
-- The Userid component holds all provisionable attributes for a 
-- userid. Every Network Management Interface requires a user to 
-- supply a valid userid and password to log in, like most computer 
-- systems.
-- The instance value must be the userid string itself, consisting of 1-8 
-- alphanumeric (letters and numbers) characters. Letters in the userid 
-- string are case-insensitive.

acUserid OBJECT IDENTIFIER ::= { ac 2 }



acUseridRowStatusTable OBJECT-TYPE
   SYNTAX     SEQUENCE OF AcUseridRowStatusEntry
   ACCESS     not-accessible
   STATUS     mandatory
   DESCRIPTION
     "This entry controls the addition and deletion of 
      acUserid components."
::= { acUserid 1 }

acUseridRowStatusEntry OBJECT-TYPE
   SYNTAX     AcUseridRowStatusEntry
   ACCESS     not-accessible
   STATUS     mandatory
   DESCRIPTION
     "A single entry in the table represents a single 
      acUserid component."
   INDEX {
      acIndex,
      acUseridIndex }
::= { acUseridRowStatusTable 1 }

AcUseridRowStatusEntry ::= SEQUENCE {
   acUseridRowStatus
      RowStatus,
   acUseridComponentName
      DisplayString,
   acUseridStorageType
      StorageType,
   acUseridIndex
      AsciiStringIndex }

acUseridRowStatus OBJECT-TYPE
   SYNTAX     RowStatus 
   ACCESS     read-write
   STATUS     mandatory
   DESCRIPTION
     "This variable is used as the basis for SNMP naming of
      acUserid components.
      These components can be added and deleted."
::= { acUseridRowStatusEntry 1 }

acUseridComponentName OBJECT-TYPE
   SYNTAX     DisplayString 
   ACCESS     read-only
   STATUS     mandatory
   DESCRIPTION
     "This variable provides the component's string name for
      use with the ASCII Console Interface"
::= { acUseridRowStatusEntry 2 }

acUseridStorageType OBJECT-TYPE
   SYNTAX     StorageType 
   ACCESS     read-only
   STATUS     mandatory
   DESCRIPTION
     "This variable represents the storage type value for the
      acUserid tables."
::= { acUseridRowStatusEntry 4 }

acUseridIndex OBJECT-TYPE
   SYNTAX     AsciiStringIndex (SIZE (1..8))
   ACCESS     not-accessible
   STATUS     mandatory
   DESCRIPTION
     "This variable represents the index for the acUserid tables."
::= { acUseridRowStatusEntry 10 }

acUseridProvTable OBJECT-TYPE
   SYNTAX     SEQUENCE OF AcUseridProvEntry
   ACCESS     not-accessible
   STATUS     mandatory
   DESCRIPTION
     "This group contains the provisionable attributes for a userid."
::= { acUserid 10 }

acUseridProvEntry OBJECT-TYPE
   SYNTAX     AcUseridProvEntry
   ACCESS     not-accessible
   STATUS     mandatory
   DESCRIPTION
     "An entry in the acUseridProvTable."
   INDEX {
      acIndex,
      acUseridIndex }
::= { acUseridProvTable 1 }

AcUseridProvEntry ::= SEQUENCE {
   acUseridPassword
      AsciiString,
   acUseridCustomerIdentifier
      Unsigned32,
   acUseridCommandScope
      INTEGER,
   acUseridCommandImpact
      INTEGER,
   acUseridAllowedAccess
      OCTET STRING,
   acUseridLoginDirectory
      AsciiString,
   acUseridAllowedOutAccess
      OCTET STRING }

acUseridPassword OBJECT-TYPE
   SYNTAX     AsciiString (SIZE (5..8))
   ACCESS     write-only
   STATUS     mandatory
   DESCRIPTION
     "This attribute holds the password for the userid. This is a write-only 
      attribute to provide additional security for passwords. The password 
      string consists of 5-8 characters, which may be any printable ASCII 
      characters. If the password string includes any non-alphanumeric 
      character, such as $ or *, the entire string must be enclosed in 
      double quotes. Letters in the password string are case-sensitive."
::= { acUseridProvEntry 1 }

acUseridCustomerIdentifier OBJECT-TYPE
   SYNTAX     Unsigned32 (0..8191)
   ACCESS     read-write
   STATUS     mandatory
   DESCRIPTION
     "This attribute indicates the Customer Identifier (CID) assigned to 
      the userid. The CID is used in Customer Network Management 
      (CNM). A CNM operator may only send commands to components 
      provisioned with the same CID as the operator. A CNM operator 
      will only receive event data, such as alarms, which is generated by 
      components provisioned with the same CID as the operator. 
      The special CID of 0 is reserved for the network owner, known as 
      the Netman. 
      The Passport CID attribute is compatible with DPN-100 Netman 
      and Basic CIDs."
   DEFVAL     { 0 }
::= { acUseridProvEntry 2 }

acUseridCommandScope OBJECT-TYPE
   SYNTAX     INTEGER  {
                 network(1),
                 device(2),
                 application(3) }
   ACCESS     read-write
   STATUS     mandatory
   DESCRIPTION
     "This attribute indicates the command scope assigned to the userid. 
      The scope determines the importance of the components on which 
      the userid will be allowed to execute commands. Scope has three 
      levels:
      
      1) Network scope implies the userid can manage components that 
      affect the operation of the entire network, such as trunks.
      2) Device scope implies the userid can manage components that 
      affect the operation of the entire Passport module, such as 
      processors or the file system.
      3) Application scope implies the userid can manage components 
      that affect the operation of a single application.
      
      Note that scope is hierarchical: A userid provisioned with network 
      scope can also manage components with a scope of device or 
      application."
   DEFVAL     { application }
::= { acUseridProvEntry 3 }

acUseridCommandImpact OBJECT-TYPE
   SYNTAX     INTEGER  {
                 debug(3),
                 systemAdministration(4),
                 configuration(5),
                 service(6),
                 passive(7) }
   ACCESS     read-write
   STATUS     mandatory
   DESCRIPTION
     "This attribute indicates the command impact assigned to the userid. 
      The impact determines the importance of the commands which the 
      userid will be allowed to execute. Impact has five levels:
      
      1) Debug impact implies the userid can issue all debugging 
      commands. Debug is the highest impact level.
      2) System Administration impact implies the userid can issue 
      provisioning commands on security components. This means the 
      userid can Add, Delete, Display, or Set the Userid and IpAccess 
      subcomponents of AccessControl.
      3) Configuration impact implies the userid can issue provisioning 
      commands to alter the provisioned configuration of the Passport 
      module, such as Start Prov, Add, Delete, and Set.
      4) Service impact implies the userid can issue operational 
      commands which may affect the service of running components, 
      such as Lock and Unlock.
      5) Passive impact implies the userid can only issue query 
      commands which display unrestricted information but otherwise do 
      not affect the operation or configuration of the Passport module. 
      Commands such as List and Display. Passive is the lowest impact 
      level.
      
      Note that impact is hierarchical: A userid provisioned with debug 
      impact can also issue all other commands at lower impact levels."
   DEFVAL     { passive }
::= { acUseridProvEntry 4 }

acUseridAllowedAccess OBJECT-TYPE
   SYNTAX     OCTET STRING (SIZE (1))
   ACCESS     read-write
   STATUS     mandatory
   DESCRIPTION
     "This attribute indicates the set of network management interfaces 
      through which the userid will be allowed incoming access to the 
      Passport. The allowedAccess attribute can be used to restrict a 
      userid to a desired subset of the network management interfaces 
      provided.

      Description of bits:
      local(0)
      telnet(1)
      fmip(2)
      ftp(3)"
   DEFVAL     { '80'H }
::= { acUseridProvEntry 5 }

acUseridLoginDirectory OBJECT-TYPE
   SYNTAX     AsciiString (SIZE (1..128))
   ACCESS     read-write
   STATUS     mandatory
   DESCRIPTION
     "This attribute is the login directory for file system commands or 
      FTP commands. The userid will initially be placed in this directory 
      upon logging in to Telnet, FMIP, Local or FTP.
      The default value of '/' is the root of the /sfs/ shadowed file system."
   DEFVAL     { '2f'H }  -- "/"
::= { acUseridProvEntry 6 }

acUseridAllowedOutAccess OBJECT-TYPE
   SYNTAX     OCTET STRING (SIZE (1))
   ACCESS     read-write
   STATUS     mandatory
   DESCRIPTION
     "This attribute indicates whether or not the userid will be allowed 
      outgoing Telnet access from the Passport.

      Description of bits:
      telnet(0)"
::= { acUseridProvEntry 7 }


-- AccessControl IpAccess/<IP address>
-- This component represents a single "friendly" remote IP address 
-- which is permitted to call into the Telnet, FTP, or FMIP Interfaces 
-- on the Passport. All the friendly IP addresses must be provisioned 
-- as IpAccess components. The IpAccess components, taken together, 
-- form a complete list of all the IP addresses which are allowed 
-- access to the Passport's Network Management Interfaces. This set 
-- of friendly IP addresses excludes all other addresses, restricting 
-- access only to the friendly computers.
-- The instance value is the IP address itself, or an IP subnetwork 
-- address, entered in Internet   nnn.nnn.nnn.nnn   notation. An IP 
-- subnetwork address, in combination with the ipAddressMask 
-- attribute described below, may be provisioned to include an entire 
-- IP subnetwork into the friendly list with a single IpAccess 
-- component.
-- 
-- Note that with the introduction of Telnet client capability, the 
-- IpAccess lists must allow for the fact that Telnet access may now be 
-- from another Passport (or another type of node) in the network, not 
-- just management workstations.

acIpAccess OBJECT IDENTIFIER ::= { ac 3 }



acIpAccessRowStatusTable OBJECT-TYPE
   SYNTAX     SEQUENCE OF AcIpAccessRowStatusEntry
   ACCESS     not-accessible
   STATUS     mandatory
   DESCRIPTION
     "This entry controls the addition and deletion of 
      acIpAccess components."
::= { acIpAccess 1 }

acIpAccessRowStatusEntry OBJECT-TYPE
   SYNTAX     AcIpAccessRowStatusEntry
   ACCESS     not-accessible
   STATUS     mandatory
   DESCRIPTION
     "A single entry in the table represents a single 
      acIpAccess component."
   INDEX {
      acIndex,
      acIpAccessIndex }
::= { acIpAccessRowStatusTable 1 }

AcIpAccessRowStatusEntry ::= SEQUENCE {
   acIpAccessRowStatus
      RowStatus,
   acIpAccessComponentName
      DisplayString,
   acIpAccessStorageType
      StorageType,
   acIpAccessIndex
      IpAddress }

acIpAccessRowStatus OBJECT-TYPE
   SYNTAX     RowStatus 
   ACCESS     read-write
   STATUS     mandatory
   DESCRIPTION
     "This variable is used as the basis for SNMP naming of
      acIpAccess components.
      These components can be added and deleted."
::= { acIpAccessRowStatusEntry 1 }

acIpAccessComponentName OBJECT-TYPE
   SYNTAX     DisplayString 
   ACCESS     read-only
   STATUS     mandatory
   DESCRIPTION
     "This variable provides the component's string name for
      use with the ASCII Console Interface"
::= { acIpAccessRowStatusEntry 2 }

acIpAccessStorageType OBJECT-TYPE
   SYNTAX     StorageType 
   ACCESS     read-only
   STATUS     mandatory
   DESCRIPTION
     "This variable represents the storage type value for the
      acIpAccess tables."
::= { acIpAccessRowStatusEntry 4 }

acIpAccessIndex OBJECT-TYPE
   SYNTAX     IpAddress 
   ACCESS     not-accessible
   STATUS     mandatory
   DESCRIPTION
     "This variable represents the index for the acIpAccess tables."
::= { acIpAccessRowStatusEntry 10 }

acIpAccessProvTable OBJECT-TYPE
   SYNTAX     SEQUENCE OF AcIpAccessProvEntry
   ACCESS     not-accessible
   STATUS     mandatory
   DESCRIPTION
     "This group contains the provisionable attributes for an IpAccess 
      component."
::= { acIpAccess 10 }

acIpAccessProvEntry OBJECT-TYPE
   SYNTAX     AcIpAccessProvEntry
   ACCESS     not-accessible
   STATUS     mandatory
   DESCRIPTION
     "An entry in the acIpAccessProvTable."
   INDEX {
      acIndex,
      acIpAccessIndex }
::= { acIpAccessProvTable 1 }

AcIpAccessProvEntry ::= SEQUENCE {
   acIpAccessIpAddressMask
      IpAddress }

acIpAccessIpAddressMask OBJECT-TYPE
   SYNTAX     IpAddress 
   ACCESS     read-write
   STATUS     mandatory
   DESCRIPTION
     "This attribute indicates the bit mask indicating the significant bits 
      which are used in the comparison of an incoming IP address against 
      the 'friendly' IP address in the instance value of the IpAccess 
      component. This bit mask is ANDed to the incoming IP address, 
      and ANDed to the instance value, before the comparison.
      
      An IP subnetwork address, in combination with this bit mask 
      attribute, may be provisioned to include an entire IP subnetwork 
      into the friendly IP address list with a single IpAccess component."
   DEFVAL     { 'ffffffff'H }  -- "255.255.255.255"
::= { acIpAccessProvEntry 1 }




-- 
-- Version and Compliance statements
-- 



-- Object-Group Statement:
-- A list of all current accessible leaf objects.

-- OBJECTS { nmisTelnetSessionUserid,
--           nmisLocalStorageType,
--           nmisFmipSessionStorageType,
--           acUseridPassword,
--           acIpAccessIpAddressMask,
--           acUseridCommandImpact,
--           nmisTelnetComponentName,
--           nmisTelnetSessionClientRowStatus,
--           nmisLocalSessionScreenWidth,
--           nmisLocalSessionComponentName,
--           nmisLocalSessionDataStreams,
--           acUseridLoginDirectory,
--           acUseridCommandScope,
--           nmisRowStatus,
--           nmisFtpStorageType,
--           nmisFmipSessionRemoteTcpPort,
--           nmisTelnetOperationalState,
--           nmisTelnetSessionRemoteIpAddr,
--           nmisLocalAdminState,
--           nmisLocalSessionRowStatus,
--           acStorageType,
--           nmisTelnetSessionClientRemoteTcpPort,
--           nmisFtpSessionRemoteTcpPort,
--           nmisFtpSessionComponentName,
--           nmisLocalRowStatus,
--           nmisFmipSessionRowStatus,
--           nmisFmipMaxAllowedSessions,
--           nmisLocalSessionUserid,
--           nmisFtpMaxAllowedSessions,
--           nmisTelnetSessionStorageType,
--           nmisFtpAdminState,
--           acIpAccessStorageType,
--           nmisComponentName,
--           nmisLocalActiveSessions,
--           nmisFmipStorageType,
--           nmisTelnetSessionRemoteTcpPort,
--           nmisLocalUsageState,
--           nmisFtpRowStatus,
--           nmisFtpSessionRowStatus,
--           nmisFmipSessionScreenWidth,
--           acUseridRowStatus,
--           nmisFtpSessionUserid,
--           nmisLocalComponentName,
--           nmisFmipSessionComponentName,
--           nmisFmipSessionDataStreams,
--           acUseridCustomerIdentifier,
--           acUseridAllowedAccess,
--           nmisFtpActiveSessions,
--           nmisLocalSessionHostCard,
--           nmisTelnetSessionRowStatus,
--           nmisTelnetMaxAllowedSessions,
--           nmisFmipAdminState,
--           nmisFtpUsageState,
--           nmisLocalOperationalState,
--           acIpAccessRowStatus,
--           acPublicKeyAuth,
--           nmisFtpComponentName,
--           nmisTelnetStorageType,
--           nmisFmipRowStatus,
--           acUseridComponentName,
--           nmisTelnetSessionClientVirtualRouter,
--           nmisFmipSessionUserid,
--           nmisLocalSessionStorageType,
--           acUseridAllowedOutAccess,
--           nmisTelnetSessionScreenWidth,
--           nmisFmipSessionRemoteIpAddr,
--           nmisFmipActiveSessions,
--           nmisTelnetSessionComponentName,
--           nmisTelnetSessionDataStreams,
--           nmisFtpSessionRemoteIpAddr,
--           acRowStatus,
--           nmisFmipUsageState,
--           acIpAccessComponentName,
--           nmisTelnetUsageState,
--           nmisTelnetAdminState,
--           nmisFtpOperationalState,
--           nmisFmipComponentName,
--           nmisFtpSessionStorageType,
--           nmisTelnetSessionClientRemoteIpAddr,
--           acUseridStorageType,
--           nmisTelnetRowStatus,
--           nmisStorageType,
--           nmisTelnetSessionClientComponentName,
--           acComponentName,
--           nmisTelnetSessionClientStorageType,
--           nmisFmipOperationalState,
--           nmisLocalMaxAllowedSessions,
--           nmisTelnetActiveSessions }
-- STATUS  mandatory
-- DESCRIPTION
--   "A list of all current accessible leaf objects."

mgmtInterfacesGroup OBJECT IDENTIFIER ::= { mgmtInterfacesMIB 1 }
mgmtInterfacesGroupBE OBJECT IDENTIFIER ::= { mgmtInterfacesGroup 5 }
mgmtInterfacesGroupBE01 OBJECT IDENTIFIER ::= { mgmtInterfacesGroupBE 2 }
mgmtInterfacesGroupBE01A OBJECT IDENTIFIER ::= { mgmtInterfacesGroupBE01 2 }



-- Agent-Capabilities Statement:

-- PRODUCT-RELEASE "Passport Release 7.0 MgmtInterfaces."
-- STATUS          mandatory
-- DESCRIPTION     "MgmtInterfaces MIB: MIB Version BE01A,
--                  Software Version BG00S4C."
-- SUPPORTS        Nortel-Magellan-Passport-MgmtInterfacesMIB
--    INCLUDES     { mgmtInterfacesGroupBE01A }

mgmtInterfacesCapabilities OBJECT IDENTIFIER ::= { mgmtInterfacesMIB 3 }
mgmtInterfacesCapabilitiesBE OBJECT IDENTIFIER ::= { mgmtInterfacesCapabilities 5 }
mgmtInterfacesCapabilitiesBE01 OBJECT IDENTIFIER ::= { mgmtInterfacesCapabilitiesBE 2 }
mgmtInterfacesCapabilitiesBE01A OBJECT IDENTIFIER ::= { mgmtInterfacesCapabilitiesBE01 2 }





END
