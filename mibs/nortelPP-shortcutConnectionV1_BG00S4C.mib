Nortel-Magellan-Passport-ShortcutConnectionMIB
DEFINITIONS ::= BEGIN



IMPORTS

      OBJECT-TYPE
   FROM RFC-1212

      passportMIBs
   FROM Nortel-Magellan-Passport-UsefulDefinitionsMIB

      Counter32,
      RowPointer,
      DisplayString,
      StorageType,
      RowStatus,
      Integer32,
      Unsigned32
   FROM Nortel-Magellan-Passport-StandardTextualConventionsMIB

      NonReplicated,
      HexString
   FROM Nortel-Magellan-Passport-TextualConventionsMIB

      vrIndex,
      vrPpIndex,
      vrPp
   FROM Nortel-Magellan-Passport-VirtualRouterMIB;




-- LAST-UPDATED   "9906090000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     ShortcutConnection Enterprise MIB."

shortcutConnectionMIB OBJECT IDENTIFIER ::= { passportMIBs 78 }









-- 
-- *** THIS SUBTREE CURRENTLY NOT IMPLEMENTED ***
-- 

-- Vr/<string> Pp/<string> ShortcutConnection/n
-- This component represents a shortcut connection (SVC) for use by 
-- NHRP.

vrPpSc OBJECT IDENTIFIER ::= { vrPp 16 }



vrPpScRowStatusTable OBJECT-TYPE
   SYNTAX     SEQUENCE OF VrPpScRowStatusEntry
   ACCESS     not-accessible
   STATUS     mandatory
   DESCRIPTION
     "*** THIS TABLE CURRENTLY NOT IMPLEMENTED ***

      This entry controls the addition and deletion of 
      vrPpSc components."
::= { vrPpSc 1 }

vrPpScRowStatusEntry OBJECT-TYPE
   SYNTAX     VrPpScRowStatusEntry
   ACCESS     not-accessible
   STATUS     mandatory
   DESCRIPTION
     "A single entry in the table represents a single 
      vrPpSc component."
   INDEX {
      vrIndex,
      vrPpIndex,
      vrPpScIndex }
::= { vrPpScRowStatusTable 1 }

VrPpScRowStatusEntry ::= SEQUENCE {
   vrPpScRowStatus
      RowStatus,
   vrPpScComponentName
      DisplayString,
   vrPpScStorageType
      StorageType,
   vrPpScIndex
      Integer32 }

vrPpScRowStatus OBJECT-TYPE
   SYNTAX     RowStatus 
   ACCESS     read-only
   STATUS     mandatory
   DESCRIPTION
     "This variable is used as the basis for SNMP naming of
      vrPpSc components.
      These components cannot be added nor deleted."
::= { vrPpScRowStatusEntry 1 }

vrPpScComponentName OBJECT-TYPE
   SYNTAX     DisplayString 
   ACCESS     read-only
   STATUS     mandatory
   DESCRIPTION
     "This variable provides the component's string name for
      use with the ASCII Console Interface"
::= { vrPpScRowStatusEntry 2 }

vrPpScStorageType OBJECT-TYPE
   SYNTAX     StorageType 
   ACCESS     read-only
   STATUS     mandatory
   DESCRIPTION
     "This variable represents the storage type value for the
      vrPpSc tables."
::= { vrPpScRowStatusEntry 4 }

vrPpScIndex OBJECT-TYPE
   SYNTAX     Integer32 (0..1023)
   ACCESS     not-accessible
   STATUS     mandatory
   DESCRIPTION
     "This variable represents the index for the vrPpSc tables."
::= { vrPpScRowStatusEntry 10 }

vrPpScOperTable OBJECT-TYPE
   SYNTAX     SEQUENCE OF VrPpScOperEntry
   ACCESS     not-accessible
   STATUS     mandatory
   DESCRIPTION
     "*** THIS TABLE CURRENTLY NOT IMPLEMENTED ***

      This group contains the operational status attributes of the 
      ShortcutConnection component."
::= { vrPpSc 10 }

vrPpScOperEntry OBJECT-TYPE
   SYNTAX     VrPpScOperEntry
   ACCESS     not-accessible
   STATUS     mandatory
   DESCRIPTION
     "An entry in the vrPpScOperTable."
   INDEX {
      vrIndex,
      vrPpIndex,
      vrPpScIndex }
::= { vrPpScOperTable 1 }

VrPpScOperEntry ::= SEQUENCE {
   vrPpScRemoteNbmaAddress
      HexString,
   vrPpScAge
      Unsigned32,
   vrPpScMtu
      Unsigned32,
   vrPpScConnSource
      INTEGER,
   vrPpScType
      INTEGER }

vrPpScRemoteNbmaAddress OBJECT-TYPE
   SYNTAX     HexString (SIZE (0..20))
   ACCESS     read-only
   STATUS     mandatory
   DESCRIPTION
     "This attribute indicates the NBMA address of the far (remote) end."
::= { vrPpScOperEntry 1 }

vrPpScAge OBJECT-TYPE
   SYNTAX     Unsigned32 (0..4292967295)
   ACCESS     read-only
   STATUS     mandatory
   DESCRIPTION
     "This attribute indicates how long the connection has been up."
::= { vrPpScOperEntry 2 }

vrPpScMtu OBJECT-TYPE
   SYNTAX     Unsigned32 (0..0 | 576..18944)
   ACCESS     read-only
   STATUS     mandatory
   DESCRIPTION
     "This attribute indicates the Layer 2 MTU (that is, CPCS-SDU for 
      ATM) of this connection."
::= { vrPpScOperEntry 3 }

vrPpScConnSource OBJECT-TYPE
   SYNTAX     INTEGER  {
                 local(1),
                 remote(2) }
   ACCESS     read-only
   STATUS     mandatory
   DESCRIPTION
     "This attributes indicates which end originated the connect request 
      for this connection."
::= { vrPpScOperEntry 4 }

vrPpScType OBJECT-TYPE
   SYNTAX     INTEGER  {
                 unidirectional(1),
                 bidirectional(2) }
   ACCESS     read-only
   STATUS     mandatory
   DESCRIPTION
     "This attributes indicates the type of this connection."
::= { vrPpScOperEntry 5 }

vrPpScStatsTable OBJECT-TYPE
   SYNTAX     SEQUENCE OF VrPpScStatsEntry
   ACCESS     not-accessible
   STATUS     mandatory
   DESCRIPTION
     "*** THIS TABLE CURRENTLY NOT IMPLEMENTED ***

      This group contains the statistical attributes of the 
      ShortcutConnection component."
::= { vrPpSc 11 }

vrPpScStatsEntry OBJECT-TYPE
   SYNTAX     VrPpScStatsEntry
   ACCESS     not-accessible
   STATUS     mandatory
   DESCRIPTION
     "An entry in the vrPpScStatsTable."
   INDEX {
      vrIndex,
      vrPpIndex,
      vrPpScIndex }
::= { vrPpScStatsTable 1 }

VrPpScStatsEntry ::= SEQUENCE {
   vrPpScTxFrames
      Counter32,
   vrPpScRxFrames
      Counter32 }

vrPpScTxFrames OBJECT-TYPE
   SYNTAX     Counter32 
   ACCESS     read-only
   STATUS     mandatory
   DESCRIPTION
     "This attribute counts the frames transmitted over this connection.
      This counter wraps to zero when the maximum value is exceeded."
::= { vrPpScStatsEntry 1 }

vrPpScRxFrames OBJECT-TYPE
   SYNTAX     Counter32 
   ACCESS     read-only
   STATUS     mandatory
   DESCRIPTION
     "This attributes counts the frames received over this connection.
      This counter wraps to zero when the maximum value is exceeded."
::= { vrPpScStatsEntry 2 }

-- 
-- *** THIS SUBTREE CURRENTLY NOT IMPLEMENTED ***
-- 

-- An AtmConnection component is created for each ATM connection 
-- established by an application. It shows where the data traffic for this 
-- connection is directed.

vrPpScAtmCon OBJECT IDENTIFIER ::= { vrPpSc 4 }



vrPpScAtmConRowStatusTable OBJECT-TYPE
   SYNTAX     SEQUENCE OF VrPpScAtmConRowStatusEntry
   ACCESS     not-accessible
   STATUS     mandatory
   DESCRIPTION
     "*** THIS TABLE CURRENTLY NOT IMPLEMENTED ***

      This entry controls the addition and deletion of 
      vrPpScAtmCon components."
::= { vrPpScAtmCon 1 }

vrPpScAtmConRowStatusEntry OBJECT-TYPE
   SYNTAX     VrPpScAtmConRowStatusEntry
   ACCESS     not-accessible
   STATUS     mandatory
   DESCRIPTION
     "A single entry in the table represents a single 
      vrPpScAtmCon component."
   INDEX {
      vrIndex,
      vrPpIndex,
      vrPpScIndex,
      vrPpScAtmConIndex }
::= { vrPpScAtmConRowStatusTable 1 }

VrPpScAtmConRowStatusEntry ::= SEQUENCE {
   vrPpScAtmConRowStatus
      RowStatus,
   vrPpScAtmConComponentName
      DisplayString,
   vrPpScAtmConStorageType
      StorageType,
   vrPpScAtmConIndex
      NonReplicated }

vrPpScAtmConRowStatus OBJECT-TYPE
   SYNTAX     RowStatus 
   ACCESS     read-only
   STATUS     mandatory
   DESCRIPTION
     "This variable is used as the basis for SNMP naming of
      vrPpScAtmCon components.
      These components cannot be added nor deleted."
::= { vrPpScAtmConRowStatusEntry 1 }

vrPpScAtmConComponentName OBJECT-TYPE
   SYNTAX     DisplayString 
   ACCESS     read-only
   STATUS     mandatory
   DESCRIPTION
     "This variable provides the component's string name for
      use with the ASCII Console Interface"
::= { vrPpScAtmConRowStatusEntry 2 }

vrPpScAtmConStorageType OBJECT-TYPE
   SYNTAX     StorageType 
   ACCESS     read-only
   STATUS     mandatory
   DESCRIPTION
     "This variable represents the storage type value for the
      vrPpScAtmCon tables."
::= { vrPpScAtmConRowStatusEntry 4 }

vrPpScAtmConIndex OBJECT-TYPE
   SYNTAX     NonReplicated 
   ACCESS     not-accessible
   STATUS     mandatory
   DESCRIPTION
     "This variable represents the index for the vrPpScAtmCon tables."
::= { vrPpScAtmConRowStatusEntry 10 }

vrPpScAtmConOperTable OBJECT-TYPE
   SYNTAX     SEQUENCE OF VrPpScAtmConOperEntry
   ACCESS     not-accessible
   STATUS     mandatory
   DESCRIPTION
     "*** THIS TABLE CURRENTLY NOT IMPLEMENTED ***

      This attribute group contains the operational attributes for the 
      NapAtmConnection component."
::= { vrPpScAtmCon 10 }

vrPpScAtmConOperEntry OBJECT-TYPE
   SYNTAX     VrPpScAtmConOperEntry
   ACCESS     not-accessible
   STATUS     mandatory
   DESCRIPTION
     "An entry in the vrPpScAtmConOperTable."
   INDEX {
      vrIndex,
      vrPpIndex,
      vrPpScIndex,
      vrPpScAtmConIndex }
::= { vrPpScAtmConOperTable 1 }

VrPpScAtmConOperEntry ::= SEQUENCE {
   vrPpScAtmConNextHop
      RowPointer }

vrPpScAtmConNextHop OBJECT-TYPE
   SYNTAX     RowPointer 
   ACCESS     read-only
   STATUS     mandatory
   DESCRIPTION
     "This attribute shows the component name of the AtmIf Vcc Ep or 
      AtmCon component to which this switched connection is 
      established."
::= { vrPpScAtmConOperEntry 1 }




-- 
-- Version and Compliance statements
-- 



-- Object-Group Statement:
-- A list of all current accessible leaf objects.

-- OBJECTS { vrPpScType,
--           vrPpScMtu,
--           vrPpScTxFrames,
--           vrPpScComponentName,
--           vrPpScAtmConStorageType,
--           vrPpScAtmConRowStatus,
--           vrPpScRxFrames,
--           vrPpScAge,
--           vrPpScStorageType,
--           vrPpScRowStatus,
--           vrPpScRemoteNbmaAddress,
--           vrPpScConnSource,
--           vrPpScAtmConNextHop,
--           vrPpScAtmConComponentName }
-- STATUS  mandatory
-- DESCRIPTION
--   "A list of all current accessible leaf objects."

shortcutConnectionGroup OBJECT IDENTIFIER ::= { shortcutConnectionMIB 1 }
shortcutConnectionGroupBE OBJECT IDENTIFIER ::= { shortcutConnectionGroup 5 }
shortcutConnectionGroupBE01 OBJECT IDENTIFIER ::= { shortcutConnectionGroupBE 2 }
shortcutConnectionGroupBE01A OBJECT IDENTIFIER ::= { shortcutConnectionGroupBE01 2 }



-- Agent-Capabilities Statement:

-- PRODUCT-RELEASE "Passport Release 7.0 ShortcutConnection."
-- STATUS          mandatory
-- DESCRIPTION     "ShortcutConnection MIB: MIB Version BE01A,
--                  Software Version BG00S4C."
-- SUPPORTS        Nortel-Magellan-Passport-ShortcutConnectionMIB
--    INCLUDES     { shortcutConnectionGroupBE01A }

shortcutConnectionCapabilities OBJECT IDENTIFIER ::= { shortcutConnectionMIB 3 }
shortcutConnectionCapabilitiesBE OBJECT IDENTIFIER ::= { shortcutConnectionCapabilities 5 }
shortcutConnectionCapabilitiesBE01 OBJECT IDENTIFIER ::= { shortcutConnectionCapabilitiesBE 2 }
shortcutConnectionCapabilitiesBE01A OBJECT IDENTIFIER ::= { shortcutConnectionCapabilitiesBE01 2 }





END
