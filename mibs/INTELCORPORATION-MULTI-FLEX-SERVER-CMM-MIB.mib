-- INTEL CONFIDENTIAL
-- Copyright 2006, 2007
-- Intel Corporation All Rights Reserved.
--
-- The source code contained or described herein and all documents related to
-- the source code ("Material") are owned by Intel Corporation or its
-- suppliers and licensors. Title to the Material remains with Intel
-- Corporation or its suppliers and licensors. The Material contains trade
-- secrets and proprietary and confidential information of Intel or its
-- suppliers and licensors. The Material is protected by worldwide copyright
-- and trade secret laws and treaty provisions. No part of the Material may be
-- used, copied, reproduced, modified, published, uploaded, posted,
-- transmitted, distributed, or disclosed in any way without Intel's prior
-- express written permission.
--
-- Unless otherwise expressly permitted by Intel in a separate license
-- agreement, use of the Material is subject to the copyright notices,
-- trademarks, warranty, use, and disclosure restrictions reflected on the
-- outside of the media, in the documents themselves, and in the "About" or
-- "Read Me" or similar file contained within this source code. Unless
-- otherwise expressly agreed by Intel in writing, you may not remove
-- or alter such notices in any way.
--

    INTELCORPORATION-MULTI-FLEX-SERVER-CMM-MIB DEFINITIONS ::= BEGIN

        IMPORTS
            MODULE-IDENTITY, OBJECT-TYPE, OBJECT-IDENTITY, Integer32, Unsigned32
                FROM SNMPv2-SMI

            OBJECT-GROUP
                FROM SNMPv2-CONF

            DisplayString, PhysAddress
                FROM SNMPv2-TC

            regModule, groups
                FROM INTELCORPORATION-MULTI-FLEX-SERVER-REG

            Index, Presence, Power, PowerLedStates, FaultLedStates,
            PresenceLedStates, IdromBinary16 
                FROM INTELCORPORATION-MULTI-FLEX-SERVER-TC

            chassis
                FROM INTELCORPORATION-MULTI-FLEX-SERVER-MIB;


            multiFlexServerCmmMibModule MODULE-IDENTITY
                LAST-UPDATED "200708161330Z"        -- August 16, 2007 at 13:30 GMT
                ORGANIZATION
                    "Intel Corporation"
                CONTACT-INFO
                    "Brian Kurle
                    Intel Corporation
                    JF5-2-C3
                    Tel: 503-712-5032
                    E-Mail: brianx.j.kurle@intel.com"
                DESCRIPTION
                    "CMM Module of the Multi-Flex Server"
                REVISION "200708161330Z"        -- August 16, 2007 at 13:30 GMT
                DESCRIPTION
                    "Reordered Revision to reverse chronological as some
                    browsers choke, cleaned up some other simple nit-picky
                    errors"
                REVISION "200707111230Z"        -- July 11, 2007 at 12:30 GMT
                DESCRIPTION
                    "Dropped cmmSoftwareVersion as it is superfluous
                    (currently the same as the firmwareBundleID).
                    Dropped cmmBmcVersion as there is no BMC version."
                REVISION "200706072030Z"        -- June 07, 2007 at 20:30 GMT
                DESCRIPTION
                    "Added the IdromBinary16 to represent the asset tag,
                    part number, and serial number fields within the IDROM
                    fields."
                REVISION "200706071330Z"        -- June 07, 2007 at 13:30 GMT
                DESCRIPTION
                    "Corrected maximum/nominal IDROM parameters and comments"
                REVISION "200705292000Z"        -- May 29, 2007 at 20:00 GMT
                DESCRIPTION
                    "Moved presence to first column passed index to be
                    consistent with other tables"
                REVISION "200705091130Z"        -- May 09, 2007 at 11:30 GMT
                DESCRIPTION
                    "Dropped support for the GUEL as it will be accessible
                    directly via the web"
                REVISION "200704091030Z"        -- April 09, 2007 at 10:30 GMT
                DESCRIPTION
                    "Renamed cmmFirmwareVersion to cmmBmcFirmwareVersion to
                    clarify which firmware"
                REVISION "200703121800Z"        -- March 12, 2007 at 18:00 GMT
                DESCRIPTION
                    "Moved FirmwareBundleId from chassis to CMM Tree.
                    cmmTable data now complies with IDROM (DID/DSD)
                    information.
                    Added cmmPowerLedStates, cmmFaultLedStates, &
                    cmmPresenceLedStates to cmmTable.
                    Added ebfFirmwareVersion.
                    Added cmmFirmwareVersion.

                    Renumbered / reorganized accordingly"
                REVISION "200703061030Z"        -- March 06, 2007 at 10:30 GMT
                DESCRIPTION
                    "Changed Mask representation from an Opaque to a
                    DisplayString at the request of the architects such
                    that it now is an ASCII representation of bit string
                    reflecting the presence with the left most 'bit' being
                    bit 1 and max* bits being represented."
                REVISION "200702221700Z"        -- February 22, 2007 at 17:00 GMT
                DESCRIPTION
                    "Renamed MIB file and updated internal relevance to
                    formal product name Multi-Flex Server"
                REVISION "200611070701Z"        -- November 07, 2006 at 07:01 GMT
                DESCRIPTION
                    "Consolidated use of Presence datatype and changed 'theChassis' to 'chassis'"
                REVISION "200609291529Z"        -- September 29, 2006 at 15:29 GMT
                DESCRIPTION
                    "Partitioned off and created as it's own module"
                ::= { regModule 11 }


-- ----------------------------------------------------------------------------
--
-- CMM group.
--
-- This group contains information about CMM.
--
-- ----------------------------------------------------------------------------

--
-- CMM relevant pieces stored in the chassis
--

        maxCmms OBJECT-TYPE
            SYNTAX Unsigned32
            MAX-ACCESS read-only
            STATUS current
            DESCRIPTION
                "Maximum number of CMMs possible in this chassis."
            ::= { chassis 11 }

        numOfCmms OBJECT-TYPE
            SYNTAX Integer32
            MAX-ACCESS read-only
            STATUS current
            DESCRIPTION
                "The number of CMMs in the system.

                This is a bit of overkill as the first version doesn't have
                more than one CMM, but as there is talk of future revisions
                containing a second, this is designed in to be consistent
                with the other modules."
            ::= { chassis 21 }

        cmmPresenceMask OBJECT-TYPE
            SYNTAX DisplayString
            MAX-ACCESS read-only
            STATUS current
            DESCRIPTION
                "ASCII representation of bit string reflecting the presence
                of the CMMs with the left most 'bit' being bit 1 and
                maxCmms bits being represented.

                Thus, '1' would express that CMM 1 (of the only one CMM) is
                present"
            ::= { chassis 31 }

--
-- CMM tree
--

        cmms OBJECT-IDENTITY
            STATUS current
            DESCRIPTION
                "Container for CMM specific information as well as all
                components logically contained within."
            ::= { chassis 201 }


        firmwareBundleId OBJECT-TYPE
            SYNTAX DisplayString
            MAX-ACCESS read-only
            STATUS current
            DESCRIPTION
                "Firmware bundle identification (Tag of all
                firmware/software versions on all FRUs)"
            ::= { cmms 1 }


--
-- Info on the CMM, itself
--

        cmmTable OBJECT-TYPE
            SYNTAX SEQUENCE OF CmmEntry
            MAX-ACCESS not-accessible
            STATUS current
            DESCRIPTION
                "Each row describes a CMM in the chassis"
            ::= { cmms 2 }

        cmmEntry OBJECT-TYPE
            SYNTAX CmmEntry
            MAX-ACCESS not-accessible
            STATUS current
            DESCRIPTION
                ".."
            INDEX { cmmIndex }
            ::= { cmmTable 1 }

        CmmEntry ::=
            SEQUENCE {

                cmmIndex                            Index,
                cmmPresence                         Presence,
                cmmVendor                           DisplayString,
                cmmMfgDate                          DisplayString,
                cmmDeviceName                       DisplayString,
                cmmPart                             IdromBinary16,
                cmmSerialNo                         IdromBinary16,
                cmmMaximumPower                     Power,
                cmmNominalPower                     Power,
                cmmAssetTag                         IdromBinary16,
                cmmExternalMac                      PhysAddress,
                cmmChassisMac                       PhysAddress,
                cmmPowerLed                         PowerLedStates,
                cmmFaultLed                         FaultLedStates,
                cmmPresenceLed                      PresenceLedStates,
                cmmEbfFirmwareVersion               DisplayString

             }

        cmmIndex OBJECT-TYPE
            SYNTAX Index
            MAX-ACCESS read-only
            STATUS current
            DESCRIPTION
                "column used to identify a particular CMM."
            ::= { cmmEntry 1 }

        cmmPresence OBJECT-TYPE
            SYNTAX Presence
            MAX-ACCESS read-only
            STATUS current
            DESCRIPTION
                "Flag whether this CMM is present (forward thinking for
                future products that will contain redundant CMMs)"
            ::= { cmmEntry 2 }

--
-- IDROM info
--

        cmmVendor OBJECT-TYPE
            SYNTAX DisplayString
            MAX-ACCESS read-only
            STATUS current
            DESCRIPTION
                "Device manufacturer"
            ::= { cmmEntry 3 }

        cmmMfgDate OBJECT-TYPE
            SYNTAX DisplayString
            MAX-ACCESS read-only
            STATUS current
            DESCRIPTION
                "Manufacture date/time"
            ::= { cmmEntry 4 }

        cmmDeviceName OBJECT-TYPE
            SYNTAX DisplayString
            MAX-ACCESS read-only
            STATUS current
            DESCRIPTION
                "Device Name"
            ::= { cmmEntry 5 }

        cmmPart OBJECT-TYPE
            SYNTAX IdromBinary16
            MAX-ACCESS read-only
            STATUS current
            DESCRIPTION
                "Device Part Number"
            ::= { cmmEntry 6 }

        cmmSerialNo OBJECT-TYPE
            SYNTAX IdromBinary16
            MAX-ACCESS read-only
            STATUS current
            DESCRIPTION
                "Device Serial Number"
            ::= { cmmEntry 7 }

        cmmMaximumPower OBJECT-TYPE
            SYNTAX Power
            MAX-ACCESS read-only
            STATUS current
            DESCRIPTION
                "Static maximum power generation / consumption (in watts):

                <0      - Negative numbers indicate device consumes power (in watts)
                >0      - Positive numbers indicate device generates power (in watts)
                0       - Device is passive (does not not consume or generate power)
                -1      - Maximum power generation/consumption not known or specified"
            ::= { cmmEntry 8 }

        cmmNominalPower OBJECT-TYPE
            SYNTAX Power
            MAX-ACCESS read-only
            STATUS current
            DESCRIPTION
                "Static Nominal power generation / consumption (in watts):

                <0      - Negative numbers indicate device consumes power (in watts)
                >0      - Positive numbers indicate device generates power (in watts)
                0       - Device is passive (does not not consume or generate power)
                -1      - Nominal power generation/consumption not known or specified"
            ::= { cmmEntry 9 }

        cmmAssetTag OBJECT-TYPE
            SYNTAX IdromBinary16
            MAX-ACCESS read-only
            STATUS current
            DESCRIPTION
                "Asset Tag # of device"
            ::= { cmmEntry 10 }

--
-- DSD IDROM info
--

        cmmExternalMac OBJECT-TYPE
            SYNTAX PhysAddress
            MAX-ACCESS read-only
            STATUS current
            DESCRIPTION
                "MAC Address of external (front panel) Ethernet interface"
            ::= { cmmEntry 11 }

        cmmChassisMac OBJECT-TYPE
            SYNTAX PhysAddress
            MAX-ACCESS read-only
            STATUS current
            DESCRIPTION
                "MAC Address of internal (chassis) Ethernet interface"
            ::= { cmmEntry 12 }

--
-- Physical Interface
--

        cmmPowerLed OBJECT-TYPE
            SYNTAX PowerLedStates
            MAX-ACCESS read-only
            STATUS current
            DESCRIPTION
                "State of the Power LED on the CMM"
            ::= { cmmEntry 13 }

        cmmFaultLed OBJECT-TYPE
            SYNTAX FaultLedStates
            MAX-ACCESS read-only
            STATUS current
            DESCRIPTION
                "State of the Fault LED on the CMM"
            ::= { cmmEntry 14 }

        cmmPresenceLed OBJECT-TYPE
            SYNTAX PresenceLedStates
            MAX-ACCESS read-write
            STATUS current
            DESCRIPTION
                "State of the Presence LED on the CMM (and optionally
                intiate identification)"
            ::= { cmmEntry 15 }

--
-- Revision info
--

        cmmEbfFirmwareVersion OBJECT-TYPE
            SYNTAX DisplayString
            MAX-ACCESS read-only
            STATUS current
            DESCRIPTION
                "Firmware version of the EBF"
            ::= { cmmEntry 16 }


--
-- (CMM) Group information
--

        cmmGroup OBJECT-GROUP
            OBJECTS {

                maxCmms,
                numOfCmms,
                cmmPresenceMask,
                firmwareBundleId,

                cmmIndex,
                cmmPresence,
                cmmVendor,
                cmmMfgDate,
                cmmDeviceName,
                cmmPart,
                cmmSerialNo,
                cmmMaximumPower,
                cmmNominalPower,
                cmmAssetTag,
                cmmExternalMac,
                cmmChassisMac,
                cmmPowerLed,
                cmmFaultLed,
                cmmPresenceLed,
                cmmEbfFirmwareVersion

        }
            STATUS current
            DESCRIPTION
                "Description."
            ::= { groups 11 }


    END

--  vim:ts=4:ai:nohls:nowrap:expandtab
