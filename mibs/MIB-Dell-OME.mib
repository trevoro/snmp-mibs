-------------------------------------------------------------------------------
-- OM Essentials MIB : OME.mib 
-- 
-- Copyright (c) 2012 Dell Inc. 
-- All Rights Reserved. 
-- 
-- The information and functionality described by this MIB file, 
-- like many MIB files, is subject to change without notice. 
-- Please examine the version number of this MIB and compare it 
-- to the version number you are expecting. 
-- 
-- MIB Version 1.1                      30 Oct 2012
-- 
--
-------------------------------------------------------------------------------


-------------------------------------------------------------------------------
-- Begin MIB
-------------------------------------------------------------------------------

MIB-Dell-OME DEFINITIONS ::= BEGIN

IMPORTS
    enterprises
        FROM RFC1155-SMI
    OBJECT-TYPE
        FROM RFC-1212
    TRAP-TYPE
        FROM RFC-1215
    DisplayString
        FROM RFC1213-MIB;


-------------------------------------------------------------------------------
-- OME Branch Location (.1.3.6.1.4.1.674.11000.1000.100)
-------------------------------------------------------------------------------

dell                            OBJECT IDENTIFIER ::= { enterprises    674   }
enterpriseSW                    OBJECT IDENTIFIER ::= { dell           11000 }
sysMgmtBranch					OBJECT IDENTIFIER ::= { enterpriseSW   1000  }
omEssentialsMIB	               	OBJECT IDENTIFIER ::= { sysMgmtBranch   100  }
omEssentialsTrap                OBJECT IDENTIFIER ::= { omEssentialsMIB   1  }

-------------------------------------------------------------------------------
--
-- Custom Types
--
-------------------------------------------------------------------------------

DellString                      ::= DisplayString (SIZE (0..512))
DellString1                      ::= DisplayString (SIZE (0..128))

-------------------------------------------------------------------------------
--
-- Trap Attributes (Varbinds)
--
-------------------------------------------------------------------------------

omeAlertMessage                           OBJECT-TYPE
    SYNTAX      DellString
    ACCESS      read-only
    STATUS      mandatory
    DESCRIPTION
       "Message in the alert."
    ::= { omEssentialsTrap 1 }
omeAlertDevice                           OBJECT-TYPE
    SYNTAX      DellString
    ACCESS      read-only
    STATUS      mandatory
    DESCRIPTION
       "Name of the device where alert originated."
    ::= { omEssentialsTrap 2 }
omeAlertSeverity                 OBJECT-TYPE 
      SYNTAX         DellString1
      ACCESS         read-only 
      STATUS         mandatory 
      DESCRIPTION 
         "Original severity of the alert." 
    ::= { omEssentialsTrap 3 }

-------------------------------------------------------------------------------
--
-- Traps
--
-------------------------------------------------------------------------------

omeTestAlert           TRAP-TYPE 
    ENTERPRISE  omEssentialsTrap 
    VARIABLES  { omeAlertMessage, omeAlertDevice, omeAlertSeverity } 
    DESCRIPTION 
       "Test alert forwarded from OM Essentials." 

    --#TYPE		"Test alert forwarded from OM Essentials." 
    --#SUMMARY	 	"Test alert from OM Essentials. Sending device: %s, Severity: %s, Message: %s." 
    --#ARGUMENTS	{1,2,0} 
    --#SEVERITY	 	INFORMATIONAL 
    ::= 1

omeAlertSystemUp                                   TRAP-TYPE
    ENTERPRISE  omEssentialsTrap
    VARIABLES { omeAlertMessage, omeAlertDevice }
    DESCRIPTION
       "System up message from OM Essentials. Sent when OM Essentials detects a device has come online."

    --#TYPE       	"System Up Message from OM Essentials"
    --#SUMMARY		"%s: %s" 
    --#ARGUMENTS	{0,1} 
    --#SEVERITY   	INFORMATIONAL

    ::= 1000

omeAlertSystemDown               TRAP-TYPE 
    ENTERPRISE  omEssentialsTrap 
    VARIABLES  { omeAlertMessage, omeAlertDevice } 
    DESCRIPTION 
       "System down message from OM Essentials. Sent when OM Essentials detects a device has gone offline." 

    --#TYPE		"System Down Message from OM Essentials" 
    --#SUMMARY		"%s: %s" 
    --#ARGUMENTS	{0,1} 
    --#SEVERITY		CRITICAL 

    ::= 1001 
 
omeAlertForwardedAlert           TRAP-TYPE 
    ENTERPRISE  omEssentialsTrap 
    VARIABLES  { omeAlertMessage, omeAlertDevice, omeAlertSeverity } 
    DESCRIPTION 
       "Forwarded alert from OM Essentials. The event may have originated as an SNMP trap or CIM indication to the OM Essentials Console. The alert format is normalized." 

    --#TYPE		"Forwarded Alert from OM Essentials" 
    --#SUMMARY	 	"Forwarded Alert from OM Essentials. Sending device: %s, Severity: %s, Message: %s." 
    --#ARGUMENTS	{1,2,0} 
    --#SEVERITY	 	INFORMATIONAL 
    ::= 2000

-- 
-- Device Status Internal Alerts.
-- 

omeAlertUnknownStatus           TRAP-TYPE 
    ENTERPRISE  omEssentialsTrap 
    VARIABLES  { omeAlertDevice } 
    DESCRIPTION 
       "System monitoring alert from Essentials. Sent when status of the remote device is Unknown." 

    --#TYPE		"Status Alert" 
    --#SUMMARY	 	"Device %s has changed status to Unknown." 
    --#ARGUMENTS	{0}  
    --#SEVERITY	 	UNKNOWN 
    ::= 3001

omeAlertNormalStatus           TRAP-TYPE 
    ENTERPRISE  omEssentialsTrap 
    VARIABLES  { omeAlertDevice } 
    DESCRIPTION 
       "System monitoring alert from Essentials. Sent when status of the remote device is Normal." 

    --#TYPE		"Status Alert" 
    --#SUMMARY	 	"Device %s has changed status to Normal." 
    --#ARGUMENTS	{0}  
    --#SEVERITY	 	INFORMATIONAL 
    ::= 3002	

omeAlertWarningStatus           TRAP-TYPE 
    ENTERPRISE  omEssentialsTrap 
    VARIABLES  { omeAlertDevice } 
    DESCRIPTION 
       "System monitoring alert from Essentials. Sent when status of the remote device is Warning." 

    --#TYPE		"Status Alert" 
    --#SUMMARY	 	"Device %s has changed status to Warning." 
    --#ARGUMENTS	{0}  
    --#SEVERITY	 	MINOR 
    ::= 3003

omeAlertCriticalStatus           TRAP-TYPE 
    ENTERPRISE  omEssentialsTrap 
    VARIABLES  { omeAlertDevice } 
    DESCRIPTION 
       "System monitoring alert from Essentials. Sent when status of the remote device is Critical." 

    --#TYPE		"Status Alert" 
    --#SUMMARY	 	"Device %s has changed status to Critical." 
    --#ARGUMENTS	{0} 
    --#SEVERITY	 	CRITICAL 
    ::= 3004	
	
END

-------------------------------------------------------------------------------
-- End MIB
-------------------------------------------------------------------------------
