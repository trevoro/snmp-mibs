--			Ascend mibqos MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBQOS-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibqosProfile  OBJECT IDENTIFIER ::= { configuration 169}

	-- The mibqosProfile table
	--
	-- This table contains parameters for the mibqosProfile profile
	--

    mibqosProfileTable	OBJECT-TYPE
	SYNTAX		SEQUENCE OF MibqosProfileEntry
	ACCESS		not-accessible
	STATUS		mandatory
	DESCRIPTION	"A list of mibqosProfile profile entries."
	::= { mibqosProfile 1 }

    mibqosProfileEntry	OBJECT-TYPE
	SYNTAX		MibqosProfileEntry
	ACCESS		not-accessible
	STATUS		mandatory
	DESCRIPTION	"A mibqosProfile entry containing objects that
			 maps to the parameters of mibqosProfile profile."
	INDEX		{ qosProfile-Index-o }
	::= { mibqosProfileTable 1 }

    MibqosProfileEntry ::=
	SEQUENCE {
	    qosProfile-Index-o
		INTEGER,
	    qosProfile-Enabled
		INTEGER,
	    qosProfile-AllowClientDscp
		INTEGER,
	    qosProfile-Action-o
		INTEGER
	}

    qosProfile-Index-o	OBJECT-TYPE
	SYNTAX	INTEGER
	ACCESS	read-only
	STATUS	mandatory
	DESCRIPTION	""
	::= { mibqosProfileEntry 1 }

    qosProfile-Enabled	OBJECT-TYPE
	SYNTAX	INTEGER {
		    no (1),
		    yes (2)
		}
	ACCESS	read-write
	STATUS	mandatory
	DESCRIPTION	"System QoS support Enabled/Disabled"
	::= { mibqosProfileEntry 2 }

    qosProfile-AllowClientDscp	OBJECT-TYPE
	SYNTAX	INTEGER {
		    no (1),
		    yes (2)
		}
	ACCESS	read-write
	STATUS	mandatory
	DESCRIPTION	"System QoS support Enabled/Disabled"
	::= { mibqosProfileEntry 3 }

    qosProfile-Action-o	OBJECT-TYPE
	SYNTAX	INTEGER {
		    noAction (1),
		    createProfile (2),
		    deleteProfile (3)
		}
	ACCESS	read-write
	STATUS	mandatory
	DESCRIPTION	""
	::= { mibqosProfileEntry 4 }


	-- The mibqosProfile__tag_map table
	--
	-- This table contains parameters for the mibqosProfile__tag_map profile
	--

    mibqosProfile-TagMapTable	OBJECT-TYPE
	SYNTAX		SEQUENCE OF MibqosProfile-TagMapEntry
	ACCESS		not-accessible
	STATUS		mandatory
	DESCRIPTION	"A list of mibqosProfile__tag_map profile entries."
	::= { mibqosProfile 2 }

    mibqosProfile-TagMapEntry	OBJECT-TYPE
	SYNTAX		MibqosProfile-TagMapEntry
	ACCESS		not-accessible
	STATUS		mandatory
	DESCRIPTION	"A mibqosProfile__tag_map entry containing objects that
			 maps to the parameters of mibqosProfile__tag_map profile."
	INDEX		{ qosProfile-TagMap-Index-o, qosProfile-TagMap-Index1-o }
	::= { mibqosProfile-TagMapTable 1 }

    MibqosProfile-TagMapEntry ::=
	SEQUENCE {
	    qosProfile-TagMap-Index-o
		INTEGER,
	    qosProfile-TagMap-Index1-o
		INTEGER,
	    qosProfile-TagMap-Active
		INTEGER,
	    qosProfile-TagMap-Dscp
		DisplayString,
	    qosProfile-TagMap-QosTag
		INTEGER
	}

    qosProfile-TagMap-Index-o	OBJECT-TYPE
	SYNTAX	INTEGER
	ACCESS	read-only
	STATUS	mandatory
	DESCRIPTION	""
	::= { mibqosProfile-TagMapEntry 1 }

    qosProfile-TagMap-Index1-o	OBJECT-TYPE
	SYNTAX	INTEGER
	ACCESS	read-only
	STATUS	mandatory
	DESCRIPTION	""
	::= { mibqosProfile-TagMapEntry 2 }

    qosProfile-TagMap-Active	OBJECT-TYPE
	SYNTAX	INTEGER {
		    no (1),
		    yes (2)
		}
	ACCESS	read-write
	STATUS	mandatory
	DESCRIPTION	"Mapping Enabled/Disabled."
	::= { mibqosProfile-TagMapEntry 3 }

    qosProfile-TagMap-Dscp	OBJECT-TYPE
	SYNTAX	DisplayString
	ACCESS	read-write
	STATUS	mandatory
	DESCRIPTION	"Match DSCP value to be used to set the QOS Tag."
	::= { mibqosProfile-TagMapEntry 4 }

    qosProfile-TagMap-QosTag	OBJECT-TYPE
	SYNTAX	INTEGER
	ACCESS	read-write
	STATUS	mandatory
	DESCRIPTION	"QOS Tag to be used with the matche IP TOS byte."
	::= { mibqosProfile-TagMapEntry 5 }

END
