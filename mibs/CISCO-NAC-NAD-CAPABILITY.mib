-- *****************************************************************
-- CISCO-NAC-NAD-CAPABILITY.my:
-- Cisco CISCO-NAC-NAD-MIB AGENT-CAPABILITIES
--   
-- June 2005, Liwei Lue
--   
-- Copyright (c) 2005,-2007 by Cisco Systems, Inc.
--  
-- All rights reserved.
-- ****************************************************************

CISCO-NAC-NAD-CAPABILITY DEFINITIONS ::= BEGIN

IMPORTS
    MODULE-IDENTITY,
    Unsigned32
        FROM SNMPv2-SMI
    AGENT-CAPABILITIES
        FROM SNMPv2-CONF
    ciscoAgentCapability
        FROM CISCO-SMI;


ciscoNacNadCapability MODULE-IDENTITY
    LAST-UPDATED    "200612120000Z"
    ORGANIZATION    "Cisco Systems, Inc."
    CONTACT-INFO
            "Cisco Systems
            Customer Service

            Postal: 170 West Tasman Drive
            San Jose, CA  95134
            USA

            Tel: +1 800 553-NETS

            E-mail: cs-nac@cisco.com, cs-lan-switch-snmp@cisco.com"
    DESCRIPTION
        "The capabilities description of CISCO-NAC-NAD-MIB."
    REVISION        "200612120000Z"
    DESCRIPTION
        "Added capability statement ciscoNacNadCapCatOSV08R0601."
    REVISION        "200507010000Z"
    DESCRIPTION
        "Initial version of this MIB module."
          ::= { ciscoAgentCapability 440 }



ciscoNacNadCapCatOSV08R0501 AGENT-CAPABILITIES
    PRODUCT-RELEASE "Cisco CatOS 8.5(1) on Catalyst 6000/6500
                         and Cisco 7600 series devices."
    STATUS          current
    DESCRIPTION     "CISCO-NAC-NAD-MIB capabilities."

    SUPPORTS        CISCO-NAC-NAD-MIB
    INCLUDES        {
                        ciscoNacNadEouGlobalGroup,
                        ciscoNacNadEouAuthIpGroup,
                        ciscoNacNadEouAuthMacGroup,
                        ciscoNacNadEouIfConfigGroup,
                        ciscoNacNadEouHostGroup,
                        ciscoNacNadEouIfAdminGroup
                    }
    VARIATION       cnnEouMaxRetry
    SYNTAX          Unsigned32 (1..10 )
    DESCRIPTION     "Only a limited set of values is supported."

    VARIATION       cnnEouPort
    ACCESS          read-only
    DESCRIPTION     "Unable to set this on CatOS."

    VARIATION       cnnEouAllowIpStationId
    ACCESS          read-only
    DESCRIPTION     "Unable to set this on CatOS."

    VARIATION       cnnEouTimeoutAAA
    SYNTAX          Unsigned32 (1..60 )
    DESCRIPTION     "Only a limited set of values is supported."

    VARIATION       cnnEouTimeoutHoldPeriod
    SYNTAX          Unsigned32 (60..86400 )
    DESCRIPTION     "Only a limited set of values is supported."

    VARIATION       cnnEouTimeoutRetransmit
    SYNTAX          Unsigned32 (1..60 )
    DESCRIPTION     "Only a limited set of values is supported."

    VARIATION       cnnEouTimeoutRevalidation
    SYNTAX          Unsigned32 (0  |  5..86400 )
    DESCRIPTION     "Only a limited set of values is supported."

    VARIATION       cnnEouTimeoutStatusQuery
    SYNTAX          Unsigned32 (30..1800 )
    DESCRIPTION     "Only a limited set of values is supported."

    VARIATION       cnnEouAuthIpStorageType
    ACCESS          read-only
    DESCRIPTION     "Write/create not implemented."

    VARIATION       cnnEouAuthIpRowStatus
    SYNTAX          INTEGER  {
                        active(1),
                        createAndGo(4),
                        destroy(6)
                    }
    DESCRIPTION
        "Only limited set of enumerated values
        are supported."

    VARIATION       cnnEouAuthIpPolicy
    SYNTAX          OCTET STRING (SIZE (0..31))
    DESCRIPTION     "Only limited set of values are supported."

    VARIATION       cnnEouAuthMacStorageType
    ACCESS          read-only
    DESCRIPTION     "Write/create not implemented."

    VARIATION       cnnEouAuthMacRowStatus
    SYNTAX          INTEGER  {
                        active(1),
                        createAndGo(4),
                        destroy(6)
                    }
    DESCRIPTION
        "Only limited set of enumerated values
        are supported."

    VARIATION       cnnEouAuthMacPolicy
    SYNTAX          OCTET STRING (SIZE (0..31))
    DESCRIPTION     "Only limited set of values are supported."

    VARIATION       cnnEouIfValidateAction
    SYNTAX          INTEGER  {
                        initialize(1),
                        revalidate(2)
                    }
    DESCRIPTION
        "Only limited set of enumerated values
        are supported."

    VARIATION       cnnEouHostValidateAction
    SYNTAX          INTEGER  {
                        none(1),
                        initializeAll(2),
                        initializeAuthClientless(3),
                        initializeAuthEap(4),
                        initializeAuthStatic(5),
                        initializeIp(6),
                        initializeMac(7),
                        initializePostureToken(8),
                        revalidateAll(9),
                        revalidateAuthClientless(10),
                        revalidateAuthEap(11),
                        revalidateAuthStatic(12),
                        revalidateIp(13),
                        revalidateMac(14),
                        revalidatePostureToken(15)
                    }
    DESCRIPTION
        "Only limited set of enumerated values
        are supported."

    VARIATION       cnnEouHostValidateIpAddrType
    SYNTAX          INTEGER  {
                        ipv4(1)
                    }
    DESCRIPTION
        "Only limited set of enumerated values
        are supported."

    VARIATION       cnnEouHostQueryIpAddrType
    SYNTAX          INTEGER  {
                        ipv4(1)
                    }
    DESCRIPTION
        "Only limited set of enumerated values
        are supported."

    VARIATION       cnnEouHostResultIpAddrType
    SYNTAX          INTEGER  {
                        ipv4(1)
                    }
    DESCRIPTION
        "Only limited set of enumerated values
        are supported."

    ::= { ciscoNacNadCapability 1 }

ciscoNacNadCapCatOSV08R0601 AGENT-CAPABILITIES
    PRODUCT-RELEASE "Cisco CatOS 8.6(1)."
    STATUS          current
    DESCRIPTION     "CISCO-NAC-NAD-MIB capabilities."

    SUPPORTS        CISCO-NAC-NAD-MIB
    INCLUDES        {
                        ciscoNacNadEouGlobalGroup,
                        ciscoNacNadEouAuthIpGroup,
                        ciscoNacNadEouAuthMacGroup,
                        ciscoNacNadEouIfConfigGroup,
                        ciscoNacNadEouHostGrp,
                        ciscoNacNadEouIfAdminGroup,
                        ciscoNacNadEouIfAaaFailPolicyGrp,
                        cnnIpDeviceTrackingConfigGrp,
                        cnnEouCriticalRecoveryDelayGrp
                    }
    VARIATION       cnnEouMaxRetry
    SYNTAX          Integer32 (1..10 )
    DESCRIPTION     "Only a limited set of values is supported."

    VARIATION       cnnEouPort
    SYNTAX          Unsigned32 (4096..65535 )
    DESCRIPTION     "Only a limited set of values is supported."

    VARIATION       cnnEouRateLimit
    SYNTAX          Unsigned32 (0  |  10..200 )
    DESCRIPTION     "Only a limited set of values is supported."

    VARIATION       cnnEouTimeoutAAA
    SYNTAX          Unsigned32 (1..60 )
    DESCRIPTION     "Only a limited set of values is supported."

    VARIATION       cnnEouTimeoutHoldPeriod
    SYNTAX          Unsigned32 (60..86400 )
    DESCRIPTION     "Only a limited set of values is supported."

    VARIATION       cnnEouTimeoutRetransmit
    SYNTAX          Unsigned32 (1..60 )
    DESCRIPTION     "Only a limited set of values is supported."

    VARIATION       cnnEouTimeoutRevalidation
    SYNTAX          Unsigned32 (5..86400 )
    DESCRIPTION     "Only a limited set of values is supported."

    VARIATION       cnnEouTimeoutStatusQuery
    SYNTAX          Unsigned32 (30..1800 )
    DESCRIPTION     "Only a limited set of values is supported."

    VARIATION       cnnEouAuthIpStorageType
    ACCESS          read-only
    DESCRIPTION     "Write/create not implemented."

    VARIATION       cnnEouAuthIpRowStatus
    SYNTAX          INTEGER  {
                        active(1),
                        createAndGo(4),
                        destroy(6)
                    }
    DESCRIPTION
        "Only limited set of enumerated values
        are supported."

    VARIATION       cnnEouAuthIpPolicy
    SYNTAX          OCTET STRING (SIZE (0..31))
    DESCRIPTION     "Only limited set of values are supported."

    VARIATION       cnnEouAuthMacStorageType
    ACCESS          read-only
    DESCRIPTION     "Write/create not implemented."

    VARIATION       cnnEouAuthMacRowStatus
    SYNTAX          INTEGER  {
                        active(1),
                        createAndGo(4),
                        destroy(6)
                    }
    DESCRIPTION
        "Only limited set of enumerated values
        are supported."

    VARIATION       cnnEouAuthMacPolicy
    SYNTAX          OCTET STRING (SIZE (0..31))
    DESCRIPTION     "Only limited set of values are supported."

    VARIATION       cnnEouIfValidateAction
    SYNTAX          INTEGER  {
                        initialize(1),
                        revalidate(2)
                    }
    DESCRIPTION
        "Only limited set of enumerated values
        are supported."

    VARIATION       cnnEouHostValidateAction
    SYNTAX          INTEGER  {
                        none(1),
                        initializeAll(2),
                        initializeAuthClientless(3),
                        initializeAuthEap(4),
                        initializeAuthStatic(5),
                        initializeIp(6),
                        initializeMac(7),
                        initializePostureToken(8),
                        revalidateAll(9),
                        revalidateAuthClientless(10),
                        revalidateAuthEap(11),
                        revalidateAuthStatic(12),
                        revalidateIp(13),
                        revalidateMac(14),
                        revalidatePostureToken(15),
                        initializePostureTokenStr(23),
                        revalidatePostureTokenStr(24)
                    }
    DESCRIPTION
        "Only limited set of enumerated values
        are supported."

    VARIATION       cnnEouHostValidateIpAddrType
    SYNTAX          INTEGER  {
                        ipv4(1)
                    }
    DESCRIPTION
        "Only limited set of enumerated values
        are supported."

    VARIATION       cnnEouHostValidatePostureTokenStr
    SYNTAX          OCTET STRING (SIZE (0..32))
    DESCRIPTION     "Only limited set of values are supported."

    VARIATION       cnnEouHostQueryIpAddrType
    SYNTAX          INTEGER  {
                        ipv4(1)
                    }
    DESCRIPTION
        "Only limited set of enumerated values
        are supported."

    VARIATION       cnnEouHostQueryPostureTokenStr
    SYNTAX          OCTET STRING (SIZE (0..32))
    DESCRIPTION     "Only limited set of values are supported."

    VARIATION       cnnEouIfAaaFailPolicy
    SYNTAX          OCTET STRING (SIZE (0..31))
    DESCRIPTION     "Only limited set of values are supported."

    VARIATION       cnnIpDeviceTrackingProbeCount
    SYNTAX          Unsigned32 (1..10 )
    DESCRIPTION     "Only a limited set of values is supported."

    VARIATION       cnnIpDeviceTrackingProbeInterval
    SYNTAX          Unsigned32 (5..65535 )
    DESCRIPTION     "Only a limited set of values is supported."

    VARIATION       cnnEouCriticalRecoveryDelay
    SYNTAX          Unsigned32 (0..10000 )
    DESCRIPTION     "Only a limited set of values is supported."

    ::= { ciscoNacNadCapability 2 }

END
