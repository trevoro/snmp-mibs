-- ZyXEL Communications Corporation
-- Private Enterprise MIB definition 
  
-- This file describes the ZyXEL Communications Corporation Enterprise MIB.
-- It contains ZyXEL products OIDs, and common managed objects.

-- $Log: ZYXEL-VLAN-MAPPING-MIB.mib $ 
-- Revision 1.3  2012/09/19 08:21:16  Kevin 
-- if it's leaf node, revise the vender name from zyxel to zy 
-- Revision 1.2  2012/07/05 06:25:05  Kevin 
-- 1. upgrade from SNMP to SNMPv2  
-- 2. clean warning 
-- Revision 1.1  2012/05/30 07:50:53  Kevin 
-- Initial revision 

ZYXEL-VLAN-MAPPING-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelVlanMapping MODULE-IDENTITY
		LAST-UPDATED	"201207010000Z"    
		ORGANIZATION "Enterprise Solution ZyXEL"     
		CONTACT-INFO
			""	   
		DESCRIPTION
			"The subtree for VLAN mapping"
		::= { esMgmt 88 }		

	zyxelVlanMappingSetup    	OBJECT IDENTIFIER ::= { zyxelVlanMapping 1 }
		
	
-- *******************************************************************
-- *
-- * zyxelVlanMappingSetup
-- *
-- *******************************************************************  

-- zyxelVlanMappingState	                             
        zyVlanMappingState OBJECT-TYPE
        SYNTAX  EnabledStatus
        MAX-ACCESS  read-write
        STATUS  current
        DESCRIPTION
                      	"Enable/Disable VLAN mapping on the switch. With VLAN mapping enabled, 
                      	the switch can map the VLAN ID and priority level of packets received from a 
                      	private network to those used in the service provider's network."
        ::= { zyxelVlanMappingSetup 1 }

                                               
-- zyxelVlanMappingPortTable

        zyxelVlanMappingPortTable OBJECT-TYPE
        SYNTAX	SEQUENCE OF ZyxelVlanMappingPortEntry
        MAX-ACCESS  not-accessible
        STATUS  current
        DESCRIPTION
                 	"The table contains VLAN mapping port configuration."
        ::= { zyxelVlanMappingSetup 2 }
        
		zyxelVlanMappingPortEntry OBJECT-TYPE
        SYNTAX	ZyxelVlanMappingPortEntry
        MAX-ACCESS	not-accessible
        STATUS	current
        DESCRIPTION    	
					"An entry contains VLAN mapping port configuration."
        INDEX          	{ dot1dBasePort }
        ::= { zyxelVlanMappingPortTable 1 }

        ZyxelVlanMappingPortEntry ::=
           SEQUENCE {
        	zyVlanMappingPortState	EnabledStatus
           }

        zyVlanMappingPortState OBJECT-TYPE
        SYNTAX  EnabledStatus
        MAX-ACCESS  read-write
        STATUS  current
        DESCRIPTION
                      	"Enable/Disable the VLAN mapping feature on this port."
        ::= { zyxelVlanMappingPortEntry 1 }
             
             
-- zyxelVlanMappingMaxNumberOfRules                                  
        zyVlanMappingMaxNumberOfRules OBJECT-TYPE
        SYNTAX  INTEGER
        MAX-ACCESS  read-only
        STATUS  current
        DESCRIPTION
                      	"The maximum number of VLAN mapping rule entries that can be created."
        ::= { zyxelVlanMappingSetup 3 }

     
             
-- zyxelVlanMappingTable
        zyxelVlanMappingTable OBJECT-TYPE
        SYNTAX	SEQUENCE OF ZyxelVlanMappingEntry
        MAX-ACCESS  not-accessible
        STATUS  current
        DESCRIPTION
                 	"The table contains VLAN mapping configuration."
        ::= { zyxelVlanMappingSetup 4 }
        
		zyxelVlanMappingEntry OBJECT-TYPE
        SYNTAX	ZyxelVlanMappingEntry
        MAX-ACCESS	not-accessible
        STATUS	current
        DESCRIPTION    	
					"An entry contains VLAN mapping configuration."
        INDEX          	{ zyVlanMappingPort, zyVlanMappingVid }
        ::= { zyxelVlanMappingTable 1 }

        ZyxelVlanMappingEntry ::=
           SEQUENCE {
           	zyVlanMappingName			DisplayString,
        	zyVlanMappingPort			INTEGER,
        	zyVlanMappingVid			INTEGER,
        	zyVlanMappingTranslatedVid	INTEGER,
        	zyVlanMappingPriority		INTEGER,
        	zyVlanMappingRowStatus		RowStatus
           }

        zyVlanMappingName OBJECT-TYPE
        SYNTAX  DisplayString
        MAX-ACCESS  read-write
        STATUS  current
        DESCRIPTION
                      	"Set a descriptive name of VLAN mapping rule for identification purposes."
        ::= { zyxelVlanMappingEntry 1 }

        zyVlanMappingPort OBJECT-TYPE
        SYNTAX  INTEGER
        MAX-ACCESS  not-accessible
        STATUS  current
        DESCRIPTION
                     	"The port to be included in this rule."
        ::= { zyxelVlanMappingEntry 2 }

        zyVlanMappingVid OBJECT-TYPE
        SYNTAX  INTEGER
        MAX-ACCESS  not-accessible
        STATUS  current
        DESCRIPTION
                     	"This is the VLAN tag carried in the packets and will be translated into the VID you specified in the Translated VID entry."
        ::= { zyxelVlanMappingEntry 3 }
        
        zyVlanMappingTranslatedVid OBJECT-TYPE
        SYNTAX  INTEGER
        MAX-ACCESS  read-write
        STATUS  current
        DESCRIPTION
                     	"Set a VLAN ID (from 1 to 4094) into which the customer VID carried in the packets will be translated."
        ::= { zyxelVlanMappingEntry 4 }
        
        zyVlanMappingPriority OBJECT-TYPE
        SYNTAX  INTEGER {
        		prioriry-0(0),
        		prioriry-1(1),
        		prioriry-2(2),
        		prioriry-3(3),
        		prioriry-4(4),
        		prioriry-5(5),
        		prioriry-6(6),
        		prioriry-7(7)
        }

        MAX-ACCESS  read-write
        STATUS  current
        DESCRIPTION
                     	"Set a priority level (from 0 to 7). This is the priority level 
                     	that replaces the customer priority level in the tagged packets or adds to the untagged packets."
        ::= { zyxelVlanMappingEntry 5 }

        zyVlanMappingRowStatus OBJECT-TYPE
        SYNTAX  RowStatus
        MAX-ACCESS  read-create
        STATUS  current
        DESCRIPTION
                     	"This object allows to create and delete a VLAN mapping rule entry."
        ::= { zyxelVlanMappingEntry 6 }
 
END
