USR-GWCWAN-MIB DEFINITIONS ::= BEGIN
    IMPORTS
        OBJECT-TYPE, MODULE-IDENTITY, NOTIFICATION-TYPE,
        IpAddress, Integer32
            FROM SNMPv2-SMI
        DisplayString
            FROM SNMPv2-TC
        InterfaceIndex, common
            FROM USR-DEFINITIONS-MIB;
    usrGwcwan MODULE-IDENTITY
         LAST-UPDATED "200205051900Z"
         ORGANIZATION "CommWorks Corporation, a 3Com Company"
         CONTACT-INFO "Customer Support"
         DESCRIPTION
                 "The commWorks enterprise defined MIB objects
                   for the Network Element."
--       REVISION    "200205051900Z"
--       DESCRIPTION "Converted traps to SNMPv2"
         ::= { common 58 }
-- Gwcwan virtual interface table
    usrGwcwanIfTable OBJECT-TYPE
        SYNTAX SEQUENCE OF UsrGwcwanIfEntry
        MAX-ACCESS not-accessible
        STATUS current
        DESCRIPTION
            "A list of Gwcwan interface entries."
        ::= { usrGwcwan 1 }
    usrGwcwanIfEntry OBJECT-TYPE
        SYNTAX UsrGwcwanIfEntry
        MAX-ACCESS not-accessible
        STATUS current
        DESCRIPTION
            "Parameter values for a Gwcwan interfaces."
        INDEX { usrGwcwanIfIndex }
        ::= { usrGwcwanIfTable 1 }
    UsrGwcwanIfEntry ::=
        SEQUENCE 
            {
            usrGwcwanIfIndex
		InterfaceIndex,
            usrGwcwanIfName
               DisplayString,
            usrGwcwanIfType
		INTEGER
            }
    usrGwcwanIfIndex OBJECT-TYPE
        SYNTAX InterfaceIndex
        MAX-ACCESS read-only
        STATUS current
        DESCRIPTION
            "The value of ifIndex for the port.  By convention
            and if possible, hardware port numbers map directly
            to external connectors.  The value for each port must
            remain constant at least from one re-initialization
            of the network management agent to the next."
        ::= { usrGwcwanIfEntry 1 }
   usrGwcwanIfName OBJECT-TYPE
       SYNTAX DisplayString (SIZE (0..32))
       MAX-ACCESS read-only
       STATUS current
       DESCRIPTION
           "The textual name of the interface.  It is of the form
	    wan:# for physical interfaces and of the form wan:#/linkname
	    for logicalinterfaces where # is the physical
            interface this logical interface resides on, and
            linkname is assigned by the administrator."
	--CONFIGURABLE
       ::= { usrGwcwanIfEntry 2 }
    usrGwcwanIfType OBJECT-TYPE
        SYNTAX INTEGER 
            {
            usrGwcwanV35(1),
            usrGwcwanDS1(2),
            usrGwcwanWSOCK(3)
            }
        MAX-ACCESS read-only
        STATUS current
        DESCRIPTION
            "This helps determine the type of physical interface /
             NIC Type/ WAN Driver Type."
        ::= { usrGwcwanIfEntry 3 }
   usrGwcwanV35IfTable OBJECT-TYPE
       SYNTAX SEQUENCE OF UsrGwcwanV35IfEntry
       MAX-ACCESS not-accessible
       STATUS current
       DESCRIPTION
           "A list of Gwcwan V35 virtual interface entries."
       ::= { usrGwcwan 2 }
   usrGwcwanV35IfEntry OBJECT-TYPE
       SYNTAX UsrGwcwanV35IfEntry
       MAX-ACCESS not-accessible
       STATUS current
       DESCRIPTION
           "Parameter values for V35 Gwcwan virtual interface."
       INDEX { usrGwcwanV35IfIndex }
       ::= { usrGwcwanV35IfTable 1 }
   UsrGwcwanV35IfEntry ::=
       SEQUENCE {
           usrGwcwanV35IfIndex
               InterfaceIndex,
           usrGwcwanV35ClockRefMode
		INTEGER,
    	   usrGwcwanV35ClockInvertedMode
        	INTEGER,
           usrGwcwanV35FlagIdlePattern
                INTEGER,
           usrGwcwanV35PortType
               INTEGER
       }
   usrGwcwanV35IfIndex OBJECT-TYPE
       SYNTAX InterfaceIndex
       MAX-ACCESS read-only
       STATUS current
       DESCRIPTION
           "The value of ifIndex for the port.  By convention
           and if possible, hardware port numbers map directly
           to external connectors.  The value for each port must
           remain constant at least from one re-initialization
           of the network management agent to the next."
       ::= { usrGwcwanV35IfEntry 1 }
    usrGwcwanV35ClockRefMode OBJECT-TYPE
        SYNTAX INTEGER
            {
            usrGwcwanDTELoopBack(1),
            usrGwcwanDCELoopBack(2)
            }
        MAX-ACCESS read-write
        STATUS current
        DESCRIPTION
            "Valid only when usrGwcwanIfType is usrGwcwanV35.
             The clock ref mode of this v35 interface"
        --CONFIGURABLE
       ::= { usrGwcwanV35IfEntry 2 }
    usrGwcwanV35ClockInvertedMode OBJECT-TYPE
        SYNTAX INTEGER
            {
            usrGwcwanNoneInverted(1),
            usrGwcwanClockInverted(2)
            }
        MAX-ACCESS read-write
        STATUS current
        DESCRIPTION
            "Valid only when usrGwcwanIfType is usrGwcwanV35.
             The Clock inverted mode"
        --CONFIGURABLE
       ::= { usrGwcwanV35IfEntry 3 }
     usrGwcwanV35FlagIdlePattern OBJECT-TYPE
        SYNTAX INTEGER 
            {
            usrGwcwanFlagIdlePattern(1),
            usrGwcwanFlagIdlePatternInvalid(2)
            } 
        MAX-ACCESS read-write
        STATUS current
        DESCRIPTION
            "Valid only when usrGwcwanIfType is usrGwcwanV35.
             This mib is an addon to rfc1659 rs232SyncPortIdlePattern mib.
             rfc1659 does not support idle pattern as flag (7F).
             If this flag is set to flagIdlePattern, then Pilgrim sets wapi
             idle pattern to flag. Other wise, Pilgrim sets wapi according
             the value set in rs232SyncPortIdlePattern."
        --CONFIGURABLE
       ::= { usrGwcwanV35IfEntry 4 }
     usrGwcwanV35PortType OBJECT-TYPE
       SYNTAX INTEGER {
			rs232(2), rs422(3), v35(5), x21(6)
		      }
        MAX-ACCESS read-write
        STATUS current
        DESCRIPTION
           "The port's hardware type. This is actually a subset of
   	    rs232PortType parameter defined by RFC1659. It was
	    necessary to re-define this variable since Write access
	    is not allowed to the parameter defined by RFC1659."
        --CONFIGURABLE
       ::= { usrGwcwanV35IfEntry 5 }
   usrGwcwanT1E1IfTable OBJECT-TYPE
       SYNTAX SEQUENCE OF UsrGwcwanT1E1IfEntry
       MAX-ACCESS not-accessible
       STATUS current
       DESCRIPTION
           "A list of Gwcwan T1E1 virtual interface entries."
       ::= { usrGwcwan 3 }
   usrGwcwanT1E1IfEntry OBJECT-TYPE
       SYNTAX UsrGwcwanT1E1IfEntry
       MAX-ACCESS not-accessible
       STATUS current
       DESCRIPTION
           "Parameter values for T1E1 Gwcwan virtual interface."
       INDEX { usrGwcwanT1E1IfIndex }
       ::= { usrGwcwanT1E1IfTable 1 }
   UsrGwcwanT1E1IfEntry ::=
       SEQUENCE {
           usrGwcwanT1E1IfIndex
               InterfaceIndex,
    	   usrGwcwanDS1CableLen
               INTEGER,
    	   usrGwcwanDS1LineBuildout
               INTEGER
       }
   usrGwcwanT1E1IfIndex OBJECT-TYPE
       SYNTAX InterfaceIndex
       MAX-ACCESS read-only
       STATUS current
       DESCRIPTION
           "The value of ifIndex for the port.  By convention
           and if possible, hardware port numbers map directly
           to external connectors.  The value for each port must
           remain constant at least from one re-initialization
           of the network management agent to the next."
       ::= { usrGwcwanT1E1IfEntry 1 }
    usrGwcwanDS1CableLen OBJECT-TYPE
        SYNTAX INTEGER
            {
            usrGwcwanDS1CableLen0to131ft(1),
            usrGwcwanDS1CableLen131to262ft(2),
            usrGwcwanDS1CableLen262to393ft(3),
            usrGwcwanDS1CableLen393to524ft(4),
            usrGwcwanDS1CableLen524to655ft(5),
            usrGwcwanDS1CableLen655to786ft(6),
            usrGwcwanDS1CableLenLongHaul(7)
            }
        MAX-ACCESS read-write
        STATUS current
        DESCRIPTION
            "Valid only when usrGwcwanIfType is usrGwcwanDS1.
             The cable length of DS1 interface. If the interface is
             long haul, use usrGwcwanDS1CableLenLongHaul. Otherwise,
             use specified cable length."
        --CONFIGURABLE
        ::= { usrGwcwanT1E1IfEntry 2 }
    usrGwcwanDS1LineBuildout OBJECT-TYPE
        SYNTAX INTEGER
            {
            usrGwcwanDS1linebuildout0db(1),
            usrGwcwanDS1linebuildout7d5db(2),
            usrGwcwanDS1linebuildout15db(3),
            usrGwcwanDS1linebuildout22d5db(4)
            }
        MAX-ACCESS read-write
        STATUS current
        DESCRIPTION
            "Valid only when usrGwcwanIfType is usrGwcwanDS1.
             The line build out of DS1 interface."
        --CONFIGURABLE
        ::= { usrGwcwanT1E1IfEntry 3 }
    usrGwcwanWSOCKIfTable OBJECT-TYPE
        SYNTAX SEQUENCE OF UsrGwcwanWSOCKIfEntry
        MAX-ACCESS not-accessible
        STATUS current
        DESCRIPTION
            "A list of Gwcwan WSOCK virtual interface entries."
        ::= { usrGwcwan 4 }
    usrGwcwanWSOCKIfEntry OBJECT-TYPE
        SYNTAX UsrGwcwanWSOCKIfEntry
        MAX-ACCESS not-accessible
        STATUS current
        DESCRIPTION
            "Parameter values for WSOCK Gwcwan virtual interface."
        INDEX { usrGwcwanWSOCKIfIndex }
        ::= { usrGwcwanWSOCKIfTable 1 }
    UsrGwcwanWSOCKIfEntry ::=
        SEQUENCE {
            usrGwcwanWSOCKIfIndex   InterfaceIndex,
            usrGwcwanIPConnType     INTEGER,
            usrGwcwanRemoteIp       IpAddress,
            usrGwcwanRemotePort     Integer32,
            usrGwcwanLocalPort      Integer32
            }
    usrGwcwanWSOCKIfIndex OBJECT-TYPE
        SYNTAX InterfaceIndex
        MAX-ACCESS read-only
        STATUS current
        DESCRIPTION
            "The value of ifIndex for the port.  By convention
            and if possible, hardware port numbers map directly
            to external connectors.  The value for each port must
            remain constant at least from one re-initialization
            of the network management agent to the next."
        ::= { usrGwcwanWSOCKIfEntry 1 }
    usrGwcwanIPConnType OBJECT-TYPE
        SYNTAX INTEGER 
            {
            usrGwcwanUDP(1),
            usrGwcwanTCP(2)
            }
        MAX-ACCESS read-write
        STATUS current
        DESCRIPTION
            "Valid only when usrGwcwanIfType is usrGwcwanWSOCK.
             The type of IP service to use to make the sockets
             connection (UDP or TCP)."
        --CONFIGURABLE
        ::= { usrGwcwanWSOCKIfEntry 2 }
    usrGwcwanRemoteIp OBJECT-TYPE
        SYNTAX IpAddress
        MAX-ACCESS read-write
        STATUS current
        DESCRIPTION
            "Valid only when usrGwcwanIfType is usrGwcwanWSOCK.
             The remote IP address this virtual port sends to."
        --CONFIGURABLE
        ::= { usrGwcwanWSOCKIfEntry 3 }
    usrGwcwanRemotePort OBJECT-TYPE
        SYNTAX Integer32
        MAX-ACCESS read-write
        STATUS current
        DESCRIPTION
            "Valid only when usrGwcwanIfType is usrGwcwanWSOCK.
             The remote UDP/IP port this virtual port sends to."
        --CONFIGURABLE
        ::= { usrGwcwanWSOCKIfEntry 4 }
    usrGwcwanLocalPort OBJECT-TYPE
        SYNTAX Integer32
        MAX-ACCESS read-write
        STATUS current
        DESCRIPTION
            "Valid only when usrGwcwanIfType is usrGwcwanWSOCK.
             The local UDP/IP port this virtual port listens to."
        --CONFIGURABLE
        ::= { usrGwcwanWSOCKIfEntry 5 }
    usrGwcwanT1E1TrapEnaTable OBJECT-TYPE
	SYNTAX SEQUENCE OF UsrGwcwanT1E1TrapEnaEntry
	MAX-ACCESS not-accessible
	STATUS current
	DESCRIPTION
	"A trap enable table that defines a column for every trap 
	that a DS1 entity can generate."
        ::= { usrGwcwan 5 }
    usrGwcwanT1E1TrapEnaEntry OBJECT-TYPE
	SYNTAX UsrGwcwanT1E1TrapEnaEntry
	MAX-ACCESS not-accessible
	STATUS current
	DESCRIPTION
	"There is one entry in this table for every DS1 that exists 
	in the chassis."
	INDEX { usrGwcwanT1E1TrapEnaDS1Index }
	::= { usrGwcwanT1E1TrapEnaTable 1 }
    UsrGwcwanT1E1TrapEnaEntry ::=
	SEQUENCE {
	    usrGwcwanT1E1TrapEnaDS1Index
		Integer32,
	    usrGwcwanT1E1TrapEnaYellowAlarm
		INTEGER,
	    usrGwcwanT1E1TrapEnaSndYellowAlarm
		INTEGER,
	    usrGwcwanT1E1TrapEnaAlarmIndSignal
		INTEGER,
	    usrGwcwanT1E1TrapEnaSndAlarmIndSignal
		INTEGER,
	    usrGwcwanT1E1TrapEnaRedAlarm
		INTEGER,
	    usrGwcwanT1E1TrapEnaLossOfSignal
		INTEGER,
	    usrGwcwanT1E1TrapEnaloopBack
		INTEGER,
	    usrGwcwanT1E1TrapEnaRcvTestCode
		INTEGER
	}
    usrGwcwanT1E1TrapEnaDS1Index OBJECT-TYPE
	SYNTAX Integer32
	MAX-ACCESS read-only
	STATUS current
	DESCRIPTION
	"The value of ifIndex for the DS1/ES1 port.  By convention
	and if possible, hardware port numbers map directly
	to external connectors.  The value for each port must
	remain constant at least from one re-initialization
	of the network management agent to the next."
	::= { usrGwcwanT1E1TrapEnaEntry 1 }
    usrGwcwanT1E1TrapEnaYellowAlarm OBJECT-TYPE
	SYNTAX INTEGER{
	  enableTrap(1),
	  disableAll(2),
	  enableLog(3),
	  enableAll(4)
	}
	MAX-ACCESS read-write
	STATUS current
	DESCRIPTION
	"Enable the generation of an SNMP trap for Far-End Loss of
	Frame condition (signaled by a received Yellow Alarm) on the
	specified DS1. This corresponds to dsx1RcvFarEndLOF bit in
	dsx1LineStatus variable"
	--CONFIGURABLE
	::= { usrGwcwanT1E1TrapEnaEntry 2 }
    usrGwcwanT1E1TrapEnaSndYellowAlarm OBJECT-TYPE
	SYNTAX INTEGER{
	  enableTrap(1),
	  disableAll(2),
	  enableLog(3),
	  enableAll(4)
	}
	MAX-ACCESS read-write
	STATUS current
	DESCRIPTION
	"Enable the generation of an SNMP trap for Near End Sending
	Yellow Alarm condition on the specified DS1. This corresponds
	to dsx1XmtFarEndLOF bit in dsx1LineStatus variable"
	--CONFIGURABLE
	::= { usrGwcwanT1E1TrapEnaEntry 3 }
    usrGwcwanT1E1TrapEnaAlarmIndSignal OBJECT-TYPE
	SYNTAX INTEGER{
	  enableTrap(1),
	  disableAll(2),
	  enableLog(3),
	  enableAll(4)
	}
	MAX-ACCESS read-write
	STATUS current
	DESCRIPTION
	"Enable the generation of an SNMP trap for Far End Sending
	Alarm Indication Signal condition on the specified DS1. This
	corresponds to dsx1RcvAIS bit in dsx1LineStatus variable"
	--CONFIGURABLE
	::= { usrGwcwanT1E1TrapEnaEntry 4 }
    usrGwcwanT1E1TrapEnaSndAlarmIndSignal OBJECT-TYPE
	SYNTAX INTEGER{
	  enableTrap(1),
	  disableAll(2),
	  enableLog(3),
	  enableAll(4)
	}
	MAX-ACCESS read-write
	STATUS current
	DESCRIPTION
	"Enable the generation of an SNMP trap for Near End Sending
	Alarm Indication Signal condition on the specified DS1.
	This corresponds to dsx1XmtAIS bit in dsx1LineStatus variable"
	--CONFIGURABLE
	::= { usrGwcwanT1E1TrapEnaEntry 5 }
    usrGwcwanT1E1TrapEnaRedAlarm OBJECT-TYPE
	SYNTAX INTEGER{
	  enableTrap(1),
	  disableAll(2),
	  enableLog(3),
	  enableAll(4)
	}
	MAX-ACCESS read-write
	STATUS current
	DESCRIPTION
	"Enable the generation of an SNMP trap for Near End Loss Of
	Frame (in red alarm condition) condition on the specified DS1.
	This corresponds to dsx1LossOfFrame bit in dsx1LineStatus variable"
	--CONFIGURABLE
	::= { usrGwcwanT1E1TrapEnaEntry 6 }
    usrGwcwanT1E1TrapEnaLossOfSignal OBJECT-TYPE
	SYNTAX INTEGER{
	  enableTrap(1),
	  disableAll(2),
	  enableLog(3),
	  enableAll(4)
	}
	MAX-ACCESS read-write
	STATUS current
	DESCRIPTION
	"Enable the generation of an SNMP trap for Near End Loss Of
	Signal condition on the specified DS1. This corresponds to
	dsx1LossOfSignal bit in dsx1LineStatus variable"
	--CONFIGURABLE
	::= { usrGwcwanT1E1TrapEnaEntry 7 }
    usrGwcwanT1E1TrapEnaloopBack OBJECT-TYPE
	SYNTAX INTEGER{
	  enableTrap(1),
	  disableAll(2),
	  enableLog(3),
	  enableAll(4)
	}
	MAX-ACCESS read-write
	STATUS current
	DESCRIPTION
	"Enable the generation of an SNMP trap for Near End loopback
	condition on the specified DS1. This corresponds to
	dsx1LoopbackState bit in dsx1LineStatus variable"
	--CONFIGURABLE
	::= { usrGwcwanT1E1TrapEnaEntry 8 }
    usrGwcwanT1E1TrapEnaRcvTestCode OBJECT-TYPE
	SYNTAX INTEGER {
	  enableTrap(1),
	  disableAll(2),
	  enableLog(3),
	  enableAll(4)
	}
	MAX-ACCESS read-write
	STATUS current
	DESCRIPTION
	"Enable the generation of an SNMP trap for Near End test code
	condition on the specified DS1. This corresponds to
	dsx1RcvTestCode bit in dsx1LineStatus variable"
	--CONFIGURABLE
	::= { usrGwcwanT1E1TrapEnaEntry 9 }
--  GWC traps
    usrGwcwanTraps OBJECT IDENTIFIER ::= { usrGwcwan 6 }
	usrGwcwanT1E1YellowAlarm NOTIFICATION-TYPE
    OBJECTS {
	  usrGwcwanT1E1TrapEnaDS1Index
	}
    STATUS  current
	DESCRIPTION
	"This trap is generated for an active Far-End Loss of Frame
	condition (signaled by a received Yellow Alarm) on the
	specified DS1."
    --#TYPE    "DS1/ES1 port Failure Event"
    --#SUMMARY  "Yellow Alarm: Far-End Loss of Frame for DS1 Interface %d"
    --#ARGUMENTS { 0 }
    --#SEVERITY MAJOR
    --#STATE    OPERATIONAL
    --#PROBABLECAUSE "Port or Hardware Error"
    ::= { usrGwcwanTraps 1 }
	usrGwcwanT1E1ClrYellowAlarm NOTIFICATION-TYPE
    OBJECTS {
	  usrGwcwanT1E1TrapEnaDS1Index
	}
    STATUS  current
	DESCRIPTION
	"This trap is generated when Far-End Loss of Frame condition
	(signaled by a received Yellow Alarm) clears on the
	specified DS1."
    --#TYPE    "DS1/ES1 port Failure Event"
    --#SUMMARY  "Yellow Alarm: Far-End Loss of Frame condition cleared for DS1 Interface %d"
    --#ARGUMENTS { 0 }
    --#SEVERITY CLEARED
    --#STATE    OPERATIONAL
    --#PROBABLECAUSE "Error Condition Cleared"
	::= { usrGwcwanTraps 2 }
	usrGwcwanT1E1SndYellowAlarm NOTIFICATION-TYPE
    OBJECTS {
	  usrGwcwanT1E1TrapEnaDS1Index
	}
    STATUS  current
	DESCRIPTION
	"This trap is generated for an active Near End Sending Yellow
	Alarm condition on the specified DS1."
    --#TYPE    "DS1/ES1 port Failure Event"
    --#SUMMARY  "Yellow Alarm: Near-End Loss of Frame for DS1 Interface %d"
    --#ARGUMENTS { 0 }
    --#SEVERITY MAJOR
    --#STATE    OPERATIONAL
    --#PROBABLECAUSE "Port or Hardware Error"
	::= { usrGwcwanTraps 3 }
	usrGwcwanT1E1ClrSndYellowAlarm NOTIFICATION-TYPE
    OBJECTS {
	  usrGwcwanT1E1TrapEnaDS1Index
	}
    STATUS  current
	DESCRIPTION
	"This trap is generated when Near End Sending Yellow
	Alarm condition clears on the specified DS1."
    --#TYPE    "DS1/ES1 port Failure Event"
    --#SUMMARY  "Yellow Alarm: Near-End Loss of Frame condition cleared for DS1 Interface %d"
    --#ARGUMENTS { 0 }
    --#SEVERITY CLEARED
    --#STATE    OPERATIONAL
    --#PROBABLECAUSE "Error Condition Cleared"
	::= { usrGwcwanTraps 4 }
	usrGwcwanT1E1AlarmIndSignal NOTIFICATION-TYPE
    OBJECTS {
	  usrGwcwanT1E1TrapEnaDS1Index
	}
    STATUS  current
	DESCRIPTION
	"This trap is generated for an active Far End Sending Alarm
	Indication Signal condition on the specified DS1."
    --#TYPE    "DS1/ES1 port Failure Event"
    --#SUMMARY  "Far-End Sending Alarm Indication Signal for DS1 Interface %d"
    --#ARGUMENTS { 0 }
    --#SEVERITY MAJOR
    --#STATE    OPERATIONAL
    --#PROBABLECAUSE "Port or Hardware Error"
	::= { usrGwcwanTraps 5 }
	usrGwcwanT1E1ClrAlarmIndSignal NOTIFICATION-TYPE
    OBJECTS {
	  usrGwcwanT1E1TrapEnaDS1Index
	}
    STATUS  current
	DESCRIPTION
	"This trap is generated when Far End Sending Alarm
	Indication Signal condition clears on the specified DS1."
    --#TYPE    "DS1/ES1 port Failure Event"
    --#SUMMARY  "Far-End Alarm Indication Signal condition cleared for DS1 Interface %d"
    --#ARGUMENTS { 0 }
    --#SEVERITY CLEARED
    --#STATE    OPERATIONAL
    --#PROBABLECAUSE "Error Condition Cleared"
	::= { usrGwcwanTraps 6 }
	usrGwcwanT1E1SndAlarmIndSignal NOTIFICATION-TYPE
    OBJECTS {
	  usrGwcwanT1E1TrapEnaDS1Index
	}
    STATUS  current
	DESCRIPTION
	"This trap is generated for an active Near End Sending Alarm
	Indication Signal condition on the specified DS1."
    --#TYPE    "DS1/ES1 port Failure Event"
    --#SUMMARY  "Near-End Sending Alarm Indication Signal for DS1 Interface %d"
    --#ARGUMENTS { 0 }
    --#SEVERITY MAJOR
    --#STATE    OPERATIONAL
    --#PROBABLECAUSE "Port or Hardware Error"
	::= { usrGwcwanTraps 7 }
	usrGwcwanT1E1ClrSndAlarmIndSignal NOTIFICATION-TYPE
    OBJECTS {
	  usrGwcwanT1E1TrapEnaDS1Index
	}
    STATUS  current
	DESCRIPTION
	"This trap is generated when Near End Sending Alarm
	Indication Signal condition clears on the specified DS1."
    --#TYPE    "DS1/ES1 port Failure Event"
    --#SUMMARY  "Near-End Alarm Indication Signal condition cleared for DS1 Interface %d"
    --#ARGUMENTS { 0 }
    --#SEVERITY CLEARED
    --#STATE    OPERATIONAL
    --#PROBABLECAUSE "Error Condition Cleared"
	::= { usrGwcwanTraps 8 }
	usrGwcwanT1E1RedAlarm NOTIFICATION-TYPE
    OBJECTS {
	  usrGwcwanT1E1TrapEnaDS1Index
	}
    STATUS  current
	DESCRIPTION
	"This trap is generated for an active Near End Loss Of Frame
	(in red alarm condition) condition on the specified DS1."
    --#TYPE    "DS1/ES1 port Failure Event"
    --#SUMMARY  "Red Alarm: Near-End Loss of Frame for DS1 Interface %d"
    --#ARGUMENTS { 0 }
    --#SEVERITY MAJOR
    --#STATE    OPERATIONAL
    --#PROBABLECAUSE "Port or Hardware Error"
	::= { usrGwcwanTraps 9 }
	usrGwcwanT1E1ClrRedAlarm NOTIFICATION-TYPE
    OBJECTS {
	  usrGwcwanT1E1TrapEnaDS1Index
	}
    STATUS  current
	DESCRIPTION
	"This trap is generated when Near End Loss Of Frame
	(in red alarm condition) condition clears on the specified DS1."
    --#TYPE    "DS1/ES1 port Failure Event"
    --#SUMMARY  "Red Alarm: Near-End Loss of Frame condition cleared for DS1 Interface %d"
    --#ARGUMENTS { 0 }
    --#SEVERITY CLEARED
    --#STATE    OPERATIONAL
    --#PROBABLECAUSE "Error Condition Cleared"
	::= { usrGwcwanTraps 10 }
	usrGwcwanT1E1LossOfSignal NOTIFICATION-TYPE
    OBJECTS {
	  usrGwcwanT1E1TrapEnaDS1Index
	}
    STATUS  current
	DESCRIPTION
	"This trap is generated for an active Near End Loss Of Signal
	condition on the specified DS1."
    --#TYPE    "DS1/ES1 port Failure Event"
    --#SUMMARY  "Near-End Loss of Signal for DS1 Interface %d"
    --#ARGUMENTS { 0 }
    --#SEVERITY MAJOR
    --#STATE    OPERATIONAL
    --#PROBABLECAUSE "Port or Hardware Error"
	::= { usrGwcwanTraps 11 }
	usrGwcwanT1E1ClrLossOfSignal NOTIFICATION-TYPE
    OBJECTS {
	  usrGwcwanT1E1TrapEnaDS1Index
	}
    STATUS  current
	DESCRIPTION
	"This trap is generated when Near End Loss Of Signal condition
	clears on the specified DS1."
    --#TYPE    "DS1/ES1 port Failure Event"
    --#SUMMARY  "Near-End Loss of Signal condition cleared for DS1 Interface %d"
    --#ARGUMENTS { 0 }
    --#SEVERITY CLEARED
    --#STATE    OPERATIONAL
    --#PROBABLECAUSE "Error Condition Cleared"
	::= { usrGwcwanTraps 12 }
	usrGwcwanT1E1loopBack NOTIFICATION-TYPE
    OBJECTS {
	  usrGwcwanT1E1TrapEnaDS1Index
	}
    STATUS  current
	DESCRIPTION
	"This trap is generated for an active Near End loopback condition
	on the specified DS1."
    --#TYPE    "DS1/ES1 port Failure Event"
    --#SUMMARY " Near-End LoopBack condition on DS1 interface %d"
    --#ARGUMENTS { 0 }
    --#SEVERITY MAJOR
    --#STATE    OPERATIONAL
    --#PROBABLECAUSE "Port or Hardware Error"
	::= { usrGwcwanTraps 13 }
	usrGwcwanT1E1ClrloopBack NOTIFICATION-TYPE
    OBJECTS {
	  usrGwcwanT1E1TrapEnaDS1Index
	}
    STATUS  current
	DESCRIPTION
	"This trap is generated when Near End loopback condition clears
	on the specified DS1."
    --#TYPE    "DS1/ES1 port Failure Event"
    --#SUMMARY " Near-End LoopBack condition cleared on DS1 interface %d"
    --#ARGUMENTS { 0 }
    --#SEVERITY CLEARED
    --#STATE    OPERATIONAL
    --#PROBABLECAUSE "Port or Hardware Error"
	::= { usrGwcwanTraps 14 }
	usrGwcwanT1E1RcvTestCode NOTIFICATION-TYPE
    OBJECTS {
	  usrGwcwanT1E1TrapEnaDS1Index
	}
    STATUS  current
	DESCRIPTION
	"This trap is generated for an active Near End test code
	condition on the specified DS1."
    --#TYPE    "DS1/ES1 port Failure Event"
    --#SUMMARY " Near-End TestCode condition on DS1 interface %d"
    --#ARGUMENTS { 0 }
    --#SEVERITY MAJOR
    --#STATE    OPERATIONAL
    --#PROBABLECAUSE "Port or Hardware Error"
	::= { usrGwcwanTraps 15 }
	usrGwcwanT1E1ClrRcvTestCode NOTIFICATION-TYPE
    OBJECTS {
	  usrGwcwanT1E1TrapEnaDS1Index
	}
    STATUS  current
	DESCRIPTION
	"This trap is generated when Near End test code condition
	clears on the specified DS1."
    --#TYPE    "DS1/ES1 port Failure Event"
    --#SUMMARY " Near-End TestCode condition cleared on DS1 interface %d"
    --#ARGUMENTS { 0 }
    --#SEVERITY CLEARED
    --#STATE    OPERATIONAL
    --#PROBABLECAUSE "Error Clondition Cleared"
	::= { usrGwcwanTraps 16 }
   END
