-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
--
INFO-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
--modules         OBJECT IDENTIFIER ::= { agent 2 }
--hardware        OBJECT IDENTIFIER ::= { modules 1 }
--
--

info	OBJECT IDENTIFIER ::= { base 2 }
system	OBJECT IDENTIFIER ::= { info 1 }
info-agent	OBJECT IDENTIFIER ::= { info 2 }
modules	OBJECT IDENTIFIER ::= { info 3 }

general	OBJECT IDENTIFIER ::= { info-agent 1 }
fileinfo OBJECT IDENTIFIER ::= { info-agent 3 }

moduleEntry	OBJECT IDENTIFIER ::= { moduleTable 1 }
module	OBJECT IDENTIFIER ::= { moduleEntry 1 }
moduledesc	OBJECT IDENTIFIER ::= { moduleEntry 2 }
i18nModuleDesc	OBJECT IDENTIFIER ::= { moduleEntry 3 }
version	OBJECT IDENTIFIER ::= { moduleEntry 4 }
instance	OBJECT IDENTIFIER ::= { moduleEntry 5 }
modulecnt	OBJECT IDENTIFIER ::= { moduleEntry 6 }
name	OBJECT IDENTIFIER ::= { moduleEntry 7 }
xfile	OBJECT IDENTIFIER ::= { moduleEntry 8 }
alarmactionfiles	OBJECT IDENTIFIER ::= { fileinfo 1 }
sunmclogfiles	OBJECT IDENTIFIER ::= { fileinfo 2 }
oaversion	OBJECT IDENTIFIER ::= { general 1 }
tclversion	OBJECT IDENTIFIER ::= { general 2 }
tclpatchlevel	OBJECT IDENTIFIER ::= { general 3 }
component	OBJECT IDENTIFIER ::= { general 4 }
features	OBJECT IDENTIFIER ::= { general 5 }
timezone	OBJECT IDENTIFIER ::= { general 6 }
editModuleEntry	OBJECT IDENTIFIER ::= { editModuleTable 1 }
moduleTable	OBJECT IDENTIFIER ::= { modules 1 }
editModuleTable	OBJECT IDENTIFIER ::= { modules 2 }
name	OBJECT IDENTIFIER ::= { editModuleEntry 1 }
xfile	OBJECT IDENTIFIER ::= { editModuleEntry 2 }

END
