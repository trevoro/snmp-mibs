-- *****************************************************************************
-- Unisphere-Data-DHCP-CONF
--
-- SNMP Agent Capabilities definitions for the DHCP MIB.
--
-- Copyright (c) 2001, 2002 Unisphere Networks, Inc.  All rights reserved.
-- *****************************************************************************

Unisphere-Data-DHCP-CONF DEFINITIONS ::= BEGIN

IMPORTS
    MODULE-IDENTITY, OBJECT-IDENTITY
        FROM SNMPv2-SMI
    AGENT-CAPABILITIES
        FROM SNMPv2-CONF
    usDataAgents
        FROM Unisphere-Data-Agents
    usdDhcpRelayGroup, usdDhcpProxyGroup, usdDhcpLocalServerGroup,
	 usdDhcpLocalServerGroup2, usdDhcpRelayGroup2
        FROM Unisphere-Data-DHCP-MIB;

usdDhcpAgent MODULE-IDENTITY
    LAST-UPDATED "200205101937Z"  -- 10-May-02 03:37 PM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the DHCP component of the SNMP
        agent in the Unisphere Data Routing Switch family of products.  The DHCP
        application has subcomponents that run independently of each other and
        therefore have separate agent capabilities definitions."
    -- Revision History
    REVISION    "200205101937Z"  -- 10-May-02 03:37 PM EDT  - RX 4.0
    DESCRIPTION
        "Added local server reservation and cable modem support.
         Refined agent info enable into agent circuit ID enable and agent remote
         ID enable."
    REVISION    "200103301846Z"  -- 30-Mar-01 01:46 PM EST  - RX 3.2
    DESCRIPTION
        "The initial release of this management information module."
    ::= { usDataAgents 8 }


-- *****************************************************************************
-- The DHCP relay agent capabilities.
-- *****************************************************************************
usdDhcpRelayAgent OBJECT-IDENTITY
    STATUS      current
    DESCRIPTION
        "The DHCP relay subcomponent of the DHCP application.  MIB support for
        each subcomponent can run independently of the other subcomponents."
    ::= { usdDhcpAgent 1 }

usdDhcpRelayAgentV1 AGENT-CAPABILITIES
    PRODUCT-RELEASE
        "Version 1 of the DHCP relay subcomponent of the Unisphere Routing
        Switch SNMP agent.  This version of the DHCP relay subcomponent is
        supported in the Unisphere RX 1.3 and subsequent system releases."
    STATUS      obsolete
    DESCRIPTION
        "The MIB supported by the SNMP agent for the DHCP application in the
        Unisphere Routing Switch.  These capabilities became obsolete when
        the agent info enable was refined."
    SUPPORTS    Unisphere-Data-DHCP-MIB
        INCLUDES  {
            usdDhcpRelayGroup }
    ::= { usdDhcpRelayAgent 1 }

usdDhcpRelayAgentV2 AGENT-CAPABILITIES
    PRODUCT-RELEASE
        "Version 2 of the DHCP relay subcomponent of the Unisphere Routing
        Switch SNMP agent.  This version of the DHCP relay subcomponent is
        supported in the Unisphere RX 4.0 and subsequent system releases."
    STATUS      current
    DESCRIPTION
        "The MIB supported by the SNMP agent for the DHCP application in the
        Unisphere Routing Switch."
    SUPPORTS    Unisphere-Data-DHCP-MIB
        INCLUDES  {
            usdDhcpRelayGroup,
            usdDhcpRelayGroup2 }
    ::= { usdDhcpRelayAgent 2 }


-- *****************************************************************************
-- The DHCP proxy agent capabilities.
-- *****************************************************************************
usdDhcpProxyAgent OBJECT-IDENTITY
    STATUS      current
    DESCRIPTION
        "The DHCP proxy subcomponent of the DHCP application.  MIB support for
        each subcomponent can run independently of the other subcomponents."
    ::= { usdDhcpAgent 2 }

usdDhcpProxyAgentV1 AGENT-CAPABILITIES
    PRODUCT-RELEASE
        "Version 1 of the DHCP proxy subcomponent of the Unisphere Routing
        Switch SNMP agent.  This version of the DHCP proxy subcomponent is
        supported in the Unisphere RX 1.3 and subsequent system releases."
    STATUS      current
    DESCRIPTION
        "The MIB supported by the SNMP agent for the DHCP application in the
        Unisphere Routing Switch."
    SUPPORTS    Unisphere-Data-DHCP-MIB
        INCLUDES  {
            usdDhcpProxyGroup }
    ::= { usdDhcpProxyAgent 1 }


-- *****************************************************************************
-- The DHCP local server agent capabilities.
-- *****************************************************************************
usdDhcpLocalServerAgent OBJECT-IDENTITY
    STATUS      current
    DESCRIPTION
        "The DHCP local server subcomponent of the DHCP application.  MIB
        support for each subcomponent can run independently of the other
        subcomponents."
    ::= { usdDhcpAgent 3 }

usdDhcpLocalServerAgentV1 AGENT-CAPABILITIES
    PRODUCT-RELEASE
        "Version 1 of the DHCP local server subcomponent of the Unisphere
        Routing Switch SNMP agent.  This version of the DHCP local server
        subcomponent was supported in the Unisphere RX 3.1 and subsequent 3.x
        system releases."
    STATUS      obsolete
    DESCRIPTION
        "The MIB supported by the SNMP agent for the DHCP application in the
        Unisphere Routing Switch.  These capabilities became obsolete when
        support was added for reservations and cable modems."
    SUPPORTS    Unisphere-Data-DHCP-MIB
        INCLUDES  {
            usdDhcpLocalServerGroup }
    ::= { usdDhcpLocalServerAgent 1 }

usdDhcpLocalServerAgentV2 AGENT-CAPABILITIES
    PRODUCT-RELEASE
        "Version 2 of the DHCP local server subcomponent of the Unisphere
        Routing Switch SNMP agent.  This version of the DHCP local server
        subcomponent is supported in the Unisphere RX 4.0 and subsequent system
        releases."
    STATUS      current
    DESCRIPTION
        "The MIB supported by the SNMP agent for the DHCP application in the
        Unisphere Routing Switch."
    SUPPORTS    Unisphere-Data-DHCP-MIB
        INCLUDES  {
            usdDhcpLocalServerGroup2 }
    ::= { usdDhcpLocalServerAgent 2 }

END
