Nortel-Magellan-Passport-LogicalProcessorMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      PassportCounter64,
      InterfaceIndex,
      Gauge32,
      Integer32,
      Unsigned32
   FROM Nortel-Magellan-Passport-StandardTextualConventionsMIB

      AsciiString,
      Hex,
      NonReplicated,
      EnterpriseDateAndTime,
      Link
   FROM Nortel-Magellan-Passport-TextualConventionsMIB;




-- LAST-UPDATED   "9906090000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     LogicalProcessor Enterprise MIB."

logicalProcessorMIB OBJECT IDENTIFIER ::= { passportMIBs 11 }










-- LogicalProcessor/n
-- The LogicalProcessor (Lp) component is a root component. One Lp 
-- component is created for each Logical Processor. An Lp may be 
-- configured to run on up to two cards; one as the main card, and the 
-- other as the spare card. When two cards are configured, the Lp runs 
-- on one card, and waits for that card to fail before starting to run on 
-- the other card.

lp OBJECT IDENTIFIER ::= { components 12 }



lpRowStatusTable OBJECT-TYPE
   SYNTAX     SEQUENCE OF LpRowStatusEntry
   ACCESS     not-accessible
   STATUS     mandatory
   DESCRIPTION
     "This entry controls the addition and deletion of 
      lp components."
::= { lp 1 }

lpRowStatusEntry OBJECT-TYPE
   SYNTAX     LpRowStatusEntry
   ACCESS     not-accessible
   STATUS     mandatory
   DESCRIPTION
     "A single entry in the table represents a single 
      lp component."
   INDEX {
      lpIndex }
::= { lpRowStatusTable 1 }

LpRowStatusEntry ::= SEQUENCE {
   lpRowStatus
      RowStatus,
   lpComponentName
      DisplayString,
   lpStorageType
      StorageType,
   lpIndex
      Integer32 }

lpRowStatus OBJECT-TYPE
   SYNTAX     RowStatus 
   ACCESS     read-write
   STATUS     mandatory
   DESCRIPTION
     "This variable is used as the basis for SNMP naming of
      lp components.
      These components can be added and deleted."
::= { lpRowStatusEntry 1 }

lpComponentName OBJECT-TYPE
   SYNTAX     DisplayString 
   ACCESS     read-only
   STATUS     mandatory
   DESCRIPTION
     "This variable provides the component's string name for
      use with the ASCII Console Interface"
::= { lpRowStatusEntry 2 }

lpStorageType OBJECT-TYPE
   SYNTAX     StorageType 
   ACCESS     read-only
   STATUS     mandatory
   DESCRIPTION
     "This variable represents the storage type value for the
      lp tables."
::= { lpRowStatusEntry 4 }

lpIndex OBJECT-TYPE
   SYNTAX     Integer32 (0..15)
   ACCESS     not-accessible
   STATUS     mandatory
   DESCRIPTION
     "This variable represents the index for the lp tables."
::= { lpRowStatusEntry 10 }

lpProvTable OBJECT-TYPE
   SYNTAX     SEQUENCE OF LpProvEntry
   ACCESS     not-accessible
   STATUS     mandatory
   DESCRIPTION
     "This Group contains the provisionable attributes for the LP 
      component."
::= { lp 100 }

lpProvEntry OBJECT-TYPE
   SYNTAX     LpProvEntry
   ACCESS     not-accessible
   STATUS     mandatory
   DESCRIPTION
     "An entry in the lpProvTable."
   INDEX {
      lpIndex }
::= { lpProvTable 1 }

LpProvEntry ::= SEQUENCE {
   lpMainCard
      Link,
   lpSpareCard
      Link,
   lpLogicalProcessorType
      Link }

lpMainCard OBJECT-TYPE
   SYNTAX     Link 
   ACCESS     read-write
   STATUS     mandatory
   DESCRIPTION
     "This is the preferred processor card on which this LP should be 
      assigned."
::= { lpProvEntry 1 }

lpSpareCard OBJECT-TYPE
   SYNTAX     Link 
   ACCESS     read-write
   STATUS     mandatory
   DESCRIPTION
     "This is the spare processor card on which this LP should be 
      assigned."
::= { lpProvEntry 2 }

lpLogicalProcessorType OBJECT-TYPE
   SYNTAX     Link 
   ACCESS     read-write
   STATUS     mandatory
   DESCRIPTION
     "This is the Logical Processor Type (LPT) that determines which 
      software this LP will run."
::= { lpProvEntry 3 }

lpCidDataTable OBJECT-TYPE
   SYNTAX     SEQUENCE OF LpCidDataEntry
   ACCESS     not-accessible
   STATUS     mandatory
   DESCRIPTION
     "This group contains the attribute for a component's Customer 
      Identifier (CID). Refer to the attribute description for a detailed 
      explanation of CIDs."
::= { lp 101 }

lpCidDataEntry OBJECT-TYPE
   SYNTAX     LpCidDataEntry
   ACCESS     not-accessible
   STATUS     mandatory
   DESCRIPTION
     "An entry in the lpCidDataTable."
   INDEX {
      lpIndex }
::= { lpCidDataTable 1 }

LpCidDataEntry ::= SEQUENCE {
   lpCustomerIdentifier
      Unsigned32 }

lpCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpCidDataEntry 1 }

lpStateTable OBJECT-TYPE
   SYNTAX     SEQUENCE OF LpStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lp 102 }

lpStateEntry OBJECT-TYPE
   SYNTAX     LpStateEntry
   ACCESS     not-accessible
   STATUS     mandatory
   DESCRIPTION
     "An entry in the lpStateTable."
   INDEX {
      lpIndex }
::= { lpStateTable 1 }

LpStateEntry ::= SEQUENCE {
   lpAdminState
      INTEGER,
   lpOperationalState
      INTEGER,
   lpUsageState
      INTEGER,
   lpAvailabilityStatus
      OCTET STRING,
   lpProceduralStatus
      OCTET STRING,
   lpControlStatus
      OCTET STRING,
   lpAlarmStatus
      OCTET STRING,
   lpStandbyStatus
      INTEGER,
   lpUnknownStatus
      INTEGER }

lpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpStateEntry 1 }

lpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpStateEntry 2 }

lpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpStateEntry 3 }

lpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpStateEntry 4 }

lpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpStateEntry 5 }

lpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpStateEntry 6 }

lpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpStateEntry 7 }

lpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpStateEntry 8 }

lpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpStateEntry 9 }

lpOperTable OBJECT-TYPE
   SYNTAX     SEQUENCE OF LpOperEntry
   ACCESS     not-accessible
   STATUS     mandatory
   DESCRIPTION
     "This Group contains the operational attributes for the LP 
      component."
::= { lp 103 }

lpOperEntry OBJECT-TYPE
   SYNTAX     LpOperEntry
   ACCESS     not-accessible
   STATUS     mandatory
   DESCRIPTION
     "An entry in the lpOperTable."
   INDEX {
      lpIndex }
::= { lpOperTable 1 }

LpOperEntry ::= SEQUENCE {
   lpActiveCard
      RowPointer,
   lpMainCardStatus
      INTEGER,
   lpSpareCardStatus
      INTEGER,
   lpRestartOnCpSwitch
      INTEGER,
   lpScheduledSwitchover
      EnterpriseDateAndTime }

lpActiveCard OBJECT-TYPE
   SYNTAX     RowPointer 
   ACCESS     read-only
   STATUS     mandatory
   DESCRIPTION
     "This attribute indicates on which card this LP is currently running 
      (if any)."
::= { lpOperEntry 1 }

lpMainCardStatus OBJECT-TYPE
   SYNTAX     INTEGER  {
                 notProvisioned(0),
                 notAvailable(1),
                 available(3),
                 active(4) }
   ACCESS     read-only
   STATUS     mandatory
   DESCRIPTION
     "This attribute specifies the status of this LP's main card. The 
      following values have been defined:
      notProvisioned		 No main card has been provisioned
      notAvailable		 The main card is not available
      available		 The main card is available (running as standby)
      active		 The main card is running as active"
::= { lpOperEntry 2 }

lpSpareCardStatus OBJECT-TYPE
   SYNTAX     INTEGER  {
                 notProvisioned(0),
                 notAvailable(1),
                 alreadyInUse(2),
                 available(3),
                 active(4) }
   ACCESS     read-only
   STATUS     mandatory
   DESCRIPTION
     "This attribute specifies the status of this LP's spare card. The 
      following values have been defined:
      notProvisioned		 No spare card has been provisioned
      notAvailable		 The spare card is not available
      alreadyInUse		 The spare card is already in use by another LP
      available		 The spare card is available (running as standby)
      active		 The spare card is running as active"
::= { lpOperEntry 3 }

lpRestartOnCpSwitch OBJECT-TYPE
   SYNTAX     INTEGER  {
                 false(0),
                 true(1) }
   ACCESS     read-only
   STATUS     mandatory
   DESCRIPTION
     "This attribute indicates whether the Lp always restarts upon a CP 
      switchover. The value is true  if the featureList of the associated Sw 
      Lpt component contains a feature that does not support hitless CP 
      switchover. The value is also  true  when the feature 
      noHitlessCpSwitch is provisioned on  the CP. A  value of false does 
      not guarantee 'no restart'; dynamic conditions may still result in an 
      FP restart when a CP switchover occurs."
::= { lpOperEntry 4 }

lpScheduledSwitchover OBJECT-TYPE
   SYNTAX     EnterpriseDateAndTime (SIZE (0 | 16))
   ACCESS     read-only
   STATUS     mandatory
   DESCRIPTION
     "This attribute indicates the execution time of the scheduled 
      switchover. When there is no switchover scheduled the time is 
      equals to 0 (0000-00-00 00:00)."
::= { lpOperEntry 5 }

lpUtilTable OBJECT-TYPE
   SYNTAX     SEQUENCE OF LpUtilEntry
   ACCESS     not-accessible
   STATUS     mandatory
   DESCRIPTION
     "This group contains the operational attributes that specify the 
      processor's utilization levels. When this group exists for an LP 
      component, the attributes are representative of the active card."
::= { lp 104 }

lpUtilEntry OBJECT-TYPE
   SYNTAX     LpUtilEntry
   ACCESS     not-accessible
   STATUS     mandatory
   DESCRIPTION
     "An entry in the lpUtilTable."
   INDEX {
      lpIndex }
::= { lpUtilTable 1 }

LpUtilEntry ::= SEQUENCE {
   lpTimeInterval
      Unsigned32,
   lpCpuUtil
      Gauge32,
   lpCpuUtilAvg
      Gauge32,
   lpCpuUtilAvgMin
      Gauge32,
   lpCpuUtilAvgMax
      Gauge32,
   lpMsgBlockUsage
      Gauge32,
   lpMsgBlockUsageAvg
      Gauge32,
   lpMsgBlockUsageAvgMin
      Gauge32,
   lpMsgBlockUsageAvgMax
      Gauge32,
   lpLocalMsgBlockUsage
      Gauge32,
   lpLocalMsgBlockUsageAvg
      Gauge32,
   lpLocalMsgBlockUsageMin
      Gauge32,
   lpLocalMsgBlockUsageMax
      Gauge32 }

lpTimeInterval OBJECT-TYPE
   SYNTAX     Unsigned32 (0..15)
   ACCESS     read-only
   STATUS     mandatory
   DESCRIPTION
     "This attribute indicates the time period (in minutes) for which the 
      average, minimum and maximum utilization values are calculated.  
      This attribute is reset to 0 every 15 minutes."
::= { lpUtilEntry 1 }

lpCpuUtil OBJECT-TYPE
   SYNTAX     Gauge32 (0..100)
   ACCESS     read-only
   STATUS     mandatory
   DESCRIPTION
     "This attribute indicates an approximation of the current processor 
      utilization level (expressed as a percentage)."
::= { lpUtilEntry 2 }

lpCpuUtilAvg OBJECT-TYPE
   SYNTAX     Gauge32 (0..100)
   ACCESS     read-only
   STATUS     mandatory
   DESCRIPTION
     "This attribute indicates an average processor utilization level over 
      the specified time period, timeInterval. This average is calculated 
      based on one minute CPU utilization averages."
::= { lpUtilEntry 3 }

lpCpuUtilAvgMin OBJECT-TYPE
   SYNTAX     Gauge32 (0..100)
   ACCESS     read-only
   STATUS     mandatory
   DESCRIPTION
     "This attribute indicates the minimum processor utilization level over 
      a specified time period, timeInterval. This is based on one minute 
      CPU utilization averages."
::= { lpUtilEntry 4 }

lpCpuUtilAvgMax OBJECT-TYPE
   SYNTAX     Gauge32 (0..100)
   ACCESS     read-only
   STATUS     mandatory
   DESCRIPTION
     "This attribute indicates the maximum processor utilization level 
      over a specified time period, timeInterval. This is based on one 
      minute CPU utilization averages."
::= { lpUtilEntry 5 }

lpMsgBlockUsage OBJECT-TYPE
   SYNTAX     Gauge32 (0..2147483647)
   ACCESS     read-only
   STATUS     mandatory
   DESCRIPTION
     "This attribute indicates the processor's current shared message 
      block memory utilization (in kilobytes).
      If there is no shared memory on the card, this attribute indicates 0."
::= { lpUtilEntry 6 }

lpMsgBlockUsageAvg OBJECT-TYPE
   SYNTAX     Gauge32 (0..2147483647)
   ACCESS     read-only
   STATUS     mandatory
   DESCRIPTION
     "This attribute indicates the processor's average memory utilization 
      (in kilobytes) of shared message blocks, calculated over a specified 
      time period, timeInterval.  This utilization value is calculated using 
      15 second samples.  At the start of each timeInterval, this average 
      memory utilization is reset to the current usage, 
      sharedMsgBlockUsage.
      If there is no shared memory on the card, this attribute indicates 0."
::= { lpUtilEntry 7 }

lpMsgBlockUsageAvgMin OBJECT-TYPE
   SYNTAX     Gauge32 (0..2147483647)
   ACCESS     read-only
   STATUS     mandatory
   DESCRIPTION
     "This attribute indicates the processor's minimum memory 
      utilization (in kilobytes) of shared message blocks, calculated over a 
      specified time period, timeInterval.  This utilization value is 
      calculated using 15 second samples.  At the start of each 
      timeInterval, this minimum memory utilization is reset to the 
      current usage, sharedMsgBlockUsage.
      If there is no shared memory on the card, this attribute indicates 0."
::= { lpUtilEntry 8 }

lpMsgBlockUsageAvgMax OBJECT-TYPE
   SYNTAX     Gauge32 (0..2147483647)
   ACCESS     read-only
   STATUS     mandatory
   DESCRIPTION
     "This attribute indicates the processor's maximum memory 
      utilization (in kilobytes) of shared message blocks, calculated over a 
      specified time period, timeInterval.  This utilization value is 
      calculated using 15 second samples.  At the start of each 
      timeInterval, this maximum memory utilization is reset to the 
      current usage, sharedMsgBlockUsage.
      If there is no shared memory on the card, this attribute indicates 0."
::= { lpUtilEntry 9 }

lpLocalMsgBlockUsage OBJECT-TYPE
   SYNTAX     Gauge32 (0..2147483647)
   ACCESS     read-only
   STATUS     mandatory
   DESCRIPTION
     "This attribute indicates the processor's current memory utilization 
      (in kilobytes) of message blocks which are used for local messaging 
      on the card."
::= { lpUtilEntry 10 }

lpLocalMsgBlockUsageAvg OBJECT-TYPE
   SYNTAX     Gauge32 (0..2147483647)
   ACCESS     read-only
   STATUS     mandatory
   DESCRIPTION
     "This attribute indicates the processor's average memory utilization 
      (in kilobytes) of message blocks used for local messaging on the 
      card, calculated over a specified time period, timeInterval.  This 
      utilization value is calculated using 15 second samples.  At the start 
      of each timeInterval, this average memory utilization is reset to the 
      current usage, localMsgBlockUsage."
::= { lpUtilEntry 11 }

lpLocalMsgBlockUsageMin OBJECT-TYPE
   SYNTAX     Gauge32 (0..2147483647)
   ACCESS     read-only
   STATUS     mandatory
   DESCRIPTION
     "This attribute indicates the processor's minimum memory 
      utilization (in kilobytes) of message blocks used for local 
      messaging on the card, calculated over a specified time period, 
      timeInterval.  This utilization value is updated at 15 second 
      intervals.  At the start of each timeInterval, this minimum memory 
      utilization is reset to the current usage, localMsgBlockUsage."
::= { lpUtilEntry 12 }

lpLocalMsgBlockUsageMax OBJECT-TYPE
   SYNTAX     Gauge32 (0..2147483647)
   ACCESS     read-only
   STATUS     mandatory
   DESCRIPTION
     "This attribute indicates the processor's maximum memory 
      utilization (in kilobytes) of message blocks used for local 
      messaging on the card, calculated over a specified time period, 
      timeInterval.  This utilization value is updated at 15 second 
      intervals.  At the start of each timeInterval, this maximum memory 
      utilization is reset to the current usage, localMsgBlockUsage."
::= { lpUtilEntry 13 }

lpCapTable OBJECT-TYPE
   SYNTAX     SEQUENCE OF LpCapEntry
   ACCESS     not-accessible
   STATUS     mandatory
   DESCRIPTION
     "This group contains the operational attributes that specify the 
      processor's capacity levels. When this group exists for an LP 
      component, the attributes are representative of the active Card."
::= { lp 105 }

lpCapEntry OBJECT-TYPE
   SYNTAX     LpCapEntry
   ACCESS     not-accessible
   STATUS     mandatory
   DESCRIPTION
     "An entry in the lpCapTable."
   INDEX {
      lpIndex }
::= { lpCapTable 1 }

LpCapEntry ::= SEQUENCE {
   lpMsgBlockCapacity
      Unsigned32,
   lpLocalMsgBlockCapacity
      Unsigned32 }

lpMsgBlockCapacity OBJECT-TYPE
   SYNTAX     Unsigned32 (0..2147483647)
   ACCESS     read-only
   STATUS     mandatory
   DESCRIPTION
     "This attribute indicates the processor card's shared message block 
      memory capacity (in kilobytes)."
::= { lpCapEntry 1 }

lpLocalMsgBlockCapacity OBJECT-TYPE
   SYNTAX     Unsigned32 (0..2147483647)
   ACCESS     read-only
   STATUS     mandatory
   DESCRIPTION
     "This attribute indicates the processor card's local message block 
      memory capacity (in kilobytes).  These message blocks are used for 
      local messaging on the card."
::= { lpCapEntry 2 }

lpLinkToApplicationsTable OBJECT-TYPE
   SYNTAX     SEQUENCE OF LpLinkToApplicationsEntry
   ACCESS     not-accessible
   STATUS     mandatory
   DESCRIPTION
     "This attribute allows applications to link themselves directly to the 
      LP component."
::= { lp 242 }

lpLinkToApplicationsEntry OBJECT-TYPE
   SYNTAX     LpLinkToApplicationsEntry
   ACCESS     not-accessible
   STATUS     mandatory
   DESCRIPTION
     "An entry in the lpLinkToApplicationsTable."
   INDEX {
      lpIndex,
      lpLinkToApplicationsValue }
::= { lpLinkToApplicationsTable 1 }

LpLinkToApplicationsEntry ::= SEQUENCE {
   lpLinkToApplicationsValue
      Link }

lpLinkToApplicationsValue OBJECT-TYPE
   SYNTAX     Link 
   ACCESS     read-only
   STATUS     mandatory
   DESCRIPTION
     "This variable represents both the value and the index for the
      lpLinkToApplicationsTable."
::= { lpLinkToApplicationsEntry 1 }

lpMemoryCapacityTable OBJECT-TYPE
   SYNTAX     SEQUENCE OF LpMemoryCapacityEntry
   ACCESS     not-accessible
   STATUS     mandatory
   DESCRIPTION
     "This attribute indicates the processor card's memory capacity (in 
      kilobytes) for each type of memory."
::= { lp 244 }

lpMemoryCapacityEntry OBJECT-TYPE
   SYNTAX     LpMemoryCapacityEntry
   ACCESS     not-accessible
   STATUS     mandatory
   DESCRIPTION
     "An entry in the lpMemoryCapacityTable."
   INDEX {
      lpIndex,
      lpMemoryCapacityIndex }
::= { lpMemoryCapacityTable 1 }

LpMemoryCapacityEntry ::= SEQUENCE {
   lpMemoryCapacityIndex
      INTEGER,
   lpMemoryCapacityValue
      Unsigned32 }

lpMemoryCapacityIndex OBJECT-TYPE
   SYNTAX     INTEGER  {
                 fastRam(0),
                 normalRam(1),
                 sharedRam(2) }
   ACCESS     not-accessible
   STATUS     mandatory
   DESCRIPTION
     "This variable represents the lpMemoryCapacityTable
      specific index for the lpMemoryCapacityTable."
::= { lpMemoryCapacityEntry 1 }

lpMemoryCapacityValue OBJECT-TYPE
   SYNTAX     Unsigned32 (0..2147483647)
   ACCESS     read-only
   STATUS     mandatory
   DESCRIPTION
     "This variable represents an individual value for the
      lpMemoryCapacityTable."
::= { lpMemoryCapacityEntry 2 }

lpMemoryUsageTable OBJECT-TYPE
   SYNTAX     SEQUENCE OF LpMemoryUsageEntry
   ACCESS     not-accessible
   STATUS     mandatory
   DESCRIPTION
     "This attribute indicates the processor's current memory utilization 
      (in kilobytes) for each type of memory."
::= { lp 245 }

lpMemoryUsageEntry OBJECT-TYPE
   SYNTAX     LpMemoryUsageEntry
   ACCESS     not-accessible
   STATUS     mandatory
   DESCRIPTION
     "An entry in the lpMemoryUsageTable."
   INDEX {
      lpIndex,
      lpMemoryUsageIndex }
::= { lpMemoryUsageTable 1 }

LpMemoryUsageEntry ::= SEQUENCE {
   lpMemoryUsageIndex
      INTEGER,
   lpMemoryUsageValue
      Gauge32 }

lpMemoryUsageIndex OBJECT-TYPE
   SYNTAX     INTEGER  {
                 fastRam(0),
                 normalRam(1),
                 sharedRam(2) }
   ACCESS     not-accessible
   STATUS     mandatory
   DESCRIPTION
     "This variable represents the lpMemoryUsageTable
      specific index for the lpMemoryUsageTable."
::= { lpMemoryUsageEntry 1 }

lpMemoryUsageValue OBJECT-TYPE
   SYNTAX     Gauge32 (0..2147483647)
   ACCESS     read-only
   STATUS     mandatory
   DESCRIPTION
     "This variable represents an individual value for the
      lpMemoryUsageTable."
::= { lpMemoryUsageEntry 2 }

lpMemoryUsageAvgTable OBJECT-TYPE
   SYNTAX     SEQUENCE OF LpMemoryUsageAvgEntry
   ACCESS     not-accessible
   STATUS     mandatory
   DESCRIPTION
     "This attribute indicates the processor's average memory utilization 
      (in kilobytes) for each type of memory in the specified time period, 
      timeInterval. This value is calculated using 15 second samples."
::= { lp 276 }

lpMemoryUsageAvgEntry OBJECT-TYPE
   SYNTAX     LpMemoryUsageAvgEntry
   ACCESS     not-accessible
   STATUS     mandatory
   DESCRIPTION
     "An entry in the lpMemoryUsageAvgTable."
   INDEX {
      lpIndex,
      lpMemoryUsageAvgIndex }
::= { lpMemoryUsageAvgTable 1 }

LpMemoryUsageAvgEntry ::= SEQUENCE {
   lpMemoryUsageAvgIndex
      INTEGER,
   lpMemoryUsageAvgValue
      Gauge32 }

lpMemoryUsageAvgIndex OBJECT-TYPE
   SYNTAX     INTEGER  {
                 fastRam(0),
                 normalRam(1),
                 sharedRam(2) }
   ACCESS     not-accessible
   STATUS     mandatory
   DESCRIPTION
     "This variable represents the lpMemoryUsageAvgTable
      specific index for the lpMemoryUsageAvgTable."
::= { lpMemoryUsageAvgEntry 1 }

lpMemoryUsageAvgValue OBJECT-TYPE
   SYNTAX     Gauge32 (0..2147483647)
   ACCESS     read-only
   STATUS     mandatory
   DESCRIPTION
     "This variable represents an individual value for the
      lpMemoryUsageAvgTable."
::= { lpMemoryUsageAvgEntry 2 }

lpMemoryUsageAvgMinTable OBJECT-TYPE
   SYNTAX     SEQUENCE OF LpMemoryUsageAvgMinEntry
   ACCESS     not-accessible
   STATUS     mandatory
   DESCRIPTION
     "This attribute indicates the processor's minimum memory 
      utilization (in kilobytes) for each type of memory in the specified 
      time period, timeInterval. This value is calculated using 15 second 
      samples."
::= { lp 277 }

lpMemoryUsageAvgMinEntry OBJECT-TYPE
   SYNTAX     LpMemoryUsageAvgMinEntry
   ACCESS     not-accessible
   STATUS     mandatory
   DESCRIPTION
     "An entry in the lpMemoryUsageAvgMinTable."
   INDEX {
      lpIndex,
      lpMemoryUsageAvgMinIndex }
::= { lpMemoryUsageAvgMinTable 1 }

LpMemoryUsageAvgMinEntry ::= SEQUENCE {
   lpMemoryUsageAvgMinIndex
      INTEGER,
   lpMemoryUsageAvgMinValue
      Gauge32 }

lpMemoryUsageAvgMinIndex OBJECT-TYPE
   SYNTAX     INTEGER  {
                 fastRam(0),
                 normalRam(1),
                 sharedRam(2) }
   ACCESS     not-accessible
   STATUS     mandatory
   DESCRIPTION
     "This variable represents the lpMemoryUsageAvgMinTable
      specific index for the lpMemoryUsageAvgMinTable."
::= { lpMemoryUsageAvgMinEntry 1 }

lpMemoryUsageAvgMinValue OBJECT-TYPE
   SYNTAX     Gauge32 (0..2147483647)
   ACCESS     read-only
   STATUS     mandatory
   DESCRIPTION
     "This variable represents an individual value for the
      lpMemoryUsageAvgMinTable."
::= { lpMemoryUsageAvgMinEntry 2 }

lpMemoryUsageAvgMaxTable OBJECT-TYPE
   SYNTAX     SEQUENCE OF LpMemoryUsageAvgMaxEntry
   ACCESS     not-accessible
   STATUS     mandatory
   DESCRIPTION
     "This attribute indicates the processor's maximum memory 
      utilization (in kilobytes) for each type of memory in the specified 
      time period, timeInterval. This value is calculated using 15 second 
      samples."
::= { lp 278 }

lpMemoryUsageAvgMaxEntry OBJECT-TYPE
   SYNTAX     LpMemoryUsageAvgMaxEntry
   ACCESS     not-accessible
   STATUS     mandatory
   DESCRIPTION
     "An entry in the lpMemoryUsageAvgMaxTable."
   INDEX {
      lpIndex,
      lpMemoryUsageAvgMaxIndex }
::= { lpMemoryUsageAvgMaxTable 1 }

LpMemoryUsageAvgMaxEntry ::= SEQUENCE {
   lpMemoryUsageAvgMaxIndex
      INTEGER,
   lpMemoryUsageAvgMaxValue
      Gauge32 }

lpMemoryUsageAvgMaxIndex OBJECT-TYPE
   SYNTAX     INTEGER  {
                 fastRam(0),
                 normalRam(1),
                 sharedRam(2) }
   ACCESS     not-accessible
   STATUS     mandatory
   DESCRIPTION
     "This variable represents the lpMemoryUsageAvgMaxTable
      specific index for the lpMemoryUsageAvgMaxTable."
::= { lpMemoryUsageAvgMaxEntry 1 }

lpMemoryUsageAvgMaxValue OBJECT-TYPE
   SYNTAX     Gauge32 (0..2147483647)
   ACCESS     read-only
   STATUS     mandatory
   DESCRIPTION
     "This variable represents an individual value for the
      lpMemoryUsageAvgMaxTable."
::= { lpMemoryUsageAvgMaxEntry 2 }


-- Lp/n DS3/n
-- The DS3 component controls a DS3 port on a DS3 Function 
-- Processor. Non-zero Instance numbers for the DS3 are only allowed 
-- on cell-based boards.

lpDS3 OBJECT IDENTIFIER ::= { lp 5 }



lpDS3RowStatusTable OBJECT-TYPE
   SYNTAX     SEQUENCE OF LpDS3RowStatusEntry
   ACCESS     not-accessible
   STATUS     mandatory
   DESCRIPTION
     "This entry controls the addition and deletion of 
      lpDS3 components."
::= { lpDS3 1 }

lpDS3RowStatusEntry OBJECT-TYPE
   SYNTAX     LpDS3RowStatusEntry
   ACCESS     not-accessible
   STATUS     mandatory
   DESCRIPTION
     "A single entry in the table represents a single 
      lpDS3 component."
   INDEX {
      lpIndex,
      lpDS3Index }
::= { lpDS3RowStatusTable 1 }

LpDS3RowStatusEntry ::= SEQUENCE {
   lpDS3RowStatus
      RowStatus,
   lpDS3ComponentName
      DisplayString,
   lpDS3StorageType
      StorageType,
   lpDS3Index
      Integer32 }

lpDS3RowStatus OBJECT-TYPE
   SYNTAX     RowStatus 
   ACCESS     read-write
   STATUS     mandatory
   DESCRIPTION
     "This variable is used as the basis for SNMP naming of
      lpDS3 components.
      These components can be added and deleted."
::= { lpDS3RowStatusEntry 1 }

lpDS3ComponentName OBJECT-TYPE
   SYNTAX     DisplayString 
   ACCESS     read-only
   STATUS     mandatory
   DESCRIPTION
     "This variable provides the component's string name for
      use with the ASCII Console Interface"
::= { lpDS3RowStatusEntry 2 }

lpDS3StorageType OBJECT-TYPE
   SYNTAX     StorageType 
   ACCESS     read-only
   STATUS     mandatory
   DESCRIPTION
     "This variable represents the storage type value for the
      lpDS3 tables."
::= { lpDS3RowStatusEntry 4 }

lpDS3Index OBJECT-TYPE
   SYNTAX     Integer32 (0..2)
   ACCESS     not-accessible
   STATUS     mandatory
   DESCRIPTION
     "This variable represents the index for the lpDS3 tables."
::= { lpDS3RowStatusEntry 10 }

lpDS3ProvTable OBJECT-TYPE
   SYNTAX     SEQUENCE OF LpDS3ProvEntry
   ACCESS     not-accessible
   STATUS     mandatory
   DESCRIPTION
     "This group contains all of the provisioning data for a DS3 
      component."
::= { lpDS3 10 }

lpDS3ProvEntry OBJECT-TYPE
   SYNTAX     LpDS3ProvEntry
   ACCESS     not-accessible
   STATUS     mandatory
   DESCRIPTION
     "An entry in the lpDS3ProvTable."
   INDEX {
      lpIndex,
      lpDS3Index }
::= { lpDS3ProvTable 1 }

LpDS3ProvEntry ::= SEQUENCE {
   lpDS3CbitParity
      INTEGER,
   lpDS3LineLength
      Unsigned32,
   lpDS3ClockingSource
      INTEGER,
   lpDS3ApplicationFramerName
      Link,
   lpDS3Mapping
      INTEGER }

lpDS3CbitParity OBJECT-TYPE
   SYNTAX     INTEGER  {
                 off(0),
                 on(1) }
   ACCESS     read-write
   STATUS     mandatory
   DESCRIPTION
     "This attribute indicates if C-Bit parity has been turned ON or OFF. 
      The CBIT component will appear under the DS3 component when 
      the cbitParity attribute is set to on."
   DEFVAL     { on }
::= { lpDS3ProvEntry 1 }

lpDS3LineLength OBJECT-TYPE
   SYNTAX     Unsigned32 (0..450)
   ACCESS     read-write
   STATUS     mandatory
   DESCRIPTION
     "This attribute defines the line length for equalization calculations 
      for the DS3 line. The range is between 0 and 450 feet (1 metre = 
      3.28 feet). 
      Note: There are currently only two ranges as far as the equalization 
      calculation performed on the FP is concerned: 0 to 224ft and 225 to 
      450ft."
   DEFVAL     { 1 }
::= { lpDS3ProvEntry 2 }

lpDS3ClockingSource OBJECT-TYPE
   SYNTAX     INTEGER  {
                 local(0),
                 line(1),
                 module(2),
                 otherPort(4) }
   ACCESS     read-write
   STATUS     mandatory
   DESCRIPTION
     "This attribute defines the type of clocking source used for 
      synchronizing the DS3 transmit clock: local means direct use of the 
      local clock oscillator at its centre frequency; line means use of a 
      signal phase-locked to the incoming DS3 line rate; module means 
      the use of a signal phase-locked to the CP reference clock.
      Note that the multiport cell-based cards have one common clock 
      source for all ports. For this reason, the following rules apply for the 
      value of clockingSource across the board's three ports: 
      All three clockingSource values must be 'local' OR
      All three clockingSource values must be 'module' OR
      One clockingSource value must be 'line' and the other two must be 
      'otherPort'.
      The there is no NS component provisioned, the default value for this 
      attribute will be local. If the NS component has been provisioned, 
      the default value is module, except for the 1pDS3C cards.
      For the 1pDS3C cards, the default and only valid value for this 
      attribute is local. The clockingSource of the DS1 sub-component 
      becomes the effective clocking source for this attribute. All the DS1 
      sub-components have the same clocking source."
::= { lpDS3ProvEntry 3 }

lpDS3ApplicationFramerName OBJECT-TYPE
   SYNTAX     Link 
   ACCESS     read-write
   STATUS     mandatory
   DESCRIPTION
     "This attribute defines the link to the software stack. It defines which 
      application is running on top of the DS3 component."
::= { lpDS3ProvEntry 4 }

lpDS3Mapping OBJECT-TYPE
   SYNTAX     INTEGER  {
                 direct(0),
                 plcp(1) }
   ACCESS     read-write
   STATUS     mandatory
   DESCRIPTION
     "This attribute indicates if ATM cells will be mapped directly into 
      the DS3 payload, or whether PLCP mapping will be used. The 
      PLCP component will appear under the DS3 component when this 
      attribute is set to plcp. This attribute will be ignored when set on 
      frame-based cards."
   DEFVAL     { direct }
::= { lpDS3ProvEntry 5 }

lpDS3CidDataTable OBJECT-TYPE
   SYNTAX     SEQUENCE OF LpDS3CidDataEntry
   ACCESS     not-accessible
   STATUS     mandatory
   DESCRIPTION
     "This group contains the attribute for a component's Customer 
      Identifier (CID). Refer to the attribute description for a detailed 
      explanation of CIDs."
::= { lpDS3 11 }

lpDS3CidDataEntry OBJECT-TYPE
   SYNTAX     LpDS3CidDataEntry
   ACCESS     not-accessible
   STATUS     mandatory
   DESCRIPTION
     "An entry in the lpDS3CidDataTable."
   INDEX {
      lpIndex,
      lpDS3Index }
::= { lpDS3CidDataTable 1 }

LpDS3CidDataEntry ::= SEQUENCE {
   lpDS3CustomerIdentifier
      Unsigned32 }

lpDS3CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpDS3CidDataEntry 1 }

lpDS3AdminInfoTable OBJECT-TYPE
   SYNTAX     SEQUENCE OF LpDS3AdminInfoEntry
   ACCESS     not-accessible
   STATUS     mandatory
   DESCRIPTION
     "This group contains the attributes pertaining to the vendor of the 
      equipment."
::= { lpDS3 12 }

lpDS3AdminInfoEntry OBJECT-TYPE
   SYNTAX     LpDS3AdminInfoEntry
   ACCESS     not-accessible
   STATUS     mandatory
   DESCRIPTION
     "An entry in the lpDS3AdminInfoTable."
   INDEX {
      lpIndex,
      lpDS3Index }
::= { lpDS3AdminInfoTable 1 }

LpDS3AdminInfoEntry ::= SEQUENCE {
   lpDS3Vendor
      AsciiString,
   lpDS3CommentText
      AsciiString }

lpDS3Vendor OBJECT-TYPE
   SYNTAX     AsciiString (SIZE (0..20))
   ACCESS     read-write
   STATUS     mandatory
   DESCRIPTION
     "This is the name of the vendor supplying the facility."
::= { lpDS3AdminInfoEntry 1 }

lpDS3CommentText OBJECT-TYPE
   SYNTAX     AsciiString (SIZE (0..60))
   ACCESS     read-write
   STATUS     mandatory
   DESCRIPTION
     "Any miscellaneous text about the facility."
::= { lpDS3AdminInfoEntry 2 }

lpDS3IfEntryTable OBJECT-TYPE
   SYNTAX     SEQUENCE OF LpDS3IfEntryEntry
   ACCESS     not-accessible
   STATUS     mandatory
   DESCRIPTION
     "This group contains the provisionable attributes for the ifEntry."
::= { lpDS3 13 }

lpDS3IfEntryEntry OBJECT-TYPE
   SYNTAX     LpDS3IfEntryEntry
   ACCESS     not-accessible
   STATUS     mandatory
   DESCRIPTION
     "An entry in the lpDS3IfEntryTable."
   INDEX {
      lpIndex,
      lpDS3Index }
::= { lpDS3IfEntryTable 1 }

LpDS3IfEntryEntry ::= SEQUENCE {
   lpDS3IfAdminStatus
      INTEGER,
   lpDS3IfIndex
      InterfaceIndex }

lpDS3IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpDS3IfEntryEntry 1 }

lpDS3IfIndex OBJECT-TYPE
   SYNTAX     InterfaceIndex (1..65535)
   ACCESS     read-only
   STATUS     mandatory
   DESCRIPTION
     "This is the index for the IfEntry. Its value is automatically initialized 
      during the provisioning process."
::= { lpDS3IfEntryEntry 2 }

lpDS3OperStatusTable OBJECT-TYPE
   SYNTAX     SEQUENCE OF LpDS3OperStatusEntry
   ACCESS     not-accessible
   STATUS     mandatory
   DESCRIPTION
     "This group includes the Operational Status attribute. This attribute 
      defines the current operational state of this component."
::= { lpDS3 14 }

lpDS3OperStatusEntry OBJECT-TYPE
   SYNTAX     LpDS3OperStatusEntry
   ACCESS     not-accessible
   STATUS     mandatory
   DESCRIPTION
     "An entry in the lpDS3OperStatusTable."
   INDEX {
      lpIndex,
      lpDS3Index }
::= { lpDS3OperStatusTable 1 }

LpDS3OperStatusEntry ::= SEQUENCE {
   lpDS3SnmpOperStatus
      INTEGER }

lpDS3SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpDS3OperStatusEntry 1 }

lpDS3StateTable OBJECT-TYPE
   SYNTAX     SEQUENCE OF LpDS3StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpDS3 15 }

lpDS3StateEntry OBJECT-TYPE
   SYNTAX     LpDS3StateEntry
   ACCESS     not-accessible
   STATUS     mandatory
   DESCRIPTION
     "An entry in the lpDS3StateTable."
   INDEX {
      lpIndex,
      lpDS3Index }
::= { lpDS3StateTable 1 }

LpDS3StateEntry ::= SEQUENCE {
   lpDS3AdminState
      INTEGER,
   lpDS3OperationalState
      INTEGER,
   lpDS3UsageState
      INTEGER,
   lpDS3AvailabilityStatus
      OCTET STRING,
   lpDS3ProceduralStatus
      OCTET STRING,
   lpDS3ControlStatus
      OCTET STRING,
   lpDS3AlarmStatus
      OCTET STRING,
   lpDS3StandbyStatus
      INTEGER,
   lpDS3UnknownStatus
      INTEGER }

lpDS3AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpDS3StateEntry 1 }

lpDS3OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpDS3StateEntry 2 }

lpDS3UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpDS3StateEntry 3 }

lpDS3AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpDS3StateEntry 4 }

lpDS3ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpDS3StateEntry 5 }

lpDS3ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpDS3StateEntry 6 }

lpDS3AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpDS3StateEntry 7 }

lpDS3StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpDS3StateEntry 8 }

lpDS3UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpDS3StateEntry 9 }

lpDS3OperTable OBJECT-TYPE
   SYNTAX     SEQUENCE OF LpDS3OperEntry
   ACCESS     not-accessible
   STATUS     mandatory
   DESCRIPTION
     "This group contains the common operational data for DS3 
      component."
::= { lpDS3 16 }

lpDS3OperEntry OBJECT-TYPE
   SYNTAX     LpDS3OperEntry
   ACCESS     not-accessible
   STATUS     mandatory
   DESCRIPTION
     "An entry in the lpDS3OperTable."
   INDEX {
      lpIndex,
      lpDS3Index }
::= { lpDS3OperTable 1 }

LpDS3OperEntry ::= SEQUENCE {
   lpDS3LosAlarm
      INTEGER,
   lpDS3LofAlarm
      INTEGER,
   lpDS3RxAisAlarm
      INTEGER,
   lpDS3RxRaiAlarm
      INTEGER,
   lpDS3RxIdle
      INTEGER,
   lpDS3TxAis
      INTEGER,
   lpDS3TxRai
      INTEGER,
   lpDS3TxIdle
      INTEGER }

lpDS3LosAlarm OBJECT-TYPE
   SYNTAX     INTEGER  {
                 on(0),
                 off(1) }
   ACCESS     read-only
   STATUS     mandatory
   DESCRIPTION
     "This attribute displays whether a Loss Of Signal (LOS) alarm state 
      has been entered. An LOS alarm state is entered when LOS defects 
      have been observed and accumulated for a period of 2.5 seconds +/- 
      0.5 seconds. An LOS defect is detected at the DS3 line interface 
      upon observing 175 +/- 75 continuous pulse positions with no 
      pulses of either positive or negative polarity. If the LOS defects are 
      intermittently occurring, the LOS defect accumulator is 
      decremented at a rate of 1/10 of the incrementing rate (alarm 
      integration ratio of 1/10), with all measurements based on a 200 ms 
      polling cycle.
      The DS3 component goes into an operational state of disabled until 
      the LOS alarm condition is cleared. The LOS alarm state is cleared 
      after LOS defects have been absent for a period of 10 seconds +/- 
      0.5 seconds.
      The losAlarm attribute is always set to off when the component has 
      been locked and left offline."
   DEFVAL     { off }
::= { lpDS3OperEntry 1 }

lpDS3LofAlarm OBJECT-TYPE
   SYNTAX     INTEGER  {
                 on(0),
                 off(1) }
   ACCESS     read-only
   STATUS     mandatory
   DESCRIPTION
     "This attribute displays whether a Loss Of Frame (LOF) alarm state 
      has been entered. An LOF alarm state is entered when Severely 
      Errored Frame (SEF) defects have been observed and accumulated 
      for a period of 2.5 seconds +/- 0.5 seconds. A SEF defect is 
      detected when 3 (or more) out of 16 (or fewer) F-bits are in error, or 
      one (or more) M-bits in two (or more) out of four (or fewer) 
      consecutive M-frames are in error. If the LOF defects are 
      intermittently occurring, the LOF defect accumulator is 
      decremented at a rate of 1/10 of the incrementing rate (alarm 
      integration ratio of 1/10), with all measurements based on a 200 ms 
      polling cycle.
      The DS3 component goes into an operational state of disabled until 
      the LOF alarm condition is cleared. The condition is cleared when 
      framing has been achieved for a period of 10 seconds +/- 0.5 
      seconds. As long as SEF defects are detected, the node also 
      transmits the far-end SEF/AIS defect indicator over the outgoing 
      line. When not running in C-Bit Parity mode, the txRai attribute is 
      also set to on when transmitting the far-end SEF/AIS defect 
      indicator on the outgoing line.
      The lofAlarm attribute is always set to off when the component has 
      been locked and left offline."
   DEFVAL     { off }
::= { lpDS3OperEntry 2 }

lpDS3RxAisAlarm OBJECT-TYPE
   SYNTAX     INTEGER  {
                 on(0),
                 off(1) }
   ACCESS     read-only
   STATUS     mandatory
   DESCRIPTION
     "This attribute displays whether an Alarm Indication Signal (AIS) 
      alarm state has been entered. An AIS alarm state is entered when 
      AIS defects have been observed and accumulated for 2.5 seconds +/
      - 0.5 seconds. An AIS defect is the occurrence of AIS (valid DS3 
      frame with payload containing the 1010...sequence and with C-Bits 
      set to zero) in contiguous M-frames for a time greater than 100 
      milliseconds. If the AIS defects are intermittently occurring, the 
      AIS defect accumulator is decremented at a rate of 1/10 of the 
      incrementing rate (alarm integration ratio of 1/10), with all 
      measurements based on a 200 ms polling cycle.
      The DS3 component goes into an operational state of disabled until 
      the AIS alarm condition is cleared (after AIS has been no longer 
      detected for a period of 10 seconds +/- 0.5 seconds). As long as AIS 
      is detected, the node also transmits the far-end SEF/AIS defect 
      indicator over the outgoing line. When not running in C-Bit Parity 
      mode, the txRai attribute is also set to on when transmitting the far-
      end SEF/AIS defect indicator on the outgoing line.
      The rxAisAlarm attribute is always set to off when the component 
      has been locked and left offline."
   DEFVAL     { off }
::= { lpDS3OperEntry 3 }

lpDS3RxRaiAlarm OBJECT-TYPE
   SYNTAX     INTEGER  {
                 on(0),
                 off(1) }
   ACCESS     read-only
   STATUS     mandatory
   DESCRIPTION
     "This attribute displays whether a Remote Alarm Indication (RAI) 
      alarm state has been entered. 
      When not running the C-Bit Parity mode, the RAI alarm state is 
      entered when the far-end SEF/AIS defect indicator has been 
      observed and accumulated for a period of 2.5 seconds +/- 0.5 
      seconds on the incoming DS3 line. If the RAI defects are 
      intermittently occurring, the RAI defect accumulator is 
      decremented at a rate of 1/10 of the incrementing rate (alarm 
      integration ratio of 1/10), with all measurements based on a 200 ms 
      polling cycle. The DS3 component goes into an operational state of 
      disabled until the RAI alarm condition is cleared. The condition is 
      cleared when the far-end SEF/AIS defect indicator has not been 
      detected for 10 seconds +/- 0.5 seconds. 
      When running the C-Bit Parity mode, the RAI alarm state is entered 
      upon detection of a far-end alarm over the Far-End Alarm and 
      Control (FEAC) channel. The RAI alarm state is exited as soon as 
      no more far-end alarm is detected on the FEAC channel. The far-
      end alarms that can be detected on the FEAC channel and that cause 
      the RAI alarm state to be entered are: equipment failure alarm 
      (service affecting), LOS alarm, LOF alarm, idle and AIS alarm.
      The rxRaiAlarm attribute is always set to off when the component 
      has been locked and left offline."
   DEFVAL     { off }
::= { lpDS3OperEntry 4 }

lpDS3RxIdle OBJECT-TYPE
   SYNTAX     INTEGER  {
                 on(0),
                 off(1) }
   ACCESS     read-only
   STATUS     mandatory
   DESCRIPTION
     "This attribute displays whether an Idle failure condition has been 
      reported on the DS3 port. An Idle condition is reported when DS3 
      Idle defects have been observed and accumulated for a period of 2.5 
      seconds +/- 0.5 seconds. The DS3 Idle defect is the occurrence of a 
      valid DS3 frame with the information bits set to a 11001100.. 
      sequence. If the DS3 Idle defects are intermittently occurring, the 
      DS3 Idle defect accumulator is decremented at a rate of 1/10 of the 
      incrementing rate (alarm integration ratio of 1/10), with all 
      measurements based on a 200 ms polling cycle.
      The DS3 component goes into an operational state of disabled until 
      the Idle failure condition is cleared. The failure condition is cleared 
      when the DS3 idle pattern has not been detected for at least 10 
      seconds +/- 0.5 seconds.
      The rxIdle attribute is always set to off when the component has 
      been locked and left offline.
      The idle pattern indicates that the far-end is physically connected 
      but not put in service. For instance, DS3 idle is transmitted on the 
      outgoing line when the DS3 component is locked and not used for 
      operational testing."
   DEFVAL     { off }
::= { lpDS3OperEntry 5 }

lpDS3TxAis OBJECT-TYPE
   SYNTAX     INTEGER  {
                 on(0),
                 off(1) }
   ACCESS     read-only
   STATUS     mandatory
   DESCRIPTION
     "This attribute displays whether an Alarm Indication Signal (AIS) 
      alarm is being transmitted on the DS3 line. Currently, AIS is never 
      transmitted by a Passport DS3 node."
   DEFVAL     { off }
::= { lpDS3OperEntry 6 }

lpDS3TxRai OBJECT-TYPE
   SYNTAX     INTEGER  {
                 on(0),
                 off(1) }
   ACCESS     read-only
   STATUS     mandatory
   DESCRIPTION
     "When not running C-Bit Parity mode, this attribute displays whether 
      the far-end SEF/AIS defect indicator is transmitted over the 
      outgoing line when the DS3 component has been unlocked or used 
      in operational testing. When running in C-Bit Parity mode, this 
      attribute displays whether a far-end alarm is sent over the Far-End 
      Alarm and Control (FEAC) channel when the DS3 component has 
      been unlocked or used in operational testing. When the DS3 
      component is locked and not used in operational testing, this 
      attribute is always set to off."
   DEFVAL     { off }
::= { lpDS3OperEntry 7 }

lpDS3TxIdle OBJECT-TYPE
   SYNTAX     INTEGER  {
                 on(0),
                 off(1) }
   ACCESS     read-only
   STATUS     mandatory
   DESCRIPTION
     "This attribute displays whether the DS3 Idle signal is transmitted 
      over the outgoing line. DS3 Idle is sent when the DS3 component 
      has been locked and not used in operational testing."
   DEFVAL     { off }
::= { lpDS3OperEntry 8 }

lpDS3StatsTable OBJECT-TYPE
   SYNTAX     SEQUENCE OF LpDS3StatsEntry
   ACCESS     not-accessible
   STATUS     mandatory
   DESCRIPTION
     "This group contains the specific DS3 common operational data for a 
      DS3 component. Each attribute type is a non-negative integer which 
      monotonically increases until it reaches a maximum value, at which 
      point it wraps around and starts increasing again from zero."
::= { lpDS3 17 }

lpDS3StatsEntry OBJECT-TYPE
   SYNTAX     LpDS3StatsEntry
   ACCESS     not-accessible
   STATUS     mandatory
   DESCRIPTION
     "An entry in the lpDS3StatsTable."
   INDEX {
      lpIndex,
      lpDS3Index }
::= { lpDS3StatsTable 1 }

LpDS3StatsEntry ::= SEQUENCE {
   lpDS3RunningTime
      Counter32,
   lpDS3ErrorFreeSec
      Counter32,
   lpDS3LineCodeViolations
      Counter32,
   lpDS3LineErroredSec
      Counter32,
   lpDS3LineSevErroredSec
      Counter32,
   lpDS3LineLosSec
      Counter32,
   lpDS3LineFailures
      Counter32,
   lpDS3PathCodeViolations
      Counter32,
   lpDS3PathErroredSec
      Counter32,
   lpDS3PathSevErroredSec
      Counter32,
   lpDS3PathSefAisSec
      Counter32,
   lpDS3PathUnavailSec
      Counter32,
   lpDS3PathFailures
      Counter32 }

lpDS3RunningTime OBJECT-TYPE
   SYNTAX     Counter32 
   ACCESS     read-only
   STATUS     mandatory
   DESCRIPTION
     "This attribute indicates the total number of seconds since the DS3 
      component has been activated and been in unlocked state or used 
      for operational testing. All the other error counts that follow as well 
      as each DS3 subcomponent's error counts can be updated when this 
      count is active."
::= { lpDS3StatsEntry 1 }

lpDS3ErrorFreeSec OBJECT-TYPE
   SYNTAX     Counter32 
   ACCESS     read-only
   STATUS     mandatory
   DESCRIPTION
     "This attribute indicates the number of seconds that the DS3 port has 
      been in an error free state."
::= { lpDS3StatsEntry 2 }

lpDS3LineCodeViolations OBJECT-TYPE
   SYNTAX     Counter32 
   ACCESS     read-only
   STATUS     mandatory
   DESCRIPTION
     "This attribute indicates the total number of Line Code Violations 
      (LCV) detected. A DS3 Line Code Violation is a B3Zs error. LCV 
      counting is inhibited for second intervals where Line Severely 
      Errored Second (LSES) is counted.
      This attribute is a non-negative integer which monotonically 
      increases until it reaches a maximum value, at which point it wraps 
      around and starts increasing again from zero."
::= { lpDS3StatsEntry 3 }

lpDS3LineErroredSec OBJECT-TYPE
   SYNTAX     Counter32 
   ACCESS     read-only
   STATUS     mandatory
   DESCRIPTION
     "This attribute indicates the total number of Line Errored Seconds 
      (LES) that have been counted. A LES is declared for second 
      intervals containing one or more LCV or one or more Loss Of 
      Signal (LOS) defects."
::= { lpDS3StatsEntry 4 }

lpDS3LineSevErroredSec OBJECT-TYPE
   SYNTAX     Counter32 
   ACCESS     read-only
   STATUS     mandatory
   DESCRIPTION
     "This attribute indicates the total number of Line Severely Errored 
      Seconds (LSES) that have been counted. A LSES is declared for 
      second intervals containing more than 44 LCVs or one or more 
      LOS defects."
::= { lpDS3StatsEntry 5 }

lpDS3LineLosSec OBJECT-TYPE
   SYNTAX     Counter32 
   ACCESS     read-only
   STATUS     mandatory
   DESCRIPTION
     "This attribute indicates the total number of Line LOS Seconds 
      (LOSS) that have been counted. A LOSS is declared for second 
      intervals containing one or more LOS defects."
::= { lpDS3StatsEntry 6 }

lpDS3LineFailures OBJECT-TYPE
   SYNTAX     Counter32 
   ACCESS     read-only
   STATUS     mandatory
   DESCRIPTION
     "This attribute indicates the total number of times that a line failure 
      (LOS failure) has been declared.
      This attribute is a non-negative integer which monotonically 
      increases until it reaches a maximum value, at which point it wraps 
      around and starts increasing again from zero."
::= { lpDS3StatsEntry 7 }

lpDS3PathCodeViolations OBJECT-TYPE
   SYNTAX     Counter32 
   ACCESS     read-only
   STATUS     mandatory
   DESCRIPTION
     "This attribute indicates the total number of Path Code Violations 
      (PCVs) detected. Each PCV corresponds to a P-bit parity error, or 
      possibly a frame error or a disagreement between P-bits or X-bits. 
      PCV counting is inhibited over second intervals where a Path 
      Severely Errored Second (PSES) is counted. Counting of PCVs is 
      also inhibited over second intervals where a Path Unavailable 
      Second (PUAS) is counted. 
      This attribute is a non-negative integer which monotonically 
      increases until it reaches a maximum value, at which point it wraps 
      around and starts increasing again from zero."
::= { lpDS3StatsEntry 8 }

lpDS3PathErroredSec OBJECT-TYPE
   SYNTAX     Counter32 
   ACCESS     read-only
   STATUS     mandatory
   DESCRIPTION
     "This attribute indicates the total number of Path Errored Seconds 
      (PESs) that have been counted. A PES is declared for second 
      intervals containing one or more Path Code Violations (PCV) or one 
      or more Severely Errored Frame (SEF) or Alarm Indication Signal 
      (AIS) defects. Counting of Path Errored Seconds is inhibited when 
      Path Unavailable Seconds (PUAS) is counted over the monitored 
      second."
::= { lpDS3StatsEntry 9 }

lpDS3PathSevErroredSec OBJECT-TYPE
   SYNTAX     Counter32 
   ACCESS     read-only
   STATUS     mandatory
   DESCRIPTION
     "This attribute indicates the total number of Path Severely Errored 
      Seconds (PSESs) that have been counted. A PSES is declared for 
      second intervals containing more than 44 PCVs or one or more SEF 
      or AIS defects. Counting of PSESs is inhibited when Path 
      Unavailable Seconds (PUAS) is counted over the monitored second."
::= { lpDS3StatsEntry 10 }

lpDS3PathSefAisSec OBJECT-TYPE
   SYNTAX     Counter32 
   ACCESS     read-only
   STATUS     mandatory
   DESCRIPTION
     "This attribute indicates the total number of SEF/AIS Seconds 
      (PSASs). A PSAS is declared for second intervals containing one or 
      more Severely Errored Frame (SEF) or Alarm Indication Signal 
      (AIS) defects. Counting of PSAS is inhibited when Path 
      Unavailable Seconds (PUAS) is counted over the monitored second."
::= { lpDS3StatsEntry 11 }

lpDS3PathUnavailSec OBJECT-TYPE
   SYNTAX     Counter32 
   ACCESS     read-only
   STATUS     mandatory
   DESCRIPTION
     "This attribute indicates the total number of one second intervals for 
      which the DS3 path is unavailable. The DS3 path becomes 
      unavailable at the onset of 10 consecutive Path Severely Errored 
      Seconds (PSES). The 10 PSESs are included in the unavailable 
      time. Once unavailable, the DS3 path becomes available at the onset 
      of 10 contiguous seconds with no PSES. The 10 seconds with no 
      PSES are excluded from the unavailable time. For second intervals 
      where PUAS is counted, counting of Path Coding Violations (PCV), 
      Path Errored Seconds (PES), Path Severely Errored Seconds (PSES) 
      and Path Sef/Ais Seconds (PSAS) is inhibited."
::= { lpDS3StatsEntry 12 }

lpDS3PathFailures OBJECT-TYPE
   SYNTAX     Counter32 
   ACCESS     read-only
   STATUS     mandatory
   DESCRIPTION
     "This attribute indicates the total number of times that a path failure 
      (LOF/AIS failure) has been declared.
      This attribute is a non-negative integer which monotonically 
      increases until it reaches a maximum value, at which point it wraps 
      around and starts increasing again from zero."
::= { lpDS3StatsEntry 13 }


-- 
-- The Test component is configured to control a hardware facility test 
-- on a physical (V35, X21, DS1, E1, DS3, E3 etc.) or a logical port.

lpDS3Test OBJECT IDENTIFIER ::= { lpDS3 2 }



lpDS3TestRowStatusTable OBJECT-TYPE
   SYNTAX     SEQUENCE OF LpDS3TestRowStatusEntry
   ACCESS     not-accessible
   STATUS     mandatory
   DESCRIPTION
     "This entry controls the addition and deletion of 
      lpDS3Test components."
::= { lpDS3Test 1 }

lpDS3TestRowStatusEntry OBJECT-TYPE
   SYNTAX     LpDS3TestRowStatusEntry
   ACCESS     not-accessible
   STATUS     mandatory
   DESCRIPTION
     "A single entry in the table represents a single 
      lpDS3Test component."
   INDEX {
      lpIndex,
      lpDS3Index,
      lpDS3TestIndex }
::= { lpDS3TestRowStatusTable 1 }

LpDS3TestRowStatusEntry ::= SEQUENCE {
   lpDS3TestRowStatus
      RowStatus,
   lpDS3TestComponentName
      DisplayString,
   lpDS3TestStorageType
      StorageType,
   lpDS3TestIndex
      NonReplicated }

lpDS3TestRowStatus OBJECT-TYPE
   SYNTAX     RowStatus 
   ACCESS     read-only
   STATUS     mandatory
   DESCRIPTION
     "This variable is used as the basis for SNMP naming of
      lpDS3Test components.
      These components cannot be added nor deleted."
::= { lpDS3TestRowStatusEntry 1 }

lpDS3TestComponentName OBJECT-TYPE
   SYNTAX     DisplayString 
   ACCESS     read-only
   STATUS     mandatory
   DESCRIPTION
     "This variable provides the component's string name for
      use with the ASCII Console Interface"
::= { lpDS3TestRowStatusEntry 2 }

lpDS3TestStorageType OBJECT-TYPE
   SYNTAX     StorageType 
   ACCESS     read-only
   STATUS     mandatory
   DESCRIPTION
     "This variable represents the storage type value for the
      lpDS3Test tables."
::= { lpDS3TestRowStatusEntry 4 }

lpDS3TestIndex OBJECT-TYPE
   SYNTAX     NonReplicated 
   ACCESS     not-accessible
   STATUS     mandatory
   DESCRIPTION
     "This variable represents the index for the lpDS3Test tables."
::= { lpDS3TestRowStatusEntry 10 }

lpDS3TestStateTable OBJECT-TYPE
   SYNTAX     SEQUENCE OF LpDS3TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpDS3Test 10 }

lpDS3TestStateEntry OBJECT-TYPE
   SYNTAX     LpDS3TestStateEntry
   ACCESS     not-accessible
   STATUS     mandatory
   DESCRIPTION
     "An entry in the lpDS3TestStateTable."
   INDEX {
      lpIndex,
      lpDS3Index,
      lpDS3TestIndex }
::= { lpDS3TestStateTable 1 }

LpDS3TestStateEntry ::= SEQUENCE {
   lpDS3TestAdminState
      INTEGER,
   lpDS3TestOperationalState
      INTEGER,
   lpDS3TestUsageState
      INTEGER }

lpDS3TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpDS3TestStateEntry 1 }

lpDS3TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpDS3TestStateEntry 2 }

lpDS3TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpDS3TestStateEntry 3 }

lpDS3TestSetupTable OBJECT-TYPE
   SYNTAX     SEQUENCE OF LpDS3TestSetupEntry
   ACCESS     not-accessible
   STATUS     mandatory
   DESCRIPTION
     "This group contains all of the operational data for a Test 
      component."
::= { lpDS3Test 11 }

lpDS3TestSetupEntry OBJECT-TYPE
   SYNTAX     LpDS3TestSetupEntry
   ACCESS     not-accessible
   STATUS     mandatory
   DESCRIPTION
     "An entry in the lpDS3TestSetupTable."
   INDEX {
      lpIndex,
      lpDS3Index,
      lpDS3TestIndex }
::= { lpDS3TestSetupTable 1 }

LpDS3TestSetupEntry ::= SEQUENCE {
   lpDS3TestPurpose
      AsciiString,
   lpDS3TestType
      INTEGER,
   lpDS3TestFrmSize
      Unsigned32,
   lpDS3TestFrmPatternType
      INTEGER,
   lpDS3TestCustomizedPattern
      Hex,
   lpDS3TestDataStartDelay
      Unsigned32,
   lpDS3TestDisplayInterval
      Unsigned32,
   lpDS3TestDuration
      Unsigned32 }

lpDS3TestPurpose OBJECT-TYPE
   SYNTAX     AsciiString (SIZE (0..40))
   ACCESS     read-write
   STATUS     mandatory
   DESCRIPTION
     "This attribute records the purpose of the test so that the test results 
      can be associated and properly analyzed."
::= { lpDS3TestSetupEntry 1 }

lpDS3TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpDS3TestSetupEntry 2 }

lpDS3TestFrmSize OBJECT-TYPE
   SYNTAX     Unsigned32 (4..4096)
   ACCESS     read-write
   STATUS     mandatory
   DESCRIPTION
     "This attribute defines the size of the test data frames in number of 
      bytes."
   DEFVAL     { 1024 }
::= { lpDS3TestSetupEntry 3 }

lpDS3TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpDS3TestSetupEntry 4 }

lpDS3TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpDS3TestSetupEntry 5 }

lpDS3TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpDS3TestSetupEntry 6 }

lpDS3TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpDS3TestSetupEntry 7 }

lpDS3TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpDS3TestSetupEntry 8 }

lpDS3TestResultsTable OBJECT-TYPE
   SYNTAX     SEQUENCE OF LpDS3TestResultsEntry
   ACCESS     not-accessible
   STATUS     mandatory
   DESCRIPTION
     "This group contains all the statistics related attributes of the Test 
      component."
::= { lpDS3Test 12 }

lpDS3TestResultsEntry OBJECT-TYPE
   SYNTAX     LpDS3TestResultsEntry
   ACCESS     not-accessible
   STATUS     mandatory
   DESCRIPTION
     "An entry in the lpDS3TestResultsTable."
   INDEX {
      lpIndex,
      lpDS3Index,
      lpDS3TestIndex }
::= { lpDS3TestResultsTable 1 }

LpDS3TestResultsEntry ::= SEQUENCE {
   lpDS3TestElapsedTime
      Counter32,
   lpDS3TestTimeRemaining
      Unsigned32,
   lpDS3TestCauseOfTermination
      INTEGER,
   lpDS3TestBitsTx
      PassportCounter64,
   lpDS3TestBytesTx
      PassportCounter64,
   lpDS3TestFrmTx
      PassportCounter64,
   lpDS3TestBitsRx
      PassportCounter64,
   lpDS3TestBytesRx
      PassportCounter64,
   lpDS3TestFrmRx
      PassportCounter64,
   lpDS3TestErroredFrmRx
      PassportCounter64,
   lpDS3TestBitErrorRate
      AsciiString }

lpDS3TestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpDS3TestResultsEntry 1 }

lpDS3TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpDS3TestResultsEntry 2 }

lpDS3TestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpDS3TestResultsEntry 3 }

lpDS3TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpDS3TestResultsEntry 4 }

lpDS3TestBytesTx OBJECT-TYPE
   SYNTAX     PassportCounter64 
   ACCESS     read-only
   STATUS     mandatory
   DESCRIPTION
     "This attribute is the total number of bytes sent during the test 
      period. This counter is not expected to reach its maximum value."
::= { lpDS3TestResultsEntry 5 }

lpDS3TestFrmTx OBJECT-TYPE
   SYNTAX     PassportCounter64 
   ACCESS     read-only
   STATUS     mandatory
   DESCRIPTION
     "This attribute is the total number of frames sent during the test 
      period. This counter is not expected to reach its maximum value."
::= { lpDS3TestResultsEntry 6 }

lpDS3TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpDS3TestResultsEntry 7 }

lpDS3TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpDS3TestResultsEntry 8 }

lpDS3TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpDS3TestResultsEntry 9 }

lpDS3TestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpDS3TestResultsEntry 10 }

lpDS3TestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpDS3TestResultsEntry 11 }


-- Lp/n DS3/n CBIT
-- The CBIT component is configured to display all DS3 C-Bit parity 
-- related operational and statistical data. It will appear under the DS3 
-- component when the DS3 cbitParity attribute is set to on.

lpDS3CBit OBJECT IDENTIFIER ::= { lpDS3 3 }



lpDS3CBitRowStatusTable OBJECT-TYPE
   SYNTAX     SEQUENCE OF LpDS3CBitRowStatusEntry
   ACCESS     not-accessible
   STATUS     mandatory
   DESCRIPTION
     "This entry controls the addition and deletion of 
      lpDS3CBit components."
::= { lpDS3CBit 1 }

lpDS3CBitRowStatusEntry OBJECT-TYPE
   SYNTAX     LpDS3CBitRowStatusEntry
   ACCESS     not-accessible
   STATUS     mandatory
   DESCRIPTION
     "A single entry in the table represents a single 
      lpDS3CBit component."
   INDEX {
      lpIndex,
      lpDS3Index,
      lpDS3CBitIndex }
::= { lpDS3CBitRowStatusTable 1 }

LpDS3CBitRowStatusEntry ::= SEQUENCE {
   lpDS3CBitRowStatus
      RowStatus,
   lpDS3CBitComponentName
      DisplayString,
   lpDS3CBitStorageType
      StorageType,
   lpDS3CBitIndex
      NonReplicated }

lpDS3CBitRowStatus OBJECT-TYPE
   SYNTAX     RowStatus 
   ACCESS     read-only
   STATUS     mandatory
   DESCRIPTION
     "This variable is used as the basis for SNMP naming of
      lpDS3CBit components.
      These components cannot be added nor deleted."
::= { lpDS3CBitRowStatusEntry 1 }

lpDS3CBitComponentName OBJECT-TYPE
   SYNTAX     DisplayString 
   ACCESS     read-only
   STATUS     mandatory
   DESCRIPTION
     "This variable provides the component's string name for
      use with the ASCII Console Interface"
::= { lpDS3CBitRowStatusEntry 2 }

lpDS3CBitStorageType OBJECT-TYPE
   SYNTAX     StorageType 
   ACCESS     read-only
   STATUS     mandatory
   DESCRIPTION
     "This variable represents the storage type value for the
      lpDS3CBit tables."
::= { lpDS3CBitRowStatusEntry 4 }

lpDS3CBitIndex OBJECT-TYPE
   SYNTAX     NonReplicated 
   ACCESS     not-accessible
   STATUS     mandatory
   DESCRIPTION
     "This variable represents the index for the lpDS3CBit tables."
::= { lpDS3CBitRowStatusEntry 10 }

lpDS3CBitOperationalTable OBJECT-TYPE
   SYNTAX     SEQUENCE OF LpDS3CBitOperationalEntry
   ACCESS     not-accessible
   STATUS     mandatory
   DESCRIPTION
     "This group contains the DS3 C-Bit Parity operational data for the 
      CBIT component."
::= { lpDS3CBit 10 }

lpDS3CBitOperationalEntry OBJECT-TYPE
   SYNTAX     LpDS3CBitOperationalEntry
   ACCESS     not-accessible
   STATUS     mandatory
   DESCRIPTION
     "An entry in the lpDS3CBitOperationalTable."
   INDEX {
      lpIndex,
      lpDS3Index,
      lpDS3CBitIndex }
::= { lpDS3CBitOperationalTable 1 }

LpDS3CBitOperationalEntry ::= SEQUENCE {
   lpDS3CBitFarEndAlarm
      INTEGER,
   lpDS3CBitLoopedbackToFarEnd
      OCTET STRING,
   lpDS3CBitLoopbackAtFarEndRequested
      OCTET STRING }

lpDS3CBitFarEndAlarm OBJECT-TYPE
   SYNTAX     INTEGER  {
                 equipmentFailure(0),
                 los(1),
                 sef(2),
                 ais(3),
                 idle(4),
                 none(5) }
   ACCESS     read-only
   STATUS     mandatory
   DESCRIPTION
     "This attribute indicates the Far-End alarm signal that is currently 
      received at the DS3 interface. This signal is carried over the Far-
      End Alarm and Control (FEAC) bits of DS3 frames. Five far-end 
      alarm signals can be received: far-end equipment failure that is 
      received when the far-end terminal has detected a local equipment 
      failure; far-end Loss Of Signal (LOS) that is received when the far-
      end DS3 terminal has declared a LOS failure condition; far-end 
      Loss of Frame (LOF) when the far-end DS3 terminal has declared a 
      Loss Of Frame (LOF) failure condition; far-end Alarm Indication 
      Signal (AIS) when the far-end has declared an AIS failure 
      condition; far-end Idle when the far-end has declared an Idle signal 
      condition."
   DEFVAL     { none }
::= { lpDS3CBitOperationalEntry 1 }

lpDS3CBitLoopedbackToFarEnd OBJECT-TYPE
   SYNTAX     OCTET STRING (SIZE (4))
   ACCESS     read-only
   STATUS     mandatory
   DESCRIPTION
     "This indicates whether or not the DS3 component is currently 
      looping back the incoming DS3 signal or one of its DS1 tributaries 
      to the far-end DS3 terminal. This is activated when the far-end DS3 
      equipment has ordered the local terminal to do so.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      notused29(29)
      notused30(30)
      ds3Line(31)"
::= { lpDS3CBitOperationalEntry 2 }

lpDS3CBitLoopbackAtFarEndRequested OBJECT-TYPE
   SYNTAX     OCTET STRING (SIZE (4))
   ACCESS     read-only
   STATUS     mandatory
   DESCRIPTION
     "This attribute indicates which DS1 tributaries are being looped 
      back, or if the DS3 line is being looped back. Each value listed 
      indicates a loopback request has been made. When a loopback 
      deactivation command has been sent to the far end, the 
      corresponding value will be removed from the list.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      notused29(29)
      notused30(30)
      ds3Line(31)"
::= { lpDS3CBitOperationalEntry 3 }

lpDS3CBitStatsTable OBJECT-TYPE
   SYNTAX     SEQUENCE OF LpDS3CBitStatsEntry
   ACCESS     not-accessible
   STATUS     mandatory
   DESCRIPTION
     "This group contains the DS3 C-Bit Parity statistical data for the 
      CBIT component. Each attribute type is a non-negative integer 
      which monotonically increases until it reaches a maximum value, at 
      which point it wraps around and starts increasing again from zero."
::= { lpDS3CBit 11 }

lpDS3CBitStatsEntry OBJECT-TYPE
   SYNTAX     LpDS3CBitStatsEntry
   ACCESS     not-accessible
   STATUS     mandatory
   DESCRIPTION
     "An entry in the lpDS3CBitStatsTable."
   INDEX {
      lpIndex,
      lpDS3Index,
      lpDS3CBitIndex }
::= { lpDS3CBitStatsTable 1 }

LpDS3CBitStatsEntry ::= SEQUENCE {
   lpDS3CBitCbitErrorFreeSec
      Counter32,
   lpDS3CBitCbitCodeViolations
      Counter32,
   lpDS3CBitCbitErroredSec
      Counter32,
   lpDS3CBitCbitSevErroredSec
      Counter32,
   lpDS3CBitCbitUnavailSec
      Counter32,
   lpDS3CBitFarEndErrorFreeSec
      Counter32,
   lpDS3CBitFarEndCodeViolations
      Counter32,
   lpDS3CBitFarEndErroredSec
      Counter32,
   lpDS3CBitFarEndSevErroredSec
      Counter32,
   lpDS3CBitFarEndSefAisSec
      Counter32,
   lpDS3CBitFarEndUnavailSec
      Counter32,
   lpDS3CBitFarEndFailures
      Counter32 }

lpDS3CBitCbitErrorFreeSec OBJECT-TYPE
   SYNTAX     Counter32 
   ACCESS     read-only
   STATUS     mandatory
   DESCRIPTION
     "This attribute indicates the number of seconds that the DS3 port has 
      not suffered any C-Bit errors."
::= { lpDS3CBitStatsEntry 1 }

lpDS3CBitCbitCodeViolations OBJECT-TYPE
   SYNTAX     Counter32 
   ACCESS     read-only
   STATUS     mandatory
   DESCRIPTION
     "This attribute indicates the total count of C-Bit Parity Code 
      Violations (CCV). A CCV is obtained when the parity calculated 
      over the previous DS3 frame and the value of the CP-bits appearing 
      in the current DS3 frame differ. The value of this attribute will wrap 
      around to 0 if it does reach its maximum value. CCV counting is 
      inhibited for second intervals where C-Bit Parity Severely Errored 
      Seconds (CSES) are counted. It is also inhibited for second intervals 
      where C-Bit Unavailable Seconds (CUAS) are counted.
      This attribute is a non-negative integer which monotonically 
      increases until it reaches a maximum value, at which point it wraps 
      around and starts increasing again from zero."
::= { lpDS3CBitStatsEntry 2 }

lpDS3CBitCbitErroredSec OBJECT-TYPE
   SYNTAX     Counter32 
   ACCESS     read-only
   STATUS     mandatory
   DESCRIPTION
     "This attribute indicates the total number of C-Bit Parity Errored 
      Seconds (CES). A CES second is declared for second intervals 
      containing one or more CCVs or when one or more SEF (Severely 
      Errored Frame) or AIS (Alarm Indication Signal) defects.
      CES counting is inhibited for second intervals where C-Bit 
      Unavailable Seconds (CUAS) are counted."
::= { lpDS3CBitStatsEntry 3 }

lpDS3CBitCbitSevErroredSec OBJECT-TYPE
   SYNTAX     Counter32 
   ACCESS     read-only
   STATUS     mandatory
   DESCRIPTION
     "This attribute indicates the total number of C-Bit Parity Severely 
      Errored Seconds (CSES). A CSES is declared for second intervals 
      containing more than 44 CCVs or one or more SEF or AIS defects. 
      The occurrence of CSES in a one second interval causes the 
      inhibition of CCV counting during that second interval. CSES 
      counting is also inhibited for second intervals where C-Bit 
      Unavailable Seconds (CUAS) are counted."
::= { lpDS3CBitStatsEntry 4 }

lpDS3CBitCbitUnavailSec OBJECT-TYPE
   SYNTAX     Counter32 
   ACCESS     read-only
   STATUS     mandatory
   DESCRIPTION
     "This attribute indicates the total number of one second intervals for 
      which the DS3 path is unavailable. The DS3 path becomes 
      unavailable at the onset of 10 consecutive C-Bit Severely Errored 
      Seconds (CSES). The 10 CSESs are included in the unavailable 
      time. Once unavailable, the DS3 path becomes available at the onset 
      of 10 contiguous seconds with no CSES. The 10 seconds with no 
      CSES are excluded from the unavailable time. For second intervals 
      where CUAS is counted, counting of C-Bit Coding Violations 
      (CCV), C-Bit Errored Seconds (CES) and C-Bit Severely Errored 
      Seconds (CSES) is inhibited."
::= { lpDS3CBitStatsEntry 5 }

lpDS3CBitFarEndErrorFreeSec OBJECT-TYPE
   SYNTAX     Counter32 
   ACCESS     read-only
   STATUS     mandatory
   DESCRIPTION
     "This attribute indicates the number of seconds that the DS3 port has 
      not suffered of any far-end errors."
::= { lpDS3CBitStatsEntry 6 }

lpDS3CBitFarEndCodeViolations OBJECT-TYPE
   SYNTAX     Counter32 
   ACCESS     read-only
   STATUS     mandatory
   DESCRIPTION
     "This attribute indicates the total count of DS3 frames containing a 
      Coding Violation on the Far-End (FECV), also known as a Far-End 
      Block Error (FEBE). Each FEBE is reported over the FEBE bits 
      each time the far-end DS3 terminal detects a C-BIT Parity error 
      over a received DS3 frame. For second intervals where Far-End 
      Unavailable Seconds (FEAUS) or Far-End Severely Errored 
      Seconds (FESES) are counted, counting of FECVs is inhibited.
      This attribute is a non-negative integer which monotonically 
      increases until it reaches a maximum value, at which point it wraps 
      around and starts increasing again from zero."
::= { lpDS3CBitStatsEntry 7 }

lpDS3CBitFarEndErroredSec OBJECT-TYPE
   SYNTAX     Counter32 
   ACCESS     read-only
   STATUS     mandatory
   DESCRIPTION
     "This attribute indicates the total number of Far-End Errored 
      Seconds (FEES). A FEES is declared for second intervals 
      containing with one or more FECVs or one or more far-end SEF/
      AIS defects. A far-end SEF/AIS defect occurs when the X-Bits of 
      the DS3 frame are received as being set to zero. For second 
      intervals where Far-End Unavailable Seconds (FEUAS) are 
      counted, counting of FEESs is inhibited."
::= { lpDS3CBitStatsEntry 8 }

lpDS3CBitFarEndSevErroredSec OBJECT-TYPE
   SYNTAX     Counter32 
   ACCESS     read-only
   STATUS     mandatory
   DESCRIPTION
     "This attribute indicates the total number of Far-End Severely 
      Errored Seconds (FESES). A FESES is declared for second 
      intervals containing more than 44 FECVs or one or more far-end 
      SEF/AIS defects. For second intervals where a FESES is counted, 
      counting of FECVs is inhibited. For second intervals where Far-End 
      Unavailable Seconds (FEUAS) are counted, counting of FESESs is 
      inhibited."
::= { lpDS3CBitStatsEntry 9 }

lpDS3CBitFarEndSefAisSec OBJECT-TYPE
   SYNTAX     Counter32 
   ACCESS     read-only
   STATUS     mandatory
   DESCRIPTION
     "This attribute indicates the total number of Far-End SEF/AIS 
      Seconds (FESAS). A FESAS is declared for second intervals 
      containing one or more far-end SEF/AIS defects.For second 
      intervals where Far-End Unavailable Seconds (FEUAS) are 
      counted, counting of FESASs is inhibited."
::= { lpDS3CBitStatsEntry 10 }

lpDS3CBitFarEndUnavailSec OBJECT-TYPE
   SYNTAX     Counter32 
   ACCESS     read-only
   STATUS     mandatory
   DESCRIPTION
     "This attribute indicates the total number of one second intervals for 
      which the DS3 far-end path is unavailable. The DS3 far-end path 
      becomes unavailable at the onset of 10 consecutive Far-End 
      Severely Errored Seconds (FESES). The 10 FESESs are included in 
      the unavailable time. Once unavailable, the DS3 far-end path 
      becomes available at the onset of 10 contiguous seconds with no 
      FESES. The 10 seconds with no FESES are excluded from the 
      unavailable time. For second intervals where FEUAS is counted, 
      counting of Far-End Coding Violations (FECV), Far-End Errored 
      Seconds (FEES), Far-End Severely Errored Seconds (FESES) and 
      Far-End Sef/Ais Seconds (FESAS) is inhibited."
::= { lpDS3CBitStatsEntry 11 }

lpDS3CBitFarEndFailures OBJECT-TYPE
   SYNTAX     Counter32 
   ACCESS     read-only
   STATUS     mandatory
   DESCRIPTION
     "This attribute indicates the total number of times that a far-end path 
      failure (i.e. a Far-End SEF/AIS defect) has been declared.
      This attribute is a non-negative integer which monotonically 
      increases until it reaches a maximum value, at which point it wraps 
      around and starts increasing again from zero."
::= { lpDS3CBitStatsEntry 12 }


-- LP/n DS3/n PLCP
-- LP/n E3/n PLCP
-- The PLCP component is configured to display all DS3/E3 PLCP 
-- related operational and statistical data. It will appear under the DS3 
-- or E3 components when the mapping attribute is set to plcp.

lpDS3Plcp OBJECT IDENTIFIER ::= { lpDS3 4 }



lpDS3PlcpRowStatusTable OBJECT-TYPE
   SYNTAX     SEQUENCE OF LpDS3PlcpRowStatusEntry
   ACCESS     not-accessible
   STATUS     mandatory
   DESCRIPTION
     "This entry controls the addition and deletion of 
      lpDS3Plcp components."
::= { lpDS3Plcp 1 }

lpDS3PlcpRowStatusEntry OBJECT-TYPE
   SYNTAX     LpDS3PlcpRowStatusEntry
   ACCESS     not-accessible
   STATUS     mandatory
   DESCRIPTION
     "A single entry in the table represents a single 
      lpDS3Plcp component."
   INDEX {
      lpIndex,
      lpDS3Index,
      lpDS3PlcpIndex }
::= { lpDS3PlcpRowStatusTable 1 }

LpDS3PlcpRowStatusEntry ::= SEQUENCE {
   lpDS3PlcpRowStatus
      RowStatus,
   lpDS3PlcpComponentName
      DisplayString,
   lpDS3PlcpStorageType
      StorageType,
   lpDS3PlcpIndex
      NonReplicated }

lpDS3PlcpRowStatus OBJECT-TYPE
   SYNTAX     RowStatus 
   ACCESS     read-only
   STATUS     mandatory
   DESCRIPTION
     "This variable is used as the basis for SNMP naming of
      lpDS3Plcp components.
      These components cannot be added nor deleted."
::= { lpDS3PlcpRowStatusEntry 1 }

lpDS3PlcpComponentName OBJECT-TYPE
   SYNTAX     DisplayString 
   ACCESS     read-only
   STATUS     mandatory
   DESCRIPTION
     "This variable provides the component's string name for
      use with the ASCII Console Interface"
::= { lpDS3PlcpRowStatusEntry 2 }

lpDS3PlcpStorageType OBJECT-TYPE
   SYNTAX     StorageType 
   ACCESS     read-only
   STATUS     mandatory
   DESCRIPTION
     "This variable represents the storage type value for the
      lpDS3Plcp tables."
::= { lpDS3PlcpRowStatusEntry 4 }

lpDS3PlcpIndex OBJECT-TYPE
   SYNTAX     NonReplicated 
   ACCESS     not-accessible
   STATUS     mandatory
   DESCRIPTION
     "This variable represents the index for the lpDS3Plcp tables."
::= { lpDS3PlcpRowStatusEntry 10 }

lpDS3PlcpOperationalTable OBJECT-TYPE
   SYNTAX     SEQUENCE OF LpDS3PlcpOperationalEntry
   ACCESS     not-accessible
   STATUS     mandatory
   DESCRIPTION
     "This group contains the operational data for the PLCP component."
::= { lpDS3Plcp 10 }

lpDS3PlcpOperationalEntry OBJECT-TYPE
   SYNTAX     LpDS3PlcpOperationalEntry
   ACCESS     not-accessible
   STATUS     mandatory
   DESCRIPTION
     "An entry in the lpDS3PlcpOperationalTable."
   INDEX {
      lpIndex,
      lpDS3Index,
      lpDS3PlcpIndex }
::= { lpDS3PlcpOperationalTable 1 }

LpDS3PlcpOperationalEntry ::= SEQUENCE {
   lpDS3PlcpLofAlarm
      INTEGER,
   lpDS3PlcpRxRaiAlarm
      INTEGER }

lpDS3PlcpLofAlarm OBJECT-TYPE
   SYNTAX     INTEGER  {
                 on(0),
                 off(1) }
   ACCESS     read-only
   STATUS     mandatory
   DESCRIPTION
     "This attribute displays whether a PLCP Loss Of Frame (LOF) 
      failure alarm state has been entered. An LOF failure is declared 
      when a PLCP LOF defect persists for 2.5 s +/- 0.5 s. An LOF defect 
      occurs when an OOF (Out of Frame) state persists for more than 1 
      ms. If the OOF events are intermittent, the LOF defect counter is 
      decremented at a rate of 1/12 (for DS3 PLCP) or 1/9 (for G.751 E3 
      PLCP) of the incrementing rate, with all measurements based on a 
      200 ms polling cycle. An OOF event (also known as a PLCP SEF 
      event) is declared when an error is detected in both the A1 and A2 
      octets, or when two consecutive POHIDs are found in error.
      OOF is removed when two valid sets of framing octets and two 
      valid and sequential POHID octets have been found. The LOF 
      defect is removed when the defect counter reaches zero, i.e. when 
      OOF events are absent for more than 12 ms (DS3 PLCP) or 9 ms 
      (G.751 E3 PLCP). LOF failure alarm is cleared when LOF defect is 
      absent for 10.0 s +/- 0.5 s
      The DS3 or E3 component goes into an operational state of disabled 
      until the LOF failure alarm is cleared. The terminal declaring the 
      LOF failure alarm will transmit a PLCP RAI signal to the far-end 
      for the duration of the alarm.
      The lofAlarm attribute is always set to off when the DS3 or E3 
      component has been locked and left offline."
   DEFVAL     { off }
::= { lpDS3PlcpOperationalEntry 1 }

lpDS3PlcpRxRaiAlarm OBJECT-TYPE
   SYNTAX     INTEGER  {
                 on(0),
                 off(1) }
   ACCESS     read-only
   STATUS     mandatory
   DESCRIPTION
     "This attribute displays whether a PLCP Remote Alarm Indication 
      (RAI) failure alarm state has been entered. An RAI failure alarm 
      occurs when ten consecutive PLCP RAI bits (bit 5 in the G1 byte) 
      are high on the incoming line. An RAI failure alarm is cleared when 
      ten consecutive RAI bits are set to 0.
      Note: Some standards call this alarm RFI.
      The rxRaiAlarm attribute is always set to off when the DS3 or E3 
      component has been locked and left offline."
   DEFVAL     { off }
::= { lpDS3PlcpOperationalEntry 2 }

lpDS3PlcpStatsTable OBJECT-TYPE
   SYNTAX     SEQUENCE OF LpDS3PlcpStatsEntry
   ACCESS     not-accessible
   STATUS     mandatory
   DESCRIPTION
     "This group contains the statistical data for the PLCP component. 
      Each attribute type is a non-negative integer which monotonically 
      increases until it reaches a maximum value, at which point it wraps 
      around and starts increasing again from zero."
::= { lpDS3Plcp 11 }

lpDS3PlcpStatsEntry OBJECT-TYPE
   SYNTAX     LpDS3PlcpStatsEntry
   ACCESS     not-accessible
   STATUS     mandatory
   DESCRIPTION
     "An entry in the lpDS3PlcpStatsTable."
   INDEX {
      lpIndex,
      lpDS3Index,
      lpDS3PlcpIndex }
::= { lpDS3PlcpStatsTable 1 }

LpDS3PlcpStatsEntry ::= SEQUENCE {
   lpDS3PlcpErrorFreeSec
      Counter32,
   lpDS3PlcpCodingViolations
      Counter32,
   lpDS3PlcpErroredSec
      Counter32,
   lpDS3PlcpSevErroredSec
      Counter32,
   lpDS3PlcpSevErroredFramingSec
      Counter32,
   lpDS3PlcpUnavailSec
      Counter32,
   lpDS3PlcpFarEndErrorFreeSec
      Counter32,
   lpDS3PlcpFarEndCodingViolations
      Counter32,
   lpDS3PlcpFarEndErroredSec
      Counter32,
   lpDS3PlcpFarEndSevErroredSec
      Counter32,
   lpDS3PlcpFarEndUnavailableSec
      Counter32 }

lpDS3PlcpErrorFreeSec OBJECT-TYPE
   SYNTAX     Counter32 
   ACCESS     read-only
   STATUS     mandatory
   DESCRIPTION
     "This attribute indicates the number of seconds during which the 
      near-end PLCP path layer had no errors."
::= { lpDS3PlcpStatsEntry 1 }

lpDS3PlcpCodingViolations OBJECT-TYPE
   SYNTAX     Counter32 
   ACCESS     read-only
   STATUS     mandatory
   DESCRIPTION
     "This attribute indicates the total number of BIP-8 Errors, framing 
      pattern octet errors, and path overhead identification errors detected 
      in received PLCP frames. 
      Counting of PLCP CV is inhibited for second intervals where PLCP 
      Severely Errored Framing Seconds (SEFS) or PLCP Unavailable 
      Seconds (UAS) are counted.
      This attribute is a non-negative integer which monotonically 
      increases until it reaches a maximum value, at which point it wraps 
      around and starts increasing again from zero."
::= { lpDS3PlcpStatsEntry 2 }

lpDS3PlcpErroredSec OBJECT-TYPE
   SYNTAX     Counter32 
   ACCESS     read-only
   STATUS     mandatory
   DESCRIPTION
     "This attribute indicates the number of seconds containing one or 
      more PLCP Coding Violations (CV) or in which a PLCP Severely 
      Errored Framing Second (SEFS) was counted. 
      Counting of PLCP ES is inhibited during second intervals where 
      PLCP Unavailable Seconds (UAS) are counted."
::= { lpDS3PlcpStatsEntry 3 }

lpDS3PlcpSevErroredSec OBJECT-TYPE
   SYNTAX     Counter32 
   ACCESS     read-only
   STATUS     mandatory
   DESCRIPTION
     "This attribute indicates the number of seconds containing 5 or more 
      PLCPCVs or in which a PLCPSEFS was counted (i.e. a PLCP OOF 
      event occurred). 
      Counting of PLCP SES is inhibited during second intervals where 
      PLCP Unavailable Seconds (UAS) are counted."
::= { lpDS3PlcpStatsEntry 4 }

lpDS3PlcpSevErroredFramingSec OBJECT-TYPE
   SYNTAX     Counter32 
   ACCESS     read-only
   STATUS     mandatory
   DESCRIPTION
     "This attribute indicates the number of seconds containing one or 
      more PLCP Severely Errored Frame (SEF) events. An SEF event is 
      equivalent to a PLCP OOF (Out of Frame) event.
      Counting of PLCPP SEFSs is inhibited for second intervals where 
      PLCP Unavailable Seconds (UAS) are counted."
::= { lpDS3PlcpStatsEntry 5 }

lpDS3PlcpUnavailSec OBJECT-TYPE
   SYNTAX     Counter32 
   ACCESS     read-only
   STATUS     mandatory
   DESCRIPTION
     "This attribute indicates the number of seconds when the near-end 
      PLCP layer is unavailable. The PLCP Path Layer becomes 
      unavailable at the declaration of PLCP LOF (Loss of Frame) failure 
      alarm state. The PLCP Path Layer becomes available again only 
      after clearing this condition.
      For second intervals where PLCP UAS are counted, counting of 
      PLCP Severely Errored Framing Seconds (SEFS), PLCP Coding 
      Violations (CV), PLCP Errored Seconds (ES), PLCP Severely 
      Errored Seconds (SES) and PLCP Far-End Severely Errored 
      Seconds (FESES) is inhibited."
::= { lpDS3PlcpStatsEntry 6 }

lpDS3PlcpFarEndErrorFreeSec OBJECT-TYPE
   SYNTAX     Counter32 
   ACCESS     read-only
   STATUS     mandatory
   DESCRIPTION
     "This attribute indicates the number of seconds during which the far-
      end PLCP path layer had no errors."
::= { lpDS3PlcpStatsEntry 7 }

lpDS3PlcpFarEndCodingViolations OBJECT-TYPE
   SYNTAX     Counter32 
   ACCESS     read-only
   STATUS     mandatory
   DESCRIPTION
     "This attribute indicates the total number of PLCP Far-End Block 
      Errors (FEBE) reported by the far-end terminal. 
      Counting of FEBEs is inhibited for second intervals where PLCP 
      Far-End Unavailable Seconds (FEUAS) are counted.
      This attribute is a non-negative integer which monotonically 
      increases until it reaches a maximum value, at which point it wraps 
      around and starts increasing again from zero."
::= { lpDS3PlcpStatsEntry 8 }

lpDS3PlcpFarEndErroredSec OBJECT-TYPE
   SYNTAX     Counter32 
   ACCESS     read-only
   STATUS     mandatory
   DESCRIPTION
     "This attribute indicates the number of seconds containing one or 
      more PLCP Far-End Coding Violations (FECV).
      Counting of PLCP FEES is inhibited during second intervals where 
      PLCP Far-End Unavailable Seconds (FEUAS) are counted."
::= { lpDS3PlcpStatsEntry 9 }

lpDS3PlcpFarEndSevErroredSec OBJECT-TYPE
   SYNTAX     Counter32 
   ACCESS     read-only
   STATUS     mandatory
   DESCRIPTION
     "This attribute indicates the number of seconds containing 5 or more 
      PLCP Far-End Coding Violations (FECV). 
      Counting of PLCP FESES is inhibited for second intervals where 
      PLCP Far-End Unavailable Seconds (FEUAS) are counted."
::= { lpDS3PlcpStatsEntry 10 }

lpDS3PlcpFarEndUnavailableSec OBJECT-TYPE
   SYNTAX     Counter32 
   ACCESS     read-only
   STATUS     mandatory
   DESCRIPTION
     "This attribute indicates the number of seconds during which the 
      PLCP far end is unavailable. The PLCP Path Layer becomes 
      unavailable at the declaration of PLCP RAI (Remote Alarm 
      Indication). Service becomes available again after this condition is 
      cleared. For second intervals where PLCP FEUAS are counted, 
      counting of PLCP Far-End Coding Violations (FECV), PLCP Far-
      End Errored Seconds (FEES), and PLCP Far-End Severely Errored 
      Seconds (FESES) is inhibited."
::= { lpDS3PlcpStatsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

lpDS3Cell OBJECT IDENTIFIER ::= { lpDS3 5 }



lpDS3CellRowStatusTable OBJECT-TYPE
   SYNTAX     SEQUENCE OF LpDS3CellRowStatusEntry
   ACCESS     not-accessible
   STATUS     mandatory
   DESCRIPTION
     "This entry controls the addition and deletion of 
      lpDS3Cell components."
::= { lpDS3Cell 1 }

lpDS3CellRowStatusEntry OBJECT-TYPE
   SYNTAX     LpDS3CellRowStatusEntry
   ACCESS     not-accessible
   STATUS     mandatory
   DESCRIPTION
     "A single entry in the table represents a single 
      lpDS3Cell component."
   INDEX {
      lpIndex,
      lpDS3Index,
      lpDS3CellIndex }
::= { lpDS3CellRowStatusTable 1 }

LpDS3CellRowStatusEntry ::= SEQUENCE {
   lpDS3CellRowStatus
      RowStatus,
   lpDS3CellComponentName
      DisplayString,
   lpDS3CellStorageType
      StorageType,
   lpDS3CellIndex
      NonReplicated }

lpDS3CellRowStatus OBJECT-TYPE
   SYNTAX     RowStatus 
   ACCESS     read-write
   STATUS     mandatory
   DESCRIPTION
     "This variable is used as the basis for SNMP naming of
      lpDS3Cell components.
      These components can be added and deleted."
::= { lpDS3CellRowStatusEntry 1 }

lpDS3CellComponentName OBJECT-TYPE
   SYNTAX     DisplayString 
   ACCESS     read-only
   STATUS     mandatory
   DESCRIPTION
     "This variable provides the component's string name for
      use with the ASCII Console Interface"
::= { lpDS3CellRowStatusEntry 2 }

lpDS3CellStorageType OBJECT-TYPE
   SYNTAX     StorageType 
   ACCESS     read-only
   STATUS     mandatory
   DESCRIPTION
     "This variable represents the storage type value for the
      lpDS3Cell tables."
::= { lpDS3CellRowStatusEntry 4 }

lpDS3CellIndex OBJECT-TYPE
   SYNTAX     NonReplicated 
   ACCESS     not-accessible
   STATUS     mandatory
   DESCRIPTION
     "This variable represents the index for the lpDS3Cell tables."
::= { lpDS3CellRowStatusEntry 10 }

lpDS3CellProvTable OBJECT-TYPE
   SYNTAX     SEQUENCE OF LpDS3CellProvEntry
   ACCESS     not-accessible
   STATUS     mandatory
   DESCRIPTION
     "This group contains the provisioning attributes for the AtmCell 
      component."
::= { lpDS3Cell 10 }

lpDS3CellProvEntry OBJECT-TYPE
   SYNTAX     LpDS3CellProvEntry
   ACCESS     not-accessible
   STATUS     mandatory
   DESCRIPTION
     "An entry in the lpDS3CellProvTable."
   INDEX {
      lpIndex,
      lpDS3Index,
      lpDS3CellIndex }
::= { lpDS3CellProvTable 1 }

LpDS3CellProvEntry ::= SEQUENCE {
   lpDS3CellAlarmActDelay
      Unsigned32,
   lpDS3CellScrambleCellPayload
      INTEGER,
   lpDS3CellCorrectSingleBitHeaderErrors
      INTEGER }

lpDS3CellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { lpDS3CellProvEntry 1 }

lpDS3CellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { lpDS3CellProvEntry 2 }

lpDS3CellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { lpDS3CellProvEntry 3 }

lpDS3CellOperTable OBJECT-TYPE
   SYNTAX     SEQUENCE OF LpDS3CellOperEntry
   ACCESS     not-accessible
   STATUS     mandatory
   DESCRIPTION
     "This group contains the common operational attributes for the 
      AtmCell component."
::= { lpDS3Cell 11 }

lpDS3CellOperEntry OBJECT-TYPE
   SYNTAX     LpDS3CellOperEntry
   ACCESS     not-accessible
   STATUS     mandatory
   DESCRIPTION
     "An entry in the lpDS3CellOperTable."
   INDEX {
      lpIndex,
      lpDS3Index,
      lpDS3CellIndex }
::= { lpDS3CellOperTable 1 }

LpDS3CellOperEntry ::= SEQUENCE {
   lpDS3CellLcdAlarm
      INTEGER }

lpDS3CellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { lpDS3CellOperEntry 1 }

lpDS3CellStatsTable OBJECT-TYPE
   SYNTAX     SEQUENCE OF LpDS3CellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { lpDS3Cell 12 }

lpDS3CellStatsEntry OBJECT-TYPE
   SYNTAX     LpDS3CellStatsEntry
   ACCESS     not-accessible
   STATUS     mandatory
   DESCRIPTION
     "An entry in the lpDS3CellStatsTable."
   INDEX {
      lpIndex,
      lpDS3Index,
      lpDS3CellIndex }
::= { lpDS3CellStatsTable 1 }

LpDS3CellStatsEntry ::= SEQUENCE {
   lpDS3CellUncorrectableHecErrors
      Counter32,
   lpDS3CellSevErroredSec
      Counter32,
   lpDS3CellReceiveCellUtilization
      Gauge32,
   lpDS3CellTransmitCellUtilization
      Gauge32,
   lpDS3CellCorrectableHeaderErrors
      Counter32 }

lpDS3CellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { lpDS3CellStatsEntry 1 }

lpDS3CellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { lpDS3CellStatsEntry 2 }

lpDS3CellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { lpDS3CellStatsEntry 3 }

lpDS3CellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { lpDS3CellStatsEntry 4 }

lpDS3CellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { lpDS3CellStatsEntry 5 }


-- Lp/n DS3/n DS1/n
-- The DS1 component controls and monitors a DS1 tributary of a 
-- channelized DS3 port on a 1pDS3C or 2pDS3cAal Function 
-- Processor.

lpDS3DS1 OBJECT IDENTIFIER ::= { lpDS3 6 }



lpDS3DS1RowStatusTable OBJECT-TYPE
   SYNTAX     SEQUENCE OF LpDS3DS1RowStatusEntry
   ACCESS     not-accessible
   STATUS     mandatory
   DESCRIPTION
     "This entry controls the addition and deletion of 
      lpDS3DS1 components."
::= { lpDS3DS1 1 }

lpDS3DS1RowStatusEntry OBJECT-TYPE
   SYNTAX     LpDS3DS1RowStatusEntry
   ACCESS     not-accessible
   STATUS     mandatory
   DESCRIPTION
     "A single entry in the table represents a single 
      lpDS3DS1 component."
   INDEX {
      lpIndex,
      lpDS3Index,
      lpDS3DS1Index }
::= { lpDS3DS1RowStatusTable 1 }

LpDS3DS1RowStatusEntry ::= SEQUENCE {
   lpDS3DS1RowStatus
      RowStatus,
   lpDS3DS1ComponentName
      DisplayString,
   lpDS3DS1StorageType
      StorageType,
   lpDS3DS1Index
      Integer32 }

lpDS3DS1RowStatus OBJECT-TYPE
   SYNTAX     RowStatus 
   ACCESS     read-write
   STATUS     mandatory
   DESCRIPTION
     "This variable is used as the basis for SNMP naming of
      lpDS3DS1 components.
      These components can be added and deleted."
::= { lpDS3DS1RowStatusEntry 1 }

lpDS3DS1ComponentName OBJECT-TYPE
   SYNTAX     DisplayString 
   ACCESS     read-only
   STATUS     mandatory
   DESCRIPTION
     "This variable provides the component's string name for
      use with the ASCII Console Interface"
::= { lpDS3DS1RowStatusEntry 2 }

lpDS3DS1StorageType OBJECT-TYPE
   SYNTAX     StorageType 
   ACCESS     read-only
   STATUS     mandatory
   DESCRIPTION
     "This variable represents the storage type value for the
      lpDS3DS1 tables."
::= { lpDS3DS1RowStatusEntry 4 }

lpDS3DS1Index OBJECT-TYPE
   SYNTAX     Integer32 (1..28)
   ACCESS     not-accessible
   STATUS     mandatory
   DESCRIPTION
     "This variable represents the index for the lpDS3DS1 tables."
::= { lpDS3DS1RowStatusEntry 10 }

lpDS3DS1ProvTable OBJECT-TYPE
   SYNTAX     SEQUENCE OF LpDS3DS1ProvEntry
   ACCESS     not-accessible
   STATUS     mandatory
   DESCRIPTION
     "This group contains all of the provisioning data for a DS1 
      component."
::= { lpDS3DS1 10 }

lpDS3DS1ProvEntry OBJECT-TYPE
   SYNTAX     LpDS3DS1ProvEntry
   ACCESS     not-accessible
   STATUS     mandatory
   DESCRIPTION
     "An entry in the lpDS3DS1ProvTable."
   INDEX {
      lpIndex,
      lpDS3Index,
      lpDS3DS1Index }
::= { lpDS3DS1ProvTable 1 }

LpDS3DS1ProvEntry ::= SEQUENCE {
   lpDS3DS1LineType
      INTEGER,
   lpDS3DS1ZeroCoding
      INTEGER,
   lpDS3DS1ClockingSource
      INTEGER }

lpDS3DS1LineType OBJECT-TYPE
   SYNTAX     INTEGER  {
                 d4(0),
                 esf(1),
                 d4Cas(4),
                 esfCas(5) }
   ACCESS     read-write
   STATUS     mandatory
   DESCRIPTION
     "This attribute defines the framing of the DS1 tributary.
      d4 defines a framing pattern of 12 frames per multiframe.
      esf defines a framing pattern of 24 frames per multiframe.
      d4Cas defines a framing pattern of 12 frames per multiframe with 
      channel associated signalling.
      esfCas defines a framing pattern of 24 frames per multiframe with 
      channel associated signalling."
   DEFVAL     { esf }
::= { lpDS3DS1ProvEntry 1 }

lpDS3DS1ZeroCoding OBJECT-TYPE
   SYNTAX     INTEGER  {
                 bit7Stuffing(0),
                 none(3) }
   ACCESS     read-write
   STATUS     mandatory
   DESCRIPTION
     "This attribute defines the zero encoding on the DS1 tributary.
      bit7Stuffing sets bit 7 of every timeslot to a one to guarantee ones's 
      density. This reduces the available bandwidth of the channel by 1/8.
      none does no zero encoding."
   DEFVAL     { none }
::= { lpDS3DS1ProvEntry 2 }

lpDS3DS1ClockingSource OBJECT-TYPE
   SYNTAX     INTEGER  {
                 local(0),
                 line(1),
                 module(2) }
   ACCESS     read-write
   STATUS     mandatory
   DESCRIPTION
     "This attribute defines the source of the transmit clock for the DS1 
      tributary.
      When the clocking source is selected from local, the crystal on the 
      port generates the clocking for the DS1 tributary.
      When the clocking source is selected from line, the port 
      synchronizes to the clock from the DS1 tributary.
      When the clocking source is selected from module, the ports clock 
      synchronizes to the clock provided by the oscillator on the active 
      CP.
      On a 1pDS3C card, if the NetworkSynchronization (NS) component 
      is present the default value of this attribute will be module otherwise 
      it will be line.
      On a 2pDS3cAal card, the only valid values are local and module. If 
      the NS component is present the default value of this attribute will 
      be module otherwise it will be local."
::= { lpDS3DS1ProvEntry 3 }

lpDS3DS1CidDataTable OBJECT-TYPE
   SYNTAX     SEQUENCE OF LpDS3DS1CidDataEntry
   ACCESS     not-accessible
   STATUS     mandatory
   DESCRIPTION
     "This group contains the attribute for a component's Customer 
      Identifier (CID). Refer to the attribute description for a detailed 
      explanation of CIDs."
::= { lpDS3DS1 11 }

lpDS3DS1CidDataEntry OBJECT-TYPE
   SYNTAX     LpDS3DS1CidDataEntry
   ACCESS     not-accessible
   STATUS     mandatory
   DESCRIPTION
     "An entry in the lpDS3DS1CidDataTable."
   INDEX {
      lpIndex,
      lpDS3Index,
      lpDS3DS1Index }
::= { lpDS3DS1CidDataTable 1 }

LpDS3DS1CidDataEntry ::= SEQUENCE {
   lpDS3DS1CustomerIdentifier
      Unsigned32 }

lpDS3DS1CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpDS3DS1CidDataEntry 1 }

lpDS3DS1AdminInfoTable OBJECT-TYPE
   SYNTAX     SEQUENCE OF LpDS3DS1AdminInfoEntry
   ACCESS     not-accessible
   STATUS     mandatory
   DESCRIPTION
     "This group contains the attributes pertaining to the vendor of the 
      equipment."
::= { lpDS3DS1 12 }

lpDS3DS1AdminInfoEntry OBJECT-TYPE
   SYNTAX     LpDS3DS1AdminInfoEntry
   ACCESS     not-accessible
   STATUS     mandatory
   DESCRIPTION
     "An entry in the lpDS3DS1AdminInfoTable."
   INDEX {
      lpIndex,
      lpDS3Index,
      lpDS3DS1Index }
::= { lpDS3DS1AdminInfoTable 1 }

LpDS3DS1AdminInfoEntry ::= SEQUENCE {
   lpDS3DS1Vendor
      AsciiString,
   lpDS3DS1CommentText
      AsciiString }

lpDS3DS1Vendor OBJECT-TYPE
   SYNTAX     AsciiString (SIZE (0..20))
   ACCESS     read-write
   STATUS     mandatory
   DESCRIPTION
     "This is the name of the vendor supplying the facility."
::= { lpDS3DS1AdminInfoEntry 1 }

lpDS3DS1CommentText OBJECT-TYPE
   SYNTAX     AsciiString (SIZE (0..60))
   ACCESS     read-write
   STATUS     mandatory
   DESCRIPTION
     "Any miscellaneous text about the facility."
::= { lpDS3DS1AdminInfoEntry 2 }

lpDS3DS1IfEntryTable OBJECT-TYPE
   SYNTAX     SEQUENCE OF LpDS3DS1IfEntryEntry
   ACCESS     not-accessible
   STATUS     mandatory
   DESCRIPTION
     "This group contains the provisionable attributes for the ifEntry."
::= { lpDS3DS1 13 }

lpDS3DS1IfEntryEntry OBJECT-TYPE
   SYNTAX     LpDS3DS1IfEntryEntry
   ACCESS     not-accessible
   STATUS     mandatory
   DESCRIPTION
     "An entry in the lpDS3DS1IfEntryTable."
   INDEX {
      lpIndex,
      lpDS3Index,
      lpDS3DS1Index }
::= { lpDS3DS1IfEntryTable 1 }

LpDS3DS1IfEntryEntry ::= SEQUENCE {
   lpDS3DS1IfAdminStatus
      INTEGER,
   lpDS3DS1IfIndex
      InterfaceIndex }

lpDS3DS1IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpDS3DS1IfEntryEntry 1 }

lpDS3DS1IfIndex OBJECT-TYPE
   SYNTAX     InterfaceIndex (1..65535)
   ACCESS     read-only
   STATUS     mandatory
   DESCRIPTION
     "This is the index for the IfEntry. Its value is automatically initialized 
      during the provisioning process."
::= { lpDS3DS1IfEntryEntry 2 }

lpDS3DS1OperStatusTable OBJECT-TYPE
   SYNTAX     SEQUENCE OF LpDS3DS1OperStatusEntry
   ACCESS     not-accessible
   STATUS     mandatory
   DESCRIPTION
     "This group includes the Operational Status attribute. This attribute 
      defines the current operational state of this component."
::= { lpDS3DS1 14 }

lpDS3DS1OperStatusEntry OBJECT-TYPE
   SYNTAX     LpDS3DS1OperStatusEntry
   ACCESS     not-accessible
   STATUS     mandatory
   DESCRIPTION
     "An entry in the lpDS3DS1OperStatusTable."
   INDEX {
      lpIndex,
      lpDS3Index,
      lpDS3DS1Index }
::= { lpDS3DS1OperStatusTable 1 }

LpDS3DS1OperStatusEntry ::= SEQUENCE {
   lpDS3DS1SnmpOperStatus
      INTEGER }

lpDS3DS1SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpDS3DS1OperStatusEntry 1 }

lpDS3DS1StateTable OBJECT-TYPE
   SYNTAX     SEQUENCE OF LpDS3DS1StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpDS3DS1 15 }

lpDS3DS1StateEntry OBJECT-TYPE
   SYNTAX     LpDS3DS1StateEntry
   ACCESS     not-accessible
   STATUS     mandatory
   DESCRIPTION
     "An entry in the lpDS3DS1StateTable."
   INDEX {
      lpIndex,
      lpDS3Index,
      lpDS3DS1Index }
::= { lpDS3DS1StateTable 1 }

LpDS3DS1StateEntry ::= SEQUENCE {
   lpDS3DS1AdminState
      INTEGER,
   lpDS3DS1OperationalState
      INTEGER,
   lpDS3DS1UsageState
      INTEGER,
   lpDS3DS1AvailabilityStatus
      OCTET STRING,
   lpDS3DS1ProceduralStatus
      OCTET STRING,
   lpDS3DS1ControlStatus
      OCTET STRING,
   lpDS3DS1AlarmStatus
      OCTET STRING,
   lpDS3DS1StandbyStatus
      INTEGER,
   lpDS3DS1UnknownStatus
      INTEGER }

lpDS3DS1AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpDS3DS1StateEntry 1 }

lpDS3DS1OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpDS3DS1StateEntry 2 }

lpDS3DS1UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpDS3DS1StateEntry 3 }

lpDS3DS1AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpDS3DS1StateEntry 4 }

lpDS3DS1ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpDS3DS1StateEntry 5 }

lpDS3DS1ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpDS3DS1StateEntry 6 }

lpDS3DS1AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpDS3DS1StateEntry 7 }

lpDS3DS1StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpDS3DS1StateEntry 8 }

lpDS3DS1UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpDS3DS1StateEntry 9 }

lpDS3DS1OperTable OBJECT-TYPE
   SYNTAX     SEQUENCE OF LpDS3DS1OperEntry
   ACCESS     not-accessible
   STATUS     mandatory
   DESCRIPTION
     "This group contains the common operational data for a component 
      in a digital hierarchy interface."
::= { lpDS3DS1 16 }

lpDS3DS1OperEntry OBJECT-TYPE
   SYNTAX     LpDS3DS1OperEntry
   ACCESS     not-accessible
   STATUS     mandatory
   DESCRIPTION
     "An entry in the lpDS3DS1OperTable."
   INDEX {
      lpIndex,
      lpDS3Index,
      lpDS3DS1Index }
::= { lpDS3DS1OperTable 1 }

LpDS3DS1OperEntry ::= SEQUENCE {
   lpDS3DS1RxAisAlarm
      INTEGER,
   lpDS3DS1LofAlarm
      INTEGER,
   lpDS3DS1RxRaiAlarm
      INTEGER,
   lpDS3DS1TxAisAlarm
      INTEGER,
   lpDS3DS1TxRaiAlarm
      INTEGER }

lpDS3DS1RxAisAlarm OBJECT-TYPE
   SYNTAX     INTEGER  {
                 on(0),
                 off(1) }
   ACCESS     read-only
   STATUS     mandatory
   DESCRIPTION
     "This attribute indicates whether an AIS (Alarm Indication Signal) 
      alarm state has been entered. The AIS Alarm state is entered when 
      AIS defects have been observed and accumulated for 2.5 seconds 
      +/- 0.5 seconds. An AIS defect is detected after having received less 
      than 3 zeros in a 2048 bit period. If the AIS defects are 
      intermittently occurring, the AIS defect accumulator is decremented 
      at a rate of 1/10 of the incrementing rate (alarm integration ratio of 
      1/10), with all measurements based on a 200 ms polling cycle. This 
      tributary goes into an operationalState of disabled for the duration 
      of an AIS alarm state.
      The AIS alarm state is cleared when AIS defects are absent for 10 
      seconds +/- 0.5 seconds."
   DEFVAL     { off }
::= { lpDS3DS1OperEntry 1 }

lpDS3DS1LofAlarm OBJECT-TYPE
   SYNTAX     INTEGER  {
                 on(0),
                 off(1) }
   ACCESS     read-only
   STATUS     mandatory
   DESCRIPTION
     "This attribute indicates whether a LOF (Loss of Frame) alarm state 
      has been entered. The LOF alarm state is entered when LOF defects 
      (2 out of 5 framing bits in error ) have been detected for 3 seconds 
      +/- 0.5 seconds. If the LOF defects are intermittently occurring, the 
      LOF defect accumulator is decremented at a rate of 1/10 of the 
      incrementing rate (alarm integration ratio of 1/10), with all 
      measurements based on a 200 ms polling cycle. This tributary goes 
      into an operationalState of disabled until the LOF alarm state is 
      cleared. Also, an RAI alarm is transmitted to the far end for the 
      duration of the LOF alarm state 
      The condition is cleared when framing has been achieved for 10 
      seconds +/- 0.5 seconds."
   DEFVAL     { off }
::= { lpDS3DS1OperEntry 2 }

lpDS3DS1RxRaiAlarm OBJECT-TYPE
   SYNTAX     INTEGER  {
                 on(0),
                 off(1) }
   ACCESS     read-only
   STATUS     mandatory
   DESCRIPTION
     "This attribute indicates whether an RAI (Remote Alarm Indication) 
      alarm state has been entered. An RAI alarm state is entered when 
      the RAI defect indicator has been observed and accumulated for 3.5 
      seconds +/- 0.5 seconds. If the RAI defects are intermittently 
      occurring, the RAI defect accumulator is decremented at a rate of 1/
      10 of the incrementing rate (alarm integration ratio of 1/10), with all 
      measurements based on a 200 ms polling cycle. 
      The RAI alarm state is cleared when the RAI defect indicator has 
      been absent for 10 seconds +/- 0.5 seconds. The RAI alarm is 
      usually an indication that the far end facility is unable to gain 
      synchronization."
   DEFVAL     { off }
::= { lpDS3DS1OperEntry 3 }

lpDS3DS1TxAisAlarm OBJECT-TYPE
   SYNTAX     INTEGER  {
                 on(0),
                 off(1) }
   ACCESS     read-only
   STATUS     mandatory
   DESCRIPTION
     "This attribute indicates whether an AIS (Alarm Indication Signal) 
      alarm is being transmitted on the line. An AIS alarm is transmitted 
      when the tributary is in a locked state."
   DEFVAL     { off }
::= { lpDS3DS1OperEntry 4 }

lpDS3DS1TxRaiAlarm OBJECT-TYPE
   SYNTAX     INTEGER  {
                 on(0),
                 off(1) }
   ACCESS     read-only
   STATUS     mandatory
   DESCRIPTION
     "This attribute indicates whether a RAI signal is being sent on the 
      outgoing line. The RAI signal is transmitted when the tributary 
      detects a LOF alarm condition."
   DEFVAL     { off }
::= { lpDS3DS1OperEntry 5 }

lpDS3DS1StatsTable OBJECT-TYPE
   SYNTAX     SEQUENCE OF LpDS3DS1StatsEntry
   ACCESS     not-accessible
   STATUS     mandatory
   DESCRIPTION
     "This group contains the common statistical data for a component in 
      a digital hierarchy interface."
::= { lpDS3DS1 17 }

lpDS3DS1StatsEntry OBJECT-TYPE
   SYNTAX     LpDS3DS1StatsEntry
   ACCESS     not-accessible
   STATUS     mandatory
   DESCRIPTION
     "An entry in the lpDS3DS1StatsTable."
   INDEX {
      lpIndex,
      lpDS3Index,
      lpDS3DS1Index }
::= { lpDS3DS1StatsTable 1 }

LpDS3DS1StatsEntry ::= SEQUENCE {
   lpDS3DS1RunningTime
      Counter32,
   lpDS3DS1ErrorFreeSec
      Counter32,
   lpDS3DS1ErroredSec
      Counter32,
   lpDS3DS1SevErroredSec
      Counter32,
   lpDS3DS1SevErroredFrmSec
      Counter32,
   lpDS3DS1UnavailSec
      Counter32,
   lpDS3DS1CrcErrors
      Counter32,
   lpDS3DS1FrmErrors
      Counter32,
   lpDS3DS1SlipErrors
      Counter32 }

lpDS3DS1RunningTime OBJECT-TYPE
   SYNTAX     Counter32 
   ACCESS     read-only
   STATUS     mandatory
   DESCRIPTION
     "This attribute counts the number of seconds since the tributary was 
      activated."
::= { lpDS3DS1StatsEntry 1 }

lpDS3DS1ErrorFreeSec OBJECT-TYPE
   SYNTAX     Counter32 
   ACCESS     read-only
   STATUS     mandatory
   DESCRIPTION
     "This attribute counts the number of seconds that the tributary has 
      been in an error free state."
::= { lpDS3DS1StatsEntry 2 }

lpDS3DS1ErroredSec OBJECT-TYPE
   SYNTAX     Counter32 
   ACCESS     read-only
   STATUS     mandatory
   DESCRIPTION
     "This attribute counts the number of errored seconds the tributary has 
      counted since it was activated. An errored second is declared when 
      a second with one or more Code Violation Error events, or one or 
      more Out Of Frame events occurs. A code violation error may be a 
      CRC error or a BPV error. An Out Of Frame event occurs when 2 
      out of 5 framing bits are in error."
::= { lpDS3DS1StatsEntry 3 }

lpDS3DS1SevErroredSec OBJECT-TYPE
   SYNTAX     Counter32 
   ACCESS     read-only
   STATUS     mandatory
   DESCRIPTION
     "This attribute counts the number of severely errored seconds the 
      tributary has counted since it was activated. A severely errored 
      second occurs when a second with 320 or more Code Violation 
      Error events or one or more Out Of Frame events occurs."
::= { lpDS3DS1StatsEntry 4 }

lpDS3DS1SevErroredFrmSec OBJECT-TYPE
   SYNTAX     Counter32 
   ACCESS     read-only
   STATUS     mandatory
   DESCRIPTION
     "This attribute counts the number of severely errored framing 
      seconds the tributary has counted since it was activated A severely 
      errored framing second occurs when a second with one or more Out 
      Of Frame events occurs."
::= { lpDS3DS1StatsEntry 5 }

lpDS3DS1UnavailSec OBJECT-TYPE
   SYNTAX     Counter32 
   ACCESS     read-only
   STATUS     mandatory
   DESCRIPTION
     "This attribute counts the total number of seconds that the tributary 
      has been in an unavailable signal state. An unavailable signal state 
      occurs at the onset of 10 consecutive Severely Errored Seconds. The 
      state is cleared at the onset of 10 seconds with no Severely Errored 
      Seconds."
::= { lpDS3DS1StatsEntry 6 }

lpDS3DS1CrcErrors OBJECT-TYPE
   SYNTAX     Counter32 
   ACCESS     read-only
   STATUS     mandatory
   DESCRIPTION
     "This attribute counts the total number of CRC-6 errors. These will 
      only be counted when the lineType is esf."
::= { lpDS3DS1StatsEntry 7 }

lpDS3DS1FrmErrors OBJECT-TYPE
   SYNTAX     Counter32 
   ACCESS     read-only
   STATUS     mandatory
   DESCRIPTION
     "This attribute counts the total number of frame errors. A frame error 
      is an error in the framing bits."
::= { lpDS3DS1StatsEntry 8 }

lpDS3DS1SlipErrors OBJECT-TYPE
   SYNTAX     Counter32 
   ACCESS     read-only
   STATUS     mandatory
   DESCRIPTION
     "The total number of times that the line experienced a controlled 
      frame slip."
::= { lpDS3DS1StatsEntry 9 }


-- Channel
-- The Channel component is configured to control a group of 
-- timeslots that form a fractional group on a DS1 or E1 port. 
-- Cell-based cards allow only one channel per port, and this is 
-- automatically provisioned with all available timeslots. Similarly, the 
-- 1pDS3C card type only allows one channel per port, and this is 
-- automatically provisioned with all available timeslots.
-- Warning: On cell-based cards, creation of the AtmCell component 
-- under the Chan and automatic timeslot provisioning is not 
-- guaranteed behavior, since it is possible to add a Chan component 
-- before provisioning the cardType. In general, do not add a Chan 
-- component before provisioning the cardType.

lpDS3DS1Chan OBJECT IDENTIFIER ::= { lpDS3DS1 2 }



lpDS3DS1ChanRowStatusTable OBJECT-TYPE
   SYNTAX     SEQUENCE OF LpDS3DS1ChanRowStatusEntry
   ACCESS     not-accessible
   STATUS     mandatory
   DESCRIPTION
     "This entry controls the addition and deletion of 
      lpDS3DS1Chan components."
::= { lpDS3DS1Chan 1 }

lpDS3DS1ChanRowStatusEntry OBJECT-TYPE
   SYNTAX     LpDS3DS1ChanRowStatusEntry
   ACCESS     not-accessible
   STATUS     mandatory
   DESCRIPTION
     "A single entry in the table represents a single 
      lpDS3DS1Chan component."
   INDEX {
      lpIndex,
      lpDS3Index,
      lpDS3DS1Index,
      lpDS3DS1ChanIndex }
::= { lpDS3DS1ChanRowStatusTable 1 }

LpDS3DS1ChanRowStatusEntry ::= SEQUENCE {
   lpDS3DS1ChanRowStatus
      RowStatus,
   lpDS3DS1ChanComponentName
      DisplayString,
   lpDS3DS1ChanStorageType
      StorageType,
   lpDS3DS1ChanIndex
      Integer32 }

lpDS3DS1ChanRowStatus OBJECT-TYPE
   SYNTAX     RowStatus 
   ACCESS     read-write
   STATUS     mandatory
   DESCRIPTION
     "This variable is used as the basis for SNMP naming of
      lpDS3DS1Chan components.
      These components can be added and deleted."
::= { lpDS3DS1ChanRowStatusEntry 1 }

lpDS3DS1ChanComponentName OBJECT-TYPE
   SYNTAX     DisplayString 
   ACCESS     read-only
   STATUS     mandatory
   DESCRIPTION
     "This variable provides the component's string name for
      use with the ASCII Console Interface"
::= { lpDS3DS1ChanRowStatusEntry 2 }

lpDS3DS1ChanStorageType OBJECT-TYPE
   SYNTAX     StorageType 
   ACCESS     read-only
   STATUS     mandatory
   DESCRIPTION
     "This variable represents the storage type value for the
      lpDS3DS1Chan tables."
::= { lpDS3DS1ChanRowStatusEntry 4 }

lpDS3DS1ChanIndex OBJECT-TYPE
   SYNTAX     Integer32 (0)
   ACCESS     not-accessible
   STATUS     mandatory
   DESCRIPTION
     "This variable represents the index for the lpDS3DS1Chan tables."
::= { lpDS3DS1ChanRowStatusEntry 10 }

lpDS3DS1ChanProvTable OBJECT-TYPE
   SYNTAX     SEQUENCE OF LpDS3DS1ChanProvEntry
   ACCESS     not-accessible
   STATUS     mandatory
   DESCRIPTION
     "This group contains all of the provisional data for a Channel 
      component."
::= { lpDS3DS1Chan 10 }

lpDS3DS1ChanProvEntry OBJECT-TYPE
   SYNTAX     LpDS3DS1ChanProvEntry
   ACCESS     not-accessible
   STATUS     mandatory
   DESCRIPTION
     "An entry in the lpDS3DS1ChanProvTable."
   INDEX {
      lpIndex,
      lpDS3Index,
      lpDS3DS1Index,
      lpDS3DS1ChanIndex }
::= { lpDS3DS1ChanProvTable 1 }

LpDS3DS1ChanProvEntry ::= SEQUENCE {
   lpDS3DS1ChanTimeslots
      OCTET STRING,
   lpDS3DS1ChanTimeslotDataRate
      INTEGER,
   lpDS3DS1ChanApplicationFramerName
      Link }

lpDS3DS1ChanTimeslots OBJECT-TYPE
   SYNTAX     OCTET STRING (SIZE (4))
   ACCESS     read-write
   STATUS     mandatory
   DESCRIPTION
     "This attribute contains the list of timeslots that are used by the 
      Channel component. Valid numbers are 1-24 for a Channel used by 
      a DS1 component, and 1-31 for a Channel used by an E1 
      component.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { lpDS3DS1ChanProvEntry 1 }

lpDS3DS1ChanTimeslotDataRate OBJECT-TYPE
   SYNTAX     INTEGER  {
                 n56k(0),
                 doNotOverride(1) }
   ACCESS     read-write
   STATUS     mandatory
   DESCRIPTION
     "This attribute selects the data rate of the timeslots in a channel of a 
      DS1 component. For E1, the data rate of the timeslots will always 
      be 64kbit/s regardless of this attribute.
      When doNotOverride is selected for a channel on a DS1, the data 
      rate of the channel's timeslots are dependent on the zeroCoding 
      selection of the DS1 component. If the zeroCoding is B8ZS (where 
      supported on the FP) or none, the timeslot's data rate will be 
      64kbit/s. If the zeroCoding option is bit7Stuffing, the data rate of a 
      timeslot will be 56kbit/s.
      When 56kbit/s is selected for a channel on a DS1, the least 
      significant bit of each timeslot of this Channel will always be set to 
      1 and not used for data. The data rate for the timeslots of this 
      channel is therefore restricted to 56kbit/s.
      One application of this attribute is to allow a DS1 line to support 
      mixing channels that originate from lines that use different 
      zeroCoding schemes."
   DEFVAL     { doNotOverride }
::= { lpDS3DS1ChanProvEntry 2 }

lpDS3DS1ChanApplicationFramerName OBJECT-TYPE
   SYNTAX     Link 
   ACCESS     read-write
   STATUS     mandatory
   DESCRIPTION
     "This attribute defines the link to the software stack. It defines which 
      application is running on top of this hardware component."
::= { lpDS3DS1ChanProvEntry 3 }

lpDS3DS1ChanCidDataTable OBJECT-TYPE
   SYNTAX     SEQUENCE OF LpDS3DS1ChanCidDataEntry
   ACCESS     not-accessible
   STATUS     mandatory
   DESCRIPTION
     "This group contains the attribute for a component's Customer 
      Identifier (CID). Refer to the attribute description for a detailed 
      explanation of CIDs."
::= { lpDS3DS1Chan 11 }

lpDS3DS1ChanCidDataEntry OBJECT-TYPE
   SYNTAX     LpDS3DS1ChanCidDataEntry
   ACCESS     not-accessible
   STATUS     mandatory
   DESCRIPTION
     "An entry in the lpDS3DS1ChanCidDataTable."
   INDEX {
      lpIndex,
      lpDS3Index,
      lpDS3DS1Index,
      lpDS3DS1ChanIndex }
::= { lpDS3DS1ChanCidDataTable 1 }

LpDS3DS1ChanCidDataEntry ::= SEQUENCE {
   lpDS3DS1ChanCustomerIdentifier
      Unsigned32 }

lpDS3DS1ChanCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpDS3DS1ChanCidDataEntry 1 }

lpDS3DS1ChanIfEntryTable OBJECT-TYPE
   SYNTAX     SEQUENCE OF LpDS3DS1ChanIfEntryEntry
   ACCESS     not-accessible
   STATUS     mandatory
   DESCRIPTION
     "This group contains the provisionable attributes for the ifEntry."
::= { lpDS3DS1Chan 12 }

lpDS3DS1ChanIfEntryEntry OBJECT-TYPE
   SYNTAX     LpDS3DS1ChanIfEntryEntry
   ACCESS     not-accessible
   STATUS     mandatory
   DESCRIPTION
     "An entry in the lpDS3DS1ChanIfEntryTable."
   INDEX {
      lpIndex,
      lpDS3Index,
      lpDS3DS1Index,
      lpDS3DS1ChanIndex }
::= { lpDS3DS1ChanIfEntryTable 1 }

LpDS3DS1ChanIfEntryEntry ::= SEQUENCE {
   lpDS3DS1ChanIfAdminStatus
      INTEGER,
   lpDS3DS1ChanIfIndex
      InterfaceIndex }

lpDS3DS1ChanIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpDS3DS1ChanIfEntryEntry 1 }

lpDS3DS1ChanIfIndex OBJECT-TYPE
   SYNTAX     InterfaceIndex (1..65535)
   ACCESS     read-only
   STATUS     mandatory
   DESCRIPTION
     "This is the index for the IfEntry. Its value is automatically initialized 
      during the provisioning process."
::= { lpDS3DS1ChanIfEntryEntry 2 }

lpDS3DS1ChanOperStatusTable OBJECT-TYPE
   SYNTAX     SEQUENCE OF LpDS3DS1ChanOperStatusEntry
   ACCESS     not-accessible
   STATUS     mandatory
   DESCRIPTION
     "This group includes the Operational Status attribute. This attribute 
      defines the current operational state of this component."
::= { lpDS3DS1Chan 13 }

lpDS3DS1ChanOperStatusEntry OBJECT-TYPE
   SYNTAX     LpDS3DS1ChanOperStatusEntry
   ACCESS     not-accessible
   STATUS     mandatory
   DESCRIPTION
     "An entry in the lpDS3DS1ChanOperStatusTable."
   INDEX {
      lpIndex,
      lpDS3Index,
      lpDS3DS1Index,
      lpDS3DS1ChanIndex }
::= { lpDS3DS1ChanOperStatusTable 1 }

LpDS3DS1ChanOperStatusEntry ::= SEQUENCE {
   lpDS3DS1ChanSnmpOperStatus
      INTEGER }

lpDS3DS1ChanSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpDS3DS1ChanOperStatusEntry 1 }

lpDS3DS1ChanStateTable OBJECT-TYPE
   SYNTAX     SEQUENCE OF LpDS3DS1ChanStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpDS3DS1Chan 14 }

lpDS3DS1ChanStateEntry OBJECT-TYPE
   SYNTAX     LpDS3DS1ChanStateEntry
   ACCESS     not-accessible
   STATUS     mandatory
   DESCRIPTION
     "An entry in the lpDS3DS1ChanStateTable."
   INDEX {
      lpIndex,
      lpDS3Index,
      lpDS3DS1Index,
      lpDS3DS1ChanIndex }
::= { lpDS3DS1ChanStateTable 1 }

LpDS3DS1ChanStateEntry ::= SEQUENCE {
   lpDS3DS1ChanAdminState
      INTEGER,
   lpDS3DS1ChanOperationalState
      INTEGER,
   lpDS3DS1ChanUsageState
      INTEGER,
   lpDS3DS1ChanAvailabilityStatus
      OCTET STRING,
   lpDS3DS1ChanProceduralStatus
      OCTET STRING,
   lpDS3DS1ChanControlStatus
      OCTET STRING,
   lpDS3DS1ChanAlarmStatus
      OCTET STRING,
   lpDS3DS1ChanStandbyStatus
      INTEGER,
   lpDS3DS1ChanUnknownStatus
      INTEGER }

lpDS3DS1ChanAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpDS3DS1ChanStateEntry 1 }

lpDS3DS1ChanOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpDS3DS1ChanStateEntry 2 }

lpDS3DS1ChanUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpDS3DS1ChanStateEntry 3 }

lpDS3DS1ChanAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpDS3DS1ChanStateEntry 4 }

lpDS3DS1ChanProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpDS3DS1ChanStateEntry 5 }

lpDS3DS1ChanControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpDS3DS1ChanStateEntry 6 }

lpDS3DS1ChanAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpDS3DS1ChanStateEntry 7 }

lpDS3DS1ChanStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpDS3DS1ChanStateEntry 8 }

lpDS3DS1ChanUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpDS3DS1ChanStateEntry 9 }

lpDS3DS1ChanOperTable OBJECT-TYPE
   SYNTAX     SEQUENCE OF LpDS3DS1ChanOperEntry
   ACCESS     not-accessible
   STATUS     mandatory
   DESCRIPTION
     "This group contains all of the operational data for a Channel 
      component."
::= { lpDS3DS1Chan 15 }

lpDS3DS1ChanOperEntry OBJECT-TYPE
   SYNTAX     LpDS3DS1ChanOperEntry
   ACCESS     not-accessible
   STATUS     mandatory
   DESCRIPTION
     "An entry in the lpDS3DS1ChanOperTable."
   INDEX {
      lpIndex,
      lpDS3Index,
      lpDS3DS1Index,
      lpDS3DS1ChanIndex }
::= { lpDS3DS1ChanOperTable 1 }

LpDS3DS1ChanOperEntry ::= SEQUENCE {
   lpDS3DS1ChanActualChannelSpeed
      Gauge32 }

lpDS3DS1ChanActualChannelSpeed OBJECT-TYPE
   SYNTAX     Gauge32 (0..4294967295)
   ACCESS     read-only
   STATUS     mandatory
   DESCRIPTION
     "This attribute displays the measured link speed of the Channel 
      component."
   DEFVAL     { 0 }
::= { lpDS3DS1ChanOperEntry 1 }

lpDS3DS1ChanAdminInfoTable OBJECT-TYPE
   SYNTAX     SEQUENCE OF LpDS3DS1ChanAdminInfoEntry
   ACCESS     not-accessible
   STATUS     mandatory
   DESCRIPTION
     "This group contains the attributes pertaining to the vendor of the 
      equipment."
::= { lpDS3DS1Chan 16 }

lpDS3DS1ChanAdminInfoEntry OBJECT-TYPE
   SYNTAX     LpDS3DS1ChanAdminInfoEntry
   ACCESS     not-accessible
   STATUS     mandatory
   DESCRIPTION
     "An entry in the lpDS3DS1ChanAdminInfoTable."
   INDEX {
      lpIndex,
      lpDS3Index,
      lpDS3DS1Index,
      lpDS3DS1ChanIndex }
::= { lpDS3DS1ChanAdminInfoTable 1 }

LpDS3DS1ChanAdminInfoEntry ::= SEQUENCE {
   lpDS3DS1ChanVendor
      AsciiString,
   lpDS3DS1ChanCommentText
      AsciiString }

lpDS3DS1ChanVendor OBJECT-TYPE
   SYNTAX     AsciiString (SIZE (0..20))
   ACCESS     read-write
   STATUS     mandatory
   DESCRIPTION
     "This is the name of the vendor supplying the facility."
::= { lpDS3DS1ChanAdminInfoEntry 1 }

lpDS3DS1ChanCommentText OBJECT-TYPE
   SYNTAX     AsciiString (SIZE (0..60))
   ACCESS     read-write
   STATUS     mandatory
   DESCRIPTION
     "Any miscellaneous text about the facility."
::= { lpDS3DS1ChanAdminInfoEntry 2 }


-- 
-- The Test component is configured to control a hardware facility test 
-- on a physical (V35, X21, DS1, E1, DS3, E3 etc.) or a logical port.

lpDS3DS1ChanTest OBJECT IDENTIFIER ::= { lpDS3DS1Chan 2 }



lpDS3DS1ChanTestRowStatusTable OBJECT-TYPE
   SYNTAX     SEQUENCE OF LpDS3DS1ChanTestRowStatusEntry
   ACCESS     not-accessible
   STATUS     mandatory
   DESCRIPTION
     "This entry controls the addition and deletion of 
      lpDS3DS1ChanTest components."
::= { lpDS3DS1ChanTest 1 }

lpDS3DS1ChanTestRowStatusEntry OBJECT-TYPE
   SYNTAX     LpDS3DS1ChanTestRowStatusEntry
   ACCESS     not-accessible
   STATUS     mandatory
   DESCRIPTION
     "A single entry in the table represents a single 
      lpDS3DS1ChanTest component."
   INDEX {
      lpIndex,
      lpDS3Index,
      lpDS3DS1Index,
      lpDS3DS1ChanIndex,
      lpDS3DS1ChanTestIndex }
::= { lpDS3DS1ChanTestRowStatusTable 1 }

LpDS3DS1ChanTestRowStatusEntry ::= SEQUENCE {
   lpDS3DS1ChanTestRowStatus
      RowStatus,
   lpDS3DS1ChanTestComponentName
      DisplayString,
   lpDS3DS1ChanTestStorageType
      StorageType,
   lpDS3DS1ChanTestIndex
      NonReplicated }

lpDS3DS1ChanTestRowStatus OBJECT-TYPE
   SYNTAX     RowStatus 
   ACCESS     read-only
   STATUS     mandatory
   DESCRIPTION
     "This variable is used as the basis for SNMP naming of
      lpDS3DS1ChanTest components.
      These components cannot be added nor deleted."
::= { lpDS3DS1ChanTestRowStatusEntry 1 }

lpDS3DS1ChanTestComponentName OBJECT-TYPE
   SYNTAX     DisplayString 
   ACCESS     read-only
   STATUS     mandatory
   DESCRIPTION
     "This variable provides the component's string name for
      use with the ASCII Console Interface"
::= { lpDS3DS1ChanTestRowStatusEntry 2 }

lpDS3DS1ChanTestStorageType OBJECT-TYPE
   SYNTAX     StorageType 
   ACCESS     read-only
   STATUS     mandatory
   DESCRIPTION
     "This variable represents the storage type value for the
      lpDS3DS1ChanTest tables."
::= { lpDS3DS1ChanTestRowStatusEntry 4 }

lpDS3DS1ChanTestIndex OBJECT-TYPE
   SYNTAX     NonReplicated 
   ACCESS     not-accessible
   STATUS     mandatory
   DESCRIPTION
     "This variable represents the index for the lpDS3DS1ChanTest tables."
::= { lpDS3DS1ChanTestRowStatusEntry 10 }

lpDS3DS1ChanTestStateTable OBJECT-TYPE
   SYNTAX     SEQUENCE OF LpDS3DS1ChanTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpDS3DS1ChanTest 10 }

lpDS3DS1ChanTestStateEntry OBJECT-TYPE
   SYNTAX     LpDS3DS1ChanTestStateEntry
   ACCESS     not-accessible
   STATUS     mandatory
   DESCRIPTION
     "An entry in the lpDS3DS1ChanTestStateTable."
   INDEX {
      lpIndex,
      lpDS3Index,
      lpDS3DS1Index,
      lpDS3DS1ChanIndex,
      lpDS3DS1ChanTestIndex }
::= { lpDS3DS1ChanTestStateTable 1 }

LpDS3DS1ChanTestStateEntry ::= SEQUENCE {
   lpDS3DS1ChanTestAdminState
      INTEGER,
   lpDS3DS1ChanTestOperationalState
      INTEGER,
   lpDS3DS1ChanTestUsageState
      INTEGER }

lpDS3DS1ChanTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpDS3DS1ChanTestStateEntry 1 }

lpDS3DS1ChanTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpDS3DS1ChanTestStateEntry 2 }

lpDS3DS1ChanTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpDS3DS1ChanTestStateEntry 3 }

lpDS3DS1ChanTestSetupTable OBJECT-TYPE
   SYNTAX     SEQUENCE OF LpDS3DS1ChanTestSetupEntry
   ACCESS     not-accessible
   STATUS     mandatory
   DESCRIPTION
     "This group contains all of the operational data for a Test 
      component."
::= { lpDS3DS1ChanTest 11 }

lpDS3DS1ChanTestSetupEntry OBJECT-TYPE
   SYNTAX     LpDS3DS1ChanTestSetupEntry
   ACCESS     not-accessible
   STATUS     mandatory
   DESCRIPTION
     "An entry in the lpDS3DS1ChanTestSetupTable."
   INDEX {
      lpIndex,
      lpDS3Index,
      lpDS3DS1Index,
      lpDS3DS1ChanIndex,
      lpDS3DS1ChanTestIndex }
::= { lpDS3DS1ChanTestSetupTable 1 }

LpDS3DS1ChanTestSetupEntry ::= SEQUENCE {
   lpDS3DS1ChanTestPurpose
      AsciiString,
   lpDS3DS1ChanTestType
      INTEGER,
   lpDS3DS1ChanTestFrmSize
      Unsigned32,
   lpDS3DS1ChanTestFrmPatternType
      INTEGER,
   lpDS3DS1ChanTestCustomizedPattern
      Hex,
   lpDS3DS1ChanTestDataStartDelay
      Unsigned32,
   lpDS3DS1ChanTestDisplayInterval
      Unsigned32,
   lpDS3DS1ChanTestDuration
      Unsigned32 }

lpDS3DS1ChanTestPurpose OBJECT-TYPE
   SYNTAX     AsciiString (SIZE (0..40))
   ACCESS     read-write
   STATUS     mandatory
   DESCRIPTION
     "This attribute records the purpose of the test so that the test results 
      can be associated and properly analyzed."
::= { lpDS3DS1ChanTestSetupEntry 1 }

lpDS3DS1ChanTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpDS3DS1ChanTestSetupEntry 2 }

lpDS3DS1ChanTestFrmSize OBJECT-TYPE
   SYNTAX     Unsigned32 (4..4096)
   ACCESS     read-write
   STATUS     mandatory
   DESCRIPTION
     "This attribute defines the size of the test data frames in number of 
      bytes."
   DEFVAL     { 1024 }
::= { lpDS3DS1ChanTestSetupEntry 3 }

lpDS3DS1ChanTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpDS3DS1ChanTestSetupEntry 4 }

lpDS3DS1ChanTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpDS3DS1ChanTestSetupEntry 5 }

lpDS3DS1ChanTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpDS3DS1ChanTestSetupEntry 6 }

lpDS3DS1ChanTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpDS3DS1ChanTestSetupEntry 7 }

lpDS3DS1ChanTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpDS3DS1ChanTestSetupEntry 8 }

lpDS3DS1ChanTestResultsTable OBJECT-TYPE
   SYNTAX     SEQUENCE OF LpDS3DS1ChanTestResultsEntry
   ACCESS     not-accessible
   STATUS     mandatory
   DESCRIPTION
     "This group contains all the statistics related attributes of the Test 
      component."
::= { lpDS3DS1ChanTest 12 }

lpDS3DS1ChanTestResultsEntry OBJECT-TYPE
   SYNTAX     LpDS3DS1ChanTestResultsEntry
   ACCESS     not-accessible
   STATUS     mandatory
   DESCRIPTION
     "An entry in the lpDS3DS1ChanTestResultsTable."
   INDEX {
      lpIndex,
      lpDS3Index,
      lpDS3DS1Index,
      lpDS3DS1ChanIndex,
      lpDS3DS1ChanTestIndex }
::= { lpDS3DS1ChanTestResultsTable 1 }

LpDS3DS1ChanTestResultsEntry ::= SEQUENCE {
   lpDS3DS1ChanTestElapsedTime
      Counter32,
   lpDS3DS1ChanTestTimeRemaining
      Unsigned32,
   lpDS3DS1ChanTestCauseOfTermination
      INTEGER,
   lpDS3DS1ChanTestBitsTx
      PassportCounter64,
   lpDS3DS1ChanTestBytesTx
      PassportCounter64,
   lpDS3DS1ChanTestFrmTx
      PassportCounter64,
   lpDS3DS1ChanTestBitsRx
      PassportCounter64,
   lpDS3DS1ChanTestBytesRx
      PassportCounter64,
   lpDS3DS1ChanTestFrmRx
      PassportCounter64,
   lpDS3DS1ChanTestErroredFrmRx
      PassportCounter64,
   lpDS3DS1ChanTestBitErrorRate
      AsciiString }

lpDS3DS1ChanTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpDS3DS1ChanTestResultsEntry 1 }

lpDS3DS1ChanTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpDS3DS1ChanTestResultsEntry 2 }

lpDS3DS1ChanTestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpDS3DS1ChanTestResultsEntry 3 }

lpDS3DS1ChanTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpDS3DS1ChanTestResultsEntry 4 }

lpDS3DS1ChanTestBytesTx OBJECT-TYPE
   SYNTAX     PassportCounter64 
   ACCESS     read-only
   STATUS     mandatory
   DESCRIPTION
     "This attribute is the total number of bytes sent during the test 
      period. This counter is not expected to reach its maximum value."
::= { lpDS3DS1ChanTestResultsEntry 5 }

lpDS3DS1ChanTestFrmTx OBJECT-TYPE
   SYNTAX     PassportCounter64 
   ACCESS     read-only
   STATUS     mandatory
   DESCRIPTION
     "This attribute is the total number of frames sent during the test 
      period. This counter is not expected to reach its maximum value."
::= { lpDS3DS1ChanTestResultsEntry 6 }

lpDS3DS1ChanTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpDS3DS1ChanTestResultsEntry 7 }

lpDS3DS1ChanTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpDS3DS1ChanTestResultsEntry 8 }

lpDS3DS1ChanTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpDS3DS1ChanTestResultsEntry 9 }

lpDS3DS1ChanTestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpDS3DS1ChanTestResultsEntry 10 }

lpDS3DS1ChanTestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpDS3DS1ChanTestResultsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

lpDS3DS1ChanCell OBJECT IDENTIFIER ::= { lpDS3DS1Chan 3 }



lpDS3DS1ChanCellRowStatusTable OBJECT-TYPE
   SYNTAX     SEQUENCE OF LpDS3DS1ChanCellRowStatusEntry
   ACCESS     not-accessible
   STATUS     mandatory
   DESCRIPTION
     "This entry controls the addition and deletion of 
      lpDS3DS1ChanCell components."
::= { lpDS3DS1ChanCell 1 }

lpDS3DS1ChanCellRowStatusEntry OBJECT-TYPE
   SYNTAX     LpDS3DS1ChanCellRowStatusEntry
   ACCESS     not-accessible
   STATUS     mandatory
   DESCRIPTION
     "A single entry in the table represents a single 
      lpDS3DS1ChanCell component."
   INDEX {
      lpIndex,
      lpDS3Index,
      lpDS3DS1Index,
      lpDS3DS1ChanIndex,
      lpDS3DS1ChanCellIndex }
::= { lpDS3DS1ChanCellRowStatusTable 1 }

LpDS3DS1ChanCellRowStatusEntry ::= SEQUENCE {
   lpDS3DS1ChanCellRowStatus
      RowStatus,
   lpDS3DS1ChanCellComponentName
      DisplayString,
   lpDS3DS1ChanCellStorageType
      StorageType,
   lpDS3DS1ChanCellIndex
      NonReplicated }

lpDS3DS1ChanCellRowStatus OBJECT-TYPE
   SYNTAX     RowStatus 
   ACCESS     read-write
   STATUS     mandatory
   DESCRIPTION
     "This variable is used as the basis for SNMP naming of
      lpDS3DS1ChanCell components.
      These components can be added and deleted."
::= { lpDS3DS1ChanCellRowStatusEntry 1 }

lpDS3DS1ChanCellComponentName OBJECT-TYPE
   SYNTAX     DisplayString 
   ACCESS     read-only
   STATUS     mandatory
   DESCRIPTION
     "This variable provides the component's string name for
      use with the ASCII Console Interface"
::= { lpDS3DS1ChanCellRowStatusEntry 2 }

lpDS3DS1ChanCellStorageType OBJECT-TYPE
   SYNTAX     StorageType 
   ACCESS     read-only
   STATUS     mandatory
   DESCRIPTION
     "This variable represents the storage type value for the
      lpDS3DS1ChanCell tables."
::= { lpDS3DS1ChanCellRowStatusEntry 4 }

lpDS3DS1ChanCellIndex OBJECT-TYPE
   SYNTAX     NonReplicated 
   ACCESS     not-accessible
   STATUS     mandatory
   DESCRIPTION
     "This variable represents the index for the lpDS3DS1ChanCell tables."
::= { lpDS3DS1ChanCellRowStatusEntry 10 }

lpDS3DS1ChanCellProvTable OBJECT-TYPE
   SYNTAX     SEQUENCE OF LpDS3DS1ChanCellProvEntry
   ACCESS     not-accessible
   STATUS     mandatory
   DESCRIPTION
     "This group contains the provisioning attributes for the AtmCell 
      component."
::= { lpDS3DS1ChanCell 10 }

lpDS3DS1ChanCellProvEntry OBJECT-TYPE
   SYNTAX     LpDS3DS1ChanCellProvEntry
   ACCESS     not-accessible
   STATUS     mandatory
   DESCRIPTION
     "An entry in the lpDS3DS1ChanCellProvTable."
   INDEX {
      lpIndex,
      lpDS3Index,
      lpDS3DS1Index,
      lpDS3DS1ChanIndex,
      lpDS3DS1ChanCellIndex }
::= { lpDS3DS1ChanCellProvTable 1 }

LpDS3DS1ChanCellProvEntry ::= SEQUENCE {
   lpDS3DS1ChanCellAlarmActDelay
      Unsigned32,
   lpDS3DS1ChanCellScrambleCellPayload
      INTEGER,
   lpDS3DS1ChanCellCorrectSingleBitHeaderErrors
      INTEGER }

lpDS3DS1ChanCellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { lpDS3DS1ChanCellProvEntry 1 }

lpDS3DS1ChanCellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { lpDS3DS1ChanCellProvEntry 2 }

lpDS3DS1ChanCellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { lpDS3DS1ChanCellProvEntry 3 }

lpDS3DS1ChanCellOperTable OBJECT-TYPE
   SYNTAX     SEQUENCE OF LpDS3DS1ChanCellOperEntry
   ACCESS     not-accessible
   STATUS     mandatory
   DESCRIPTION
     "This group contains the common operational attributes for the 
      AtmCell component."
::= { lpDS3DS1ChanCell 11 }

lpDS3DS1ChanCellOperEntry OBJECT-TYPE
   SYNTAX     LpDS3DS1ChanCellOperEntry
   ACCESS     not-accessible
   STATUS     mandatory
   DESCRIPTION
     "An entry in the lpDS3DS1ChanCellOperTable."
   INDEX {
      lpIndex,
      lpDS3Index,
      lpDS3DS1Index,
      lpDS3DS1ChanIndex,
      lpDS3DS1ChanCellIndex }
::= { lpDS3DS1ChanCellOperTable 1 }

LpDS3DS1ChanCellOperEntry ::= SEQUENCE {
   lpDS3DS1ChanCellLcdAlarm
      INTEGER }

lpDS3DS1ChanCellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { lpDS3DS1ChanCellOperEntry 1 }

lpDS3DS1ChanCellStatsTable OBJECT-TYPE
   SYNTAX     SEQUENCE OF LpDS3DS1ChanCellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { lpDS3DS1ChanCell 12 }

lpDS3DS1ChanCellStatsEntry OBJECT-TYPE
   SYNTAX     LpDS3DS1ChanCellStatsEntry
   ACCESS     not-accessible
   STATUS     mandatory
   DESCRIPTION
     "An entry in the lpDS3DS1ChanCellStatsTable."
   INDEX {
      lpIndex,
      lpDS3Index,
      lpDS3DS1Index,
      lpDS3DS1ChanIndex,
      lpDS3DS1ChanCellIndex }
::= { lpDS3DS1ChanCellStatsTable 1 }

LpDS3DS1ChanCellStatsEntry ::= SEQUENCE {
   lpDS3DS1ChanCellUncorrectableHecErrors
      Counter32,
   lpDS3DS1ChanCellSevErroredSec
      Counter32,
   lpDS3DS1ChanCellReceiveCellUtilization
      Gauge32,
   lpDS3DS1ChanCellTransmitCellUtilization
      Gauge32,
   lpDS3DS1ChanCellCorrectableHeaderErrors
      Counter32 }

lpDS3DS1ChanCellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { lpDS3DS1ChanCellStatsEntry 1 }

lpDS3DS1ChanCellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { lpDS3DS1ChanCellStatsEntry 2 }

lpDS3DS1ChanCellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { lpDS3DS1ChanCellStatsEntry 3 }

lpDS3DS1ChanCellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { lpDS3DS1ChanCellStatsEntry 4 }

lpDS3DS1ChanCellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { lpDS3DS1ChanCellStatsEntry 5 }


-- Lp/x Ds1/y Chan/z Tc
-- Lp/x E1/y Chan/z Tc
-- 
-- The Tc component is used to provision and monitor trunk 
-- conditioning options. A separate instance of this component is 
-- required for each Chan on a Port which is offering a structured 
-- constant bit rate service.
-- 
-- Under certain failure alarm conditions, trunk conditioning 
-- replacementData is substituted into the timeslots as defined by the 
-- Chan component. Trunk conditioning signaling is also substituted 
-- into the appropriate Channel Associated Signaling (CAS) bits when 
-- a lineType that uses CAS has been defined.
-- 
-- When used with AAL1 Circuit Emulation Service, trunk 
-- conditioning is transmitted towards the ATM network under the 
-- following conditions:
-- lossOfSignal (LOS)
-- lossOfFrame (LOF)
-- remoteAlarmIndication (RAI)
-- alarmIndicationSignal (AIS)
-- bufferUnderflow (BU)
-- and in addition for E1:
-- lossOfMultiframe (LOMF)
-- receiveMultiframeRemoteAlarmIndication (RMRAI)
-- 
-- When used with AAL1 Circuit Emulation Service, trunk 
-- conditioning is transmitted towards the PDH network under the 
-- following conditions:
-- bufferUnderflow (BU)
-- AAL1 protocol errors.
-- 

lpDS3DS1ChanTc OBJECT IDENTIFIER ::= { lpDS3DS1Chan 4 }



lpDS3DS1ChanTcRowStatusTable OBJECT-TYPE
   SYNTAX     SEQUENCE OF LpDS3DS1ChanTcRowStatusEntry
   ACCESS     not-accessible
   STATUS     mandatory
   DESCRIPTION
     "This entry controls the addition and deletion of 
      lpDS3DS1ChanTc components."
::= { lpDS3DS1ChanTc 1 }

lpDS3DS1ChanTcRowStatusEntry OBJECT-TYPE
   SYNTAX     LpDS3DS1ChanTcRowStatusEntry
   ACCESS     not-accessible
   STATUS     mandatory
   DESCRIPTION
     "A single entry in the table represents a single 
      lpDS3DS1ChanTc component."
   INDEX {
      lpIndex,
      lpDS3Index,
      lpDS3DS1Index,
      lpDS3DS1ChanIndex,
      lpDS3DS1ChanTcIndex }
::= { lpDS3DS1ChanTcRowStatusTable 1 }

LpDS3DS1ChanTcRowStatusEntry ::= SEQUENCE {
   lpDS3DS1ChanTcRowStatus
      RowStatus,
   lpDS3DS1ChanTcComponentName
      DisplayString,
   lpDS3DS1ChanTcStorageType
      StorageType,
   lpDS3DS1ChanTcIndex
      NonReplicated }

lpDS3DS1ChanTcRowStatus OBJECT-TYPE
   SYNTAX     RowStatus 
   ACCESS     read-write
   STATUS     mandatory
   DESCRIPTION
     "This variable is used as the basis for SNMP naming of
      lpDS3DS1ChanTc components.
      These components can be added and deleted."
::= { lpDS3DS1ChanTcRowStatusEntry 1 }

lpDS3DS1ChanTcComponentName OBJECT-TYPE
   SYNTAX     DisplayString 
   ACCESS     read-only
   STATUS     mandatory
   DESCRIPTION
     "This variable provides the component's string name for
      use with the ASCII Console Interface"
::= { lpDS3DS1ChanTcRowStatusEntry 2 }

lpDS3DS1ChanTcStorageType OBJECT-TYPE
   SYNTAX     StorageType 
   ACCESS     read-only
   STATUS     mandatory
   DESCRIPTION
     "This variable represents the storage type value for the
      lpDS3DS1ChanTc tables."
::= { lpDS3DS1ChanTcRowStatusEntry 4 }

lpDS3DS1ChanTcIndex OBJECT-TYPE
   SYNTAX     NonReplicated 
   ACCESS     not-accessible
   STATUS     mandatory
   DESCRIPTION
     "This variable represents the index for the lpDS3DS1ChanTc tables."
::= { lpDS3DS1ChanTcRowStatusEntry 10 }

lpDS3DS1ChanTcProvTable OBJECT-TYPE
   SYNTAX     SEQUENCE OF LpDS3DS1ChanTcProvEntry
   ACCESS     not-accessible
   STATUS     mandatory
   DESCRIPTION
     "This group contains all specific provisioning data for a Tc 
      component."
::= { lpDS3DS1ChanTc 10 }

lpDS3DS1ChanTcProvEntry OBJECT-TYPE
   SYNTAX     LpDS3DS1ChanTcProvEntry
   ACCESS     not-accessible
   STATUS     mandatory
   DESCRIPTION
     "An entry in the lpDS3DS1ChanTcProvTable."
   INDEX {
      lpIndex,
      lpDS3Index,
      lpDS3DS1Index,
      lpDS3DS1ChanIndex,
      lpDS3DS1ChanTcIndex }
::= { lpDS3DS1ChanTcProvTable 1 }

LpDS3DS1ChanTcProvEntry ::= SEQUENCE {
   lpDS3DS1ChanTcReplacementData
      Hex,
   lpDS3DS1ChanTcSignalOneDuration
      Unsigned32 }

lpDS3DS1ChanTcReplacementData OBJECT-TYPE
   SYNTAX     Hex (0..255)
   ACCESS     read-write
   STATUS     mandatory
   DESCRIPTION
     "This attribute specifies the trunk conditioning data byte to be 
      substituted into the timeslots defined by the Chan component under 
      fault conditions. 
      
      replacementData can be set to any two digit hexadecimal number. 
      The following are recommended values:
      DS1 MUX Out Of Service Code = 0x1A
      E1 MUX Out Of Service Code = 0xFF"
   DEFVAL     { 255 }
::= { lpDS3DS1ChanTcProvEntry 1 }

lpDS3DS1ChanTcSignalOneDuration OBJECT-TYPE
   SYNTAX     Unsigned32 (0..60)
   ACCESS     read-write
   STATUS     mandatory
   DESCRIPTION
     "This attribute specifies the time duration in seconds for which 
      signalOne is substituted into the appropriate signaling bits, when a 
      lineType that uses CAS has been defined. When signalOneDuration 
      has expired signalTwo is substituted into the appropriate signaling 
      bits.
      
      If signalOneDuration is set to zero then only signalTwo is 
      substituted into the appropriate signaling bits during error 
      conditions.
      
      signalOneDuration can be set to any integer value from 0 to 60 
      seconds."
   DEFVAL     { 0 }
::= { lpDS3DS1ChanTcProvEntry 2 }

lpDS3DS1ChanTcOpTable OBJECT-TYPE
   SYNTAX     SEQUENCE OF LpDS3DS1ChanTcOpEntry
   ACCESS     not-accessible
   STATUS     mandatory
   DESCRIPTION
     "This group contains all specific operational data for a Tc 
      component."
::= { lpDS3DS1ChanTc 11 }

lpDS3DS1ChanTcOpEntry OBJECT-TYPE
   SYNTAX     LpDS3DS1ChanTcOpEntry
   ACCESS     not-accessible
   STATUS     mandatory
   DESCRIPTION
     "An entry in the lpDS3DS1ChanTcOpTable."
   INDEX {
      lpIndex,
      lpDS3Index,
      lpDS3DS1Index,
      lpDS3DS1ChanIndex,
      lpDS3DS1ChanTcIndex }
::= { lpDS3DS1ChanTcOpTable 1 }

LpDS3DS1ChanTcOpEntry ::= SEQUENCE {
   lpDS3DS1ChanTcIngressConditioning
      INTEGER,
   lpDS3DS1ChanTcEgressConditioning
      INTEGER }

lpDS3DS1ChanTcIngressConditioning OBJECT-TYPE
   SYNTAX     INTEGER  {
                 off(0),
                 on(1) }
   ACCESS     read-only
   STATUS     mandatory
   DESCRIPTION
     "This attribute indicates the status of locally generated trunk 
      conditioning towards the ATM network.
      
      When trunk conditioning is being locally generated towards the 
      ATM network, ingressConditioning is set to on.
      
      When trunk conditioning is not being locally generated towards the 
      ATM network, ingressConditioning is set to off.
      
      Trunk conditioning is transmitted towards the ATM network under 
      the following conditions:
      lossOfSignal (LOS)
      lossOfFrame (LOF)
      remoteAlarmIndication (RAI)
      alarmIndicationSignal (AIS)
      bufferUnderflow (BU)
      and in addition for E1:
      lossOfMultiframe (LOMF)
      receiveMultiframeRemoteAlarmIndication (RMRAI)"
   DEFVAL     { off }
::= { lpDS3DS1ChanTcOpEntry 1 }

lpDS3DS1ChanTcEgressConditioning OBJECT-TYPE
   SYNTAX     INTEGER  {
                 off(0),
                 on(1) }
   ACCESS     read-only
   STATUS     mandatory
   DESCRIPTION
     "This attribute indicates the status of locally generated trunk 
      conditioning towards the PDH line.
      
      When trunk conditioning is being locally generated towards the 
      PDH line, egressConditioning is set to on.
      
      When trunk conditioning is not being locally generated towards the 
      PDH line, egressConditioning is set to off.
      
      Trunk conditioning is transmitted towards the PDH line under the 
      following conditions:
      bufferUnderflow (BU)
      AAL1 protocol errors."
   DEFVAL     { off }
::= { lpDS3DS1ChanTcOpEntry 2 }

lpDS3DS1ChanTcSigOneTable OBJECT-TYPE
   SYNTAX     SEQUENCE OF LpDS3DS1ChanTcSigOneEntry
   ACCESS     not-accessible
   STATUS     mandatory
   DESCRIPTION
     "This attribute specifies the value to be substituted into the ABCD 
      signaling bits for the timeslots defined by the Chan component 
      under fault conditions. The value will be substituted for the duration 
      provisioned in signalOneDuration when a lineType that uses CAS 
      has been defined. 
      
      For a lineType of d4Cas (Super Frame), signaling bits C and D are 
      required to equal bits A and B respectively."
::= { lpDS3DS1ChanTc 398 }

lpDS3DS1ChanTcSigOneEntry OBJECT-TYPE
   SYNTAX     LpDS3DS1ChanTcSigOneEntry
   ACCESS     not-accessible
   STATUS     mandatory
   DESCRIPTION
     "An entry in the lpDS3DS1ChanTcSigOneTable."
   INDEX {
      lpIndex,
      lpDS3Index,
      lpDS3DS1Index,
      lpDS3DS1ChanIndex,
      lpDS3DS1ChanTcIndex,
      lpDS3DS1ChanTcSigOneIndex }
::= { lpDS3DS1ChanTcSigOneTable 1 }

LpDS3DS1ChanTcSigOneEntry ::= SEQUENCE {
   lpDS3DS1ChanTcSigOneIndex
      INTEGER,
   lpDS3DS1ChanTcSigOneValue
      Unsigned32 }

lpDS3DS1ChanTcSigOneIndex OBJECT-TYPE
   SYNTAX     INTEGER  {
                 d(0),
                 c(1),
                 b(2),
                 a(3) }
   ACCESS     not-accessible
   STATUS     mandatory
   DESCRIPTION
     "This variable represents the lpDS3DS1ChanTcSigOneTable
      specific index for the lpDS3DS1ChanTcSigOneTable."
::= { lpDS3DS1ChanTcSigOneEntry 1 }

lpDS3DS1ChanTcSigOneValue OBJECT-TYPE
   SYNTAX     Unsigned32 (0..1)
   ACCESS     read-write
   STATUS     mandatory
   DESCRIPTION
     "This variable represents an individual value for the
      lpDS3DS1ChanTcSigOneTable."
::= { lpDS3DS1ChanTcSigOneEntry 2 }

lpDS3DS1ChanTcSigTwoTable OBJECT-TYPE
   SYNTAX     SEQUENCE OF LpDS3DS1ChanTcSigTwoEntry
   ACCESS     not-accessible
   STATUS     mandatory
   DESCRIPTION
     "This attribute specifies the value to be substituted into the ABCD 
      signaling bits for the timeslots defined by the Chan component 
      under fault conditions. The value will be substituted after the 
      duration provisioned in signalOneDuration has expired and when a 
      lineType that uses CAS has been defined. 
      
      For a lineType of d4Cas (Super Frame), signaling bits C and D are 
      required to equal bits A and B respectively."
::= { lpDS3DS1ChanTc 399 }

lpDS3DS1ChanTcSigTwoEntry OBJECT-TYPE
   SYNTAX     LpDS3DS1ChanTcSigTwoEntry
   ACCESS     not-accessible
   STATUS     mandatory
   DESCRIPTION
     "An entry in the lpDS3DS1ChanTcSigTwoTable."
   INDEX {
      lpIndex,
      lpDS3Index,
      lpDS3DS1Index,
      lpDS3DS1ChanIndex,
      lpDS3DS1ChanTcIndex,
      lpDS3DS1ChanTcSigTwoIndex }
::= { lpDS3DS1ChanTcSigTwoTable 1 }

LpDS3DS1ChanTcSigTwoEntry ::= SEQUENCE {
   lpDS3DS1ChanTcSigTwoIndex
      INTEGER,
   lpDS3DS1ChanTcSigTwoValue
      Unsigned32 }

lpDS3DS1ChanTcSigTwoIndex OBJECT-TYPE
   SYNTAX     INTEGER  {
                 d(0),
                 c(1),
                 b(2),
                 a(3) }
   ACCESS     not-accessible
   STATUS     mandatory
   DESCRIPTION
     "This variable represents the lpDS3DS1ChanTcSigTwoTable
      specific index for the lpDS3DS1ChanTcSigTwoTable."
::= { lpDS3DS1ChanTcSigTwoEntry 1 }

lpDS3DS1ChanTcSigTwoValue OBJECT-TYPE
   SYNTAX     Unsigned32 (0..1)
   ACCESS     read-write
   STATUS     mandatory
   DESCRIPTION
     "This variable represents an individual value for the
      lpDS3DS1ChanTcSigTwoTable."
::= { lpDS3DS1ChanTcSigTwoEntry 2 }


-- 
-- The Test component is configured to control a hardware facility test 
-- on a physical (V35, X21, DS1, E1, DS3, E3 etc.) or a logical port.

lpDS3DS1Test OBJECT IDENTIFIER ::= { lpDS3DS1 3 }



lpDS3DS1TestRowStatusTable OBJECT-TYPE
   SYNTAX     SEQUENCE OF LpDS3DS1TestRowStatusEntry
   ACCESS     not-accessible
   STATUS     mandatory
   DESCRIPTION
     "This entry controls the addition and deletion of 
      lpDS3DS1Test components."
::= { lpDS3DS1Test 1 }

lpDS3DS1TestRowStatusEntry OBJECT-TYPE
   SYNTAX     LpDS3DS1TestRowStatusEntry
   ACCESS     not-accessible
   STATUS     mandatory
   DESCRIPTION
     "A single entry in the table represents a single 
      lpDS3DS1Test component."
   INDEX {
      lpIndex,
      lpDS3Index,
      lpDS3DS1Index,
      lpDS3DS1TestIndex }
::= { lpDS3DS1TestRowStatusTable 1 }

LpDS3DS1TestRowStatusEntry ::= SEQUENCE {
   lpDS3DS1TestRowStatus
      RowStatus,
   lpDS3DS1TestComponentName
      DisplayString,
   lpDS3DS1TestStorageType
      StorageType,
   lpDS3DS1TestIndex
      NonReplicated }

lpDS3DS1TestRowStatus OBJECT-TYPE
   SYNTAX     RowStatus 
   ACCESS     read-only
   STATUS     mandatory
   DESCRIPTION
     "This variable is used as the basis for SNMP naming of
      lpDS3DS1Test components.
      These components cannot be added nor deleted."
::= { lpDS3DS1TestRowStatusEntry 1 }

lpDS3DS1TestComponentName OBJECT-TYPE
   SYNTAX     DisplayString 
   ACCESS     read-only
   STATUS     mandatory
   DESCRIPTION
     "This variable provides the component's string name for
      use with the ASCII Console Interface"
::= { lpDS3DS1TestRowStatusEntry 2 }

lpDS3DS1TestStorageType OBJECT-TYPE
   SYNTAX     StorageType 
   ACCESS     read-only
   STATUS     mandatory
   DESCRIPTION
     "This variable represents the storage type value for the
      lpDS3DS1Test tables."
::= { lpDS3DS1TestRowStatusEntry 4 }

lpDS3DS1TestIndex OBJECT-TYPE
   SYNTAX     NonReplicated 
   ACCESS     not-accessible
   STATUS     mandatory
   DESCRIPTION
     "This variable represents the index for the lpDS3DS1Test tables."
::= { lpDS3DS1TestRowStatusEntry 10 }

lpDS3DS1TestStateTable OBJECT-TYPE
   SYNTAX     SEQUENCE OF LpDS3DS1TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpDS3DS1Test 10 }

lpDS3DS1TestStateEntry OBJECT-TYPE
   SYNTAX     LpDS3DS1TestStateEntry
   ACCESS     not-accessible
   STATUS     mandatory
   DESCRIPTION
     "An entry in the lpDS3DS1TestStateTable."
   INDEX {
      lpIndex,
      lpDS3Index,
      lpDS3DS1Index,
      lpDS3DS1TestIndex }
::= { lpDS3DS1TestStateTable 1 }

LpDS3DS1TestStateEntry ::= SEQUENCE {
   lpDS3DS1TestAdminState
      INTEGER,
   lpDS3DS1TestOperationalState
      INTEGER,
   lpDS3DS1TestUsageState
      INTEGER }

lpDS3DS1TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpDS3DS1TestStateEntry 1 }

lpDS3DS1TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpDS3DS1TestStateEntry 2 }

lpDS3DS1TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpDS3DS1TestStateEntry 3 }

lpDS3DS1TestSetupTable OBJECT-TYPE
   SYNTAX     SEQUENCE OF LpDS3DS1TestSetupEntry
   ACCESS     not-accessible
   STATUS     mandatory
   DESCRIPTION
     "This group contains all of the operational data for a Test 
      component."
::= { lpDS3DS1Test 11 }

lpDS3DS1TestSetupEntry OBJECT-TYPE
   SYNTAX     LpDS3DS1TestSetupEntry
   ACCESS     not-accessible
   STATUS     mandatory
   DESCRIPTION
     "An entry in the lpDS3DS1TestSetupTable."
   INDEX {
      lpIndex,
      lpDS3Index,
      lpDS3DS1Index,
      lpDS3DS1TestIndex }
::= { lpDS3DS1TestSetupTable 1 }

LpDS3DS1TestSetupEntry ::= SEQUENCE {
   lpDS3DS1TestPurpose
      AsciiString,
   lpDS3DS1TestType
      INTEGER,
   lpDS3DS1TestFrmSize
      Unsigned32,
   lpDS3DS1TestFrmPatternType
      INTEGER,
   lpDS3DS1TestCustomizedPattern
      Hex,
   lpDS3DS1TestDataStartDelay
      Unsigned32,
   lpDS3DS1TestDisplayInterval
      Unsigned32,
   lpDS3DS1TestDuration
      Unsigned32 }

lpDS3DS1TestPurpose OBJECT-TYPE
   SYNTAX     AsciiString (SIZE (0..40))
   ACCESS     read-write
   STATUS     mandatory
   DESCRIPTION
     "This attribute records the purpose of the test so that the test results 
      can be associated and properly analyzed."
::= { lpDS3DS1TestSetupEntry 1 }

lpDS3DS1TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpDS3DS1TestSetupEntry 2 }

lpDS3DS1TestFrmSize OBJECT-TYPE
   SYNTAX     Unsigned32 (4..4096)
   ACCESS     read-write
   STATUS     mandatory
   DESCRIPTION
     "This attribute defines the size of the test data frames in number of 
      bytes."
   DEFVAL     { 1024 }
::= { lpDS3DS1TestSetupEntry 3 }

lpDS3DS1TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpDS3DS1TestSetupEntry 4 }

lpDS3DS1TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpDS3DS1TestSetupEntry 5 }

lpDS3DS1TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpDS3DS1TestSetupEntry 6 }

lpDS3DS1TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpDS3DS1TestSetupEntry 7 }

lpDS3DS1TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpDS3DS1TestSetupEntry 8 }

lpDS3DS1TestResultsTable OBJECT-TYPE
   SYNTAX     SEQUENCE OF LpDS3DS1TestResultsEntry
   ACCESS     not-accessible
   STATUS     mandatory
   DESCRIPTION
     "This group contains all the statistics related attributes of the Test 
      component."
::= { lpDS3DS1Test 12 }

lpDS3DS1TestResultsEntry OBJECT-TYPE
   SYNTAX     LpDS3DS1TestResultsEntry
   ACCESS     not-accessible
   STATUS     mandatory
   DESCRIPTION
     "An entry in the lpDS3DS1TestResultsTable."
   INDEX {
      lpIndex,
      lpDS3Index,
      lpDS3DS1Index,
      lpDS3DS1TestIndex }
::= { lpDS3DS1TestResultsTable 1 }

LpDS3DS1TestResultsEntry ::= SEQUENCE {
   lpDS3DS1TestElapsedTime
      Counter32,
   lpDS3DS1TestTimeRemaining
      Unsigned32,
   lpDS3DS1TestCauseOfTermination
      INTEGER,
   lpDS3DS1TestBitsTx
      PassportCounter64,
   lpDS3DS1TestBytesTx
      PassportCounter64,
   lpDS3DS1TestFrmTx
      PassportCounter64,
   lpDS3DS1TestBitsRx
      PassportCounter64,
   lpDS3DS1TestBytesRx
      PassportCounter64,
   lpDS3DS1TestFrmRx
      PassportCounter64,
   lpDS3DS1TestErroredFrmRx
      PassportCounter64,
   lpDS3DS1TestBitErrorRate
      AsciiString }

lpDS3DS1TestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpDS3DS1TestResultsEntry 1 }

lpDS3DS1TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpDS3DS1TestResultsEntry 2 }

lpDS3DS1TestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpDS3DS1TestResultsEntry 3 }

lpDS3DS1TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpDS3DS1TestResultsEntry 4 }

lpDS3DS1TestBytesTx OBJECT-TYPE
   SYNTAX     PassportCounter64 
   ACCESS     read-only
   STATUS     mandatory
   DESCRIPTION
     "This attribute is the total number of bytes sent during the test 
      period. This counter is not expected to reach its maximum value."
::= { lpDS3DS1TestResultsEntry 5 }

lpDS3DS1TestFrmTx OBJECT-TYPE
   SYNTAX     PassportCounter64 
   ACCESS     read-only
   STATUS     mandatory
   DESCRIPTION
     "This attribute is the total number of frames sent during the test 
      period. This counter is not expected to reach its maximum value."
::= { lpDS3DS1TestResultsEntry 6 }

lpDS3DS1TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpDS3DS1TestResultsEntry 7 }

lpDS3DS1TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpDS3DS1TestResultsEntry 8 }

lpDS3DS1TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpDS3DS1TestResultsEntry 9 }

lpDS3DS1TestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpDS3DS1TestResultsEntry 10 }

lpDS3DS1TestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpDS3DS1TestResultsEntry 11 }


-- LP/n E3/n
-- The E3 component controls an E3 port on an E3 Function 
-- Processor.

lpE3 OBJECT IDENTIFIER ::= { lp 6 }



lpE3RowStatusTable OBJECT-TYPE
   SYNTAX     SEQUENCE OF LpE3RowStatusEntry
   ACCESS     not-accessible
   STATUS     mandatory
   DESCRIPTION
     "This entry controls the addition and deletion of 
      lpE3 components."
::= { lpE3 1 }

lpE3RowStatusEntry OBJECT-TYPE
   SYNTAX     LpE3RowStatusEntry
   ACCESS     not-accessible
   STATUS     mandatory
   DESCRIPTION
     "A single entry in the table represents a single 
      lpE3 component."
   INDEX {
      lpIndex,
      lpE3Index }
::= { lpE3RowStatusTable 1 }

LpE3RowStatusEntry ::= SEQUENCE {
   lpE3RowStatus
      RowStatus,
   lpE3ComponentName
      DisplayString,
   lpE3StorageType
      StorageType,
   lpE3Index
      Integer32 }

lpE3RowStatus OBJECT-TYPE
   SYNTAX     RowStatus 
   ACCESS     read-write
   STATUS     mandatory
   DESCRIPTION
     "This variable is used as the basis for SNMP naming of
      lpE3 components.
      These components can be added and deleted."
::= { lpE3RowStatusEntry 1 }

lpE3ComponentName OBJECT-TYPE
   SYNTAX     DisplayString 
   ACCESS     read-only
   STATUS     mandatory
   DESCRIPTION
     "This variable provides the component's string name for
      use with the ASCII Console Interface"
::= { lpE3RowStatusEntry 2 }

lpE3StorageType OBJECT-TYPE
   SYNTAX     StorageType 
   ACCESS     read-only
   STATUS     mandatory
   DESCRIPTION
     "This variable represents the storage type value for the
      lpE3 tables."
::= { lpE3RowStatusEntry 4 }

lpE3Index OBJECT-TYPE
   SYNTAX     Integer32 (0..2)
   ACCESS     not-accessible
   STATUS     mandatory
   DESCRIPTION
     "This variable represents the index for the lpE3 tables."
::= { lpE3RowStatusEntry 10 }

lpE3ProvTable OBJECT-TYPE
   SYNTAX     SEQUENCE OF LpE3ProvEntry
   ACCESS     not-accessible
   STATUS     mandatory
   DESCRIPTION
     "This group contains all of the provisioning data for a E3 
      component."
::= { lpE3 10 }

lpE3ProvEntry OBJECT-TYPE
   SYNTAX     LpE3ProvEntry
   ACCESS     not-accessible
   STATUS     mandatory
   DESCRIPTION
     "An entry in the lpE3ProvTable."
   INDEX {
      lpIndex,
      lpE3Index }
::= { lpE3ProvTable 1 }

LpE3ProvEntry ::= SEQUENCE {
   lpE3LineLength
      Unsigned32,
   lpE3ClockingSource
      INTEGER,
   lpE3ApplicationFramerName
      Link,
   lpE3Mapping
      INTEGER,
   lpE3Framing
      INTEGER,
   lpE3LinkAlarmActivationThreshold
      Unsigned32,
   lpE3LinkAlarmScanInterval
      Unsigned32 }

lpE3LineLength OBJECT-TYPE
   SYNTAX     Unsigned32 (0..300)
   ACCESS     read-write
   STATUS     mandatory
   DESCRIPTION
     "This attribute defines the line length for equalization calculations 
      for the E3 line. The line length range is between 0 and 300 metres 
      (1 metres = 3.28 feet)."
   DEFVAL     { 1 }
::= { lpE3ProvEntry 1 }

lpE3ClockingSource OBJECT-TYPE
   SYNTAX     INTEGER  {
                 local(0),
                 line(1),
                 module(2),
                 otherPort(4) }
   ACCESS     read-write
   STATUS     mandatory
   DESCRIPTION
     "This attribute defines the type of clocking source used for 
      synchronizing the E3 transmit clock: local means direct use of the 
      local clock oscillator at its centre frequency; line means use of a 
      signal phase-locked to the incoming E3 line rate; module means the 
      use of a signal phase-locked to the CP reference clock.
      Note that the multiport cell-based cards have one common clock 
      source for each of the three ports. For this reason, the following 
      rules apply for the value of clockingSource across the board's three 
      ports: 
      All three clockingSource values must be 'local' OR
      All three clockingSource values must be 'module' OR
      One clockingSource value must be 'line' and the other two must be 
      'otherPort'.
      The default value for this attribute will be module if a CP clock is 
      available, and local otherwise."
::= { lpE3ProvEntry 2 }

lpE3ApplicationFramerName OBJECT-TYPE
   SYNTAX     Link 
   ACCESS     read-write
   STATUS     mandatory
   DESCRIPTION
     "This attribute defines the link to the software stack. It defines which 
      application is running on top of the E3 component."
::= { lpE3ProvEntry 3 }

lpE3Mapping OBJECT-TYPE
   SYNTAX     INTEGER  {
                 direct(0),
                 plcp(1) }
   ACCESS     read-write
   STATUS     mandatory
   DESCRIPTION
     "This attribute indicates if ATM cells will be mapped directly into 
      the E3 payload, or whether PLCP mapping will be used. The PLCP 
      component will appear under the E3 component when this attribute 
      is set to plcp. This attribute will be ignored when set on frame-
      based cards."
   DEFVAL     { direct }
::= { lpE3ProvEntry 4 }

lpE3Framing OBJECT-TYPE
   SYNTAX     INTEGER  {
                 g751(0),
                 g832(1) }
   ACCESS     read-write
   STATUS     mandatory
   DESCRIPTION
     "This attribute indicates if the framing mode will be in accordance 
      with the CCITT G.751 or G.832 specification. The G832 
      component will appear under the E3 component when this attribute 
      is set to g832. This attribute may only be set on cell-based card 
      types. Note also that this attribute may only be set to g751 if the 
      mapping attribute is set to plcp.
      The default value of this attribute will be g751 for frame-based 
      cards, and g832 for cell-based cards.
      Note: when E3 framing is changed from g832 to g751, the G832 
      component must be deleted."
::= { lpE3ProvEntry 5 }

lpE3LinkAlarmActivationThreshold OBJECT-TYPE
   SYNTAX     Unsigned32 (100..2600)
   ACCESS     read-write
   STATUS     mandatory
   DESCRIPTION
     "This attribute specifies the time interval between the detection of a 
      sustained link failure and the activation of an alarm. It is 
      provisionable for E3 cards."
   DEFVAL     { 2200 }
::= { lpE3ProvEntry 6 }

lpE3LinkAlarmScanInterval OBJECT-TYPE
   SYNTAX     Unsigned32 (50..250)
   ACCESS     read-write
   STATUS     mandatory
   DESCRIPTION
     "This attribute specifies the alarm scan timer polling interval. It 
      determines how frequently the status of the link is monitored after a 
      first link error interrupt. It is provisionable for E3 cards."
   DEFVAL     { 200 }
::= { lpE3ProvEntry 7 }

lpE3CidDataTable OBJECT-TYPE
   SYNTAX     SEQUENCE OF LpE3CidDataEntry
   ACCESS     not-accessible
   STATUS     mandatory
   DESCRIPTION
     "This group contains the attribute for a component's Customer 
      Identifier (CID). Refer to the attribute description for a detailed 
      explanation of CIDs."
::= { lpE3 11 }

lpE3CidDataEntry OBJECT-TYPE
   SYNTAX     LpE3CidDataEntry
   ACCESS     not-accessible
   STATUS     mandatory
   DESCRIPTION
     "An entry in the lpE3CidDataTable."
   INDEX {
      lpIndex,
      lpE3Index }
::= { lpE3CidDataTable 1 }

LpE3CidDataEntry ::= SEQUENCE {
   lpE3CustomerIdentifier
      Unsigned32 }

lpE3CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpE3CidDataEntry 1 }

lpE3AdminInfoTable OBJECT-TYPE
   SYNTAX     SEQUENCE OF LpE3AdminInfoEntry
   ACCESS     not-accessible
   STATUS     mandatory
   DESCRIPTION
     "This group contains the attributes pertaining to the vendor of the 
      equipment."
::= { lpE3 12 }

lpE3AdminInfoEntry OBJECT-TYPE
   SYNTAX     LpE3AdminInfoEntry
   ACCESS     not-accessible
   STATUS     mandatory
   DESCRIPTION
     "An entry in the lpE3AdminInfoTable."
   INDEX {
      lpIndex,
      lpE3Index }
::= { lpE3AdminInfoTable 1 }

LpE3AdminInfoEntry ::= SEQUENCE {
   lpE3Vendor
      AsciiString,
   lpE3CommentText
      AsciiString }

lpE3Vendor OBJECT-TYPE
   SYNTAX     AsciiString (SIZE (0..20))
   ACCESS     read-write
   STATUS     mandatory
   DESCRIPTION
     "This is the name of the vendor supplying the facility."
::= { lpE3AdminInfoEntry 1 }

lpE3CommentText OBJECT-TYPE
   SYNTAX     AsciiString (SIZE (0..60))
   ACCESS     read-write
   STATUS     mandatory
   DESCRIPTION
     "Any miscellaneous text about the facility."
::= { lpE3AdminInfoEntry 2 }

lpE3IfEntryTable OBJECT-TYPE
   SYNTAX     SEQUENCE OF LpE3IfEntryEntry
   ACCESS     not-accessible
   STATUS     mandatory
   DESCRIPTION
     "This group contains the provisionable attributes for the ifEntry."
::= { lpE3 13 }

lpE3IfEntryEntry OBJECT-TYPE
   SYNTAX     LpE3IfEntryEntry
   ACCESS     not-accessible
   STATUS     mandatory
   DESCRIPTION
     "An entry in the lpE3IfEntryTable."
   INDEX {
      lpIndex,
      lpE3Index }
::= { lpE3IfEntryTable 1 }

LpE3IfEntryEntry ::= SEQUENCE {
   lpE3IfAdminStatus
      INTEGER,
   lpE3IfIndex
      InterfaceIndex }

lpE3IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpE3IfEntryEntry 1 }

lpE3IfIndex OBJECT-TYPE
   SYNTAX     InterfaceIndex (1..65535)
   ACCESS     read-only
   STATUS     mandatory
   DESCRIPTION
     "This is the index for the IfEntry. Its value is automatically initialized 
      during the provisioning process."
::= { lpE3IfEntryEntry 2 }

lpE3OperStatusTable OBJECT-TYPE
   SYNTAX     SEQUENCE OF LpE3OperStatusEntry
   ACCESS     not-accessible
   STATUS     mandatory
   DESCRIPTION
     "This group includes the Operational Status attribute. This attribute 
      defines the current operational state of this component."
::= { lpE3 14 }

lpE3OperStatusEntry OBJECT-TYPE
   SYNTAX     LpE3OperStatusEntry
   ACCESS     not-accessible
   STATUS     mandatory
   DESCRIPTION
     "An entry in the lpE3OperStatusTable."
   INDEX {
      lpIndex,
      lpE3Index }
::= { lpE3OperStatusTable 1 }

LpE3OperStatusEntry ::= SEQUENCE {
   lpE3SnmpOperStatus
      INTEGER }

lpE3SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpE3OperStatusEntry 1 }

lpE3StateTable OBJECT-TYPE
   SYNTAX     SEQUENCE OF LpE3StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpE3 15 }

lpE3StateEntry OBJECT-TYPE
   SYNTAX     LpE3StateEntry
   ACCESS     not-accessible
   STATUS     mandatory
   DESCRIPTION
     "An entry in the lpE3StateTable."
   INDEX {
      lpIndex,
      lpE3Index }
::= { lpE3StateTable 1 }

LpE3StateEntry ::= SEQUENCE {
   lpE3AdminState
      INTEGER,
   lpE3OperationalState
      INTEGER,
   lpE3UsageState
      INTEGER,
   lpE3AvailabilityStatus
      OCTET STRING,
   lpE3ProceduralStatus
      OCTET STRING,
   lpE3ControlStatus
      OCTET STRING,
   lpE3AlarmStatus
      OCTET STRING,
   lpE3StandbyStatus
      INTEGER,
   lpE3UnknownStatus
      INTEGER }

lpE3AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpE3StateEntry 1 }

lpE3OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpE3StateEntry 2 }

lpE3UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpE3StateEntry 3 }

lpE3AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpE3StateEntry 4 }

lpE3ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpE3StateEntry 5 }

lpE3ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpE3StateEntry 6 }

lpE3AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpE3StateEntry 7 }

lpE3StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpE3StateEntry 8 }

lpE3UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpE3StateEntry 9 }

lpE3OperTable OBJECT-TYPE
   SYNTAX     SEQUENCE OF LpE3OperEntry
   ACCESS     not-accessible
   STATUS     mandatory
   DESCRIPTION
     "This group contains the common operational data for E3 
      component."
::= { lpE3 16 }

lpE3OperEntry OBJECT-TYPE
   SYNTAX     LpE3OperEntry
   ACCESS     not-accessible
   STATUS     mandatory
   DESCRIPTION
     "An entry in the lpE3OperTable."
   INDEX {
      lpIndex,
      lpE3Index }
::= { lpE3OperTable 1 }

LpE3OperEntry ::= SEQUENCE {
   lpE3LosAlarm
      INTEGER,
   lpE3LofAlarm
      INTEGER,
   lpE3RxAisAlarm
      INTEGER,
   lpE3RxRaiAlarm
      INTEGER,
   lpE3TxAis
      INTEGER,
   lpE3TxRai
      INTEGER }

lpE3LosAlarm OBJECT-TYPE
   SYNTAX     INTEGER  {
                 on(0),
                 off(1) }
   ACCESS     read-only
   STATUS     mandatory
   DESCRIPTION
     "This attribute displays whether a Loss Of Signal (LOS) alarm state 
      has been entered. An LOS alarm state is entered when LOS defects 
      has been observed and accumulated for a period of 2.5 seconds +/- 
      0.5 seconds. An LOS defect is detected at the E3 line interface upon 
      observing N continuous pulse positions with no pulses of either 
      positive or negative polarity, where N is between 10 and 255. If the 
      LOS defects are intermittently occurring, the LOS defect 
      accumulator is decremented at a rate of 1/10 of the incrementing 
      rate (alarm integration ratio of 1/10), with all measurements based 
      on a 200 ms polling cycle.
      The E3 component goes into an operational state of disabled until 
      the LOS alarm condition is cleared. The LOS alarm state is cleared 
      when the LOS defects are absent for a period of 10 seconds +/- 0.5 
      seconds.
      The losAlarm attribute is always set to off when the component has 
      been locked and left offline."
   DEFVAL     { off }
::= { lpE3OperEntry 1 }

lpE3LofAlarm OBJECT-TYPE
   SYNTAX     INTEGER  {
                 on(0),
                 off(1) }
   ACCESS     read-only
   STATUS     mandatory
   DESCRIPTION
     "This attribute displays whether a Loss Of Frame (LOF) alarm state 
      has been entered. An LOF alarm state is entered when Severely 
      Errored Frame (SEF) defects have been detected and accumulated 
      for a period of 2.5 seconds +/- 0.5 seconds. An E3 SEF defect is 
      reported after detecting Frame Alignment Signal (FAS) errors on 4 
      consecutive E3 frames received on the incoming line. If the LOF 
      defects are intermittently occurring, the LOF defect accumulator is 
      decremented at a rate of 1/10 of the incrementing rate (alarm 
      integration ratio of 1/10), with all measurements based on a 200 ms 
      polling cycle.
      The E3 component goes into an operational state of disabled until 
      the LOF alarm condition is cleared. The condition is cleared when 
      E3 framing has been achieved for a period of 10 seconds +/- 0.5 
      seconds. As long as SEF defects are detected, the node also 
      transmits the far-end SEF/AIS (in G.751 E3) or FERF (in G.832) 
      defect indicator over the outgoing line. The txRai attribute is set to 
      on when transmitting the far-end SEF/AIS defect indicator on the 
      outgoing line.
      The lofAlarm attribute is always set to off when the component has 
      been locked and left offline."
   DEFVAL     { off }
::= { lpE3OperEntry 2 }

lpE3RxAisAlarm OBJECT-TYPE
   SYNTAX     INTEGER  {
                 on(0),
                 off(1) }
   ACCESS     read-only
   STATUS     mandatory
   DESCRIPTION
     "This attribute displays whether an Alarm Indication Signal (AIS) 
      alarm when state has been entered. An AIS alarm state is entered 
      when AIS defects have been observed and accumulated for a period 
      of 2.5 seconds +/- 0.5 seconds on the incoming E3 line. An AIS 
      defect is the occurrence of the AIS (unframed signal with a density 
      of zeros below a certain threshold such as defined by ITU 
      Recommendation G.775). If the AIS defects are intermittently 
      occurring, the AIS defect accumulator is decremented at a rate of 1/
      10 of the incrementing rate (alarm integration ratio of 1/10), with all 
      measurements based on a 200 ms polling cycle.
      The E3 component goes into an operational state of disabled until 
      the AIS alarm condition is cleared (after AIS has been no longer 
      detected for a period of 10 seconds +/- 0.5 seconds). As long as AIS 
      is detected on the incoming line, the node also transmits the far-end 
      SEF/AIS (in G.751 E3) or FERF (in G.832) defect indicator over 
      the outgoing line. The txRai attribute is set to on when transmitting 
      the far-end SEF/AIS defect indicator on the outgoing line.
      The rxAisAlarm attribute is always set to off when the component 
      has been locked and left offline."
   DEFVAL     { off }
::= { lpE3OperEntry 3 }

lpE3RxRaiAlarm OBJECT-TYPE
   SYNTAX     INTEGER  {
                 on(0),
                 off(1) }
   ACCESS     read-only
   STATUS     mandatory
   DESCRIPTION
     "This attribute displays whether a Remote Alarm Indication (RAI) 
      alarm state has been entered. A RAI alarm state is entered when far-
      end SEF/AIS defects (or Far-End Receive Failure (FERF) defects in 
      G.832 E3 Framing mode) have been observed and accumulated for 
      a period of 2.5 seconds +/- 0.5 seconds on the E3 incoming line. If 
      the RAI defects are intermittently occurring, the RAI defect 
      accumulator is decremented at a rate of 1/10 of the incrementing 
      rate (alarm integration ratio of 1/10), with all measurements based 
      on a 200 ms polling cycle.
      The E3 component goes into an operational state of disabled until 
      the RAI alarm condition is cleared. The condition is cleared when 
      the far-end defect indicator has not been detected for 10 seconds +/- 
      0.5 seconds. The declaration of a RAI Alarm is usually a signal that 
      the far end facility is unable to gain synchronization.
      The rxRaiAlarm attribute is always set to off when the component 
      has been locked and left offline."
   DEFVAL     { off }
::= { lpE3OperEntry 4 }

lpE3TxAis OBJECT-TYPE
   SYNTAX     INTEGER  {
                 on(0),
                 off(1) }
   ACCESS     read-only
   STATUS     mandatory
   DESCRIPTION
     "This attribute displays whether an AIS alarm is being transmitted on 
      the E3 line. AIS is transmitted on the outgoing line when the E3 
      component is locked and not used for operational testing."
   DEFVAL     { off }
::= { lpE3OperEntry 5 }

lpE3TxRai OBJECT-TYPE
   SYNTAX     INTEGER  {
                 on(0),
                 off(1) }
   ACCESS     read-only
   STATUS     mandatory
   DESCRIPTION
     "This attribute displays whether the far-end SEF/AIS defect indicator 
      is transmitted over the outgoing line when the E3 component has 
      been unlocked or used in operational testing. When the E3 
      component is locked and not used in operational testing, this 
      attribute is always set to off. The far-end SEF/AIS defect indicator is 
      transmitted over the outgoing line when SEF/AIS defects are 
      detected on the incoming line. In G.832 E3 Framing mode, the 
      FERF bit is set to '1' to transmit the SEF/AIS defect indicator."
   DEFVAL     { off }
::= { lpE3OperEntry 6 }

lpE3StatsTable OBJECT-TYPE
   SYNTAX     SEQUENCE OF LpE3StatsEntry
   ACCESS     not-accessible
   STATUS     mandatory
   DESCRIPTION
     "This group contains the common operational data for E3 
      component. Each attribute type is a non-negative integer which 
      monotonically increases until it reaches a maximum value, at which 
      point it wraps around and starts increasing again from zero."
::= { lpE3 17 }

lpE3StatsEntry OBJECT-TYPE
   SYNTAX     LpE3StatsEntry
   ACCESS     not-accessible
   STATUS     mandatory
   DESCRIPTION
     "An entry in the lpE3StatsTable."
   INDEX {
      lpIndex,
      lpE3Index }
::= { lpE3StatsTable 1 }

LpE3StatsEntry ::= SEQUENCE {
   lpE3RunningTime
      Counter32,
   lpE3ErrorFreeSec
      Counter32,
   lpE3LineCodeViolations
      Counter32,
   lpE3LineErroredSec
      Counter32,
   lpE3LineSevErroredSec
      Counter32,
   lpE3LineLosSec
      Counter32,
   lpE3LineFailures
      Counter32,
   lpE3PathCodeViolations
      Counter32,
   lpE3PathErroredSec
      Counter32,
   lpE3PathSevErroredSec
      Counter32,
   lpE3PathSefAisSec
      Counter32,
   lpE3PathUnavailSec
      Counter32,
   lpE3PathFailures
      Counter32 }

lpE3RunningTime OBJECT-TYPE
   SYNTAX     Counter32 
   ACCESS     read-only
   STATUS     mandatory
   DESCRIPTION
     "This attribute indicates the total number of seconds since the E3 
      component has been activated and been in unlocked state or used 
      for operational testing. All the other error counts that follow as well 
      as each E3 subcomponent's error counts can be updated when this 
      count is active."
::= { lpE3StatsEntry 1 }

lpE3ErrorFreeSec OBJECT-TYPE
   SYNTAX     Counter32 
   ACCESS     read-only
   STATUS     mandatory
   DESCRIPTION
     "This attribute indicates the number of seconds that the E3 port has 
      been in an error free state."
::= { lpE3StatsEntry 2 }

lpE3LineCodeViolations OBJECT-TYPE
   SYNTAX     Counter32 
   ACCESS     read-only
   STATUS     mandatory
   DESCRIPTION
     "This attribute indicates the total number of Line Code Violations 
      (LCV) detected. An E3 Line Code Violation is an HDB3 coded 
      signal error. LCV counting is inhibited for second intervals where a 
      Line Severely Errored Second (LSES) is counted. 
      This attribute is a non-negative integer which monotonically 
      increases until it reaches a maximum value, at which point it wraps 
      around and starts increasing again from zero."
::= { lpE3StatsEntry 3 }

lpE3LineErroredSec OBJECT-TYPE
   SYNTAX     Counter32 
   ACCESS     read-only
   STATUS     mandatory
   DESCRIPTION
     "This attribute indicates the total number of Line Errored Seconds 
      (LES) that have been counted. A LES is declared for interval 
      seconds containing one or more Line Code Violations (LCV) or one 
      or more Loss Of Signal (LOS) defects."
::= { lpE3StatsEntry 4 }

lpE3LineSevErroredSec OBJECT-TYPE
   SYNTAX     Counter32 
   ACCESS     read-only
   STATUS     mandatory
   DESCRIPTION
     "This attribute indicates the total number of Line Severely Errored 
      Seconds (LSES) that have been counted. A LSES is declared for 
      second intervals containing more than 34 Line Code Violations 
      (LCV) or one or more Loss of Signal (LOS) defects."
::= { lpE3StatsEntry 5 }

lpE3LineLosSec OBJECT-TYPE
   SYNTAX     Counter32 
   ACCESS     read-only
   STATUS     mandatory
   DESCRIPTION
     "This attribute indicates the total number of Line LOS Seconds 
      (LOSS) that have been counted. A LOSS is declared for second 
      intervals containing one or more Loss of Signal (LOS) defects."
::= { lpE3StatsEntry 6 }

lpE3LineFailures OBJECT-TYPE
   SYNTAX     Counter32 
   ACCESS     read-only
   STATUS     mandatory
   DESCRIPTION
     "This attribute indicates the total number of times that a line failure 
      (LOS failure) has been declared.
      This attribute is a non-negative integer which monotonically 
      increases until it reaches a maximum value, at which point it wraps 
      around and starts increasing again from zero."
::= { lpE3StatsEntry 7 }

lpE3PathCodeViolations OBJECT-TYPE
   SYNTAX     Counter32 
   ACCESS     read-only
   STATUS     mandatory
   DESCRIPTION
     "This attribute indicates the total number of Path Code Violations 
      (PCV) detected. An E3 PCV is an error in the Frame Alignment 
      (FA) signal, or, in G.832 Framing Mode, an error in the Frame 
      Alignment signal or a BIP-8 error. PCV counting is inhibited over 
      second intervals where a Path Severely Errored Second (PSES) is 
      counted. Counting of PCVs is also inhibited over second intervals 
      where a Path Unavailable Second (PUAS) is counted. 
      This attribute is a non-negative integer which monotonically 
      increases until it reaches a maximum value, at which point it wraps 
      around and starts increasing again from zero."
::= { lpE3StatsEntry 8 }

lpE3PathErroredSec OBJECT-TYPE
   SYNTAX     Counter32 
   ACCESS     read-only
   STATUS     mandatory
   DESCRIPTION
     "This attribute indicates the total number of Path Errored Seconds 
      (PES) that have been counted. A PES is declared for second 
      intervals containing one or more Path Code Violations (PCV) or one 
      or more Severely Errored Frame (SEF) or Alarm Indication Signal 
      (AIS) defects. Counting of Path Errored Seconds is inhibited when 
      a Path Unavailable Second (PUAS) is counted over the monitored 
      second."
::= { lpE3StatsEntry 9 }

lpE3PathSevErroredSec OBJECT-TYPE
   SYNTAX     Counter32 
   ACCESS     read-only
   STATUS     mandatory
   DESCRIPTION
     "This attribute indicates the total number of Path Severely Errored 
      Seconds (PSES) that have been counted. A PSES is declared for 
      second intervals containing more than 22 (G.751 E3) or 34 (G.832 
      E3) Path Code Violations (PCV) or one or more Severely Errored 
      Frame (SEF) or Alarm Indication Signal (AIS) defects. Counting of 
      PSESs is inhibited when a Path Unavailable Second (PUAS) is 
      counted over the monitored second."
::= { lpE3StatsEntry 10 }

lpE3PathSefAisSec OBJECT-TYPE
   SYNTAX     Counter32 
   ACCESS     read-only
   STATUS     mandatory
   DESCRIPTION
     "This attribute indicates the total number of Path SEF/AIS Seconds 
      (PSAS). A PSAS is declared for second intervals containing one or 
      more Severely Errored Frame (SEF) or Alarm Indication Signal 
      (AIS) defects. Counting of PSAS is inhibited when Path 
      Unavailable Seconds (PUAS) is counted over the monitored second."
::= { lpE3StatsEntry 11 }

lpE3PathUnavailSec OBJECT-TYPE
   SYNTAX     Counter32 
   ACCESS     read-only
   STATUS     mandatory
   DESCRIPTION
     "This attribute indicates the total number of one second intervals for 
      which the E3 path is unavailable. The E3 path becomes unavailable 
      at the onset of 10 consecutive Path Severely Errored Seconds 
      (PSES). The 10 PSESs are included in the unavailable time. Once 
      unavailable, the E3 path becomes available at the onset of 10 
      contiguous seconds with no PSES. The 10 seconds with no PSES 
      are excluded from the unavailable time. For second intervals where 
      PUAS is counted, counting of Path Code Violations (PCV), Path 
      Errored Seconds (PES), Path Severely Errored Seconds (PSES) and 
      Path SefAis Seconds (PSAS) is inhibited."
::= { lpE3StatsEntry 12 }

lpE3PathFailures OBJECT-TYPE
   SYNTAX     Counter32 
   ACCESS     read-only
   STATUS     mandatory
   DESCRIPTION
     "This attribute indicates the total number of times that a path failure 
      (LOF/AIS failure) has been declared.
      This attribute is a non-negative integer which monotonically 
      increases until it reaches a maximum value, at which point it wraps 
      around and starts increasing again from zero."
::= { lpE3StatsEntry 13 }


-- 
-- The Test component is configured to control a hardware facility test 
-- on a physical (V35, X21, DS1, E1, DS3, E3 etc.) or a logical port.

lpE3Test OBJECT IDENTIFIER ::= { lpE3 2 }



lpE3TestRowStatusTable OBJECT-TYPE
   SYNTAX     SEQUENCE OF LpE3TestRowStatusEntry
   ACCESS     not-accessible
   STATUS     mandatory
   DESCRIPTION
     "This entry controls the addition and deletion of 
      lpE3Test components."
::= { lpE3Test 1 }

lpE3TestRowStatusEntry OBJECT-TYPE
   SYNTAX     LpE3TestRowStatusEntry
   ACCESS     not-accessible
   STATUS     mandatory
   DESCRIPTION
     "A single entry in the table represents a single 
      lpE3Test component."
   INDEX {
      lpIndex,
      lpE3Index,
      lpE3TestIndex }
::= { lpE3TestRowStatusTable 1 }

LpE3TestRowStatusEntry ::= SEQUENCE {
   lpE3TestRowStatus
      RowStatus,
   lpE3TestComponentName
      DisplayString,
   lpE3TestStorageType
      StorageType,
   lpE3TestIndex
      NonReplicated }

lpE3TestRowStatus OBJECT-TYPE
   SYNTAX     RowStatus 
   ACCESS     read-only
   STATUS     mandatory
   DESCRIPTION
     "This variable is used as the basis for SNMP naming of
      lpE3Test components.
      These components cannot be added nor deleted."
::= { lpE3TestRowStatusEntry 1 }

lpE3TestComponentName OBJECT-TYPE
   SYNTAX     DisplayString 
   ACCESS     read-only
   STATUS     mandatory
   DESCRIPTION
     "This variable provides the component's string name for
      use with the ASCII Console Interface"
::= { lpE3TestRowStatusEntry 2 }

lpE3TestStorageType OBJECT-TYPE
   SYNTAX     StorageType 
   ACCESS     read-only
   STATUS     mandatory
   DESCRIPTION
     "This variable represents the storage type value for the
      lpE3Test tables."
::= { lpE3TestRowStatusEntry 4 }

lpE3TestIndex OBJECT-TYPE
   SYNTAX     NonReplicated 
   ACCESS     not-accessible
   STATUS     mandatory
   DESCRIPTION
     "This variable represents the index for the lpE3Test tables."
::= { lpE3TestRowStatusEntry 10 }

lpE3TestStateTable OBJECT-TYPE
   SYNTAX     SEQUENCE OF LpE3TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpE3Test 10 }

lpE3TestStateEntry OBJECT-TYPE
   SYNTAX     LpE3TestStateEntry
   ACCESS     not-accessible
   STATUS     mandatory
   DESCRIPTION
     "An entry in the lpE3TestStateTable."
   INDEX {
      lpIndex,
      lpE3Index,
      lpE3TestIndex }
::= { lpE3TestStateTable 1 }

LpE3TestStateEntry ::= SEQUENCE {
   lpE3TestAdminState
      INTEGER,
   lpE3TestOperationalState
      INTEGER,
   lpE3TestUsageState
      INTEGER }

lpE3TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpE3TestStateEntry 1 }

lpE3TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpE3TestStateEntry 2 }

lpE3TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpE3TestStateEntry 3 }

lpE3TestSetupTable OBJECT-TYPE
   SYNTAX     SEQUENCE OF LpE3TestSetupEntry
   ACCESS     not-accessible
   STATUS     mandatory
   DESCRIPTION
     "This group contains all of the operational data for a Test 
      component."
::= { lpE3Test 11 }

lpE3TestSetupEntry OBJECT-TYPE
   SYNTAX     LpE3TestSetupEntry
   ACCESS     not-accessible
   STATUS     mandatory
   DESCRIPTION
     "An entry in the lpE3TestSetupTable."
   INDEX {
      lpIndex,
      lpE3Index,
      lpE3TestIndex }
::= { lpE3TestSetupTable 1 }

LpE3TestSetupEntry ::= SEQUENCE {
   lpE3TestPurpose
      AsciiString,
   lpE3TestType
      INTEGER,
   lpE3TestFrmSize
      Unsigned32,
   lpE3TestFrmPatternType
      INTEGER,
   lpE3TestCustomizedPattern
      Hex,
   lpE3TestDataStartDelay
      Unsigned32,
   lpE3TestDisplayInterval
      Unsigned32,
   lpE3TestDuration
      Unsigned32 }

lpE3TestPurpose OBJECT-TYPE
   SYNTAX     AsciiString (SIZE (0..40))
   ACCESS     read-write
   STATUS     mandatory
   DESCRIPTION
     "This attribute records the purpose of the test so that the test results 
      can be associated and properly analyzed."
::= { lpE3TestSetupEntry 1 }

lpE3TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpE3TestSetupEntry 2 }

lpE3TestFrmSize OBJECT-TYPE
   SYNTAX     Unsigned32 (4..4096)
   ACCESS     read-write
   STATUS     mandatory
   DESCRIPTION
     "This attribute defines the size of the test data frames in number of 
      bytes."
   DEFVAL     { 1024 }
::= { lpE3TestSetupEntry 3 }

lpE3TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpE3TestSetupEntry 4 }

lpE3TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpE3TestSetupEntry 5 }

lpE3TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpE3TestSetupEntry 6 }

lpE3TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpE3TestSetupEntry 7 }

lpE3TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpE3TestSetupEntry 8 }

lpE3TestResultsTable OBJECT-TYPE
   SYNTAX     SEQUENCE OF LpE3TestResultsEntry
   ACCESS     not-accessible
   STATUS     mandatory
   DESCRIPTION
     "This group contains all the statistics related attributes of the Test 
      component."
::= { lpE3Test 12 }

lpE3TestResultsEntry OBJECT-TYPE
   SYNTAX     LpE3TestResultsEntry
   ACCESS     not-accessible
   STATUS     mandatory
   DESCRIPTION
     "An entry in the lpE3TestResultsTable."
   INDEX {
      lpIndex,
      lpE3Index,
      lpE3TestIndex }
::= { lpE3TestResultsTable 1 }

LpE3TestResultsEntry ::= SEQUENCE {
   lpE3TestElapsedTime
      Counter32,
   lpE3TestTimeRemaining
      Unsigned32,
   lpE3TestCauseOfTermination
      INTEGER,
   lpE3TestBitsTx
      PassportCounter64,
   lpE3TestBytesTx
      PassportCounter64,
   lpE3TestFrmTx
      PassportCounter64,
   lpE3TestBitsRx
      PassportCounter64,
   lpE3TestBytesRx
      PassportCounter64,
   lpE3TestFrmRx
      PassportCounter64,
   lpE3TestErroredFrmRx
      PassportCounter64,
   lpE3TestBitErrorRate
      AsciiString }

lpE3TestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpE3TestResultsEntry 1 }

lpE3TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpE3TestResultsEntry 2 }

lpE3TestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpE3TestResultsEntry 3 }

lpE3TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpE3TestResultsEntry 4 }

lpE3TestBytesTx OBJECT-TYPE
   SYNTAX     PassportCounter64 
   ACCESS     read-only
   STATUS     mandatory
   DESCRIPTION
     "This attribute is the total number of bytes sent during the test 
      period. This counter is not expected to reach its maximum value."
::= { lpE3TestResultsEntry 5 }

lpE3TestFrmTx OBJECT-TYPE
   SYNTAX     PassportCounter64 
   ACCESS     read-only
   STATUS     mandatory
   DESCRIPTION
     "This attribute is the total number of frames sent during the test 
      period. This counter is not expected to reach its maximum value."
::= { lpE3TestResultsEntry 6 }

lpE3TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpE3TestResultsEntry 7 }

lpE3TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpE3TestResultsEntry 8 }

lpE3TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpE3TestResultsEntry 9 }

lpE3TestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpE3TestResultsEntry 10 }

lpE3TestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpE3TestResultsEntry 11 }


-- G832
-- The G832 component is configured to display all E3 G832 related 
-- operational and statistical data. It will appear under the E3 
-- components when the E3 framing attribute is set to g832.
-- Note: when E3 framing is changed from g832 to g751, the G832 
-- component must be deleted.

lpE3G832 OBJECT IDENTIFIER ::= { lpE3 3 }



lpE3G832RowStatusTable OBJECT-TYPE
   SYNTAX     SEQUENCE OF LpE3G832RowStatusEntry
   ACCESS     not-accessible
   STATUS     mandatory
   DESCRIPTION
     "This entry controls the addition and deletion of 
      lpE3G832 components."
::= { lpE3G832 1 }

lpE3G832RowStatusEntry OBJECT-TYPE
   SYNTAX     LpE3G832RowStatusEntry
   ACCESS     not-accessible
   STATUS     mandatory
   DESCRIPTION
     "A single entry in the table represents a single 
      lpE3G832 component."
   INDEX {
      lpIndex,
      lpE3Index,
      lpE3G832Index }
::= { lpE3G832RowStatusTable 1 }

LpE3G832RowStatusEntry ::= SEQUENCE {
   lpE3G832RowStatus
      RowStatus,
   lpE3G832ComponentName
      DisplayString,
   lpE3G832StorageType
      StorageType,
   lpE3G832Index
      NonReplicated }

lpE3G832RowStatus OBJECT-TYPE
   SYNTAX     RowStatus 
   ACCESS     read-write
   STATUS     mandatory
   DESCRIPTION
     "This variable is used as the basis for SNMP naming of
      lpE3G832 components.
      These components can be added and deleted."
::= { lpE3G832RowStatusEntry 1 }

lpE3G832ComponentName OBJECT-TYPE
   SYNTAX     DisplayString 
   ACCESS     read-only
   STATUS     mandatory
   DESCRIPTION
     "This variable provides the component's string name for
      use with the ASCII Console Interface"
::= { lpE3G832RowStatusEntry 2 }

lpE3G832StorageType OBJECT-TYPE
   SYNTAX     StorageType 
   ACCESS     read-only
   STATUS     mandatory
   DESCRIPTION
     "This variable represents the storage type value for the
      lpE3G832 tables."
::= { lpE3G832RowStatusEntry 4 }

lpE3G832Index OBJECT-TYPE
   SYNTAX     NonReplicated 
   ACCESS     not-accessible
   STATUS     mandatory
   DESCRIPTION
     "This variable represents the index for the lpE3G832 tables."
::= { lpE3G832RowStatusEntry 10 }

lpE3G832ProvisionedTable OBJECT-TYPE
   SYNTAX     SEQUENCE OF LpE3G832ProvisionedEntry
   ACCESS     not-accessible
   STATUS     mandatory
   DESCRIPTION
     "This group contains the provisionable data for the G832 component."
::= { lpE3G832 10 }

lpE3G832ProvisionedEntry OBJECT-TYPE
   SYNTAX     LpE3G832ProvisionedEntry
   ACCESS     not-accessible
   STATUS     mandatory
   DESCRIPTION
     "An entry in the lpE3G832ProvisionedTable."
   INDEX {
      lpIndex,
      lpE3Index,
      lpE3G832Index }
::= { lpE3G832ProvisionedTable 1 }

LpE3G832ProvisionedEntry ::= SEQUENCE {
   lpE3G832TrailTraceTransmitted
      AsciiString,
   lpE3G832TrailTraceExpected
      AsciiString }

lpE3G832TrailTraceTransmitted OBJECT-TYPE
   SYNTAX     AsciiString (SIZE (0..15))
   ACCESS     read-write
   STATUS     mandatory
   DESCRIPTION
     "This attribute indicates the E.164 address which is to be encoded in 
      the trail access point identifier, which is transmitted using the Trail 
      Trace (TR) field of the transmitted E3 Frame. 
      Both the expected trail access point identifier and the transmitted 
      trail access point identifier are provisionable attributes of the G832 
      component.
      The 16 byte Trail Trace frame is composed of one byte containing a 
      frame start marker and a CRC-7 calculation over the previous 
      frame, and 15 bytes for transporting an E.164 address. If less than 
      the full 15 bytes are used, the address is padded with NULL 
      characters."
   DEFVAL     { ''H }  -- ""
::= { lpE3G832ProvisionedEntry 1 }

lpE3G832TrailTraceExpected OBJECT-TYPE
   SYNTAX     AsciiString (SIZE (0..15))
   ACCESS     read-write
   STATUS     mandatory
   DESCRIPTION
     "This attribute indicates the E.164 address which is expected in the 
      trail access point identifier, which is transmitted using the Trail 
      Trace (TR) field of the transmitted E3 Frame. 
      Both the expected trail access point identifier and the transmitted 
      trail access point identifier are provisionable attributes of the G832 
      component.
      The 16 byte Trail Trace frame is composed of one byte containing a 
      frame start marker and a CRC-7 calculation over the previous 
      frame, and 15 bytes for transporting an E.164 address. If less than 
      the full 15 bytes are used, the address is padded with NULL 
      characters."
   DEFVAL     { ''H }  -- ""
::= { lpE3G832ProvisionedEntry 2 }

lpE3G832OperationalTable OBJECT-TYPE
   SYNTAX     SEQUENCE OF LpE3G832OperationalEntry
   ACCESS     not-accessible
   STATUS     mandatory
   DESCRIPTION
     "This group contains the operational data for the G832 component."
::= { lpE3G832 11 }

lpE3G832OperationalEntry OBJECT-TYPE
   SYNTAX     LpE3G832OperationalEntry
   ACCESS     not-accessible
   STATUS     mandatory
   DESCRIPTION
     "An entry in the lpE3G832OperationalTable."
   INDEX {
      lpIndex,
      lpE3Index,
      lpE3G832Index }
::= { lpE3G832OperationalTable 1 }

LpE3G832OperationalEntry ::= SEQUENCE {
   lpE3G832UnexpectedPayloadType
      INTEGER,
   lpE3G832TrailTraceMismatch
      INTEGER,
   lpE3G832TimingMarker
      INTEGER,
   lpE3G832TrailTraceReceived
      AsciiString }

lpE3G832UnexpectedPayloadType OBJECT-TYPE
   SYNTAX     INTEGER  {
                 on(0),
                 off(1) }
   ACCESS     read-only
   STATUS     mandatory
   DESCRIPTION
     "This attribute displays whether the Unexpected Payload Type (UPT) 
      alarm state has been entered. The UPT alarm state is entered when 
      UPT defects have been observed and accumulated for a period of 
      2.5 seconds +/- 0.5 seconds. The UPT defect is reported when a 
      received frame fails to agree with the expected Payload Type. If the 
      UPT defects are intermittently occurring, the UPT defect 
      accumulator is decremented at a rate of 1/10 of the incrementing 
      rate (alarm integration ratio of 1/10), with all measurements based 
      on a 200 ms polling cycle..
      The UPT alarm is cleared when the Payload Type in the received 
      frame agrees with the expected Payload Type for a period of 10 
      seconds +/- 0.5 seconds.
      The unexpectedPayloadType attribute is always set to off when the 
      E3 component has been locked and left offline."
::= { lpE3G832OperationalEntry 1 }

lpE3G832TrailTraceMismatch OBJECT-TYPE
   SYNTAX     INTEGER  {
                 on(0),
                 off(1) }
   ACCESS     read-only
   STATUS     mandatory
   DESCRIPTION
     "This attribute displays whether the Trail Trace Mismatch (TTM) 
      alarm state has been entered. The TTM alarm state is entered when 
      TTM defects have been observed and accumulated for a period of 
      2.5 seconds +/- 0.5 seconds. The TTM defect is reported when the 
      trail access point identifier contained in the Trail Trace (TR) field in 
      the received frame fails to agree with the expected identifier. If the 
      TTM defects are intermittently occurring, the TTM defect 
      accumulator is decremented at a rate of 1/10 of the incrementing 
      rate (alarm integration ratio of 1/10), with all measurements based 
      on a 200 ms polling cycle.
      The TTM alarm is cleared when the trail access point identifier in 
      the received frame agrees with the expected identifier for a period of 
      10 seconds +/- 0.5 seconds.
      The trailTraceMismatch attribute is always set to off when the E3 
      component has been locked and left offline.
      Both the expected trail access identifier and the transmitted trail 
      access identifier are provisionable attributes of the G832 
      component."
::= { lpE3G832OperationalEntry 2 }

lpE3G832TimingMarker OBJECT-TYPE
   SYNTAX     INTEGER  {
                 notTraceable(0),
                 traceable(1) }
   ACCESS     read-only
   STATUS     mandatory
   DESCRIPTION
     "Indicates whether or not the timing source at the far-end node is 
      traceable to a Primary Reference Clock. 
      The timingMarker indication is controlled by the timing marker bit 
      in the G832 MA byte. If the received timing marker bit is 1 for five 
      consecutive frames, and five consecutive 0s are not received for two 
      seconds, the timingMarker indication will be set to not traceable. If 
      the received timing marker bit is 0 for five consecutive frames and 
      five consecutive 1s are not received for two seconds, the 
      timingMarker indication will be set to traceable."
::= { lpE3G832OperationalEntry 3 }

lpE3G832TrailTraceReceived OBJECT-TYPE
   SYNTAX     AsciiString (SIZE (0..15))
   ACCESS     read-only
   STATUS     mandatory
   DESCRIPTION
     "This attribute indicates the 15 byte E.164 address which is currently 
      being received in the trail trace (TR) field of the E3 G832 frame. If 
      this attribute differs from the provisioned trailTraceTransmitted 
      string a trail trace mismatch (TTM) defect is reported, possibly 
      resulting in a TTM alarm, as described for operational attribute 
      trailTraceMismatch."
::= { lpE3G832OperationalEntry 4 }

lpE3G832StatsTable OBJECT-TYPE
   SYNTAX     SEQUENCE OF LpE3G832StatsEntry
   ACCESS     not-accessible
   STATUS     mandatory
   DESCRIPTION
     "This group contains the statistical data for the G832 component. 
      Each attribute type is a non-negative integer which monotonically 
      increases until it reaches a maximum value, at which point it wraps 
      around and starts increasing again from zero."
::= { lpE3G832 12 }

lpE3G832StatsEntry OBJECT-TYPE
   SYNTAX     LpE3G832StatsEntry
   ACCESS     not-accessible
   STATUS     mandatory
   DESCRIPTION
     "An entry in the lpE3G832StatsTable."
   INDEX {
      lpIndex,
      lpE3Index,
      lpE3G832Index }
::= { lpE3G832StatsTable 1 }

LpE3G832StatsEntry ::= SEQUENCE {
   lpE3G832FarEndErrorFreeSec
      Counter32,
   lpE3G832FarEndCodeViolations
      Counter32,
   lpE3G832FarEndErroredSec
      Counter32,
   lpE3G832FarEndSevErroredSec
      Counter32,
   lpE3G832FarEndSefAisSec
      Counter32,
   lpE3G832FarEndUnavailSec
      Counter32 }

lpE3G832FarEndErrorFreeSec OBJECT-TYPE
   SYNTAX     Counter32 
   ACCESS     read-only
   STATUS     mandatory
   DESCRIPTION
     "This attribute indicates the number of seconds that the E3 line has 
      not suffered any G832 errors."
::= { lpE3G832StatsEntry 1 }

lpE3G832FarEndCodeViolations OBJECT-TYPE
   SYNTAX     Counter32 
   ACCESS     read-only
   STATUS     mandatory
   DESCRIPTION
     "A count of E3 frames containing a Far-End Block Error (FEBE). A 
      FEBE is reported over the FEBE bit each time the far-end terminal 
      detects a BIP-8 error in a received E3 frame. For second intervals 
      where Far End Unavailable Seconds (FEUAS) or Far End Severely 
      Errored Seconds (FESES) are counted, counting of FECVs is 
      inhibited.
      This attribute is a non-negative integer which monotonically 
      increases until it reaches a maximum value, at which point it wraps 
      around and starts increasing again from zero."
::= { lpE3G832StatsEntry 2 }

lpE3G832FarEndErroredSec OBJECT-TYPE
   SYNTAX     Counter32 
   ACCESS     read-only
   STATUS     mandatory
   DESCRIPTION
     "This attribute indicates the total number of Far-End Errored 
      Seconds (FEES). A FEES is declared for second intervals 
      containing with one or more Far-End Coding Violations (FECV) or 
      one or more Far-End Receive Failure (FERF) defects. A FERF 
      defect occurs when the FERF bit in the received frame is set to one. 
      For second intervals where Far End Unavailable Seconds (FEUAS) 
      are counted, counting of FEESs is inhibited."
::= { lpE3G832StatsEntry 3 }

lpE3G832FarEndSevErroredSec OBJECT-TYPE
   SYNTAX     Counter32 
   ACCESS     read-only
   STATUS     mandatory
   DESCRIPTION
     "This attribute indicates the total number of Far-End Severely 
      Errored Seconds (FESESs). A FESES is declared for second 
      intervals containing more than 34 Far-End Coding Violations 
      (FECV) or one or more Far-End Receive Failure (FERF) defects. 
      For second intervals where a Far-End Severely Errored Seconds 
      (FESES) is counted, counting of FECVs is inhibited. For second 
      intervals where Far End Unavailable Seconds (FEUAS) are counted, 
      counting of FESESs is inhibited."
::= { lpE3G832StatsEntry 4 }

lpE3G832FarEndSefAisSec OBJECT-TYPE
   SYNTAX     Counter32 
   ACCESS     read-only
   STATUS     mandatory
   DESCRIPTION
     "This attribute indicates the total number of Far-End SEF/AIS 
      Seconds (FESAS). A FESAS is declared for second intervals 
      containing one or more Far-End Receive Failure (FERF) defects. 
      For second intervals where Far End Unavailable Seconds (FEUAS) 
      are counted, counting of FESAS is inhibited."
::= { lpE3G832StatsEntry 5 }

lpE3G832FarEndUnavailSec OBJECT-TYPE
   SYNTAX     Counter32 
   ACCESS     read-only
   STATUS     mandatory
   DESCRIPTION
     "This attribute indicates the total number of one second intervals for 
      which the E3 far-end path is unavailable. The E3 far-end path 
      becomes unavailable at the onset of 10 consecutive Far End 
      Severely Errored Seconds (FESES). It comes available at the onset 
      of 10 contiguous seconds with no FESES. The unavailable time 
      includes the initial 10 seconds to enter the unavailable state but not 
      the 10 seconds to exit the state For second intervals where FEUAS 
      is counted, counting of Far End Coding Violations (FECV), Far-
      End Errored Seconds (FEES), Far-End Severely Errored Seconds 
      (FESES) and Far-End SefAis Seconds (FESAS) are inhibited."
::= { lpE3G832StatsEntry 6 }


-- LP/n DS3/n PLCP
-- LP/n E3/n PLCP
-- The PLCP component is configured to display all DS3/E3 PLCP 
-- related operational and statistical data. It will appear under the DS3 
-- or E3 components when the mapping attribute is set to plcp.

lpE3Plcp OBJECT IDENTIFIER ::= { lpE3 4 }



lpE3PlcpRowStatusTable OBJECT-TYPE
   SYNTAX     SEQUENCE OF LpE3PlcpRowStatusEntry
   ACCESS     not-accessible
   STATUS     mandatory
   DESCRIPTION
     "This entry controls the addition and deletion of 
      lpE3Plcp components."
::= { lpE3Plcp 1 }

lpE3PlcpRowStatusEntry OBJECT-TYPE
   SYNTAX     LpE3PlcpRowStatusEntry
   ACCESS     not-accessible
   STATUS     mandatory
   DESCRIPTION
     "A single entry in the table represents a single 
      lpE3Plcp component."
   INDEX {
      lpIndex,
      lpE3Index,
      lpE3PlcpIndex }
::= { lpE3PlcpRowStatusTable 1 }

LpE3PlcpRowStatusEntry ::= SEQUENCE {
   lpE3PlcpRowStatus
      RowStatus,
   lpE3PlcpComponentName
      DisplayString,
   lpE3PlcpStorageType
      StorageType,
   lpE3PlcpIndex
      NonReplicated }

lpE3PlcpRowStatus OBJECT-TYPE
   SYNTAX     RowStatus 
   ACCESS     read-only
   STATUS     mandatory
   DESCRIPTION
     "This variable is used as the basis for SNMP naming of
      lpE3Plcp components.
      These components cannot be added nor deleted."
::= { lpE3PlcpRowStatusEntry 1 }

lpE3PlcpComponentName OBJECT-TYPE
   SYNTAX     DisplayString 
   ACCESS     read-only
   STATUS     mandatory
   DESCRIPTION
     "This variable provides the component's string name for
      use with the ASCII Console Interface"
::= { lpE3PlcpRowStatusEntry 2 }

lpE3PlcpStorageType OBJECT-TYPE
   SYNTAX     StorageType 
   ACCESS     read-only
   STATUS     mandatory
   DESCRIPTION
     "This variable represents the storage type value for the
      lpE3Plcp tables."
::= { lpE3PlcpRowStatusEntry 4 }

lpE3PlcpIndex OBJECT-TYPE
   SYNTAX     NonReplicated 
   ACCESS     not-accessible
   STATUS     mandatory
   DESCRIPTION
     "This variable represents the index for the lpE3Plcp tables."
::= { lpE3PlcpRowStatusEntry 10 }

lpE3PlcpOperationalTable OBJECT-TYPE
   SYNTAX     SEQUENCE OF LpE3PlcpOperationalEntry
   ACCESS     not-accessible
   STATUS     mandatory
   DESCRIPTION
     "This group contains the operational data for the PLCP component."
::= { lpE3Plcp 10 }

lpE3PlcpOperationalEntry OBJECT-TYPE
   SYNTAX     LpE3PlcpOperationalEntry
   ACCESS     not-accessible
   STATUS     mandatory
   DESCRIPTION
     "An entry in the lpE3PlcpOperationalTable."
   INDEX {
      lpIndex,
      lpE3Index,
      lpE3PlcpIndex }
::= { lpE3PlcpOperationalTable 1 }

LpE3PlcpOperationalEntry ::= SEQUENCE {
   lpE3PlcpLofAlarm
      INTEGER,
   lpE3PlcpRxRaiAlarm
      INTEGER }

lpE3PlcpLofAlarm OBJECT-TYPE
   SYNTAX     INTEGER  {
                 on(0),
                 off(1) }
   ACCESS     read-only
   STATUS     mandatory
   DESCRIPTION
     "This attribute displays whether a PLCP Loss Of Frame (LOF) 
      failure alarm state has been entered. An LOF failure is declared 
      when a PLCP LOF defect persists for 2.5 s +/- 0.5 s. An LOF defect 
      occurs when an OOF (Out of Frame) state persists for more than 1 
      ms. If the OOF events are intermittent, the LOF defect counter is 
      decremented at a rate of 1/12 (for DS3 PLCP) or 1/9 (for G.751 E3 
      PLCP) of the incrementing rate, with all measurements based on a 
      200 ms polling cycle. An OOF event (also known as a PLCP SEF 
      event) is declared when an error is detected in both the A1 and A2 
      octets, or when two consecutive POHIDs are found in error.
      OOF is removed when two valid sets of framing octets and two 
      valid and sequential POHID octets have been found. The LOF 
      defect is removed when the defect counter reaches zero, i.e. when 
      OOF events are absent for more than 12 ms (DS3 PLCP) or 9 ms 
      (G.751 E3 PLCP). LOF failure alarm is cleared when LOF defect is 
      absent for 10.0 s +/- 0.5 s
      The DS3 or E3 component goes into an operational state of disabled 
      until the LOF failure alarm is cleared. The terminal declaring the 
      LOF failure alarm will transmit a PLCP RAI signal to the far-end 
      for the duration of the alarm.
      The lofAlarm attribute is always set to off when the DS3 or E3 
      component has been locked and left offline."
   DEFVAL     { off }
::= { lpE3PlcpOperationalEntry 1 }

lpE3PlcpRxRaiAlarm OBJECT-TYPE
   SYNTAX     INTEGER  {
                 on(0),
                 off(1) }
   ACCESS     read-only
   STATUS     mandatory
   DESCRIPTION
     "This attribute displays whether a PLCP Remote Alarm Indication 
      (RAI) failure alarm state has been entered. An RAI failure alarm 
      occurs when ten consecutive PLCP RAI bits (bit 5 in the G1 byte) 
      are high on the incoming line. An RAI failure alarm is cleared when 
      ten consecutive RAI bits are set to 0.
      Note: Some standards call this alarm RFI.
      The rxRaiAlarm attribute is always set to off when the DS3 or E3 
      component has been locked and left offline."
   DEFVAL     { off }
::= { lpE3PlcpOperationalEntry 2 }

lpE3PlcpStatsTable OBJECT-TYPE
   SYNTAX     SEQUENCE OF LpE3PlcpStatsEntry
   ACCESS     not-accessible
   STATUS     mandatory
   DESCRIPTION
     "This group contains the statistical data for the PLCP component. 
      Each attribute type is a non-negative integer which monotonically 
      increases until it reaches a maximum value, at which point it wraps 
      around and starts increasing again from zero."
::= { lpE3Plcp 11 }

lpE3PlcpStatsEntry OBJECT-TYPE
   SYNTAX     LpE3PlcpStatsEntry
   ACCESS     not-accessible
   STATUS     mandatory
   DESCRIPTION
     "An entry in the lpE3PlcpStatsTable."
   INDEX {
      lpIndex,
      lpE3Index,
      lpE3PlcpIndex }
::= { lpE3PlcpStatsTable 1 }

LpE3PlcpStatsEntry ::= SEQUENCE {
   lpE3PlcpErrorFreeSec
      Counter32,
   lpE3PlcpCodingViolations
      Counter32,
   lpE3PlcpErroredSec
      Counter32,
   lpE3PlcpSevErroredSec
      Counter32,
   lpE3PlcpSevErroredFramingSec
      Counter32,
   lpE3PlcpUnavailSec
      Counter32,
   lpE3PlcpFarEndErrorFreeSec
      Counter32,
   lpE3PlcpFarEndCodingViolations
      Counter32,
   lpE3PlcpFarEndErroredSec
      Counter32,
   lpE3PlcpFarEndSevErroredSec
      Counter32,
   lpE3PlcpFarEndUnavailableSec
      Counter32 }

lpE3PlcpErrorFreeSec OBJECT-TYPE
   SYNTAX     Counter32 
   ACCESS     read-only
   STATUS     mandatory
   DESCRIPTION
     "This attribute indicates the number of seconds during which the 
      near-end PLCP path layer had no errors."
::= { lpE3PlcpStatsEntry 1 }

lpE3PlcpCodingViolations OBJECT-TYPE
   SYNTAX     Counter32 
   ACCESS     read-only
   STATUS     mandatory
   DESCRIPTION
     "This attribute indicates the total number of BIP-8 Errors, framing 
      pattern octet errors, and path overhead identification errors detected 
      in received PLCP frames. 
      Counting of PLCP CV is inhibited for second intervals where PLCP 
      Severely Errored Framing Seconds (SEFS) or PLCP Unavailable 
      Seconds (UAS) are counted.
      This attribute is a non-negative integer which monotonically 
      increases until it reaches a maximum value, at which point it wraps 
      around and starts increasing again from zero."
::= { lpE3PlcpStatsEntry 2 }

lpE3PlcpErroredSec OBJECT-TYPE
   SYNTAX     Counter32 
   ACCESS     read-only
   STATUS     mandatory
   DESCRIPTION
     "This attribute indicates the number of seconds containing one or 
      more PLCP Coding Violations (CV) or in which a PLCP Severely 
      Errored Framing Second (SEFS) was counted. 
      Counting of PLCP ES is inhibited during second intervals where 
      PLCP Unavailable Seconds (UAS) are counted."
::= { lpE3PlcpStatsEntry 3 }

lpE3PlcpSevErroredSec OBJECT-TYPE
   SYNTAX     Counter32 
   ACCESS     read-only
   STATUS     mandatory
   DESCRIPTION
     "This attribute indicates the number of seconds containing 5 or more 
      PLCPCVs or in which a PLCPSEFS was counted (i.e. a PLCP OOF 
      event occurred). 
      Counting of PLCP SES is inhibited during second intervals where 
      PLCP Unavailable Seconds (UAS) are counted."
::= { lpE3PlcpStatsEntry 4 }

lpE3PlcpSevErroredFramingSec OBJECT-TYPE
   SYNTAX     Counter32 
   ACCESS     read-only
   STATUS     mandatory
   DESCRIPTION
     "This attribute indicates the number of seconds containing one or 
      more PLCP Severely Errored Frame (SEF) events. An SEF event is 
      equivalent to a PLCP OOF (Out of Frame) event.
      Counting of PLCPP SEFSs is inhibited for second intervals where 
      PLCP Unavailable Seconds (UAS) are counted."
::= { lpE3PlcpStatsEntry 5 }

lpE3PlcpUnavailSec OBJECT-TYPE
   SYNTAX     Counter32 
   ACCESS     read-only
   STATUS     mandatory
   DESCRIPTION
     "This attribute indicates the number of seconds when the near-end 
      PLCP layer is unavailable. The PLCP Path Layer becomes 
      unavailable at the declaration of PLCP LOF (Loss of Frame) failure 
      alarm state. The PLCP Path Layer becomes available again only 
      after clearing this condition.
      For second intervals where PLCP UAS are counted, counting of 
      PLCP Severely Errored Framing Seconds (SEFS), PLCP Coding 
      Violations (CV), PLCP Errored Seconds (ES), PLCP Severely 
      Errored Seconds (SES) and PLCP Far-End Severely Errored 
      Seconds (FESES) is inhibited."
::= { lpE3PlcpStatsEntry 6 }

lpE3PlcpFarEndErrorFreeSec OBJECT-TYPE
   SYNTAX     Counter32 
   ACCESS     read-only
   STATUS     mandatory
   DESCRIPTION
     "This attribute indicates the number of seconds during which the far-
      end PLCP path layer had no errors."
::= { lpE3PlcpStatsEntry 7 }

lpE3PlcpFarEndCodingViolations OBJECT-TYPE
   SYNTAX     Counter32 
   ACCESS     read-only
   STATUS     mandatory
   DESCRIPTION
     "This attribute indicates the total number of PLCP Far-End Block 
      Errors (FEBE) reported by the far-end terminal. 
      Counting of FEBEs is inhibited for second intervals where PLCP 
      Far-End Unavailable Seconds (FEUAS) are counted.
      This attribute is a non-negative integer which monotonically 
      increases until it reaches a maximum value, at which point it wraps 
      around and starts increasing again from zero."
::= { lpE3PlcpStatsEntry 8 }

lpE3PlcpFarEndErroredSec OBJECT-TYPE
   SYNTAX     Counter32 
   ACCESS     read-only
   STATUS     mandatory
   DESCRIPTION
     "This attribute indicates the number of seconds containing one or 
      more PLCP Far-End Coding Violations (FECV).
      Counting of PLCP FEES is inhibited during second intervals where 
      PLCP Far-End Unavailable Seconds (FEUAS) are counted."
::= { lpE3PlcpStatsEntry 9 }

lpE3PlcpFarEndSevErroredSec OBJECT-TYPE
   SYNTAX     Counter32 
   ACCESS     read-only
   STATUS     mandatory
   DESCRIPTION
     "This attribute indicates the number of seconds containing 5 or more 
      PLCP Far-End Coding Violations (FECV). 
      Counting of PLCP FESES is inhibited for second intervals where 
      PLCP Far-End Unavailable Seconds (FEUAS) are counted."
::= { lpE3PlcpStatsEntry 10 }

lpE3PlcpFarEndUnavailableSec OBJECT-TYPE
   SYNTAX     Counter32 
   ACCESS     read-only
   STATUS     mandatory
   DESCRIPTION
     "This attribute indicates the number of seconds during which the 
      PLCP far end is unavailable. The PLCP Path Layer becomes 
      unavailable at the declaration of PLCP RAI (Remote Alarm 
      Indication). Service becomes available again after this condition is 
      cleared. For second intervals where PLCP FEUAS are counted, 
      counting of PLCP Far-End Coding Violations (FECV), PLCP Far-
      End Errored Seconds (FEES), and PLCP Far-End Severely Errored 
      Seconds (FESES) is inhibited."
::= { lpE3PlcpStatsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

lpE3Cell OBJECT IDENTIFIER ::= { lpE3 5 }



lpE3CellRowStatusTable OBJECT-TYPE
   SYNTAX     SEQUENCE OF LpE3CellRowStatusEntry
   ACCESS     not-accessible
   STATUS     mandatory
   DESCRIPTION
     "This entry controls the addition and deletion of 
      lpE3Cell components."
::= { lpE3Cell 1 }

lpE3CellRowStatusEntry OBJECT-TYPE
   SYNTAX     LpE3CellRowStatusEntry
   ACCESS     not-accessible
   STATUS     mandatory
   DESCRIPTION
     "A single entry in the table represents a single 
      lpE3Cell component."
   INDEX {
      lpIndex,
      lpE3Index,
      lpE3CellIndex }
::= { lpE3CellRowStatusTable 1 }

LpE3CellRowStatusEntry ::= SEQUENCE {
   lpE3CellRowStatus
      RowStatus,
   lpE3CellComponentName
      DisplayString,
   lpE3CellStorageType
      StorageType,
   lpE3CellIndex
      NonReplicated }

lpE3CellRowStatus OBJECT-TYPE
   SYNTAX     RowStatus 
   ACCESS     read-write
   STATUS     mandatory
   DESCRIPTION
     "This variable is used as the basis for SNMP naming of
      lpE3Cell components.
      These components can be added and deleted."
::= { lpE3CellRowStatusEntry 1 }

lpE3CellComponentName OBJECT-TYPE
   SYNTAX     DisplayString 
   ACCESS     read-only
   STATUS     mandatory
   DESCRIPTION
     "This variable provides the component's string name for
      use with the ASCII Console Interface"
::= { lpE3CellRowStatusEntry 2 }

lpE3CellStorageType OBJECT-TYPE
   SYNTAX     StorageType 
   ACCESS     read-only
   STATUS     mandatory
   DESCRIPTION
     "This variable represents the storage type value for the
      lpE3Cell tables."
::= { lpE3CellRowStatusEntry 4 }

lpE3CellIndex OBJECT-TYPE
   SYNTAX     NonReplicated 
   ACCESS     not-accessible
   STATUS     mandatory
   DESCRIPTION
     "This variable represents the index for the lpE3Cell tables."
::= { lpE3CellRowStatusEntry 10 }

lpE3CellProvTable OBJECT-TYPE
   SYNTAX     SEQUENCE OF LpE3CellProvEntry
   ACCESS     not-accessible
   STATUS     mandatory
   DESCRIPTION
     "This group contains the provisioning attributes for the AtmCell 
      component."
::= { lpE3Cell 10 }

lpE3CellProvEntry OBJECT-TYPE
   SYNTAX     LpE3CellProvEntry
   ACCESS     not-accessible
   STATUS     mandatory
   DESCRIPTION
     "An entry in the lpE3CellProvTable."
   INDEX {
      lpIndex,
      lpE3Index,
      lpE3CellIndex }
::= { lpE3CellProvTable 1 }

LpE3CellProvEntry ::= SEQUENCE {
   lpE3CellAlarmActDelay
      Unsigned32,
   lpE3CellScrambleCellPayload
      INTEGER,
   lpE3CellCorrectSingleBitHeaderErrors
      INTEGER }

lpE3CellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { lpE3CellProvEntry 1 }

lpE3CellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { lpE3CellProvEntry 2 }

lpE3CellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { lpE3CellProvEntry 3 }

lpE3CellOperTable OBJECT-TYPE
   SYNTAX     SEQUENCE OF LpE3CellOperEntry
   ACCESS     not-accessible
   STATUS     mandatory
   DESCRIPTION
     "This group contains the common operational attributes for the 
      AtmCell component."
::= { lpE3Cell 11 }

lpE3CellOperEntry OBJECT-TYPE
   SYNTAX     LpE3CellOperEntry
   ACCESS     not-accessible
   STATUS     mandatory
   DESCRIPTION
     "An entry in the lpE3CellOperTable."
   INDEX {
      lpIndex,
      lpE3Index,
      lpE3CellIndex }
::= { lpE3CellOperTable 1 }

LpE3CellOperEntry ::= SEQUENCE {
   lpE3CellLcdAlarm
      INTEGER }

lpE3CellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { lpE3CellOperEntry 1 }

lpE3CellStatsTable OBJECT-TYPE
   SYNTAX     SEQUENCE OF LpE3CellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { lpE3Cell 12 }

lpE3CellStatsEntry OBJECT-TYPE
   SYNTAX     LpE3CellStatsEntry
   ACCESS     not-accessible
   STATUS     mandatory
   DESCRIPTION
     "An entry in the lpE3CellStatsTable."
   INDEX {
      lpIndex,
      lpE3Index,
      lpE3CellIndex }
::= { lpE3CellStatsTable 1 }

LpE3CellStatsEntry ::= SEQUENCE {
   lpE3CellUncorrectableHecErrors
      Counter32,
   lpE3CellSevErroredSec
      Counter32,
   lpE3CellReceiveCellUtilization
      Gauge32,
   lpE3CellTransmitCellUtilization
      Gauge32,
   lpE3CellCorrectableHeaderErrors
      Counter32 }

lpE3CellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { lpE3CellStatsEntry 1 }

lpE3CellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { lpE3CellStatsEntry 2 }

lpE3CellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { lpE3CellStatsEntry 3 }

lpE3CellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { lpE3CellStatsEntry 4 }

lpE3CellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { lpE3CellStatsEntry 5 }


-- Lp/n DS1/n
-- The DS1 component controls and monitors a DS1 port on a DS1 
-- Function Processor. Frame-based cards support up to eight ports, 
-- cell-based cards support up to eight ports, and AAL1 cards support 
-- up to four ports.

lpDS1 OBJECT IDENTIFIER ::= { lp 7 }



lpDS1RowStatusTable OBJECT-TYPE
   SYNTAX     SEQUENCE OF LpDS1RowStatusEntry
   ACCESS     not-accessible
   STATUS     mandatory
   DESCRIPTION
     "This entry controls the addition and deletion of 
      lpDS1 components."
::= { lpDS1 1 }

lpDS1RowStatusEntry OBJECT-TYPE
   SYNTAX     LpDS1RowStatusEntry
   ACCESS     not-accessible
   STATUS     mandatory
   DESCRIPTION
     "A single entry in the table represents a single 
      lpDS1 component."
   INDEX {
      lpIndex,
      lpDS1Index }
::= { lpDS1RowStatusTable 1 }

LpDS1RowStatusEntry ::= SEQUENCE {
   lpDS1RowStatus
      RowStatus,
   lpDS1ComponentName
      DisplayString,
   lpDS1StorageType
      StorageType,
   lpDS1Index
      Integer32 }

lpDS1RowStatus OBJECT-TYPE
   SYNTAX     RowStatus 
   ACCESS     read-write
   STATUS     mandatory
   DESCRIPTION
     "This variable is used as the basis for SNMP naming of
      lpDS1 components.
      These components can be added and deleted."
::= { lpDS1RowStatusEntry 1 }

lpDS1ComponentName OBJECT-TYPE
   SYNTAX     DisplayString 
   ACCESS     read-only
   STATUS     mandatory
   DESCRIPTION
     "This variable provides the component's string name for
      use with the ASCII Console Interface"
::= { lpDS1RowStatusEntry 2 }

lpDS1StorageType OBJECT-TYPE
   SYNTAX     StorageType 
   ACCESS     read-only
   STATUS     mandatory
   DESCRIPTION
     "This variable represents the storage type value for the
      lpDS1 tables."
::= { lpDS1RowStatusEntry 4 }

lpDS1Index OBJECT-TYPE
   SYNTAX     Integer32 (0..7)
   ACCESS     not-accessible
   STATUS     mandatory
   DESCRIPTION
     "This variable represents the index for the lpDS1 tables."
::= { lpDS1RowStatusEntry 10 }

lpDS1ProvTable OBJECT-TYPE
   SYNTAX     SEQUENCE OF LpDS1ProvEntry
   ACCESS     not-accessible
   STATUS     mandatory
   DESCRIPTION
     "This group contains all of the provisioning data for a DS1 
      component."
::= { lpDS1 10 }

lpDS1ProvEntry OBJECT-TYPE
   SYNTAX     LpDS1ProvEntry
   ACCESS     not-accessible
   STATUS     mandatory
   DESCRIPTION
     "An entry in the lpDS1ProvTable."
   INDEX {
      lpIndex,
      lpDS1Index }
::= { lpDS1ProvTable 1 }

LpDS1ProvEntry ::= SEQUENCE {
   lpDS1LineType
      INTEGER,
   lpDS1ZeroCoding
      INTEGER,
   lpDS1ClockingSource
      INTEGER,
   lpDS1RaiAlarmType
      INTEGER,
   lpDS1LineLength
      Unsigned32 }

lpDS1LineType OBJECT-TYPE
   SYNTAX     INTEGER  {
                 d4(0),
                 esf(1),
                 d4Cas(4),
                 esfCas(5),
                 unframed(6) }
   ACCESS     read-write
   STATUS     mandatory
   DESCRIPTION
     "This attribute defines the framing of the DS1 line.
      d4 defines a framing pattern of 12 frames per multiframe.
      esf defines a framing pattern of 24 frames per multiframe.
      d4Cas defines a framing pattern of 12 frames per multiframe with 
      channel associated signalling.
      esfCas defines a framing pattern of 24 frames per multiframe with 
      channel associated signalling.
      unframed defines an unknown framing pattern for clear channels.
      For cell-based cards only the default option esf is permitted."
   DEFVAL     { esf }
::= { lpDS1ProvEntry 1 }

lpDS1ZeroCoding OBJECT-TYPE
   SYNTAX     INTEGER  {
                 bit7Stuffing(0),
                 b8zs(1),
                 ami(2) }
   ACCESS     read-write
   STATUS     mandatory
   DESCRIPTION
     "This attribute defines the zero encoding on the DS1 line.
      bit7Stuffing sets bit 7 of every timeslot to a one to guarantee ones's 
      density. This reduces the available bandwidth of the channel by 1/8.
      b8zs substitutes a pattern of bipolar violations if more than 7 zeros 
      in a row are to be transported.
      ami specifies Alternate Mark Inversion, in which successive marks 
      (ones) alternate between positive and negative polarity voltage 
      signals, and spaces (zeros) are sent as a zero amplitude signal.
      When zeroCoding is set to ami and lineType is set to d4, it is 
      recommended that raiAlarmType be set to SBit in order to avoid 
      possible mimic RAI alarm.
      For cell-based cards only the default value b8zs is permitted."
   DEFVAL     { b8zs }
::= { lpDS1ProvEntry 2 }

lpDS1ClockingSource OBJECT-TYPE
   SYNTAX     INTEGER  {
                 local(0),
                 line(1),
                 module(2),
                 otherPort(3),
                 srtsMode(4) }
   ACCESS     read-write
   STATUS     mandatory
   DESCRIPTION
     "This attribute defines the source of the transmit clock for the DS1 
      line.
      When local is selected, the crystal on the port generates the 
      clocking for the line.
      When line is selected, the port synchronizes to the clock from the 
      facility.
      When module is selected, the ports clock synchronizes to the clock 
      provided by the oscillator on the active CP.
      When otherPort is selected, the port synchronizes to the port with a 
      clocking source of line.
      When srtsMode is selected, the port synchronization is taken from 
      the SRTS (Synchronous Residual Time-Stamp) bits extracted from 
      the AAL1 cells. This option is only available for unstructured 
      AAL1 data services when the other ports on the card have their 
      clocking source set to module.
      If the NetworkSynchronization (NS) component is present the 
      default value of this attribute will be module otherwise it will 
      default to local.
      Note that 3pDS1Atm cards have one common clock source for all 
      ports and do not support the line clock source; all three ports must 
      have the same value, either local or module."
::= { lpDS1ProvEntry 3 }

lpDS1RaiAlarmType OBJECT-TYPE
   SYNTAX     INTEGER  {
                 sBit(0),
                 bit2(1),
                 fdl(2) }
   ACCESS     read-write
   STATUS     mandatory
   DESCRIPTION
     "This attribute defines the method of sending a RAI (Remote Alarm 
      Indication) alarm on a DS1 line.
      When SBit is selected, RAI alarm is sent by setting the S bit in 
      frame 12.
      When Bit2 is selected, RAI alarm is sent by setting bit 2 in all 
      timeslots to 0.
      When fdl is selected, RAI alarm is sent by a repeating pattern of 00 
      hex and FF hex on the FDL link.
      Note that for lineType of d4, only the SBit and the Bit2 methods are 
      applicable. Whereas for lineType of esf, only the Bit2 and the fdl 
      methods are applicable.
      SBit method is recommended if lineType is set to d4 and 
      zeroCoding is set to ami. This will help to avoid potential mimic 
      RAI alarm when 1's density is too low in the data transmitted.
      For cell-based cards only the default value fdl is permitted."
   DEFVAL     { fdl }
::= { lpDS1ProvEntry 4 }

lpDS1LineLength OBJECT-TYPE
   SYNTAX     Unsigned32 (0..655)
   ACCESS     read-write
   STATUS     mandatory
   DESCRIPTION
     "This attribute defines the line length (in feet) for equalization 
      calculations for the DS1 line. The value ranges between 0-655. For 
      8pDS1Atm cards the actual value used for equalization is rounded 
      up to the nearest 110 feet; for all other card types the actual value 
      used is rounded to the nearest 50 feet."
   DEFVAL     { 0 }
::= { lpDS1ProvEntry 5 }

lpDS1CidDataTable OBJECT-TYPE
   SYNTAX     SEQUENCE OF LpDS1CidDataEntry
   ACCESS     not-accessible
   STATUS     mandatory
   DESCRIPTION
     "This group contains the attribute for a component's Customer 
      Identifier (CID). Refer to the attribute description for a detailed 
      explanation of CIDs."
::= { lpDS1 11 }

lpDS1CidDataEntry OBJECT-TYPE
   SYNTAX     LpDS1CidDataEntry
   ACCESS     not-accessible
   STATUS     mandatory
   DESCRIPTION
     "An entry in the lpDS1CidDataTable."
   INDEX {
      lpIndex,
      lpDS1Index }
::= { lpDS1CidDataTable 1 }

LpDS1CidDataEntry ::= SEQUENCE {
   lpDS1CustomerIdentifier
      Unsigned32 }

lpDS1CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpDS1CidDataEntry 1 }

lpDS1AdminInfoTable OBJECT-TYPE
   SYNTAX     SEQUENCE OF LpDS1AdminInfoEntry
   ACCESS     not-accessible
   STATUS     mandatory
   DESCRIPTION
     "This group contains the attributes pertaining to the vendor of the 
      equipment."
::= { lpDS1 12 }

lpDS1AdminInfoEntry OBJECT-TYPE
   SYNTAX     LpDS1AdminInfoEntry
   ACCESS     not-accessible
   STATUS     mandatory
   DESCRIPTION
     "An entry in the lpDS1AdminInfoTable."
   INDEX {
      lpIndex,
      lpDS1Index }
::= { lpDS1AdminInfoTable 1 }

LpDS1AdminInfoEntry ::= SEQUENCE {
   lpDS1Vendor
      AsciiString,
   lpDS1CommentText
      AsciiString }

lpDS1Vendor OBJECT-TYPE
   SYNTAX     AsciiString (SIZE (0..20))
   ACCESS     read-write
   STATUS     mandatory
   DESCRIPTION
     "This is the name of the vendor supplying the facility."
::= { lpDS1AdminInfoEntry 1 }

lpDS1CommentText OBJECT-TYPE
   SYNTAX     AsciiString (SIZE (0..60))
   ACCESS     read-write
   STATUS     mandatory
   DESCRIPTION
     "Any miscellaneous text about the facility."
::= { lpDS1AdminInfoEntry 2 }

lpDS1IfEntryTable OBJECT-TYPE
   SYNTAX     SEQUENCE OF LpDS1IfEntryEntry
   ACCESS     not-accessible
   STATUS     mandatory
   DESCRIPTION
     "This group contains the provisionable attributes for the ifEntry."
::= { lpDS1 13 }

lpDS1IfEntryEntry OBJECT-TYPE
   SYNTAX     LpDS1IfEntryEntry
   ACCESS     not-accessible
   STATUS     mandatory
   DESCRIPTION
     "An entry in the lpDS1IfEntryTable."
   INDEX {
      lpIndex,
      lpDS1Index }
::= { lpDS1IfEntryTable 1 }

LpDS1IfEntryEntry ::= SEQUENCE {
   lpDS1IfAdminStatus
      INTEGER,
   lpDS1IfIndex
      InterfaceIndex }

lpDS1IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpDS1IfEntryEntry 1 }

lpDS1IfIndex OBJECT-TYPE
   SYNTAX     InterfaceIndex (1..65535)
   ACCESS     read-only
   STATUS     mandatory
   DESCRIPTION
     "This is the index for the IfEntry. Its value is automatically initialized 
      during the provisioning process."
::= { lpDS1IfEntryEntry 2 }

lpDS1OperStatusTable OBJECT-TYPE
   SYNTAX     SEQUENCE OF LpDS1OperStatusEntry
   ACCESS     not-accessible
   STATUS     mandatory
   DESCRIPTION
     "This group includes the Operational Status attribute. This attribute 
      defines the current operational state of this component."
::= { lpDS1 14 }

lpDS1OperStatusEntry OBJECT-TYPE
   SYNTAX     LpDS1OperStatusEntry
   ACCESS     not-accessible
   STATUS     mandatory
   DESCRIPTION
     "An entry in the lpDS1OperStatusTable."
   INDEX {
      lpIndex,
      lpDS1Index }
::= { lpDS1OperStatusTable 1 }

LpDS1OperStatusEntry ::= SEQUENCE {
   lpDS1SnmpOperStatus
      INTEGER }

lpDS1SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpDS1OperStatusEntry 1 }

lpDS1StateTable OBJECT-TYPE
   SYNTAX     SEQUENCE OF LpDS1StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpDS1 15 }

lpDS1StateEntry OBJECT-TYPE
   SYNTAX     LpDS1StateEntry
   ACCESS     not-accessible
   STATUS     mandatory
   DESCRIPTION
     "An entry in the lpDS1StateTable."
   INDEX {
      lpIndex,
      lpDS1Index }
::= { lpDS1StateTable 1 }

LpDS1StateEntry ::= SEQUENCE {
   lpDS1AdminState
      INTEGER,
   lpDS1OperationalState
      INTEGER,
   lpDS1UsageState
      INTEGER,
   lpDS1AvailabilityStatus
      OCTET STRING,
   lpDS1ProceduralStatus
      OCTET STRING,
   lpDS1ControlStatus
      OCTET STRING,
   lpDS1AlarmStatus
      OCTET STRING,
   lpDS1StandbyStatus
      INTEGER,
   lpDS1UnknownStatus
      INTEGER }

lpDS1AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpDS1StateEntry 1 }

lpDS1OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpDS1StateEntry 2 }

lpDS1UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpDS1StateEntry 3 }

lpDS1AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpDS1StateEntry 4 }

lpDS1ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpDS1StateEntry 5 }

lpDS1ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpDS1StateEntry 6 }

lpDS1AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpDS1StateEntry 7 }

lpDS1StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpDS1StateEntry 8 }

lpDS1UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpDS1StateEntry 9 }

lpDS1OperTable OBJECT-TYPE
   SYNTAX     SEQUENCE OF LpDS1OperEntry
   ACCESS     not-accessible
   STATUS     mandatory
   DESCRIPTION
     "This group contains the common operational data for a component 
      in a digital hierarchy interface."
::= { lpDS1 16 }

lpDS1OperEntry OBJECT-TYPE
   SYNTAX     LpDS1OperEntry
   ACCESS     not-accessible
   STATUS     mandatory
   DESCRIPTION
     "An entry in the lpDS1OperTable."
   INDEX {
      lpIndex,
      lpDS1Index }
::= { lpDS1OperTable 1 }

LpDS1OperEntry ::= SEQUENCE {
   lpDS1LosAlarm
      INTEGER,
   lpDS1RxAisAlarm
      INTEGER,
   lpDS1LofAlarm
      INTEGER,
   lpDS1RxRaiAlarm
      INTEGER,
   lpDS1TxAisAlarm
      INTEGER,
   lpDS1TxRaiAlarm
      INTEGER }

lpDS1LosAlarm OBJECT-TYPE
   SYNTAX     INTEGER  {
                 on(0),
                 off(1) }
   ACCESS     read-only
   STATUS     mandatory
   DESCRIPTION
     "This attribute displays whether a LOS (Loss of Signal) alarm state 
      has been entered. A LOS alarm is declared after LOS defects have 
      been observed and accumulated for a period of 2 seconds +/- 0.5 
      seconds (for 3pDS1Atm, 3pE1Atm, 8pDS1Atm, and 8pE1Atm 
      cards: 2.5 seconds +/- 0.5 seconds).  A LOS defect is detected upon 
      observing all zeros for 150 ms (for 3pDS1Atm, 3pE1Atm, 
      8pDS1Atm, and 8pE1Atm cards: upon observing 175 +/- 75 pulse 
      positions with no pulses of either positive or negative polarity). If 
      the LOS defects are intermittently occurring, the LOS defect 
      accumulator is decremented at a rate of 1/10 of the incrementing 
      rate (alarm integration ratio of 1/10), with all measurements based 
      on a 200 ms polling cycle.
      The port goes into an operational state of disabled until the LOS 
      alarm state is cleared. Also, an RAI alarm is transmitted to the far 
      end for the duration of the LOS alarm state.
      The LOS alarm state is cleared when LOS defects are absent for 10 
      seconds +/- 0.5 seconds."
   DEFVAL     { off }
::= { lpDS1OperEntry 1 }

lpDS1RxAisAlarm OBJECT-TYPE
   SYNTAX     INTEGER  {
                 on(0),
                 off(1) }
   ACCESS     read-only
   STATUS     mandatory
   DESCRIPTION
     "This attribute displays whether an AIS (Alarm Indication Signal) 
      alarm state has been entered. The AIS Alarm state is entered when 
      AIS defects have been observed and accumulated for 2.5 seconds +/
      - 0.5 seconds. An AIS defect is detected after having received less 
      than 3 zeros in a 2048 bit period (for 8pDS1Atm cards: when both 
      an Out Of Frame condition exists and a 1's density of at least 99.9% 
      is present for a time T, where 3 ms  T  75 ms; for 8pE1Atm 
      cards: when both an Out Of Frame condition exists and fewer than 
      three 0's have been received in 512 bit periods). If the AIS defects 
      are intermittently occurring, the AIS defect accumulator is 
      decremented at a rate of 1/10 of the incrementing rate (alarm 
      integration ratio of 1/10), with all measurements based on a 200 ms 
      polling cycle.
      The port goes into an operational state of disabled for the duration 
      of an AIS alarm state.
      The AIS alarm state is cleared when AIS defects are absent for 10 
      seconds +/- 0.5 seconds."
   DEFVAL     { off }
::= { lpDS1OperEntry 2 }

lpDS1LofAlarm OBJECT-TYPE
   SYNTAX     INTEGER  {
                 on(0),
                 off(1) }
   ACCESS     read-only
   STATUS     mandatory
   DESCRIPTION
     "This attribute displays whether a LOF (Loss of Frame) alarm state 
      has been entered. The LOF alarm state is entered when LOF defects 
      (for DS1: 2 out of 5 framing bits in error; for E1: 3 consecutive 
      frame alignment patterns in error) have been detected for 3 seconds 
      +/- 0.5 seconds (for 3pDS1Atm, 3pE1Atm, 8pDS1Atm, and 
      8pE1Atm cards: 2.5 seconds +/- 0.5 seconds). If the LOF defects 
      are intermittently occurring, the LOF defect accumulator is 
      decremented at a rate of 1/10 of the incrementing rate (alarm 
      integration ratio of 1/10), with all measurements based on a 200 ms 
      polling cycle.
      The port goes into an operational state of disabled until the LOF 
      alarm state is cleared. Also, an RAI alarm is transmitted to the far 
      end for the duration of the LOF alarm state 
      The condition is cleared when framing has been achieved for 10 
      seconds +/- 0.5 seconds."
   DEFVAL     { off }
::= { lpDS1OperEntry 3 }

lpDS1RxRaiAlarm OBJECT-TYPE
   SYNTAX     INTEGER  {
                 on(0),
                 off(1) }
   ACCESS     read-only
   STATUS     mandatory
   DESCRIPTION
     "This attribute displays whether an RAI (Remote Alarm Indication) 
      alarm state has been entered. An RAI alarm state is entered when 
      the RAI defect indicator has been observed and accumulated for 3.5 
      seconds +/- 0.5 seconds. For 3pDS1Atm, and 8pDS1Atm cards: 
      alarm is declared immediately upon observing the defect is present, 
      with no integration time. For 3pE1Atm, and 8pE1Atm cards: alarm 
      state is entered when the RAI defect indicator has been observed 
      and accumulated for 2.5 seconds +/- 0.5 seconds. If the RAI defects 
      are intermittently occurring, the RAI defect accumulator is 
      decremented at a rate of 1/10 of the incrementing rate (alarm 
      integration ratio of 1/10), with all measurements based on a 200 ms 
      polling cycle. 
      The RAI alarm state is cleared when the RAI defect indicator has 
      been absent for 10 seconds +/- 0.5 seconds (for 3pDS1Atm, and 
      8pDS1Atm cards: alarm is cleared immediately upon observing the 
      defect is absent, with no integration time).
      The RAI alarm is usually an indication that the far end facility is 
      unable to gain synchronization."
   DEFVAL     { off }
::= { lpDS1OperEntry 4 }

lpDS1TxAisAlarm OBJECT-TYPE
   SYNTAX     INTEGER  {
                 on(0),
                 off(1) }
   ACCESS     read-only
   STATUS     mandatory
   DESCRIPTION
     "This attribute displays whether an AIS (Alarm Indication Signal) 
      alarm is being transmitted on the line. An AIS alarm is transmitted 
      when the port is in a locked state."
   DEFVAL     { off }
::= { lpDS1OperEntry 5 }

lpDS1TxRaiAlarm OBJECT-TYPE
   SYNTAX     INTEGER  {
                 on(0),
                 off(1) }
   ACCESS     read-only
   STATUS     mandatory
   DESCRIPTION
     "This attribute displays whether a RAI signal is being sent on the 
      outgoing line. The RAI signal is transmitted when the port detects a 
      LOF alarm condition (for 3pDS1Atm, 3pE1Atm, 8pDS1Atm, and 
      8pE1Atm cards: RAI is transmitted when the port detects a LOS, 
      LOF, or AIS condition)."
   DEFVAL     { off }
::= { lpDS1OperEntry 6 }

lpDS1StatsTable OBJECT-TYPE
   SYNTAX     SEQUENCE OF LpDS1StatsEntry
   ACCESS     not-accessible
   STATUS     mandatory
   DESCRIPTION
     "This group contains the common statistical data for a component in 
      a digital hierarchy interface."
::= { lpDS1 17 }

lpDS1StatsEntry OBJECT-TYPE
   SYNTAX     LpDS1StatsEntry
   ACCESS     not-accessible
   STATUS     mandatory
   DESCRIPTION
     "An entry in the lpDS1StatsTable."
   INDEX {
      lpIndex,
      lpDS1Index }
::= { lpDS1StatsTable 1 }

LpDS1StatsEntry ::= SEQUENCE {
   lpDS1RunningTime
      Counter32,
   lpDS1ErrorFreeSec
      Counter32,
   lpDS1ErroredSec
      Counter32,
   lpDS1SevErroredSec
      Counter32,
   lpDS1SevErroredFrmSec
      Counter32,
   lpDS1UnavailSec
      Counter32,
   lpDS1BpvErrors
      Counter32,
   lpDS1CrcErrors
      Counter32,
   lpDS1FrmErrors
      Counter32,
   lpDS1LosStateChanges
      Counter32,
   lpDS1SlipErrors
      Counter32 }

lpDS1RunningTime OBJECT-TYPE
   SYNTAX     Counter32 
   ACCESS     read-only
   STATUS     mandatory
   DESCRIPTION
     "The number of seconds since the port component was activated."
::= { lpDS1StatsEntry 1 }

lpDS1ErrorFreeSec OBJECT-TYPE
   SYNTAX     Counter32 
   ACCESS     read-only
   STATUS     mandatory
   DESCRIPTION
     "The number of seconds that the port has been in an error free state."
::= { lpDS1StatsEntry 2 }

lpDS1ErroredSec OBJECT-TYPE
   SYNTAX     Counter32 
   ACCESS     read-only
   STATUS     mandatory
   DESCRIPTION
     "An errored second is declared when a second with one or more 
      Code Violation Error events, or one or more Out Of Frame events 
      occurs. A code violation error may be a CRC error or a BPV error. 
      An Out Of Frame event occurs when 2 out of 5 framing bits are in 
      error."
::= { lpDS1StatsEntry 3 }

lpDS1SevErroredSec OBJECT-TYPE
   SYNTAX     Counter32 
   ACCESS     read-only
   STATUS     mandatory
   DESCRIPTION
     "A severely errored second occurs when a second with 320 or more 
      Code Violation Error events or one or more Out Of Frame events 
      occurs."
::= { lpDS1StatsEntry 4 }

lpDS1SevErroredFrmSec OBJECT-TYPE
   SYNTAX     Counter32 
   ACCESS     read-only
   STATUS     mandatory
   DESCRIPTION
     "A severely errored framing second occurs when a second with one 
      or more Out Of Frame events occurs."
::= { lpDS1StatsEntry 5 }

lpDS1UnavailSec OBJECT-TYPE
   SYNTAX     Counter32 
   ACCESS     read-only
   STATUS     mandatory
   DESCRIPTION
     "The total number of seconds that the interface is in an unavailable 
      signal state. An unavailable signal state occurs at the onset of 10 
      consecutive Severely Errored Seconds. The state is cleared at the 
      onset of 10 seconds with no Severely Errored Seconds."
::= { lpDS1StatsEntry 6 }

lpDS1BpvErrors OBJECT-TYPE
   SYNTAX     Counter32 
   ACCESS     read-only
   STATUS     mandatory
   DESCRIPTION
     "The current count of Bipolar Violations. A bipolar violation is an 
      error in the alternate mark inversion pattern (AMI) on the line."
::= { lpDS1StatsEntry 7 }

lpDS1CrcErrors OBJECT-TYPE
   SYNTAX     Counter32 
   ACCESS     read-only
   STATUS     mandatory
   DESCRIPTION
     "If the interface is a DS1 line, it is the current count of CRC-6 errors. 
      These will only be counted when the lineType is ESF.
      If the interface is an E1 line, it is the total number of CRC-4 errors. 
      These will only be counted when crc4Mode is on."
::= { lpDS1StatsEntry 8 }

lpDS1FrmErrors OBJECT-TYPE
   SYNTAX     Counter32 
   ACCESS     read-only
   STATUS     mandatory
   DESCRIPTION
     "The current count of frame errors. A frame error is an error in the 
      framing bits"
::= { lpDS1StatsEntry 9 }

lpDS1LosStateChanges OBJECT-TYPE
   SYNTAX     Counter32 
   ACCESS     read-only
   STATUS     mandatory
   DESCRIPTION
     "The total number of times that the line lost signal."
::= { lpDS1StatsEntry 10 }

lpDS1SlipErrors OBJECT-TYPE
   SYNTAX     Counter32 
   ACCESS     read-only
   STATUS     mandatory
   DESCRIPTION
     "The total number of times that the line experienced a controlled 
      frame slip. This attribute is incremented for ports on the voice cards 
      (for example the 1pDS1V and the 1pE1V function processors) only."
::= { lpDS1StatsEntry 11 }


-- Channel
-- The Channel component is configured to control a group of 
-- timeslots that form a fractional group on a DS1 or E1 port. 
-- Cell-based cards allow only one channel per port, and this is 
-- automatically provisioned with all available timeslots. Similarly, the 
-- 1pDS3C card type only allows one channel per port, and this is 
-- automatically provisioned with all available timeslots.
-- Warning: On cell-based cards, creation of the AtmCell component 
-- under the Chan and automatic timeslot provisioning is not 
-- guaranteed behavior, since it is possible to add a Chan component 
-- before provisioning the cardType. In general, do not add a Chan 
-- component before provisioning the cardType.

lpDS1Chan OBJECT IDENTIFIER ::= { lpDS1 2 }



lpDS1ChanRowStatusTable OBJECT-TYPE
   SYNTAX     SEQUENCE OF LpDS1ChanRowStatusEntry
   ACCESS     not-accessible
   STATUS     mandatory
   DESCRIPTION
     "This entry controls the addition and deletion of 
      lpDS1Chan components."
::= { lpDS1Chan 1 }

lpDS1ChanRowStatusEntry OBJECT-TYPE
   SYNTAX     LpDS1ChanRowStatusEntry
   ACCESS     not-accessible
   STATUS     mandatory
   DESCRIPTION
     "A single entry in the table represents a single 
      lpDS1Chan component."
   INDEX {
      lpIndex,
      lpDS1Index,
      lpDS1ChanIndex }
::= { lpDS1ChanRowStatusTable 1 }

LpDS1ChanRowStatusEntry ::= SEQUENCE {
   lpDS1ChanRowStatus
      RowStatus,
   lpDS1ChanComponentName
      DisplayString,
   lpDS1ChanStorageType
      StorageType,
   lpDS1ChanIndex
      Integer32 }

lpDS1ChanRowStatus OBJECT-TYPE
   SYNTAX     RowStatus 
   ACCESS     read-write
   STATUS     mandatory
   DESCRIPTION
     "This variable is used as the basis for SNMP naming of
      lpDS1Chan components.
      These components can be added and deleted."
::= { lpDS1ChanRowStatusEntry 1 }

lpDS1ChanComponentName OBJECT-TYPE
   SYNTAX     DisplayString 
   ACCESS     read-only
   STATUS     mandatory
   DESCRIPTION
     "This variable provides the component's string name for
      use with the ASCII Console Interface"
::= { lpDS1ChanRowStatusEntry 2 }

lpDS1ChanStorageType OBJECT-TYPE
   SYNTAX     StorageType 
   ACCESS     read-only
   STATUS     mandatory
   DESCRIPTION
     "This variable represents the storage type value for the
      lpDS1Chan tables."
::= { lpDS1ChanRowStatusEntry 4 }

lpDS1ChanIndex OBJECT-TYPE
   SYNTAX     Integer32 (0..24)
   ACCESS     not-accessible
   STATUS     mandatory
   DESCRIPTION
     "This variable represents the index for the lpDS1Chan tables."
::= { lpDS1ChanRowStatusEntry 10 }

lpDS1ChanProvTable OBJECT-TYPE
   SYNTAX     SEQUENCE OF LpDS1ChanProvEntry
   ACCESS     not-accessible
   STATUS     mandatory
   DESCRIPTION
     "This group contains all of the provisional data for a Channel 
      component."
::= { lpDS1Chan 10 }

lpDS1ChanProvEntry OBJECT-TYPE
   SYNTAX     LpDS1ChanProvEntry
   ACCESS     not-accessible
   STATUS     mandatory
   DESCRIPTION
     "An entry in the lpDS1ChanProvTable."
   INDEX {
      lpIndex,
      lpDS1Index,
      lpDS1ChanIndex }
::= { lpDS1ChanProvTable 1 }

LpDS1ChanProvEntry ::= SEQUENCE {
   lpDS1ChanTimeslots
      OCTET STRING,
   lpDS1ChanTimeslotDataRate
      INTEGER,
   lpDS1ChanApplicationFramerName
      Link }

lpDS1ChanTimeslots OBJECT-TYPE
   SYNTAX     OCTET STRING (SIZE (4))
   ACCESS     read-write
   STATUS     mandatory
   DESCRIPTION
     "This attribute contains the list of timeslots that are used by the 
      Channel component. Valid numbers are 1-24 for a Channel used by 
      a DS1 component, and 1-31 for a Channel used by an E1 
      component.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { lpDS1ChanProvEntry 1 }

lpDS1ChanTimeslotDataRate OBJECT-TYPE
   SYNTAX     INTEGER  {
                 n56k(0),
                 doNotOverride(1) }
   ACCESS     read-write
   STATUS     mandatory
   DESCRIPTION
     "This attribute selects the data rate of the timeslots in a channel of a 
      DS1 component. For E1, the data rate of the timeslots will always 
      be 64kbit/s regardless of this attribute.
      When doNotOverride is selected for a channel on a DS1, the data 
      rate of the channel's timeslots are dependent on the zeroCoding 
      selection of the DS1 component. If the zeroCoding is B8ZS (where 
      supported on the FP) or none, the timeslot's data rate will be 
      64kbit/s. If the zeroCoding option is bit7Stuffing, the data rate of a 
      timeslot will be 56kbit/s.
      When 56kbit/s is selected for a channel on a DS1, the least 
      significant bit of each timeslot of this Channel will always be set to 
      1 and not used for data. The data rate for the timeslots of this 
      channel is therefore restricted to 56kbit/s.
      One application of this attribute is to allow a DS1 line to support 
      mixing channels that originate from lines that use different 
      zeroCoding schemes."
   DEFVAL     { doNotOverride }
::= { lpDS1ChanProvEntry 2 }

lpDS1ChanApplicationFramerName OBJECT-TYPE
   SYNTAX     Link 
   ACCESS     read-write
   STATUS     mandatory
   DESCRIPTION
     "This attribute defines the link to the software stack. It defines which 
      application is running on top of this hardware component."
::= { lpDS1ChanProvEntry 3 }

lpDS1ChanCidDataTable OBJECT-TYPE
   SYNTAX     SEQUENCE OF LpDS1ChanCidDataEntry
   ACCESS     not-accessible
   STATUS     mandatory
   DESCRIPTION
     "This group contains the attribute for a component's Customer 
      Identifier (CID). Refer to the attribute description for a detailed 
      explanation of CIDs."
::= { lpDS1Chan 11 }

lpDS1ChanCidDataEntry OBJECT-TYPE
   SYNTAX     LpDS1ChanCidDataEntry
   ACCESS     not-accessible
   STATUS     mandatory
   DESCRIPTION
     "An entry in the lpDS1ChanCidDataTable."
   INDEX {
      lpIndex,
      lpDS1Index,
      lpDS1ChanIndex }
::= { lpDS1ChanCidDataTable 1 }

LpDS1ChanCidDataEntry ::= SEQUENCE {
   lpDS1ChanCustomerIdentifier
      Unsigned32 }

lpDS1ChanCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpDS1ChanCidDataEntry 1 }

lpDS1ChanIfEntryTable OBJECT-TYPE
   SYNTAX     SEQUENCE OF LpDS1ChanIfEntryEntry
   ACCESS     not-accessible
   STATUS     mandatory
   DESCRIPTION
     "This group contains the provisionable attributes for the ifEntry."
::= { lpDS1Chan 12 }

lpDS1ChanIfEntryEntry OBJECT-TYPE
   SYNTAX     LpDS1ChanIfEntryEntry
   ACCESS     not-accessible
   STATUS     mandatory
   DESCRIPTION
     "An entry in the lpDS1ChanIfEntryTable."
   INDEX {
      lpIndex,
      lpDS1Index,
      lpDS1ChanIndex }
::= { lpDS1ChanIfEntryTable 1 }

LpDS1ChanIfEntryEntry ::= SEQUENCE {
   lpDS1ChanIfAdminStatus
      INTEGER,
   lpDS1ChanIfIndex
      InterfaceIndex }

lpDS1ChanIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpDS1ChanIfEntryEntry 1 }

lpDS1ChanIfIndex OBJECT-TYPE
   SYNTAX     InterfaceIndex (1..65535)
   ACCESS     read-only
   STATUS     mandatory
   DESCRIPTION
     "This is the index for the IfEntry. Its value is automatically initialized 
      during the provisioning process."
::= { lpDS1ChanIfEntryEntry 2 }

lpDS1ChanOperStatusTable OBJECT-TYPE
   SYNTAX     SEQUENCE OF LpDS1ChanOperStatusEntry
   ACCESS     not-accessible
   STATUS     mandatory
   DESCRIPTION
     "This group includes the Operational Status attribute. This attribute 
      defines the current operational state of this component."
::= { lpDS1Chan 13 }

lpDS1ChanOperStatusEntry OBJECT-TYPE
   SYNTAX     LpDS1ChanOperStatusEntry
   ACCESS     not-accessible
   STATUS     mandatory
   DESCRIPTION
     "An entry in the lpDS1ChanOperStatusTable."
   INDEX {
      lpIndex,
      lpDS1Index,
      lpDS1ChanIndex }
::= { lpDS1ChanOperStatusTable 1 }

LpDS1ChanOperStatusEntry ::= SEQUENCE {
   lpDS1ChanSnmpOperStatus
      INTEGER }

lpDS1ChanSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpDS1ChanOperStatusEntry 1 }

lpDS1ChanStateTable OBJECT-TYPE
   SYNTAX     SEQUENCE OF LpDS1ChanStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpDS1Chan 14 }

lpDS1ChanStateEntry OBJECT-TYPE
   SYNTAX     LpDS1ChanStateEntry
   ACCESS     not-accessible
   STATUS     mandatory
   DESCRIPTION
     "An entry in the lpDS1ChanStateTable."
   INDEX {
      lpIndex,
      lpDS1Index,
      lpDS1ChanIndex }
::= { lpDS1ChanStateTable 1 }

LpDS1ChanStateEntry ::= SEQUENCE {
   lpDS1ChanAdminState
      INTEGER,
   lpDS1ChanOperationalState
      INTEGER,
   lpDS1ChanUsageState
      INTEGER,
   lpDS1ChanAvailabilityStatus
      OCTET STRING,
   lpDS1ChanProceduralStatus
      OCTET STRING,
   lpDS1ChanControlStatus
      OCTET STRING,
   lpDS1ChanAlarmStatus
      OCTET STRING,
   lpDS1ChanStandbyStatus
      INTEGER,
   lpDS1ChanUnknownStatus
      INTEGER }

lpDS1ChanAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpDS1ChanStateEntry 1 }

lpDS1ChanOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpDS1ChanStateEntry 2 }

lpDS1ChanUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpDS1ChanStateEntry 3 }

lpDS1ChanAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpDS1ChanStateEntry 4 }

lpDS1ChanProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpDS1ChanStateEntry 5 }

lpDS1ChanControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpDS1ChanStateEntry 6 }

lpDS1ChanAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpDS1ChanStateEntry 7 }

lpDS1ChanStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpDS1ChanStateEntry 8 }

lpDS1ChanUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpDS1ChanStateEntry 9 }

lpDS1ChanOperTable OBJECT-TYPE
   SYNTAX     SEQUENCE OF LpDS1ChanOperEntry
   ACCESS     not-accessible
   STATUS     mandatory
   DESCRIPTION
     "This group contains all of the operational data for a Channel 
      component."
::= { lpDS1Chan 15 }

lpDS1ChanOperEntry OBJECT-TYPE
   SYNTAX     LpDS1ChanOperEntry
   ACCESS     not-accessible
   STATUS     mandatory
   DESCRIPTION
     "An entry in the lpDS1ChanOperTable."
   INDEX {
      lpIndex,
      lpDS1Index,
      lpDS1ChanIndex }
::= { lpDS1ChanOperTable 1 }

LpDS1ChanOperEntry ::= SEQUENCE {
   lpDS1ChanActualChannelSpeed
      Gauge32 }

lpDS1ChanActualChannelSpeed OBJECT-TYPE
   SYNTAX     Gauge32 (0..4294967295)
   ACCESS     read-only
   STATUS     mandatory
   DESCRIPTION
     "This attribute displays the measured link speed of the Channel 
      component."
   DEFVAL     { 0 }
::= { lpDS1ChanOperEntry 1 }

lpDS1ChanAdminInfoTable OBJECT-TYPE
   SYNTAX     SEQUENCE OF LpDS1ChanAdminInfoEntry
   ACCESS     not-accessible
   STATUS     mandatory
   DESCRIPTION
     "This group contains the attributes pertaining to the vendor of the 
      equipment."
::= { lpDS1Chan 16 }

lpDS1ChanAdminInfoEntry OBJECT-TYPE
   SYNTAX     LpDS1ChanAdminInfoEntry
   ACCESS     not-accessible
   STATUS     mandatory
   DESCRIPTION
     "An entry in the lpDS1ChanAdminInfoTable."
   INDEX {
      lpIndex,
      lpDS1Index,
      lpDS1ChanIndex }
::= { lpDS1ChanAdminInfoTable 1 }

LpDS1ChanAdminInfoEntry ::= SEQUENCE {
   lpDS1ChanVendor
      AsciiString,
   lpDS1ChanCommentText
      AsciiString }

lpDS1ChanVendor OBJECT-TYPE
   SYNTAX     AsciiString (SIZE (0..20))
   ACCESS     read-write
   STATUS     mandatory
   DESCRIPTION
     "This is the name of the vendor supplying the facility."
::= { lpDS1ChanAdminInfoEntry 1 }

lpDS1ChanCommentText OBJECT-TYPE
   SYNTAX     AsciiString (SIZE (0..60))
   ACCESS     read-write
   STATUS     mandatory
   DESCRIPTION
     "Any miscellaneous text about the facility."
::= { lpDS1ChanAdminInfoEntry 2 }


-- 
-- The Test component is configured to control a hardware facility test 
-- on a physical (V35, X21, DS1, E1, DS3, E3 etc.) or a logical port.

lpDS1ChanTest OBJECT IDENTIFIER ::= { lpDS1Chan 2 }



lpDS1ChanTestRowStatusTable OBJECT-TYPE
   SYNTAX     SEQUENCE OF LpDS1ChanTestRowStatusEntry
   ACCESS     not-accessible
   STATUS     mandatory
   DESCRIPTION
     "This entry controls the addition and deletion of 
      lpDS1ChanTest components."
::= { lpDS1ChanTest 1 }

lpDS1ChanTestRowStatusEntry OBJECT-TYPE
   SYNTAX     LpDS1ChanTestRowStatusEntry
   ACCESS     not-accessible
   STATUS     mandatory
   DESCRIPTION
     "A single entry in the table represents a single 
      lpDS1ChanTest component."
   INDEX {
      lpIndex,
      lpDS1Index,
      lpDS1ChanIndex,
      lpDS1ChanTestIndex }
::= { lpDS1ChanTestRowStatusTable 1 }

LpDS1ChanTestRowStatusEntry ::= SEQUENCE {
   lpDS1ChanTestRowStatus
      RowStatus,
   lpDS1ChanTestComponentName
      DisplayString,
   lpDS1ChanTestStorageType
      StorageType,
   lpDS1ChanTestIndex
      NonReplicated }

lpDS1ChanTestRowStatus OBJECT-TYPE
   SYNTAX     RowStatus 
   ACCESS     read-only
   STATUS     mandatory
   DESCRIPTION
     "This variable is used as the basis for SNMP naming of
      lpDS1ChanTest components.
      These components cannot be added nor deleted."
::= { lpDS1ChanTestRowStatusEntry 1 }

lpDS1ChanTestComponentName OBJECT-TYPE
   SYNTAX     DisplayString 
   ACCESS     read-only
   STATUS     mandatory
   DESCRIPTION
     "This variable provides the component's string name for
      use with the ASCII Console Interface"
::= { lpDS1ChanTestRowStatusEntry 2 }

lpDS1ChanTestStorageType OBJECT-TYPE
   SYNTAX     StorageType 
   ACCESS     read-only
   STATUS     mandatory
   DESCRIPTION
     "This variable represents the storage type value for the
      lpDS1ChanTest tables."
::= { lpDS1ChanTestRowStatusEntry 4 }

lpDS1ChanTestIndex OBJECT-TYPE
   SYNTAX     NonReplicated 
   ACCESS     not-accessible
   STATUS     mandatory
   DESCRIPTION
     "This variable represents the index for the lpDS1ChanTest tables."
::= { lpDS1ChanTestRowStatusEntry 10 }

lpDS1ChanTestStateTable OBJECT-TYPE
   SYNTAX     SEQUENCE OF LpDS1ChanTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpDS1ChanTest 10 }

lpDS1ChanTestStateEntry OBJECT-TYPE
   SYNTAX     LpDS1ChanTestStateEntry
   ACCESS     not-accessible
   STATUS     mandatory
   DESCRIPTION
     "An entry in the lpDS1ChanTestStateTable."
   INDEX {
      lpIndex,
      lpDS1Index,
      lpDS1ChanIndex,
      lpDS1ChanTestIndex }
::= { lpDS1ChanTestStateTable 1 }

LpDS1ChanTestStateEntry ::= SEQUENCE {
   lpDS1ChanTestAdminState
      INTEGER,
   lpDS1ChanTestOperationalState
      INTEGER,
   lpDS1ChanTestUsageState
      INTEGER }

lpDS1ChanTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpDS1ChanTestStateEntry 1 }

lpDS1ChanTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpDS1ChanTestStateEntry 2 }

lpDS1ChanTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpDS1ChanTestStateEntry 3 }

lpDS1ChanTestSetupTable OBJECT-TYPE
   SYNTAX     SEQUENCE OF LpDS1ChanTestSetupEntry
   ACCESS     not-accessible
   STATUS     mandatory
   DESCRIPTION
     "This group contains all of the operational data for a Test 
      component."
::= { lpDS1ChanTest 11 }

lpDS1ChanTestSetupEntry OBJECT-TYPE
   SYNTAX     LpDS1ChanTestSetupEntry
   ACCESS     not-accessible
   STATUS     mandatory
   DESCRIPTION
     "An entry in the lpDS1ChanTestSetupTable."
   INDEX {
      lpIndex,
      lpDS1Index,
      lpDS1ChanIndex,
      lpDS1ChanTestIndex }
::= { lpDS1ChanTestSetupTable 1 }

LpDS1ChanTestSetupEntry ::= SEQUENCE {
   lpDS1ChanTestPurpose
      AsciiString,
   lpDS1ChanTestType
      INTEGER,
   lpDS1ChanTestFrmSize
      Unsigned32,
   lpDS1ChanTestFrmPatternType
      INTEGER,
   lpDS1ChanTestCustomizedPattern
      Hex,
   lpDS1ChanTestDataStartDelay
      Unsigned32,
   lpDS1ChanTestDisplayInterval
      Unsigned32,
   lpDS1ChanTestDuration
      Unsigned32 }

lpDS1ChanTestPurpose OBJECT-TYPE
   SYNTAX     AsciiString (SIZE (0..40))
   ACCESS     read-write
   STATUS     mandatory
   DESCRIPTION
     "This attribute records the purpose of the test so that the test results 
      can be associated and properly analyzed."
::= { lpDS1ChanTestSetupEntry 1 }

lpDS1ChanTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpDS1ChanTestSetupEntry 2 }

lpDS1ChanTestFrmSize OBJECT-TYPE
   SYNTAX     Unsigned32 (4..4096)
   ACCESS     read-write
   STATUS     mandatory
   DESCRIPTION
     "This attribute defines the size of the test data frames in number of 
      bytes."
   DEFVAL     { 1024 }
::= { lpDS1ChanTestSetupEntry 3 }

lpDS1ChanTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpDS1ChanTestSetupEntry 4 }

lpDS1ChanTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpDS1ChanTestSetupEntry 5 }

lpDS1ChanTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpDS1ChanTestSetupEntry 6 }

lpDS1ChanTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpDS1ChanTestSetupEntry 7 }

lpDS1ChanTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpDS1ChanTestSetupEntry 8 }

lpDS1ChanTestResultsTable OBJECT-TYPE
   SYNTAX     SEQUENCE OF LpDS1ChanTestResultsEntry
   ACCESS     not-accessible
   STATUS     mandatory
   DESCRIPTION
     "This group contains all the statistics related attributes of the Test 
      component."
::= { lpDS1ChanTest 12 }

lpDS1ChanTestResultsEntry OBJECT-TYPE
   SYNTAX     LpDS1ChanTestResultsEntry
   ACCESS     not-accessible
   STATUS     mandatory
   DESCRIPTION
     "An entry in the lpDS1ChanTestResultsTable."
   INDEX {
      lpIndex,
      lpDS1Index,
      lpDS1ChanIndex,
      lpDS1ChanTestIndex }
::= { lpDS1ChanTestResultsTable 1 }

LpDS1ChanTestResultsEntry ::= SEQUENCE {
   lpDS1ChanTestElapsedTime
      Counter32,
   lpDS1ChanTestTimeRemaining
      Unsigned32,
   lpDS1ChanTestCauseOfTermination
      INTEGER,
   lpDS1ChanTestBitsTx
      PassportCounter64,
   lpDS1ChanTestBytesTx
      PassportCounter64,
   lpDS1ChanTestFrmTx
      PassportCounter64,
   lpDS1ChanTestBitsRx
      PassportCounter64,
   lpDS1ChanTestBytesRx
      PassportCounter64,
   lpDS1ChanTestFrmRx
      PassportCounter64,
   lpDS1ChanTestErroredFrmRx
      PassportCounter64,
   lpDS1ChanTestBitErrorRate
      AsciiString }

lpDS1ChanTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpDS1ChanTestResultsEntry 1 }

lpDS1ChanTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpDS1ChanTestResultsEntry 2 }

lpDS1ChanTestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpDS1ChanTestResultsEntry 3 }

lpDS1ChanTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpDS1ChanTestResultsEntry 4 }

lpDS1ChanTestBytesTx OBJECT-TYPE
   SYNTAX     PassportCounter64 
   ACCESS     read-only
   STATUS     mandatory
   DESCRIPTION
     "This attribute is the total number of bytes sent during the test 
      period. This counter is not expected to reach its maximum value."
::= { lpDS1ChanTestResultsEntry 5 }

lpDS1ChanTestFrmTx OBJECT-TYPE
   SYNTAX     PassportCounter64 
   ACCESS     read-only
   STATUS     mandatory
   DESCRIPTION
     "This attribute is the total number of frames sent during the test 
      period. This counter is not expected to reach its maximum value."
::= { lpDS1ChanTestResultsEntry 6 }

lpDS1ChanTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpDS1ChanTestResultsEntry 7 }

lpDS1ChanTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpDS1ChanTestResultsEntry 8 }

lpDS1ChanTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpDS1ChanTestResultsEntry 9 }

lpDS1ChanTestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpDS1ChanTestResultsEntry 10 }

lpDS1ChanTestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpDS1ChanTestResultsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

lpDS1ChanCell OBJECT IDENTIFIER ::= { lpDS1Chan 3 }



lpDS1ChanCellRowStatusTable OBJECT-TYPE
   SYNTAX     SEQUENCE OF LpDS1ChanCellRowStatusEntry
   ACCESS     not-accessible
   STATUS     mandatory
   DESCRIPTION
     "This entry controls the addition and deletion of 
      lpDS1ChanCell components."
::= { lpDS1ChanCell 1 }

lpDS1ChanCellRowStatusEntry OBJECT-TYPE
   SYNTAX     LpDS1ChanCellRowStatusEntry
   ACCESS     not-accessible
   STATUS     mandatory
   DESCRIPTION
     "A single entry in the table represents a single 
      lpDS1ChanCell component."
   INDEX {
      lpIndex,
      lpDS1Index,
      lpDS1ChanIndex,
      lpDS1ChanCellIndex }
::= { lpDS1ChanCellRowStatusTable 1 }

LpDS1ChanCellRowStatusEntry ::= SEQUENCE {
   lpDS1ChanCellRowStatus
      RowStatus,
   lpDS1ChanCellComponentName
      DisplayString,
   lpDS1ChanCellStorageType
      StorageType,
   lpDS1ChanCellIndex
      NonReplicated }

lpDS1ChanCellRowStatus OBJECT-TYPE
   SYNTAX     RowStatus 
   ACCESS     read-write
   STATUS     mandatory
   DESCRIPTION
     "This variable is used as the basis for SNMP naming of
      lpDS1ChanCell components.
      These components can be added and deleted."
::= { lpDS1ChanCellRowStatusEntry 1 }

lpDS1ChanCellComponentName OBJECT-TYPE
   SYNTAX     DisplayString 
   ACCESS     read-only
   STATUS     mandatory
   DESCRIPTION
     "This variable provides the component's string name for
      use with the ASCII Console Interface"
::= { lpDS1ChanCellRowStatusEntry 2 }

lpDS1ChanCellStorageType OBJECT-TYPE
   SYNTAX     StorageType 
   ACCESS     read-only
   STATUS     mandatory
   DESCRIPTION
     "This variable represents the storage type value for the
      lpDS1ChanCell tables."
::= { lpDS1ChanCellRowStatusEntry 4 }

lpDS1ChanCellIndex OBJECT-TYPE
   SYNTAX     NonReplicated 
   ACCESS     not-accessible
   STATUS     mandatory
   DESCRIPTION
     "This variable represents the index for the lpDS1ChanCell tables."
::= { lpDS1ChanCellRowStatusEntry 10 }

lpDS1ChanCellProvTable OBJECT-TYPE
   SYNTAX     SEQUENCE OF LpDS1ChanCellProvEntry
   ACCESS     not-accessible
   STATUS     mandatory
   DESCRIPTION
     "This group contains the provisioning attributes for the AtmCell 
      component."
::= { lpDS1ChanCell 10 }

lpDS1ChanCellProvEntry OBJECT-TYPE
   SYNTAX     LpDS1ChanCellProvEntry
   ACCESS     not-accessible
   STATUS     mandatory
   DESCRIPTION
     "An entry in the lpDS1ChanCellProvTable."
   INDEX {
      lpIndex,
      lpDS1Index,
      lpDS1ChanIndex,
      lpDS1ChanCellIndex }
::= { lpDS1ChanCellProvTable 1 }

LpDS1ChanCellProvEntry ::= SEQUENCE {
   lpDS1ChanCellAlarmActDelay
      Unsigned32,
   lpDS1ChanCellScrambleCellPayload
      INTEGER,
   lpDS1ChanCellCorrectSingleBitHeaderErrors
      INTEGER }

lpDS1ChanCellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { lpDS1ChanCellProvEntry 1 }

lpDS1ChanCellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { lpDS1ChanCellProvEntry 2 }

lpDS1ChanCellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { lpDS1ChanCellProvEntry 3 }

lpDS1ChanCellOperTable OBJECT-TYPE
   SYNTAX     SEQUENCE OF LpDS1ChanCellOperEntry
   ACCESS     not-accessible
   STATUS     mandatory
   DESCRIPTION
     "This group contains the common operational attributes for the 
      AtmCell component."
::= { lpDS1ChanCell 11 }

lpDS1ChanCellOperEntry OBJECT-TYPE
   SYNTAX     LpDS1ChanCellOperEntry
   ACCESS     not-accessible
   STATUS     mandatory
   DESCRIPTION
     "An entry in the lpDS1ChanCellOperTable."
   INDEX {
      lpIndex,
      lpDS1Index,
      lpDS1ChanIndex,
      lpDS1ChanCellIndex }
::= { lpDS1ChanCellOperTable 1 }

LpDS1ChanCellOperEntry ::= SEQUENCE {
   lpDS1ChanCellLcdAlarm
      INTEGER }

lpDS1ChanCellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { lpDS1ChanCellOperEntry 1 }

lpDS1ChanCellStatsTable OBJECT-TYPE
   SYNTAX     SEQUENCE OF LpDS1ChanCellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { lpDS1ChanCell 12 }

lpDS1ChanCellStatsEntry OBJECT-TYPE
   SYNTAX     LpDS1ChanCellStatsEntry
   ACCESS     not-accessible
   STATUS     mandatory
   DESCRIPTION
     "An entry in the lpDS1ChanCellStatsTable."
   INDEX {
      lpIndex,
      lpDS1Index,
      lpDS1ChanIndex,
      lpDS1ChanCellIndex }
::= { lpDS1ChanCellStatsTable 1 }

LpDS1ChanCellStatsEntry ::= SEQUENCE {
   lpDS1ChanCellUncorrectableHecErrors
      Counter32,
   lpDS1ChanCellSevErroredSec
      Counter32,
   lpDS1ChanCellReceiveCellUtilization
      Gauge32,
   lpDS1ChanCellTransmitCellUtilization
      Gauge32,
   lpDS1ChanCellCorrectableHeaderErrors
      Counter32 }

lpDS1ChanCellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { lpDS1ChanCellStatsEntry 1 }

lpDS1ChanCellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { lpDS1ChanCellStatsEntry 2 }

lpDS1ChanCellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { lpDS1ChanCellStatsEntry 3 }

lpDS1ChanCellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { lpDS1ChanCellStatsEntry 4 }

lpDS1ChanCellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { lpDS1ChanCellStatsEntry 5 }


-- Lp/x Ds1/y Chan/z Tc
-- Lp/x E1/y Chan/z Tc
-- 
-- The Tc component is used to provision and monitor trunk 
-- conditioning options. A separate instance of this component is 
-- required for each Chan on a Port which is offering a structured 
-- constant bit rate service.
-- 
-- Under certain failure alarm conditions, trunk conditioning 
-- replacementData is substituted into the timeslots as defined by the 
-- Chan component. Trunk conditioning signaling is also substituted 
-- into the appropriate Channel Associated Signaling (CAS) bits when 
-- a lineType that uses CAS has been defined.
-- 
-- When used with AAL1 Circuit Emulation Service, trunk 
-- conditioning is transmitted towards the ATM network under the 
-- following conditions:
-- lossOfSignal (LOS)
-- lossOfFrame (LOF)
-- remoteAlarmIndication (RAI)
-- alarmIndicationSignal (AIS)
-- bufferUnderflow (BU)
-- and in addition for E1:
-- lossOfMultiframe (LOMF)
-- receiveMultiframeRemoteAlarmIndication (RMRAI)
-- 
-- When used with AAL1 Circuit Emulation Service, trunk 
-- conditioning is transmitted towards the PDH network under the 
-- following conditions:
-- bufferUnderflow (BU)
-- AAL1 protocol errors.
-- 

lpDS1ChanTc OBJECT IDENTIFIER ::= { lpDS1Chan 4 }



lpDS1ChanTcRowStatusTable OBJECT-TYPE
   SYNTAX     SEQUENCE OF LpDS1ChanTcRowStatusEntry
   ACCESS     not-accessible
   STATUS     mandatory
   DESCRIPTION
     "This entry controls the addition and deletion of 
      lpDS1ChanTc components."
::= { lpDS1ChanTc 1 }

lpDS1ChanTcRowStatusEntry OBJECT-TYPE
   SYNTAX     LpDS1ChanTcRowStatusEntry
   ACCESS     not-accessible
   STATUS     mandatory
   DESCRIPTION
     "A single entry in the table represents a single 
      lpDS1ChanTc component."
   INDEX {
      lpIndex,
      lpDS1Index,
      lpDS1ChanIndex,
      lpDS1ChanTcIndex }
::= { lpDS1ChanTcRowStatusTable 1 }

LpDS1ChanTcRowStatusEntry ::= SEQUENCE {
   lpDS1ChanTcRowStatus
      RowStatus,
   lpDS1ChanTcComponentName
      DisplayString,
   lpDS1ChanTcStorageType
      StorageType,
   lpDS1ChanTcIndex
      NonReplicated }

lpDS1ChanTcRowStatus OBJECT-TYPE
   SYNTAX     RowStatus 
   ACCESS     read-write
   STATUS     mandatory
   DESCRIPTION
     "This variable is used as the basis for SNMP naming of
      lpDS1ChanTc components.
      These components can be added and deleted."
::= { lpDS1ChanTcRowStatusEntry 1 }

lpDS1ChanTcComponentName OBJECT-TYPE
   SYNTAX     DisplayString 
   ACCESS     read-only
   STATUS     mandatory
   DESCRIPTION
     "This variable provides the component's string name for
      use with the ASCII Console Interface"
::= { lpDS1ChanTcRowStatusEntry 2 }

lpDS1ChanTcStorageType OBJECT-TYPE
   SYNTAX     StorageType 
   ACCESS     read-only
   STATUS     mandatory
   DESCRIPTION
     "This variable represents the storage type value for the
      lpDS1ChanTc tables."
::= { lpDS1ChanTcRowStatusEntry 4 }

lpDS1ChanTcIndex OBJECT-TYPE
   SYNTAX     NonReplicated 
   ACCESS     not-accessible
   STATUS     mandatory
   DESCRIPTION
     "This variable represents the index for the lpDS1ChanTc tables."
::= { lpDS1ChanTcRowStatusEntry 10 }

lpDS1ChanTcProvTable OBJECT-TYPE
   SYNTAX     SEQUENCE OF LpDS1ChanTcProvEntry
   ACCESS     not-accessible
   STATUS     mandatory
   DESCRIPTION
     "This group contains all specific provisioning data for a Tc 
      component."
::= { lpDS1ChanTc 10 }

lpDS1ChanTcProvEntry OBJECT-TYPE
   SYNTAX     LpDS1ChanTcProvEntry
   ACCESS     not-accessible
   STATUS     mandatory
   DESCRIPTION
     "An entry in the lpDS1ChanTcProvTable."
   INDEX {
      lpIndex,
      lpDS1Index,
      lpDS1ChanIndex,
      lpDS1ChanTcIndex }
::= { lpDS1ChanTcProvTable 1 }

LpDS1ChanTcProvEntry ::= SEQUENCE {
   lpDS1ChanTcReplacementData
      Hex,
   lpDS1ChanTcSignalOneDuration
      Unsigned32 }

lpDS1ChanTcReplacementData OBJECT-TYPE
   SYNTAX     Hex (0..255)
   ACCESS     read-write
   STATUS     mandatory
   DESCRIPTION
     "This attribute specifies the trunk conditioning data byte to be 
      substituted into the timeslots defined by the Chan component under 
      fault conditions. 
      
      replacementData can be set to any two digit hexadecimal number. 
      The following are recommended values:
      DS1 MUX Out Of Service Code = 0x1A
      E1 MUX Out Of Service Code = 0xFF"
   DEFVAL     { 255 }
::= { lpDS1ChanTcProvEntry 1 }

lpDS1ChanTcSignalOneDuration OBJECT-TYPE
   SYNTAX     Unsigned32 (0..60)
   ACCESS     read-write
   STATUS     mandatory
   DESCRIPTION
     "This attribute specifies the time duration in seconds for which 
      signalOne is substituted into the appropriate signaling bits, when a 
      lineType that uses CAS has been defined. When signalOneDuration 
      has expired signalTwo is substituted into the appropriate signaling 
      bits.
      
      If signalOneDuration is set to zero then only signalTwo is 
      substituted into the appropriate signaling bits during error 
      conditions.
      
      signalOneDuration can be set to any integer value from 0 to 60 
      seconds."
   DEFVAL     { 0 }
::= { lpDS1ChanTcProvEntry 2 }

lpDS1ChanTcOpTable OBJECT-TYPE
   SYNTAX     SEQUENCE OF LpDS1ChanTcOpEntry
   ACCESS     not-accessible
   STATUS     mandatory
   DESCRIPTION
     "This group contains all specific operational data for a Tc 
      component."
::= { lpDS1ChanTc 11 }

lpDS1ChanTcOpEntry OBJECT-TYPE
   SYNTAX     LpDS1ChanTcOpEntry
   ACCESS     not-accessible
   STATUS     mandatory
   DESCRIPTION
     "An entry in the lpDS1ChanTcOpTable."
   INDEX {
      lpIndex,
      lpDS1Index,
      lpDS1ChanIndex,
      lpDS1ChanTcIndex }
::= { lpDS1ChanTcOpTable 1 }

LpDS1ChanTcOpEntry ::= SEQUENCE {
   lpDS1ChanTcIngressConditioning
      INTEGER,
   lpDS1ChanTcEgressConditioning
      INTEGER }

lpDS1ChanTcIngressConditioning OBJECT-TYPE
   SYNTAX     INTEGER  {
                 off(0),
                 on(1) }
   ACCESS     read-only
   STATUS     mandatory
   DESCRIPTION
     "This attribute indicates the status of locally generated trunk 
      conditioning towards the ATM network.
      
      When trunk conditioning is being locally generated towards the 
      ATM network, ingressConditioning is set to on.
      
      When trunk conditioning is not being locally generated towards the 
      ATM network, ingressConditioning is set to off.
      
      Trunk conditioning is transmitted towards the ATM network under 
      the following conditions:
      lossOfSignal (LOS)
      lossOfFrame (LOF)
      remoteAlarmIndication (RAI)
      alarmIndicationSignal (AIS)
      bufferUnderflow (BU)
      and in addition for E1:
      lossOfMultiframe (LOMF)
      receiveMultiframeRemoteAlarmIndication (RMRAI)"
   DEFVAL     { off }
::= { lpDS1ChanTcOpEntry 1 }

lpDS1ChanTcEgressConditioning OBJECT-TYPE
   SYNTAX     INTEGER  {
                 off(0),
                 on(1) }
   ACCESS     read-only
   STATUS     mandatory
   DESCRIPTION
     "This attribute indicates the status of locally generated trunk 
      conditioning towards the PDH line.
      
      When trunk conditioning is being locally generated towards the 
      PDH line, egressConditioning is set to on.
      
      When trunk conditioning is not being locally generated towards the 
      PDH line, egressConditioning is set to off.
      
      Trunk conditioning is transmitted towards the PDH line under the 
      following conditions:
      bufferUnderflow (BU)
      AAL1 protocol errors."
   DEFVAL     { off }
::= { lpDS1ChanTcOpEntry 2 }

lpDS1ChanTcSigOneTable OBJECT-TYPE
   SYNTAX     SEQUENCE OF LpDS1ChanTcSigOneEntry
   ACCESS     not-accessible
   STATUS     mandatory
   DESCRIPTION
     "This attribute specifies the value to be substituted into the ABCD 
      signaling bits for the timeslots defined by the Chan component 
      under fault conditions. The value will be substituted for the duration 
      provisioned in signalOneDuration when a lineType that uses CAS 
      has been defined. 
      
      For a lineType of d4Cas (Super Frame), signaling bits C and D are 
      required to equal bits A and B respectively."
::= { lpDS1ChanTc 398 }

lpDS1ChanTcSigOneEntry OBJECT-TYPE
   SYNTAX     LpDS1ChanTcSigOneEntry
   ACCESS     not-accessible
   STATUS     mandatory
   DESCRIPTION
     "An entry in the lpDS1ChanTcSigOneTable."
   INDEX {
      lpIndex,
      lpDS1Index,
      lpDS1ChanIndex,
      lpDS1ChanTcIndex,
      lpDS1ChanTcSigOneIndex }
::= { lpDS1ChanTcSigOneTable 1 }

LpDS1ChanTcSigOneEntry ::= SEQUENCE {
   lpDS1ChanTcSigOneIndex
      INTEGER,
   lpDS1ChanTcSigOneValue
      Unsigned32 }

lpDS1ChanTcSigOneIndex OBJECT-TYPE
   SYNTAX     INTEGER  {
                 d(0),
                 c(1),
                 b(2),
                 a(3) }
   ACCESS     not-accessible
   STATUS     mandatory
   DESCRIPTION
     "This variable represents the lpDS1ChanTcSigOneTable
      specific index for the lpDS1ChanTcSigOneTable."
::= { lpDS1ChanTcSigOneEntry 1 }

lpDS1ChanTcSigOneValue OBJECT-TYPE
   SYNTAX     Unsigned32 (0..1)
   ACCESS     read-write
   STATUS     mandatory
   DESCRIPTION
     "This variable represents an individual value for the
      lpDS1ChanTcSigOneTable."
::= { lpDS1ChanTcSigOneEntry 2 }

lpDS1ChanTcSigTwoTable OBJECT-TYPE
   SYNTAX     SEQUENCE OF LpDS1ChanTcSigTwoEntry
   ACCESS     not-accessible
   STATUS     mandatory
   DESCRIPTION
     "This attribute specifies the value to be substituted into the ABCD 
      signaling bits for the timeslots defined by the Chan component 
      under fault conditions. The value will be substituted after the 
      duration provisioned in signalOneDuration has expired and when a 
      lineType that uses CAS has been defined. 
      
      For a lineType of d4Cas (Super Frame), signaling bits C and D are 
      required to equal bits A and B respectively."
::= { lpDS1ChanTc 399 }

lpDS1ChanTcSigTwoEntry OBJECT-TYPE
   SYNTAX     LpDS1ChanTcSigTwoEntry
   ACCESS     not-accessible
   STATUS     mandatory
   DESCRIPTION
     "An entry in the lpDS1ChanTcSigTwoTable."
   INDEX {
      lpIndex,
      lpDS1Index,
      lpDS1ChanIndex,
      lpDS1ChanTcIndex,
      lpDS1ChanTcSigTwoIndex }
::= { lpDS1ChanTcSigTwoTable 1 }

LpDS1ChanTcSigTwoEntry ::= SEQUENCE {
   lpDS1ChanTcSigTwoIndex
      INTEGER,
   lpDS1ChanTcSigTwoValue
      Unsigned32 }

lpDS1ChanTcSigTwoIndex OBJECT-TYPE
   SYNTAX     INTEGER  {
                 d(0),
                 c(1),
                 b(2),
                 a(3) }
   ACCESS     not-accessible
   STATUS     mandatory
   DESCRIPTION
     "This variable represents the lpDS1ChanTcSigTwoTable
      specific index for the lpDS1ChanTcSigTwoTable."
::= { lpDS1ChanTcSigTwoEntry 1 }

lpDS1ChanTcSigTwoValue OBJECT-TYPE
   SYNTAX     Unsigned32 (0..1)
   ACCESS     read-write
   STATUS     mandatory
   DESCRIPTION
     "This variable represents an individual value for the
      lpDS1ChanTcSigTwoTable."
::= { lpDS1ChanTcSigTwoEntry 2 }


-- 
-- The Test component is configured to control a hardware facility test 
-- on a physical (V35, X21, DS1, E1, DS3, E3 etc.) or a logical port.

lpDS1Test OBJECT IDENTIFIER ::= { lpDS1 3 }



lpDS1TestRowStatusTable OBJECT-TYPE
   SYNTAX     SEQUENCE OF LpDS1TestRowStatusEntry
   ACCESS     not-accessible
   STATUS     mandatory
   DESCRIPTION
     "This entry controls the addition and deletion of 
      lpDS1Test components."
::= { lpDS1Test 1 }

lpDS1TestRowStatusEntry OBJECT-TYPE
   SYNTAX     LpDS1TestRowStatusEntry
   ACCESS     not-accessible
   STATUS     mandatory
   DESCRIPTION
     "A single entry in the table represents a single 
      lpDS1Test component."
   INDEX {
      lpIndex,
      lpDS1Index,
      lpDS1TestIndex }
::= { lpDS1TestRowStatusTable 1 }

LpDS1TestRowStatusEntry ::= SEQUENCE {
   lpDS1TestRowStatus
      RowStatus,
   lpDS1TestComponentName
      DisplayString,
   lpDS1TestStorageType
      StorageType,
   lpDS1TestIndex
      NonReplicated }

lpDS1TestRowStatus OBJECT-TYPE
   SYNTAX     RowStatus 
   ACCESS     read-only
   STATUS     mandatory
   DESCRIPTION
     "This variable is used as the basis for SNMP naming of
      lpDS1Test components.
      These components cannot be added nor deleted."
::= { lpDS1TestRowStatusEntry 1 }

lpDS1TestComponentName OBJECT-TYPE
   SYNTAX     DisplayString 
   ACCESS     read-only
   STATUS     mandatory
   DESCRIPTION
     "This variable provides the component's string name for
      use with the ASCII Console Interface"
::= { lpDS1TestRowStatusEntry 2 }

lpDS1TestStorageType OBJECT-TYPE
   SYNTAX     StorageType 
   ACCESS     read-only
   STATUS     mandatory
   DESCRIPTION
     "This variable represents the storage type value for the
      lpDS1Test tables."
::= { lpDS1TestRowStatusEntry 4 }

lpDS1TestIndex OBJECT-TYPE
   SYNTAX     NonReplicated 
   ACCESS     not-accessible
   STATUS     mandatory
   DESCRIPTION
     "This variable represents the index for the lpDS1Test tables."
::= { lpDS1TestRowStatusEntry 10 }

lpDS1TestStateTable OBJECT-TYPE
   SYNTAX     SEQUENCE OF LpDS1TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpDS1Test 10 }

lpDS1TestStateEntry OBJECT-TYPE
   SYNTAX     LpDS1TestStateEntry
   ACCESS     not-accessible
   STATUS     mandatory
   DESCRIPTION
     "An entry in the lpDS1TestStateTable."
   INDEX {
      lpIndex,
      lpDS1Index,
      lpDS1TestIndex }
::= { lpDS1TestStateTable 1 }

LpDS1TestStateEntry ::= SEQUENCE {
   lpDS1TestAdminState
      INTEGER,
   lpDS1TestOperationalState
      INTEGER,
   lpDS1TestUsageState
      INTEGER }

lpDS1TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpDS1TestStateEntry 1 }

lpDS1TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpDS1TestStateEntry 2 }

lpDS1TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpDS1TestStateEntry 3 }

lpDS1TestSetupTable OBJECT-TYPE
   SYNTAX     SEQUENCE OF LpDS1TestSetupEntry
   ACCESS     not-accessible
   STATUS     mandatory
   DESCRIPTION
     "This group contains all of the operational data for a Test 
      component."
::= { lpDS1Test 11 }

lpDS1TestSetupEntry OBJECT-TYPE
   SYNTAX     LpDS1TestSetupEntry
   ACCESS     not-accessible
   STATUS     mandatory
   DESCRIPTION
     "An entry in the lpDS1TestSetupTable."
   INDEX {
      lpIndex,
      lpDS1Index,
      lpDS1TestIndex }
::= { lpDS1TestSetupTable 1 }

LpDS1TestSetupEntry ::= SEQUENCE {
   lpDS1TestPurpose
      AsciiString,
   lpDS1TestType
      INTEGER,
   lpDS1TestFrmSize
      Unsigned32,
   lpDS1TestFrmPatternType
      INTEGER,
   lpDS1TestCustomizedPattern
      Hex,
   lpDS1TestDataStartDelay
      Unsigned32,
   lpDS1TestDisplayInterval
      Unsigned32,
   lpDS1TestDuration
      Unsigned32 }

lpDS1TestPurpose OBJECT-TYPE
   SYNTAX     AsciiString (SIZE (0..40))
   ACCESS     read-write
   STATUS     mandatory
   DESCRIPTION
     "This attribute records the purpose of the test so that the test results 
      can be associated and properly analyzed."
::= { lpDS1TestSetupEntry 1 }

lpDS1TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpDS1TestSetupEntry 2 }

lpDS1TestFrmSize OBJECT-TYPE
   SYNTAX     Unsigned32 (4..4096)
   ACCESS     read-write
   STATUS     mandatory
   DESCRIPTION
     "This attribute defines the size of the test data frames in number of 
      bytes."
   DEFVAL     { 1024 }
::= { lpDS1TestSetupEntry 3 }

lpDS1TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpDS1TestSetupEntry 4 }

lpDS1TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpDS1TestSetupEntry 5 }

lpDS1TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpDS1TestSetupEntry 6 }

lpDS1TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpDS1TestSetupEntry 7 }

lpDS1TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpDS1TestSetupEntry 8 }

lpDS1TestResultsTable OBJECT-TYPE
   SYNTAX     SEQUENCE OF LpDS1TestResultsEntry
   ACCESS     not-accessible
   STATUS     mandatory
   DESCRIPTION
     "This group contains all the statistics related attributes of the Test 
      component."
::= { lpDS1Test 12 }

lpDS1TestResultsEntry OBJECT-TYPE
   SYNTAX     LpDS1TestResultsEntry
   ACCESS     not-accessible
   STATUS     mandatory
   DESCRIPTION
     "An entry in the lpDS1TestResultsTable."
   INDEX {
      lpIndex,
      lpDS1Index,
      lpDS1TestIndex }
::= { lpDS1TestResultsTable 1 }

LpDS1TestResultsEntry ::= SEQUENCE {
   lpDS1TestElapsedTime
      Counter32,
   lpDS1TestTimeRemaining
      Unsigned32,
   lpDS1TestCauseOfTermination
      INTEGER,
   lpDS1TestBitsTx
      PassportCounter64,
   lpDS1TestBytesTx
      PassportCounter64,
   lpDS1TestFrmTx
      PassportCounter64,
   lpDS1TestBitsRx
      PassportCounter64,
   lpDS1TestBytesRx
      PassportCounter64,
   lpDS1TestFrmRx
      PassportCounter64,
   lpDS1TestErroredFrmRx
      PassportCounter64,
   lpDS1TestBitErrorRate
      AsciiString }

lpDS1TestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpDS1TestResultsEntry 1 }

lpDS1TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpDS1TestResultsEntry 2 }

lpDS1TestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpDS1TestResultsEntry 3 }

lpDS1TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpDS1TestResultsEntry 4 }

lpDS1TestBytesTx OBJECT-TYPE
   SYNTAX     PassportCounter64 
   ACCESS     read-only
   STATUS     mandatory
   DESCRIPTION
     "This attribute is the total number of bytes sent during the test 
      period. This counter is not expected to reach its maximum value."
::= { lpDS1TestResultsEntry 5 }

lpDS1TestFrmTx OBJECT-TYPE
   SYNTAX     PassportCounter64 
   ACCESS     read-only
   STATUS     mandatory
   DESCRIPTION
     "This attribute is the total number of frames sent during the test 
      period. This counter is not expected to reach its maximum value."
::= { lpDS1TestResultsEntry 6 }

lpDS1TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpDS1TestResultsEntry 7 }

lpDS1TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpDS1TestResultsEntry 8 }

lpDS1TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpDS1TestResultsEntry 9 }

lpDS1TestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpDS1TestResultsEntry 10 }

lpDS1TestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpDS1TestResultsEntry 11 }


-- LogicalProcessor/n Ds1/0 Dsp
-- The Dsp component presents the status of the Digital Signal 
-- Processors (DSPs) present on a voice card.
-- A voice card's Dsp component is created automatically whenever 
-- the parent DS1 component becomes active, and remains in 
-- existence as long as the card remains operational. Dsp components 
-- cannot be added or deleted.

lpDS1Dsp OBJECT IDENTIFIER ::= { lpDS1 4 }



lpDS1DspRowStatusTable OBJECT-TYPE
   SYNTAX     SEQUENCE OF LpDS1DspRowStatusEntry
   ACCESS     not-accessible
   STATUS     mandatory
   DESCRIPTION
     "This entry controls the addition and deletion of 
      lpDS1Dsp components."
::= { lpDS1Dsp 1 }

lpDS1DspRowStatusEntry OBJECT-TYPE
   SYNTAX     LpDS1DspRowStatusEntry
   ACCESS     not-accessible
   STATUS     mandatory
   DESCRIPTION
     "A single entry in the table represents a single 
      lpDS1Dsp component."
   INDEX {
      lpIndex,
      lpDS1Index,
      lpDS1DspIndex }
::= { lpDS1DspRowStatusTable 1 }

LpDS1DspRowStatusEntry ::= SEQUENCE {
   lpDS1DspRowStatus
      RowStatus,
   lpDS1DspComponentName
      DisplayString,
   lpDS1DspStorageType
      StorageType,
   lpDS1DspIndex
      NonReplicated }

lpDS1DspRowStatus OBJECT-TYPE
   SYNTAX     RowStatus 
   ACCESS     read-only
   STATUS     mandatory
   DESCRIPTION
     "This variable is used as the basis for SNMP naming of
      lpDS1Dsp components.
      These components cannot be added nor deleted."
::= { lpDS1DspRowStatusEntry 1 }

lpDS1DspComponentName OBJECT-TYPE
   SYNTAX     DisplayString 
   ACCESS     read-only
   STATUS     mandatory
   DESCRIPTION
     "This variable provides the component's string name for
      use with the ASCII Console Interface"
::= { lpDS1DspRowStatusEntry 2 }

lpDS1DspStorageType OBJECT-TYPE
   SYNTAX     StorageType 
   ACCESS     read-only
   STATUS     mandatory
   DESCRIPTION
     "This variable represents the storage type value for the
      lpDS1Dsp tables."
::= { lpDS1DspRowStatusEntry 4 }

lpDS1DspIndex OBJECT-TYPE
   SYNTAX     NonReplicated 
   ACCESS     not-accessible
   STATUS     mandatory
   DESCRIPTION
     "This variable represents the index for the lpDS1Dsp tables."
::= { lpDS1DspRowStatusEntry 10 }


-- LogicalProcessor/n Ds1/0 Audio
-- The Audio component presents the audio status of all timeslots on a 
-- given DS1.
-- A voice card's Audio component is created automatically whenever 
-- the parent DS1 component becomes active, and remains in 
-- existence as long as the card remains operational. Audio 
-- components cannot be added or deleted.

lpDS1Audio OBJECT IDENTIFIER ::= { lpDS1 5 }



lpDS1AudioRowStatusTable OBJECT-TYPE
   SYNTAX     SEQUENCE OF LpDS1AudioRowStatusEntry
   ACCESS     not-accessible
   STATUS     mandatory
   DESCRIPTION
     "This entry controls the addition and deletion of 
      lpDS1Audio components."
::= { lpDS1Audio 1 }

lpDS1AudioRowStatusEntry OBJECT-TYPE
   SYNTAX     LpDS1AudioRowStatusEntry
   ACCESS     not-accessible
   STATUS     mandatory
   DESCRIPTION
     "A single entry in the table represents a single 
      lpDS1Audio component."
   INDEX {
      lpIndex,
      lpDS1Index,
      lpDS1AudioIndex }
::= { lpDS1AudioRowStatusTable 1 }

LpDS1AudioRowStatusEntry ::= SEQUENCE {
   lpDS1AudioRowStatus
      RowStatus,
   lpDS1AudioComponentName
      DisplayString,
   lpDS1AudioStorageType
      StorageType,
   lpDS1AudioIndex
      NonReplicated }

lpDS1AudioRowStatus OBJECT-TYPE
   SYNTAX     RowStatus 
   ACCESS     read-only
   STATUS     mandatory
   DESCRIPTION
     "This variable is used as the basis for SNMP naming of
      lpDS1Audio components.
      These components cannot be added nor deleted."
::= { lpDS1AudioRowStatusEntry 1 }

lpDS1AudioComponentName OBJECT-TYPE
   SYNTAX     DisplayString 
   ACCESS     read-only
   STATUS     mandatory
   DESCRIPTION
     "This variable provides the component's string name for
      use with the ASCII Console Interface"
::= { lpDS1AudioRowStatusEntry 2 }

lpDS1AudioStorageType OBJECT-TYPE
   SYNTAX     StorageType 
   ACCESS     read-only
   STATUS     mandatory
   DESCRIPTION
     "This variable represents the storage type value for the
      lpDS1Audio tables."
::= { lpDS1AudioRowStatusEntry 4 }

lpDS1AudioIndex OBJECT-TYPE
   SYNTAX     NonReplicated 
   ACCESS     not-accessible
   STATUS     mandatory
   DESCRIPTION
     "This variable represents the index for the lpDS1Audio tables."
::= { lpDS1AudioRowStatusEntry 10 }


-- Lp/n E1/n
-- The E1 component controls an E1 port on an E1 Function 
-- Processor. Frame-based cards support up to four ports, cell-based 
-- cards support up to eight ports, and AAL1 cards support up to four 
-- ports.

lpE1 OBJECT IDENTIFIER ::= { lp 8 }



lpE1RowStatusTable OBJECT-TYPE
   SYNTAX     SEQUENCE OF LpE1RowStatusEntry
   ACCESS     not-accessible
   STATUS     mandatory
   DESCRIPTION
     "This entry controls the addition and deletion of 
      lpE1 components."
::= { lpE1 1 }

lpE1RowStatusEntry OBJECT-TYPE
   SYNTAX     LpE1RowStatusEntry
   ACCESS     not-accessible
   STATUS     mandatory
   DESCRIPTION
     "A single entry in the table represents a single 
      lpE1 component."
   INDEX {
      lpIndex,
      lpE1Index }
::= { lpE1RowStatusTable 1 }

LpE1RowStatusEntry ::= SEQUENCE {
   lpE1RowStatus
      RowStatus,
   lpE1ComponentName
      DisplayString,
   lpE1StorageType
      StorageType,
   lpE1Index
      Integer32 }

lpE1RowStatus OBJECT-TYPE
   SYNTAX     RowStatus 
   ACCESS     read-write
   STATUS     mandatory
   DESCRIPTION
     "This variable is used as the basis for SNMP naming of
      lpE1 components.
      These components can be added and deleted."
::= { lpE1RowStatusEntry 1 }

lpE1ComponentName OBJECT-TYPE
   SYNTAX     DisplayString 
   ACCESS     read-only
   STATUS     mandatory
   DESCRIPTION
     "This variable provides the component's string name for
      use with the ASCII Console Interface"
::= { lpE1RowStatusEntry 2 }

lpE1StorageType OBJECT-TYPE
   SYNTAX     StorageType 
   ACCESS     read-only
   STATUS     mandatory
   DESCRIPTION
     "This variable represents the storage type value for the
      lpE1 tables."
::= { lpE1RowStatusEntry 4 }

lpE1Index OBJECT-TYPE
   SYNTAX     Integer32 (0..32)
   ACCESS     not-accessible
   STATUS     mandatory
   DESCRIPTION
     "This variable represents the index for the lpE1 tables."
::= { lpE1RowStatusEntry 10 }

lpE1ProvTable OBJECT-TYPE
   SYNTAX     SEQUENCE OF LpE1ProvEntry
   ACCESS     not-accessible
   STATUS     mandatory
   DESCRIPTION
     "This group contains all of the provisioning data for an E1 
      component."
::= { lpE1 10 }

lpE1ProvEntry OBJECT-TYPE
   SYNTAX     LpE1ProvEntry
   ACCESS     not-accessible
   STATUS     mandatory
   DESCRIPTION
     "An entry in the lpE1ProvTable."
   INDEX {
      lpIndex,
      lpE1Index }
::= { lpE1ProvTable 1 }

LpE1ProvEntry ::= SEQUENCE {
   lpE1LineType
      INTEGER,
   lpE1ClockingSource
      INTEGER,
   lpE1Crc4Mode
      INTEGER,
   lpE1SendRaiOnAis
      INTEGER,
   lpE1RaiDeclareAlarmTime
      Unsigned32,
   lpE1RaiClearAlarmTime
      Unsigned32 }

lpE1LineType OBJECT-TYPE
   SYNTAX     INTEGER  {
                 ccs(2),
                 cas(3),
                 unframed(6) }
   ACCESS     read-write
   STATUS     mandatory
   DESCRIPTION
     "This attribute specifies the framing of the E1 line.
      When cas (channel associated signalling) is selected, timeslot 16 is 
      reserved for multiframe signalling and only 30 timeslots are 
      available for data. The signalling bits are not interpreted.
      When ccs (common channel signalling) is selected, timeslot 16 is 
      not reserved for multiframe signalling and 31 timeslots are available 
      for data. The signalling bits are not interpreted. 
      When unframed is selected, a clear channel is defined whereby data 
      from all timeslots including the framing data (in timeslot 0) and 
      timeslot 16 are passed transparently. This value is valid only for 
      AAL1 cards.
      
      For cell-based cards the ATM Forum specifies that timeslot 16 be 
      reserved, leaving 30 timeslots available for data.
      
      The default value is cas except for the 8pE1Atm card, for which the 
      default and only valid value is ccs."
::= { lpE1ProvEntry 1 }

lpE1ClockingSource OBJECT-TYPE
   SYNTAX     INTEGER  {
                 local(0),
                 line(1),
                 module(2),
                 otherPort(3),
                 srtsMode(4) }
   ACCESS     read-write
   STATUS     mandatory
   DESCRIPTION
     "This attribute defines the source of the transmit clock for the E1 
      line.
      When local is selected, the crystal on the port generates the 
      clocking for the line.
      When line is selected, the port synchronizes to the clock from the 
      facility.
      When module is selected, the ports clock synchronizes to the clock 
      provided by the oscillator on the active CP.
      When otherPort is selected, the port synchronizes to the port with a 
      clocking source of line.
      When srtsMode is selected, the port sychronization is taken from 
      the SRTS (Synchronous Residual Time Stamp) bits within the ATM 
      cell.
      If the NetworkSynchronization (NS) component is present the 
      default value of this attribute will be module otherwise it will 
      default to line except for the 3pE1Atm card which defaults to local.
      
      The 3pE1Atm card has one common clock source for all ports and 
      does not support the line clock source; all three ports must have the 
      same value, either local or module.
      
      The clockingSource values otherPort and srtsMode are only valid 
      for the AAL1 cards.
      
      For the AAL1 cards either:
      all four ports' clockingSource values must be local OR
      all four ports' clockingSource values must be module OR
      one port's clockingSource value must be line and the other three 
      must be otherPort. A port can only have srtsMode selected if the 
      other ports are module or srtsMode."
::= { lpE1ProvEntry 2 }

lpE1Crc4Mode OBJECT-TYPE
   SYNTAX     INTEGER  {
                 on(0),
                 off(1) }
   ACCESS     read-write
   STATUS     mandatory
   DESCRIPTION
     "This attribute defines whether the CRC-4 checking and generation 
      on the E1 line is enabled or disabled.
      
      The default CRC-4 mode is off except for the cell-based cards 
      which default to on as per the ATM Forum."
::= { lpE1ProvEntry 3 }

lpE1SendRaiOnAis OBJECT-TYPE
   SYNTAX     INTEGER  {
                 no(0),
                 yes(1) }
   ACCESS     read-write
   STATUS     mandatory
   DESCRIPTION
     "This attribute defines whether the Remote Alarm Indicator (RAI) 
      will be sent when receiving an AIS alarm. The value is yes by 
      default; it can be changed to no only for ports on J2MV cards."
   DEFVAL     { yes }
::= { lpE1ProvEntry 4 }

lpE1RaiDeclareAlarmTime OBJECT-TYPE
   SYNTAX     Unsigned32 (0 | 1..20000)
   ACCESS     read-write
   STATUS     mandatory
   DESCRIPTION
     "This attribute specifies the period of time that a Remote Alarm 
      Indicator (RAI) must be present before declaring an RAI alarm. The 
      value of auto sets the RAI declare time to the default value for E1 
      and E1C card types which do not have hardware support for RAI 
      response. On E1C card types with hardware support, if the value of 
      auto is set, RAI response is done according to the standards. If auto 
      is set, the value of the raiClearAlarmTime attribute is ignored and 
      auto is used. This attribute is for E1 and E1C card types only. For 
      all other card types, the default value must be used.

      VALUES (

      0 = auto

      )"
   DEFVAL     { 100 }
::= { lpE1ProvEntry 5 }

lpE1RaiClearAlarmTime OBJECT-TYPE
   SYNTAX     Unsigned32 (0 | 1..20000)
   ACCESS     read-write
   STATUS     mandatory
   DESCRIPTION
     "This attribute specifies the period of time that a Remote Alarm 
      Indicator (RAI) has been absent before clearing an RAI alarm. The 
      value of auto sets the RAI clear time to the default value for E1 and 
      E1C card types which do not have hardware support for RAI 
      response. On E1C card types with hardware support, if the value of 
      auto is set, RAI response is done according to the standards. If auto 
      is set, the value of the raiDeclareAlarmTime attribute is ignored and 
      auto is used. This attribute is for E1 and E1C card types only. For 
      all other card types, the default value must be used.

      VALUES (

      0 = auto

      )"
   DEFVAL     { 100 }
::= { lpE1ProvEntry 6 }

lpE1CidDataTable OBJECT-TYPE
   SYNTAX     SEQUENCE OF LpE1CidDataEntry
   ACCESS     not-accessible
   STATUS     mandatory
   DESCRIPTION
     "This group contains the attribute for a component's Customer 
      Identifier (CID). Refer to the attribute description for a detailed 
      explanation of CIDs."
::= { lpE1 11 }

lpE1CidDataEntry OBJECT-TYPE
   SYNTAX     LpE1CidDataEntry
   ACCESS     not-accessible
   STATUS     mandatory
   DESCRIPTION
     "An entry in the lpE1CidDataTable."
   INDEX {
      lpIndex,
      lpE1Index }
::= { lpE1CidDataTable 1 }

LpE1CidDataEntry ::= SEQUENCE {
   lpE1CustomerIdentifier
      Unsigned32 }

lpE1CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpE1CidDataEntry 1 }

lpE1AdminInfoTable OBJECT-TYPE
   SYNTAX     SEQUENCE OF LpE1AdminInfoEntry
   ACCESS     not-accessible
   STATUS     mandatory
   DESCRIPTION
     "This group contains the attributes pertaining to the vendor of the 
      equipment."
::= { lpE1 12 }

lpE1AdminInfoEntry OBJECT-TYPE
   SYNTAX     LpE1AdminInfoEntry
   ACCESS     not-accessible
   STATUS     mandatory
   DESCRIPTION
     "An entry in the lpE1AdminInfoTable."
   INDEX {
      lpIndex,
      lpE1Index }
::= { lpE1AdminInfoTable 1 }

LpE1AdminInfoEntry ::= SEQUENCE {
   lpE1Vendor
      AsciiString,
   lpE1CommentText
      AsciiString }

lpE1Vendor OBJECT-TYPE
   SYNTAX     AsciiString (SIZE (0..20))
   ACCESS     read-write
   STATUS     mandatory
   DESCRIPTION
     "This is the name of the vendor supplying the facility."
::= { lpE1AdminInfoEntry 1 }

lpE1CommentText OBJECT-TYPE
   SYNTAX     AsciiString (SIZE (0..60))
   ACCESS     read-write
   STATUS     mandatory
   DESCRIPTION
     "Any miscellaneous text about the facility."
::= { lpE1AdminInfoEntry 2 }

lpE1IfEntryTable OBJECT-TYPE
   SYNTAX     SEQUENCE OF LpE1IfEntryEntry
   ACCESS     not-accessible
   STATUS     mandatory
   DESCRIPTION
     "This group contains the provisionable attributes for the ifEntry."
::= { lpE1 13 }

lpE1IfEntryEntry OBJECT-TYPE
   SYNTAX     LpE1IfEntryEntry
   ACCESS     not-accessible
   STATUS     mandatory
   DESCRIPTION
     "An entry in the lpE1IfEntryTable."
   INDEX {
      lpIndex,
      lpE1Index }
::= { lpE1IfEntryTable 1 }

LpE1IfEntryEntry ::= SEQUENCE {
   lpE1IfAdminStatus
      INTEGER,
   lpE1IfIndex
      InterfaceIndex }

lpE1IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpE1IfEntryEntry 1 }

lpE1IfIndex OBJECT-TYPE
   SYNTAX     InterfaceIndex (1..65535)
   ACCESS     read-only
   STATUS     mandatory
   DESCRIPTION
     "This is the index for the IfEntry. Its value is automatically initialized 
      during the provisioning process."
::= { lpE1IfEntryEntry 2 }

lpE1OperStatusTable OBJECT-TYPE
   SYNTAX     SEQUENCE OF LpE1OperStatusEntry
   ACCESS     not-accessible
   STATUS     mandatory
   DESCRIPTION
     "This group includes the Operational Status attribute. This attribute 
      defines the current operational state of this component."
::= { lpE1 14 }

lpE1OperStatusEntry OBJECT-TYPE
   SYNTAX     LpE1OperStatusEntry
   ACCESS     not-accessible
   STATUS     mandatory
   DESCRIPTION
     "An entry in the lpE1OperStatusTable."
   INDEX {
      lpIndex,
      lpE1Index }
::= { lpE1OperStatusTable 1 }

LpE1OperStatusEntry ::= SEQUENCE {
   lpE1SnmpOperStatus
      INTEGER }

lpE1SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpE1OperStatusEntry 1 }

lpE1StateTable OBJECT-TYPE
   SYNTAX     SEQUENCE OF LpE1StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpE1 15 }

lpE1StateEntry OBJECT-TYPE
   SYNTAX     LpE1StateEntry
   ACCESS     not-accessible
   STATUS     mandatory
   DESCRIPTION
     "An entry in the lpE1StateTable."
   INDEX {
      lpIndex,
      lpE1Index }
::= { lpE1StateTable 1 }

LpE1StateEntry ::= SEQUENCE {
   lpE1AdminState
      INTEGER,
   lpE1OperationalState
      INTEGER,
   lpE1UsageState
      INTEGER,
   lpE1AvailabilityStatus
      OCTET STRING,
   lpE1ProceduralStatus
      OCTET STRING,
   lpE1ControlStatus
      OCTET STRING,
   lpE1AlarmStatus
      OCTET STRING,
   lpE1StandbyStatus
      INTEGER,
   lpE1UnknownStatus
      INTEGER }

lpE1AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpE1StateEntry 1 }

lpE1OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpE1StateEntry 2 }

lpE1UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpE1StateEntry 3 }

lpE1AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpE1StateEntry 4 }

lpE1ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpE1StateEntry 5 }

lpE1ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpE1StateEntry 6 }

lpE1AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpE1StateEntry 7 }

lpE1StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpE1StateEntry 8 }

lpE1UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpE1StateEntry 9 }

lpE1OperTable OBJECT-TYPE
   SYNTAX     SEQUENCE OF LpE1OperEntry
   ACCESS     not-accessible
   STATUS     mandatory
   DESCRIPTION
     "This group contains the common operational data for a component 
      in a digital hierarchy interface."
::= { lpE1 16 }

lpE1OperEntry OBJECT-TYPE
   SYNTAX     LpE1OperEntry
   ACCESS     not-accessible
   STATUS     mandatory
   DESCRIPTION
     "An entry in the lpE1OperTable."
   INDEX {
      lpIndex,
      lpE1Index }
::= { lpE1OperTable 1 }

LpE1OperEntry ::= SEQUENCE {
   lpE1LosAlarm
      INTEGER,
   lpE1RxAisAlarm
      INTEGER,
   lpE1LofAlarm
      INTEGER,
   lpE1RxRaiAlarm
      INTEGER,
   lpE1TxAisAlarm
      INTEGER,
   lpE1TxRaiAlarm
      INTEGER }

lpE1LosAlarm OBJECT-TYPE
   SYNTAX     INTEGER  {
                 on(0),
                 off(1) }
   ACCESS     read-only
   STATUS     mandatory
   DESCRIPTION
     "This attribute displays whether a LOS (Loss of Signal) alarm state 
      has been entered. A LOS alarm is declared after LOS defects have 
      been observed and accumulated for a period of 2 seconds +/- 0.5 
      seconds (for 3pDS1Atm, 3pE1Atm, 8pDS1Atm, and 8pE1Atm 
      cards: 2.5 seconds +/- 0.5 seconds).  A LOS defect is detected upon 
      observing all zeros for 150 ms (for 3pDS1Atm, 3pE1Atm, 
      8pDS1Atm, and 8pE1Atm cards: upon observing 175 +/- 75 pulse 
      positions with no pulses of either positive or negative polarity). If 
      the LOS defects are intermittently occurring, the LOS defect 
      accumulator is decremented at a rate of 1/10 of the incrementing 
      rate (alarm integration ratio of 1/10), with all measurements based 
      on a 200 ms polling cycle.
      The port goes into an operational state of disabled until the LOS 
      alarm state is cleared. Also, an RAI alarm is transmitted to the far 
      end for the duration of the LOS alarm state.
      The LOS alarm state is cleared when LOS defects are absent for 10 
      seconds +/- 0.5 seconds."
   DEFVAL     { off }
::= { lpE1OperEntry 1 }

lpE1RxAisAlarm OBJECT-TYPE
   SYNTAX     INTEGER  {
                 on(0),
                 off(1) }
   ACCESS     read-only
   STATUS     mandatory
   DESCRIPTION
     "This attribute displays whether an AIS (Alarm Indication Signal) 
      alarm state has been entered. The AIS Alarm state is entered when 
      AIS defects have been observed and accumulated for 2.5 seconds +/
      - 0.5 seconds. An AIS defect is detected after having received less 
      than 3 zeros in a 2048 bit period (for 8pDS1Atm cards: when both 
      an Out Of Frame condition exists and a 1's density of at least 99.9% 
      is present for a time T, where 3 ms  T  75 ms; for 8pE1Atm 
      cards: when both an Out Of Frame condition exists and fewer than 
      three 0's have been received in 512 bit periods). If the AIS defects 
      are intermittently occurring, the AIS defect accumulator is 
      decremented at a rate of 1/10 of the incrementing rate (alarm 
      integration ratio of 1/10), with all measurements based on a 200 ms 
      polling cycle.
      The port goes into an operational state of disabled for the duration 
      of an AIS alarm state.
      The AIS alarm state is cleared when AIS defects are absent for 10 
      seconds +/- 0.5 seconds."
   DEFVAL     { off }
::= { lpE1OperEntry 2 }

lpE1LofAlarm OBJECT-TYPE
   SYNTAX     INTEGER  {
                 on(0),
                 off(1) }
   ACCESS     read-only
   STATUS     mandatory
   DESCRIPTION
     "This attribute displays whether a LOF (Loss of Frame) alarm state 
      has been entered. The LOF alarm state is entered when LOF defects 
      (for DS1: 2 out of 5 framing bits in error; for E1: 3 consecutive 
      frame alignment patterns in error) have been detected for 3 seconds 
      +/- 0.5 seconds (for 3pDS1Atm, 3pE1Atm, 8pDS1Atm, and 
      8pE1Atm cards: 2.5 seconds +/- 0.5 seconds). If the LOF defects 
      are intermittently occurring, the LOF defect accumulator is 
      decremented at a rate of 1/10 of the incrementing rate (alarm 
      integration ratio of 1/10), with all measurements based on a 200 ms 
      polling cycle.
      The port goes into an operational state of disabled until the LOF 
      alarm state is cleared. Also, an RAI alarm is transmitted to the far 
      end for the duration of the LOF alarm state 
      The condition is cleared when framing has been achieved for 10 
      seconds +/- 0.5 seconds."
   DEFVAL     { off }
::= { lpE1OperEntry 3 }

lpE1RxRaiAlarm OBJECT-TYPE
   SYNTAX     INTEGER  {
                 on(0),
                 off(1) }
   ACCESS     read-only
   STATUS     mandatory
   DESCRIPTION
     "This attribute displays whether an RAI (Remote Alarm Indication) 
      alarm state has been entered. An RAI alarm state is entered when 
      the RAI defect indicator has been observed and accumulated for 3.5 
      seconds +/- 0.5 seconds. For 3pDS1Atm, and 8pDS1Atm cards: 
      alarm is declared immediately upon observing the defect is present, 
      with no integration time. For 3pE1Atm, and 8pE1Atm cards: alarm 
      state is entered when the RAI defect indicator has been observed 
      and accumulated for 2.5 seconds +/- 0.5 seconds. If the RAI defects 
      are intermittently occurring, the RAI defect accumulator is 
      decremented at a rate of 1/10 of the incrementing rate (alarm 
      integration ratio of 1/10), with all measurements based on a 200 ms 
      polling cycle. 
      The RAI alarm state is cleared when the RAI defect indicator has 
      been absent for 10 seconds +/- 0.5 seconds (for 3pDS1Atm, and 
      8pDS1Atm cards: alarm is cleared immediately upon observing the 
      defect is absent, with no integration time).
      The RAI alarm is usually an indication that the far end facility is 
      unable to gain synchronization."
   DEFVAL     { off }
::= { lpE1OperEntry 4 }

lpE1TxAisAlarm OBJECT-TYPE
   SYNTAX     INTEGER  {
                 on(0),
                 off(1) }
   ACCESS     read-only
   STATUS     mandatory
   DESCRIPTION
     "This attribute displays whether an AIS (Alarm Indication Signal) 
      alarm is being transmitted on the line. An AIS alarm is transmitted 
      when the port is in a locked state."
   DEFVAL     { off }
::= { lpE1OperEntry 5 }

lpE1TxRaiAlarm OBJECT-TYPE
   SYNTAX     INTEGER  {
                 on(0),
                 off(1) }
   ACCESS     read-only
   STATUS     mandatory
   DESCRIPTION
     "This attribute displays whether a RAI signal is being sent on the 
      outgoing line. The RAI signal is transmitted when the port detects a 
      LOF alarm condition (for 3pDS1Atm, 3pE1Atm, 8pDS1Atm, and 
      8pE1Atm cards: RAI is transmitted when the port detects a LOS, 
      LOF, or AIS condition)."
   DEFVAL     { off }
::= { lpE1OperEntry 6 }

lpE1E1OperTable OBJECT-TYPE
   SYNTAX     SEQUENCE OF LpE1E1OperEntry
   ACCESS     not-accessible
   STATUS     mandatory
   DESCRIPTION
     "This group contains all of the operational data for a E1 component 
      that are not defined in the DSCommonOp group."
::= { lpE1 17 }

lpE1E1OperEntry OBJECT-TYPE
   SYNTAX     LpE1E1OperEntry
   ACCESS     not-accessible
   STATUS     mandatory
   DESCRIPTION
     "An entry in the lpE1E1OperTable."
   INDEX {
      lpIndex,
      lpE1Index }
::= { lpE1E1OperTable 1 }

LpE1E1OperEntry ::= SEQUENCE {
   lpE1MultifrmLofAlarm
      INTEGER,
   lpE1RxMultifrmRaiAlarm
      INTEGER,
   lpE1TxMultifrmRaiAlarm
      INTEGER }

lpE1MultifrmLofAlarm OBJECT-TYPE
   SYNTAX     INTEGER  {
                 on(0),
                 off(1) }
   ACCESS     read-only
   STATUS     mandatory
   DESCRIPTION
     "This attribute indicates whether a multiframe LOF (loss of frame) 
      alarm state is entered. A multiframe LOF alarm state is entered 
      when a multiframe LOF defect (2 consecutive errors in the 
      multiframe alignment signal) has been detected and accumulated 
      for 2.5 seconds +/- 0.5 seconds. If the multiframe LOF defects are 
      intermittently occurring, the multiframe LOF defect accumulator is 
      decremented at a rate of 1/10 of the incrementing rate (alarm 
      integration ratio of 1/10), with all measurements based on a 200 ms 
      polling cycle.
      The alarm is cleared when the defect is not detected for 10 seconds 
      +/- 0.5 seconds. When the multiframe LOF alarm is on, a 
      multiframe RAI alarm indicator is transmitted on the line.
      
      The 8pE1Atm card does not support the multiframe LOF alarm."
   DEFVAL     { off }
::= { lpE1E1OperEntry 1 }

lpE1RxMultifrmRaiAlarm OBJECT-TYPE
   SYNTAX     INTEGER  {
                 on(0),
                 off(1) }
   ACCESS     read-only
   STATUS     mandatory
   DESCRIPTION
     "This attribute displays whether a multiframe RAI (remote alarm 
      indicator) alarm state has been entered. A multiframe RAI alarm 
      state is entered when a multiframe RAI alarm indicator (bit 6 of 
      timeslot 16 in frame 0 is set to a one) is observed and accumulated 
      for 2.5 seconds +/- 0.5 seconds. If the multiframe RAI indicator is 
      intermittently received, the multiframe RAI defect accumulator is 
      decremented at a rate of 1/10 of the incrementing rate (alarm 
      integration ratio of 1/10), with all measurements based on a 200 ms 
      polling cycle.
      The multiframe RAI alarm condition is cleared when the 
      multiframe RAI alarm indication is not received for 10 seconds +/- 
      0.5 seconds. The multiframe RAI alarm is usually an indication that 
      the far end facility is unable to gain multiframe synchronization.
      
      The 8pE1Atm card does not support the multiframe RAI alarm."
   DEFVAL     { off }
::= { lpE1E1OperEntry 2 }

lpE1TxMultifrmRaiAlarm OBJECT-TYPE
   SYNTAX     INTEGER  {
                 on(0),
                 off(1) }
   ACCESS     read-only
   STATUS     mandatory
   DESCRIPTION
     "This attribute displays whether a multiframe RAI (remote alarm 
      indicator) alarm is being sent on the E1 line. This is transmitted 
      when the E1 port detects a multiframe LOF condition.
      
      The 8pE1Atm card does not generate the multiframe RAI alarm."
   DEFVAL     { off }
::= { lpE1E1OperEntry 3 }

lpE1StatsTable OBJECT-TYPE
   SYNTAX     SEQUENCE OF LpE1StatsEntry
   ACCESS     not-accessible
   STATUS     mandatory
   DESCRIPTION
     "This group contains the common statistical data for a component in 
      a digital hierarchy interface."
::= { lpE1 18 }

lpE1StatsEntry OBJECT-TYPE
   SYNTAX     LpE1StatsEntry
   ACCESS     not-accessible
   STATUS     mandatory
   DESCRIPTION
     "An entry in the lpE1StatsTable."
   INDEX {
      lpIndex,
      lpE1Index }
::= { lpE1StatsTable 1 }

LpE1StatsEntry ::= SEQUENCE {
   lpE1RunningTime
      Counter32,
   lpE1ErrorFreeSec
      Counter32,
   lpE1ErroredSec
      Counter32,
   lpE1SevErroredSec
      Counter32,
   lpE1SevErroredFrmSec
      Counter32,
   lpE1UnavailSec
      Counter32,
   lpE1BpvErrors
      Counter32,
   lpE1CrcErrors
      Counter32,
   lpE1FrmErrors
      Counter32,
   lpE1LosStateChanges
      Counter32,
   lpE1SlipErrors
      Counter32 }

lpE1RunningTime OBJECT-TYPE
   SYNTAX     Counter32 
   ACCESS     read-only
   STATUS     mandatory
   DESCRIPTION
     "The number of seconds since the port component was activated."
::= { lpE1StatsEntry 1 }

lpE1ErrorFreeSec OBJECT-TYPE
   SYNTAX     Counter32 
   ACCESS     read-only
   STATUS     mandatory
   DESCRIPTION
     "The number of seconds that the port has been in an error free state."
::= { lpE1StatsEntry 2 }

lpE1ErroredSec OBJECT-TYPE
   SYNTAX     Counter32 
   ACCESS     read-only
   STATUS     mandatory
   DESCRIPTION
     "An errored second is declared when a second with one or more 
      Code Violation Error events, or one or more Out Of Frame events 
      occurs. A code violation error may be a CRC error or a BPV error. 
      An Out Of Frame event occurs when 2 out of 5 framing bits are in 
      error."
::= { lpE1StatsEntry 3 }

lpE1SevErroredSec OBJECT-TYPE
   SYNTAX     Counter32 
   ACCESS     read-only
   STATUS     mandatory
   DESCRIPTION
     "A severely errored second occurs when a second with 320 or more 
      Code Violation Error events or one or more Out Of Frame events 
      occurs."
::= { lpE1StatsEntry 4 }

lpE1SevErroredFrmSec OBJECT-TYPE
   SYNTAX     Counter32 
   ACCESS     read-only
   STATUS     mandatory
   DESCRIPTION
     "A severely errored framing second occurs when a second with one 
      or more Out Of Frame events occurs."
::= { lpE1StatsEntry 5 }

lpE1UnavailSec OBJECT-TYPE
   SYNTAX     Counter32 
   ACCESS     read-only
   STATUS     mandatory
   DESCRIPTION
     "The total number of seconds that the interface is in an unavailable 
      signal state. An unavailable signal state occurs at the onset of 10 
      consecutive Severely Errored Seconds. The state is cleared at the 
      onset of 10 seconds with no Severely Errored Seconds."
::= { lpE1StatsEntry 6 }

lpE1BpvErrors OBJECT-TYPE
   SYNTAX     Counter32 
   ACCESS     read-only
   STATUS     mandatory
   DESCRIPTION
     "The current count of Bipolar Violations. A bipolar violation is an 
      error in the alternate mark inversion pattern (AMI) on the line."
::= { lpE1StatsEntry 7 }

lpE1CrcErrors OBJECT-TYPE
   SYNTAX     Counter32 
   ACCESS     read-only
   STATUS     mandatory
   DESCRIPTION
     "If the interface is a DS1 line, it is the current count of CRC-6 errors. 
      These will only be counted when the lineType is ESF.
      If the interface is an E1 line, it is the total number of CRC-4 errors. 
      These will only be counted when crc4Mode is on."
::= { lpE1StatsEntry 8 }

lpE1FrmErrors OBJECT-TYPE
   SYNTAX     Counter32 
   ACCESS     read-only
   STATUS     mandatory
   DESCRIPTION
     "The current count of frame errors. A frame error is an error in the 
      framing bits"
::= { lpE1StatsEntry 9 }

lpE1LosStateChanges OBJECT-TYPE
   SYNTAX     Counter32 
   ACCESS     read-only
   STATUS     mandatory
   DESCRIPTION
     "The total number of times that the line lost signal."
::= { lpE1StatsEntry 10 }

lpE1SlipErrors OBJECT-TYPE
   SYNTAX     Counter32 
   ACCESS     read-only
   STATUS     mandatory
   DESCRIPTION
     "The total number of times that the line experienced a controlled 
      frame slip. This attribute is incremented for ports on the voice cards 
      (for example the 1pDS1V and the 1pE1V function processors) only."
::= { lpE1StatsEntry 11 }


-- Channel
-- The Channel component is configured to control a group of 
-- timeslots that form a fractional group on a DS1 or E1 port. 
-- Cell-based cards allow only one channel per port, and this is 
-- automatically provisioned with all available timeslots. Similarly, the 
-- 1pDS3C card type only allows one channel per port, and this is 
-- automatically provisioned with all available timeslots.
-- Warning: On cell-based cards, creation of the AtmCell component 
-- under the Chan and automatic timeslot provisioning is not 
-- guaranteed behavior, since it is possible to add a Chan component 
-- before provisioning the cardType. In general, do not add a Chan 
-- component before provisioning the cardType.

lpE1Chan OBJECT IDENTIFIER ::= { lpE1 2 }



lpE1ChanRowStatusTable OBJECT-TYPE
   SYNTAX     SEQUENCE OF LpE1ChanRowStatusEntry
   ACCESS     not-accessible
   STATUS     mandatory
   DESCRIPTION
     "This entry controls the addition and deletion of 
      lpE1Chan components."
::= { lpE1Chan 1 }

lpE1ChanRowStatusEntry OBJECT-TYPE
   SYNTAX     LpE1ChanRowStatusEntry
   ACCESS     not-accessible
   STATUS     mandatory
   DESCRIPTION
     "A single entry in the table represents a single 
      lpE1Chan component."
   INDEX {
      lpIndex,
      lpE1Index,
      lpE1ChanIndex }
::= { lpE1ChanRowStatusTable 1 }

LpE1ChanRowStatusEntry ::= SEQUENCE {
   lpE1ChanRowStatus
      RowStatus,
   lpE1ChanComponentName
      DisplayString,
   lpE1ChanStorageType
      StorageType,
   lpE1ChanIndex
      Integer32 }

lpE1ChanRowStatus OBJECT-TYPE
   SYNTAX     RowStatus 
   ACCESS     read-write
   STATUS     mandatory
   DESCRIPTION
     "This variable is used as the basis for SNMP naming of
      lpE1Chan components.
      These components can be added and deleted."
::= { lpE1ChanRowStatusEntry 1 }

lpE1ChanComponentName OBJECT-TYPE
   SYNTAX     DisplayString 
   ACCESS     read-only
   STATUS     mandatory
   DESCRIPTION
     "This variable provides the component's string name for
      use with the ASCII Console Interface"
::= { lpE1ChanRowStatusEntry 2 }

lpE1ChanStorageType OBJECT-TYPE
   SYNTAX     StorageType 
   ACCESS     read-only
   STATUS     mandatory
   DESCRIPTION
     "This variable represents the storage type value for the
      lpE1Chan tables."
::= { lpE1ChanRowStatusEntry 4 }

lpE1ChanIndex OBJECT-TYPE
   SYNTAX     Integer32 (0..31)
   ACCESS     not-accessible
   STATUS     mandatory
   DESCRIPTION
     "This variable represents the index for the lpE1Chan tables."
::= { lpE1ChanRowStatusEntry 10 }

lpE1ChanProvTable OBJECT-TYPE
   SYNTAX     SEQUENCE OF LpE1ChanProvEntry
   ACCESS     not-accessible
   STATUS     mandatory
   DESCRIPTION
     "This group contains all of the provisional data for a Channel 
      component."
::= { lpE1Chan 10 }

lpE1ChanProvEntry OBJECT-TYPE
   SYNTAX     LpE1ChanProvEntry
   ACCESS     not-accessible
   STATUS     mandatory
   DESCRIPTION
     "An entry in the lpE1ChanProvTable."
   INDEX {
      lpIndex,
      lpE1Index,
      lpE1ChanIndex }
::= { lpE1ChanProvTable 1 }

LpE1ChanProvEntry ::= SEQUENCE {
   lpE1ChanTimeslots
      OCTET STRING,
   lpE1ChanTimeslotDataRate
      INTEGER,
   lpE1ChanApplicationFramerName
      Link }

lpE1ChanTimeslots OBJECT-TYPE
   SYNTAX     OCTET STRING (SIZE (4))
   ACCESS     read-write
   STATUS     mandatory
   DESCRIPTION
     "This attribute contains the list of timeslots that are used by the 
      Channel component. Valid numbers are 1-24 for a Channel used by 
      a DS1 component, and 1-31 for a Channel used by an E1 
      component.

      Description of bits:
      notused0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { lpE1ChanProvEntry 1 }

lpE1ChanTimeslotDataRate OBJECT-TYPE
   SYNTAX     INTEGER  {
                 n56k(0),
                 doNotOverride(1) }
   ACCESS     read-write
   STATUS     mandatory
   DESCRIPTION
     "This attribute selects the data rate of the timeslots in a channel of a 
      DS1 component. For E1, the data rate of the timeslots will always 
      be 64kbit/s regardless of this attribute.
      When doNotOverride is selected for a channel on a DS1, the data 
      rate of the channel's timeslots are dependent on the zeroCoding 
      selection of the DS1 component. If the zeroCoding is B8ZS (where 
      supported on the FP) or none, the timeslot's data rate will be 
      64kbit/s. If the zeroCoding option is bit7Stuffing, the data rate of a 
      timeslot will be 56kbit/s.
      When 56kbit/s is selected for a channel on a DS1, the least 
      significant bit of each timeslot of this Channel will always be set to 
      1 and not used for data. The data rate for the timeslots of this 
      channel is therefore restricted to 56kbit/s.
      One application of this attribute is to allow a DS1 line to support 
      mixing channels that originate from lines that use different 
      zeroCoding schemes."
   DEFVAL     { doNotOverride }
::= { lpE1ChanProvEntry 2 }

lpE1ChanApplicationFramerName OBJECT-TYPE
   SYNTAX     Link 
   ACCESS     read-write
   STATUS     mandatory
   DESCRIPTION
     "This attribute defines the link to the software stack. It defines which 
      application is running on top of this hardware component."
::= { lpE1ChanProvEntry 3 }

lpE1ChanCidDataTable OBJECT-TYPE
   SYNTAX     SEQUENCE OF LpE1ChanCidDataEntry
   ACCESS     not-accessible
   STATUS     mandatory
   DESCRIPTION
     "This group contains the attribute for a component's Customer 
      Identifier (CID). Refer to the attribute description for a detailed 
      explanation of CIDs."
::= { lpE1Chan 11 }

lpE1ChanCidDataEntry OBJECT-TYPE
   SYNTAX     LpE1ChanCidDataEntry
   ACCESS     not-accessible
   STATUS     mandatory
   DESCRIPTION
     "An entry in the lpE1ChanCidDataTable."
   INDEX {
      lpIndex,
      lpE1Index,
      lpE1ChanIndex }
::= { lpE1ChanCidDataTable 1 }

LpE1ChanCidDataEntry ::= SEQUENCE {
   lpE1ChanCustomerIdentifier
      Unsigned32 }

lpE1ChanCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpE1ChanCidDataEntry 1 }

lpE1ChanIfEntryTable OBJECT-TYPE
   SYNTAX     SEQUENCE OF LpE1ChanIfEntryEntry
   ACCESS     not-accessible
   STATUS     mandatory
   DESCRIPTION
     "This group contains the provisionable attributes for the ifEntry."
::= { lpE1Chan 12 }

lpE1ChanIfEntryEntry OBJECT-TYPE
   SYNTAX     LpE1ChanIfEntryEntry
   ACCESS     not-accessible
   STATUS     mandatory
   DESCRIPTION
     "An entry in the lpE1ChanIfEntryTable."
   INDEX {
      lpIndex,
      lpE1Index,
      lpE1ChanIndex }
::= { lpE1ChanIfEntryTable 1 }

LpE1ChanIfEntryEntry ::= SEQUENCE {
   lpE1ChanIfAdminStatus
      INTEGER,
   lpE1ChanIfIndex
      InterfaceIndex }

lpE1ChanIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpE1ChanIfEntryEntry 1 }

lpE1ChanIfIndex OBJECT-TYPE
   SYNTAX     InterfaceIndex (1..65535)
   ACCESS     read-only
   STATUS     mandatory
   DESCRIPTION
     "This is the index for the IfEntry. Its value is automatically initialized 
      during the provisioning process."
::= { lpE1ChanIfEntryEntry 2 }

lpE1ChanOperStatusTable OBJECT-TYPE
   SYNTAX     SEQUENCE OF LpE1ChanOperStatusEntry
   ACCESS     not-accessible
   STATUS     mandatory
   DESCRIPTION
     "This group includes the Operational Status attribute. This attribute 
      defines the current operational state of this component."
::= { lpE1Chan 13 }

lpE1ChanOperStatusEntry OBJECT-TYPE
   SYNTAX     LpE1ChanOperStatusEntry
   ACCESS     not-accessible
   STATUS     mandatory
   DESCRIPTION
     "An entry in the lpE1ChanOperStatusTable."
   INDEX {
      lpIndex,
      lpE1Index,
      lpE1ChanIndex }
::= { lpE1ChanOperStatusTable 1 }

LpE1ChanOperStatusEntry ::= SEQUENCE {
   lpE1ChanSnmpOperStatus
      INTEGER }

lpE1ChanSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpE1ChanOperStatusEntry 1 }

lpE1ChanStateTable OBJECT-TYPE
   SYNTAX     SEQUENCE OF LpE1ChanStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpE1Chan 14 }

lpE1ChanStateEntry OBJECT-TYPE
   SYNTAX     LpE1ChanStateEntry
   ACCESS     not-accessible
   STATUS     mandatory
   DESCRIPTION
     "An entry in the lpE1ChanStateTable."
   INDEX {
      lpIndex,
      lpE1Index,
      lpE1ChanIndex }
::= { lpE1ChanStateTable 1 }

LpE1ChanStateEntry ::= SEQUENCE {
   lpE1ChanAdminState
      INTEGER,
   lpE1ChanOperationalState
      INTEGER,
   lpE1ChanUsageState
      INTEGER,
   lpE1ChanAvailabilityStatus
      OCTET STRING,
   lpE1ChanProceduralStatus
      OCTET STRING,
   lpE1ChanControlStatus
      OCTET STRING,
   lpE1ChanAlarmStatus
      OCTET STRING,
   lpE1ChanStandbyStatus
      INTEGER,
   lpE1ChanUnknownStatus
      INTEGER }

lpE1ChanAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpE1ChanStateEntry 1 }

lpE1ChanOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpE1ChanStateEntry 2 }

lpE1ChanUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpE1ChanStateEntry 3 }

lpE1ChanAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpE1ChanStateEntry 4 }

lpE1ChanProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpE1ChanStateEntry 5 }

lpE1ChanControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpE1ChanStateEntry 6 }

lpE1ChanAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpE1ChanStateEntry 7 }

lpE1ChanStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpE1ChanStateEntry 8 }

lpE1ChanUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpE1ChanStateEntry 9 }

lpE1ChanOperTable OBJECT-TYPE
   SYNTAX     SEQUENCE OF LpE1ChanOperEntry
   ACCESS     not-accessible
   STATUS     mandatory
   DESCRIPTION
     "This group contains all of the operational data for a Channel 
      component."
::= { lpE1Chan 15 }

lpE1ChanOperEntry OBJECT-TYPE
   SYNTAX     LpE1ChanOperEntry
   ACCESS     not-accessible
   STATUS     mandatory
   DESCRIPTION
     "An entry in the lpE1ChanOperTable."
   INDEX {
      lpIndex,
      lpE1Index,
      lpE1ChanIndex }
::= { lpE1ChanOperTable 1 }

LpE1ChanOperEntry ::= SEQUENCE {
   lpE1ChanActualChannelSpeed
      Gauge32 }

lpE1ChanActualChannelSpeed OBJECT-TYPE
   SYNTAX     Gauge32 (0..4294967295)
   ACCESS     read-only
   STATUS     mandatory
   DESCRIPTION
     "This attribute displays the measured link speed of the Channel 
      component."
   DEFVAL     { 0 }
::= { lpE1ChanOperEntry 1 }

lpE1ChanAdminInfoTable OBJECT-TYPE
   SYNTAX     SEQUENCE OF LpE1ChanAdminInfoEntry
   ACCESS     not-accessible
   STATUS     mandatory
   DESCRIPTION
     "This group contains the attributes pertaining to the vendor of the 
      equipment."
::= { lpE1Chan 16 }

lpE1ChanAdminInfoEntry OBJECT-TYPE
   SYNTAX     LpE1ChanAdminInfoEntry
   ACCESS     not-accessible
   STATUS     mandatory
   DESCRIPTION
     "An entry in the lpE1ChanAdminInfoTable."
   INDEX {
      lpIndex,
      lpE1Index,
      lpE1ChanIndex }
::= { lpE1ChanAdminInfoTable 1 }

LpE1ChanAdminInfoEntry ::= SEQUENCE {
   lpE1ChanVendor
      AsciiString,
   lpE1ChanCommentText
      AsciiString }

lpE1ChanVendor OBJECT-TYPE
   SYNTAX     AsciiString (SIZE (0..20))
   ACCESS     read-write
   STATUS     mandatory
   DESCRIPTION
     "This is the name of the vendor supplying the facility."
::= { lpE1ChanAdminInfoEntry 1 }

lpE1ChanCommentText OBJECT-TYPE
   SYNTAX     AsciiString (SIZE (0..60))
   ACCESS     read-write
   STATUS     mandatory
   DESCRIPTION
     "Any miscellaneous text about the facility."
::= { lpE1ChanAdminInfoEntry 2 }


-- 
-- The Test component is configured to control a hardware facility test 
-- on a physical (V35, X21, DS1, E1, DS3, E3 etc.) or a logical port.

lpE1ChanTest OBJECT IDENTIFIER ::= { lpE1Chan 2 }



lpE1ChanTestRowStatusTable OBJECT-TYPE
   SYNTAX     SEQUENCE OF LpE1ChanTestRowStatusEntry
   ACCESS     not-accessible
   STATUS     mandatory
   DESCRIPTION
     "This entry controls the addition and deletion of 
      lpE1ChanTest components."
::= { lpE1ChanTest 1 }

lpE1ChanTestRowStatusEntry OBJECT-TYPE
   SYNTAX     LpE1ChanTestRowStatusEntry
   ACCESS     not-accessible
   STATUS     mandatory
   DESCRIPTION
     "A single entry in the table represents a single 
      lpE1ChanTest component."
   INDEX {
      lpIndex,
      lpE1Index,
      lpE1ChanIndex,
      lpE1ChanTestIndex }
::= { lpE1ChanTestRowStatusTable 1 }

LpE1ChanTestRowStatusEntry ::= SEQUENCE {
   lpE1ChanTestRowStatus
      RowStatus,
   lpE1ChanTestComponentName
      DisplayString,
   lpE1ChanTestStorageType
      StorageType,
   lpE1ChanTestIndex
      NonReplicated }

lpE1ChanTestRowStatus OBJECT-TYPE
   SYNTAX     RowStatus 
   ACCESS     read-only
   STATUS     mandatory
   DESCRIPTION
     "This variable is used as the basis for SNMP naming of
      lpE1ChanTest components.
      These components cannot be added nor deleted."
::= { lpE1ChanTestRowStatusEntry 1 }

lpE1ChanTestComponentName OBJECT-TYPE
   SYNTAX     DisplayString 
   ACCESS     read-only
   STATUS     mandatory
   DESCRIPTION
     "This variable provides the component's string name for
      use with the ASCII Console Interface"
::= { lpE1ChanTestRowStatusEntry 2 }

lpE1ChanTestStorageType OBJECT-TYPE
   SYNTAX     StorageType 
   ACCESS     read-only
   STATUS     mandatory
   DESCRIPTION
     "This variable represents the storage type value for the
      lpE1ChanTest tables."
::= { lpE1ChanTestRowStatusEntry 4 }

lpE1ChanTestIndex OBJECT-TYPE
   SYNTAX     NonReplicated 
   ACCESS     not-accessible
   STATUS     mandatory
   DESCRIPTION
     "This variable represents the index for the lpE1ChanTest tables."
::= { lpE1ChanTestRowStatusEntry 10 }

lpE1ChanTestStateTable OBJECT-TYPE
   SYNTAX     SEQUENCE OF LpE1ChanTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpE1ChanTest 10 }

lpE1ChanTestStateEntry OBJECT-TYPE
   SYNTAX     LpE1ChanTestStateEntry
   ACCESS     not-accessible
   STATUS     mandatory
   DESCRIPTION
     "An entry in the lpE1ChanTestStateTable."
   INDEX {
      lpIndex,
      lpE1Index,
      lpE1ChanIndex,
      lpE1ChanTestIndex }
::= { lpE1ChanTestStateTable 1 }

LpE1ChanTestStateEntry ::= SEQUENCE {
   lpE1ChanTestAdminState
      INTEGER,
   lpE1ChanTestOperationalState
      INTEGER,
   lpE1ChanTestUsageState
      INTEGER }

lpE1ChanTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpE1ChanTestStateEntry 1 }

lpE1ChanTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpE1ChanTestStateEntry 2 }

lpE1ChanTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpE1ChanTestStateEntry 3 }

lpE1ChanTestSetupTable OBJECT-TYPE
   SYNTAX     SEQUENCE OF LpE1ChanTestSetupEntry
   ACCESS     not-accessible
   STATUS     mandatory
   DESCRIPTION
     "This group contains all of the operational data for a Test 
      component."
::= { lpE1ChanTest 11 }

lpE1ChanTestSetupEntry OBJECT-TYPE
   SYNTAX     LpE1ChanTestSetupEntry
   ACCESS     not-accessible
   STATUS     mandatory
   DESCRIPTION
     "An entry in the lpE1ChanTestSetupTable."
   INDEX {
      lpIndex,
      lpE1Index,
      lpE1ChanIndex,
      lpE1ChanTestIndex }
::= { lpE1ChanTestSetupTable 1 }

LpE1ChanTestSetupEntry ::= SEQUENCE {
   lpE1ChanTestPurpose
      AsciiString,
   lpE1ChanTestType
      INTEGER,
   lpE1ChanTestFrmSize
      Unsigned32,
   lpE1ChanTestFrmPatternType
      INTEGER,
   lpE1ChanTestCustomizedPattern
      Hex,
   lpE1ChanTestDataStartDelay
      Unsigned32,
   lpE1ChanTestDisplayInterval
      Unsigned32,
   lpE1ChanTestDuration
      Unsigned32 }

lpE1ChanTestPurpose OBJECT-TYPE
   SYNTAX     AsciiString (SIZE (0..40))
   ACCESS     read-write
   STATUS     mandatory
   DESCRIPTION
     "This attribute records the purpose of the test so that the test results 
      can be associated and properly analyzed."
::= { lpE1ChanTestSetupEntry 1 }

lpE1ChanTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpE1ChanTestSetupEntry 2 }

lpE1ChanTestFrmSize OBJECT-TYPE
   SYNTAX     Unsigned32 (4..4096)
   ACCESS     read-write
   STATUS     mandatory
   DESCRIPTION
     "This attribute defines the size of the test data frames in number of 
      bytes."
   DEFVAL     { 1024 }
::= { lpE1ChanTestSetupEntry 3 }

lpE1ChanTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpE1ChanTestSetupEntry 4 }

lpE1ChanTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpE1ChanTestSetupEntry 5 }

lpE1ChanTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpE1ChanTestSetupEntry 6 }

lpE1ChanTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpE1ChanTestSetupEntry 7 }

lpE1ChanTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpE1ChanTestSetupEntry 8 }

lpE1ChanTestResultsTable OBJECT-TYPE
   SYNTAX     SEQUENCE OF LpE1ChanTestResultsEntry
   ACCESS     not-accessible
   STATUS     mandatory
   DESCRIPTION
     "This group contains all the statistics related attributes of the Test 
      component."
::= { lpE1ChanTest 12 }

lpE1ChanTestResultsEntry OBJECT-TYPE
   SYNTAX     LpE1ChanTestResultsEntry
   ACCESS     not-accessible
   STATUS     mandatory
   DESCRIPTION
     "An entry in the lpE1ChanTestResultsTable."
   INDEX {
      lpIndex,
      lpE1Index,
      lpE1ChanIndex,
      lpE1ChanTestIndex }
::= { lpE1ChanTestResultsTable 1 }

LpE1ChanTestResultsEntry ::= SEQUENCE {
   lpE1ChanTestElapsedTime
      Counter32,
   lpE1ChanTestTimeRemaining
      Unsigned32,
   lpE1ChanTestCauseOfTermination
      INTEGER,
   lpE1ChanTestBitsTx
      PassportCounter64,
   lpE1ChanTestBytesTx
      PassportCounter64,
   lpE1ChanTestFrmTx
      PassportCounter64,
   lpE1ChanTestBitsRx
      PassportCounter64,
   lpE1ChanTestBytesRx
      PassportCounter64,
   lpE1ChanTestFrmRx
      PassportCounter64,
   lpE1ChanTestErroredFrmRx
      PassportCounter64,
   lpE1ChanTestBitErrorRate
      AsciiString }

lpE1ChanTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpE1ChanTestResultsEntry 1 }

lpE1ChanTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpE1ChanTestResultsEntry 2 }

lpE1ChanTestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpE1ChanTestResultsEntry 3 }

lpE1ChanTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpE1ChanTestResultsEntry 4 }

lpE1ChanTestBytesTx OBJECT-TYPE
   SYNTAX     PassportCounter64 
   ACCESS     read-only
   STATUS     mandatory
   DESCRIPTION
     "This attribute is the total number of bytes sent during the test 
      period. This counter is not expected to reach its maximum value."
::= { lpE1ChanTestResultsEntry 5 }

lpE1ChanTestFrmTx OBJECT-TYPE
   SYNTAX     PassportCounter64 
   ACCESS     read-only
   STATUS     mandatory
   DESCRIPTION
     "This attribute is the total number of frames sent during the test 
      period. This counter is not expected to reach its maximum value."
::= { lpE1ChanTestResultsEntry 6 }

lpE1ChanTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpE1ChanTestResultsEntry 7 }

lpE1ChanTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpE1ChanTestResultsEntry 8 }

lpE1ChanTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpE1ChanTestResultsEntry 9 }

lpE1ChanTestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpE1ChanTestResultsEntry 10 }

lpE1ChanTestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpE1ChanTestResultsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

lpE1ChanCell OBJECT IDENTIFIER ::= { lpE1Chan 3 }



lpE1ChanCellRowStatusTable OBJECT-TYPE
   SYNTAX     SEQUENCE OF LpE1ChanCellRowStatusEntry
   ACCESS     not-accessible
   STATUS     mandatory
   DESCRIPTION
     "This entry controls the addition and deletion of 
      lpE1ChanCell components."
::= { lpE1ChanCell 1 }

lpE1ChanCellRowStatusEntry OBJECT-TYPE
   SYNTAX     LpE1ChanCellRowStatusEntry
   ACCESS     not-accessible
   STATUS     mandatory
   DESCRIPTION
     "A single entry in the table represents a single 
      lpE1ChanCell component."
   INDEX {
      lpIndex,
      lpE1Index,
      lpE1ChanIndex,
      lpE1ChanCellIndex }
::= { lpE1ChanCellRowStatusTable 1 }

LpE1ChanCellRowStatusEntry ::= SEQUENCE {
   lpE1ChanCellRowStatus
      RowStatus,
   lpE1ChanCellComponentName
      DisplayString,
   lpE1ChanCellStorageType
      StorageType,
   lpE1ChanCellIndex
      NonReplicated }

lpE1ChanCellRowStatus OBJECT-TYPE
   SYNTAX     RowStatus 
   ACCESS     read-write
   STATUS     mandatory
   DESCRIPTION
     "This variable is used as the basis for SNMP naming of
      lpE1ChanCell components.
      These components can be added and deleted."
::= { lpE1ChanCellRowStatusEntry 1 }

lpE1ChanCellComponentName OBJECT-TYPE
   SYNTAX     DisplayString 
   ACCESS     read-only
   STATUS     mandatory
   DESCRIPTION
     "This variable provides the component's string name for
      use with the ASCII Console Interface"
::= { lpE1ChanCellRowStatusEntry 2 }

lpE1ChanCellStorageType OBJECT-TYPE
   SYNTAX     StorageType 
   ACCESS     read-only
   STATUS     mandatory
   DESCRIPTION
     "This variable represents the storage type value for the
      lpE1ChanCell tables."
::= { lpE1ChanCellRowStatusEntry 4 }

lpE1ChanCellIndex OBJECT-TYPE
   SYNTAX     NonReplicated 
   ACCESS     not-accessible
   STATUS     mandatory
   DESCRIPTION
     "This variable represents the index for the lpE1ChanCell tables."
::= { lpE1ChanCellRowStatusEntry 10 }

lpE1ChanCellProvTable OBJECT-TYPE
   SYNTAX     SEQUENCE OF LpE1ChanCellProvEntry
   ACCESS     not-accessible
   STATUS     mandatory
   DESCRIPTION
     "This group contains the provisioning attributes for the AtmCell 
      component."
::= { lpE1ChanCell 10 }

lpE1ChanCellProvEntry OBJECT-TYPE
   SYNTAX     LpE1ChanCellProvEntry
   ACCESS     not-accessible
   STATUS     mandatory
   DESCRIPTION
     "An entry in the lpE1ChanCellProvTable."
   INDEX {
      lpIndex,
      lpE1Index,
      lpE1ChanIndex,
      lpE1ChanCellIndex }
::= { lpE1ChanCellProvTable 1 }

LpE1ChanCellProvEntry ::= SEQUENCE {
   lpE1ChanCellAlarmActDelay
      Unsigned32,
   lpE1ChanCellScrambleCellPayload
      INTEGER,
   lpE1ChanCellCorrectSingleBitHeaderErrors
      INTEGER }

lpE1ChanCellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { lpE1ChanCellProvEntry 1 }

lpE1ChanCellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { lpE1ChanCellProvEntry 2 }

lpE1ChanCellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { lpE1ChanCellProvEntry 3 }

lpE1ChanCellOperTable OBJECT-TYPE
   SYNTAX     SEQUENCE OF LpE1ChanCellOperEntry
   ACCESS     not-accessible
   STATUS     mandatory
   DESCRIPTION
     "This group contains the common operational attributes for the 
      AtmCell component."
::= { lpE1ChanCell 11 }

lpE1ChanCellOperEntry OBJECT-TYPE
   SYNTAX     LpE1ChanCellOperEntry
   ACCESS     not-accessible
   STATUS     mandatory
   DESCRIPTION
     "An entry in the lpE1ChanCellOperTable."
   INDEX {
      lpIndex,
      lpE1Index,
      lpE1ChanIndex,
      lpE1ChanCellIndex }
::= { lpE1ChanCellOperTable 1 }

LpE1ChanCellOperEntry ::= SEQUENCE {
   lpE1ChanCellLcdAlarm
      INTEGER }

lpE1ChanCellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { lpE1ChanCellOperEntry 1 }

lpE1ChanCellStatsTable OBJECT-TYPE
   SYNTAX     SEQUENCE OF LpE1ChanCellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { lpE1ChanCell 12 }

lpE1ChanCellStatsEntry OBJECT-TYPE
   SYNTAX     LpE1ChanCellStatsEntry
   ACCESS     not-accessible
   STATUS     mandatory
   DESCRIPTION
     "An entry in the lpE1ChanCellStatsTable."
   INDEX {
      lpIndex,
      lpE1Index,
      lpE1ChanIndex,
      lpE1ChanCellIndex }
::= { lpE1ChanCellStatsTable 1 }

LpE1ChanCellStatsEntry ::= SEQUENCE {
   lpE1ChanCellUncorrectableHecErrors
      Counter32,
   lpE1ChanCellSevErroredSec
      Counter32,
   lpE1ChanCellReceiveCellUtilization
      Gauge32,
   lpE1ChanCellTransmitCellUtilization
      Gauge32,
   lpE1ChanCellCorrectableHeaderErrors
      Counter32 }

lpE1ChanCellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { lpE1ChanCellStatsEntry 1 }

lpE1ChanCellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { lpE1ChanCellStatsEntry 2 }

lpE1ChanCellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { lpE1ChanCellStatsEntry 3 }

lpE1ChanCellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { lpE1ChanCellStatsEntry 4 }

lpE1ChanCellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { lpE1ChanCellStatsEntry 5 }


-- Lp/x Ds1/y Chan/z Tc
-- Lp/x E1/y Chan/z Tc
-- 
-- The Tc component is used to provision and monitor trunk 
-- conditioning options. A separate instance of this component is 
-- required for each Chan on a Port which is offering a structured 
-- constant bit rate service.
-- 
-- Under certain failure alarm conditions, trunk conditioning 
-- replacementData is substituted into the timeslots as defined by the 
-- Chan component. Trunk conditioning signaling is also substituted 
-- into the appropriate Channel Associated Signaling (CAS) bits when 
-- a lineType that uses CAS has been defined.
-- 
-- When used with AAL1 Circuit Emulation Service, trunk 
-- conditioning is transmitted towards the ATM network under the 
-- following conditions:
-- lossOfSignal (LOS)
-- lossOfFrame (LOF)
-- remoteAlarmIndication (RAI)
-- alarmIndicationSignal (AIS)
-- bufferUnderflow (BU)
-- and in addition for E1:
-- lossOfMultiframe (LOMF)
-- receiveMultiframeRemoteAlarmIndication (RMRAI)
-- 
-- When used with AAL1 Circuit Emulation Service, trunk 
-- conditioning is transmitted towards the PDH network under the 
-- following conditions:
-- bufferUnderflow (BU)
-- AAL1 protocol errors.
-- 

lpE1ChanTc OBJECT IDENTIFIER ::= { lpE1Chan 4 }



lpE1ChanTcRowStatusTable OBJECT-TYPE
   SYNTAX     SEQUENCE OF LpE1ChanTcRowStatusEntry
   ACCESS     not-accessible
   STATUS     mandatory
   DESCRIPTION
     "This entry controls the addition and deletion of 
      lpE1ChanTc components."
::= { lpE1ChanTc 1 }

lpE1ChanTcRowStatusEntry OBJECT-TYPE
   SYNTAX     LpE1ChanTcRowStatusEntry
   ACCESS     not-accessible
   STATUS     mandatory
   DESCRIPTION
     "A single entry in the table represents a single 
      lpE1ChanTc component."
   INDEX {
      lpIndex,
      lpE1Index,
      lpE1ChanIndex,
      lpE1ChanTcIndex }
::= { lpE1ChanTcRowStatusTable 1 }

LpE1ChanTcRowStatusEntry ::= SEQUENCE {
   lpE1ChanTcRowStatus
      RowStatus,
   lpE1ChanTcComponentName
      DisplayString,
   lpE1ChanTcStorageType
      StorageType,
   lpE1ChanTcIndex
      NonReplicated }

lpE1ChanTcRowStatus OBJECT-TYPE
   SYNTAX     RowStatus 
   ACCESS     read-write
   STATUS     mandatory
   DESCRIPTION
     "This variable is used as the basis for SNMP naming of
      lpE1ChanTc components.
      These components can be added and deleted."
::= { lpE1ChanTcRowStatusEntry 1 }

lpE1ChanTcComponentName OBJECT-TYPE
   SYNTAX     DisplayString 
   ACCESS     read-only
   STATUS     mandatory
   DESCRIPTION
     "This variable provides the component's string name for
      use with the ASCII Console Interface"
::= { lpE1ChanTcRowStatusEntry 2 }

lpE1ChanTcStorageType OBJECT-TYPE
   SYNTAX     StorageType 
   ACCESS     read-only
   STATUS     mandatory
   DESCRIPTION
     "This variable represents the storage type value for the
      lpE1ChanTc tables."
::= { lpE1ChanTcRowStatusEntry 4 }

lpE1ChanTcIndex OBJECT-TYPE
   SYNTAX     NonReplicated 
   ACCESS     not-accessible
   STATUS     mandatory
   DESCRIPTION
     "This variable represents the index for the lpE1ChanTc tables."
::= { lpE1ChanTcRowStatusEntry 10 }

lpE1ChanTcProvTable OBJECT-TYPE
   SYNTAX     SEQUENCE OF LpE1ChanTcProvEntry
   ACCESS     not-accessible
   STATUS     mandatory
   DESCRIPTION
     "This group contains all specific provisioning data for a Tc 
      component."
::= { lpE1ChanTc 10 }

lpE1ChanTcProvEntry OBJECT-TYPE
   SYNTAX     LpE1ChanTcProvEntry
   ACCESS     not-accessible
   STATUS     mandatory
   DESCRIPTION
     "An entry in the lpE1ChanTcProvTable."
   INDEX {
      lpIndex,
      lpE1Index,
      lpE1ChanIndex,
      lpE1ChanTcIndex }
::= { lpE1ChanTcProvTable 1 }

LpE1ChanTcProvEntry ::= SEQUENCE {
   lpE1ChanTcReplacementData
      Hex,
   lpE1ChanTcSignalOneDuration
      Unsigned32 }

lpE1ChanTcReplacementData OBJECT-TYPE
   SYNTAX     Hex (0..255)
   ACCESS     read-write
   STATUS     mandatory
   DESCRIPTION
     "This attribute specifies the trunk conditioning data byte to be 
      substituted into the timeslots defined by the Chan component under 
      fault conditions. 
      
      replacementData can be set to any two digit hexadecimal number. 
      The following are recommended values:
      DS1 MUX Out Of Service Code = 0x1A
      E1 MUX Out Of Service Code = 0xFF"
   DEFVAL     { 255 }
::= { lpE1ChanTcProvEntry 1 }

lpE1ChanTcSignalOneDuration OBJECT-TYPE
   SYNTAX     Unsigned32 (0..60)
   ACCESS     read-write
   STATUS     mandatory
   DESCRIPTION
     "This attribute specifies the time duration in seconds for which 
      signalOne is substituted into the appropriate signaling bits, when a 
      lineType that uses CAS has been defined. When signalOneDuration 
      has expired signalTwo is substituted into the appropriate signaling 
      bits.
      
      If signalOneDuration is set to zero then only signalTwo is 
      substituted into the appropriate signaling bits during error 
      conditions.
      
      signalOneDuration can be set to any integer value from 0 to 60 
      seconds."
   DEFVAL     { 0 }
::= { lpE1ChanTcProvEntry 2 }

lpE1ChanTcOpTable OBJECT-TYPE
   SYNTAX     SEQUENCE OF LpE1ChanTcOpEntry
   ACCESS     not-accessible
   STATUS     mandatory
   DESCRIPTION
     "This group contains all specific operational data for a Tc 
      component."
::= { lpE1ChanTc 11 }

lpE1ChanTcOpEntry OBJECT-TYPE
   SYNTAX     LpE1ChanTcOpEntry
   ACCESS     not-accessible
   STATUS     mandatory
   DESCRIPTION
     "An entry in the lpE1ChanTcOpTable."
   INDEX {
      lpIndex,
      lpE1Index,
      lpE1ChanIndex,
      lpE1ChanTcIndex }
::= { lpE1ChanTcOpTable 1 }

LpE1ChanTcOpEntry ::= SEQUENCE {
   lpE1ChanTcIngressConditioning
      INTEGER,
   lpE1ChanTcEgressConditioning
      INTEGER }

lpE1ChanTcIngressConditioning OBJECT-TYPE
   SYNTAX     INTEGER  {
                 off(0),
                 on(1) }
   ACCESS     read-only
   STATUS     mandatory
   DESCRIPTION
     "This attribute indicates the status of locally generated trunk 
      conditioning towards the ATM network.
      
      When trunk conditioning is being locally generated towards the 
      ATM network, ingressConditioning is set to on.
      
      When trunk conditioning is not being locally generated towards the 
      ATM network, ingressConditioning is set to off.
      
      Trunk conditioning is transmitted towards the ATM network under 
      the following conditions:
      lossOfSignal (LOS)
      lossOfFrame (LOF)
      remoteAlarmIndication (RAI)
      alarmIndicationSignal (AIS)
      bufferUnderflow (BU)
      and in addition for E1:
      lossOfMultiframe (LOMF)
      receiveMultiframeRemoteAlarmIndication (RMRAI)"
   DEFVAL     { off }
::= { lpE1ChanTcOpEntry 1 }

lpE1ChanTcEgressConditioning OBJECT-TYPE
   SYNTAX     INTEGER  {
                 off(0),
                 on(1) }
   ACCESS     read-only
   STATUS     mandatory
   DESCRIPTION
     "This attribute indicates the status of locally generated trunk 
      conditioning towards the PDH line.
      
      When trunk conditioning is being locally generated towards the 
      PDH line, egressConditioning is set to on.
      
      When trunk conditioning is not being locally generated towards the 
      PDH line, egressConditioning is set to off.
      
      Trunk conditioning is transmitted towards the PDH line under the 
      following conditions:
      bufferUnderflow (BU)
      AAL1 protocol errors."
   DEFVAL     { off }
::= { lpE1ChanTcOpEntry 2 }

lpE1ChanTcSigOneTable OBJECT-TYPE
   SYNTAX     SEQUENCE OF LpE1ChanTcSigOneEntry
   ACCESS     not-accessible
   STATUS     mandatory
   DESCRIPTION
     "This attribute specifies the value to be substituted into the ABCD 
      signaling bits for the timeslots defined by the Chan component 
      under fault conditions. The value will be substituted for the duration 
      provisioned in signalOneDuration when a lineType that uses CAS 
      has been defined. 
      
      For a lineType of d4Cas (Super Frame), signaling bits C and D are 
      required to equal bits A and B respectively."
::= { lpE1ChanTc 398 }

lpE1ChanTcSigOneEntry OBJECT-TYPE
   SYNTAX     LpE1ChanTcSigOneEntry
   ACCESS     not-accessible
   STATUS     mandatory
   DESCRIPTION
     "An entry in the lpE1ChanTcSigOneTable."
   INDEX {
      lpIndex,
      lpE1Index,
      lpE1ChanIndex,
      lpE1ChanTcIndex,
      lpE1ChanTcSigOneIndex }
::= { lpE1ChanTcSigOneTable 1 }

LpE1ChanTcSigOneEntry ::= SEQUENCE {
   lpE1ChanTcSigOneIndex
      INTEGER,
   lpE1ChanTcSigOneValue
      Unsigned32 }

lpE1ChanTcSigOneIndex OBJECT-TYPE
   SYNTAX     INTEGER  {
                 d(0),
                 c(1),
                 b(2),
                 a(3) }
   ACCESS     not-accessible
   STATUS     mandatory
   DESCRIPTION
     "This variable represents the lpE1ChanTcSigOneTable
      specific index for the lpE1ChanTcSigOneTable."
::= { lpE1ChanTcSigOneEntry 1 }

lpE1ChanTcSigOneValue OBJECT-TYPE
   SYNTAX     Unsigned32 (0..1)
   ACCESS     read-write
   STATUS     mandatory
   DESCRIPTION
     "This variable represents an individual value for the
      lpE1ChanTcSigOneTable."
::= { lpE1ChanTcSigOneEntry 2 }

lpE1ChanTcSigTwoTable OBJECT-TYPE
   SYNTAX     SEQUENCE OF LpE1ChanTcSigTwoEntry
   ACCESS     not-accessible
   STATUS     mandatory
   DESCRIPTION
     "This attribute specifies the value to be substituted into the ABCD 
      signaling bits for the timeslots defined by the Chan component 
      under fault conditions. The value will be substituted after the 
      duration provisioned in signalOneDuration has expired and when a 
      lineType that uses CAS has been defined. 
      
      For a lineType of d4Cas (Super Frame), signaling bits C and D are 
      required to equal bits A and B respectively."
::= { lpE1ChanTc 399 }

lpE1ChanTcSigTwoEntry OBJECT-TYPE
   SYNTAX     LpE1ChanTcSigTwoEntry
   ACCESS     not-accessible
   STATUS     mandatory
   DESCRIPTION
     "An entry in the lpE1ChanTcSigTwoTable."
   INDEX {
      lpIndex,
      lpE1Index,
      lpE1ChanIndex,
      lpE1ChanTcIndex,
      lpE1ChanTcSigTwoIndex }
::= { lpE1ChanTcSigTwoTable 1 }

LpE1ChanTcSigTwoEntry ::= SEQUENCE {
   lpE1ChanTcSigTwoIndex
      INTEGER,
   lpE1ChanTcSigTwoValue
      Unsigned32 }

lpE1ChanTcSigTwoIndex OBJECT-TYPE
   SYNTAX     INTEGER  {
                 d(0),
                 c(1),
                 b(2),
                 a(3) }
   ACCESS     not-accessible
   STATUS     mandatory
   DESCRIPTION
     "This variable represents the lpE1ChanTcSigTwoTable
      specific index for the lpE1ChanTcSigTwoTable."
::= { lpE1ChanTcSigTwoEntry 1 }

lpE1ChanTcSigTwoValue OBJECT-TYPE
   SYNTAX     Unsigned32 (0..1)
   ACCESS     read-write
   STATUS     mandatory
   DESCRIPTION
     "This variable represents an individual value for the
      lpE1ChanTcSigTwoTable."
::= { lpE1ChanTcSigTwoEntry 2 }


-- 
-- The Test component is configured to control a hardware facility test 
-- on a physical (V35, X21, DS1, E1, DS3, E3 etc.) or a logical port.

lpE1Test OBJECT IDENTIFIER ::= { lpE1 3 }



lpE1TestRowStatusTable OBJECT-TYPE
   SYNTAX     SEQUENCE OF LpE1TestRowStatusEntry
   ACCESS     not-accessible
   STATUS     mandatory
   DESCRIPTION
     "This entry controls the addition and deletion of 
      lpE1Test components."
::= { lpE1Test 1 }

lpE1TestRowStatusEntry OBJECT-TYPE
   SYNTAX     LpE1TestRowStatusEntry
   ACCESS     not-accessible
   STATUS     mandatory
   DESCRIPTION
     "A single entry in the table represents a single 
      lpE1Test component."
   INDEX {
      lpIndex,
      lpE1Index,
      lpE1TestIndex }
::= { lpE1TestRowStatusTable 1 }

LpE1TestRowStatusEntry ::= SEQUENCE {
   lpE1TestRowStatus
      RowStatus,
   lpE1TestComponentName
      DisplayString,
   lpE1TestStorageType
      StorageType,
   lpE1TestIndex
      NonReplicated }

lpE1TestRowStatus OBJECT-TYPE
   SYNTAX     RowStatus 
   ACCESS     read-only
   STATUS     mandatory
   DESCRIPTION
     "This variable is used as the basis for SNMP naming of
      lpE1Test components.
      These components cannot be added nor deleted."
::= { lpE1TestRowStatusEntry 1 }

lpE1TestComponentName OBJECT-TYPE
   SYNTAX     DisplayString 
   ACCESS     read-only
   STATUS     mandatory
   DESCRIPTION
     "This variable provides the component's string name for
      use with the ASCII Console Interface"
::= { lpE1TestRowStatusEntry 2 }

lpE1TestStorageType OBJECT-TYPE
   SYNTAX     StorageType 
   ACCESS     read-only
   STATUS     mandatory
   DESCRIPTION
     "This variable represents the storage type value for the
      lpE1Test tables."
::= { lpE1TestRowStatusEntry 4 }

lpE1TestIndex OBJECT-TYPE
   SYNTAX     NonReplicated 
   ACCESS     not-accessible
   STATUS     mandatory
   DESCRIPTION
     "This variable represents the index for the lpE1Test tables."
::= { lpE1TestRowStatusEntry 10 }

lpE1TestStateTable OBJECT-TYPE
   SYNTAX     SEQUENCE OF LpE1TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpE1Test 10 }

lpE1TestStateEntry OBJECT-TYPE
   SYNTAX     LpE1TestStateEntry
   ACCESS     not-accessible
   STATUS     mandatory
   DESCRIPTION
     "An entry in the lpE1TestStateTable."
   INDEX {
      lpIndex,
      lpE1Index,
      lpE1TestIndex }
::= { lpE1TestStateTable 1 }

LpE1TestStateEntry ::= SEQUENCE {
   lpE1TestAdminState
      INTEGER,
   lpE1TestOperationalState
      INTEGER,
   lpE1TestUsageState
      INTEGER }

lpE1TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpE1TestStateEntry 1 }

lpE1TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpE1TestStateEntry 2 }

lpE1TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpE1TestStateEntry 3 }

lpE1TestSetupTable OBJECT-TYPE
   SYNTAX     SEQUENCE OF LpE1TestSetupEntry
   ACCESS     not-accessible
   STATUS     mandatory
   DESCRIPTION
     "This group contains all of the operational data for a Test 
      component."
::= { lpE1Test 11 }

lpE1TestSetupEntry OBJECT-TYPE
   SYNTAX     LpE1TestSetupEntry
   ACCESS     not-accessible
   STATUS     mandatory
   DESCRIPTION
     "An entry in the lpE1TestSetupTable."
   INDEX {
      lpIndex,
      lpE1Index,
      lpE1TestIndex }
::= { lpE1TestSetupTable 1 }

LpE1TestSetupEntry ::= SEQUENCE {
   lpE1TestPurpose
      AsciiString,
   lpE1TestType
      INTEGER,
   lpE1TestFrmSize
      Unsigned32,
   lpE1TestFrmPatternType
      INTEGER,
   lpE1TestCustomizedPattern
      Hex,
   lpE1TestDataStartDelay
      Unsigned32,
   lpE1TestDisplayInterval
      Unsigned32,
   lpE1TestDuration
      Unsigned32 }

lpE1TestPurpose OBJECT-TYPE
   SYNTAX     AsciiString (SIZE (0..40))
   ACCESS     read-write
   STATUS     mandatory
   DESCRIPTION
     "This attribute records the purpose of the test so that the test results 
      can be associated and properly analyzed."
::= { lpE1TestSetupEntry 1 }

lpE1TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpE1TestSetupEntry 2 }

lpE1TestFrmSize OBJECT-TYPE
   SYNTAX     Unsigned32 (4..4096)
   ACCESS     read-write
   STATUS     mandatory
   DESCRIPTION
     "This attribute defines the size of the test data frames in number of 
      bytes."
   DEFVAL     { 1024 }
::= { lpE1TestSetupEntry 3 }

lpE1TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpE1TestSetupEntry 4 }

lpE1TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpE1TestSetupEntry 5 }

lpE1TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpE1TestSetupEntry 6 }

lpE1TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpE1TestSetupEntry 7 }

lpE1TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpE1TestSetupEntry 8 }

lpE1TestResultsTable OBJECT-TYPE
   SYNTAX     SEQUENCE OF LpE1TestResultsEntry
   ACCESS     not-accessible
   STATUS     mandatory
   DESCRIPTION
     "This group contains all the statistics related attributes of the Test 
      component."
::= { lpE1Test 12 }

lpE1TestResultsEntry OBJECT-TYPE
   SYNTAX     LpE1TestResultsEntry
   ACCESS     not-accessible
   STATUS     mandatory
   DESCRIPTION
     "An entry in the lpE1TestResultsTable."
   INDEX {
      lpIndex,
      lpE1Index,
      lpE1TestIndex }
::= { lpE1TestResultsTable 1 }

LpE1TestResultsEntry ::= SEQUENCE {
   lpE1TestElapsedTime
      Counter32,
   lpE1TestTimeRemaining
      Unsigned32,
   lpE1TestCauseOfTermination
      INTEGER,
   lpE1TestBitsTx
      PassportCounter64,
   lpE1TestBytesTx
      PassportCounter64,
   lpE1TestFrmTx
      PassportCounter64,
   lpE1TestBitsRx
      PassportCounter64,
   lpE1TestBytesRx
      PassportCounter64,
   lpE1TestFrmRx
      PassportCounter64,
   lpE1TestErroredFrmRx
      PassportCounter64,
   lpE1TestBitErrorRate
      AsciiString }

lpE1TestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpE1TestResultsEntry 1 }

lpE1TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpE1TestResultsEntry 2 }

lpE1TestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpE1TestResultsEntry 3 }

lpE1TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpE1TestResultsEntry 4 }

lpE1TestBytesTx OBJECT-TYPE
   SYNTAX     PassportCounter64 
   ACCESS     read-only
   STATUS     mandatory
   DESCRIPTION
     "This attribute is the total number of bytes sent during the test 
      period. This counter is not expected to reach its maximum value."
::= { lpE1TestResultsEntry 5 }

lpE1TestFrmTx OBJECT-TYPE
   SYNTAX     PassportCounter64 
   ACCESS     read-only
   STATUS     mandatory
   DESCRIPTION
     "This attribute is the total number of frames sent during the test 
      period. This counter is not expected to reach its maximum value."
::= { lpE1TestResultsEntry 6 }

lpE1TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpE1TestResultsEntry 7 }

lpE1TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpE1TestResultsEntry 8 }

lpE1TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpE1TestResultsEntry 9 }

lpE1TestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpE1TestResultsEntry 10 }

lpE1TestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpE1TestResultsEntry 11 }


-- LogicalProcessor/n E1/0 Dsp
-- The Dsp component presents the status of the Digital Signal 
-- Processors (DSPs) present on a voice card.
-- A voice card's Dsp component is created automatically whenever 
-- the parent E1 component becomes active, and remains in existence 
-- as long as the E1 component exists. Dsp components cannot be 
-- added or deleted.

lpE1Dsp OBJECT IDENTIFIER ::= { lpE1 4 }



lpE1DspRowStatusTable OBJECT-TYPE
   SYNTAX     SEQUENCE OF LpE1DspRowStatusEntry
   ACCESS     not-accessible
   STATUS     mandatory
   DESCRIPTION
     "This entry controls the addition and deletion of 
      lpE1Dsp components."
::= { lpE1Dsp 1 }

lpE1DspRowStatusEntry OBJECT-TYPE
   SYNTAX     LpE1DspRowStatusEntry
   ACCESS     not-accessible
   STATUS     mandatory
   DESCRIPTION
     "A single entry in the table represents a single 
      lpE1Dsp component."
   INDEX {
      lpIndex,
      lpE1Index,
      lpE1DspIndex }
::= { lpE1DspRowStatusTable 1 }

LpE1DspRowStatusEntry ::= SEQUENCE {
   lpE1DspRowStatus
      RowStatus,
   lpE1DspComponentName
      DisplayString,
   lpE1DspStorageType
      StorageType,
   lpE1DspIndex
      NonReplicated }

lpE1DspRowStatus OBJECT-TYPE
   SYNTAX     RowStatus 
   ACCESS     read-only
   STATUS     mandatory
   DESCRIPTION
     "This variable is used as the basis for SNMP naming of
      lpE1Dsp components.
      These components cannot be added nor deleted."
::= { lpE1DspRowStatusEntry 1 }

lpE1DspComponentName OBJECT-TYPE
   SYNTAX     DisplayString 
   ACCESS     read-only
   STATUS     mandatory
   DESCRIPTION
     "This variable provides the component's string name for
      use with the ASCII Console Interface"
::= { lpE1DspRowStatusEntry 2 }

lpE1DspStorageType OBJECT-TYPE
   SYNTAX     StorageType 
   ACCESS     read-only
   STATUS     mandatory
   DESCRIPTION
     "This variable represents the storage type value for the
      lpE1Dsp tables."
::= { lpE1DspRowStatusEntry 4 }

lpE1DspIndex OBJECT-TYPE
   SYNTAX     NonReplicated 
   ACCESS     not-accessible
   STATUS     mandatory
   DESCRIPTION
     "This variable represents the index for the lpE1Dsp tables."
::= { lpE1DspRowStatusEntry 10 }


-- LogicalProcessor/n E1/0 Audio
-- The Audio component presents the audio status of the channels on a 
-- voice card.
-- A voice card's Audio component is created automatically whenever 
-- the parent E1 component becomes active, and remains in existence 
-- as long as the E1 component exists. Audio components cannot be 
-- added or deleted.

lpE1Audio OBJECT IDENTIFIER ::= { lpE1 5 }



lpE1AudioRowStatusTable OBJECT-TYPE
   SYNTAX     SEQUENCE OF LpE1AudioRowStatusEntry
   ACCESS     not-accessible
   STATUS     mandatory
   DESCRIPTION
     "This entry controls the addition and deletion of 
      lpE1Audio components."
::= { lpE1Audio 1 }

lpE1AudioRowStatusEntry OBJECT-TYPE
   SYNTAX     LpE1AudioRowStatusEntry
   ACCESS     not-accessible
   STATUS     mandatory
   DESCRIPTION
     "A single entry in the table represents a single 
      lpE1Audio component."
   INDEX {
      lpIndex,
      lpE1Index,
      lpE1AudioIndex }
::= { lpE1AudioRowStatusTable 1 }

LpE1AudioRowStatusEntry ::= SEQUENCE {
   lpE1AudioRowStatus
      RowStatus,
   lpE1AudioComponentName
      DisplayString,
   lpE1AudioStorageType
      StorageType,
   lpE1AudioIndex
      NonReplicated }

lpE1AudioRowStatus OBJECT-TYPE
   SYNTAX     RowStatus 
   ACCESS     read-only
   STATUS     mandatory
   DESCRIPTION
     "This variable is used as the basis for SNMP naming of
      lpE1Audio components.
      These components cannot be added nor deleted."
::= { lpE1AudioRowStatusEntry 1 }

lpE1AudioComponentName OBJECT-TYPE
   SYNTAX     DisplayString 
   ACCESS     read-only
   STATUS     mandatory
   DESCRIPTION
     "This variable provides the component's string name for
      use with the ASCII Console Interface"
::= { lpE1AudioRowStatusEntry 2 }

lpE1AudioStorageType OBJECT-TYPE
   SYNTAX     StorageType 
   ACCESS     read-only
   STATUS     mandatory
   DESCRIPTION
     "This variable represents the storage type value for the
      lpE1Audio tables."
::= { lpE1AudioRowStatusEntry 4 }

lpE1AudioIndex OBJECT-TYPE
   SYNTAX     NonReplicated 
   ACCESS     not-accessible
   STATUS     mandatory
   DESCRIPTION
     "This variable represents the index for the lpE1Audio tables."
::= { lpE1AudioRowStatusEntry 10 }


-- 
-- Lp/n V35/n
-- 
-- The V35 component controls a Passport V.35 interface.

lpV35 OBJECT IDENTIFIER ::= { lp 9 }



lpV35RowStatusTable OBJECT-TYPE
   SYNTAX     SEQUENCE OF LpV35RowStatusEntry
   ACCESS     not-accessible
   STATUS     mandatory
   DESCRIPTION
     "This entry controls the addition and deletion of 
      lpV35 components."
::= { lpV35 1 }

lpV35RowStatusEntry OBJECT-TYPE
   SYNTAX     LpV35RowStatusEntry
   ACCESS     not-accessible
   STATUS     mandatory
   DESCRIPTION
     "A single entry in the table represents a single 
      lpV35 component."
   INDEX {
      lpIndex,
      lpV35Index }
::= { lpV35RowStatusTable 1 }

LpV35RowStatusEntry ::= SEQUENCE {
   lpV35RowStatus
      RowStatus,
   lpV35ComponentName
      DisplayString,
   lpV35StorageType
      StorageType,
   lpV35Index
      Integer32 }

lpV35RowStatus OBJECT-TYPE
   SYNTAX     RowStatus 
   ACCESS     read-write
   STATUS     mandatory
   DESCRIPTION
     "This variable is used as the basis for SNMP naming of
      lpV35 components.
      These components can be added and deleted."
::= { lpV35RowStatusEntry 1 }

lpV35ComponentName OBJECT-TYPE
   SYNTAX     DisplayString 
   ACCESS     read-only
   STATUS     mandatory
   DESCRIPTION
     "This variable provides the component's string name for
      use with the ASCII Console Interface"
::= { lpV35RowStatusEntry 2 }

lpV35StorageType OBJECT-TYPE
   SYNTAX     StorageType 
   ACCESS     read-only
   STATUS     mandatory
   DESCRIPTION
     "This variable represents the storage type value for the
      lpV35 tables."
::= { lpV35RowStatusEntry 4 }

lpV35Index OBJECT-TYPE
   SYNTAX     Integer32 (0..7)
   ACCESS     not-accessible
   STATUS     mandatory
   DESCRIPTION
     "This variable represents the index for the lpV35 tables."
::= { lpV35RowStatusEntry 10 }

lpV35ProvTable OBJECT-TYPE
   SYNTAX     SEQUENCE OF LpV35ProvEntry
   ACCESS     not-accessible
   STATUS     mandatory
   DESCRIPTION
     "This group contains all specific provisioning data for a V35 
      component."
::= { lpV35 10 }

lpV35ProvEntry OBJECT-TYPE
   SYNTAX     LpV35ProvEntry
   ACCESS     not-accessible
   STATUS     mandatory
   DESCRIPTION
     "An entry in the lpV35ProvTable."
   INDEX {
      lpIndex,
      lpV35Index }
::= { lpV35ProvTable 1 }

LpV35ProvEntry ::= SEQUENCE {
   lpV35LinkMode
      INTEGER,
   lpV35ReadyLineState
      OCTET STRING,
   lpV35DataTransferLineState
      OCTET STRING,
   lpV35LineStatusTimeOut
      Unsigned32,
   lpV35LineSpeed
      Unsigned32,
   lpV35ClockingSource
      INTEGER,
   lpV35DteDataClockSource
      INTEGER,
   lpV35ApplicationFramerName
      Link,
   lpV35EnableDynamicSpeed
      INTEGER }

lpV35LinkMode OBJECT-TYPE
   SYNTAX     INTEGER  {
                 dte(0),
                 dce(128) }
   ACCESS     read-write
   STATUS     mandatory
   DESCRIPTION
     "This attribute defines the intended gender of the V.35 interface. The 
      actual gender of the interface is determined by the physical 
      connection to the patch panel. If the hardware setup does not match 
      this attribute, an alarm will be generated.
      
      In dte mode, the RTS line signal is driven as specified by the 
      attribute readyLineState when the interface passes its initial 
      diagnostics. Then, the RTS line signal will be driven as specified in 
      the attribute dataTransferLineState when the application is ready to 
      transfer data. On the other hand, the input line signals (RFS, DSR, 
      and DCD) are compared against those specified in the attributes 
      readyLineState and dataTransferLineState. The application will be 
      notified when the specified input line states are observed.
      
      In dce mode, the V35 component behaves similarly as when it is in 
      dte mode. However, it will be driving the DCE line signals (RFS, 
      DSR, and DCD) and monitoring the DTE line signal (RTS) as 
      specified by the attributes readyLineState and 
      dataTransferLineState."
   DEFVAL     { dte }
::= { lpV35ProvEntry 1 }

lpV35ReadyLineState OBJECT-TYPE
   SYNTAX     OCTET STRING (SIZE (1))
   ACCESS     read-write
   STATUS     mandatory
   DESCRIPTION
     "This attribute specifies the line signals originating from the V.35 
      interface that will always be turned on, provided the interface passes 
      its diagnostics. This set of signals is generally required for 
      maintaining the connection. Note that both DTE and DCE signals 
      are specified in this attribute. The appropriate set of specified 
      signals will be turned on or checked according to the 
      actualLinkMode.
      See also linkMode.

      Description of bits:
      rfs(0)
      dsr(1)
      dcd(2)
      rts(3)"
   DEFVAL     { 'f0'H }
::= { lpV35ProvEntry 2 }

lpV35DataTransferLineState OBJECT-TYPE
   SYNTAX     OCTET STRING (SIZE (1))
   ACCESS     read-write
   STATUS     mandatory
   DESCRIPTION
     "This attribute specifies the line signals required to indicate that the 
      external equipment is in a good state (that is, data transfer can 
      proceed). Note that both DTE and DCE signals are specified in this 
      attribute. The appropriate set of specified signals will be turned on 
      or checked according to the actualLinkMode. The value of this 
      attribute must be a superset of that of the readyLineState attribute.
      See also linkMode.

      Description of bits:
      rfs(0)
      dsr(1)
      dcd(2)
      rts(3)"
   DEFVAL     { 'f0'H }
::= { lpV35ProvEntry 3 }

lpV35LineStatusTimeOut OBJECT-TYPE
   SYNTAX     Unsigned32 (10..20000)
   ACCESS     read-write
   STATUS     mandatory
   DESCRIPTION
     "This attribute defines the time that the line state must be stable 
      (good or bad) before a line state change is declared."
   DEFVAL     { 1000 }
::= { lpV35ProvEntry 4 }

lpV35LineSpeed OBJECT-TYPE
   SYNTAX     Unsigned32 (9600..3840000)
   ACCESS     read-write
   STATUS     mandatory
   DESCRIPTION
     "This attribute defines the speed of the line for source clocking. This 
      attribute is ignored if the interface is not providing a clock. The 
      clock rate is rounded up to the nearest available value. Note that the 
      actual clock rates are available in the operational attributes 
      actualTxLineSpeed and actualRxLineSpeed. The actual lineSpeeds 
      configurable on a V.35 DCE interface are: 3840000, 2560000, 
      2048000, 1920000, 1536000, 1344000, 1280000, 1024000, 960000, 
      768000, 672000, 640000, 512000, 448000, 384000, 336000, 
      320000, 256000, 224000, 192000, 168000, 128000, 112000, 64000, 
      56000, 48000, 32000, 19200, 9600. Note that linspeeds of 1024000 
      and 2048000 cannot be provisioned on cards that have ports 
      provisioned at 3840000, 2560000, 1920000, 1280000, 960000, 
      640000 or 320000."
   DEFVAL     { 192000 }
::= { lpV35ProvEntry 5 }

lpV35ClockingSource OBJECT-TYPE
   SYNTAX     INTEGER  {
                 local(0),
                 module(1) }
   ACCESS     read-write
   STATUS     mandatory
   DESCRIPTION
     "This attribute defines the source of synchronization of the outgoing 
      clocks. This attribute is only used when the actualLinkMode is dce.
      
      If the value of the attribute is local, the outgoing clocks are 
      synchronized to a local oscillator on the FP.
      
      If the value of the attribute is module, the outgoing clocks are 
      synchronized to the oscillator on the active CP."
::= { lpV35ProvEntry 6 }

lpV35DteDataClockSource OBJECT-TYPE
   SYNTAX     INTEGER  {
                 fromDce(0),
                 fromDte(2) }
   ACCESS     read-write
   STATUS     mandatory
   DESCRIPTION
     "This attribute is only used when the actualLinkMode  is dce. It is 
      used to determine the clock to be used to recover the receive data. A 
      DTE interface uses TSET(DCE) and RSET(DCE) for timing.
      
      If the value of the attribute is fromDce, the DCE uses the internally 
      generated transmit clock to supply both TSET(DCE) and 
      RSET(DCE).
      
      If the value of the attribute is fromDte, the DCE still uses the 
      internally generated transmit clock to supply TSET(DCE), but the 
      receive timing is derived from TSET(DTE) on the link. 
      
      The fromDte mode is recommended when the DTE is far away from 
      the DCE interface. Note that TSET(DTE) is CCITT V.24 circuit 
      113; TSET(DCE) is CCITT V.24 circuit 114; and RSET(DCE) is 
      CCITT V.24 circuit 115."
   DEFVAL     { fromDce }
::= { lpV35ProvEntry 7 }

lpV35ApplicationFramerName OBJECT-TYPE
   SYNTAX     Link 
   ACCESS     read-write
   STATUS     mandatory
   DESCRIPTION
     "This attribute contains the component name of a Framer which is 
      associated with the V35 component."
::= { lpV35ProvEntry 8 }

lpV35EnableDynamicSpeed OBJECT-TYPE
   SYNTAX     INTEGER  {
                 no(0),
                 yes(1) }
   ACCESS     read-write
   STATUS     mandatory
   DESCRIPTION
     "When set to yes, this attribute specifies that the transmit link speed 
      should be set to the calculated receiver link speed. This attribute can 
      be set to yes only if the linkMode is dce and the 
      dteDataClockSource is fromDte."
   DEFVAL     { no }
::= { lpV35ProvEntry 9 }

lpV35CidDataTable OBJECT-TYPE
   SYNTAX     SEQUENCE OF LpV35CidDataEntry
   ACCESS     not-accessible
   STATUS     mandatory
   DESCRIPTION
     "This group contains the attribute for a component's Customer 
      Identifier (CID). Refer to the attribute description for a detailed 
      explanation of CIDs."
::= { lpV35 11 }

lpV35CidDataEntry OBJECT-TYPE
   SYNTAX     LpV35CidDataEntry
   ACCESS     not-accessible
   STATUS     mandatory
   DESCRIPTION
     "An entry in the lpV35CidDataTable."
   INDEX {
      lpIndex,
      lpV35Index }
::= { lpV35CidDataTable 1 }

LpV35CidDataEntry ::= SEQUENCE {
   lpV35CustomerIdentifier
      Unsigned32 }

lpV35CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpV35CidDataEntry 1 }

lpV35AdminInfoTable OBJECT-TYPE
   SYNTAX     SEQUENCE OF LpV35AdminInfoEntry
   ACCESS     not-accessible
   STATUS     mandatory
   DESCRIPTION
     "This group contains the attributes pertaining to the vendor of the 
      equipment."
::= { lpV35 12 }

lpV35AdminInfoEntry OBJECT-TYPE
   SYNTAX     LpV35AdminInfoEntry
   ACCESS     not-accessible
   STATUS     mandatory
   DESCRIPTION
     "An entry in the lpV35AdminInfoTable."
   INDEX {
      lpIndex,
      lpV35Index }
::= { lpV35AdminInfoTable 1 }

LpV35AdminInfoEntry ::= SEQUENCE {
   lpV35Vendor
      AsciiString,
   lpV35CommentText
      AsciiString }

lpV35Vendor OBJECT-TYPE
   SYNTAX     AsciiString (SIZE (0..20))
   ACCESS     read-write
   STATUS     mandatory
   DESCRIPTION
     "This is the name of the vendor supplying the facility."
::= { lpV35AdminInfoEntry 1 }

lpV35CommentText OBJECT-TYPE
   SYNTAX     AsciiString (SIZE (0..60))
   ACCESS     read-write
   STATUS     mandatory
   DESCRIPTION
     "Any miscellaneous text about the facility."
::= { lpV35AdminInfoEntry 2 }

lpV35IfEntryTable OBJECT-TYPE
   SYNTAX     SEQUENCE OF LpV35IfEntryEntry
   ACCESS     not-accessible
   STATUS     mandatory
   DESCRIPTION
     "This group contains the provisionable attributes for the ifEntry."
::= { lpV35 13 }

lpV35IfEntryEntry OBJECT-TYPE
   SYNTAX     LpV35IfEntryEntry
   ACCESS     not-accessible
   STATUS     mandatory
   DESCRIPTION
     "An entry in the lpV35IfEntryTable."
   INDEX {
      lpIndex,
      lpV35Index }
::= { lpV35IfEntryTable 1 }

LpV35IfEntryEntry ::= SEQUENCE {
   lpV35IfAdminStatus
      INTEGER,
   lpV35IfIndex
      InterfaceIndex }

lpV35IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpV35IfEntryEntry 1 }

lpV35IfIndex OBJECT-TYPE
   SYNTAX     InterfaceIndex (1..65535)
   ACCESS     read-only
   STATUS     mandatory
   DESCRIPTION
     "This is the index for the IfEntry. Its value is automatically initialized 
      during the provisioning process."
::= { lpV35IfEntryEntry 2 }

lpV35OperStatusTable OBJECT-TYPE
   SYNTAX     SEQUENCE OF LpV35OperStatusEntry
   ACCESS     not-accessible
   STATUS     mandatory
   DESCRIPTION
     "This group includes the Operational Status attribute. This attribute 
      defines the current operational state of this component."
::= { lpV35 14 }

lpV35OperStatusEntry OBJECT-TYPE
   SYNTAX     LpV35OperStatusEntry
   ACCESS     not-accessible
   STATUS     mandatory
   DESCRIPTION
     "An entry in the lpV35OperStatusTable."
   INDEX {
      lpIndex,
      lpV35Index }
::= { lpV35OperStatusTable 1 }

LpV35OperStatusEntry ::= SEQUENCE {
   lpV35SnmpOperStatus
      INTEGER }

lpV35SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpV35OperStatusEntry 1 }

lpV35StateTable OBJECT-TYPE
   SYNTAX     SEQUENCE OF LpV35StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpV35 15 }

lpV35StateEntry OBJECT-TYPE
   SYNTAX     LpV35StateEntry
   ACCESS     not-accessible
   STATUS     mandatory
   DESCRIPTION
     "An entry in the lpV35StateTable."
   INDEX {
      lpIndex,
      lpV35Index }
::= { lpV35StateTable 1 }

LpV35StateEntry ::= SEQUENCE {
   lpV35AdminState
      INTEGER,
   lpV35OperationalState
      INTEGER,
   lpV35UsageState
      INTEGER,
   lpV35AvailabilityStatus
      OCTET STRING,
   lpV35ProceduralStatus
      OCTET STRING,
   lpV35ControlStatus
      OCTET STRING,
   lpV35AlarmStatus
      OCTET STRING,
   lpV35StandbyStatus
      INTEGER,
   lpV35UnknownStatus
      INTEGER }

lpV35AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpV35StateEntry 1 }

lpV35OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpV35StateEntry 2 }

lpV35UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpV35StateEntry 3 }

lpV35AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpV35StateEntry 4 }

lpV35ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpV35StateEntry 5 }

lpV35ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpV35StateEntry 6 }

lpV35AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpV35StateEntry 7 }

lpV35StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpV35StateEntry 8 }

lpV35UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpV35StateEntry 9 }

lpV35OperTable OBJECT-TYPE
   SYNTAX     SEQUENCE OF LpV35OperEntry
   ACCESS     not-accessible
   STATUS     mandatory
   DESCRIPTION
     "This group contains all specific operational data for a V35 
      component."
::= { lpV35 16 }

lpV35OperEntry OBJECT-TYPE
   SYNTAX     LpV35OperEntry
   ACCESS     not-accessible
   STATUS     mandatory
   DESCRIPTION
     "An entry in the lpV35OperTable."
   INDEX {
      lpIndex,
      lpV35Index }
::= { lpV35OperTable 1 }

LpV35OperEntry ::= SEQUENCE {
   lpV35ActualLinkMode
      INTEGER,
   lpV35LineState
      OCTET STRING,
   lpV35ActualTxLineSpeed
      Gauge32,
   lpV35ActualRxLineSpeed
      Gauge32,
   lpV35DataXferStateChanges
      Counter32 }

lpV35ActualLinkMode OBJECT-TYPE
   SYNTAX     INTEGER  {
                 dte(0),
                 dce(128) }
   ACCESS     read-only
   STATUS     mandatory
   DESCRIPTION
     "This attribute contains the actual link mode defined by the 
      hardware. Note that the hardware overrides the provisionable data. 
      The interface behaves as a DCE or DTE according to the 
      actualLinkMode."
::= { lpV35OperEntry 1 }

lpV35LineState OBJECT-TYPE
   SYNTAX     OCTET STRING (SIZE (1))
   ACCESS     read-only
   STATUS     mandatory
   DESCRIPTION
     "This attribute contains the current state of the interface signals.

      Description of bits:
      rfs(0)
      dsr(1)
      dcd(2)
      rts(3)"
::= { lpV35OperEntry 2 }

lpV35ActualTxLineSpeed OBJECT-TYPE
   SYNTAX     Gauge32 (0..4294967295)
   ACCESS     read-only
   STATUS     mandatory
   DESCRIPTION
     "This attribute is the measured speed of the transmit clock."
::= { lpV35OperEntry 3 }

lpV35ActualRxLineSpeed OBJECT-TYPE
   SYNTAX     Gauge32 (0..4294967295)
   ACCESS     read-only
   STATUS     mandatory
   DESCRIPTION
     "This attribute is the measured speed of the receive clock."
::= { lpV35OperEntry 4 }

lpV35DataXferStateChanges OBJECT-TYPE
   SYNTAX     Counter32 
   ACCESS     read-only
   STATUS     mandatory
   DESCRIPTION
     "This attribute contains the number of times that the line has entered 
      or exited the data transfer state."
::= { lpV35OperEntry 5 }


-- 
-- The Test component is configured to control a hardware facility test 
-- on a physical (V35, X21, DS1, E1, DS3, E3 etc.) or a logical port.

lpV35Test OBJECT IDENTIFIER ::= { lpV35 2 }



lpV35TestRowStatusTable OBJECT-TYPE
   SYNTAX     SEQUENCE OF LpV35TestRowStatusEntry
   ACCESS     not-accessible
   STATUS     mandatory
   DESCRIPTION
     "This entry controls the addition and deletion of 
      lpV35Test components."
::= { lpV35Test 1 }

lpV35TestRowStatusEntry OBJECT-TYPE
   SYNTAX     LpV35TestRowStatusEntry
   ACCESS     not-accessible
   STATUS     mandatory
   DESCRIPTION
     "A single entry in the table represents a single 
      lpV35Test component."
   INDEX {
      lpIndex,
      lpV35Index,
      lpV35TestIndex }
::= { lpV35TestRowStatusTable 1 }

LpV35TestRowStatusEntry ::= SEQUENCE {
   lpV35TestRowStatus
      RowStatus,
   lpV35TestComponentName
      DisplayString,
   lpV35TestStorageType
      StorageType,
   lpV35TestIndex
      NonReplicated }

lpV35TestRowStatus OBJECT-TYPE
   SYNTAX     RowStatus 
   ACCESS     read-only
   STATUS     mandatory
   DESCRIPTION
     "This variable is used as the basis for SNMP naming of
      lpV35Test components.
      These components cannot be added nor deleted."
::= { lpV35TestRowStatusEntry 1 }

lpV35TestComponentName OBJECT-TYPE
   SYNTAX     DisplayString 
   ACCESS     read-only
   STATUS     mandatory
   DESCRIPTION
     "This variable provides the component's string name for
      use with the ASCII Console Interface"
::= { lpV35TestRowStatusEntry 2 }

lpV35TestStorageType OBJECT-TYPE
   SYNTAX     StorageType 
   ACCESS     read-only
   STATUS     mandatory
   DESCRIPTION
     "This variable represents the storage type value for the
      lpV35Test tables."
::= { lpV35TestRowStatusEntry 4 }

lpV35TestIndex OBJECT-TYPE
   SYNTAX     NonReplicated 
   ACCESS     not-accessible
   STATUS     mandatory
   DESCRIPTION
     "This variable represents the index for the lpV35Test tables."
::= { lpV35TestRowStatusEntry 10 }

lpV35TestStateTable OBJECT-TYPE
   SYNTAX     SEQUENCE OF LpV35TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpV35Test 10 }

lpV35TestStateEntry OBJECT-TYPE
   SYNTAX     LpV35TestStateEntry
   ACCESS     not-accessible
   STATUS     mandatory
   DESCRIPTION
     "An entry in the lpV35TestStateTable."
   INDEX {
      lpIndex,
      lpV35Index,
      lpV35TestIndex }
::= { lpV35TestStateTable 1 }

LpV35TestStateEntry ::= SEQUENCE {
   lpV35TestAdminState
      INTEGER,
   lpV35TestOperationalState
      INTEGER,
   lpV35TestUsageState
      INTEGER }

lpV35TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpV35TestStateEntry 1 }

lpV35TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpV35TestStateEntry 2 }

lpV35TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpV35TestStateEntry 3 }

lpV35TestSetupTable OBJECT-TYPE
   SYNTAX     SEQUENCE OF LpV35TestSetupEntry
   ACCESS     not-accessible
   STATUS     mandatory
   DESCRIPTION
     "This group contains all of the operational data for a Test 
      component."
::= { lpV35Test 11 }

lpV35TestSetupEntry OBJECT-TYPE
   SYNTAX     LpV35TestSetupEntry
   ACCESS     not-accessible
   STATUS     mandatory
   DESCRIPTION
     "An entry in the lpV35TestSetupTable."
   INDEX {
      lpIndex,
      lpV35Index,
      lpV35TestIndex }
::= { lpV35TestSetupTable 1 }

LpV35TestSetupEntry ::= SEQUENCE {
   lpV35TestPurpose
      AsciiString,
   lpV35TestType
      INTEGER,
   lpV35TestFrmSize
      Unsigned32,
   lpV35TestFrmPatternType
      INTEGER,
   lpV35TestCustomizedPattern
      Hex,
   lpV35TestDataStartDelay
      Unsigned32,
   lpV35TestDisplayInterval
      Unsigned32,
   lpV35TestDuration
      Unsigned32 }

lpV35TestPurpose OBJECT-TYPE
   SYNTAX     AsciiString (SIZE (0..40))
   ACCESS     read-write
   STATUS     mandatory
   DESCRIPTION
     "This attribute records the purpose of the test so that the test results 
      can be associated and properly analyzed."
::= { lpV35TestSetupEntry 1 }

lpV35TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpV35TestSetupEntry 2 }

lpV35TestFrmSize OBJECT-TYPE
   SYNTAX     Unsigned32 (4..4096)
   ACCESS     read-write
   STATUS     mandatory
   DESCRIPTION
     "This attribute defines the size of the test data frames in number of 
      bytes."
   DEFVAL     { 1024 }
::= { lpV35TestSetupEntry 3 }

lpV35TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpV35TestSetupEntry 4 }

lpV35TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpV35TestSetupEntry 5 }

lpV35TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpV35TestSetupEntry 6 }

lpV35TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpV35TestSetupEntry 7 }

lpV35TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpV35TestSetupEntry 8 }

lpV35TestResultsTable OBJECT-TYPE
   SYNTAX     SEQUENCE OF LpV35TestResultsEntry
   ACCESS     not-accessible
   STATUS     mandatory
   DESCRIPTION
     "This group contains all the statistics related attributes of the Test 
      component."
::= { lpV35Test 12 }

lpV35TestResultsEntry OBJECT-TYPE
   SYNTAX     LpV35TestResultsEntry
   ACCESS     not-accessible
   STATUS     mandatory
   DESCRIPTION
     "An entry in the lpV35TestResultsTable."
   INDEX {
      lpIndex,
      lpV35Index,
      lpV35TestIndex }
::= { lpV35TestResultsTable 1 }

LpV35TestResultsEntry ::= SEQUENCE {
   lpV35TestElapsedTime
      Counter32,
   lpV35TestTimeRemaining
      Unsigned32,
   lpV35TestCauseOfTermination
      INTEGER,
   lpV35TestBitsTx
      PassportCounter64,
   lpV35TestBytesTx
      PassportCounter64,
   lpV35TestFrmTx
      PassportCounter64,
   lpV35TestBitsRx
      PassportCounter64,
   lpV35TestBytesRx
      PassportCounter64,
   lpV35TestFrmRx
      PassportCounter64,
   lpV35TestErroredFrmRx
      PassportCounter64,
   lpV35TestBitErrorRate
      AsciiString }

lpV35TestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpV35TestResultsEntry 1 }

lpV35TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpV35TestResultsEntry 2 }

lpV35TestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpV35TestResultsEntry 3 }

lpV35TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpV35TestResultsEntry 4 }

lpV35TestBytesTx OBJECT-TYPE
   SYNTAX     PassportCounter64 
   ACCESS     read-only
   STATUS     mandatory
   DESCRIPTION
     "This attribute is the total number of bytes sent during the test 
      period. This counter is not expected to reach its maximum value."
::= { lpV35TestResultsEntry 5 }

lpV35TestFrmTx OBJECT-TYPE
   SYNTAX     PassportCounter64 
   ACCESS     read-only
   STATUS     mandatory
   DESCRIPTION
     "This attribute is the total number of frames sent during the test 
      period. This counter is not expected to reach its maximum value."
::= { lpV35TestResultsEntry 6 }

lpV35TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpV35TestResultsEntry 7 }

lpV35TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpV35TestResultsEntry 8 }

lpV35TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpV35TestResultsEntry 9 }

lpV35TestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpV35TestResultsEntry 10 }

lpV35TestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpV35TestResultsEntry 11 }


-- 
-- Lp/n X21/n
-- 
-- The X21 component controls a Passport V.11 interface.

lpX21 OBJECT IDENTIFIER ::= { lp 10 }



lpX21RowStatusTable OBJECT-TYPE
   SYNTAX     SEQUENCE OF LpX21RowStatusEntry
   ACCESS     not-accessible
   STATUS     mandatory
   DESCRIPTION
     "This entry controls the addition and deletion of 
      lpX21 components."
::= { lpX21 1 }

lpX21RowStatusEntry OBJECT-TYPE
   SYNTAX     LpX21RowStatusEntry
   ACCESS     not-accessible
   STATUS     mandatory
   DESCRIPTION
     "A single entry in the table represents a single 
      lpX21 component."
   INDEX {
      lpIndex,
      lpX21Index }
::= { lpX21RowStatusTable 1 }

LpX21RowStatusEntry ::= SEQUENCE {
   lpX21RowStatus
      RowStatus,
   lpX21ComponentName
      DisplayString,
   lpX21StorageType
      StorageType,
   lpX21Index
      Integer32 }

lpX21RowStatus OBJECT-TYPE
   SYNTAX     RowStatus 
   ACCESS     read-write
   STATUS     mandatory
   DESCRIPTION
     "This variable is used as the basis for SNMP naming of
      lpX21 components.
      These components can be added and deleted."
::= { lpX21RowStatusEntry 1 }

lpX21ComponentName OBJECT-TYPE
   SYNTAX     DisplayString 
   ACCESS     read-only
   STATUS     mandatory
   DESCRIPTION
     "This variable provides the component's string name for
      use with the ASCII Console Interface"
::= { lpX21RowStatusEntry 2 }

lpX21StorageType OBJECT-TYPE
   SYNTAX     StorageType 
   ACCESS     read-only
   STATUS     mandatory
   DESCRIPTION
     "This variable represents the storage type value for the
      lpX21 tables."
::= { lpX21RowStatusEntry 4 }

lpX21Index OBJECT-TYPE
   SYNTAX     Integer32 (0..7)
   ACCESS     not-accessible
   STATUS     mandatory
   DESCRIPTION
     "This variable represents the index for the lpX21 tables."
::= { lpX21RowStatusEntry 10 }

lpX21ProvTable OBJECT-TYPE
   SYNTAX     SEQUENCE OF LpX21ProvEntry
   ACCESS     not-accessible
   STATUS     mandatory
   DESCRIPTION
     "This group contains all specific provisioning data for an X21 
      component."
::= { lpX21 10 }

lpX21ProvEntry OBJECT-TYPE
   SYNTAX     LpX21ProvEntry
   ACCESS     not-accessible
   STATUS     mandatory
   DESCRIPTION
     "An entry in the lpX21ProvTable."
   INDEX {
      lpIndex,
      lpX21Index }
::= { lpX21ProvTable 1 }

LpX21ProvEntry ::= SEQUENCE {
   lpX21LinkMode
      INTEGER,
   lpX21ReadyLineState
      OCTET STRING,
   lpX21DataTransferLineState
      OCTET STRING,
   lpX21LineStatusTimeOut
      Unsigned32,
   lpX21LineSpeed
      Unsigned32,
   lpX21ClockingSource
      INTEGER,
   lpX21DteDataClockSource
      INTEGER,
   lpX21LineTerminationRequired
      INTEGER,
   lpX21ApplicationFramerName
      Link,
   lpX21EnableDynamicSpeed
      INTEGER }

lpX21LinkMode OBJECT-TYPE
   SYNTAX     INTEGER  {
                 dte(0),
                 dce(128) }
   ACCESS     read-write
   STATUS     mandatory
   DESCRIPTION
     "This attribute defines the intended gender of the X21 component 
      (V.11 interface). The actual gender of the interface is determined by 
      the physical connection to the patch panel. If the hardware setup 
      does not match this attribute, an alarm will be generated.
      
      In dte mode, the control line signal is driven as specified by the 
      attribute readyLineState when the interface passes its initial 
      diagnostics. Then, the control line signal will be driven as specified 
      in the attribute dataTransferLineState when the application is ready 
      to transfer data. On the other hand, the input line signal (indication) 
      is compared against those specified in the attributes readyLineState 
      and dataTransferLineState. The application will be notified when 
      the specified line states are observed.
      
      In dce mode, the X21 component behaves similarly as when it is in 
      dte mode. However, it will be driving the DCE line signal (control) 
      and monitoring the DTE line signal (indication) as specified by the 
      attributes readyLineState and dataTransferLineState."
   DEFVAL     { dte }
::= { lpX21ProvEntry 1 }

lpX21ReadyLineState OBJECT-TYPE
   SYNTAX     OCTET STRING (SIZE (1))
   ACCESS     read-write
   STATUS     mandatory
   DESCRIPTION
     "This attribute specifies the line signals originating from the V.11 
      interface that will always be turned on, provided the interface passes 
      its diagnostics. This set of signals is generally required to maintain 
      the connection. Note that both DTE and DCE signals are specified 
      in this attribute. The appropriate set of specified signals will be 
      turned on or checked according to the actualLinkMode.
      See also linkMode.

      Description of bits:
      indication(0)
      control(1)"
   DEFVAL     { 'c0'H }
::= { lpX21ProvEntry 2 }

lpX21DataTransferLineState OBJECT-TYPE
   SYNTAX     OCTET STRING (SIZE (1))
   ACCESS     read-write
   STATUS     mandatory
   DESCRIPTION
     "The state of the line signals required to indicate that the external 
      equipment is in a good state (that is, data transfer can proceed). 
      Note that both DTE and DCE signals are specified in this attribute. 
      The appropriate set of specified signals will be turned on or checked 
      according to the actualLinkMode. The value of this attribute must 
      be a superset of that of the readyLineState attribute.
      See also linkMode.

      Description of bits:
      indication(0)
      control(1)"
   DEFVAL     { 'c0'H }
::= { lpX21ProvEntry 3 }

lpX21LineStatusTimeOut OBJECT-TYPE
   SYNTAX     Unsigned32 (10..20000)
   ACCESS     read-write
   STATUS     mandatory
   DESCRIPTION
     "This attribute defines the time the line state must be stable (good or 
      bad) before a state change is declared."
   DEFVAL     { 1000 }
::= { lpX21ProvEntry 4 }

lpX21LineSpeed OBJECT-TYPE
   SYNTAX     Unsigned32 (9600..7680000)
   ACCESS     read-write
   STATUS     mandatory
   DESCRIPTION
     "This attribute defines the speed of the line for source clocking. This 
      attribute is ignored if the interface is not providing a clock. The 
      clock rate is rounded up to the nearest available value. Note that the 
      actual clock rates are available in the operational attributes 
      actualTxLineSpeed and actualRxLineSpeed. The actual lineSpeeds 
      configurable on a V.11 DCE interface are: 7680000, 3840000, 
      2560000, 2048000, 1920000, 1536000, 1344000, 1280000, 
      1024000, 960000, 768000, 672000, 640000, 512000, 448000, 
      384000, 336000, 320000, 256000, 224000, 192000, 168000, 
      128000, 112000, 64000, 56000, 48000, 32000, 19200, 9600. Note 
      that linspeeds of 1024000 and 2048000 cannot be provisioned on 
      cards that have ports provisioned at 3840000, 2560000, 1920000, 
      1280000, 960000, 640000 or 320000.
      DESCRIPTION"
   DEFVAL     { 192000 }
::= { lpX21ProvEntry 5 }

lpX21ClockingSource OBJECT-TYPE
   SYNTAX     INTEGER  {
                 local(0),
                 module(1) }
   ACCESS     read-write
   STATUS     mandatory
   DESCRIPTION
     "This attribute defines the source of synchronization of the outgoing 
      clocks. This attribute is only used when the actualLinkMode is dce.
      
      If the value of the attribute is local, the outgoing clocks are 
      synchronized to a local oscillator on the FP.
      
      If the value of the attribute is module, the outgoing clocks are 
      synchronized to the oscillator on the active CP."
::= { lpX21ProvEntry 6 }

lpX21DteDataClockSource OBJECT-TYPE
   SYNTAX     INTEGER  {
                 fromDce(0),
                 fromDte(2) }
   ACCESS     read-write
   STATUS     mandatory
   DESCRIPTION
     "This attribute is only used when the actualLinkMode is dce. It is 
      used to determine the clock to be used to recover the receive data. 
      Note that a V.11 DTE interface uses the S clock (see X.21 standard) 
      for both receive data and transmit data timing. The DTE interface 
      always loops the received S clock back to the DCE as the X clock 
      (see X.21 standard).
      
      If the value of the attribute is fromDce, the DCE V.11 interface uses 
      the internally generated transmit clock as the S clock and for both 
      receive and transmit data timing. The X clock is ignored.
      
      If the value of the attribute is fromDte, the DCE still uses the 
      internally generated transmit clock as the S clock and for transmit 
      data timing, but the receive data timing is derived from the X clock.
      
      The fromDte mode is recommended when the DTE is far away from 
      the DCE interface."
   DEFVAL     { fromDce }
::= { lpX21ProvEntry 7 }

lpX21LineTerminationRequired OBJECT-TYPE
   SYNTAX     INTEGER  {
                 no(0),
                 yes(1) }
   ACCESS     read-write
   STATUS     mandatory
   DESCRIPTION
     "This attribute specifies whether termination is required for this 
      interface. If the hardware setup does not match this attribute, an 
      alarm will be generated."
   DEFVAL     { yes }
::= { lpX21ProvEntry 8 }

lpX21ApplicationFramerName OBJECT-TYPE
   SYNTAX     Link 
   ACCESS     read-write
   STATUS     mandatory
   DESCRIPTION
     "This attribute contains the component name of a Framer which is 
      associated with the X21 component."
::= { lpX21ProvEntry 9 }

lpX21EnableDynamicSpeed OBJECT-TYPE
   SYNTAX     INTEGER  {
                 no(0),
                 yes(1) }
   ACCESS     read-write
   STATUS     mandatory
   DESCRIPTION
     "When set to yes, this attribute specifies that the transmit link speed 
      should be set to the calculated receiver link speed. This attribute can 
      be set to yes only if the linkMode is dce and the 
      dteDataClockSource is fromDte.."
   DEFVAL     { no }
::= { lpX21ProvEntry 10 }

lpX21CidDataTable OBJECT-TYPE
   SYNTAX     SEQUENCE OF LpX21CidDataEntry
   ACCESS     not-accessible
   STATUS     mandatory
   DESCRIPTION
     "This group contains the attribute for a component's Customer 
      Identifier (CID). Refer to the attribute description for a detailed 
      explanation of CIDs."
::= { lpX21 11 }

lpX21CidDataEntry OBJECT-TYPE
   SYNTAX     LpX21CidDataEntry
   ACCESS     not-accessible
   STATUS     mandatory
   DESCRIPTION
     "An entry in the lpX21CidDataTable."
   INDEX {
      lpIndex,
      lpX21Index }
::= { lpX21CidDataTable 1 }

LpX21CidDataEntry ::= SEQUENCE {
   lpX21CustomerIdentifier
      Unsigned32 }

lpX21CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpX21CidDataEntry 1 }

lpX21AdminInfoTable OBJECT-TYPE
   SYNTAX     SEQUENCE OF LpX21AdminInfoEntry
   ACCESS     not-accessible
   STATUS     mandatory
   DESCRIPTION
     "This group contains the attributes pertaining to the vendor of the 
      equipment."
::= { lpX21 12 }

lpX21AdminInfoEntry OBJECT-TYPE
   SYNTAX     LpX21AdminInfoEntry
   ACCESS     not-accessible
   STATUS     mandatory
   DESCRIPTION
     "An entry in the lpX21AdminInfoTable."
   INDEX {
      lpIndex,
      lpX21Index }
::= { lpX21AdminInfoTable 1 }

LpX21AdminInfoEntry ::= SEQUENCE {
   lpX21Vendor
      AsciiString,
   lpX21CommentText
      AsciiString }

lpX21Vendor OBJECT-TYPE
   SYNTAX     AsciiString (SIZE (0..20))
   ACCESS     read-write
   STATUS     mandatory
   DESCRIPTION
     "This is the name of the vendor supplying the facility."
::= { lpX21AdminInfoEntry 1 }

lpX21CommentText OBJECT-TYPE
   SYNTAX     AsciiString (SIZE (0..60))
   ACCESS     read-write
   STATUS     mandatory
   DESCRIPTION
     "Any miscellaneous text about the facility."
::= { lpX21AdminInfoEntry 2 }

lpX21IfEntryTable OBJECT-TYPE
   SYNTAX     SEQUENCE OF LpX21IfEntryEntry
   ACCESS     not-accessible
   STATUS     mandatory
   DESCRIPTION
     "This group contains the provisionable attributes for the ifEntry."
::= { lpX21 13 }

lpX21IfEntryEntry OBJECT-TYPE
   SYNTAX     LpX21IfEntryEntry
   ACCESS     not-accessible
   STATUS     mandatory
   DESCRIPTION
     "An entry in the lpX21IfEntryTable."
   INDEX {
      lpIndex,
      lpX21Index }
::= { lpX21IfEntryTable 1 }

LpX21IfEntryEntry ::= SEQUENCE {
   lpX21IfAdminStatus
      INTEGER,
   lpX21IfIndex
      InterfaceIndex }

lpX21IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpX21IfEntryEntry 1 }

lpX21IfIndex OBJECT-TYPE
   SYNTAX     InterfaceIndex (1..65535)
   ACCESS     read-only
   STATUS     mandatory
   DESCRIPTION
     "This is the index for the IfEntry. Its value is automatically initialized 
      during the provisioning process."
::= { lpX21IfEntryEntry 2 }

lpX21OperStatusTable OBJECT-TYPE
   SYNTAX     SEQUENCE OF LpX21OperStatusEntry
   ACCESS     not-accessible
   STATUS     mandatory
   DESCRIPTION
     "This group includes the Operational Status attribute. This attribute 
      defines the current operational state of this component."
::= { lpX21 14 }

lpX21OperStatusEntry OBJECT-TYPE
   SYNTAX     LpX21OperStatusEntry
   ACCESS     not-accessible
   STATUS     mandatory
   DESCRIPTION
     "An entry in the lpX21OperStatusTable."
   INDEX {
      lpIndex,
      lpX21Index }
::= { lpX21OperStatusTable 1 }

LpX21OperStatusEntry ::= SEQUENCE {
   lpX21SnmpOperStatus
      INTEGER }

lpX21SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpX21OperStatusEntry 1 }

lpX21StateTable OBJECT-TYPE
   SYNTAX     SEQUENCE OF LpX21StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpX21 15 }

lpX21StateEntry OBJECT-TYPE
   SYNTAX     LpX21StateEntry
   ACCESS     not-accessible
   STATUS     mandatory
   DESCRIPTION
     "An entry in the lpX21StateTable."
   INDEX {
      lpIndex,
      lpX21Index }
::= { lpX21StateTable 1 }

LpX21StateEntry ::= SEQUENCE {
   lpX21AdminState
      INTEGER,
   lpX21OperationalState
      INTEGER,
   lpX21UsageState
      INTEGER,
   lpX21AvailabilityStatus
      OCTET STRING,
   lpX21ProceduralStatus
      OCTET STRING,
   lpX21ControlStatus
      OCTET STRING,
   lpX21AlarmStatus
      OCTET STRING,
   lpX21StandbyStatus
      INTEGER,
   lpX21UnknownStatus
      INTEGER }

lpX21AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpX21StateEntry 1 }

lpX21OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpX21StateEntry 2 }

lpX21UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpX21StateEntry 3 }

lpX21AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpX21StateEntry 4 }

lpX21ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpX21StateEntry 5 }

lpX21ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpX21StateEntry 6 }

lpX21AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpX21StateEntry 7 }

lpX21StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpX21StateEntry 8 }

lpX21UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpX21StateEntry 9 }

lpX21OperTable OBJECT-TYPE
   SYNTAX     SEQUENCE OF LpX21OperEntry
   ACCESS     not-accessible
   STATUS     mandatory
   DESCRIPTION
     "This group contains all specific operational data for an X21 
      component."
::= { lpX21 16 }

lpX21OperEntry OBJECT-TYPE
   SYNTAX     LpX21OperEntry
   ACCESS     not-accessible
   STATUS     mandatory
   DESCRIPTION
     "An entry in the lpX21OperTable."
   INDEX {
      lpIndex,
      lpX21Index }
::= { lpX21OperTable 1 }

LpX21OperEntry ::= SEQUENCE {
   lpX21ActualLinkMode
      INTEGER,
   lpX21LineState
      OCTET STRING,
   lpX21ActualTxLineSpeed
      Gauge32,
   lpX21ActualRxLineSpeed
      Gauge32,
   lpX21DataXferStateChanges
      Counter32 }

lpX21ActualLinkMode OBJECT-TYPE
   SYNTAX     INTEGER  {
                 dte(0),
                 dce(128) }
   ACCESS     read-only
   STATUS     mandatory
   DESCRIPTION
     "This attribute contains the actual link mode defined by the 
      hardware. Note that the hardware overrides the provisionable data. 
      The interface behaves as a DCE or DTE according to the 
      actualLinkMode."
::= { lpX21OperEntry 1 }

lpX21LineState OBJECT-TYPE
   SYNTAX     OCTET STRING (SIZE (1))
   ACCESS     read-only
   STATUS     mandatory
   DESCRIPTION
     "This attribute contains the current state of the interface signals.

      Description of bits:
      indication(0)
      control(1)"
::= { lpX21OperEntry 2 }

lpX21ActualTxLineSpeed OBJECT-TYPE
   SYNTAX     Gauge32 (0..4294967295)
   ACCESS     read-only
   STATUS     mandatory
   DESCRIPTION
     "This attribute is the measured speed of the transmit clock."
::= { lpX21OperEntry 3 }

lpX21ActualRxLineSpeed OBJECT-TYPE
   SYNTAX     Gauge32 (0..4294967295)
   ACCESS     read-only
   STATUS     mandatory
   DESCRIPTION
     "This attribute is the measured speed of the receive clock."
::= { lpX21OperEntry 4 }

lpX21DataXferStateChanges OBJECT-TYPE
   SYNTAX     Counter32 
   ACCESS     read-only
   STATUS     mandatory
   DESCRIPTION
     "This attribute contains the number of times that the line has entered 
      or exited the data transfer state."
::= { lpX21OperEntry 5 }


-- 
-- The Test component is configured to control a hardware facility test 
-- on a physical (V35, X21, DS1, E1, DS3, E3 etc.) or a logical port.

lpX21Test OBJECT IDENTIFIER ::= { lpX21 2 }



lpX21TestRowStatusTable OBJECT-TYPE
   SYNTAX     SEQUENCE OF LpX21TestRowStatusEntry
   ACCESS     not-accessible
   STATUS     mandatory
   DESCRIPTION
     "This entry controls the addition and deletion of 
      lpX21Test components."
::= { lpX21Test 1 }

lpX21TestRowStatusEntry OBJECT-TYPE
   SYNTAX     LpX21TestRowStatusEntry
   ACCESS     not-accessible
   STATUS     mandatory
   DESCRIPTION
     "A single entry in the table represents a single 
      lpX21Test component."
   INDEX {
      lpIndex,
      lpX21Index,
      lpX21TestIndex }
::= { lpX21TestRowStatusTable 1 }

LpX21TestRowStatusEntry ::= SEQUENCE {
   lpX21TestRowStatus
      RowStatus,
   lpX21TestComponentName
      DisplayString,
   lpX21TestStorageType
      StorageType,
   lpX21TestIndex
      NonReplicated }

lpX21TestRowStatus OBJECT-TYPE
   SYNTAX     RowStatus 
   ACCESS     read-only
   STATUS     mandatory
   DESCRIPTION
     "This variable is used as the basis for SNMP naming of
      lpX21Test components.
      These components cannot be added nor deleted."
::= { lpX21TestRowStatusEntry 1 }

lpX21TestComponentName OBJECT-TYPE
   SYNTAX     DisplayString 
   ACCESS     read-only
   STATUS     mandatory
   DESCRIPTION
     "This variable provides the component's string name for
      use with the ASCII Console Interface"
::= { lpX21TestRowStatusEntry 2 }

lpX21TestStorageType OBJECT-TYPE
   SYNTAX     StorageType 
   ACCESS     read-only
   STATUS     mandatory
   DESCRIPTION
     "This variable represents the storage type value for the
      lpX21Test tables."
::= { lpX21TestRowStatusEntry 4 }

lpX21TestIndex OBJECT-TYPE
   SYNTAX     NonReplicated 
   ACCESS     not-accessible
   STATUS     mandatory
   DESCRIPTION
     "This variable represents the index for the lpX21Test tables."
::= { lpX21TestRowStatusEntry 10 }

lpX21TestStateTable OBJECT-TYPE
   SYNTAX     SEQUENCE OF LpX21TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpX21Test 10 }

lpX21TestStateEntry OBJECT-TYPE
   SYNTAX     LpX21TestStateEntry
   ACCESS     not-accessible
   STATUS     mandatory
   DESCRIPTION
     "An entry in the lpX21TestStateTable."
   INDEX {
      lpIndex,
      lpX21Index,
      lpX21TestIndex }
::= { lpX21TestStateTable 1 }

LpX21TestStateEntry ::= SEQUENCE {
   lpX21TestAdminState
      INTEGER,
   lpX21TestOperationalState
      INTEGER,
   lpX21TestUsageState
      INTEGER }

lpX21TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpX21TestStateEntry 1 }

lpX21TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpX21TestStateEntry 2 }

lpX21TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpX21TestStateEntry 3 }

lpX21TestSetupTable OBJECT-TYPE
   SYNTAX     SEQUENCE OF LpX21TestSetupEntry
   ACCESS     not-accessible
   STATUS     mandatory
   DESCRIPTION
     "This group contains all of the operational data for a Test 
      component."
::= { lpX21Test 11 }

lpX21TestSetupEntry OBJECT-TYPE
   SYNTAX     LpX21TestSetupEntry
   ACCESS     not-accessible
   STATUS     mandatory
   DESCRIPTION
     "An entry in the lpX21TestSetupTable."
   INDEX {
      lpIndex,
      lpX21Index,
      lpX21TestIndex }
::= { lpX21TestSetupTable 1 }

LpX21TestSetupEntry ::= SEQUENCE {
   lpX21TestPurpose
      AsciiString,
   lpX21TestType
      INTEGER,
   lpX21TestFrmSize
      Unsigned32,
   lpX21TestFrmPatternType
      INTEGER,
   lpX21TestCustomizedPattern
      Hex,
   lpX21TestDataStartDelay
      Unsigned32,
   lpX21TestDisplayInterval
      Unsigned32,
   lpX21TestDuration
      Unsigned32 }

lpX21TestPurpose OBJECT-TYPE
   SYNTAX     AsciiString (SIZE (0..40))
   ACCESS     read-write
   STATUS     mandatory
   DESCRIPTION
     "This attribute records the purpose of the test so that the test results 
      can be associated and properly analyzed."
::= { lpX21TestSetupEntry 1 }

lpX21TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpX21TestSetupEntry 2 }

lpX21TestFrmSize OBJECT-TYPE
   SYNTAX     Unsigned32 (4..4096)
   ACCESS     read-write
   STATUS     mandatory
   DESCRIPTION
     "This attribute defines the size of the test data frames in number of 
      bytes."
   DEFVAL     { 1024 }
::= { lpX21TestSetupEntry 3 }

lpX21TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpX21TestSetupEntry 4 }

lpX21TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpX21TestSetupEntry 5 }

lpX21TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpX21TestSetupEntry 6 }

lpX21TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpX21TestSetupEntry 7 }

lpX21TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpX21TestSetupEntry 8 }

lpX21TestResultsTable OBJECT-TYPE
   SYNTAX     SEQUENCE OF LpX21TestResultsEntry
   ACCESS     not-accessible
   STATUS     mandatory
   DESCRIPTION
     "This group contains all the statistics related attributes of the Test 
      component."
::= { lpX21Test 12 }

lpX21TestResultsEntry OBJECT-TYPE
   SYNTAX     LpX21TestResultsEntry
   ACCESS     not-accessible
   STATUS     mandatory
   DESCRIPTION
     "An entry in the lpX21TestResultsTable."
   INDEX {
      lpIndex,
      lpX21Index,
      lpX21TestIndex }
::= { lpX21TestResultsTable 1 }

LpX21TestResultsEntry ::= SEQUENCE {
   lpX21TestElapsedTime
      Counter32,
   lpX21TestTimeRemaining
      Unsigned32,
   lpX21TestCauseOfTermination
      INTEGER,
   lpX21TestBitsTx
      PassportCounter64,
   lpX21TestBytesTx
      PassportCounter64,
   lpX21TestFrmTx
      PassportCounter64,
   lpX21TestBitsRx
      PassportCounter64,
   lpX21TestBytesRx
      PassportCounter64,
   lpX21TestFrmRx
      PassportCounter64,
   lpX21TestErroredFrmRx
      PassportCounter64,
   lpX21TestBitErrorRate
      AsciiString }

lpX21TestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpX21TestResultsEntry 1 }

lpX21TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpX21TestResultsEntry 2 }

lpX21TestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpX21TestResultsEntry 3 }

lpX21TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpX21TestResultsEntry 4 }

lpX21TestBytesTx OBJECT-TYPE
   SYNTAX     PassportCounter64 
   ACCESS     read-only
   STATUS     mandatory
   DESCRIPTION
     "This attribute is the total number of bytes sent during the test 
      period. This counter is not expected to reach its maximum value."
::= { lpX21TestResultsEntry 5 }

lpX21TestFrmTx OBJECT-TYPE
   SYNTAX     PassportCounter64 
   ACCESS     read-only
   STATUS     mandatory
   DESCRIPTION
     "This attribute is the total number of frames sent during the test 
      period. This counter is not expected to reach its maximum value."
::= { lpX21TestResultsEntry 6 }

lpX21TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpX21TestResultsEntry 7 }

lpX21TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpX21TestResultsEntry 8 }

lpX21TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpX21TestResultsEntry 9 }

lpX21TestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpX21TestResultsEntry 10 }

lpX21TestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpX21TestResultsEntry 11 }


-- ApmSonet
-- The Lp/m Sonet/n component controls an OC-3 port on an OC-3 
-- Function Processor. In particular, it deals with SONET medium, 
-- section and line layers. 
-- Note that there can be Sonet and Sdh components coexisting under 
-- the same LP. However they cannot use the same instance.

lpSonet OBJECT IDENTIFIER ::= { lp 14 }



lpSonetRowStatusTable OBJECT-TYPE
   SYNTAX     SEQUENCE OF LpSonetRowStatusEntry
   ACCESS     not-accessible
   STATUS     mandatory
   DESCRIPTION
     "This entry controls the addition and deletion of 
      lpSonet components."
::= { lpSonet 1 }

lpSonetRowStatusEntry OBJECT-TYPE
   SYNTAX     LpSonetRowStatusEntry
   ACCESS     not-accessible
   STATUS     mandatory
   DESCRIPTION
     "A single entry in the table represents a single 
      lpSonet component."
   INDEX {
      lpIndex,
      lpSonetIndex }
::= { lpSonetRowStatusTable 1 }

LpSonetRowStatusEntry ::= SEQUENCE {
   lpSonetRowStatus
      RowStatus,
   lpSonetComponentName
      DisplayString,
   lpSonetStorageType
      StorageType,
   lpSonetIndex
      Integer32 }

lpSonetRowStatus OBJECT-TYPE
   SYNTAX     RowStatus 
   ACCESS     read-write
   STATUS     mandatory
   DESCRIPTION
     "This variable is used as the basis for SNMP naming of
      lpSonet components.
      These components can be added and deleted."
::= { lpSonetRowStatusEntry 1 }

lpSonetComponentName OBJECT-TYPE
   SYNTAX     DisplayString 
   ACCESS     read-only
   STATUS     mandatory
   DESCRIPTION
     "This variable provides the component's string name for
      use with the ASCII Console Interface"
::= { lpSonetRowStatusEntry 2 }

lpSonetStorageType OBJECT-TYPE
   SYNTAX     StorageType 
   ACCESS     read-only
   STATUS     mandatory
   DESCRIPTION
     "This variable represents the storage type value for the
      lpSonet tables."
::= { lpSonetRowStatusEntry 4 }

lpSonetIndex OBJECT-TYPE
   SYNTAX     Integer32 (0..2)
   ACCESS     not-accessible
   STATUS     mandatory
   DESCRIPTION
     "This variable represents the index for the lpSonet tables."
::= { lpSonetRowStatusEntry 10 }

lpSonetProvTable OBJECT-TYPE
   SYNTAX     SEQUENCE OF LpSonetProvEntry
   ACCESS     not-accessible
   STATUS     mandatory
   DESCRIPTION
     "This group contains all of the provisioning data for a Sonet or Sdh 
      component."
::= { lpSonet 10 }

lpSonetProvEntry OBJECT-TYPE
   SYNTAX     LpSonetProvEntry
   ACCESS     not-accessible
   STATUS     mandatory
   DESCRIPTION
     "An entry in the lpSonetProvTable."
   INDEX {
      lpIndex,
      lpSonetIndex }
::= { lpSonetProvTable 1 }

LpSonetProvEntry ::= SEQUENCE {
   lpSonetClockingSource
      INTEGER }

lpSonetClockingSource OBJECT-TYPE
   SYNTAX     INTEGER  {
                 local(0),
                 line(1),
                 module(2) }
   ACCESS     read-write
   STATUS     mandatory
   DESCRIPTION
     "This attribute defines the type of clocking source used for 
      synchronizing the OC-3 transmit clock: local means direct use of 
      the local clock oscillator at its centre frequency; line means the use 
      of a signal phase-locked to the incoming OC-3 line rate; module 
      means the use of a signal phase-locked to the CP reference clock. 
      When adding a Sonet/Sdh component, the clockingSource attribute 
      is set to module if the NetworkSynchronization component has 
      been added and is set to local otherwise.
      Note that the multiport OC-3 cell-based cards has one common 
      clock source for each of the three ports when either the clocking 
      source local or module is selected. For this reason, it is not allowed 
      to have at the same time the clockingSource attribute set to local on 
      one port and module on another port. Furthermore, the 
      clockingSource attribute cannot be set to module if the 
      NetworkSynchronization component has not been added."
::= { lpSonetProvEntry 1 }

lpSonetCidDataTable OBJECT-TYPE
   SYNTAX     SEQUENCE OF LpSonetCidDataEntry
   ACCESS     not-accessible
   STATUS     mandatory
   DESCRIPTION
     "This group contains the attribute for a component's Customer 
      Identifier (CID). Refer to the attribute description for a detailed 
      explanation of CIDs."
::= { lpSonet 11 }

lpSonetCidDataEntry OBJECT-TYPE
   SYNTAX     LpSonetCidDataEntry
   ACCESS     not-accessible
   STATUS     mandatory
   DESCRIPTION
     "An entry in the lpSonetCidDataTable."
   INDEX {
      lpIndex,
      lpSonetIndex }
::= { lpSonetCidDataTable 1 }

LpSonetCidDataEntry ::= SEQUENCE {
   lpSonetCustomerIdentifier
      Unsigned32 }

lpSonetCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpSonetCidDataEntry 1 }

lpSonetAdminInfoTable OBJECT-TYPE
   SYNTAX     SEQUENCE OF LpSonetAdminInfoEntry
   ACCESS     not-accessible
   STATUS     mandatory
   DESCRIPTION
     "This group contains the attributes pertaining to the vendor of the 
      equipment."
::= { lpSonet 12 }

lpSonetAdminInfoEntry OBJECT-TYPE
   SYNTAX     LpSonetAdminInfoEntry
   ACCESS     not-accessible
   STATUS     mandatory
   DESCRIPTION
     "An entry in the lpSonetAdminInfoTable."
   INDEX {
      lpIndex,
      lpSonetIndex }
::= { lpSonetAdminInfoTable 1 }

LpSonetAdminInfoEntry ::= SEQUENCE {
   lpSonetVendor
      AsciiString,
   lpSonetCommentText
      AsciiString }

lpSonetVendor OBJECT-TYPE
   SYNTAX     AsciiString (SIZE (0..20))
   ACCESS     read-write
   STATUS     mandatory
   DESCRIPTION
     "This is the name of the vendor supplying the facility."
::= { lpSonetAdminInfoEntry 1 }

lpSonetCommentText OBJECT-TYPE
   SYNTAX     AsciiString (SIZE (0..60))
   ACCESS     read-write
   STATUS     mandatory
   DESCRIPTION
     "Any miscellaneous text about the facility."
::= { lpSonetAdminInfoEntry 2 }

lpSonetIfEntryTable OBJECT-TYPE
   SYNTAX     SEQUENCE OF LpSonetIfEntryEntry
   ACCESS     not-accessible
   STATUS     mandatory
   DESCRIPTION
     "This group contains the provisionable attributes for the ifEntry."
::= { lpSonet 13 }

lpSonetIfEntryEntry OBJECT-TYPE
   SYNTAX     LpSonetIfEntryEntry
   ACCESS     not-accessible
   STATUS     mandatory
   DESCRIPTION
     "An entry in the lpSonetIfEntryTable."
   INDEX {
      lpIndex,
      lpSonetIndex }
::= { lpSonetIfEntryTable 1 }

LpSonetIfEntryEntry ::= SEQUENCE {
   lpSonetIfAdminStatus
      INTEGER,
   lpSonetIfIndex
      InterfaceIndex }

lpSonetIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpSonetIfEntryEntry 1 }

lpSonetIfIndex OBJECT-TYPE
   SYNTAX     InterfaceIndex (1..65535)
   ACCESS     read-only
   STATUS     mandatory
   DESCRIPTION
     "This is the index for the IfEntry. Its value is automatically initialized 
      during the provisioning process."
::= { lpSonetIfEntryEntry 2 }

lpSonetOperStatusTable OBJECT-TYPE
   SYNTAX     SEQUENCE OF LpSonetOperStatusEntry
   ACCESS     not-accessible
   STATUS     mandatory
   DESCRIPTION
     "This group includes the Operational Status attribute. This attribute 
      defines the current operational state of this component."
::= { lpSonet 14 }

lpSonetOperStatusEntry OBJECT-TYPE
   SYNTAX     LpSonetOperStatusEntry
   ACCESS     not-accessible
   STATUS     mandatory
   DESCRIPTION
     "An entry in the lpSonetOperStatusTable."
   INDEX {
      lpIndex,
      lpSonetIndex }
::= { lpSonetOperStatusTable 1 }

LpSonetOperStatusEntry ::= SEQUENCE {
   lpSonetSnmpOperStatus
      INTEGER }

lpSonetSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpSonetOperStatusEntry 1 }

lpSonetStateTable OBJECT-TYPE
   SYNTAX     SEQUENCE OF LpSonetStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpSonet 15 }

lpSonetStateEntry OBJECT-TYPE
   SYNTAX     LpSonetStateEntry
   ACCESS     not-accessible
   STATUS     mandatory
   DESCRIPTION
     "An entry in the lpSonetStateTable."
   INDEX {
      lpIndex,
      lpSonetIndex }
::= { lpSonetStateTable 1 }

LpSonetStateEntry ::= SEQUENCE {
   lpSonetAdminState
      INTEGER,
   lpSonetOperationalState
      INTEGER,
   lpSonetUsageState
      INTEGER,
   lpSonetAvailabilityStatus
      OCTET STRING,
   lpSonetProceduralStatus
      OCTET STRING,
   lpSonetControlStatus
      OCTET STRING,
   lpSonetAlarmStatus
      OCTET STRING,
   lpSonetStandbyStatus
      INTEGER,
   lpSonetUnknownStatus
      INTEGER }

lpSonetAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpSonetStateEntry 1 }

lpSonetOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpSonetStateEntry 2 }

lpSonetUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpSonetStateEntry 3 }

lpSonetAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpSonetStateEntry 4 }

lpSonetProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpSonetStateEntry 5 }

lpSonetControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpSonetStateEntry 6 }

lpSonetAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpSonetStateEntry 7 }

lpSonetStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpSonetStateEntry 8 }

lpSonetUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpSonetStateEntry 9 }

lpSonetOperTable OBJECT-TYPE
   SYNTAX     SEQUENCE OF LpSonetOperEntry
   ACCESS     not-accessible
   STATUS     mandatory
   DESCRIPTION
     "This group contains the common operational data for Sonet or Sdh 
      component."
::= { lpSonet 16 }

lpSonetOperEntry OBJECT-TYPE
   SYNTAX     LpSonetOperEntry
   ACCESS     not-accessible
   STATUS     mandatory
   DESCRIPTION
     "An entry in the lpSonetOperTable."
   INDEX {
      lpIndex,
      lpSonetIndex }
::= { lpSonetOperTable 1 }

LpSonetOperEntry ::= SEQUENCE {
   lpSonetLosAlarm
      INTEGER,
   lpSonetLofAlarm
      INTEGER,
   lpSonetRxAisAlarm
      INTEGER,
   lpSonetRxRfiAlarm
      INTEGER,
   lpSonetTxAis
      INTEGER,
   lpSonetTxRdi
      INTEGER,
   lpSonetUnusableTxClockRefAlarm
      INTEGER }

lpSonetLosAlarm OBJECT-TYPE
   SYNTAX     INTEGER  {
                 on(0),
                 off(1) }
   ACCESS     read-only
   STATUS     mandatory
   DESCRIPTION
     "This attribute indicates whether a Loss Of Signal (LOS) alarm state 
      has been entered. An LOS alarm state is entered when LOS defects 
      have been observed and accumulated for a period of 2.5 seconds +/- 
      0.5 seconds, or if an LOS defect is present when the criteria for 
      LOF failure declaration have been met. A LOS defect is declared 
      when 20+/-3 us of all-zeros pattern is detected. The LOS defect is 
      cleared when two valid framing words are detected and no Loss Of 
      Signal condition is detected during an interval of 20+/-3 us. If the 
      LOS defects are intermittently occurring, the LOS defect 
      accumulator is decremented at a rate of 1/10 of the incrementing 
      rate (alarm integration ratio of 1/10), with all measurements based 
      on a 200 ms polling cycle.
      The Sonet/Sdh component goes into an operational state of disabled 
      until the LOS alarm condition is cleared. The LOS alarm state is 
      cleared after LOS defects have been absent for a period of 10 
      seconds +/- 0.5 seconds.
      The losAlarm attribute is always set to off when the component has 
      been locked and left offline."
::= { lpSonetOperEntry 1 }

lpSonetLofAlarm OBJECT-TYPE
   SYNTAX     INTEGER  {
                 on(0),
                 off(1) }
   ACCESS     read-only
   STATUS     mandatory
   DESCRIPTION
     "This attribute displays whether a Loss Of Frame (LOF) alarm state 
      has been entered. An LOF alarm state is entered when LOF defects 
      have been observed and accumulated for a period of 2.5 seconds +/- 
      0.5 seconds, except when an LOS defect or failure is present. An 
      LOF defect is detected when getting contiguous errored frame 
      alignment for at least 3 msec. If the LOF defects are intermittently 
      occurring, the LOF defect accumulator is decremented at a rate of 
      1/10 of the incrementing rate (alarm integration ratio of 1/10), with 
      all measurements based on a 200 ms polling cycle.
      The Sonet/Sdh component goes into an operational state of disabled 
      until the LOF alarm condition is cleared. The condition is cleared 
      when framing has been achieved for a period of 10 seconds +/- 0.5 
      seconds.
      The lofAlarm attribute is always set to off when the component has 
      been locked and left offline."
::= { lpSonetOperEntry 2 }

lpSonetRxAisAlarm OBJECT-TYPE
   SYNTAX     INTEGER  {
                 on(0),
                 off(1) }
   ACCESS     read-only
   STATUS     mandatory
   DESCRIPTION
     "This attribute displays whether a Line Alarm Indication Signal (L-
      AIS) alarm state has been entered. An L-AIS alarm state is entered 
      when L-AIS defects have been observed and accumulated for a 
      period of 2.5 seconds +/- 0.5 seconds. The L-AIS defect is the 
      occurrence of the L-AIS signal in five contiguous STS (STM) 
      frames (111 pattern in bits 6,7, and 8 of the K2 bytes). If the L-AIS 
      defects are intermittently occurring, the L-AIS defect accumulator 
      is decremented at a rate of 1/10 of the incrementing rate (alarm 
      integration ratio of 1/10), with all measurements based on a 200 ms 
      polling cycle.
      The Sonet/Sdh component goes into an operational state of disabled 
      until the L-AIS alarm condition is cleared. The condition is cleared 
      after not detecting the L-AIS signal for a period of 10 seconds +/- 
      0.5 seconds.
      The rxAisAlarm attribute is always set to off when the component 
      has been locked and left offline."
::= { lpSonetOperEntry 3 }

lpSonetRxRfiAlarm OBJECT-TYPE
   SYNTAX     INTEGER  {
                 on(0),
                 off(1) }
   ACCESS     read-only
   STATUS     mandatory
   DESCRIPTION
     "This attribute displays whether a Line Remote Failure Indication 
      (LRFI) alarm state has been entered. An L-RFI alarm state is 
      entered when Line Remote Failure Indication (L-RDI) defects have 
      been observed and accumulated for a period of 2.5 seconds +/- 0.5 
      seconds. The L-RDI defect is the occurrence of the L-RDI signal in 
      five contiguous valid STS (STM) frame (110 pattern in bits 6,7, and 
      8 of the K2 bytes). If the L-RDI defects are intermittently occurring, 
      the L-RDI defect accumulator is decremented at a rate of 1/10 of 
      the incrementing rate (alarm integration ratio of 1/10), with all 
      measurements based on a 200 ms polling cycle.
      The Sonet/Sdh component goes into an operational state of disabled 
      until the L-RFI alarm condition is cleared. The condition is cleared 
      after not detecting the L-RDI signal for a period of 10 seconds +/- 
      0.5 seconds.
      The rxRfiAlarm attribute is always set to off when the component 
      has been locked and left offline."
::= { lpSonetOperEntry 4 }

lpSonetTxAis OBJECT-TYPE
   SYNTAX     INTEGER  {
                 on(0),
                 off(1) }
   ACCESS     read-only
   STATUS     mandatory
   DESCRIPTION
     "This attribute displays whether the Line Alarm Indication Signal (L-
      AIS) signal is being transmitted on the outgoing line. This signal is 
      transmitted when the Sonet/Sdh is locked and left offline."
::= { lpSonetOperEntry 5 }

lpSonetTxRdi OBJECT-TYPE
   SYNTAX     INTEGER  {
                 on(0),
                 off(1) }
   ACCESS     read-only
   STATUS     mandatory
   DESCRIPTION
     "This attribute displays whether the Line Remote Defect Indicator 
      (L-RDI) signal is being transmitted over the OC-3 line. The L-RDI 
      signal is transmitted upon the detection of the LOS, LOF or L-AIS 
      defect. This attribute is always set to off when the component has 
      been locked and left offline."
::= { lpSonetOperEntry 6 }

lpSonetUnusableTxClockRefAlarm OBJECT-TYPE
   SYNTAX     INTEGER  {
                 on(0),
                 off(1) }
   ACCESS     read-only
   STATUS     mandatory
   DESCRIPTION
     "This attribute displays whether an Unusable Transmit Clock 
      Reference (UTCR) alarm state has been entered. A UTCR alarm 
      state is entered when a Sonet/Sdh port provisioned to act as a 
      transmit clock reference has received the code 'do not use for 
      synchronization' in the S1 byte (in the SONET/ SDH line 
      overhead) for 2.5 +/- 0.5 seconds.
      The condition is cleared after not detecting the 'do not use for 
      synchronization' code for a period of 10 +/- 0.5 seconds or when 
      the port is no longer provisioned to act as a transmit clock 
      reference.
      A port is acting as a transmit clock reference if it is provisioned 
      with a) a clockingSource of line, or b) it has been provisioned as a 
      primaryReference, secondaryReference or tertiaryReference in the 
      NetworkSynchronization component.
      The unusableTxClockRefAlarm attribute is always set to off when 
      the component has been locked and left offline."
::= { lpSonetOperEntry 7 }

lpSonetStatsTable OBJECT-TYPE
   SYNTAX     SEQUENCE OF LpSonetStatsEntry
   ACCESS     not-accessible
   STATUS     mandatory
   DESCRIPTION
     "This group contains the statistics data for a Sonet or Sdh 
      component. Each attribute type is a non-negative integer which 
      monotonically increases until it reaches a maximum value, at which 
      point it wraps around and starts increasing again from zero."
::= { lpSonet 17 }

lpSonetStatsEntry OBJECT-TYPE
   SYNTAX     LpSonetStatsEntry
   ACCESS     not-accessible
   STATUS     mandatory
   DESCRIPTION
     "An entry in the lpSonetStatsTable."
   INDEX {
      lpIndex,
      lpSonetIndex }
::= { lpSonetStatsTable 1 }

LpSonetStatsEntry ::= SEQUENCE {
   lpSonetRunningTime
      Counter32,
   lpSonetErrorFreeSec
      Counter32,
   lpSonetSectCodeViolations
      Counter32,
   lpSonetSectErroredSec
      Counter32,
   lpSonetSectSevErroredSec
      Counter32,
   lpSonetSectLosSec
      Counter32,
   lpSonetSectSevErroredFrmSec
      Counter32,
   lpSonetSectFailures
      Counter32,
   lpSonetLineCodeViolations
      Counter32,
   lpSonetLineErroredSec
      Counter32,
   lpSonetLineSevErroredSec
      Counter32,
   lpSonetLineAisSec
      Counter32,
   lpSonetLineUnavailSec
      Counter32,
   lpSonetLineFailures
      Counter32,
   lpSonetFarEndLineErrorFreeSec
      Counter32,
   lpSonetFarEndLineCodeViolations
      Counter32,
   lpSonetFarEndLineErroredSec
      Counter32,
   lpSonetFarEndLineSevErroredSec
      Counter32,
   lpSonetFarEndLineAisSec
      Counter32,
   lpSonetFarEndLineUnavailSec
      Counter32,
   lpSonetFarEndLineFailures
      Counter32 }

lpSonetRunningTime OBJECT-TYPE
   SYNTAX     Counter32 
   ACCESS     read-only
   STATUS     mandatory
   DESCRIPTION
     "This attribute indicates the total number of seconds since the Sonet/
      Sdh component has been activated and been in unlocked state. All 
      the other error counts that follow can be updated when this count is 
      active."
::= { lpSonetStatsEntry 1 }

lpSonetErrorFreeSec OBJECT-TYPE
   SYNTAX     Counter32 
   ACCESS     read-only
   STATUS     mandatory
   DESCRIPTION
     "This attribute indicates the number of seconds that the Sonet/Sdh 
      component has been in an near-end error free state."
::= { lpSonetStatsEntry 2 }

lpSonetSectCodeViolations OBJECT-TYPE
   SYNTAX     Counter32 
   ACCESS     read-only
   STATUS     mandatory
   DESCRIPTION
     "This attribute indicates the total number of Section Code Violations 
      (SCVs) detected. A SCV corresponds to section BIP-8 error. SCV 
      counting is inhibited for second intervals where a Section Severely 
      Errored Second (SSES) is counted. The count wraps at its 
      maximum value."
::= { lpSonetStatsEntry 3 }

lpSonetSectErroredSec OBJECT-TYPE
   SYNTAX     Counter32 
   ACCESS     read-only
   STATUS     mandatory
   DESCRIPTION
     "This attribute indicates the total number of Section Errored Seconds 
      (SESs) that have been counted. A SES is declared for second 
      intervals containing one or more SCVs or one or more Loss Of 
      Signal (LOS) or Severely Errored Frame (SEF) defects. A SEF 
      defect is the occurrence of 4 contiguous errored STS or STM frame 
      alignment words."
::= { lpSonetStatsEntry 4 }

lpSonetSectSevErroredSec OBJECT-TYPE
   SYNTAX     Counter32 
   ACCESS     read-only
   STATUS     mandatory
   DESCRIPTION
     "This attribute indicates the total number of Section Severely Errored 
      Seconds (SSESs) that have been counted. A SSES is declared for 
      second intervals containing more than x SCVs or one or more LOS 
      or SEF defects. The value of x is 155 for a 155 Mbits/sec interface."
::= { lpSonetStatsEntry 5 }

lpSonetSectLosSec OBJECT-TYPE
   SYNTAX     Counter32 
   ACCESS     read-only
   STATUS     mandatory
   DESCRIPTION
     "This attribute indicates the total number of Section LOS Seconds 
      (SLOSSs) that have been counted. A SLOSS is declared for second 
      intervals containing one or more LOS defects."
::= { lpSonetStatsEntry 6 }

lpSonetSectSevErroredFrmSec OBJECT-TYPE
   SYNTAX     Counter32 
   ACCESS     read-only
   STATUS     mandatory
   DESCRIPTION
     "This attribute indicates the total number of Section Severely Errored 
      Frame Seconds (SSEFSs) that have been counted. A SSEFS is 
      declared for second intervals containing one or more SEF defects."
::= { lpSonetStatsEntry 7 }

lpSonetSectFailures OBJECT-TYPE
   SYNTAX     Counter32 
   ACCESS     read-only
   STATUS     mandatory
   DESCRIPTION
     "This attribute indicates the total number of times that a section 
      failure (LOS or LOF failure) has been declared."
::= { lpSonetStatsEntry 8 }

lpSonetLineCodeViolations OBJECT-TYPE
   SYNTAX     Counter32 
   ACCESS     read-only
   STATUS     mandatory
   DESCRIPTION
     "This attribute indicates the total number of Line Code Violations 
      (LCVs) detected. A LCV corresponds to a line BIP-24 errors. LCV 
      counting is inhibited for second intervals where a Line Severely 
      Errored Second (LSES) is counted. Counting of LCVs is also 
      inhibited over second intervals where a Line Unavailable Second 
      (LUAS) is counted. The count wraps at its maximum value."
::= { lpSonetStatsEntry 9 }

lpSonetLineErroredSec OBJECT-TYPE
   SYNTAX     Counter32 
   ACCESS     read-only
   STATUS     mandatory
   DESCRIPTION
     "This attribute indicates the total number of Line Errored Seconds 
      (LESs) that have been counted. A LES is declared for second 
      intervals containing one or more LCVs or one or more line AIS 
      defects. Counting of LES is inhibited over second intervals where a 
      LUAS is counted."
::= { lpSonetStatsEntry 10 }

lpSonetLineSevErroredSec OBJECT-TYPE
   SYNTAX     Counter32 
   ACCESS     read-only
   STATUS     mandatory
   DESCRIPTION
     "This attribute indicates the total number of Line Severely Errored 
      Seconds (LSESs) that have been counted. A LSES is declared for 
      second intervals containing more than x LCVs or one or more L-
      AIS defects. The value of x is 154 for a 155 Mbits/sec interface. 
      Counting of LSES is inhibited over second intervals where a LUAS 
      is counted."
::= { lpSonetStatsEntry 11 }

lpSonetLineAisSec OBJECT-TYPE
   SYNTAX     Counter32 
   ACCESS     read-only
   STATUS     mandatory
   DESCRIPTION
     "This attribute indicates the total number of Line AIS Seconds 
      (LAISSs) that have been counted. A LAISS is declared for second 
      intervals containing one or more L-AIS defects. Counting of LAISS 
      is inhibited over second intervals where a LUAS is counted."
::= { lpSonetStatsEntry 12 }

lpSonetLineUnavailSec OBJECT-TYPE
   SYNTAX     Counter32 
   ACCESS     read-only
   STATUS     mandatory
   DESCRIPTION
     "This attribute indicates the total number of one second intervals for 
      which the STS line is unavailable. The STS line becomes 
      unavailable at the onset of 10 consecutive LSESs. The 10 LSESs are 
      included in the unavailable time. Once unavailable, the STS line 
      becomes available at the onset of 10 contiguous seconds with no 
      LSES. The 10 seconds with no LSES are excluded from the 
      unavailable time. For second intervals where a Line Unavailable 
      Second (LUAS) is counted, counting of LCV, LES, LSES and 
      LAISS is inhibited."
::= { lpSonetStatsEntry 13 }

lpSonetLineFailures OBJECT-TYPE
   SYNTAX     Counter32 
   ACCESS     read-only
   STATUS     mandatory
   DESCRIPTION
     "This attribute indicates the total number of times that a line failure 
      (L-AIS failure) has been declared."
::= { lpSonetStatsEntry 14 }

lpSonetFarEndLineErrorFreeSec OBJECT-TYPE
   SYNTAX     Counter32 
   ACCESS     read-only
   STATUS     mandatory
   DESCRIPTION
     "This attribute indicates the number of seconds that the Sonet/Sdh 
      component has been in an far-end error free state."
::= { lpSonetStatsEntry 15 }

lpSonetFarEndLineCodeViolations OBJECT-TYPE
   SYNTAX     Counter32 
   ACCESS     read-only
   STATUS     mandatory
   DESCRIPTION
     "This attribute indicates the total number of line FEBE detected from 
      the incoming line. The counting of line FEBE is inhibited for 
      second intervals where a Far-End Line Severely Errored Second 
      (FELSES) is counted. Counting of FELCVs is also inhibited over 
      second intervals where a Far-End Line Unavailable Second 
      (FELUAS) is counted. The count wraps at its maximum value."
::= { lpSonetStatsEntry 16 }

lpSonetFarEndLineErroredSec OBJECT-TYPE
   SYNTAX     Counter32 
   ACCESS     read-only
   STATUS     mandatory
   DESCRIPTION
     "This attribute indicates the total number of Far-End Line Errored 
      Seconds (FELESs) that have been counted. A FELES is declared 
      for second intervals containing one or more Far-End Line CVs 
      (FELCVs) or one or more L-RDI defects. Counting of FELES is 
      inhibited over second intervals where a FELUAS is counted."
::= { lpSonetStatsEntry 17 }

lpSonetFarEndLineSevErroredSec OBJECT-TYPE
   SYNTAX     Counter32 
   ACCESS     read-only
   STATUS     mandatory
   DESCRIPTION
     "This attribute indicates the total number of Far-End Line Severely 
      Errored Seconds (FELSESs) that have been counted. A FELSES is 
      declared for second intervals containing more than x FELCVs or 
      one or more L-RDI defects. The value of x is 154 for a 155 Mbits/
      sec interface. Counting of FELSES is inhibited over second 
      intervals where a FELUAS is counted."
::= { lpSonetStatsEntry 18 }

lpSonetFarEndLineAisSec OBJECT-TYPE
   SYNTAX     Counter32 
   ACCESS     read-only
   STATUS     mandatory
   DESCRIPTION
     "This attribute indicates the total number of Far-End Line AIS 
      Seconds (FELAISSs) that have been counted. A FELAISS is 
      declared for second intervals one or more L-RDI defects. Counting 
      of FELAISS is inhibited over second intervals where a FELUAS is 
      counted."
::= { lpSonetStatsEntry 19 }

lpSonetFarEndLineUnavailSec OBJECT-TYPE
   SYNTAX     Counter32 
   ACCESS     read-only
   STATUS     mandatory
   DESCRIPTION
     "This attribute indicates the total number of one second intervals for 
      which the STS far-end line is unavailable. The STS far-end line 
      becomes unavailable at the onset of 10 consecutive FELSESs. The 
      10 FELSESs are included in the unavailable time. Once unavailable, 
      the STS far-end line becomes available at the onset of 10 
      contiguous seconds with no FELSES. The 10 seconds with no 
      FELSES are excluded from the unavailable time. For second 
      intervals where a Far-End Line Unavailable Second (FELUAS) is 
      counted, counting of FELCV, FELES, FELSES and FELAISS is 
      inhibited."
::= { lpSonetStatsEntry 20 }

lpSonetFarEndLineFailures OBJECT-TYPE
   SYNTAX     Counter32 
   ACCESS     read-only
   STATUS     mandatory
   DESCRIPTION
     "This attribute indicates the total number of times that a far-end line 
      failure (L-RFI failure) has been declared."
::= { lpSonetStatsEntry 21 }


-- ApmSonetSdhPath
-- The Lp/m Sonet/n Path or Lp/m Sdh/n Path component controls a 
-- path signal that is carried within a SONET or SDH signal. The Path 
-- component can only be added under a Sonet or Sdh component.

lpSonetPath OBJECT IDENTIFIER ::= { lpSonet 2 }



lpSonetPathRowStatusTable OBJECT-TYPE
   SYNTAX     SEQUENCE OF LpSonetPathRowStatusEntry
   ACCESS     not-accessible
   STATUS     mandatory
   DESCRIPTION
     "This entry controls the addition and deletion of 
      lpSonetPath components."
::= { lpSonetPath 1 }

lpSonetPathRowStatusEntry OBJECT-TYPE
   SYNTAX     LpSonetPathRowStatusEntry
   ACCESS     not-accessible
   STATUS     mandatory
   DESCRIPTION
     "A single entry in the table represents a single 
      lpSonetPath component."
   INDEX {
      lpIndex,
      lpSonetIndex,
      lpSonetPathIndex }
::= { lpSonetPathRowStatusTable 1 }

LpSonetPathRowStatusEntry ::= SEQUENCE {
   lpSonetPathRowStatus
      RowStatus,
   lpSonetPathComponentName
      DisplayString,
   lpSonetPathStorageType
      StorageType,
   lpSonetPathIndex
      Integer32 }

lpSonetPathRowStatus OBJECT-TYPE
   SYNTAX     RowStatus 
   ACCESS     read-write
   STATUS     mandatory
   DESCRIPTION
     "This variable is used as the basis for SNMP naming of
      lpSonetPath components.
      These components can be added and deleted."
::= { lpSonetPathRowStatusEntry 1 }

lpSonetPathComponentName OBJECT-TYPE
   SYNTAX     DisplayString 
   ACCESS     read-only
   STATUS     mandatory
   DESCRIPTION
     "This variable provides the component's string name for
      use with the ASCII Console Interface"
::= { lpSonetPathRowStatusEntry 2 }

lpSonetPathStorageType OBJECT-TYPE
   SYNTAX     StorageType 
   ACCESS     read-only
   STATUS     mandatory
   DESCRIPTION
     "This variable represents the storage type value for the
      lpSonetPath tables."
::= { lpSonetPathRowStatusEntry 4 }

lpSonetPathIndex OBJECT-TYPE
   SYNTAX     Integer32 (0..0)
   ACCESS     not-accessible
   STATUS     mandatory
   DESCRIPTION
     "This variable represents the index for the lpSonetPath tables."
::= { lpSonetPathRowStatusEntry 10 }

lpSonetPathProvTable OBJECT-TYPE
   SYNTAX     SEQUENCE OF LpSonetPathProvEntry
   ACCESS     not-accessible
   STATUS     mandatory
   DESCRIPTION
     "This group contains all of the provisioning data for a Sonet/Sdh 
      Path component."
::= { lpSonetPath 10 }

lpSonetPathProvEntry OBJECT-TYPE
   SYNTAX     LpSonetPathProvEntry
   ACCESS     not-accessible
   STATUS     mandatory
   DESCRIPTION
     "An entry in the lpSonetPathProvTable."
   INDEX {
      lpIndex,
      lpSonetIndex,
      lpSonetPathIndex }
::= { lpSonetPathProvTable 1 }

LpSonetPathProvEntry ::= SEQUENCE {
   lpSonetPathApplicationFramerName
      Link }

lpSonetPathApplicationFramerName OBJECT-TYPE
   SYNTAX     Link 
   ACCESS     read-write
   STATUS     mandatory
   DESCRIPTION
     "This attribute defines the link to the software stack. It defines which 
      application is running on top of the Path component."
::= { lpSonetPathProvEntry 1 }

lpSonetPathCidDataTable OBJECT-TYPE
   SYNTAX     SEQUENCE OF LpSonetPathCidDataEntry
   ACCESS     not-accessible
   STATUS     mandatory
   DESCRIPTION
     "This group contains the attribute for a component's Customer 
      Identifier (CID). Refer to the attribute description for a detailed 
      explanation of CIDs."
::= { lpSonetPath 11 }

lpSonetPathCidDataEntry OBJECT-TYPE
   SYNTAX     LpSonetPathCidDataEntry
   ACCESS     not-accessible
   STATUS     mandatory
   DESCRIPTION
     "An entry in the lpSonetPathCidDataTable."
   INDEX {
      lpIndex,
      lpSonetIndex,
      lpSonetPathIndex }
::= { lpSonetPathCidDataTable 1 }

LpSonetPathCidDataEntry ::= SEQUENCE {
   lpSonetPathCustomerIdentifier
      Unsigned32 }

lpSonetPathCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpSonetPathCidDataEntry 1 }

lpSonetPathStateTable OBJECT-TYPE
   SYNTAX     SEQUENCE OF LpSonetPathStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpSonetPath 12 }

lpSonetPathStateEntry OBJECT-TYPE
   SYNTAX     LpSonetPathStateEntry
   ACCESS     not-accessible
   STATUS     mandatory
   DESCRIPTION
     "An entry in the lpSonetPathStateTable."
   INDEX {
      lpIndex,
      lpSonetIndex,
      lpSonetPathIndex }
::= { lpSonetPathStateTable 1 }

LpSonetPathStateEntry ::= SEQUENCE {
   lpSonetPathAdminState
      INTEGER,
   lpSonetPathOperationalState
      INTEGER,
   lpSonetPathUsageState
      INTEGER,
   lpSonetPathAvailabilityStatus
      OCTET STRING,
   lpSonetPathProceduralStatus
      OCTET STRING,
   lpSonetPathControlStatus
      OCTET STRING,
   lpSonetPathAlarmStatus
      OCTET STRING,
   lpSonetPathStandbyStatus
      INTEGER,
   lpSonetPathUnknownStatus
      INTEGER }

lpSonetPathAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpSonetPathStateEntry 1 }

lpSonetPathOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpSonetPathStateEntry 2 }

lpSonetPathUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpSonetPathStateEntry 3 }

lpSonetPathAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpSonetPathStateEntry 4 }

lpSonetPathProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpSonetPathStateEntry 5 }

lpSonetPathControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpSonetPathStateEntry 6 }

lpSonetPathAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpSonetPathStateEntry 7 }

lpSonetPathStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpSonetPathStateEntry 8 }

lpSonetPathUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpSonetPathStateEntry 9 }

lpSonetPathIfEntryTable OBJECT-TYPE
   SYNTAX     SEQUENCE OF LpSonetPathIfEntryEntry
   ACCESS     not-accessible
   STATUS     mandatory
   DESCRIPTION
     "This group contains the provisionable attributes for the ifEntry."
::= { lpSonetPath 13 }

lpSonetPathIfEntryEntry OBJECT-TYPE
   SYNTAX     LpSonetPathIfEntryEntry
   ACCESS     not-accessible
   STATUS     mandatory
   DESCRIPTION
     "An entry in the lpSonetPathIfEntryTable."
   INDEX {
      lpIndex,
      lpSonetIndex,
      lpSonetPathIndex }
::= { lpSonetPathIfEntryTable 1 }

LpSonetPathIfEntryEntry ::= SEQUENCE {
   lpSonetPathIfAdminStatus
      INTEGER,
   lpSonetPathIfIndex
      InterfaceIndex }

lpSonetPathIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpSonetPathIfEntryEntry 1 }

lpSonetPathIfIndex OBJECT-TYPE
   SYNTAX     InterfaceIndex (1..65535)
   ACCESS     read-only
   STATUS     mandatory
   DESCRIPTION
     "This is the index for the IfEntry. Its value is automatically initialized 
      during the provisioning process."
::= { lpSonetPathIfEntryEntry 2 }

lpSonetPathOperStatusTable OBJECT-TYPE
   SYNTAX     SEQUENCE OF LpSonetPathOperStatusEntry
   ACCESS     not-accessible
   STATUS     mandatory
   DESCRIPTION
     "This group includes the Operational Status attribute. This attribute 
      defines the current operational state of this component."
::= { lpSonetPath 14 }

lpSonetPathOperStatusEntry OBJECT-TYPE
   SYNTAX     LpSonetPathOperStatusEntry
   ACCESS     not-accessible
   STATUS     mandatory
   DESCRIPTION
     "An entry in the lpSonetPathOperStatusTable."
   INDEX {
      lpIndex,
      lpSonetIndex,
      lpSonetPathIndex }
::= { lpSonetPathOperStatusTable 1 }

LpSonetPathOperStatusEntry ::= SEQUENCE {
   lpSonetPathSnmpOperStatus
      INTEGER }

lpSonetPathSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpSonetPathOperStatusEntry 1 }

lpSonetPathOperTable OBJECT-TYPE
   SYNTAX     SEQUENCE OF LpSonetPathOperEntry
   ACCESS     not-accessible
   STATUS     mandatory
   DESCRIPTION
     "This group contains the common operational data for Path 
      component."
::= { lpSonetPath 15 }

lpSonetPathOperEntry OBJECT-TYPE
   SYNTAX     LpSonetPathOperEntry
   ACCESS     not-accessible
   STATUS     mandatory
   DESCRIPTION
     "An entry in the lpSonetPathOperTable."
   INDEX {
      lpIndex,
      lpSonetIndex,
      lpSonetPathIndex }
::= { lpSonetPathOperTable 1 }

LpSonetPathOperEntry ::= SEQUENCE {
   lpSonetPathLopAlarm
      INTEGER,
   lpSonetPathRxAisAlarm
      INTEGER,
   lpSonetPathRxRfiAlarm
      INTEGER,
   lpSonetPathSignalLabelMismatch
      INTEGER,
   lpSonetPathTxAis
      INTEGER,
   lpSonetPathTxRdi
      INTEGER }

lpSonetPathLopAlarm OBJECT-TYPE
   SYNTAX     INTEGER  {
                 on(0),
                 off(1) }
   ACCESS     read-only
   STATUS     mandatory
   DESCRIPTION
     "This attribute displays whether a Loss Of Pointer (LOP) alarm state 
      has been entered. An LOP alarm state is entered when LOP defects 
      have been observed and accumulated for a period of 2.5 seconds +/- 
      0.5 seconds. An LOP defect occurs when no valid SPE or VC 
      pointer was received in 8 contiguous frames. If the LOP defects are 
      intermittently occurring, the LOP defect accumulator is 
      decremented at a rate of 1/10 of the incrementing rate (alarm 
      integration ratio of 1/10), with all measurements based on a 200 ms 
      polling cycle.
      The Path component goes into an operational state of disabled until 
      the LOP alarm condition is cleared. The condition is cleared when 
      no more invalid pointer has been reported for 10 seconds +/- 0.5 
      seconds.
      The lopAlarm attribute is always set to off when the Path 
      component has been locked and left offline by the operator or when 
      the Path component has been suspended since the parent component 
      has been locked."
::= { lpSonetPathOperEntry 1 }

lpSonetPathRxAisAlarm OBJECT-TYPE
   SYNTAX     INTEGER  {
                 on(0),
                 off(1) }
   ACCESS     read-only
   STATUS     mandatory
   DESCRIPTION
     "This attribute displays whether an Path Alarm Indication Signal (P-
      AIS) alarm state has been entered. An P-AIS alarm state is entered 
      when P-AIS defects have been observed and accumulated for a 
      period of 2.5 seconds +/- 0.5 seconds. The P-AIS defect is the 
      occurrence of the P-AIS signal in three contiguous valid STS or 
      STM frames (all one's in bytes H1 and H2). If the P-AIS defects are 
      intermittently occurring, the P-AIS defect accumulator is 
      decremented at a rate of 1/10 of the incrementing rate (alarm 
      integration ratio of 1/10), with all measurements based on a 200 ms 
      polling cycle.
      The Path component goes into an operational state of disabled until 
      the P-AIS alarm condition is cleared. The condition is cleared after 
      no P-AIS defect has been detected for 10 seconds +/- 0.5 seconds.
      The rxAisAlarm attribute is always set to off when the Path 
      component has been locked and left offline by the operator or when 
      the Path component has been suspended since the parent component 
      has been locked."
::= { lpSonetPathOperEntry 2 }

lpSonetPathRxRfiAlarm OBJECT-TYPE
   SYNTAX     INTEGER  {
                 on(0),
                 off(1) }
   ACCESS     read-only
   STATUS     mandatory
   DESCRIPTION
     "This attribute displays whether the Path Remote Failure Indication 
      (P-RFI) alarm state has been entered. An P-RFI alarm state is 
      entered when Path Remote Defect Indicator (P-RDI) defects have 
      been observed and accumulated for a period of 2.5 seconds +/- 0.5 
      seconds. The P-RDI defect is the occurrence of the P-RDI signal in 
      five contiguous valid STS or STM frames (bit 5 of the G1 byte set 
      to 1). If the P-RDI defects are intermittently occurring, the P-RDI 
      defect accumulator is decremented at a rate of 1/10 of the 
      incrementing rate (alarm integration ratio of 1/10)with all 
      measurements based on a 200 ms polling cycle.
      The Path component goes into an operational state of disabled until 
      the P-RFI alarm condition is cleared. The condition is cleared after 
      no P-RDI defect has been detected for 10 seconds +/- 0.5 seconds.
      The rxRfiAlarm attribute is always set to off when the Path 
      component has been locked and left offline by the operator or when 
      the Path component has been suspended since the parent component 
      has been locked."
::= { lpSonetPathOperEntry 3 }

lpSonetPathSignalLabelMismatch OBJECT-TYPE
   SYNTAX     INTEGER  {
                 on(0),
                 off(1) }
   ACCESS     read-only
   STATUS     mandatory
   DESCRIPTION
     "This attribute displays whether the Path Signal Label Mismatch (P-
      SLM) failure condition has been entered. An P-SLM failure 
      condition is entered when P-SLM defects have been observed and 
      accumulated for period of 2.5 seconds +/- 0.5 seconds. An P-SLM 
      defect occurs when detecting an unexpected path signal label. The 
      expected Path signal labels are 'Mapping for ATM' or 'Equipped - 
      Non Specific Payload'. If the P-SLM defects are intermittently 
      occurring, the P-SLM defect accumulator is decremented at a rate 
      of 1/10 of the incrementing rate (alarm integration ratio of 1/10), 
      with all measurements based on a 200 ms polling cycle.
      The Path component goes into an operational state of disabled until 
      the Path Signal Label Mismatch failure condition is cleared. The 
      condition is cleared when an expected path signal label is received 
      for 10 seconds +/- 0.5 seconds.
      The signalLabelMismatch attribute is always set to off when the 
      Path component has been locked and left offline by the operator or 
      when the Path component has been suspended since the parent 
      component has been locked."
::= { lpSonetPathOperEntry 4 }

lpSonetPathTxAis OBJECT-TYPE
   SYNTAX     INTEGER  {
                 on(0),
                 off(1) }
   ACCESS     read-only
   STATUS     mandatory
   DESCRIPTION
     "This attribute displays whether the Path Alarm Indication Signal (P-
      AIS) signal is being transmitted on the path. The P-AIS signal is 
      transmitted when the Path component has been locked and left 
      offline by the operator or when the Path component has been 
      suspended since the parent component has been locked."
::= { lpSonetPathOperEntry 5 }

lpSonetPathTxRdi OBJECT-TYPE
   SYNTAX     INTEGER  {
                 on(0),
                 off(1) }
   ACCESS     read-only
   STATUS     mandatory
   DESCRIPTION
     "This attribute displays whether the Path Remote Defect Indicator 
      (P-RDI) signal is being transmitted over the path signal. The P-RDI 
      signal is transmitted over the outgoing line upon detection of LOP, 
      P-AIS or the occurrence of the LCD state. This attribute is always 
      set to off when the Path component has been locked and left offline 
      by the operator or when the Path component has been suspended 
      since the parent component has been locked."
::= { lpSonetPathOperEntry 6 }

lpSonetPathStatsTable OBJECT-TYPE
   SYNTAX     SEQUENCE OF LpSonetPathStatsEntry
   ACCESS     not-accessible
   STATUS     mandatory
   DESCRIPTION
     "This group contains the statistics data for a Sonet/Sdh Path 
      component. Each attribute type is a non-negative integer which 
      monotonically increases until it reaches a maximum value, at which 
      point it wraps around and starts increasing again from zero."
::= { lpSonetPath 16 }

lpSonetPathStatsEntry OBJECT-TYPE
   SYNTAX     LpSonetPathStatsEntry
   ACCESS     not-accessible
   STATUS     mandatory
   DESCRIPTION
     "An entry in the lpSonetPathStatsTable."
   INDEX {
      lpIndex,
      lpSonetIndex,
      lpSonetPathIndex }
::= { lpSonetPathStatsTable 1 }

LpSonetPathStatsEntry ::= SEQUENCE {
   lpSonetPathPathErrorFreeSec
      Counter32,
   lpSonetPathPathCodeViolations
      Counter32,
   lpSonetPathPathErroredSec
      Counter32,
   lpSonetPathPathSevErroredSec
      Counter32,
   lpSonetPathPathAisLopSec
      Counter32,
   lpSonetPathPathUnavailSec
      Counter32,
   lpSonetPathPathFailures
      Counter32,
   lpSonetPathFarEndPathErrorFreeSec
      Counter32,
   lpSonetPathFarEndPathCodeViolations
      Counter32,
   lpSonetPathFarEndPathErroredSec
      Counter32,
   lpSonetPathFarEndPathSevErroredSec
      Counter32,
   lpSonetPathFarEndPathAisLopSec
      Counter32,
   lpSonetPathFarEndPathUnavailSec
      Counter32,
   lpSonetPathFarEndPathFailures
      Counter32 }

lpSonetPathPathErrorFreeSec OBJECT-TYPE
   SYNTAX     Counter32 
   ACCESS     read-only
   STATUS     mandatory
   DESCRIPTION
     "This attribute indicates the number of seconds that the Sonet/Sdh 
      Path component has been in an near-end error free state."
::= { lpSonetPathStatsEntry 1 }

lpSonetPathPathCodeViolations OBJECT-TYPE
   SYNTAX     Counter32 
   ACCESS     read-only
   STATUS     mandatory
   DESCRIPTION
     "This attribute indicates the total number of Path Code Violations 
      (PCVs) detected. Each PCV corresponds to a path BIP-8 error. PCV 
      counting is inhibited over second intervals where a Path Severely 
      Errored Second (PSES) is counted. Counting of PCVs is also 
      inhibited over second intervals where a Path Unavailable Second 
      (PUAS) is counted. The count wraps at its maximum value."
::= { lpSonetPathStatsEntry 2 }

lpSonetPathPathErroredSec OBJECT-TYPE
   SYNTAX     Counter32 
   ACCESS     read-only
   STATUS     mandatory
   DESCRIPTION
     "This attribute indicates the total number of Path Errored Seconds 
      (PESs) that have been counted. A PES is declared for second 
      intervals containing one or more PCVs or one or more LOP or path 
      AIS defects. Counting of PES is inhibited when PUAS is counted 
      over the monitored second."
::= { lpSonetPathStatsEntry 3 }

lpSonetPathPathSevErroredSec OBJECT-TYPE
   SYNTAX     Counter32 
   ACCESS     read-only
   STATUS     mandatory
   DESCRIPTION
     "This attribute indicates the total number of Path Severely Errored 
      Seconds (PSESs) that have been counted. A PSES is declared for 
      second intervals containing more than x PCVs or one or more LOP 
      or path AIS defects. The value of x is 2400 for a 155 Mbits/sec 
      interface. Counting of PSES is inhibited when PUAS is counted 
      over the monitored second."
::= { lpSonetPathStatsEntry 4 }

lpSonetPathPathAisLopSec OBJECT-TYPE
   SYNTAX     Counter32 
   ACCESS     read-only
   STATUS     mandatory
   DESCRIPTION
     "This attribute indicates the total number of path AIS and LOP 
      Seconds (PALSs). A PALS is declared for second intervals 
      containing one or more path AIS or LOP defects. Counting of PALS 
      is inhibited when PUAS is counted over the monitored second."
::= { lpSonetPathStatsEntry 5 }

lpSonetPathPathUnavailSec OBJECT-TYPE
   SYNTAX     Counter32 
   ACCESS     read-only
   STATUS     mandatory
   DESCRIPTION
     "This attribute indicates the total number of one second intervals for 
      which the STS/STM path is unavailable. The path becomes 
      unavailable at the onset of 10 consecutive PSESs. The 10 PSESs are 
      included in the unavailable time. Once unavailable, the path 
      becomes available at the onset of 10 contiguous seconds with no 
      PSES. The 10 seconds with no PSES are excluded from the 
      unavailable time. For second intervals where a Path Unavailable 
      Second (PUAS) is counted, counting of PCV, PES, PSES and PALS 
      is inhibited."
::= { lpSonetPathStatsEntry 6 }

lpSonetPathPathFailures OBJECT-TYPE
   SYNTAX     Counter32 
   ACCESS     read-only
   STATUS     mandatory
   DESCRIPTION
     "This attribute indicates the total number of times that a path failure 
      (LOP, P-AIS or Path Signal Label Mismatch failure) has been 
      declared."
::= { lpSonetPathStatsEntry 7 }

lpSonetPathFarEndPathErrorFreeSec OBJECT-TYPE
   SYNTAX     Counter32 
   ACCESS     read-only
   STATUS     mandatory
   DESCRIPTION
     "This attribute indicates the number of seconds that the Sonet/Sdh 
      Path component has been in an far-end error free state."
::= { lpSonetPathStatsEntry 8 }

lpSonetPathFarEndPathCodeViolations OBJECT-TYPE
   SYNTAX     Counter32 
   ACCESS     read-only
   STATUS     mandatory
   DESCRIPTION
     "This attribute indicates the total number of Far-End Path Code 
      Violations (FEPCVs) detected. Each FEPCV corresponds to a path 
      FEBE. FEPCV counting is inhibited over second intervals where a 
      Far-End Path Severely Errored Second (FEPSES) is counted. 
      Counting of PCVs is also inhibited over second intervals where a 
      Far-End Path Unavailable Second (FEPUAS) is counted. The count 
      wraps at its maximum value."
::= { lpSonetPathStatsEntry 9 }

lpSonetPathFarEndPathErroredSec OBJECT-TYPE
   SYNTAX     Counter32 
   ACCESS     read-only
   STATUS     mandatory
   DESCRIPTION
     "This attribute indicates the total number of Far-End Path Errored 
      Seconds (FEPESs) that have been counted. A FEPES is declared for 
      second intervals containing one or more FEPCVs or one or more 
      path RDI (P-RDI) defects. Counting of FEPES is inhibited when 
      FEPUAS is counted over the monitored second."
::= { lpSonetPathStatsEntry 10 }

lpSonetPathFarEndPathSevErroredSec OBJECT-TYPE
   SYNTAX     Counter32 
   ACCESS     read-only
   STATUS     mandatory
   DESCRIPTION
     "This attribute indicates the total number of Far-End Path Severely 
      Errored Seconds (FEPSESs) that have been counted. A FEPSES is 
      declared for second intervals containing more than x FEPCVs or 
      one or more P-RDI defects. The value of x is 2400 for a 155 Mbits/
      sec interface. Counting of FEPSESs is inhibited when FEPUAS is 
      counted over the monitored second."
::= { lpSonetPathStatsEntry 11 }

lpSonetPathFarEndPathAisLopSec OBJECT-TYPE
   SYNTAX     Counter32 
   ACCESS     read-only
   STATUS     mandatory
   DESCRIPTION
     "This attribute indicates the total number of Far-End Path AIS and 
      LOP Seconds (FEPALSs). A FEPALS is declared for second 
      intervals containing one or more P-RDI defects. Counting of 
      FEPALS is inhibited when FEPUAS is counted over the monitored 
      second."
::= { lpSonetPathStatsEntry 12 }

lpSonetPathFarEndPathUnavailSec OBJECT-TYPE
   SYNTAX     Counter32 
   ACCESS     read-only
   STATUS     mandatory
   DESCRIPTION
     "This attribute indicates the total number of one second intervals for 
      which the STS/STM far-end path is unavailable. The far-end path 
      becomes unavailable at the onset of 10 consecutive FEPSESs. The 
      10 FEPSESs are included in the unavailable time. Once unavailable, 
      the far-end path becomes available at the onset of 10 contiguous 
      seconds with no FEPSES. The 10 seconds with no FEPSES are 
      excluded from the unavailable time. For second intervals where a 
      Far-End Path Unavailable Second (FEPUAS) is counted, counting 
      of FEPCV, FEPES, FEPSES and FEPALS is inhibited."
::= { lpSonetPathStatsEntry 13 }

lpSonetPathFarEndPathFailures OBJECT-TYPE
   SYNTAX     Counter32 
   ACCESS     read-only
   STATUS     mandatory
   DESCRIPTION
     "This attribute indicates the total number of times that a STS/STM 
      far-end path failure (P-RFI failure) has been declared."
::= { lpSonetPathStatsEntry 14 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

lpSonetPathCell OBJECT IDENTIFIER ::= { lpSonetPath 2 }



lpSonetPathCellRowStatusTable OBJECT-TYPE
   SYNTAX     SEQUENCE OF LpSonetPathCellRowStatusEntry
   ACCESS     not-accessible
   STATUS     mandatory
   DESCRIPTION
     "This entry controls the addition and deletion of 
      lpSonetPathCell components."
::= { lpSonetPathCell 1 }

lpSonetPathCellRowStatusEntry OBJECT-TYPE
   SYNTAX     LpSonetPathCellRowStatusEntry
   ACCESS     not-accessible
   STATUS     mandatory
   DESCRIPTION
     "A single entry in the table represents a single 
      lpSonetPathCell component."
   INDEX {
      lpIndex,
      lpSonetIndex,
      lpSonetPathIndex,
      lpSonetPathCellIndex }
::= { lpSonetPathCellRowStatusTable 1 }

LpSonetPathCellRowStatusEntry ::= SEQUENCE {
   lpSonetPathCellRowStatus
      RowStatus,
   lpSonetPathCellComponentName
      DisplayString,
   lpSonetPathCellStorageType
      StorageType,
   lpSonetPathCellIndex
      NonReplicated }

lpSonetPathCellRowStatus OBJECT-TYPE
   SYNTAX     RowStatus 
   ACCESS     read-only
   STATUS     mandatory
   DESCRIPTION
     "This variable is used as the basis for SNMP naming of
      lpSonetPathCell components.
      These components cannot be added nor deleted."
::= { lpSonetPathCellRowStatusEntry 1 }

lpSonetPathCellComponentName OBJECT-TYPE
   SYNTAX     DisplayString 
   ACCESS     read-only
   STATUS     mandatory
   DESCRIPTION
     "This variable provides the component's string name for
      use with the ASCII Console Interface"
::= { lpSonetPathCellRowStatusEntry 2 }

lpSonetPathCellStorageType OBJECT-TYPE
   SYNTAX     StorageType 
   ACCESS     read-only
   STATUS     mandatory
   DESCRIPTION
     "This variable represents the storage type value for the
      lpSonetPathCell tables."
::= { lpSonetPathCellRowStatusEntry 4 }

lpSonetPathCellIndex OBJECT-TYPE
   SYNTAX     NonReplicated 
   ACCESS     not-accessible
   STATUS     mandatory
   DESCRIPTION
     "This variable represents the index for the lpSonetPathCell tables."
::= { lpSonetPathCellRowStatusEntry 10 }

lpSonetPathCellProvTable OBJECT-TYPE
   SYNTAX     SEQUENCE OF LpSonetPathCellProvEntry
   ACCESS     not-accessible
   STATUS     mandatory
   DESCRIPTION
     "This group contains the provisioning attributes for the AtmCell 
      component."
::= { lpSonetPathCell 10 }

lpSonetPathCellProvEntry OBJECT-TYPE
   SYNTAX     LpSonetPathCellProvEntry
   ACCESS     not-accessible
   STATUS     mandatory
   DESCRIPTION
     "An entry in the lpSonetPathCellProvTable."
   INDEX {
      lpIndex,
      lpSonetIndex,
      lpSonetPathIndex,
      lpSonetPathCellIndex }
::= { lpSonetPathCellProvTable 1 }

LpSonetPathCellProvEntry ::= SEQUENCE {
   lpSonetPathCellAlarmActDelay
      Unsigned32,
   lpSonetPathCellScrambleCellPayload
      INTEGER,
   lpSonetPathCellCorrectSingleBitHeaderErrors
      INTEGER }

lpSonetPathCellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { lpSonetPathCellProvEntry 1 }

lpSonetPathCellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { lpSonetPathCellProvEntry 2 }

lpSonetPathCellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { lpSonetPathCellProvEntry 3 }

lpSonetPathCellOperTable OBJECT-TYPE
   SYNTAX     SEQUENCE OF LpSonetPathCellOperEntry
   ACCESS     not-accessible
   STATUS     mandatory
   DESCRIPTION
     "This group contains the common operational attributes for the 
      AtmCell component."
::= { lpSonetPathCell 11 }

lpSonetPathCellOperEntry OBJECT-TYPE
   SYNTAX     LpSonetPathCellOperEntry
   ACCESS     not-accessible
   STATUS     mandatory
   DESCRIPTION
     "An entry in the lpSonetPathCellOperTable."
   INDEX {
      lpIndex,
      lpSonetIndex,
      lpSonetPathIndex,
      lpSonetPathCellIndex }
::= { lpSonetPathCellOperTable 1 }

LpSonetPathCellOperEntry ::= SEQUENCE {
   lpSonetPathCellLcdAlarm
      INTEGER }

lpSonetPathCellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { lpSonetPathCellOperEntry 1 }

lpSonetPathCellStatsTable OBJECT-TYPE
   SYNTAX     SEQUENCE OF LpSonetPathCellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { lpSonetPathCell 12 }

lpSonetPathCellStatsEntry OBJECT-TYPE
   SYNTAX     LpSonetPathCellStatsEntry
   ACCESS     not-accessible
   STATUS     mandatory
   DESCRIPTION
     "An entry in the lpSonetPathCellStatsTable."
   INDEX {
      lpIndex,
      lpSonetIndex,
      lpSonetPathIndex,
      lpSonetPathCellIndex }
::= { lpSonetPathCellStatsTable 1 }

LpSonetPathCellStatsEntry ::= SEQUENCE {
   lpSonetPathCellUncorrectableHecErrors
      Counter32,
   lpSonetPathCellSevErroredSec
      Counter32,
   lpSonetPathCellReceiveCellUtilization
      Gauge32,
   lpSonetPathCellTransmitCellUtilization
      Gauge32,
   lpSonetPathCellCorrectableHeaderErrors
      Counter32 }

lpSonetPathCellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { lpSonetPathCellStatsEntry 1 }

lpSonetPathCellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { lpSonetPathCellStatsEntry 2 }

lpSonetPathCellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { lpSonetPathCellStatsEntry 3 }

lpSonetPathCellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { lpSonetPathCellStatsEntry 4 }

lpSonetPathCellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { lpSonetPathCellStatsEntry 5 }


-- 
-- The Test component is configured to control a hardware facility test 
-- on a physical (V35, X21, DS1, E1, DS3, E3 etc.) or a logical port.

lpSonetTest OBJECT IDENTIFIER ::= { lpSonet 3 }



lpSonetTestRowStatusTable OBJECT-TYPE
   SYNTAX     SEQUENCE OF LpSonetTestRowStatusEntry
   ACCESS     not-accessible
   STATUS     mandatory
   DESCRIPTION
     "This entry controls the addition and deletion of 
      lpSonetTest components."
::= { lpSonetTest 1 }

lpSonetTestRowStatusEntry OBJECT-TYPE
   SYNTAX     LpSonetTestRowStatusEntry
   ACCESS     not-accessible
   STATUS     mandatory
   DESCRIPTION
     "A single entry in the table represents a single 
      lpSonetTest component."
   INDEX {
      lpIndex,
      lpSonetIndex,
      lpSonetTestIndex }
::= { lpSonetTestRowStatusTable 1 }

LpSonetTestRowStatusEntry ::= SEQUENCE {
   lpSonetTestRowStatus
      RowStatus,
   lpSonetTestComponentName
      DisplayString,
   lpSonetTestStorageType
      StorageType,
   lpSonetTestIndex
      NonReplicated }

lpSonetTestRowStatus OBJECT-TYPE
   SYNTAX     RowStatus 
   ACCESS     read-only
   STATUS     mandatory
   DESCRIPTION
     "This variable is used as the basis for SNMP naming of
      lpSonetTest components.
      These components cannot be added nor deleted."
::= { lpSonetTestRowStatusEntry 1 }

lpSonetTestComponentName OBJECT-TYPE
   SYNTAX     DisplayString 
   ACCESS     read-only
   STATUS     mandatory
   DESCRIPTION
     "This variable provides the component's string name for
      use with the ASCII Console Interface"
::= { lpSonetTestRowStatusEntry 2 }

lpSonetTestStorageType OBJECT-TYPE
   SYNTAX     StorageType 
   ACCESS     read-only
   STATUS     mandatory
   DESCRIPTION
     "This variable represents the storage type value for the
      lpSonetTest tables."
::= { lpSonetTestRowStatusEntry 4 }

lpSonetTestIndex OBJECT-TYPE
   SYNTAX     NonReplicated 
   ACCESS     not-accessible
   STATUS     mandatory
   DESCRIPTION
     "This variable represents the index for the lpSonetTest tables."
::= { lpSonetTestRowStatusEntry 10 }

lpSonetTestStateTable OBJECT-TYPE
   SYNTAX     SEQUENCE OF LpSonetTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpSonetTest 10 }

lpSonetTestStateEntry OBJECT-TYPE
   SYNTAX     LpSonetTestStateEntry
   ACCESS     not-accessible
   STATUS     mandatory
   DESCRIPTION
     "An entry in the lpSonetTestStateTable."
   INDEX {
      lpIndex,
      lpSonetIndex,
      lpSonetTestIndex }
::= { lpSonetTestStateTable 1 }

LpSonetTestStateEntry ::= SEQUENCE {
   lpSonetTestAdminState
      INTEGER,
   lpSonetTestOperationalState
      INTEGER,
   lpSonetTestUsageState
      INTEGER }

lpSonetTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpSonetTestStateEntry 1 }

lpSonetTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpSonetTestStateEntry 2 }

lpSonetTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpSonetTestStateEntry 3 }

lpSonetTestSetupTable OBJECT-TYPE
   SYNTAX     SEQUENCE OF LpSonetTestSetupEntry
   ACCESS     not-accessible
   STATUS     mandatory
   DESCRIPTION
     "This group contains all of the operational data for a Test 
      component."
::= { lpSonetTest 11 }

lpSonetTestSetupEntry OBJECT-TYPE
   SYNTAX     LpSonetTestSetupEntry
   ACCESS     not-accessible
   STATUS     mandatory
   DESCRIPTION
     "An entry in the lpSonetTestSetupTable."
   INDEX {
      lpIndex,
      lpSonetIndex,
      lpSonetTestIndex }
::= { lpSonetTestSetupTable 1 }

LpSonetTestSetupEntry ::= SEQUENCE {
   lpSonetTestPurpose
      AsciiString,
   lpSonetTestType
      INTEGER,
   lpSonetTestFrmSize
      Unsigned32,
   lpSonetTestFrmPatternType
      INTEGER,
   lpSonetTestCustomizedPattern
      Hex,
   lpSonetTestDataStartDelay
      Unsigned32,
   lpSonetTestDisplayInterval
      Unsigned32,
   lpSonetTestDuration
      Unsigned32 }

lpSonetTestPurpose OBJECT-TYPE
   SYNTAX     AsciiString (SIZE (0..40))
   ACCESS     read-write
   STATUS     mandatory
   DESCRIPTION
     "This attribute records the purpose of the test so that the test results 
      can be associated and properly analyzed."
::= { lpSonetTestSetupEntry 1 }

lpSonetTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpSonetTestSetupEntry 2 }

lpSonetTestFrmSize OBJECT-TYPE
   SYNTAX     Unsigned32 (4..4096)
   ACCESS     read-write
   STATUS     mandatory
   DESCRIPTION
     "This attribute defines the size of the test data frames in number of 
      bytes."
   DEFVAL     { 1024 }
::= { lpSonetTestSetupEntry 3 }

lpSonetTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpSonetTestSetupEntry 4 }

lpSonetTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpSonetTestSetupEntry 5 }

lpSonetTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpSonetTestSetupEntry 6 }

lpSonetTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpSonetTestSetupEntry 7 }

lpSonetTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpSonetTestSetupEntry 8 }

lpSonetTestResultsTable OBJECT-TYPE
   SYNTAX     SEQUENCE OF LpSonetTestResultsEntry
   ACCESS     not-accessible
   STATUS     mandatory
   DESCRIPTION
     "This group contains all the statistics related attributes of the Test 
      component."
::= { lpSonetTest 12 }

lpSonetTestResultsEntry OBJECT-TYPE
   SYNTAX     LpSonetTestResultsEntry
   ACCESS     not-accessible
   STATUS     mandatory
   DESCRIPTION
     "An entry in the lpSonetTestResultsTable."
   INDEX {
      lpIndex,
      lpSonetIndex,
      lpSonetTestIndex }
::= { lpSonetTestResultsTable 1 }

LpSonetTestResultsEntry ::= SEQUENCE {
   lpSonetTestElapsedTime
      Counter32,
   lpSonetTestTimeRemaining
      Unsigned32,
   lpSonetTestCauseOfTermination
      INTEGER,
   lpSonetTestBitsTx
      PassportCounter64,
   lpSonetTestBytesTx
      PassportCounter64,
   lpSonetTestFrmTx
      PassportCounter64,
   lpSonetTestBitsRx
      PassportCounter64,
   lpSonetTestBytesRx
      PassportCounter64,
   lpSonetTestFrmRx
      PassportCounter64,
   lpSonetTestErroredFrmRx
      PassportCounter64,
   lpSonetTestBitErrorRate
      AsciiString }

lpSonetTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpSonetTestResultsEntry 1 }

lpSonetTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpSonetTestResultsEntry 2 }

lpSonetTestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpSonetTestResultsEntry 3 }

lpSonetTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpSonetTestResultsEntry 4 }

lpSonetTestBytesTx OBJECT-TYPE
   SYNTAX     PassportCounter64 
   ACCESS     read-only
   STATUS     mandatory
   DESCRIPTION
     "This attribute is the total number of bytes sent during the test 
      period. This counter is not expected to reach its maximum value."
::= { lpSonetTestResultsEntry 5 }

lpSonetTestFrmTx OBJECT-TYPE
   SYNTAX     PassportCounter64 
   ACCESS     read-only
   STATUS     mandatory
   DESCRIPTION
     "This attribute is the total number of frames sent during the test 
      period. This counter is not expected to reach its maximum value."
::= { lpSonetTestResultsEntry 6 }

lpSonetTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpSonetTestResultsEntry 7 }

lpSonetTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpSonetTestResultsEntry 8 }

lpSonetTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpSonetTestResultsEntry 9 }

lpSonetTestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpSonetTestResultsEntry 10 }

lpSonetTestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpSonetTestResultsEntry 11 }


-- Sdh
-- The Lp/m Sdh/n component controls an OC-3 port on an OC-3 
-- Function Processor. In particular, it deals with SDH medium, 
-- section and line layers.
-- Note that there can be Sonet and Sdh components coexisting under 
-- the same LP. However they cannot use the same instance.

lpSdh OBJECT IDENTIFIER ::= { lp 15 }



lpSdhRowStatusTable OBJECT-TYPE
   SYNTAX     SEQUENCE OF LpSdhRowStatusEntry
   ACCESS     not-accessible
   STATUS     mandatory
   DESCRIPTION
     "This entry controls the addition and deletion of 
      lpSdh components."
::= { lpSdh 1 }

lpSdhRowStatusEntry OBJECT-TYPE
   SYNTAX     LpSdhRowStatusEntry
   ACCESS     not-accessible
   STATUS     mandatory
   DESCRIPTION
     "A single entry in the table represents a single 
      lpSdh component."
   INDEX {
      lpIndex,
      lpSdhIndex }
::= { lpSdhRowStatusTable 1 }

LpSdhRowStatusEntry ::= SEQUENCE {
   lpSdhRowStatus
      RowStatus,
   lpSdhComponentName
      DisplayString,
   lpSdhStorageType
      StorageType,
   lpSdhIndex
      Integer32 }

lpSdhRowStatus OBJECT-TYPE
   SYNTAX     RowStatus 
   ACCESS     read-write
   STATUS     mandatory
   DESCRIPTION
     "This variable is used as the basis for SNMP naming of
      lpSdh components.
      These components can be added and deleted."
::= { lpSdhRowStatusEntry 1 }

lpSdhComponentName OBJECT-TYPE
   SYNTAX     DisplayString 
   ACCESS     read-only
   STATUS     mandatory
   DESCRIPTION
     "This variable provides the component's string name for
      use with the ASCII Console Interface"
::= { lpSdhRowStatusEntry 2 }

lpSdhStorageType OBJECT-TYPE
   SYNTAX     StorageType 
   ACCESS     read-only
   STATUS     mandatory
   DESCRIPTION
     "This variable represents the storage type value for the
      lpSdh tables."
::= { lpSdhRowStatusEntry 4 }

lpSdhIndex OBJECT-TYPE
   SYNTAX     Integer32 (0..2)
   ACCESS     not-accessible
   STATUS     mandatory
   DESCRIPTION
     "This variable represents the index for the lpSdh tables."
::= { lpSdhRowStatusEntry 10 }

lpSdhProvTable OBJECT-TYPE
   SYNTAX     SEQUENCE OF LpSdhProvEntry
   ACCESS     not-accessible
   STATUS     mandatory
   DESCRIPTION
     "This group contains all of the provisioning data for a Sonet or Sdh 
      component."
::= { lpSdh 10 }

lpSdhProvEntry OBJECT-TYPE
   SYNTAX     LpSdhProvEntry
   ACCESS     not-accessible
   STATUS     mandatory
   DESCRIPTION
     "An entry in the lpSdhProvTable."
   INDEX {
      lpIndex,
      lpSdhIndex }
::= { lpSdhProvTable 1 }

LpSdhProvEntry ::= SEQUENCE {
   lpSdhClockingSource
      INTEGER }

lpSdhClockingSource OBJECT-TYPE
   SYNTAX     INTEGER  {
                 local(0),
                 line(1),
                 module(2) }
   ACCESS     read-write
   STATUS     mandatory
   DESCRIPTION
     "This attribute defines the type of clocking source used for 
      synchronizing the OC-3 transmit clock: local means direct use of 
      the local clock oscillator at its centre frequency; line means the use 
      of a signal phase-locked to the incoming OC-3 line rate; module 
      means the use of a signal phase-locked to the CP reference clock. 
      When adding a Sonet/Sdh component, the clockingSource attribute 
      is set to module if the NetworkSynchronization component has 
      been added and is set to local otherwise.
      Note that the multiport OC-3 cell-based cards has one common 
      clock source for each of the three ports when either the clocking 
      source local or module is selected. For this reason, it is not allowed 
      to have at the same time the clockingSource attribute set to local on 
      one port and module on another port. Furthermore, the 
      clockingSource attribute cannot be set to module if the 
      NetworkSynchronization component has not been added."
::= { lpSdhProvEntry 1 }

lpSdhCidDataTable OBJECT-TYPE
   SYNTAX     SEQUENCE OF LpSdhCidDataEntry
   ACCESS     not-accessible
   STATUS     mandatory
   DESCRIPTION
     "This group contains the attribute for a component's Customer 
      Identifier (CID). Refer to the attribute description for a detailed 
      explanation of CIDs."
::= { lpSdh 11 }

lpSdhCidDataEntry OBJECT-TYPE
   SYNTAX     LpSdhCidDataEntry
   ACCESS     not-accessible
   STATUS     mandatory
   DESCRIPTION
     "An entry in the lpSdhCidDataTable."
   INDEX {
      lpIndex,
      lpSdhIndex }
::= { lpSdhCidDataTable 1 }

LpSdhCidDataEntry ::= SEQUENCE {
   lpSdhCustomerIdentifier
      Unsigned32 }

lpSdhCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpSdhCidDataEntry 1 }

lpSdhAdminInfoTable OBJECT-TYPE
   SYNTAX     SEQUENCE OF LpSdhAdminInfoEntry
   ACCESS     not-accessible
   STATUS     mandatory
   DESCRIPTION
     "This group contains the attributes pertaining to the vendor of the 
      equipment."
::= { lpSdh 12 }

lpSdhAdminInfoEntry OBJECT-TYPE
   SYNTAX     LpSdhAdminInfoEntry
   ACCESS     not-accessible
   STATUS     mandatory
   DESCRIPTION
     "An entry in the lpSdhAdminInfoTable."
   INDEX {
      lpIndex,
      lpSdhIndex }
::= { lpSdhAdminInfoTable 1 }

LpSdhAdminInfoEntry ::= SEQUENCE {
   lpSdhVendor
      AsciiString,
   lpSdhCommentText
      AsciiString }

lpSdhVendor OBJECT-TYPE
   SYNTAX     AsciiString (SIZE (0..20))
   ACCESS     read-write
   STATUS     mandatory
   DESCRIPTION
     "This is the name of the vendor supplying the facility."
::= { lpSdhAdminInfoEntry 1 }

lpSdhCommentText OBJECT-TYPE
   SYNTAX     AsciiString (SIZE (0..60))
   ACCESS     read-write
   STATUS     mandatory
   DESCRIPTION
     "Any miscellaneous text about the facility."
::= { lpSdhAdminInfoEntry 2 }

lpSdhIfEntryTable OBJECT-TYPE
   SYNTAX     SEQUENCE OF LpSdhIfEntryEntry
   ACCESS     not-accessible
   STATUS     mandatory
   DESCRIPTION
     "This group contains the provisionable attributes for the ifEntry."
::= { lpSdh 13 }

lpSdhIfEntryEntry OBJECT-TYPE
   SYNTAX     LpSdhIfEntryEntry
   ACCESS     not-accessible
   STATUS     mandatory
   DESCRIPTION
     "An entry in the lpSdhIfEntryTable."
   INDEX {
      lpIndex,
      lpSdhIndex }
::= { lpSdhIfEntryTable 1 }

LpSdhIfEntryEntry ::= SEQUENCE {
   lpSdhIfAdminStatus
      INTEGER,
   lpSdhIfIndex
      InterfaceIndex }

lpSdhIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpSdhIfEntryEntry 1 }

lpSdhIfIndex OBJECT-TYPE
   SYNTAX     InterfaceIndex (1..65535)
   ACCESS     read-only
   STATUS     mandatory
   DESCRIPTION
     "This is the index for the IfEntry. Its value is automatically initialized 
      during the provisioning process."
::= { lpSdhIfEntryEntry 2 }

lpSdhOperStatusTable OBJECT-TYPE
   SYNTAX     SEQUENCE OF LpSdhOperStatusEntry
   ACCESS     not-accessible
   STATUS     mandatory
   DESCRIPTION
     "This group includes the Operational Status attribute. This attribute 
      defines the current operational state of this component."
::= { lpSdh 14 }

lpSdhOperStatusEntry OBJECT-TYPE
   SYNTAX     LpSdhOperStatusEntry
   ACCESS     not-accessible
   STATUS     mandatory
   DESCRIPTION
     "An entry in the lpSdhOperStatusTable."
   INDEX {
      lpIndex,
      lpSdhIndex }
::= { lpSdhOperStatusTable 1 }

LpSdhOperStatusEntry ::= SEQUENCE {
   lpSdhSnmpOperStatus
      INTEGER }

lpSdhSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpSdhOperStatusEntry 1 }

lpSdhStateTable OBJECT-TYPE
   SYNTAX     SEQUENCE OF LpSdhStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpSdh 15 }

lpSdhStateEntry OBJECT-TYPE
   SYNTAX     LpSdhStateEntry
   ACCESS     not-accessible
   STATUS     mandatory
   DESCRIPTION
     "An entry in the lpSdhStateTable."
   INDEX {
      lpIndex,
      lpSdhIndex }
::= { lpSdhStateTable 1 }

LpSdhStateEntry ::= SEQUENCE {
   lpSdhAdminState
      INTEGER,
   lpSdhOperationalState
      INTEGER,
   lpSdhUsageState
      INTEGER,
   lpSdhAvailabilityStatus
      OCTET STRING,
   lpSdhProceduralStatus
      OCTET STRING,
   lpSdhControlStatus
      OCTET STRING,
   lpSdhAlarmStatus
      OCTET STRING,
   lpSdhStandbyStatus
      INTEGER,
   lpSdhUnknownStatus
      INTEGER }

lpSdhAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpSdhStateEntry 1 }

lpSdhOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpSdhStateEntry 2 }

lpSdhUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpSdhStateEntry 3 }

lpSdhAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpSdhStateEntry 4 }

lpSdhProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpSdhStateEntry 5 }

lpSdhControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpSdhStateEntry 6 }

lpSdhAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpSdhStateEntry 7 }

lpSdhStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpSdhStateEntry 8 }

lpSdhUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpSdhStateEntry 9 }

lpSdhOperTable OBJECT-TYPE
   SYNTAX     SEQUENCE OF LpSdhOperEntry
   ACCESS     not-accessible
   STATUS     mandatory
   DESCRIPTION
     "This group contains the common operational data for Sonet or Sdh 
      component."
::= { lpSdh 16 }

lpSdhOperEntry OBJECT-TYPE
   SYNTAX     LpSdhOperEntry
   ACCESS     not-accessible
   STATUS     mandatory
   DESCRIPTION
     "An entry in the lpSdhOperTable."
   INDEX {
      lpIndex,
      lpSdhIndex }
::= { lpSdhOperTable 1 }

LpSdhOperEntry ::= SEQUENCE {
   lpSdhLosAlarm
      INTEGER,
   lpSdhLofAlarm
      INTEGER,
   lpSdhRxAisAlarm
      INTEGER,
   lpSdhRxRfiAlarm
      INTEGER,
   lpSdhTxAis
      INTEGER,
   lpSdhTxRdi
      INTEGER,
   lpSdhUnusableTxClockRefAlarm
      INTEGER }

lpSdhLosAlarm OBJECT-TYPE
   SYNTAX     INTEGER  {
                 on(0),
                 off(1) }
   ACCESS     read-only
   STATUS     mandatory
   DESCRIPTION
     "This attribute indicates whether a Loss Of Signal (LOS) alarm state 
      has been entered. An LOS alarm state is entered when LOS defects 
      have been observed and accumulated for a period of 2.5 seconds +/- 
      0.5 seconds, or if an LOS defect is present when the criteria for 
      LOF failure declaration have been met. A LOS defect is declared 
      when 20+/-3 us of all-zeros pattern is detected. The LOS defect is 
      cleared when two valid framing words are detected and no Loss Of 
      Signal condition is detected during an interval of 20+/-3 us. If the 
      LOS defects are intermittently occurring, the LOS defect 
      accumulator is decremented at a rate of 1/10 of the incrementing 
      rate (alarm integration ratio of 1/10), with all measurements based 
      on a 200 ms polling cycle.
      The Sonet/Sdh component goes into an operational state of disabled 
      until the LOS alarm condition is cleared. The LOS alarm state is 
      cleared after LOS defects have been absent for a period of 10 
      seconds +/- 0.5 seconds.
      The losAlarm attribute is always set to off when the component has 
      been locked and left offline."
::= { lpSdhOperEntry 1 }

lpSdhLofAlarm OBJECT-TYPE
   SYNTAX     INTEGER  {
                 on(0),
                 off(1) }
   ACCESS     read-only
   STATUS     mandatory
   DESCRIPTION
     "This attribute displays whether a Loss Of Frame (LOF) alarm state 
      has been entered. An LOF alarm state is entered when LOF defects 
      have been observed and accumulated for a period of 2.5 seconds +/- 
      0.5 seconds, except when an LOS defect or failure is present. An 
      LOF defect is detected when getting contiguous errored frame 
      alignment for at least 3 msec. If the LOF defects are intermittently 
      occurring, the LOF defect accumulator is decremented at a rate of 
      1/10 of the incrementing rate (alarm integration ratio of 1/10), with 
      all measurements based on a 200 ms polling cycle.
      The Sonet/Sdh component goes into an operational state of disabled 
      until the LOF alarm condition is cleared. The condition is cleared 
      when framing has been achieved for a period of 10 seconds +/- 0.5 
      seconds.
      The lofAlarm attribute is always set to off when the component has 
      been locked and left offline."
::= { lpSdhOperEntry 2 }

lpSdhRxAisAlarm OBJECT-TYPE
   SYNTAX     INTEGER  {
                 on(0),
                 off(1) }
   ACCESS     read-only
   STATUS     mandatory
   DESCRIPTION
     "This attribute displays whether a Line Alarm Indication Signal (L-
      AIS) alarm state has been entered. An L-AIS alarm state is entered 
      when L-AIS defects have been observed and accumulated for a 
      period of 2.5 seconds +/- 0.5 seconds. The L-AIS defect is the 
      occurrence of the L-AIS signal in five contiguous STS (STM) 
      frames (111 pattern in bits 6,7, and 8 of the K2 bytes). If the L-AIS 
      defects are intermittently occurring, the L-AIS defect accumulator 
      is decremented at a rate of 1/10 of the incrementing rate (alarm 
      integration ratio of 1/10), with all measurements based on a 200 ms 
      polling cycle.
      The Sonet/Sdh component goes into an operational state of disabled 
      until the L-AIS alarm condition is cleared. The condition is cleared 
      after not detecting the L-AIS signal for a period of 10 seconds +/- 
      0.5 seconds.
      The rxAisAlarm attribute is always set to off when the component 
      has been locked and left offline."
::= { lpSdhOperEntry 3 }

lpSdhRxRfiAlarm OBJECT-TYPE
   SYNTAX     INTEGER  {
                 on(0),
                 off(1) }
   ACCESS     read-only
   STATUS     mandatory
   DESCRIPTION
     "This attribute displays whether a Line Remote Failure Indication 
      (LRFI) alarm state has been entered. An L-RFI alarm state is 
      entered when Line Remote Failure Indication (L-RDI) defects have 
      been observed and accumulated for a period of 2.5 seconds +/- 0.5 
      seconds. The L-RDI defect is the occurrence of the L-RDI signal in 
      five contiguous valid STS (STM) frame (110 pattern in bits 6,7, and 
      8 of the K2 bytes). If the L-RDI defects are intermittently occurring, 
      the L-RDI defect accumulator is decremented at a rate of 1/10 of 
      the incrementing rate (alarm integration ratio of 1/10), with all 
      measurements based on a 200 ms polling cycle.
      The Sonet/Sdh component goes into an operational state of disabled 
      until the L-RFI alarm condition is cleared. The condition is cleared 
      after not detecting the L-RDI signal for a period of 10 seconds +/- 
      0.5 seconds.
      The rxRfiAlarm attribute is always set to off when the component 
      has been locked and left offline."
::= { lpSdhOperEntry 4 }

lpSdhTxAis OBJECT-TYPE
   SYNTAX     INTEGER  {
                 on(0),
                 off(1) }
   ACCESS     read-only
   STATUS     mandatory
   DESCRIPTION
     "This attribute displays whether the Line Alarm Indication Signal (L-
      AIS) signal is being transmitted on the outgoing line. This signal is 
      transmitted when the Sonet/Sdh is locked and left offline."
::= { lpSdhOperEntry 5 }

lpSdhTxRdi OBJECT-TYPE
   SYNTAX     INTEGER  {
                 on(0),
                 off(1) }
   ACCESS     read-only
   STATUS     mandatory
   DESCRIPTION
     "This attribute displays whether the Line Remote Defect Indicator 
      (L-RDI) signal is being transmitted over the OC-3 line. The L-RDI 
      signal is transmitted upon the detection of the LOS, LOF or L-AIS 
      defect. This attribute is always set to off when the component has 
      been locked and left offline."
::= { lpSdhOperEntry 6 }

lpSdhUnusableTxClockRefAlarm OBJECT-TYPE
   SYNTAX     INTEGER  {
                 on(0),
                 off(1) }
   ACCESS     read-only
   STATUS     mandatory
   DESCRIPTION
     "This attribute displays whether an Unusable Transmit Clock 
      Reference (UTCR) alarm state has been entered. A UTCR alarm 
      state is entered when a Sonet/Sdh port provisioned to act as a 
      transmit clock reference has received the code 'do not use for 
      synchronization' in the S1 byte (in the SONET/ SDH line 
      overhead) for 2.5 +/- 0.5 seconds.
      The condition is cleared after not detecting the 'do not use for 
      synchronization' code for a period of 10 +/- 0.5 seconds or when 
      the port is no longer provisioned to act as a transmit clock 
      reference.
      A port is acting as a transmit clock reference if it is provisioned 
      with a) a clockingSource of line, or b) it has been provisioned as a 
      primaryReference, secondaryReference or tertiaryReference in the 
      NetworkSynchronization component.
      The unusableTxClockRefAlarm attribute is always set to off when 
      the component has been locked and left offline."
::= { lpSdhOperEntry 7 }

lpSdhStatsTable OBJECT-TYPE
   SYNTAX     SEQUENCE OF LpSdhStatsEntry
   ACCESS     not-accessible
   STATUS     mandatory
   DESCRIPTION
     "This group contains the statistics data for a Sonet or Sdh 
      component. Each attribute type is a non-negative integer which 
      monotonically increases until it reaches a maximum value, at which 
      point it wraps around and starts increasing again from zero."
::= { lpSdh 17 }

lpSdhStatsEntry OBJECT-TYPE
   SYNTAX     LpSdhStatsEntry
   ACCESS     not-accessible
   STATUS     mandatory
   DESCRIPTION
     "An entry in the lpSdhStatsTable."
   INDEX {
      lpIndex,
      lpSdhIndex }
::= { lpSdhStatsTable 1 }

LpSdhStatsEntry ::= SEQUENCE {
   lpSdhRunningTime
      Counter32,
   lpSdhErrorFreeSec
      Counter32,
   lpSdhSectCodeViolations
      Counter32,
   lpSdhSectErroredSec
      Counter32,
   lpSdhSectSevErroredSec
      Counter32,
   lpSdhSectLosSec
      Counter32,
   lpSdhSectSevErroredFrmSec
      Counter32,
   lpSdhSectFailures
      Counter32,
   lpSdhLineCodeViolations
      Counter32,
   lpSdhLineErroredSec
      Counter32,
   lpSdhLineSevErroredSec
      Counter32,
   lpSdhLineAisSec
      Counter32,
   lpSdhLineUnavailSec
      Counter32,
   lpSdhLineFailures
      Counter32,
   lpSdhFarEndLineErrorFreeSec
      Counter32,
   lpSdhFarEndLineCodeViolations
      Counter32,
   lpSdhFarEndLineErroredSec
      Counter32,
   lpSdhFarEndLineSevErroredSec
      Counter32,
   lpSdhFarEndLineAisSec
      Counter32,
   lpSdhFarEndLineUnavailSec
      Counter32,
   lpSdhFarEndLineFailures
      Counter32 }

lpSdhRunningTime OBJECT-TYPE
   SYNTAX     Counter32 
   ACCESS     read-only
   STATUS     mandatory
   DESCRIPTION
     "This attribute indicates the total number of seconds since the Sonet/
      Sdh component has been activated and been in unlocked state. All 
      the other error counts that follow can be updated when this count is 
      active."
::= { lpSdhStatsEntry 1 }

lpSdhErrorFreeSec OBJECT-TYPE
   SYNTAX     Counter32 
   ACCESS     read-only
   STATUS     mandatory
   DESCRIPTION
     "This attribute indicates the number of seconds that the Sonet/Sdh 
      component has been in an near-end error free state."
::= { lpSdhStatsEntry 2 }

lpSdhSectCodeViolations OBJECT-TYPE
   SYNTAX     Counter32 
   ACCESS     read-only
   STATUS     mandatory
   DESCRIPTION
     "This attribute indicates the total number of Section Code Violations 
      (SCVs) detected. A SCV corresponds to section BIP-8 error. SCV 
      counting is inhibited for second intervals where a Section Severely 
      Errored Second (SSES) is counted. The count wraps at its 
      maximum value."
::= { lpSdhStatsEntry 3 }

lpSdhSectErroredSec OBJECT-TYPE
   SYNTAX     Counter32 
   ACCESS     read-only
   STATUS     mandatory
   DESCRIPTION
     "This attribute indicates the total number of Section Errored Seconds 
      (SESs) that have been counted. A SES is declared for second 
      intervals containing one or more SCVs or one or more Loss Of 
      Signal (LOS) or Severely Errored Frame (SEF) defects. A SEF 
      defect is the occurrence of 4 contiguous errored STS or STM frame 
      alignment words."
::= { lpSdhStatsEntry 4 }

lpSdhSectSevErroredSec OBJECT-TYPE
   SYNTAX     Counter32 
   ACCESS     read-only
   STATUS     mandatory
   DESCRIPTION
     "This attribute indicates the total number of Section Severely Errored 
      Seconds (SSESs) that have been counted. A SSES is declared for 
      second intervals containing more than x SCVs or one or more LOS 
      or SEF defects. The value of x is 155 for a 155 Mbits/sec interface."
::= { lpSdhStatsEntry 5 }

lpSdhSectLosSec OBJECT-TYPE
   SYNTAX     Counter32 
   ACCESS     read-only
   STATUS     mandatory
   DESCRIPTION
     "This attribute indicates the total number of Section LOS Seconds 
      (SLOSSs) that have been counted. A SLOSS is declared for second 
      intervals containing one or more LOS defects."
::= { lpSdhStatsEntry 6 }

lpSdhSectSevErroredFrmSec OBJECT-TYPE
   SYNTAX     Counter32 
   ACCESS     read-only
   STATUS     mandatory
   DESCRIPTION
     "This attribute indicates the total number of Section Severely Errored 
      Frame Seconds (SSEFSs) that have been counted. A SSEFS is 
      declared for second intervals containing one or more SEF defects."
::= { lpSdhStatsEntry 7 }

lpSdhSectFailures OBJECT-TYPE
   SYNTAX     Counter32 
   ACCESS     read-only
   STATUS     mandatory
   DESCRIPTION
     "This attribute indicates the total number of times that a section 
      failure (LOS or LOF failure) has been declared."
::= { lpSdhStatsEntry 8 }

lpSdhLineCodeViolations OBJECT-TYPE
   SYNTAX     Counter32 
   ACCESS     read-only
   STATUS     mandatory
   DESCRIPTION
     "This attribute indicates the total number of Line Code Violations 
      (LCVs) detected. A LCV corresponds to a line BIP-24 errors. LCV 
      counting is inhibited for second intervals where a Line Severely 
      Errored Second (LSES) is counted. Counting of LCVs is also 
      inhibited over second intervals where a Line Unavailable Second 
      (LUAS) is counted. The count wraps at its maximum value."
::= { lpSdhStatsEntry 9 }

lpSdhLineErroredSec OBJECT-TYPE
   SYNTAX     Counter32 
   ACCESS     read-only
   STATUS     mandatory
   DESCRIPTION
     "This attribute indicates the total number of Line Errored Seconds 
      (LESs) that have been counted. A LES is declared for second 
      intervals containing one or more LCVs or one or more line AIS 
      defects. Counting of LES is inhibited over second intervals where a 
      LUAS is counted."
::= { lpSdhStatsEntry 10 }

lpSdhLineSevErroredSec OBJECT-TYPE
   SYNTAX     Counter32 
   ACCESS     read-only
   STATUS     mandatory
   DESCRIPTION
     "This attribute indicates the total number of Line Severely Errored 
      Seconds (LSESs) that have been counted. A LSES is declared for 
      second intervals containing more than x LCVs or one or more L-
      AIS defects. The value of x is 154 for a 155 Mbits/sec interface. 
      Counting of LSES is inhibited over second intervals where a LUAS 
      is counted."
::= { lpSdhStatsEntry 11 }

lpSdhLineAisSec OBJECT-TYPE
   SYNTAX     Counter32 
   ACCESS     read-only
   STATUS     mandatory
   DESCRIPTION
     "This attribute indicates the total number of Line AIS Seconds 
      (LAISSs) that have been counted. A LAISS is declared for second 
      intervals containing one or more L-AIS defects. Counting of LAISS 
      is inhibited over second intervals where a LUAS is counted."
::= { lpSdhStatsEntry 12 }

lpSdhLineUnavailSec OBJECT-TYPE
   SYNTAX     Counter32 
   ACCESS     read-only
   STATUS     mandatory
   DESCRIPTION
     "This attribute indicates the total number of one second intervals for 
      which the STS line is unavailable. The STS line becomes 
      unavailable at the onset of 10 consecutive LSESs. The 10 LSESs are 
      included in the unavailable time. Once unavailable, the STS line 
      becomes available at the onset of 10 contiguous seconds with no 
      LSES. The 10 seconds with no LSES are excluded from the 
      unavailable time. For second intervals where a Line Unavailable 
      Second (LUAS) is counted, counting of LCV, LES, LSES and 
      LAISS is inhibited."
::= { lpSdhStatsEntry 13 }

lpSdhLineFailures OBJECT-TYPE
   SYNTAX     Counter32 
   ACCESS     read-only
   STATUS     mandatory
   DESCRIPTION
     "This attribute indicates the total number of times that a line failure 
      (L-AIS failure) has been declared."
::= { lpSdhStatsEntry 14 }

lpSdhFarEndLineErrorFreeSec OBJECT-TYPE
   SYNTAX     Counter32 
   ACCESS     read-only
   STATUS     mandatory
   DESCRIPTION
     "This attribute indicates the number of seconds that the Sonet/Sdh 
      component has been in an far-end error free state."
::= { lpSdhStatsEntry 15 }

lpSdhFarEndLineCodeViolations OBJECT-TYPE
   SYNTAX     Counter32 
   ACCESS     read-only
   STATUS     mandatory
   DESCRIPTION
     "This attribute indicates the total number of line FEBE detected from 
      the incoming line. The counting of line FEBE is inhibited for 
      second intervals where a Far-End Line Severely Errored Second 
      (FELSES) is counted. Counting of FELCVs is also inhibited over 
      second intervals where a Far-End Line Unavailable Second 
      (FELUAS) is counted. The count wraps at its maximum value."
::= { lpSdhStatsEntry 16 }

lpSdhFarEndLineErroredSec OBJECT-TYPE
   SYNTAX     Counter32 
   ACCESS     read-only
   STATUS     mandatory
   DESCRIPTION
     "This attribute indicates the total number of Far-End Line Errored 
      Seconds (FELESs) that have been counted. A FELES is declared 
      for second intervals containing one or more Far-End Line CVs 
      (FELCVs) or one or more L-RDI defects. Counting of FELES is 
      inhibited over second intervals where a FELUAS is counted."
::= { lpSdhStatsEntry 17 }

lpSdhFarEndLineSevErroredSec OBJECT-TYPE
   SYNTAX     Counter32 
   ACCESS     read-only
   STATUS     mandatory
   DESCRIPTION
     "This attribute indicates the total number of Far-End Line Severely 
      Errored Seconds (FELSESs) that have been counted. A FELSES is 
      declared for second intervals containing more than x FELCVs or 
      one or more L-RDI defects. The value of x is 154 for a 155 Mbits/
      sec interface. Counting of FELSES is inhibited over second 
      intervals where a FELUAS is counted."
::= { lpSdhStatsEntry 18 }

lpSdhFarEndLineAisSec OBJECT-TYPE
   SYNTAX     Counter32 
   ACCESS     read-only
   STATUS     mandatory
   DESCRIPTION
     "This attribute indicates the total number of Far-End Line AIS 
      Seconds (FELAISSs) that have been counted. A FELAISS is 
      declared for second intervals one or more L-RDI defects. Counting 
      of FELAISS is inhibited over second intervals where a FELUAS is 
      counted."
::= { lpSdhStatsEntry 19 }

lpSdhFarEndLineUnavailSec OBJECT-TYPE
   SYNTAX     Counter32 
   ACCESS     read-only
   STATUS     mandatory
   DESCRIPTION
     "This attribute indicates the total number of one second intervals for 
      which the STS far-end line is unavailable. The STS far-end line 
      becomes unavailable at the onset of 10 consecutive FELSESs. The 
      10 FELSESs are included in the unavailable time. Once unavailable, 
      the STS far-end line becomes available at the onset of 10 
      contiguous seconds with no FELSES. The 10 seconds with no 
      FELSES are excluded from the unavailable time. For second 
      intervals where a Far-End Line Unavailable Second (FELUAS) is 
      counted, counting of FELCV, FELES, FELSES and FELAISS is 
      inhibited."
::= { lpSdhStatsEntry 20 }

lpSdhFarEndLineFailures OBJECT-TYPE
   SYNTAX     Counter32 
   ACCESS     read-only
   STATUS     mandatory
   DESCRIPTION
     "This attribute indicates the total number of times that a far-end line 
      failure (L-RFI failure) has been declared."
::= { lpSdhStatsEntry 21 }


-- ApmSonetSdhPath
-- The Lp/m Sonet/n Path or Lp/m Sdh/n Path component controls a 
-- path signal that is carried within a SONET or SDH signal. The Path 
-- component can only be added under a Sonet or Sdh component.

lpSdhPath OBJECT IDENTIFIER ::= { lpSdh 2 }



lpSdhPathRowStatusTable OBJECT-TYPE
   SYNTAX     SEQUENCE OF LpSdhPathRowStatusEntry
   ACCESS     not-accessible
   STATUS     mandatory
   DESCRIPTION
     "This entry controls the addition and deletion of 
      lpSdhPath components."
::= { lpSdhPath 1 }

lpSdhPathRowStatusEntry OBJECT-TYPE
   SYNTAX     LpSdhPathRowStatusEntry
   ACCESS     not-accessible
   STATUS     mandatory
   DESCRIPTION
     "A single entry in the table represents a single 
      lpSdhPath component."
   INDEX {
      lpIndex,
      lpSdhIndex,
      lpSdhPathIndex }
::= { lpSdhPathRowStatusTable 1 }

LpSdhPathRowStatusEntry ::= SEQUENCE {
   lpSdhPathRowStatus
      RowStatus,
   lpSdhPathComponentName
      DisplayString,
   lpSdhPathStorageType
      StorageType,
   lpSdhPathIndex
      Integer32 }

lpSdhPathRowStatus OBJECT-TYPE
   SYNTAX     RowStatus 
   ACCESS     read-write
   STATUS     mandatory
   DESCRIPTION
     "This variable is used as the basis for SNMP naming of
      lpSdhPath components.
      These components can be added and deleted."
::= { lpSdhPathRowStatusEntry 1 }

lpSdhPathComponentName OBJECT-TYPE
   SYNTAX     DisplayString 
   ACCESS     read-only
   STATUS     mandatory
   DESCRIPTION
     "This variable provides the component's string name for
      use with the ASCII Console Interface"
::= { lpSdhPathRowStatusEntry 2 }

lpSdhPathStorageType OBJECT-TYPE
   SYNTAX     StorageType 
   ACCESS     read-only
   STATUS     mandatory
   DESCRIPTION
     "This variable represents the storage type value for the
      lpSdhPath tables."
::= { lpSdhPathRowStatusEntry 4 }

lpSdhPathIndex OBJECT-TYPE
   SYNTAX     Integer32 (0..0)
   ACCESS     not-accessible
   STATUS     mandatory
   DESCRIPTION
     "This variable represents the index for the lpSdhPath tables."
::= { lpSdhPathRowStatusEntry 10 }

lpSdhPathProvTable OBJECT-TYPE
   SYNTAX     SEQUENCE OF LpSdhPathProvEntry
   ACCESS     not-accessible
   STATUS     mandatory
   DESCRIPTION
     "This group contains all of the provisioning data for a Sonet/Sdh 
      Path component."
::= { lpSdhPath 10 }

lpSdhPathProvEntry OBJECT-TYPE
   SYNTAX     LpSdhPathProvEntry
   ACCESS     not-accessible
   STATUS     mandatory
   DESCRIPTION
     "An entry in the lpSdhPathProvTable."
   INDEX {
      lpIndex,
      lpSdhIndex,
      lpSdhPathIndex }
::= { lpSdhPathProvTable 1 }

LpSdhPathProvEntry ::= SEQUENCE {
   lpSdhPathApplicationFramerName
      Link }

lpSdhPathApplicationFramerName OBJECT-TYPE
   SYNTAX     Link 
   ACCESS     read-write
   STATUS     mandatory
   DESCRIPTION
     "This attribute defines the link to the software stack. It defines which 
      application is running on top of the Path component."
::= { lpSdhPathProvEntry 1 }

lpSdhPathCidDataTable OBJECT-TYPE
   SYNTAX     SEQUENCE OF LpSdhPathCidDataEntry
   ACCESS     not-accessible
   STATUS     mandatory
   DESCRIPTION
     "This group contains the attribute for a component's Customer 
      Identifier (CID). Refer to the attribute description for a detailed 
      explanation of CIDs."
::= { lpSdhPath 11 }

lpSdhPathCidDataEntry OBJECT-TYPE
   SYNTAX     LpSdhPathCidDataEntry
   ACCESS     not-accessible
   STATUS     mandatory
   DESCRIPTION
     "An entry in the lpSdhPathCidDataTable."
   INDEX {
      lpIndex,
      lpSdhIndex,
      lpSdhPathIndex }
::= { lpSdhPathCidDataTable 1 }

LpSdhPathCidDataEntry ::= SEQUENCE {
   lpSdhPathCustomerIdentifier
      Unsigned32 }

lpSdhPathCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpSdhPathCidDataEntry 1 }

lpSdhPathStateTable OBJECT-TYPE
   SYNTAX     SEQUENCE OF LpSdhPathStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpSdhPath 12 }

lpSdhPathStateEntry OBJECT-TYPE
   SYNTAX     LpSdhPathStateEntry
   ACCESS     not-accessible
   STATUS     mandatory
   DESCRIPTION
     "An entry in the lpSdhPathStateTable."
   INDEX {
      lpIndex,
      lpSdhIndex,
      lpSdhPathIndex }
::= { lpSdhPathStateTable 1 }

LpSdhPathStateEntry ::= SEQUENCE {
   lpSdhPathAdminState
      INTEGER,
   lpSdhPathOperationalState
      INTEGER,
   lpSdhPathUsageState
      INTEGER,
   lpSdhPathAvailabilityStatus
      OCTET STRING,
   lpSdhPathProceduralStatus
      OCTET STRING,
   lpSdhPathControlStatus
      OCTET STRING,
   lpSdhPathAlarmStatus
      OCTET STRING,
   lpSdhPathStandbyStatus
      INTEGER,
   lpSdhPathUnknownStatus
      INTEGER }

lpSdhPathAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpSdhPathStateEntry 1 }

lpSdhPathOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpSdhPathStateEntry 2 }

lpSdhPathUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpSdhPathStateEntry 3 }

lpSdhPathAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpSdhPathStateEntry 4 }

lpSdhPathProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpSdhPathStateEntry 5 }

lpSdhPathControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpSdhPathStateEntry 6 }

lpSdhPathAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpSdhPathStateEntry 7 }

lpSdhPathStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpSdhPathStateEntry 8 }

lpSdhPathUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpSdhPathStateEntry 9 }

lpSdhPathIfEntryTable OBJECT-TYPE
   SYNTAX     SEQUENCE OF LpSdhPathIfEntryEntry
   ACCESS     not-accessible
   STATUS     mandatory
   DESCRIPTION
     "This group contains the provisionable attributes for the ifEntry."
::= { lpSdhPath 13 }

lpSdhPathIfEntryEntry OBJECT-TYPE
   SYNTAX     LpSdhPathIfEntryEntry
   ACCESS     not-accessible
   STATUS     mandatory
   DESCRIPTION
     "An entry in the lpSdhPathIfEntryTable."
   INDEX {
      lpIndex,
      lpSdhIndex,
      lpSdhPathIndex }
::= { lpSdhPathIfEntryTable 1 }

LpSdhPathIfEntryEntry ::= SEQUENCE {
   lpSdhPathIfAdminStatus
      INTEGER,
   lpSdhPathIfIndex
      InterfaceIndex }

lpSdhPathIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpSdhPathIfEntryEntry 1 }

lpSdhPathIfIndex OBJECT-TYPE
   SYNTAX     InterfaceIndex (1..65535)
   ACCESS     read-only
   STATUS     mandatory
   DESCRIPTION
     "This is the index for the IfEntry. Its value is automatically initialized 
      during the provisioning process."
::= { lpSdhPathIfEntryEntry 2 }

lpSdhPathOperStatusTable OBJECT-TYPE
   SYNTAX     SEQUENCE OF LpSdhPathOperStatusEntry
   ACCESS     not-accessible
   STATUS     mandatory
   DESCRIPTION
     "This group includes the Operational Status attribute. This attribute 
      defines the current operational state of this component."
::= { lpSdhPath 14 }

lpSdhPathOperStatusEntry OBJECT-TYPE
   SYNTAX     LpSdhPathOperStatusEntry
   ACCESS     not-accessible
   STATUS     mandatory
   DESCRIPTION
     "An entry in the lpSdhPathOperStatusTable."
   INDEX {
      lpIndex,
      lpSdhIndex,
      lpSdhPathIndex }
::= { lpSdhPathOperStatusTable 1 }

LpSdhPathOperStatusEntry ::= SEQUENCE {
   lpSdhPathSnmpOperStatus
      INTEGER }

lpSdhPathSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpSdhPathOperStatusEntry 1 }

lpSdhPathOperTable OBJECT-TYPE
   SYNTAX     SEQUENCE OF LpSdhPathOperEntry
   ACCESS     not-accessible
   STATUS     mandatory
   DESCRIPTION
     "This group contains the common operational data for Path 
      component."
::= { lpSdhPath 15 }

lpSdhPathOperEntry OBJECT-TYPE
   SYNTAX     LpSdhPathOperEntry
   ACCESS     not-accessible
   STATUS     mandatory
   DESCRIPTION
     "An entry in the lpSdhPathOperTable."
   INDEX {
      lpIndex,
      lpSdhIndex,
      lpSdhPathIndex }
::= { lpSdhPathOperTable 1 }

LpSdhPathOperEntry ::= SEQUENCE {
   lpSdhPathLopAlarm
      INTEGER,
   lpSdhPathRxAisAlarm
      INTEGER,
   lpSdhPathRxRfiAlarm
      INTEGER,
   lpSdhPathSignalLabelMismatch
      INTEGER,
   lpSdhPathTxAis
      INTEGER,
   lpSdhPathTxRdi
      INTEGER }

lpSdhPathLopAlarm OBJECT-TYPE
   SYNTAX     INTEGER  {
                 on(0),
                 off(1) }
   ACCESS     read-only
   STATUS     mandatory
   DESCRIPTION
     "This attribute displays whether a Loss Of Pointer (LOP) alarm state 
      has been entered. An LOP alarm state is entered when LOP defects 
      have been observed and accumulated for a period of 2.5 seconds +/- 
      0.5 seconds. An LOP defect occurs when no valid SPE or VC 
      pointer was received in 8 contiguous frames. If the LOP defects are 
      intermittently occurring, the LOP defect accumulator is 
      decremented at a rate of 1/10 of the incrementing rate (alarm 
      integration ratio of 1/10), with all measurements based on a 200 ms 
      polling cycle.
      The Path component goes into an operational state of disabled until 
      the LOP alarm condition is cleared. The condition is cleared when 
      no more invalid pointer has been reported for 10 seconds +/- 0.5 
      seconds.
      The lopAlarm attribute is always set to off when the Path 
      component has been locked and left offline by the operator or when 
      the Path component has been suspended since the parent component 
      has been locked."
::= { lpSdhPathOperEntry 1 }

lpSdhPathRxAisAlarm OBJECT-TYPE
   SYNTAX     INTEGER  {
                 on(0),
                 off(1) }
   ACCESS     read-only
   STATUS     mandatory
   DESCRIPTION
     "This attribute displays whether an Path Alarm Indication Signal (P-
      AIS) alarm state has been entered. An P-AIS alarm state is entered 
      when P-AIS defects have been observed and accumulated for a 
      period of 2.5 seconds +/- 0.5 seconds. The P-AIS defect is the 
      occurrence of the P-AIS signal in three contiguous valid STS or 
      STM frames (all one's in bytes H1 and H2). If the P-AIS defects are 
      intermittently occurring, the P-AIS defect accumulator is 
      decremented at a rate of 1/10 of the incrementing rate (alarm 
      integration ratio of 1/10), with all measurements based on a 200 ms 
      polling cycle.
      The Path component goes into an operational state of disabled until 
      the P-AIS alarm condition is cleared. The condition is cleared after 
      no P-AIS defect has been detected for 10 seconds +/- 0.5 seconds.
      The rxAisAlarm attribute is always set to off when the Path 
      component has been locked and left offline by the operator or when 
      the Path component has been suspended since the parent component 
      has been locked."
::= { lpSdhPathOperEntry 2 }

lpSdhPathRxRfiAlarm OBJECT-TYPE
   SYNTAX     INTEGER  {
                 on(0),
                 off(1) }
   ACCESS     read-only
   STATUS     mandatory
   DESCRIPTION
     "This attribute displays whether the Path Remote Failure Indication 
      (P-RFI) alarm state has been entered. An P-RFI alarm state is 
      entered when Path Remote Defect Indicator (P-RDI) defects have 
      been observed and accumulated for a period of 2.5 seconds +/- 0.5 
      seconds. The P-RDI defect is the occurrence of the P-RDI signal in 
      five contiguous valid STS or STM frames (bit 5 of the G1 byte set 
      to 1). If the P-RDI defects are intermittently occurring, the P-RDI 
      defect accumulator is decremented at a rate of 1/10 of the 
      incrementing rate (alarm integration ratio of 1/10)with all 
      measurements based on a 200 ms polling cycle.
      The Path component goes into an operational state of disabled until 
      the P-RFI alarm condition is cleared. The condition is cleared after 
      no P-RDI defect has been detected for 10 seconds +/- 0.5 seconds.
      The rxRfiAlarm attribute is always set to off when the Path 
      component has been locked and left offline by the operator or when 
      the Path component has been suspended since the parent component 
      has been locked."
::= { lpSdhPathOperEntry 3 }

lpSdhPathSignalLabelMismatch OBJECT-TYPE
   SYNTAX     INTEGER  {
                 on(0),
                 off(1) }
   ACCESS     read-only
   STATUS     mandatory
   DESCRIPTION
     "This attribute displays whether the Path Signal Label Mismatch (P-
      SLM) failure condition has been entered. An P-SLM failure 
      condition is entered when P-SLM defects have been observed and 
      accumulated for period of 2.5 seconds +/- 0.5 seconds. An P-SLM 
      defect occurs when detecting an unexpected path signal label. The 
      expected Path signal labels are 'Mapping for ATM' or 'Equipped - 
      Non Specific Payload'. If the P-SLM defects are intermittently 
      occurring, the P-SLM defect accumulator is decremented at a rate 
      of 1/10 of the incrementing rate (alarm integration ratio of 1/10), 
      with all measurements based on a 200 ms polling cycle.
      The Path component goes into an operational state of disabled until 
      the Path Signal Label Mismatch failure condition is cleared. The 
      condition is cleared when an expected path signal label is received 
      for 10 seconds +/- 0.5 seconds.
      The signalLabelMismatch attribute is always set to off when the 
      Path component has been locked and left offline by the operator or 
      when the Path component has been suspended since the parent 
      component has been locked."
::= { lpSdhPathOperEntry 4 }

lpSdhPathTxAis OBJECT-TYPE
   SYNTAX     INTEGER  {
                 on(0),
                 off(1) }
   ACCESS     read-only
   STATUS     mandatory
   DESCRIPTION
     "This attribute displays whether the Path Alarm Indication Signal (P-
      AIS) signal is being transmitted on the path. The P-AIS signal is 
      transmitted when the Path component has been locked and left 
      offline by the operator or when the Path component has been 
      suspended since the parent component has been locked."
::= { lpSdhPathOperEntry 5 }

lpSdhPathTxRdi OBJECT-TYPE
   SYNTAX     INTEGER  {
                 on(0),
                 off(1) }
   ACCESS     read-only
   STATUS     mandatory
   DESCRIPTION
     "This attribute displays whether the Path Remote Defect Indicator 
      (P-RDI) signal is being transmitted over the path signal. The P-RDI 
      signal is transmitted over the outgoing line upon detection of LOP, 
      P-AIS or the occurrence of the LCD state. This attribute is always 
      set to off when the Path component has been locked and left offline 
      by the operator or when the Path component has been suspended 
      since the parent component has been locked."
::= { lpSdhPathOperEntry 6 }

lpSdhPathStatsTable OBJECT-TYPE
   SYNTAX     SEQUENCE OF LpSdhPathStatsEntry
   ACCESS     not-accessible
   STATUS     mandatory
   DESCRIPTION
     "This group contains the statistics data for a Sonet/Sdh Path 
      component. Each attribute type is a non-negative integer which 
      monotonically increases until it reaches a maximum value, at which 
      point it wraps around and starts increasing again from zero."
::= { lpSdhPath 16 }

lpSdhPathStatsEntry OBJECT-TYPE
   SYNTAX     LpSdhPathStatsEntry
   ACCESS     not-accessible
   STATUS     mandatory
   DESCRIPTION
     "An entry in the lpSdhPathStatsTable."
   INDEX {
      lpIndex,
      lpSdhIndex,
      lpSdhPathIndex }
::= { lpSdhPathStatsTable 1 }

LpSdhPathStatsEntry ::= SEQUENCE {
   lpSdhPathPathErrorFreeSec
      Counter32,
   lpSdhPathPathCodeViolations
      Counter32,
   lpSdhPathPathErroredSec
      Counter32,
   lpSdhPathPathSevErroredSec
      Counter32,
   lpSdhPathPathAisLopSec
      Counter32,
   lpSdhPathPathUnavailSec
      Counter32,
   lpSdhPathPathFailures
      Counter32,
   lpSdhPathFarEndPathErrorFreeSec
      Counter32,
   lpSdhPathFarEndPathCodeViolations
      Counter32,
   lpSdhPathFarEndPathErroredSec
      Counter32,
   lpSdhPathFarEndPathSevErroredSec
      Counter32,
   lpSdhPathFarEndPathAisLopSec
      Counter32,
   lpSdhPathFarEndPathUnavailSec
      Counter32,
   lpSdhPathFarEndPathFailures
      Counter32 }

lpSdhPathPathErrorFreeSec OBJECT-TYPE
   SYNTAX     Counter32 
   ACCESS     read-only
   STATUS     mandatory
   DESCRIPTION
     "This attribute indicates the number of seconds that the Sonet/Sdh 
      Path component has been in an near-end error free state."
::= { lpSdhPathStatsEntry 1 }

lpSdhPathPathCodeViolations OBJECT-TYPE
   SYNTAX     Counter32 
   ACCESS     read-only
   STATUS     mandatory
   DESCRIPTION
     "This attribute indicates the total number of Path Code Violations 
      (PCVs) detected. Each PCV corresponds to a path BIP-8 error. PCV 
      counting is inhibited over second intervals where a Path Severely 
      Errored Second (PSES) is counted. Counting of PCVs is also 
      inhibited over second intervals where a Path Unavailable Second 
      (PUAS) is counted. The count wraps at its maximum value."
::= { lpSdhPathStatsEntry 2 }

lpSdhPathPathErroredSec OBJECT-TYPE
   SYNTAX     Counter32 
   ACCESS     read-only
   STATUS     mandatory
   DESCRIPTION
     "This attribute indicates the total number of Path Errored Seconds 
      (PESs) that have been counted. A PES is declared for second 
      intervals containing one or more PCVs or one or more LOP or path 
      AIS defects. Counting of PES is inhibited when PUAS is counted 
      over the monitored second."
::= { lpSdhPathStatsEntry 3 }

lpSdhPathPathSevErroredSec OBJECT-TYPE
   SYNTAX     Counter32 
   ACCESS     read-only
   STATUS     mandatory
   DESCRIPTION
     "This attribute indicates the total number of Path Severely Errored 
      Seconds (PSESs) that have been counted. A PSES is declared for 
      second intervals containing more than x PCVs or one or more LOP 
      or path AIS defects. The value of x is 2400 for a 155 Mbits/sec 
      interface. Counting of PSES is inhibited when PUAS is counted 
      over the monitored second."
::= { lpSdhPathStatsEntry 4 }

lpSdhPathPathAisLopSec OBJECT-TYPE
   SYNTAX     Counter32 
   ACCESS     read-only
   STATUS     mandatory
   DESCRIPTION
     "This attribute indicates the total number of path AIS and LOP 
      Seconds (PALSs). A PALS is declared for second intervals 
      containing one or more path AIS or LOP defects. Counting of PALS 
      is inhibited when PUAS is counted over the monitored second."
::= { lpSdhPathStatsEntry 5 }

lpSdhPathPathUnavailSec OBJECT-TYPE
   SYNTAX     Counter32 
   ACCESS     read-only
   STATUS     mandatory
   DESCRIPTION
     "This attribute indicates the total number of one second intervals for 
      which the STS/STM path is unavailable. The path becomes 
      unavailable at the onset of 10 consecutive PSESs. The 10 PSESs are 
      included in the unavailable time. Once unavailable, the path 
      becomes available at the onset of 10 contiguous seconds with no 
      PSES. The 10 seconds with no PSES are excluded from the 
      unavailable time. For second intervals where a Path Unavailable 
      Second (PUAS) is counted, counting of PCV, PES, PSES and PALS 
      is inhibited."
::= { lpSdhPathStatsEntry 6 }

lpSdhPathPathFailures OBJECT-TYPE
   SYNTAX     Counter32 
   ACCESS     read-only
   STATUS     mandatory
   DESCRIPTION
     "This attribute indicates the total number of times that a path failure 
      (LOP, P-AIS or Path Signal Label Mismatch failure) has been 
      declared."
::= { lpSdhPathStatsEntry 7 }

lpSdhPathFarEndPathErrorFreeSec OBJECT-TYPE
   SYNTAX     Counter32 
   ACCESS     read-only
   STATUS     mandatory
   DESCRIPTION
     "This attribute indicates the number of seconds that the Sonet/Sdh 
      Path component has been in an far-end error free state."
::= { lpSdhPathStatsEntry 8 }

lpSdhPathFarEndPathCodeViolations OBJECT-TYPE
   SYNTAX     Counter32 
   ACCESS     read-only
   STATUS     mandatory
   DESCRIPTION
     "This attribute indicates the total number of Far-End Path Code 
      Violations (FEPCVs) detected. Each FEPCV corresponds to a path 
      FEBE. FEPCV counting is inhibited over second intervals where a 
      Far-End Path Severely Errored Second (FEPSES) is counted. 
      Counting of PCVs is also inhibited over second intervals where a 
      Far-End Path Unavailable Second (FEPUAS) is counted. The count 
      wraps at its maximum value."
::= { lpSdhPathStatsEntry 9 }

lpSdhPathFarEndPathErroredSec OBJECT-TYPE
   SYNTAX     Counter32 
   ACCESS     read-only
   STATUS     mandatory
   DESCRIPTION
     "This attribute indicates the total number of Far-End Path Errored 
      Seconds (FEPESs) that have been counted. A FEPES is declared for 
      second intervals containing one or more FEPCVs or one or more 
      path RDI (P-RDI) defects. Counting of FEPES is inhibited when 
      FEPUAS is counted over the monitored second."
::= { lpSdhPathStatsEntry 10 }

lpSdhPathFarEndPathSevErroredSec OBJECT-TYPE
   SYNTAX     Counter32 
   ACCESS     read-only
   STATUS     mandatory
   DESCRIPTION
     "This attribute indicates the total number of Far-End Path Severely 
      Errored Seconds (FEPSESs) that have been counted. A FEPSES is 
      declared for second intervals containing more than x FEPCVs or 
      one or more P-RDI defects. The value of x is 2400 for a 155 Mbits/
      sec interface. Counting of FEPSESs is inhibited when FEPUAS is 
      counted over the monitored second."
::= { lpSdhPathStatsEntry 11 }

lpSdhPathFarEndPathAisLopSec OBJECT-TYPE
   SYNTAX     Counter32 
   ACCESS     read-only
   STATUS     mandatory
   DESCRIPTION
     "This attribute indicates the total number of Far-End Path AIS and 
      LOP Seconds (FEPALSs). A FEPALS is declared for second 
      intervals containing one or more P-RDI defects. Counting of 
      FEPALS is inhibited when FEPUAS is counted over the monitored 
      second."
::= { lpSdhPathStatsEntry 12 }

lpSdhPathFarEndPathUnavailSec OBJECT-TYPE
   SYNTAX     Counter32 
   ACCESS     read-only
   STATUS     mandatory
   DESCRIPTION
     "This attribute indicates the total number of one second intervals for 
      which the STS/STM far-end path is unavailable. The far-end path 
      becomes unavailable at the onset of 10 consecutive FEPSESs. The 
      10 FEPSESs are included in the unavailable time. Once unavailable, 
      the far-end path becomes available at the onset of 10 contiguous 
      seconds with no FEPSES. The 10 seconds with no FEPSES are 
      excluded from the unavailable time. For second intervals where a 
      Far-End Path Unavailable Second (FEPUAS) is counted, counting 
      of FEPCV, FEPES, FEPSES and FEPALS is inhibited."
::= { lpSdhPathStatsEntry 13 }

lpSdhPathFarEndPathFailures OBJECT-TYPE
   SYNTAX     Counter32 
   ACCESS     read-only
   STATUS     mandatory
   DESCRIPTION
     "This attribute indicates the total number of times that a STS/STM 
      far-end path failure (P-RFI failure) has been declared."
::= { lpSdhPathStatsEntry 14 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

lpSdhPathCell OBJECT IDENTIFIER ::= { lpSdhPath 2 }



lpSdhPathCellRowStatusTable OBJECT-TYPE
   SYNTAX     SEQUENCE OF LpSdhPathCellRowStatusEntry
   ACCESS     not-accessible
   STATUS     mandatory
   DESCRIPTION
     "This entry controls the addition and deletion of 
      lpSdhPathCell components."
::= { lpSdhPathCell 1 }

lpSdhPathCellRowStatusEntry OBJECT-TYPE
   SYNTAX     LpSdhPathCellRowStatusEntry
   ACCESS     not-accessible
   STATUS     mandatory
   DESCRIPTION
     "A single entry in the table represents a single 
      lpSdhPathCell component."
   INDEX {
      lpIndex,
      lpSdhIndex,
      lpSdhPathIndex,
      lpSdhPathCellIndex }
::= { lpSdhPathCellRowStatusTable 1 }

LpSdhPathCellRowStatusEntry ::= SEQUENCE {
   lpSdhPathCellRowStatus
      RowStatus,
   lpSdhPathCellComponentName
      DisplayString,
   lpSdhPathCellStorageType
      StorageType,
   lpSdhPathCellIndex
      NonReplicated }

lpSdhPathCellRowStatus OBJECT-TYPE
   SYNTAX     RowStatus 
   ACCESS     read-only
   STATUS     mandatory
   DESCRIPTION
     "This variable is used as the basis for SNMP naming of
      lpSdhPathCell components.
      These components cannot be added nor deleted."
::= { lpSdhPathCellRowStatusEntry 1 }

lpSdhPathCellComponentName OBJECT-TYPE
   SYNTAX     DisplayString 
   ACCESS     read-only
   STATUS     mandatory
   DESCRIPTION
     "This variable provides the component's string name for
      use with the ASCII Console Interface"
::= { lpSdhPathCellRowStatusEntry 2 }

lpSdhPathCellStorageType OBJECT-TYPE
   SYNTAX     StorageType 
   ACCESS     read-only
   STATUS     mandatory
   DESCRIPTION
     "This variable represents the storage type value for the
      lpSdhPathCell tables."
::= { lpSdhPathCellRowStatusEntry 4 }

lpSdhPathCellIndex OBJECT-TYPE
   SYNTAX     NonReplicated 
   ACCESS     not-accessible
   STATUS     mandatory
   DESCRIPTION
     "This variable represents the index for the lpSdhPathCell tables."
::= { lpSdhPathCellRowStatusEntry 10 }

lpSdhPathCellProvTable OBJECT-TYPE
   SYNTAX     SEQUENCE OF LpSdhPathCellProvEntry
   ACCESS     not-accessible
   STATUS     mandatory
   DESCRIPTION
     "This group contains the provisioning attributes for the AtmCell 
      component."
::= { lpSdhPathCell 10 }

lpSdhPathCellProvEntry OBJECT-TYPE
   SYNTAX     LpSdhPathCellProvEntry
   ACCESS     not-accessible
   STATUS     mandatory
   DESCRIPTION
     "An entry in the lpSdhPathCellProvTable."
   INDEX {
      lpIndex,
      lpSdhIndex,
      lpSdhPathIndex,
      lpSdhPathCellIndex }
::= { lpSdhPathCellProvTable 1 }

LpSdhPathCellProvEntry ::= SEQUENCE {
   lpSdhPathCellAlarmActDelay
      Unsigned32,
   lpSdhPathCellScrambleCellPayload
      INTEGER,
   lpSdhPathCellCorrectSingleBitHeaderErrors
      INTEGER }

lpSdhPathCellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { lpSdhPathCellProvEntry 1 }

lpSdhPathCellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { lpSdhPathCellProvEntry 2 }

lpSdhPathCellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { lpSdhPathCellProvEntry 3 }

lpSdhPathCellOperTable OBJECT-TYPE
   SYNTAX     SEQUENCE OF LpSdhPathCellOperEntry
   ACCESS     not-accessible
   STATUS     mandatory
   DESCRIPTION
     "This group contains the common operational attributes for the 
      AtmCell component."
::= { lpSdhPathCell 11 }

lpSdhPathCellOperEntry OBJECT-TYPE
   SYNTAX     LpSdhPathCellOperEntry
   ACCESS     not-accessible
   STATUS     mandatory
   DESCRIPTION
     "An entry in the lpSdhPathCellOperTable."
   INDEX {
      lpIndex,
      lpSdhIndex,
      lpSdhPathIndex,
      lpSdhPathCellIndex }
::= { lpSdhPathCellOperTable 1 }

LpSdhPathCellOperEntry ::= SEQUENCE {
   lpSdhPathCellLcdAlarm
      INTEGER }

lpSdhPathCellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { lpSdhPathCellOperEntry 1 }

lpSdhPathCellStatsTable OBJECT-TYPE
   SYNTAX     SEQUENCE OF LpSdhPathCellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { lpSdhPathCell 12 }

lpSdhPathCellStatsEntry OBJECT-TYPE
   SYNTAX     LpSdhPathCellStatsEntry
   ACCESS     not-accessible
   STATUS     mandatory
   DESCRIPTION
     "An entry in the lpSdhPathCellStatsTable."
   INDEX {
      lpIndex,
      lpSdhIndex,
      lpSdhPathIndex,
      lpSdhPathCellIndex }
::= { lpSdhPathCellStatsTable 1 }

LpSdhPathCellStatsEntry ::= SEQUENCE {
   lpSdhPathCellUncorrectableHecErrors
      Counter32,
   lpSdhPathCellSevErroredSec
      Counter32,
   lpSdhPathCellReceiveCellUtilization
      Gauge32,
   lpSdhPathCellTransmitCellUtilization
      Gauge32,
   lpSdhPathCellCorrectableHeaderErrors
      Counter32 }

lpSdhPathCellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { lpSdhPathCellStatsEntry 1 }

lpSdhPathCellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { lpSdhPathCellStatsEntry 2 }

lpSdhPathCellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { lpSdhPathCellStatsEntry 3 }

lpSdhPathCellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { lpSdhPathCellStatsEntry 4 }

lpSdhPathCellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { lpSdhPathCellStatsEntry 5 }


-- 
-- The Test component is configured to control a hardware facility test 
-- on a physical (V35, X21, DS1, E1, DS3, E3 etc.) or a logical port.

lpSdhTest OBJECT IDENTIFIER ::= { lpSdh 3 }



lpSdhTestRowStatusTable OBJECT-TYPE
   SYNTAX     SEQUENCE OF LpSdhTestRowStatusEntry
   ACCESS     not-accessible
   STATUS     mandatory
   DESCRIPTION
     "This entry controls the addition and deletion of 
      lpSdhTest components."
::= { lpSdhTest 1 }

lpSdhTestRowStatusEntry OBJECT-TYPE
   SYNTAX     LpSdhTestRowStatusEntry
   ACCESS     not-accessible
   STATUS     mandatory
   DESCRIPTION
     "A single entry in the table represents a single 
      lpSdhTest component."
   INDEX {
      lpIndex,
      lpSdhIndex,
      lpSdhTestIndex }
::= { lpSdhTestRowStatusTable 1 }

LpSdhTestRowStatusEntry ::= SEQUENCE {
   lpSdhTestRowStatus
      RowStatus,
   lpSdhTestComponentName
      DisplayString,
   lpSdhTestStorageType
      StorageType,
   lpSdhTestIndex
      NonReplicated }

lpSdhTestRowStatus OBJECT-TYPE
   SYNTAX     RowStatus 
   ACCESS     read-only
   STATUS     mandatory
   DESCRIPTION
     "This variable is used as the basis for SNMP naming of
      lpSdhTest components.
      These components cannot be added nor deleted."
::= { lpSdhTestRowStatusEntry 1 }

lpSdhTestComponentName OBJECT-TYPE
   SYNTAX     DisplayString 
   ACCESS     read-only
   STATUS     mandatory
   DESCRIPTION
     "This variable provides the component's string name for
      use with the ASCII Console Interface"
::= { lpSdhTestRowStatusEntry 2 }

lpSdhTestStorageType OBJECT-TYPE
   SYNTAX     StorageType 
   ACCESS     read-only
   STATUS     mandatory
   DESCRIPTION
     "This variable represents the storage type value for the
      lpSdhTest tables."
::= { lpSdhTestRowStatusEntry 4 }

lpSdhTestIndex OBJECT-TYPE
   SYNTAX     NonReplicated 
   ACCESS     not-accessible
   STATUS     mandatory
   DESCRIPTION
     "This variable represents the index for the lpSdhTest tables."
::= { lpSdhTestRowStatusEntry 10 }

lpSdhTestStateTable OBJECT-TYPE
   SYNTAX     SEQUENCE OF LpSdhTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpSdhTest 10 }

lpSdhTestStateEntry OBJECT-TYPE
   SYNTAX     LpSdhTestStateEntry
   ACCESS     not-accessible
   STATUS     mandatory
   DESCRIPTION
     "An entry in the lpSdhTestStateTable."
   INDEX {
      lpIndex,
      lpSdhIndex,
      lpSdhTestIndex }
::= { lpSdhTestStateTable 1 }

LpSdhTestStateEntry ::= SEQUENCE {
   lpSdhTestAdminState
      INTEGER,
   lpSdhTestOperationalState
      INTEGER,
   lpSdhTestUsageState
      INTEGER }

lpSdhTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpSdhTestStateEntry 1 }

lpSdhTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpSdhTestStateEntry 2 }

lpSdhTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpSdhTestStateEntry 3 }

lpSdhTestSetupTable OBJECT-TYPE
   SYNTAX     SEQUENCE OF LpSdhTestSetupEntry
   ACCESS     not-accessible
   STATUS     mandatory
   DESCRIPTION
     "This group contains all of the operational data for a Test 
      component."
::= { lpSdhTest 11 }

lpSdhTestSetupEntry OBJECT-TYPE
   SYNTAX     LpSdhTestSetupEntry
   ACCESS     not-accessible
   STATUS     mandatory
   DESCRIPTION
     "An entry in the lpSdhTestSetupTable."
   INDEX {
      lpIndex,
      lpSdhIndex,
      lpSdhTestIndex }
::= { lpSdhTestSetupTable 1 }

LpSdhTestSetupEntry ::= SEQUENCE {
   lpSdhTestPurpose
      AsciiString,
   lpSdhTestType
      INTEGER,
   lpSdhTestFrmSize
      Unsigned32,
   lpSdhTestFrmPatternType
      INTEGER,
   lpSdhTestCustomizedPattern
      Hex,
   lpSdhTestDataStartDelay
      Unsigned32,
   lpSdhTestDisplayInterval
      Unsigned32,
   lpSdhTestDuration
      Unsigned32 }

lpSdhTestPurpose OBJECT-TYPE
   SYNTAX     AsciiString (SIZE (0..40))
   ACCESS     read-write
   STATUS     mandatory
   DESCRIPTION
     "This attribute records the purpose of the test so that the test results 
      can be associated and properly analyzed."
::= { lpSdhTestSetupEntry 1 }

lpSdhTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpSdhTestSetupEntry 2 }

lpSdhTestFrmSize OBJECT-TYPE
   SYNTAX     Unsigned32 (4..4096)
   ACCESS     read-write
   STATUS     mandatory
   DESCRIPTION
     "This attribute defines the size of the test data frames in number of 
      bytes."
   DEFVAL     { 1024 }
::= { lpSdhTestSetupEntry 3 }

lpSdhTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpSdhTestSetupEntry 4 }

lpSdhTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpSdhTestSetupEntry 5 }

lpSdhTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpSdhTestSetupEntry 6 }

lpSdhTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpSdhTestSetupEntry 7 }

lpSdhTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpSdhTestSetupEntry 8 }

lpSdhTestResultsTable OBJECT-TYPE
   SYNTAX     SEQUENCE OF LpSdhTestResultsEntry
   ACCESS     not-accessible
   STATUS     mandatory
   DESCRIPTION
     "This group contains all the statistics related attributes of the Test 
      component."
::= { lpSdhTest 12 }

lpSdhTestResultsEntry OBJECT-TYPE
   SYNTAX     LpSdhTestResultsEntry
   ACCESS     not-accessible
   STATUS     mandatory
   DESCRIPTION
     "An entry in the lpSdhTestResultsTable."
   INDEX {
      lpIndex,
      lpSdhIndex,
      lpSdhTestIndex }
::= { lpSdhTestResultsTable 1 }

LpSdhTestResultsEntry ::= SEQUENCE {
   lpSdhTestElapsedTime
      Counter32,
   lpSdhTestTimeRemaining
      Unsigned32,
   lpSdhTestCauseOfTermination
      INTEGER,
   lpSdhTestBitsTx
      PassportCounter64,
   lpSdhTestBytesTx
      PassportCounter64,
   lpSdhTestFrmTx
      PassportCounter64,
   lpSdhTestBitsRx
      PassportCounter64,
   lpSdhTestBytesRx
      PassportCounter64,
   lpSdhTestFrmRx
      PassportCounter64,
   lpSdhTestErroredFrmRx
      PassportCounter64,
   lpSdhTestBitErrorRate
      AsciiString }

lpSdhTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpSdhTestResultsEntry 1 }

lpSdhTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpSdhTestResultsEntry 2 }

lpSdhTestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpSdhTestResultsEntry 3 }

lpSdhTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpSdhTestResultsEntry 4 }

lpSdhTestBytesTx OBJECT-TYPE
   SYNTAX     PassportCounter64 
   ACCESS     read-only
   STATUS     mandatory
   DESCRIPTION
     "This attribute is the total number of bytes sent during the test 
      period. This counter is not expected to reach its maximum value."
::= { lpSdhTestResultsEntry 5 }

lpSdhTestFrmTx OBJECT-TYPE
   SYNTAX     PassportCounter64 
   ACCESS     read-only
   STATUS     mandatory
   DESCRIPTION
     "This attribute is the total number of frames sent during the test 
      period. This counter is not expected to reach its maximum value."
::= { lpSdhTestResultsEntry 6 }

lpSdhTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpSdhTestResultsEntry 7 }

lpSdhTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpSdhTestResultsEntry 8 }

lpSdhTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpSdhTestResultsEntry 9 }

lpSdhTestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpSdhTestResultsEntry 10 }

lpSdhTestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpSdhTestResultsEntry 11 }


-- Lp/n JT2/n
-- The JT2 component controls and monitors a JT2 port on a 
-- 2pJ6MAtm Function Processor. Up to two ports may be provisioned 
-- on the 2pJ6MAtm interface card.

lpJT2 OBJECT IDENTIFIER ::= { lp 16 }



lpJT2RowStatusTable OBJECT-TYPE
   SYNTAX     SEQUENCE OF LpJT2RowStatusEntry
   ACCESS     not-accessible
   STATUS     mandatory
   DESCRIPTION
     "This entry controls the addition and deletion of 
      lpJT2 components."
::= { lpJT2 1 }

lpJT2RowStatusEntry OBJECT-TYPE
   SYNTAX     LpJT2RowStatusEntry
   ACCESS     not-accessible
   STATUS     mandatory
   DESCRIPTION
     "A single entry in the table represents a single 
      lpJT2 component."
   INDEX {
      lpIndex,
      lpJT2Index }
::= { lpJT2RowStatusTable 1 }

LpJT2RowStatusEntry ::= SEQUENCE {
   lpJT2RowStatus
      RowStatus,
   lpJT2ComponentName
      DisplayString,
   lpJT2StorageType
      StorageType,
   lpJT2Index
      Integer32 }

lpJT2RowStatus OBJECT-TYPE
   SYNTAX     RowStatus 
   ACCESS     read-write
   STATUS     mandatory
   DESCRIPTION
     "This variable is used as the basis for SNMP naming of
      lpJT2 components.
      These components can be added and deleted."
::= { lpJT2RowStatusEntry 1 }

lpJT2ComponentName OBJECT-TYPE
   SYNTAX     DisplayString 
   ACCESS     read-only
   STATUS     mandatory
   DESCRIPTION
     "This variable provides the component's string name for
      use with the ASCII Console Interface"
::= { lpJT2RowStatusEntry 2 }

lpJT2StorageType OBJECT-TYPE
   SYNTAX     StorageType 
   ACCESS     read-only
   STATUS     mandatory
   DESCRIPTION
     "This variable represents the storage type value for the
      lpJT2 tables."
::= { lpJT2RowStatusEntry 4 }

lpJT2Index OBJECT-TYPE
   SYNTAX     Integer32 (0..1)
   ACCESS     not-accessible
   STATUS     mandatory
   DESCRIPTION
     "This variable represents the index for the lpJT2 tables."
::= { lpJT2RowStatusEntry 10 }

lpJT2CidDataTable OBJECT-TYPE
   SYNTAX     SEQUENCE OF LpJT2CidDataEntry
   ACCESS     not-accessible
   STATUS     mandatory
   DESCRIPTION
     "This group contains the attribute for a component's Customer 
      Identifier (CID). Refer to the attribute description for a detailed 
      explanation of CIDs."
::= { lpJT2 10 }

lpJT2CidDataEntry OBJECT-TYPE
   SYNTAX     LpJT2CidDataEntry
   ACCESS     not-accessible
   STATUS     mandatory
   DESCRIPTION
     "An entry in the lpJT2CidDataTable."
   INDEX {
      lpIndex,
      lpJT2Index }
::= { lpJT2CidDataTable 1 }

LpJT2CidDataEntry ::= SEQUENCE {
   lpJT2CustomerIdentifier
      Unsigned32 }

lpJT2CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpJT2CidDataEntry 1 }

lpJT2ProvTable OBJECT-TYPE
   SYNTAX     SEQUENCE OF LpJT2ProvEntry
   ACCESS     not-accessible
   STATUS     mandatory
   DESCRIPTION
     "This group contains all of the JT2 specific provisioning data for a 
      JT2 component."
::= { lpJT2 11 }

lpJT2ProvEntry OBJECT-TYPE
   SYNTAX     LpJT2ProvEntry
   ACCESS     not-accessible
   STATUS     mandatory
   DESCRIPTION
     "An entry in the lpJT2ProvTable."
   INDEX {
      lpIndex,
      lpJT2Index }
::= { lpJT2ProvTable 1 }

LpJT2ProvEntry ::= SEQUENCE {
   lpJT2ClockingSource
      INTEGER,
   lpJT2LineLength
      Unsigned32,
   lpJT2ApplicationFramerName
      Link }

lpJT2ClockingSource OBJECT-TYPE
   SYNTAX     INTEGER  {
                 local(0),
                 line(1),
                 module(2),
                 otherPort(4) }
   ACCESS     read-write
   STATUS     mandatory
   DESCRIPTION
     "This attribute defines the source of the transmit clock for the JT2 
      line.
      When the clocking source is selected from local, the oscillator on 
      the port generates the clocking for the line.
      When the clocking source is selected from line, the port 
      synchronizes to the clock recovered from the incoming line signal.
      When the clocking source is selected from module, the port's clock 
      synchronizes to the clock provided by the oscillator on the active 
      CP.
      Note:- that when one port is set to local, the other port must also be 
      set to local, and when one port is set to module, the other port must 
      also be set to module. If one of the ports is set to line, the other port 
      must be set to otherPort.
      Also, if a CP reference clock is available when the JT2 component 
      is added, the clocking source defaults to module, whereas if a CP 
      reference clock is not available when the component is added, the 
      clocking source defaults to local."
::= { lpJT2ProvEntry 1 }

lpJT2LineLength OBJECT-TYPE
   SYNTAX     Unsigned32 (0..480)
   ACCESS     read-write
   STATUS     mandatory
   DESCRIPTION
     "This attribute defines the line length for equalization calculations 
      for the JT2 line. The range is between 0 and 480 feet (1 metre = 
      3.28 feet)."
   DEFVAL     { 0 }
::= { lpJT2ProvEntry 2 }

lpJT2ApplicationFramerName OBJECT-TYPE
   SYNTAX     Link 
   ACCESS     read-write
   STATUS     mandatory
   DESCRIPTION
     "This attribute defines the link to the software stack. It defines which 
      application is running on top of the JT2 component."
::= { lpJT2ProvEntry 3 }

lpJT2IfEntryTable OBJECT-TYPE
   SYNTAX     SEQUENCE OF LpJT2IfEntryEntry
   ACCESS     not-accessible
   STATUS     mandatory
   DESCRIPTION
     "This group contains the provisionable attributes for the ifEntry."
::= { lpJT2 12 }

lpJT2IfEntryEntry OBJECT-TYPE
   SYNTAX     LpJT2IfEntryEntry
   ACCESS     not-accessible
   STATUS     mandatory
   DESCRIPTION
     "An entry in the lpJT2IfEntryTable."
   INDEX {
      lpIndex,
      lpJT2Index }
::= { lpJT2IfEntryTable 1 }

LpJT2IfEntryEntry ::= SEQUENCE {
   lpJT2IfAdminStatus
      INTEGER,
   lpJT2IfIndex
      InterfaceIndex }

lpJT2IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpJT2IfEntryEntry 1 }

lpJT2IfIndex OBJECT-TYPE
   SYNTAX     InterfaceIndex (1..65535)
   ACCESS     read-only
   STATUS     mandatory
   DESCRIPTION
     "This is the index for the IfEntry. Its value is automatically initialized 
      during the provisioning process."
::= { lpJT2IfEntryEntry 2 }

lpJT2OperStatusTable OBJECT-TYPE
   SYNTAX     SEQUENCE OF LpJT2OperStatusEntry
   ACCESS     not-accessible
   STATUS     mandatory
   DESCRIPTION
     "This group includes the Operational Status attribute. This attribute 
      defines the current operational state of this component."
::= { lpJT2 13 }

lpJT2OperStatusEntry OBJECT-TYPE
   SYNTAX     LpJT2OperStatusEntry
   ACCESS     not-accessible
   STATUS     mandatory
   DESCRIPTION
     "An entry in the lpJT2OperStatusTable."
   INDEX {
      lpIndex,
      lpJT2Index }
::= { lpJT2OperStatusTable 1 }

LpJT2OperStatusEntry ::= SEQUENCE {
   lpJT2SnmpOperStatus
      INTEGER }

lpJT2SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpJT2OperStatusEntry 1 }

lpJT2StateTable OBJECT-TYPE
   SYNTAX     SEQUENCE OF LpJT2StateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpJT2 14 }

lpJT2StateEntry OBJECT-TYPE
   SYNTAX     LpJT2StateEntry
   ACCESS     not-accessible
   STATUS     mandatory
   DESCRIPTION
     "An entry in the lpJT2StateTable."
   INDEX {
      lpIndex,
      lpJT2Index }
::= { lpJT2StateTable 1 }

LpJT2StateEntry ::= SEQUENCE {
   lpJT2AdminState
      INTEGER,
   lpJT2OperationalState
      INTEGER,
   lpJT2UsageState
      INTEGER,
   lpJT2AvailabilityStatus
      OCTET STRING,
   lpJT2ProceduralStatus
      OCTET STRING,
   lpJT2ControlStatus
      OCTET STRING,
   lpJT2AlarmStatus
      OCTET STRING,
   lpJT2StandbyStatus
      INTEGER,
   lpJT2UnknownStatus
      INTEGER }

lpJT2AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpJT2StateEntry 1 }

lpJT2OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpJT2StateEntry 2 }

lpJT2UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpJT2StateEntry 3 }

lpJT2AvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpJT2StateEntry 4 }

lpJT2ProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpJT2StateEntry 5 }

lpJT2ControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpJT2StateEntry 6 }

lpJT2AlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpJT2StateEntry 7 }

lpJT2StandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpJT2StateEntry 8 }

lpJT2UnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpJT2StateEntry 9 }

lpJT2OperTable OBJECT-TYPE
   SYNTAX     SEQUENCE OF LpJT2OperEntry
   ACCESS     not-accessible
   STATUS     mandatory
   DESCRIPTION
     "This group contains the JT2 specific operational data for a JT2 
      component in a digital hierarchy interface."
::= { lpJT2 15 }

lpJT2OperEntry OBJECT-TYPE
   SYNTAX     LpJT2OperEntry
   ACCESS     not-accessible
   STATUS     mandatory
   DESCRIPTION
     "An entry in the lpJT2OperTable."
   INDEX {
      lpIndex,
      lpJT2Index }
::= { lpJT2OperTable 1 }

LpJT2OperEntry ::= SEQUENCE {
   lpJT2LosAlarm
      INTEGER,
   lpJT2LofAlarm
      INTEGER,
   lpJT2RxAisPhysicalAlarm
      INTEGER,
   lpJT2RxAisPayloadAlarm
      INTEGER,
   lpJT2RxRaiAlarm
      INTEGER,
   lpJT2TxAisPhysicalAlarm
      INTEGER,
   lpJT2TxRaiAlarm
      INTEGER }

lpJT2LosAlarm OBJECT-TYPE
   SYNTAX     INTEGER  {
                 on(0),
                 off(1) }
   ACCESS     read-only
   STATUS     mandatory
   DESCRIPTION
     "This attribute displays whether a LOS (Loss of Signal) alarm state 
      is entered. An LOS alarm state is entered when LOS defects have 
      been observed and accumulated for a period of 2.5 seconds +/- 0.5 
      seconds. An LOS defect is declared at the JT2 line interface when 
      the input data is zero for 20 - 32 clock cycles. If the LOS defects are 
      intermittently occurring, the LOS defect accumulator is 
      decremented at a rate of 1/10 of the incrementing rate (alarm 
      integration ratio of 1/10), with all measurements based on a 200 ms 
      polling cycle.
      An LOS failure alarm is cleared when the LOS defect is absent for a 
      period of 10 seconds +/- 0.5 seconds. The JT2 port goes into an 
      operationalState of disabled for the duration of the LOS alarm 
      condition. While the port is in the LOS alarm state, the port also 
      transmits the far-end RAI defect indicator on the out-going JT2 line."
   DEFVAL     { off }
::= { lpJT2OperEntry 1 }

lpJT2LofAlarm OBJECT-TYPE
   SYNTAX     INTEGER  {
                 on(0),
                 off(1) }
   ACCESS     read-only
   STATUS     mandatory
   DESCRIPTION
     "This attribute indicates whether a LOF (Loss of Frame) alarm state 
      is entered. A LOF alarm state is entered when LOF defects are 
      observed and accumulated for 2.5 seconds +/- 0.5 seconds or more. 
      A LOF defect occurs when seven or more consecutive incorrect 
      frame alignment patterns (4 multiframes) are received. If the LOF 
      defects are intermittently occurring, the LOF defect accumulator is 
      decremented at a rate of 1/10 of the incrementing rate (alarm 
      integration ratio of 1/10), with all measurements based on a 200 ms 
      polling cycle.
      The LOF alarm is cleared when framing has been achieved for 10 
      seconds +/- 0.5 seconds. The port goes into an operationalState of 
      disabled for the duration of the LOF alarm condition. While the 
      port is in the LOF alarm state, the node also transmits the far-end 
      RAI defect indicator on the out-going JT2 line."
   DEFVAL     { off }
::= { lpJT2OperEntry 2 }

lpJT2RxAisPhysicalAlarm OBJECT-TYPE
   SYNTAX     INTEGER  {
                 on(0),
                 off(1) }
   ACCESS     read-only
   STATUS     mandatory
   DESCRIPTION
     "This attribute indicates whether a Physical AIS alarm state is 
      entered. A Physical AIS alarm state is entered when a Physical AIS 
      defect is observed and accumulated for a period of 2.5 seconds +/- 
      0.5 seconds. A Physical AIS defect is declared when the incoming 
      signal has two or less zeros in a sequence of 3,156 bits (0.5 ms). If 
      the physical AIS defects are intermittently occurring, the physical 
      AIS defect accumulator is decremented at a rate of 1/10 of the 
      incrementing rate (alarm integration ratio of 1/10), with all 
      measurements based on a 200 ms polling cycle.
      A Physical AIS alarm is cleared when the Physical AIS defect is 
      absent for a period of 10 seconds +/- 0.5 seconds. The port goes 
      into an operationalState of disabled until the AIS alarm condition is 
      cleared. While the port is in the Physical AIS alarm state, the node 
      also transmits the far-end RAI defect indicator on the out-going JT2 
      line."
   DEFVAL     { off }
::= { lpJT2OperEntry 3 }

lpJT2RxAisPayloadAlarm OBJECT-TYPE
   SYNTAX     INTEGER  {
                 on(0),
                 off(1) }
   ACCESS     read-only
   STATUS     mandatory
   DESCRIPTION
     "This attribute indicates whether a Payload AIS alarm state is 
      entered. A Payload AIS alarm state is entered when a Payload AIS 
      defect persists for a period of 2.5 seconds +/- 0.5 seconds. A 
      Payload AIS defect is declared when the incoming signal of the 
      6312 kbit/s frame payload (TS1 - TS96) has two or less zeros in a 
      sequence of 3,072 bits (0.5 ms). If the payload AIS defects are 
      intermittently occurring, the payload AIS defect accumulator is 
      decremented at a rate of 1/10 of the incrementing rate (alarm 
      integration ratio of 1/10), with all measurements based on a 200 ms 
      polling cycle.
      A Payload AIS failure alarm is cleared when the Payload AIS 
      defect is absent for a period of 10 seconds +/- 0.5 seconds. The port 
      goes into an operationalState of disabled until the AIS alarm 
      condition is cleared. While the port is in the Payload AIS alarm 
      state, the node also transmits the far-end RAI defect indicator on the 
      out-going JT2 line."
   DEFVAL     { off }
::= { lpJT2OperEntry 4 }

lpJT2RxRaiAlarm OBJECT-TYPE
   SYNTAX     INTEGER  {
                 on(0),
                 off(1) }
   ACCESS     read-only
   STATUS     mandatory
   DESCRIPTION
     "This attribute indicates whether a Received RAI alarm state is 
      entered. A received RAI alarm state is entered when the RAI signal 
      is detected on the incoming JT2 Line (when 16 or more consecutive 
      RAI patterns of 1111111100000000 are received on the 4 kbit/s 
      data channel (m-bits) within the framing bits of the JT2 frame). The 
      JT2 port goes into an operationalState of Disabled until the RAI 
      alarm condition is cleared. The RAI alarm is cleared when four or 
      more consecutive non-RAI patterns (anything other than 
      1111111100000000) are received."
   DEFVAL     { off }
::= { lpJT2OperEntry 5 }

lpJT2TxAisPhysicalAlarm OBJECT-TYPE
   SYNTAX     INTEGER  {
                 on(0),
                 off(1) }
   ACCESS     read-only
   STATUS     mandatory
   DESCRIPTION
     "This attribute indicates whether an AIS (Alarm Indication Signal) 
      alarm is being transmitted on the outgoing JT2 line. Currently the 
      JT2 port only transmits a Physical AIS (no Payload AIS) on the 
      outgoing JT2 line. 
      Since there is no Idle signal defined for JT2, the AIS signal is 
      transmitted when the JT2 port is in the operationalState of locked. 
      The AIS signal may also be transmitted for diagnostic testing."
   DEFVAL     { off }
::= { lpJT2OperEntry 6 }

lpJT2TxRaiAlarm OBJECT-TYPE
   SYNTAX     INTEGER  {
                 on(0),
                 off(1) }
   ACCESS     read-only
   STATUS     mandatory
   DESCRIPTION
     "This attribute indicates whether an RAI defect indication pattern is 
      being sent on the out-going JT2 line. The RAI alarm pattern is 
      transmitted in the 4 kbit/s data channel (m-bits) when the port 
      detects a LOS, AIS or LOF alarm condition."
   DEFVAL     { off }
::= { lpJT2OperEntry 7 }

lpJT2StatsTable OBJECT-TYPE
   SYNTAX     SEQUENCE OF LpJT2StatsEntry
   ACCESS     not-accessible
   STATUS     mandatory
   DESCRIPTION
     "This group contains the statistical data for a JT2 component in a 
      digital hierarchy interface."
::= { lpJT2 16 }

lpJT2StatsEntry OBJECT-TYPE
   SYNTAX     LpJT2StatsEntry
   ACCESS     not-accessible
   STATUS     mandatory
   DESCRIPTION
     "An entry in the lpJT2StatsTable."
   INDEX {
      lpIndex,
      lpJT2Index }
::= { lpJT2StatsTable 1 }

LpJT2StatsEntry ::= SEQUENCE {
   lpJT2RunningTime
      Counter32,
   lpJT2ErrorFreeSec
      Counter32,
   lpJT2ErroredSec
      Counter32,
   lpJT2SevErroredSec
      Counter32,
   lpJT2SevErroredFrmSec
      Counter32,
   lpJT2UnavailSec
      Counter32,
   lpJT2BpvErrors
      Counter32,
   lpJT2CrcErrors
      Counter32,
   lpJT2FrameErrors
      Counter32,
   lpJT2LosStateChanges
      Counter32 }

lpJT2RunningTime OBJECT-TYPE
   SYNTAX     Counter32 
   ACCESS     read-only
   STATUS     mandatory
   DESCRIPTION
     "This attribute indicates the number of seconds since the JT2 
      component was activated and placed in an unlocked state or used for 
      operational testing. All the other error counts that follow as well as 
      each JT2 subcomponent's error counts can be updated when this 
      count is active."
::= { lpJT2StatsEntry 1 }

lpJT2ErrorFreeSec OBJECT-TYPE
   SYNTAX     Counter32 
   ACCESS     read-only
   STATUS     mandatory
   DESCRIPTION
     "This attribute indicates the number of seconds that the JT2 port has 
      been in an error free state."
::= { lpJT2StatsEntry 2 }

lpJT2ErroredSec OBJECT-TYPE
   SYNTAX     Counter32 
   ACCESS     read-only
   STATUS     mandatory
   DESCRIPTION
     "This attribute indicates the total number of errored seconds for the 
      JT2 port. An errored second is declared when a second with one or 
      more Code Violation Error events, or one or more LOF or LOS 
      defects occur. A code violation error may be a cyclic redundancy 
      check (CRC) error or a bipolar violation (BPV) error."
::= { lpJT2StatsEntry 3 }

lpJT2SevErroredSec OBJECT-TYPE
   SYNTAX     Counter32 
   ACCESS     read-only
   STATUS     mandatory
   DESCRIPTION
     "This attribute indicates the total number of severely errored seconds 
      for the JT2 port. A severely errored second occurs when a second 
      with 255 or more Code Violation Error events or one or more LOF 
      or LOS defects occur."
::= { lpJT2StatsEntry 4 }

lpJT2SevErroredFrmSec OBJECT-TYPE
   SYNTAX     Counter32 
   ACCESS     read-only
   STATUS     mandatory
   DESCRIPTION
     "This attribute indicates the total number of severely errored framing 
      seconds for the JT2 port. A severely errored framing second occurs 
      when a second with one or more Framing Errors occur."
::= { lpJT2StatsEntry 5 }

lpJT2UnavailSec OBJECT-TYPE
   SYNTAX     Counter32 
   ACCESS     read-only
   STATUS     mandatory
   DESCRIPTION
     "This attribute indicates the total number of seconds that the 
      interface has been in an unavailable state. An unavailable state 
      occurs at the onset of 10 consecutive Severely Errored Seconds. 
      When the unavailable state is entered, the 10 Severely Errored 
      Seconds are immediately transfered to the count of 
      unavailableSeconds by incrementing the count of unavailSec by 10 
      and decrementing the count of sevErroredSec by 10. Whilst in the 
      unavailable state, an unavailableSecond is counted for each SES or 
      SEFS that occurs, and the count of SES and SEFS are both 
      inhibited. The unavailable state is cleared at the onset of 10 
      consecutive seconds which are not Severely Errored Seconds."
::= { lpJT2StatsEntry 6 }

lpJT2BpvErrors OBJECT-TYPE
   SYNTAX     Counter32 
   ACCESS     read-only
   STATUS     mandatory
   DESCRIPTION
     "This attribute indicates the total count of bipolar violations (BPV). 
      A bipolar violation is an error in the alternate mark inversion pattern 
      (AMI) on the line. The value of this attribute will wrap to zero when 
      it reaches its maximum value."
::= { lpJT2StatsEntry 7 }

lpJT2CrcErrors OBJECT-TYPE
   SYNTAX     Counter32 
   ACCESS     read-only
   STATUS     mandatory
   DESCRIPTION
     "This attribute indicates the total number of cyclic redundancy check 
      (CRC-5) errors detected on the incoming JT2 line. The value of this 
      attribute will wrap to 0 when its maximum value is reached."
::= { lpJT2StatsEntry 8 }

lpJT2FrameErrors OBJECT-TYPE
   SYNTAX     Counter32 
   ACCESS     read-only
   STATUS     mandatory
   DESCRIPTION
     "This attribute indicates the total number of Framing Errors that have 
      occured on the JT2 port. A Framing Error is an error in the framing 
      bits. The value of this attribute will wrap to 0 when its maximum 
      value is reached."
::= { lpJT2StatsEntry 9 }

lpJT2LosStateChanges OBJECT-TYPE
   SYNTAX     Counter32 
   ACCESS     read-only
   STATUS     mandatory
   DESCRIPTION
     "This attribute indicates the total number of times that the incoming 
      signal on the JT2 line has been lost. The value of this attribute will 
      wrap to 0 when its maximum value is reached."
::= { lpJT2StatsEntry 10 }

lpJT2AdminInfoTable OBJECT-TYPE
   SYNTAX     SEQUENCE OF LpJT2AdminInfoEntry
   ACCESS     not-accessible
   STATUS     mandatory
   DESCRIPTION
     "This group contains the attributes pertaining to the vendor of the 
      equipment."
::= { lpJT2 17 }

lpJT2AdminInfoEntry OBJECT-TYPE
   SYNTAX     LpJT2AdminInfoEntry
   ACCESS     not-accessible
   STATUS     mandatory
   DESCRIPTION
     "An entry in the lpJT2AdminInfoTable."
   INDEX {
      lpIndex,
      lpJT2Index }
::= { lpJT2AdminInfoTable 1 }

LpJT2AdminInfoEntry ::= SEQUENCE {
   lpJT2Vendor
      AsciiString,
   lpJT2CommentText
      AsciiString }

lpJT2Vendor OBJECT-TYPE
   SYNTAX     AsciiString (SIZE (0..20))
   ACCESS     read-write
   STATUS     mandatory
   DESCRIPTION
     "This is the name of the vendor supplying the facility."
::= { lpJT2AdminInfoEntry 1 }

lpJT2CommentText OBJECT-TYPE
   SYNTAX     AsciiString (SIZE (0..60))
   ACCESS     read-write
   STATUS     mandatory
   DESCRIPTION
     "Any miscellaneous text about the facility."
::= { lpJT2AdminInfoEntry 2 }


-- 
-- The Test component is configured to control a hardware facility test 
-- on a physical (V35, X21, DS1, E1, DS3, E3 etc.) or a logical port.

lpJT2Test OBJECT IDENTIFIER ::= { lpJT2 2 }



lpJT2TestRowStatusTable OBJECT-TYPE
   SYNTAX     SEQUENCE OF LpJT2TestRowStatusEntry
   ACCESS     not-accessible
   STATUS     mandatory
   DESCRIPTION
     "This entry controls the addition and deletion of 
      lpJT2Test components."
::= { lpJT2Test 1 }

lpJT2TestRowStatusEntry OBJECT-TYPE
   SYNTAX     LpJT2TestRowStatusEntry
   ACCESS     not-accessible
   STATUS     mandatory
   DESCRIPTION
     "A single entry in the table represents a single 
      lpJT2Test component."
   INDEX {
      lpIndex,
      lpJT2Index,
      lpJT2TestIndex }
::= { lpJT2TestRowStatusTable 1 }

LpJT2TestRowStatusEntry ::= SEQUENCE {
   lpJT2TestRowStatus
      RowStatus,
   lpJT2TestComponentName
      DisplayString,
   lpJT2TestStorageType
      StorageType,
   lpJT2TestIndex
      NonReplicated }

lpJT2TestRowStatus OBJECT-TYPE
   SYNTAX     RowStatus 
   ACCESS     read-only
   STATUS     mandatory
   DESCRIPTION
     "This variable is used as the basis for SNMP naming of
      lpJT2Test components.
      These components cannot be added nor deleted."
::= { lpJT2TestRowStatusEntry 1 }

lpJT2TestComponentName OBJECT-TYPE
   SYNTAX     DisplayString 
   ACCESS     read-only
   STATUS     mandatory
   DESCRIPTION
     "This variable provides the component's string name for
      use with the ASCII Console Interface"
::= { lpJT2TestRowStatusEntry 2 }

lpJT2TestStorageType OBJECT-TYPE
   SYNTAX     StorageType 
   ACCESS     read-only
   STATUS     mandatory
   DESCRIPTION
     "This variable represents the storage type value for the
      lpJT2Test tables."
::= { lpJT2TestRowStatusEntry 4 }

lpJT2TestIndex OBJECT-TYPE
   SYNTAX     NonReplicated 
   ACCESS     not-accessible
   STATUS     mandatory
   DESCRIPTION
     "This variable represents the index for the lpJT2Test tables."
::= { lpJT2TestRowStatusEntry 10 }

lpJT2TestStateTable OBJECT-TYPE
   SYNTAX     SEQUENCE OF LpJT2TestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpJT2Test 10 }

lpJT2TestStateEntry OBJECT-TYPE
   SYNTAX     LpJT2TestStateEntry
   ACCESS     not-accessible
   STATUS     mandatory
   DESCRIPTION
     "An entry in the lpJT2TestStateTable."
   INDEX {
      lpIndex,
      lpJT2Index,
      lpJT2TestIndex }
::= { lpJT2TestStateTable 1 }

LpJT2TestStateEntry ::= SEQUENCE {
   lpJT2TestAdminState
      INTEGER,
   lpJT2TestOperationalState
      INTEGER,
   lpJT2TestUsageState
      INTEGER }

lpJT2TestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpJT2TestStateEntry 1 }

lpJT2TestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpJT2TestStateEntry 2 }

lpJT2TestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpJT2TestStateEntry 3 }

lpJT2TestSetupTable OBJECT-TYPE
   SYNTAX     SEQUENCE OF LpJT2TestSetupEntry
   ACCESS     not-accessible
   STATUS     mandatory
   DESCRIPTION
     "This group contains all of the operational data for a Test 
      component."
::= { lpJT2Test 11 }

lpJT2TestSetupEntry OBJECT-TYPE
   SYNTAX     LpJT2TestSetupEntry
   ACCESS     not-accessible
   STATUS     mandatory
   DESCRIPTION
     "An entry in the lpJT2TestSetupTable."
   INDEX {
      lpIndex,
      lpJT2Index,
      lpJT2TestIndex }
::= { lpJT2TestSetupTable 1 }

LpJT2TestSetupEntry ::= SEQUENCE {
   lpJT2TestPurpose
      AsciiString,
   lpJT2TestType
      INTEGER,
   lpJT2TestFrmSize
      Unsigned32,
   lpJT2TestFrmPatternType
      INTEGER,
   lpJT2TestCustomizedPattern
      Hex,
   lpJT2TestDataStartDelay
      Unsigned32,
   lpJT2TestDisplayInterval
      Unsigned32,
   lpJT2TestDuration
      Unsigned32 }

lpJT2TestPurpose OBJECT-TYPE
   SYNTAX     AsciiString (SIZE (0..40))
   ACCESS     read-write
   STATUS     mandatory
   DESCRIPTION
     "This attribute records the purpose of the test so that the test results 
      can be associated and properly analyzed."
::= { lpJT2TestSetupEntry 1 }

lpJT2TestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpJT2TestSetupEntry 2 }

lpJT2TestFrmSize OBJECT-TYPE
   SYNTAX     Unsigned32 (4..4096)
   ACCESS     read-write
   STATUS     mandatory
   DESCRIPTION
     "This attribute defines the size of the test data frames in number of 
      bytes."
   DEFVAL     { 1024 }
::= { lpJT2TestSetupEntry 3 }

lpJT2TestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpJT2TestSetupEntry 4 }

lpJT2TestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpJT2TestSetupEntry 5 }

lpJT2TestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpJT2TestSetupEntry 6 }

lpJT2TestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpJT2TestSetupEntry 7 }

lpJT2TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpJT2TestSetupEntry 8 }

lpJT2TestResultsTable OBJECT-TYPE
   SYNTAX     SEQUENCE OF LpJT2TestResultsEntry
   ACCESS     not-accessible
   STATUS     mandatory
   DESCRIPTION
     "This group contains all the statistics related attributes of the Test 
      component."
::= { lpJT2Test 12 }

lpJT2TestResultsEntry OBJECT-TYPE
   SYNTAX     LpJT2TestResultsEntry
   ACCESS     not-accessible
   STATUS     mandatory
   DESCRIPTION
     "An entry in the lpJT2TestResultsTable."
   INDEX {
      lpIndex,
      lpJT2Index,
      lpJT2TestIndex }
::= { lpJT2TestResultsTable 1 }

LpJT2TestResultsEntry ::= SEQUENCE {
   lpJT2TestElapsedTime
      Counter32,
   lpJT2TestTimeRemaining
      Unsigned32,
   lpJT2TestCauseOfTermination
      INTEGER,
   lpJT2TestBitsTx
      PassportCounter64,
   lpJT2TestBytesTx
      PassportCounter64,
   lpJT2TestFrmTx
      PassportCounter64,
   lpJT2TestBitsRx
      PassportCounter64,
   lpJT2TestBytesRx
      PassportCounter64,
   lpJT2TestFrmRx
      PassportCounter64,
   lpJT2TestErroredFrmRx
      PassportCounter64,
   lpJT2TestBitErrorRate
      AsciiString }

lpJT2TestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpJT2TestResultsEntry 1 }

lpJT2TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpJT2TestResultsEntry 2 }

lpJT2TestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpJT2TestResultsEntry 3 }

lpJT2TestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpJT2TestResultsEntry 4 }

lpJT2TestBytesTx OBJECT-TYPE
   SYNTAX     PassportCounter64 
   ACCESS     read-only
   STATUS     mandatory
   DESCRIPTION
     "This attribute is the total number of bytes sent during the test 
      period. This counter is not expected to reach its maximum value."
::= { lpJT2TestResultsEntry 5 }

lpJT2TestFrmTx OBJECT-TYPE
   SYNTAX     PassportCounter64 
   ACCESS     read-only
   STATUS     mandatory
   DESCRIPTION
     "This attribute is the total number of frames sent during the test 
      period. This counter is not expected to reach its maximum value."
::= { lpJT2TestResultsEntry 6 }

lpJT2TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpJT2TestResultsEntry 7 }

lpJT2TestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpJT2TestResultsEntry 8 }

lpJT2TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpJT2TestResultsEntry 9 }

lpJT2TestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpJT2TestResultsEntry 10 }

lpJT2TestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpJT2TestResultsEntry 11 }


-- 
-- The AtmCell is a component that contains provisioning and 
-- operational attributes. The provisioning attributes are used to set the 
-- Loss of Cell Deliniation (LCD) alarm activation delay and to turn 
-- cell payload scrambling on or off. The operational attributes are 
-- used to report about the quality of the ATM cells received by the 
-- interface and the cell capacity utilization. The AtmCell component 
-- appears under all port components running on ATM cards.

lpJT2Cell OBJECT IDENTIFIER ::= { lpJT2 3 }



lpJT2CellRowStatusTable OBJECT-TYPE
   SYNTAX     SEQUENCE OF LpJT2CellRowStatusEntry
   ACCESS     not-accessible
   STATUS     mandatory
   DESCRIPTION
     "This entry controls the addition and deletion of 
      lpJT2Cell components."
::= { lpJT2Cell 1 }

lpJT2CellRowStatusEntry OBJECT-TYPE
   SYNTAX     LpJT2CellRowStatusEntry
   ACCESS     not-accessible
   STATUS     mandatory
   DESCRIPTION
     "A single entry in the table represents a single 
      lpJT2Cell component."
   INDEX {
      lpIndex,
      lpJT2Index,
      lpJT2CellIndex }
::= { lpJT2CellRowStatusTable 1 }

LpJT2CellRowStatusEntry ::= SEQUENCE {
   lpJT2CellRowStatus
      RowStatus,
   lpJT2CellComponentName
      DisplayString,
   lpJT2CellStorageType
      StorageType,
   lpJT2CellIndex
      NonReplicated }

lpJT2CellRowStatus OBJECT-TYPE
   SYNTAX     RowStatus 
   ACCESS     read-only
   STATUS     mandatory
   DESCRIPTION
     "This variable is used as the basis for SNMP naming of
      lpJT2Cell components.
      These components cannot be added nor deleted."
::= { lpJT2CellRowStatusEntry 1 }

lpJT2CellComponentName OBJECT-TYPE
   SYNTAX     DisplayString 
   ACCESS     read-only
   STATUS     mandatory
   DESCRIPTION
     "This variable provides the component's string name for
      use with the ASCII Console Interface"
::= { lpJT2CellRowStatusEntry 2 }

lpJT2CellStorageType OBJECT-TYPE
   SYNTAX     StorageType 
   ACCESS     read-only
   STATUS     mandatory
   DESCRIPTION
     "This variable represents the storage type value for the
      lpJT2Cell tables."
::= { lpJT2CellRowStatusEntry 4 }

lpJT2CellIndex OBJECT-TYPE
   SYNTAX     NonReplicated 
   ACCESS     not-accessible
   STATUS     mandatory
   DESCRIPTION
     "This variable represents the index for the lpJT2Cell tables."
::= { lpJT2CellRowStatusEntry 10 }

lpJT2CellProvTable OBJECT-TYPE
   SYNTAX     SEQUENCE OF LpJT2CellProvEntry
   ACCESS     not-accessible
   STATUS     mandatory
   DESCRIPTION
     "This group contains the provisioning attributes for the AtmCell 
      component."
::= { lpJT2Cell 10 }

lpJT2CellProvEntry OBJECT-TYPE
   SYNTAX     LpJT2CellProvEntry
   ACCESS     not-accessible
   STATUS     mandatory
   DESCRIPTION
     "An entry in the lpJT2CellProvTable."
   INDEX {
      lpIndex,
      lpJT2Index,
      lpJT2CellIndex }
::= { lpJT2CellProvTable 1 }

LpJT2CellProvEntry ::= SEQUENCE {
   lpJT2CellAlarmActDelay
      Unsigned32,
   lpJT2CellScrambleCellPayload
      INTEGER,
   lpJT2CellCorrectSingleBitHeaderErrors
      INTEGER }

lpJT2CellAlarmActDelay OBJECT-TYPE
   SYNTAX     Unsigned32 (0..2000)
   ACCESS     read-write
   STATUS     mandatory
   DESCRIPTION
     "This attribute defines the time during which a Loss of Cell 
      Delineation (LCD) defect should be observed before declaring an 
      LCD alarm (alarm 70115501). The time is specified in milliseconds."
   DEFVAL     { 500 }
::= { lpJT2CellProvEntry 1 }

lpJT2CellScrambleCellPayload OBJECT-TYPE
   SYNTAX     INTEGER  {
                 off(0),
                 on(1) }
   ACCESS     read-write
   STATUS     mandatory
   DESCRIPTION
     "Cell scrambling, as defined by  ITU-T Recommendation I.432., can 
      provide a solution to the problem of transmission equipment which 
      is sensitive to certain bit patterns in the ATM cell payload. This 
      attribute controls whether or not the cell payload is scrambled.
      It defaults to off for DS1 interfaces, and on for all other interfaces.
      Note that this setting must be the same at both ends of the link."
::= { lpJT2CellProvEntry 2 }

lpJT2CellCorrectSingleBitHeaderErrors OBJECT-TYPE
   SYNTAX     INTEGER  {
                 off(0),
                 on(1) }
   ACCESS     read-write
   STATUS     mandatory
   DESCRIPTION
     "This attribute specifies whether the port corrects single bit errors 
      detected in the headers of received cells. If single bit errors are 
      corrected, the affected cells are passed up to the ATM layer 
      according to normal operation. If single bit errors are not corrected, 
      these errored cells are discarded by the physical layer. Note that 
      cells containing multiple bit errors in their headers are always 
      discarded.
      
      Single bit HEC error correction must remain off for the following 
      card types: 3pDS1Atm, 8pDS1Atm, 3pE1Atm, 8pE1Atm, 
      2pJ6MAtm, 3pDS3Atm, and 3pE3Atm."
   DEFVAL     { off }
::= { lpJT2CellProvEntry 3 }

lpJT2CellOperTable OBJECT-TYPE
   SYNTAX     SEQUENCE OF LpJT2CellOperEntry
   ACCESS     not-accessible
   STATUS     mandatory
   DESCRIPTION
     "This group contains the common operational attributes for the 
      AtmCell component."
::= { lpJT2Cell 11 }

lpJT2CellOperEntry OBJECT-TYPE
   SYNTAX     LpJT2CellOperEntry
   ACCESS     not-accessible
   STATUS     mandatory
   DESCRIPTION
     "An entry in the lpJT2CellOperTable."
   INDEX {
      lpIndex,
      lpJT2Index,
      lpJT2CellIndex }
::= { lpJT2CellOperTable 1 }

LpJT2CellOperEntry ::= SEQUENCE {
   lpJT2CellLcdAlarm
      INTEGER }

lpJT2CellLcdAlarm OBJECT-TYPE
   SYNTAX     INTEGER  {
                 on(0),
                 off(1) }
   ACCESS     read-only
   STATUS     mandatory
   DESCRIPTION
     "This attribute displays whether the Loss of Cell Delineation (LCD) 
      failure alarm state has been entered. This state is entered when LCD 
      defects have been observed and accumulated for a period of time 
      specified through the alarmActDelay attribute.
      In ATM cell direct mapping mode, an LCD defect occurs when Out 
      of Cell Delineation (OCD) anomaly persists for x milliseconds, and 
      disappears when the Out of Cell Delineation (OCD) is absent for x 
      msec. An OCD anomaly occurs when 7 consecutive incorrect HECs 
      have been detected. An OCD anomaly terminates when 6 
      consecutive correct HECs have been detected.
      For an AtmCell component located under a DS3 or E3 component 
      with mapping = PLCP, the LCD defect is directly derived from the 
      PLCP LOF defect.
      If LCD defects are intermittently occurring, the LCD defect 
      accumulator is decremented at a rate of 1/10 of the incrementing 
      rate (alarm integration ratio of 1/10), with all measurements based 
      on a 200 ms polling cycle
      The component under which is located the AtmCell component goes 
      into an operational state of disabled until the LCD alarm condition 
      is cleared. The condition is cleared after the LCD defect has not 
      been reported for a period of 10 seconds +/- 0.5 seconds.
      The lcdAlarm attribute is always set to off when the parent of the 
      AtmCell component has been locked and left offline. This can also 
      happen when the Path or Channel component has been suspended 
      since its parent has been locked."
   DEFVAL     { off }
::= { lpJT2CellOperEntry 1 }

lpJT2CellStatsTable OBJECT-TYPE
   SYNTAX     SEQUENCE OF LpJT2CellStatsEntry
   ACCESS     not-accessible
   STATUS     mandatory
   DESCRIPTION
     "This group contains the Statistics attribute for the AtmCell 
      component. Each attribute type is a non-negative integer which 
      monotonically increases until it reaches a maximum value, at which 
      point it wraps around and starts increasing again from zero."
::= { lpJT2Cell 12 }

lpJT2CellStatsEntry OBJECT-TYPE
   SYNTAX     LpJT2CellStatsEntry
   ACCESS     not-accessible
   STATUS     mandatory
   DESCRIPTION
     "An entry in the lpJT2CellStatsTable."
   INDEX {
      lpIndex,
      lpJT2Index,
      lpJT2CellIndex }
::= { lpJT2CellStatsTable 1 }

LpJT2CellStatsEntry ::= SEQUENCE {
   lpJT2CellUncorrectableHecErrors
      Counter32,
   lpJT2CellSevErroredSec
      Counter32,
   lpJT2CellReceiveCellUtilization
      Gauge32,
   lpJT2CellTransmitCellUtilization
      Gauge32,
   lpJT2CellCorrectableHeaderErrors
      Counter32 }

lpJT2CellUncorrectableHecErrors OBJECT-TYPE
   SYNTAX     Counter32 
   ACCESS     read-only
   STATUS     mandatory
   DESCRIPTION
     "This attribute indicates the number of uncorrectable ATM cell 
      header errors that have been detected. Counting of 
      uncorrectableHeaderErrors is inhibited when an Out of Cell 
      Delineation (OCD) defect is present. An OCD defect occurs when 
      seven consecutive incorrect HECs have been detected. An OCD 
      defect terminates when six consecutive correct HECs have been 
      detected."
::= { lpJT2CellStatsEntry 1 }

lpJT2CellSevErroredSec OBJECT-TYPE
   SYNTAX     Counter32 
   ACCESS     read-only
   STATUS     mandatory
   DESCRIPTION
     "This attribute indicates the total number of ATM Cell Severely 
      Errored Seconds (SESs) that have been counted. 
      
      In direct mapping mode, an ATM Cell SES is declared for second 
      intervals containing one or more Out of Cell Delineation (OCD) 
      defects. An OCD defect occurs when seven consecutive incorrect 
      HECs have been detected. An OCD defect terminates when six 
      consecutive correct HECs have been detected.
      
      In PLCP mapping mode, an ATM Cell SES is declared for second 
      intervals containing one or more PLCP LOF defects.
      
      Counting of uncorrectableHeaderErrors (ucErr) and 
      correctableHeaderErrors (cErr) is inhibited when the OCD defect 
      is present."
::= { lpJT2CellStatsEntry 2 }

lpJT2CellReceiveCellUtilization OBJECT-TYPE
   SYNTAX     Gauge32 (0..100)
   ACCESS     read-only
   STATUS     mandatory
   DESCRIPTION
     "This attribute is the ratio of the number of valid, assigned cells 
      received on the link to the nominal link capacity. The utilization is 
      calculated over a period of one minute.
      This attribute is always set to 0 when the parent of the AtmCell 
      component has been locked and left offline. This can also happen 
      when the Path or Channel component has been suspended since its 
      parent has been locked."
   DEFVAL     { 0 }
::= { lpJT2CellStatsEntry 3 }

lpJT2CellTransmitCellUtilization OBJECT-TYPE
   SYNTAX     Gauge32 (0..100)
   ACCESS     read-only
   STATUS     mandatory
   DESCRIPTION
     "This attribute is the ratio of the number of valid, assigned cells 
      transmitted on the link to the nominal link capacity. The utilization 
      is calculated over a period of one minute.
      This attribute is always set to 0 when the parent of the AtmCell 
      component has been locked and left offline. This can also happen 
      when the Path or Channel component has been suspended since its 
      parent has been locked."
   DEFVAL     { 0 }
::= { lpJT2CellStatsEntry 4 }

lpJT2CellCorrectableHeaderErrors OBJECT-TYPE
   SYNTAX     Counter32 
   ACCESS     read-only
   STATUS     mandatory
   DESCRIPTION
     "This attribute indicates the number of correctable ATM cell header 
      errors that have been detected and corrected. Counting of 
      correctableHeaderErrors is inhibited when an Out of Cell 
      Delineation (OCD) defect is present. An OCD defect occurs when 
      seven consecutive incorrect HECs have been detected. An OCD 
      defect terminates when six consecutive correct HECs have been 
      detected"
::= { lpJT2CellStatsEntry 5 }


-- 
-- Lp/m Hssi/0
-- 
-- The Hssi component controls a Passport HSSI interface.

lpHssi OBJECT IDENTIFIER ::= { lp 17 }



lpHssiRowStatusTable OBJECT-TYPE
   SYNTAX     SEQUENCE OF LpHssiRowStatusEntry
   ACCESS     not-accessible
   STATUS     mandatory
   DESCRIPTION
     "This entry controls the addition and deletion of 
      lpHssi components."
::= { lpHssi 1 }

lpHssiRowStatusEntry OBJECT-TYPE
   SYNTAX     LpHssiRowStatusEntry
   ACCESS     not-accessible
   STATUS     mandatory
   DESCRIPTION
     "A single entry in the table represents a single 
      lpHssi component."
   INDEX {
      lpIndex,
      lpHssiIndex }
::= { lpHssiRowStatusTable 1 }

LpHssiRowStatusEntry ::= SEQUENCE {
   lpHssiRowStatus
      RowStatus,
   lpHssiComponentName
      DisplayString,
   lpHssiStorageType
      StorageType,
   lpHssiIndex
      Integer32 }

lpHssiRowStatus OBJECT-TYPE
   SYNTAX     RowStatus 
   ACCESS     read-write
   STATUS     mandatory
   DESCRIPTION
     "This variable is used as the basis for SNMP naming of
      lpHssi components.
      These components can be added and deleted."
::= { lpHssiRowStatusEntry 1 }

lpHssiComponentName OBJECT-TYPE
   SYNTAX     DisplayString 
   ACCESS     read-only
   STATUS     mandatory
   DESCRIPTION
     "This variable provides the component's string name for
      use with the ASCII Console Interface"
::= { lpHssiRowStatusEntry 2 }

lpHssiStorageType OBJECT-TYPE
   SYNTAX     StorageType 
   ACCESS     read-only
   STATUS     mandatory
   DESCRIPTION
     "This variable represents the storage type value for the
      lpHssi tables."
::= { lpHssiRowStatusEntry 4 }

lpHssiIndex OBJECT-TYPE
   SYNTAX     Integer32 (0..0)
   ACCESS     not-accessible
   STATUS     mandatory
   DESCRIPTION
     "This variable represents the index for the lpHssi tables."
::= { lpHssiRowStatusEntry 10 }

lpHssiProvTable OBJECT-TYPE
   SYNTAX     SEQUENCE OF LpHssiProvEntry
   ACCESS     not-accessible
   STATUS     mandatory
   DESCRIPTION
     "This group contains the specific provisioning data for a Hssi 
      component."
::= { lpHssi 10 }

lpHssiProvEntry OBJECT-TYPE
   SYNTAX     LpHssiProvEntry
   ACCESS     not-accessible
   STATUS     mandatory
   DESCRIPTION
     "An entry in the lpHssiProvTable."
   INDEX {
      lpIndex,
      lpHssiIndex }
::= { lpHssiProvTable 1 }

LpHssiProvEntry ::= SEQUENCE {
   lpHssiLinkMode
      INTEGER,
   lpHssiReadyLineState
      OCTET STRING,
   lpHssiDataTransferLineState
      OCTET STRING,
   lpHssiLineSpeed
      Unsigned32,
   lpHssiApplicationFramerName
      Link }

lpHssiLinkMode OBJECT-TYPE
   SYNTAX     INTEGER  {
                 dte(0),
                 dce(128) }
   ACCESS     read-write
   STATUS     mandatory
   DESCRIPTION
     "This attribute defines the intended gender of the HSSI port. The 
      actual gender of the port is determined by the hardware setup.
      
      In dte mode, the ta line signal is driven as specified by the attribute 
      readyLineState when the HSSI port passes its diagnostics. The ta 
      line signal is then driven as specified by the attribute 
      dataTransferLineState when the application is ready to transfer 
      data. On the other hand, the input line signal ca is compared against 
      those specified in the attributes readyLineState and 
      dataTransferLineState. The application will be notified when the 
      specified input line states are observed. 
      
      In dce mode, the Hssi component behaves similarly as when it is in 
      dte mode. However, it will be driving the dce line signal (ca) and 
      monitoring the dte line signal (ta) as specified by the attributes 
      readyLineState and dataTransferLineState."
   DEFVAL     { dce }
::= { lpHssiProvEntry 1 }

lpHssiReadyLineState OBJECT-TYPE
   SYNTAX     OCTET STRING (SIZE (1))
   ACCESS     read-write
   STATUS     mandatory
   DESCRIPTION
     "This attribute specifies the line signal originating from the HSSI 
      interface that will always be turned on, provided the HSSI interface 
      passes it diagnostics. This set of signal is generally required for 
      maintaining the connection. Note that both dte and dce signals are 
      specified in this attribute. The appropriate set of specified signals 
      will be turned on or checked according to the operational attribute 
      actualLinkMode. See also linkMode.

      Description of bits:
      ca(0)
      ta(1)"
   DEFVAL     { 'c0'H }
::= { lpHssiProvEntry 2 }

lpHssiDataTransferLineState OBJECT-TYPE
   SYNTAX     OCTET STRING (SIZE (1))
   ACCESS     read-write
   STATUS     mandatory
   DESCRIPTION
     "This attribute specifies the line signals required to indicate that the 
      external equipment is in a good state (that is, data transfer can 
      proceed). Note that both dte and dce signals are specified in this 
      attribute. The appropriate set of specified signals will be turned on 
      or checked according to the operational attribute actualLinkMode. 
      The value of this attribute must be a superset of that of the 
      readyLineState attribute.
      See also linkMode.

      Description of bits:
      ca(0)
      ta(1)"
   DEFVAL     { 'c0'H }
::= { lpHssiProvEntry 3 }

lpHssiLineSpeed OBJECT-TYPE
   SYNTAX     Unsigned32 (1000000..50000000)
   ACCESS     read-write
   STATUS     mandatory
   DESCRIPTION
     "This attribute defines the speed of the line for source clocking. This 
      attribute is ignored if the interface is not providing a clock. Note 
      that the actual clock rate are available in the operational attributes 
      actualTxLineSpeed and actualRxLineSpeed."
   DEFVAL     { 45000000 }
::= { lpHssiProvEntry 5 }

lpHssiApplicationFramerName OBJECT-TYPE
   SYNTAX     Link 
   ACCESS     read-write
   STATUS     mandatory
   DESCRIPTION
     "This attribute contains the component name of a Framer which is 
      associated with the Hssi component."
::= { lpHssiProvEntry 7 }

lpHssiCidDataTable OBJECT-TYPE
   SYNTAX     SEQUENCE OF LpHssiCidDataEntry
   ACCESS     not-accessible
   STATUS     mandatory
   DESCRIPTION
     "This group contains the attribute for a component's Customer 
      Identifier (CID). Refer to the attribute description for a detailed 
      explanation of CIDs."
::= { lpHssi 11 }

lpHssiCidDataEntry OBJECT-TYPE
   SYNTAX     LpHssiCidDataEntry
   ACCESS     not-accessible
   STATUS     mandatory
   DESCRIPTION
     "An entry in the lpHssiCidDataTable."
   INDEX {
      lpIndex,
      lpHssiIndex }
::= { lpHssiCidDataTable 1 }

LpHssiCidDataEntry ::= SEQUENCE {
   lpHssiCustomerIdentifier
      Unsigned32 }

lpHssiCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpHssiCidDataEntry 1 }

lpHssiAdminInfoTable OBJECT-TYPE
   SYNTAX     SEQUENCE OF LpHssiAdminInfoEntry
   ACCESS     not-accessible
   STATUS     mandatory
   DESCRIPTION
     "This group contains the attributes pertaining to the vendor of the 
      equipment."
::= { lpHssi 12 }

lpHssiAdminInfoEntry OBJECT-TYPE
   SYNTAX     LpHssiAdminInfoEntry
   ACCESS     not-accessible
   STATUS     mandatory
   DESCRIPTION
     "An entry in the lpHssiAdminInfoTable."
   INDEX {
      lpIndex,
      lpHssiIndex }
::= { lpHssiAdminInfoTable 1 }

LpHssiAdminInfoEntry ::= SEQUENCE {
   lpHssiVendor
      AsciiString,
   lpHssiCommentText
      AsciiString }

lpHssiVendor OBJECT-TYPE
   SYNTAX     AsciiString (SIZE (0..20))
   ACCESS     read-write
   STATUS     mandatory
   DESCRIPTION
     "This is the name of the vendor supplying the facility."
::= { lpHssiAdminInfoEntry 1 }

lpHssiCommentText OBJECT-TYPE
   SYNTAX     AsciiString (SIZE (0..60))
   ACCESS     read-write
   STATUS     mandatory
   DESCRIPTION
     "Any miscellaneous text about the facility."
::= { lpHssiAdminInfoEntry 2 }

lpHssiIfEntryTable OBJECT-TYPE
   SYNTAX     SEQUENCE OF LpHssiIfEntryEntry
   ACCESS     not-accessible
   STATUS     mandatory
   DESCRIPTION
     "This group contains the provisionable attributes for the ifEntry."
::= { lpHssi 13 }

lpHssiIfEntryEntry OBJECT-TYPE
   SYNTAX     LpHssiIfEntryEntry
   ACCESS     not-accessible
   STATUS     mandatory
   DESCRIPTION
     "An entry in the lpHssiIfEntryTable."
   INDEX {
      lpIndex,
      lpHssiIndex }
::= { lpHssiIfEntryTable 1 }

LpHssiIfEntryEntry ::= SEQUENCE {
   lpHssiIfAdminStatus
      INTEGER,
   lpHssiIfIndex
      InterfaceIndex }

lpHssiIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpHssiIfEntryEntry 1 }

lpHssiIfIndex OBJECT-TYPE
   SYNTAX     InterfaceIndex (1..65535)
   ACCESS     read-only
   STATUS     mandatory
   DESCRIPTION
     "This is the index for the IfEntry. Its value is automatically initialized 
      during the provisioning process."
::= { lpHssiIfEntryEntry 2 }

lpHssiOperStatusTable OBJECT-TYPE
   SYNTAX     SEQUENCE OF LpHssiOperStatusEntry
   ACCESS     not-accessible
   STATUS     mandatory
   DESCRIPTION
     "This group includes the Operational Status attribute. This attribute 
      defines the current operational state of this component."
::= { lpHssi 14 }

lpHssiOperStatusEntry OBJECT-TYPE
   SYNTAX     LpHssiOperStatusEntry
   ACCESS     not-accessible
   STATUS     mandatory
   DESCRIPTION
     "An entry in the lpHssiOperStatusTable."
   INDEX {
      lpIndex,
      lpHssiIndex }
::= { lpHssiOperStatusTable 1 }

LpHssiOperStatusEntry ::= SEQUENCE {
   lpHssiSnmpOperStatus
      INTEGER }

lpHssiSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpHssiOperStatusEntry 1 }

lpHssiStateTable OBJECT-TYPE
   SYNTAX     SEQUENCE OF LpHssiStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpHssi 15 }

lpHssiStateEntry OBJECT-TYPE
   SYNTAX     LpHssiStateEntry
   ACCESS     not-accessible
   STATUS     mandatory
   DESCRIPTION
     "An entry in the lpHssiStateTable."
   INDEX {
      lpIndex,
      lpHssiIndex }
::= { lpHssiStateTable 1 }

LpHssiStateEntry ::= SEQUENCE {
   lpHssiAdminState
      INTEGER,
   lpHssiOperationalState
      INTEGER,
   lpHssiUsageState
      INTEGER,
   lpHssiAvailabilityStatus
      OCTET STRING,
   lpHssiProceduralStatus
      OCTET STRING,
   lpHssiControlStatus
      OCTET STRING,
   lpHssiAlarmStatus
      OCTET STRING,
   lpHssiStandbyStatus
      INTEGER,
   lpHssiUnknownStatus
      INTEGER }

lpHssiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpHssiStateEntry 1 }

lpHssiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpHssiStateEntry 2 }

lpHssiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpHssiStateEntry 3 }

lpHssiAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpHssiStateEntry 4 }

lpHssiProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpHssiStateEntry 5 }

lpHssiControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpHssiStateEntry 6 }

lpHssiAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpHssiStateEntry 7 }

lpHssiStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpHssiStateEntry 8 }

lpHssiUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpHssiStateEntry 9 }

lpHssiOperTable OBJECT-TYPE
   SYNTAX     SEQUENCE OF LpHssiOperEntry
   ACCESS     not-accessible
   STATUS     mandatory
   DESCRIPTION
     "This group contains all specific operational data for a Hssi 
      component."
::= { lpHssi 16 }

lpHssiOperEntry OBJECT-TYPE
   SYNTAX     LpHssiOperEntry
   ACCESS     not-accessible
   STATUS     mandatory
   DESCRIPTION
     "An entry in the lpHssiOperTable."
   INDEX {
      lpIndex,
      lpHssiIndex }
::= { lpHssiOperTable 1 }

LpHssiOperEntry ::= SEQUENCE {
   lpHssiActualLinkMode
      INTEGER,
   lpHssiLineState
      OCTET STRING,
   lpHssiActualTxLineSpeed
      Gauge32,
   lpHssiActualRxLineSpeed
      Gauge32,
   lpHssiDataXferStateChanges
      Counter32 }

lpHssiActualLinkMode OBJECT-TYPE
   SYNTAX     INTEGER  {
                 dte(0),
                 dce(128) }
   ACCESS     read-only
   STATUS     mandatory
   DESCRIPTION
     "This attribute contains the actual link mode defined by the 
      hardware. Note that the hardware overrides the provisionable data. 
      The port behaves as a dce or dte according to the actualLinkMode."
::= { lpHssiOperEntry 1 }

lpHssiLineState OBJECT-TYPE
   SYNTAX     OCTET STRING (SIZE (1))
   ACCESS     read-only
   STATUS     mandatory
   DESCRIPTION
     "This attribute contains the state of the interface signals.

      Description of bits:
      ca(0)
      ta(1)
      tm(2)
      la(3)
      lb(4)"
::= { lpHssiOperEntry 2 }

lpHssiActualTxLineSpeed OBJECT-TYPE
   SYNTAX     Gauge32 (0..4294967295)
   ACCESS     read-only
   STATUS     mandatory
   DESCRIPTION
     "This attribute is the measured speed of the transmit clock. Note the 
      reported transmit speed is in an error of +/- 10000 bit/s"
::= { lpHssiOperEntry 3 }

lpHssiActualRxLineSpeed OBJECT-TYPE
   SYNTAX     Gauge32 (0..4294967295)
   ACCESS     read-only
   STATUS     mandatory
   DESCRIPTION
     "This attribute is the measured speed of the receive clock. Note the 
      reported receive speed is in an error of +/- 10000 bit/s"
::= { lpHssiOperEntry 4 }

lpHssiDataXferStateChanges OBJECT-TYPE
   SYNTAX     Counter32 
   ACCESS     read-only
   STATUS     mandatory
   DESCRIPTION
     "This attribute contains the number of times that the line has entered 
      or exited the data transfer state."
::= { lpHssiOperEntry 5 }


-- 
-- The Test component is configured to control a hardware facility test 
-- on a physical (V35, X21, DS1, E1, DS3, E3 etc.) or a logical port.

lpHssiTest OBJECT IDENTIFIER ::= { lpHssi 2 }



lpHssiTestRowStatusTable OBJECT-TYPE
   SYNTAX     SEQUENCE OF LpHssiTestRowStatusEntry
   ACCESS     not-accessible
   STATUS     mandatory
   DESCRIPTION
     "This entry controls the addition and deletion of 
      lpHssiTest components."
::= { lpHssiTest 1 }

lpHssiTestRowStatusEntry OBJECT-TYPE
   SYNTAX     LpHssiTestRowStatusEntry
   ACCESS     not-accessible
   STATUS     mandatory
   DESCRIPTION
     "A single entry in the table represents a single 
      lpHssiTest component."
   INDEX {
      lpIndex,
      lpHssiIndex,
      lpHssiTestIndex }
::= { lpHssiTestRowStatusTable 1 }

LpHssiTestRowStatusEntry ::= SEQUENCE {
   lpHssiTestRowStatus
      RowStatus,
   lpHssiTestComponentName
      DisplayString,
   lpHssiTestStorageType
      StorageType,
   lpHssiTestIndex
      NonReplicated }

lpHssiTestRowStatus OBJECT-TYPE
   SYNTAX     RowStatus 
   ACCESS     read-only
   STATUS     mandatory
   DESCRIPTION
     "This variable is used as the basis for SNMP naming of
      lpHssiTest components.
      These components cannot be added nor deleted."
::= { lpHssiTestRowStatusEntry 1 }

lpHssiTestComponentName OBJECT-TYPE
   SYNTAX     DisplayString 
   ACCESS     read-only
   STATUS     mandatory
   DESCRIPTION
     "This variable provides the component's string name for
      use with the ASCII Console Interface"
::= { lpHssiTestRowStatusEntry 2 }

lpHssiTestStorageType OBJECT-TYPE
   SYNTAX     StorageType 
   ACCESS     read-only
   STATUS     mandatory
   DESCRIPTION
     "This variable represents the storage type value for the
      lpHssiTest tables."
::= { lpHssiTestRowStatusEntry 4 }

lpHssiTestIndex OBJECT-TYPE
   SYNTAX     NonReplicated 
   ACCESS     not-accessible
   STATUS     mandatory
   DESCRIPTION
     "This variable represents the index for the lpHssiTest tables."
::= { lpHssiTestRowStatusEntry 10 }

lpHssiTestStateTable OBJECT-TYPE
   SYNTAX     SEQUENCE OF LpHssiTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpHssiTest 10 }

lpHssiTestStateEntry OBJECT-TYPE
   SYNTAX     LpHssiTestStateEntry
   ACCESS     not-accessible
   STATUS     mandatory
   DESCRIPTION
     "An entry in the lpHssiTestStateTable."
   INDEX {
      lpIndex,
      lpHssiIndex,
      lpHssiTestIndex }
::= { lpHssiTestStateTable 1 }

LpHssiTestStateEntry ::= SEQUENCE {
   lpHssiTestAdminState
      INTEGER,
   lpHssiTestOperationalState
      INTEGER,
   lpHssiTestUsageState
      INTEGER }

lpHssiTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpHssiTestStateEntry 1 }

lpHssiTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpHssiTestStateEntry 2 }

lpHssiTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpHssiTestStateEntry 3 }

lpHssiTestSetupTable OBJECT-TYPE
   SYNTAX     SEQUENCE OF LpHssiTestSetupEntry
   ACCESS     not-accessible
   STATUS     mandatory
   DESCRIPTION
     "This group contains all of the operational data for a Test 
      component."
::= { lpHssiTest 11 }

lpHssiTestSetupEntry OBJECT-TYPE
   SYNTAX     LpHssiTestSetupEntry
   ACCESS     not-accessible
   STATUS     mandatory
   DESCRIPTION
     "An entry in the lpHssiTestSetupTable."
   INDEX {
      lpIndex,
      lpHssiIndex,
      lpHssiTestIndex }
::= { lpHssiTestSetupTable 1 }

LpHssiTestSetupEntry ::= SEQUENCE {
   lpHssiTestPurpose
      AsciiString,
   lpHssiTestType
      INTEGER,
   lpHssiTestFrmSize
      Unsigned32,
   lpHssiTestFrmPatternType
      INTEGER,
   lpHssiTestCustomizedPattern
      Hex,
   lpHssiTestDataStartDelay
      Unsigned32,
   lpHssiTestDisplayInterval
      Unsigned32,
   lpHssiTestDuration
      Unsigned32 }

lpHssiTestPurpose OBJECT-TYPE
   SYNTAX     AsciiString (SIZE (0..40))
   ACCESS     read-write
   STATUS     mandatory
   DESCRIPTION
     "This attribute records the purpose of the test so that the test results 
      can be associated and properly analyzed."
::= { lpHssiTestSetupEntry 1 }

lpHssiTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpHssiTestSetupEntry 2 }

lpHssiTestFrmSize OBJECT-TYPE
   SYNTAX     Unsigned32 (4..4096)
   ACCESS     read-write
   STATUS     mandatory
   DESCRIPTION
     "This attribute defines the size of the test data frames in number of 
      bytes."
   DEFVAL     { 1024 }
::= { lpHssiTestSetupEntry 3 }

lpHssiTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpHssiTestSetupEntry 4 }

lpHssiTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpHssiTestSetupEntry 5 }

lpHssiTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpHssiTestSetupEntry 6 }

lpHssiTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpHssiTestSetupEntry 7 }

lpHssiTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpHssiTestSetupEntry 8 }

lpHssiTestResultsTable OBJECT-TYPE
   SYNTAX     SEQUENCE OF LpHssiTestResultsEntry
   ACCESS     not-accessible
   STATUS     mandatory
   DESCRIPTION
     "This group contains all the statistics related attributes of the Test 
      component."
::= { lpHssiTest 12 }

lpHssiTestResultsEntry OBJECT-TYPE
   SYNTAX     LpHssiTestResultsEntry
   ACCESS     not-accessible
   STATUS     mandatory
   DESCRIPTION
     "An entry in the lpHssiTestResultsTable."
   INDEX {
      lpIndex,
      lpHssiIndex,
      lpHssiTestIndex }
::= { lpHssiTestResultsTable 1 }

LpHssiTestResultsEntry ::= SEQUENCE {
   lpHssiTestElapsedTime
      Counter32,
   lpHssiTestTimeRemaining
      Unsigned32,
   lpHssiTestCauseOfTermination
      INTEGER,
   lpHssiTestBitsTx
      PassportCounter64,
   lpHssiTestBytesTx
      PassportCounter64,
   lpHssiTestFrmTx
      PassportCounter64,
   lpHssiTestBitsRx
      PassportCounter64,
   lpHssiTestBytesRx
      PassportCounter64,
   lpHssiTestFrmRx
      PassportCounter64,
   lpHssiTestErroredFrmRx
      PassportCounter64,
   lpHssiTestBitErrorRate
      AsciiString }

lpHssiTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpHssiTestResultsEntry 1 }

lpHssiTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpHssiTestResultsEntry 2 }

lpHssiTestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpHssiTestResultsEntry 3 }

lpHssiTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpHssiTestResultsEntry 4 }

lpHssiTestBytesTx OBJECT-TYPE
   SYNTAX     PassportCounter64 
   ACCESS     read-only
   STATUS     mandatory
   DESCRIPTION
     "This attribute is the total number of bytes sent during the test 
      period. This counter is not expected to reach its maximum value."
::= { lpHssiTestResultsEntry 5 }

lpHssiTestFrmTx OBJECT-TYPE
   SYNTAX     PassportCounter64 
   ACCESS     read-only
   STATUS     mandatory
   DESCRIPTION
     "This attribute is the total number of frames sent during the test 
      period. This counter is not expected to reach its maximum value."
::= { lpHssiTestResultsEntry 6 }

lpHssiTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpHssiTestResultsEntry 7 }

lpHssiTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpHssiTestResultsEntry 8 }

lpHssiTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpHssiTestResultsEntry 9 }

lpHssiTestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpHssiTestResultsEntry 10 }

lpHssiTestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpHssiTestResultsEntry 11 }


-- Lp Engineering
-- This component has various subcomponents which hold 
-- engineering/control parameters and corresponding indicator 
-- statistics for this LP. The subcomponents can be defined for selected 
-- services or be common to a number of services.
-- 
-- This component has no data of its own.

lpEng OBJECT IDENTIFIER ::= { lp 23 }



lpEngRowStatusTable OBJECT-TYPE
   SYNTAX     SEQUENCE OF LpEngRowStatusEntry
   ACCESS     not-accessible
   STATUS     mandatory
   DESCRIPTION
     "This entry controls the addition and deletion of 
      lpEng components."
::= { lpEng 1 }

lpEngRowStatusEntry OBJECT-TYPE
   SYNTAX     LpEngRowStatusEntry
   ACCESS     not-accessible
   STATUS     mandatory
   DESCRIPTION
     "A single entry in the table represents a single 
      lpEng component."
   INDEX {
      lpIndex,
      lpEngIndex }
::= { lpEngRowStatusTable 1 }

LpEngRowStatusEntry ::= SEQUENCE {
   lpEngRowStatus
      RowStatus,
   lpEngComponentName
      DisplayString,
   lpEngStorageType
      StorageType,
   lpEngIndex
      NonReplicated }

lpEngRowStatus OBJECT-TYPE
   SYNTAX     RowStatus 
   ACCESS     read-only
   STATUS     mandatory
   DESCRIPTION
     "This variable is used as the basis for SNMP naming of
      lpEng components.
      These components cannot be added nor deleted."
::= { lpEngRowStatusEntry 1 }

lpEngComponentName OBJECT-TYPE
   SYNTAX     DisplayString 
   ACCESS     read-only
   STATUS     mandatory
   DESCRIPTION
     "This variable provides the component's string name for
      use with the ASCII Console Interface"
::= { lpEngRowStatusEntry 2 }

lpEngStorageType OBJECT-TYPE
   SYNTAX     StorageType 
   ACCESS     read-only
   STATUS     mandatory
   DESCRIPTION
     "This variable represents the storage type value for the
      lpEng tables."
::= { lpEngRowStatusEntry 4 }

lpEngIndex OBJECT-TYPE
   SYNTAX     NonReplicated 
   ACCESS     not-accessible
   STATUS     mandatory
   DESCRIPTION
     "This variable represents the index for the lpEng tables."
::= { lpEngRowStatusEntry 10 }


-- Lp Eng DataStream/<type>
-- This component holds engineering parameters used by DCS on this 
-- LP for a particular DCS stream.

lpEngDs OBJECT IDENTIFIER ::= { lpEng 2 }



lpEngDsRowStatusTable OBJECT-TYPE
   SYNTAX     SEQUENCE OF LpEngDsRowStatusEntry
   ACCESS     not-accessible
   STATUS     mandatory
   DESCRIPTION
     "This entry controls the addition and deletion of 
      lpEngDs components."
::= { lpEngDs 1 }

lpEngDsRowStatusEntry OBJECT-TYPE
   SYNTAX     LpEngDsRowStatusEntry
   ACCESS     not-accessible
   STATUS     mandatory
   DESCRIPTION
     "A single entry in the table represents a single 
      lpEngDs component."
   INDEX {
      lpIndex,
      lpEngIndex,
      lpEngDsIndex }
::= { lpEngDsRowStatusTable 1 }

LpEngDsRowStatusEntry ::= SEQUENCE {
   lpEngDsRowStatus
      RowStatus,
   lpEngDsComponentName
      DisplayString,
   lpEngDsStorageType
      StorageType,
   lpEngDsIndex
      INTEGER }

lpEngDsRowStatus OBJECT-TYPE
   SYNTAX     RowStatus 
   ACCESS     read-write
   STATUS     mandatory
   DESCRIPTION
     "This variable is used as the basis for SNMP naming of
      lpEngDs components.
      These components can be added and deleted."
::= { lpEngDsRowStatusEntry 1 }

lpEngDsComponentName OBJECT-TYPE
   SYNTAX     DisplayString 
   ACCESS     read-only
   STATUS     mandatory
   DESCRIPTION
     "This variable provides the component's string name for
      use with the ASCII Console Interface"
::= { lpEngDsRowStatusEntry 2 }

lpEngDsStorageType OBJECT-TYPE
   SYNTAX     StorageType 
   ACCESS     read-only
   STATUS     mandatory
   DESCRIPTION
     "This variable represents the storage type value for the
      lpEngDs tables."
::= { lpEngDsRowStatusEntry 4 }

lpEngDsIndex OBJECT-TYPE
   SYNTAX     INTEGER  {
                 accounting(0),
                 alarm(1),
                 log(2),
                 debug(3),
                 scn(4),
                 trap(5),
                 stats(6) }
   ACCESS     not-accessible
   STATUS     mandatory
   DESCRIPTION
     "This variable represents the index for the lpEngDs tables."
::= { lpEngDsRowStatusEntry 10 }

lpEngDsOperTable OBJECT-TYPE
   SYNTAX     SEQUENCE OF LpEngDsOperEntry
   ACCESS     not-accessible
   STATUS     mandatory
   DESCRIPTION
     "This group contains operational attributes for the DataStream 
      components under Lp Engineering."
::= { lpEngDs 10 }

lpEngDsOperEntry OBJECT-TYPE
   SYNTAX     LpEngDsOperEntry
   ACCESS     not-accessible
   STATUS     mandatory
   DESCRIPTION
     "An entry in the lpEngDsOperTable."
   INDEX {
      lpIndex,
      lpEngIndex,
      lpEngDsIndex }
::= { lpEngDsOperTable 1 }

LpEngDsOperEntry ::= SEQUENCE {
   lpEngDsAgentQueueSize
      Unsigned32 }

lpEngDsAgentQueueSize OBJECT-TYPE
   SYNTAX     Unsigned32 (0..4294967295)
   ACCESS     read-only
   STATUS     mandatory
   DESCRIPTION
     "This attribute indicates the maximum size of the DCS Agent queue 
      size maximum for a DCS data stream on the LP. It is the maximum 
      size to which the Agent's currentQueueSize can grow. When the 
      queue is full and more data is offered to the Agent, it will be 
      discarded.
      The following are the system defaults (in number of records):
      - alarm: 100
      - accounting: 10000
      - debug: 0
      - log: 50
      - scn: 200
      - trap: 50
      - stats: 0
      To override the system defaults, see Lp Eng Ds Ov's 
      agentQueueSize attribute."
::= { lpEngDsOperEntry 1 }


-- Lp Eng Ds/<type> Override
-- This component holds provisionable engineering parameters used 
-- by DCS on this LP for a particular DCS stream.

lpEngDsOv OBJECT IDENTIFIER ::= { lpEngDs 2 }



lpEngDsOvRowStatusTable OBJECT-TYPE
   SYNTAX     SEQUENCE OF LpEngDsOvRowStatusEntry
   ACCESS     not-accessible
   STATUS     mandatory
   DESCRIPTION
     "This entry controls the addition and deletion of 
      lpEngDsOv components."
::= { lpEngDsOv 1 }

lpEngDsOvRowStatusEntry OBJECT-TYPE
   SYNTAX     LpEngDsOvRowStatusEntry
   ACCESS     not-accessible
   STATUS     mandatory
   DESCRIPTION
     "A single entry in the table represents a single 
      lpEngDsOv component."
   INDEX {
      lpIndex,
      lpEngIndex,
      lpEngDsIndex,
      lpEngDsOvIndex }
::= { lpEngDsOvRowStatusTable 1 }

LpEngDsOvRowStatusEntry ::= SEQUENCE {
   lpEngDsOvRowStatus
      RowStatus,
   lpEngDsOvComponentName
      DisplayString,
   lpEngDsOvStorageType
      StorageType,
   lpEngDsOvIndex
      NonReplicated }

lpEngDsOvRowStatus OBJECT-TYPE
   SYNTAX     RowStatus 
   ACCESS     read-write
   STATUS     mandatory
   DESCRIPTION
     "This variable is used as the basis for SNMP naming of
      lpEngDsOv components.
      These components can be added and deleted."
::= { lpEngDsOvRowStatusEntry 1 }

lpEngDsOvComponentName OBJECT-TYPE
   SYNTAX     DisplayString 
   ACCESS     read-only
   STATUS     mandatory
   DESCRIPTION
     "This variable provides the component's string name for
      use with the ASCII Console Interface"
::= { lpEngDsOvRowStatusEntry 2 }

lpEngDsOvStorageType OBJECT-TYPE
   SYNTAX     StorageType 
   ACCESS     read-only
   STATUS     mandatory
   DESCRIPTION
     "This variable represents the storage type value for the
      lpEngDsOv tables."
::= { lpEngDsOvRowStatusEntry 4 }

lpEngDsOvIndex OBJECT-TYPE
   SYNTAX     NonReplicated 
   ACCESS     not-accessible
   STATUS     mandatory
   DESCRIPTION
     "This variable represents the index for the lpEngDsOv tables."
::= { lpEngDsOvRowStatusEntry 10 }

lpEngDsOvProvTable OBJECT-TYPE
   SYNTAX     SEQUENCE OF LpEngDsOvProvEntry
   ACCESS     not-accessible
   STATUS     mandatory
   DESCRIPTION
     "This group contains provisionable attributes for the DataStream Ov 
      components under Lp Engineering.
      DESCRIPTION"
::= { lpEngDsOv 10 }

lpEngDsOvProvEntry OBJECT-TYPE
   SYNTAX     LpEngDsOvProvEntry
   ACCESS     not-accessible
   STATUS     mandatory
   DESCRIPTION
     "An entry in the lpEngDsOvProvTable."
   INDEX {
      lpIndex,
      lpEngIndex,
      lpEngDsIndex,
      lpEngDsOvIndex }
::= { lpEngDsOvProvTable 1 }

LpEngDsOvProvEntry ::= SEQUENCE {
   lpEngDsOvAgentQueueSize
      Unsigned32 }

lpEngDsOvAgentQueueSize OBJECT-TYPE
   SYNTAX     Unsigned32 (0..4294967295)
   ACCESS     read-write
   STATUS     mandatory
   DESCRIPTION
     "This attribute specifies the maximum size of the DCS Agent's 
      queue for this data stream on this LP. For more details on the 
      defaults and other information, refer to the parent component's 
      agentQueueSize attribute.
      The size should be set to 0 if absolutely no data is to be accepted 
      from applications. There are threshold alarms based on the value of 
      the Agent's currentQueueSize attribute (a Set when the queue 
      becomes 75% full and a Clear after dropping back to 50% full).
      To properly determine what to set this to, consult the 'Magellan 
      Passport Engineering Notes and Guidelines'."
::= { lpEngDsOvProvEntry 1 }




-- 
-- Version and Compliance statements
-- 



-- Object-Group Statement:
-- A list of all current accessible leaf objects.

-- OBJECTS { lpE1ChanTcSigOneValue,
--           lpEngStorageType,
--           lpHssiTestDuration,
--           lpJT2UnknownStatus,
--           lpHssiCustomerIdentifier,
--           lpE1ClockingSource,
--           lpSonetTestStorageType,
--           lpControlStatus,
--           lpSdhProceduralStatus,
--           lpX21TestBitsTx,
--           lpE1ChanCellTransmitCellUtilization,
--           lpDS3DS1ChanRowStatus,
--           lpSdhLofAlarm,
--           lpSdhSectFailures,
--           lpSonetStorageType,
--           lpDS3DS1TestBitsTx,
--           lpSonetPathCellReceiveCellUtilization,
--           lpDS3TestTimeRemaining,
--           lpHssiTestPurpose,
--           lpSdhAlarmStatus,
--           lpDS3TestType,
--           lpMsgBlockUsageAvg,
--           lpE1LineType,
--           lpSonetPathComponentName,
--           lpE1ChanTestTimeRemaining,
--           lpE1ChanTestBytesRx,
--           lpJT2LosAlarm,
--           lpV35DteDataClockSource,
--           lpX21TestBitsRx,
--           lpE1TestFrmTx,
--           lpE1ChanTestFrmPatternType,
--           lpSonetAlarmStatus,
--           lpDS3DS1TestBitsRx,
--           lpSdhAvailabilityStatus,
--           lpE3G832TrailTraceMismatch,
--           lpDS3CommentText,
--           lpDS1TestTimeRemaining,
--           lpDS1ErroredSec,
--           lpDS3DS1ChanCellComponentName,
--           lpEngDsComponentName,
--           lpDS1TestType,
--           lpE1ChanCellReceiveCellUtilization,
--           lpDS3DS1ErrorFreeSec,
--           lpJT2TxAisPhysicalAlarm,
--           lpDS3DS1ChanTcIngressConditioning,
--           lpDS3DS1ChanTestRowStatus,
--           lpDS3PathSefAisSec,
--           lpDS3StorageType,
--           lpDS3DS1ChanAvailabilityStatus,
--           lpDS1ChanTcStorageType,
--           lpSdhPathTxAis,
--           lpDS1ChanTcSignalOneDuration,
--           lpE1ChanComponentName,
--           lpE3TestFrmTx,
--           lpV35ProceduralStatus,
--           lpDS3CBitLoopedbackToFarEnd,
--           lpSdhStandbyStatus,
--           lpDS3TestUsageState,
--           lpSonetPathCellRowStatus,
--           lpE3UnknownStatus,
--           lpSonetPathFarEndPathAisLopSec,
--           lpDS1CommentText,
--           lpE3TestDataStartDelay,
--           lpTimeInterval,
--           lpJT2LosStateChanges,
--           lpSonetPathTxAis,
--           lpDS3PlcpStorageType,
--           lpHssiIfAdminStatus,
--           lpSonetPathPathAisLopSec,
--           lpDS1DspRowStatus,
--           lpE3TestBitsTx,
--           lpDS1ChanSnmpOperStatus,
--           lpDS1StorageType,
--           lpDS3LineSevErroredSec,
--           lpDS1UnavailSec,
--           lpE3TestFrmRx,
--           lpDS1TxAisAlarm,
--           lpV35SnmpOperStatus,
--           lpE1UnknownStatus,
--           lpE3G832RowStatus,
--           lpE3TestPurpose,
--           lpE3G832TrailTraceExpected,
--           lpE3TestDuration,
--           lpDS3TestElapsedTime,
--           lpE1TestDataStartDelay,
--           lpDS1LineLength,
--           lpE1ChanTestRowStatus,
--           lpSdhPathPathCodeViolations,
--           lpDS3TestStorageType,
--           lpSdhErrorFreeSec,
--           lpProceduralStatus,
--           lpSdhPathCellScrambleCellPayload,
--           lpE1ChanTestComponentName,
--           lpSonetLineAisSec,
--           lpSdhFarEndLineFailures,
--           lpLocalMsgBlockUsageMax,
--           lpSdhTestBitsTx,
--           lpHssiTestCauseOfTermination,
--           lpSonetPathUsageState,
--           lpDS3StandbyStatus,
--           lpE1TestFrmRx,
--           lpE3LineLength,
--           lpDS3TestAdminState,
--           lpSdhPathCellStorageType,
--           lpE1ChanTestDuration,
--           lpE1TestDuration,
--           lpE3TxAis,
--           lpE1CustomerIdentifier,
--           lpSonetIfIndex,
--           lpDS1TestStorageType,
--           lpX21LineState,
--           lpHssiDataTransferLineState,
--           lpX21SnmpOperStatus,
--           lpE3G832TimingMarker,
--           lpDS3DS1SlipErrors,
--           lpV35Vendor,
--           lpLocalMsgBlockUsageMin,
--           lpDS3AlarmStatus,
--           lpE3TxRai,
--           lpDS3DS1SnmpOperStatus,
--           lpSonetPathStandbyStatus,
--           lpEngRowStatus,
--           lpDS1TestAdminState,
--           lpJT2IfIndex,
--           lpDS1ChanOperationalState,
--           lpE1ChanUsageState,
--           lpDS3DS1IfAdminStatus,
--           lpDS3DS1ChanTestBitsTx,
--           lpDS3RunningTime,
--           lpMemoryUsageAvgValue,
--           lpE3TestBitsRx,
--           lpDS3CBitFarEndSevErroredSec,
--           lpDS3DS1ChanTestFrmTx,
--           lpSdhPathControlStatus,
--           lpJT2TestBitsRx,
--           lpDS3Mapping,
--           lpJT2TestAdminState,
--           lpDS3DS1ChanUnknownStatus,
--           lpSonetRowStatus,
--           lpDS1ZeroCoding,
--           lpJT2TestComponentName,
--           lpStandbyStatus,
--           lpDS1ChanCellStorageType,
--           lpDS3DS1ChanTestDataStartDelay,
--           lpE3PathCodeViolations,
--           lpDS3CellSevErroredSec,
--           lpE1ChanCellUncorrectableHecErrors,
--           lpE3CellScrambleCellPayload,
--           lpE1ChanTestFrmSize,
--           lpSdhPathLopAlarm,
--           lpX21Vendor,
--           lpSdhPathCustomerIdentifier,
--           lpE3G832FarEndErrorFreeSec,
--           lpDS1RunningTime,
--           lpE3TestCauseOfTermination,
--           lpDS3LosAlarm,
--           lpJT2RowStatus,
--           lpDS3DS1ChanTestFrmRx,
--           lpDS3DS1Vendor,
--           lpSonetRunningTime,
--           lpE3CellStorageType,
--           lpE3PlcpRowStatus,
--           lpDS3CBitFarEndSefAisSec,
--           lpDS3DS1ChanCustomerIdentifier,
--           lpE1ChanTestUsageState,
--           lpHssiReadyLineState,
--           lpE1ChanTcEgressConditioning,
--           lpE3TestErroredFrmRx,
--           lpSonetSectFailures,
--           lpDS1RxRaiAlarm,
--           lpSdhTestElapsedTime,
--           lpE3LosAlarm,
--           lpDS3TestOperationalState,
--           lpV35TestOperationalState,
--           lpSdhLineFailures,
--           lpE1TestDisplayInterval,
--           lpDS1TestFrmTx,
--           lpDS3DS1ChanTestAdminState,
--           lpSonetTestRowStatus,
--           lpHssiLinkMode,
--           lpSonetPathFarEndPathSevErroredSec,
--           lpJT2TestType,
--           lpSonetAvailabilityStatus,
--           lpJT2CommentText,
--           lpDS1ChanTestBitsRx,
--           lpHssiIfIndex,
--           lpLocalMsgBlockUsageAvg,
--           lpSdhTestBitErrorRate,
--           lpSonetPathPathSevErroredSec,
--           lpMemoryCapacityValue,
--           lpSdhPathFarEndPathErroredSec,
--           lpE1TestErroredFrmRx,
--           lpDS3PlcpRxRaiAlarm,
--           lpE1LosAlarm,
--           lpDS1ChanActualChannelSpeed,
--           lpSonetPathSignalLabelMismatch,
--           lpE1ChanTestBitErrorRate,
--           lpDS3DS1ChanTestDisplayInterval,
--           lpE3LineCodeViolations,
--           lpJT2AdminState,
--           lpE3CellComponentName,
--           lpE1TestCauseOfTermination,
--           lpMemoryUsageValue,
--           lpX21TestOperationalState,
--           lpE3G832TrailTraceReceived,
--           lpJT2TestDataStartDelay,
--           lpSdhPathCellCorrectableHeaderErrors,
--           lpDS3DS1TestOperationalState,
--           lpDS1ChanCellCorrectSingleBitHeaderErrors,
--           lpDS1IfIndex,
--           lpDS1TestFrmRx,
--           lpDS1ChanTimeslotDataRate,
--           lpV35TestPurpose,
--           lpSdhSectLosSec,
--           lpSonetPathStorageType,
--           lpE1ChanTestType,
--           lpJT2StorageType,
--           lpDS3RowStatus,
--           lpDS1TestCustomizedPattern,
--           lpHssiTestElapsedTime,
--           lpDS1ChanTcRowStatus,
--           lpDS3DS1ChanCellScrambleCellPayload,
--           lpSonetTestAdminState,
--           lpHssiTestRowStatus,
--           lpX21DataXferStateChanges,
--           lpE3ControlStatus,
--           lpDS1ChanTestCustomizedPattern,
--           lpHssiProceduralStatus,
--           lpV35TestBytesTx,
--           lpDS3CBitComponentName,
--           lpSonetFarEndLineErroredSec,
--           lpSonetSectSevErroredSec,
--           lpDS3DS1ChanCellStorageType,
--           lpE1ChanCommentText,
--           lpSdhVendor,
--           lpE3LinkAlarmActivationThreshold,
--           lpDS3PlcpFarEndErroredSec,
--           lpJT2RunningTime,
--           lpHssiTestFrmPatternType,
--           lpLocalMsgBlockCapacity,
--           lpDS3DS1TestElapsedTime,
--           lpScheduledSwitchover,
--           lpDS1RowStatus,
--           lpDS3CBitFarEndErroredSec,
--           lpX21LineTerminationRequired,
--           lpDS1ChanTestBytesRx,
--           lpE1FrmErrors,
--           lpE1ChanTestPurpose,
--           lpE1ChanStorageType,
--           lpE1ControlStatus,
--           lpJT2RxAisPayloadAlarm,
--           lpV35TestBytesRx,
--           lpDS3PlcpSevErroredFramingSec,
--           lpDS3CellComponentName,
--           lpV35TestCustomizedPattern,
--           lpDS3DS1ChanTcReplacementData,
--           lpLocalMsgBlockUsage,
--           lpV35LineSpeed,
--           lpDS3DS1ChanTestCauseOfTermination,
--           lpSdhPathProceduralStatus,
--           lpDS3TestRowStatus,
--           lpDS3CBitCbitErrorFreeSec,
--           lpV35IfAdminStatus,
--           lpMainCard,
--           lpE3CellCorrectableHeaderErrors,
--           lpDS3AvailabilityStatus,
--           lpX21TestBytesTx,
--           lpSonetUnknownStatus,
--           lpSonetFarEndLineUnavailSec,
--           lpJT2IfAdminStatus,
--           lpX21TestCustomizedPattern,
--           lpDS3PathErroredSec,
--           lpV35ClockingSource,
--           lpSonetPathLopAlarm,
--           lpSdhPathCellRowStatus,
--           lpDS3DS1TestCustomizedPattern,
--           lpE1AudioComponentName,
--           lpV35UsageState,
--           lpSdhPathFarEndPathUnavailSec,
--           lpSdhPathFarEndPathSevErroredSec,
--           lpDS3DS1ChanTimeslots,
--           lpDS3PlcpUnavailSec,
--           lpSonetTestFrmRx,
--           lpE1ChanTestStorageType,
--           lpX21TestBytesRx,
--           lpDS1ChanTcSigOneValue,
--           lpE1CommentText,
--           lpMainCardStatus,
--           lpSonetTestDuration,
--           lpSonetTxRdi,
--           lpSonetCustomerIdentifier,
--           lpDS1ClockingSource,
--           lpE3G832ComponentName,
--           lpX21IfAdminStatus,
--           lpDS1ChanCellTransmitCellUtilization,
--           lpE1ChanTestAdminState,
--           lpJT2TestFrmRx,
--           lpDS3CellUncorrectableHecErrors,
--           lpDS3DS1SevErroredSec,
--           lpJT2TestStorageType,
--           lpDS3PathUnavailSec,
--           lpDS3DS1ChanControlStatus,
--           lpJT2TestDuration,
--           lpSdhPathStandbyStatus,
--           lpCpuUtilAvgMax,
--           lpHssiTestErroredFrmRx,
--           lpDS3PlcpComponentName,
--           lpE3PlcpStorageType,
--           lpHssiTestFrmSize,
--           lpE3ProceduralStatus,
--           lpDS1LineType,
--           lpE1ChanAlarmStatus,
--           lpE3LofAlarm,
--           lpJT2TestDisplayInterval,
--           lpSonetTestDataStartDelay,
--           lpX21TestPurpose,
--           lpJT2TestErroredFrmRx,
--           lpX21EnableDynamicSpeed,
--           lpDS1ChanTestFrmPatternType,
--           lpE3CellAlarmActDelay,
--           lpDS1ChanStandbyStatus,
--           lpSonetSectCodeViolations,
--           lpDS3LineErroredSec,
--           lpSonetPathCellCorrectSingleBitHeaderErrors,
--           lpSdhFarEndLineErroredSec,
--           lpE3CellRowStatus,
--           lpSdhPathApplicationFramerName,
--           lpV35TestFrmPatternType,
--           lpCpuUtilAvgMin,
--           lpSonetPathCellSevErroredSec,
--           lpDS3DS1ChanTcEgressConditioning,
--           lpDS1ChanCellReceiveCellUtilization,
--           lpE1ProceduralStatus,
--           lpOperationalState,
--           lpE1LofAlarm,
--           lpJT2CellStorageType,
--           lpHssiTestBitsRx,
--           lpDS3DS1ChanCellCorrectableHeaderErrors,
--           lpE1ChanCellLcdAlarm,
--           lpDS1ChanComponentName,
--           lpDS3TestFrmTx,
--           lpHssiTestTimeRemaining,
--           lpEngDsOvStorageType,
--           lpDS1ChanTestElapsedTime,
--           lpDS3DS1ChanTestElapsedTime,
--           lpDS3UnknownStatus,
--           lpV35ComponentName,
--           lpDS3TestDataStartDelay,
--           lpSdhRunningTime,
--           lpEngComponentName,
--           lpDS3ProceduralStatus,
--           lpSonetTestDisplayInterval,
--           lpSonetPathCellUncorrectableHecErrors,
--           lpX21TestFrmTx,
--           lpSonetPathIfIndex,
--           lpE1ChanCellSevErroredSec,
--           lpE1ChanAdminState,
--           lpX21TestFrmPatternType,
--           lpHssiActualLinkMode,
--           lpSdhPathCellAlarmActDelay,
--           lpSdhPathPathFailures,
--           lpDS3TestFrmRx,
--           lpJT2CellScrambleCellPayload,
--           lpDS1ChanTcReplacementData,
--           lpDS3DS1TestFrmPatternType,
--           lpDS1UnknownStatus,
--           lpSonetTestErroredFrmRx,
--           lpDS3TestDuration,
--           lpDS3CustomerIdentifier,
--           lpSonetLosAlarm,
--           lpDS3AdminState,
--           lpE3G832FarEndSevErroredSec,
--           lpRestartOnCpSwitch,
--           lpDS1ChanTestComponentName,
--           lpSdhIfAdminStatus,
--           lpE3ApplicationFramerName,
--           lpE1StandbyStatus,
--           lpSdhOperationalState,
--           lpSonetTestCauseOfTermination,
--           lpV35TestComponentName,
--           lpE1ChanIfIndex,
--           lpDS3DS1ChanTestBitErrorRate,
--           lpDS3DS1ComponentName,
--           lpE1CrcErrors,
--           lpE1BpvErrors,
--           lpSonetFarEndLineCodeViolations,
--           lpDS1TestDuration,
--           lpDS3TxAis,
--           lpDS1TestBitErrorRate,
--           lpDS1CustomerIdentifier,
--           lpX21TestDuration,
--           lpDS3DS1ChanCellAlarmActDelay,
--           lpSonetTestPurpose,
--           lpSonetLineCodeViolations,
--           lpDS3DS1ChanCellRowStatus,
--           lpSdhTestPurpose,
--           lpDS3TxRai,
--           lpJT2ComponentName,
--           lpJT2BpvErrors,
--           lpHssiRowStatus,
--           lpSdhPathCellLcdAlarm,
--           lpDS1ChanUsageState,
--           lpDS3CBitFarEndUnavailSec,
--           lpE1ChanRowStatus,
--           lpE3PathFailures,
--           lpSonetPathCellComponentName,
--           lpX21TestComponentName,
--           lpE1TestBitsTx,
--           lpSonetTestType,
--           lpSdhFarEndLineErrorFreeSec,
--           lpDS3CBitStorageType,
--           lpDS1TestElapsedTime,
--           lpJT2TestRowStatus,
--           lpSonetPathFarEndPathErroredSec,
--           lpDS3DS1TestComponentName,
--           lpJT2UsageState,
--           lpSonetPathAvailabilityStatus,
--           lpDS3PathCodeViolations,
--           lpE3ErrorFreeSec,
--           lpJT2TestCustomizedPattern,
--           lpSonetControlStatus,
--           lpDS1ChanCellUncorrectableHecErrors,
--           lpDS3CellScrambleCellPayload,
--           lpDS1ChanCellLcdAlarm,
--           lpSonetPathPathErroredSec,
--           lpV35ActualRxLineSpeed,
--           lpDS3TestDisplayInterval,
--           lpDS3DS1ChanStandbyStatus,
--           lpSdhPathAdminState,
--           lpV35TestFrmSize,
--           lpE1TestBitsRx,
--           lpSonetLineSevErroredSec,
--           lpSdhTestCustomizedPattern,
--           lpDS3CellStorageType,
--           lpDS3PlcpSevErroredSec,
--           lpDS3PlcpRowStatus,
--           lpSdhLineCodeViolations,
--           lpE1ChanCellComponentName,
--           lpSonetPathCellCorrectableHeaderErrors,
--           lpDS1ChanTestUsageState,
--           lpE1ErrorFreeSec,
--           lpDS3TestBytesRx,
--           lpE1ChanTcIngressConditioning,
--           lpDS3TestErroredFrmRx,
--           lpX21UsageState,
--           lpDS3RxAisAlarm,
--           lpE1IfAdminStatus,
--           lpX21ActualTxLineSpeed,
--           lpHssiAvailabilityStatus,
--           lpE1ChanAvailabilityStatus,
--           lpV35TestUsageState,
--           lpSdhPathSnmpOperStatus,
--           lpDS3DS1ChanApplicationFramerName,
--           lpDS1LofAlarm,
--           lpDS3DS1UsageState,
--           lpDS3DS1ChanTestErroredFrmRx,
--           lpHssiLineState,
--           lpHssiTestBitsTx,
--           lpHssiUnknownStatus,
--           lpMsgBlockUsageAvgMax,
--           lpDS3TestCauseOfTermination,
--           lpE1AudioStorageType,
--           lpCpuUtilAvg,
--           lpSonetPathPathUnavailSec,
--           lpSdhComponentName,
--           lpE3PlcpFarEndSevErroredSec,
--           lpDS3DS1TxRaiAlarm,
--           lpJT2TxRaiAlarm,
--           lpV35EnableDynamicSpeed,
--           lpSonetTestElapsedTime,
--           lpX21TestFrmSize,
--           lpHssiCommentText,
--           lpDS1TestErroredFrmRx,
--           lpDS1LosAlarm,
--           lpDS1TestDisplayInterval,
--           lpDS3DS1TestFrmSize,
--           lpSdhClockingSource,
--           lpDS3DS1RxAisAlarm,
--           lpDS3LineCodeViolations,
--           lpDS1ChanTestFrmSize,
--           lpMsgBlockUsageAvgMin,
--           lpDS1ChanTcSigTwoValue,
--           lpDS1TestCauseOfTermination,
--           lpSdhTestOperationalState,
--           lpX21TestUsageState,
--           lpDS1TestBytesRx,
--           lpDS3DS1RxRaiAlarm,
--           lpE1ChanTestBitsTx,
--           lpEngDsOvAgentQueueSize,
--           lpHssiTestUsageState,
--           lpDS3DS1TestUsageState,
--           lpDS1BpvErrors,
--           lpDS3DS1ChanTcComponentName,
--           lpE3CellLcdAlarm,
--           lpDS1ChanTestTimeRemaining,
--           lpE3SnmpOperStatus,
--           lpSpareCard,
--           lpDS1ChanTestType,
--           lpEngDsStorageType,
--           lpV35OperationalState,
--           lpSdhTestComponentName,
--           lpSdhTestFrmPatternType,
--           lpV35TestTimeRemaining,
--           lpDS3DS1ProceduralStatus,
--           lpX21ProceduralStatus,
--           lpE3PlcpFarEndUnavailableSec,
--           lpV35TestType,
--           lpSdhAdminState,
--           lpDS3CBitCbitSevErroredSec,
--           lpDS3ControlStatus,
--           lpSonetProceduralStatus,
--           lpSdhPathUsageState,
--           lpDS3DS1ChanTestDuration,
--           lpSonetLofAlarm,
--           lpE1SlipErrors,
--           lpDS1ChanCommentText,
--           lpSdhTestBytesTx,
--           lpE1SnmpOperStatus,
--           lpDS3PlcpErroredSec,
--           lpDS3DS1ChanTcSigTwoValue,
--           lpJT2SevErroredFrmSec,
--           lpV35LineStatusTimeOut,
--           lpJT2TestBitErrorRate,
--           lpV35CommentText,
--           lpSdhUnusableTxClockRefAlarm,
--           lpJT2ProceduralStatus,
--           lpDS1FrmErrors,
--           lpDS3PlcpFarEndErrorFreeSec,
--           lpDS1ChanStorageType,
--           lpJT2LofAlarm,
--           lpE1ChanTestBitsRx,
--           lpSonetTestCustomizedPattern,
--           lpE1ChanTestFrmTx,
--           lpCpuUtil,
--           lpSonetPathCustomerIdentifier,
--           lpV35StorageType,
--           lpLinkToApplicationsValue,
--           lpDS3CBitFarEndCodeViolations,
--           lpE1ChanUnknownStatus,
--           lpSdhTestTimeRemaining,
--           lpE3StandbyStatus,
--           lpX21TestType,
--           lpE1ChanTestDataStartDelay,
--           lpDS1ChanAdminState,
--           lpDS3CellCorrectableHeaderErrors,
--           lpDS3DS1TestTimeRemaining,
--           lpDS3DS1ErroredSec,
--           lpE3PlcpFarEndErroredSec,
--           lpComponentName,
--           lpHssiDataXferStateChanges,
--           lpV35AdminState,
--           lpE1SevErroredFrmSec,
--           lpSdhPathRxAisAlarm,
--           lpEngDsOvComponentName,
--           lpDS3DS1ChanTcStorageType,
--           lpE1ChanTestFrmRx,
--           lpE1Vendor,
--           lpDS3DS1ChanTcSignalOneDuration,
--           lpDS1AudioComponentName,
--           lpX21CommentText,
--           lpHssiApplicationFramerName,
--           lpSonetStandbyStatus,
--           lpSdhTestBytesRx,
--           lpDS3ClockingSource,
--           lpX21OperationalState,
--           lpE1ChanCustomerIdentifier,
--           lpX21DteDataClockSource,
--           lpDS1ChanTestStorageType,
--           lpSdhPathIfAdminStatus,
--           lpSonetPathSnmpOperStatus,
--           lpX21StorageType,
--           lpDS3DS1LofAlarm,
--           lpHssiTestCustomizedPattern,
--           lpJT2CellAlarmActDelay,
--           lpE1OperationalState,
--           lpJT2CrcErrors,
--           lpDS3DS1ChanSnmpOperStatus,
--           lpDS3DS1StorageType,
--           lpSonetTestBitErrorRate,
--           lpDS3DS1UnavailSec,
--           lpX21AdminState,
--           lpDS1ChanTestAdminState,
--           lpX21ComponentName,
--           lpDS3ComponentName,
--           lpDS1TestRowStatus,
--           lpE1MultifrmLofAlarm,
--           lpX21LineStatusTimeOut,
--           lpV35TestAdminState,
--           lpE3TestOperationalState,
--           lpE1ChanTcSignalOneDuration,
--           lpSonetPathPathCodeViolations,
--           lpDS3DS1FrmErrors,
--           lpHssiLineSpeed,
--           lpSonetTestUsageState,
--           lpDS3TestBitErrorRate,
--           lpSonetPathCellScrambleCellPayload,
--           lpDS1ChanAlarmStatus,
--           lpDS3LofAlarm,
--           lpJT2ApplicationFramerName,
--           lpSonetTestBitsTx,
--           lpHssiUsageState,
--           lpHssiAdminState,
--           lpSdhPathCellReceiveCellUtilization,
--           lpSdhSectSevErroredSec,
--           lpV35AlarmStatus,
--           lpDS3DS1TestBytesRx,
--           lpDS3CellAlarmActDelay,
--           lpE3CustomerIdentifier,
--           lpSonetPathCellStorageType,
--           lpX21TestStorageType,
--           lpDS1ChanProceduralStatus,
--           lpDS3CellRowStatus,
--           lpSdhPathFarEndPathErrorFreeSec,
--           lpE1TestOperationalState,
--           lpDS3DS1ChanVendor,
--           lpDS3DS1TestStorageType,
--           lpJT2TestBitsTx,
--           lpDS1ProceduralStatus,
--           lpSonetTestBitsRx,
--           lpE1DspComponentName,
--           lpUsageState,
--           lpSdhPathPathErrorFreeSec,
--           lpX21TestAdminState,
--           lpSdhPathCellCorrectSingleBitHeaderErrors,
--           lpE1RaiDeclareAlarmTime,
--           lpJT2TestOperationalState,
--           lpE1ChanCellScrambleCellPayload,
--           lpSdhSnmpOperStatus,
--           lpJT2CellSevErroredSec,
--           lpDS3DS1TestAdminState,
--           lpSdhTestType,
--           lpDS3DS1ChanOperationalState,
--           lpDS1LosStateChanges,
--           lpSdhPathSignalLabelMismatch,
--           lpE1AudioRowStatus,
--           lpSdhSectErroredSec,
--           lpE1ChanCellStorageType,
--           lpX21AlarmStatus,
--           lpE3CellCorrectSingleBitHeaderErrors,
--           lpDS3Vendor,
--           lpSdhTestDataStartDelay,
--           lpE3PlcpFarEndErrorFreeSec,
--           lpDS3DS1AlarmStatus,
--           lpE1ChanTestErroredFrmRx,
--           lpDS3DS1ChanIfIndex,
--           lpE3TestBytesTx,
--           lpE3G832FarEndErroredSec,
--           lpV35LineState,
--           lpE3LineFailures,
--           lpE3PlcpErrorFreeSec,
--           lpV35TestBitsTx,
--           lpE3TestCustomizedPattern,
--           lpDS3DS1RunningTime,
--           lpDS3IfAdminStatus,
--           lpE1ChanTcReplacementData,
--           lpSonetTestFrmTx,
--           lpE1ChanTestCauseOfTermination,
--           lpSdhSectSevErroredFrmSec,
--           lpSdhPathFarEndPathFailures,
--           lpE1SendRaiOnAis,
--           lpDS3ApplicationFramerName,
--           lpDS1StandbyStatus,
--           lpDS1ChanTestBytesTx,
--           lpDS3DS1ChanTestOperationalState,
--           lpSonetPathRxAisAlarm,
--           lpSdhPathCellTransmitCellUtilization,
--           lpDS3IfIndex,
--           lpE3TestBytesRx,
--           lpSdhFarEndLineSevErroredSec,
--           lpX21ActualRxLineSpeed,
--           lpDS1CrcErrors,
--           lpE1ChanCellRowStatus,
--           lpJT2CellLcdAlarm,
--           lpSonetLineFailures,
--           lpE1TestCustomizedPattern,
--           lpMsgBlockCapacity,
--           lpV35IfIndex,
--           lpJT2OperationalState,
--           lpE3IfAdminStatus,
--           lpSdhLineSevErroredSec,
--           lpDS3TestBitsTx,
--           lpJT2ClockingSource,
--           lpE3G832FarEndUnavailSec,
--           lpE3PlcpLofAlarm,
--           lpHssiComponentName,
--           lpE3G832StorageType,
--           lpE1TestBytesRx,
--           lpJT2LineLength,
--           lpSdhTestStorageType,
--           lpSonetPathFarEndPathFailures,
--           lpDS1SevErroredSec,
--           lpDS1ChanRowStatus,
--           lpE1SevErroredSec,
--           lpSonetSnmpOperStatus,
--           lpDS1TestBitsTx,
--           lpDS3DS1TestType,
--           lpDS3DS1ChanActualChannelSpeed,
--           lpE1ChanControlStatus,
--           lpV35RowStatus,
--           lpE1LosStateChanges,
--           lpHssiVendor,
--           lpSdhTestAdminState,
--           lpSonetPathOperationalState,
--           lpX21IfIndex,
--           lpSonetTestTimeRemaining,
--           lpDS3ErrorFreeSec,
--           lpHssiTestFrmTx,
--           lpSdhPathComponentName,
--           lpDS3DS1ChanCellCorrectSingleBitHeaderErrors,
--           lpJT2AlarmStatus,
--           lpDS3DS1IfIndex,
--           lpDS3DS1ChanTimeslotDataRate,
--           lpJT2SnmpOperStatus,
--           lpV35ReadyLineState,
--           lpE3CellTransmitCellUtilization,
--           lpHssiTestComponentName,
--           lpDS3DS1ChanProceduralStatus,
--           lpSdhRxAisAlarm,
--           lpDS3DS1ChanTestBytesTx,
--           lpDS1TestBitsRx,
--           lpSonetSectErroredSec,
--           lpJT2ErrorFreeSec,
--           lpDS3DS1ChanTestCustomizedPattern,
--           lpDS1ChanCellComponentName,
--           lpDS1ErrorFreeSec,
--           lpDS1ChanTcIngressConditioning,
--           lpDS1ChanTestRowStatus,
--           lpE3TestAdminState,
--           lpSonetPathRowStatus,
--           lpStorageType,
--           lpE1ChanCellCorrectableHeaderErrors,
--           lpDS1ChanAvailabilityStatus,
--           lpSdhPathOperationalState,
--           lpV35TestRowStatus,
--           lpJT2TestCauseOfTermination,
--           lpDS3DS1RowStatus,
--           lpE1ChanTestElapsedTime,
--           lpSdhPathFarEndPathAisLopSec,
--           lpDS1AudioStorageType,
--           lpAdminState,
--           lpSdhPathTxRdi,
--           lpX21ReadyLineState,
--           lpJT2Vendor,
--           lpSonetOperationalState,
--           lpDS3LineFailures,
--           lpSonetSectLosSec,
--           lpE3CellReceiveCellUtilization,
--           lpDS3CBitCbitErroredSec,
--           lpSonetPathProceduralStatus,
--           lpE1ChanStandbyStatus,
--           lpSdhPathRxRfiAlarm,
--           lpDS3DS1ZeroCoding,
--           lpV35DataXferStateChanges,
--           lpE3ComponentName,
--           lpDS1ChanTestPurpose,
--           lpE1ChanTcComponentName,
--           lpSdhRxRfiAlarm,
--           lpSonetPathCellAlarmActDelay,
--           lpSdhFarEndLineAisSec,
--           lpDS3RxRaiAlarm,
--           lpX21TestRowStatus,
--           lpE1TestAdminState,
--           lpSonetAdminState,
--           lpDS3DS1ChanTcRowStatus,
--           lpSdhLineAisSec,
--           lpDS3DS1TestRowStatus,
--           lpE3G832UnexpectedPayloadType,
--           lpDS3SnmpOperStatus,
--           lpDS3DS1AvailabilityStatus,
--           lpX21ClockingSource,
--           lpDS3DS1ChanTcSigOneValue,
--           lpE1ComponentName,
--           lpSonetClockingSource,
--           lpSonetFarEndLineAisSec,
--           lpDS3CBitCbitUnavailSec,
--           lpDS3PlcpFarEndUnavailableSec,
--           lpDS3DS1ClockingSource,
--           lpDS3DS1ChanTestStorageType,
--           lpSdhTestFrmRx,
--           lpDS3TestFrmSize,
--           lpSdhIfIndex,
--           lpDS3DS1ChanCellTransmitCellUtilization,
--           lpDS3OperationalState,
--           lpE3PlcpFarEndCodingViolations,
--           lpDS1SlipErrors,
--           lpSdhPathCellUncorrectableHecErrors,
--           lpE3TestComponentName,
--           lpAlarmStatus,
--           lpDS1SnmpOperStatus,
--           lpJT2CellComponentName,
--           lpE3G832FarEndCodeViolations,
--           lpE1DspStorageType,
--           lpE3OperationalState,
--           lpE3PlcpCodingViolations,
--           lpE1TxAisAlarm,
--           lpMemoryUsageAvgMinValue,
--           lpDS3CBitFarEndFailures,
--           lpDS3DS1LineType,
--           lpDS3LineLength,
--           lpDS3DS1SevErroredFrmSec,
--           lpDS1ChanTestFrmTx,
--           lpE3TestFrmPatternType,
--           lpDS3PlcpLofAlarm,
--           lpDS3DS1ChanTestFrmPatternType,
--           lpDS1ChanUnknownStatus,
--           lpSdhRowStatus,
--           lpJT2CellCorrectableHeaderErrors,
--           lpHssiSnmpOperStatus,
--           lpE1TestComponentName,
--           lpV35TestFrmTx,
--           lpDS1ChanTestDataStartDelay,
--           lpE3TestBitErrorRate,
--           lpSdhUsageState,
--           lpSonetPathApplicationFramerName,
--           lpE3AvailabilityStatus,
--           lpV35UnknownStatus,
--           lpSdhPathUnknownStatus,
--           lpDS3DS1ChanCellReceiveCellUtilization,
--           lpV35TestDataStartDelay,
--           lpDS1ChanTestOperationalState,
--           lpDS1SevErroredFrmSec,
--           lpE3UsageState,
--           lpEngDsOvRowStatus,
--           lpSonetPathAlarmStatus,
--           lpDS1OperationalState,
--           lpSdhPathPathAisLopSec,
--           lpDS1ChanTestFrmRx,
--           lpDS1Vendor,
--           lpEngDsRowStatus,
--           lpDS3DS1ChanComponentName,
--           lpDS3TestFrmPatternType,
--           lpDS1ChanTestDuration,
--           lpV35TestFrmRx,
--           lpDS1ChanCustomerIdentifier,
--           lpSonetTestBytesTx,
--           lpSonetPathCellLcdAlarm,
--           lpJT2UnavailSec,
--           lpDS1AdminState,
--           lpV35TestDuration,
--           lpJT2CellCorrectSingleBitHeaderErrors,
--           lpE3CellUncorrectableHecErrors,
--           lpV35CustomerIdentifier,
--           lpE3TestFrmSize,
--           lpE1ChanApplicationFramerName,
--           lpDS3DS1TestBytesTx,
--           lpE1UsageState,
--           lpDS3DS1CustomerIdentifier,
--           lpE3G832TrailTraceTransmitted,
--           lpSdhTestRowStatus,
--           lpX21TestTimeRemaining,
--           lpX21UnknownStatus,
--           lpDS3TxIdle,
--           lpSonetPathPathFailures,
--           lpDS3DS1TestFrmTx,
--           lpSonetPathTxRdi,
--           lpX21TestDataStartDelay,
--           lpV35TestStorageType,
--           lpE1TestBitErrorRate,
--           lpDS3CBitLoopbackAtFarEndRequested,
--           lpDS3DS1UnknownStatus,
--           lpE1TxRaiAlarm,
--           lpSdhPathPathSevErroredSec,
--           lpSonetTestBytesRx,
--           lpDS3DS1TestDataStartDelay,
--           lpE3TestUsageState,
--           lpHssiActualRxLineSpeed,
--           lpE1TestFrmSize,
--           lpDS3DS1ChanTestComponentName,
--           lpSonetIfAdminStatus,
--           lpX21TestFrmRx,
--           lpHssiActualTxLineSpeed,
--           lpDS3RxIdle,
--           lpDS3DS1TestFrmRx,
--           lpJT2ControlStatus,
--           lpX21CustomerIdentifier,
--           lpSonetLineErroredSec,
--           lpE1RxRaiAlarm,
--           lpV35AvailabilityStatus,
--           lpDS3DS1TestDuration,
--           lpDS1ChanVendor,
--           lpDS1TestOperationalState,
--           lpE1TestUsageState,
--           lpJT2TestBytesTx,
--           lpJT2CustomerIdentifier,
--           lpHssiControlStatus,
--           lpE3PlcpSevErroredSec,
--           lpDS1ChanTcComponentName,
--           lpRowStatus,
--           lpV35DataTransferLineState,
--           lpV35ActualLinkMode,
--           lpDS1ChanCellScrambleCellPayload,
--           lpSdhPathFarEndPathCodeViolations,
--           lpDS1ChanIfAdminStatus,
--           lpE3TestDisplayInterval,
--           lpDS1ChanTestDisplayInterval,
--           lpDS3DS1ChanUsageState,
--           lpDS3CBitCbitCodeViolations,
--           lpDS1AudioRowStatus,
--           lpE1TestElapsedTime,
--           lpSpareCardStatus,
--           lpHssiTestBytesTx,
--           lpV35TestDisplayInterval,
--           lpDS1DspComponentName,
--           lpDS3CellCorrectSingleBitHeaderErrors,
--           lpSonetFarEndLineErrorFreeSec,
--           lpE1ChanTcSigTwoValue,
--           lpE1TestBytesTx,
--           lpSdhLineErroredSec,
--           lpE3TestType,
--           lpDS1ChanTestErroredFrmRx,
--           lpHssiTestType,
--           lpDS3TestBytesTx,
--           lpDS3DS1ChanCellUncorrectableHecErrors,
--           lpDS3DS1ChanCellLcdAlarm,
--           lpJT2TestFrmTx,
--           lpDS3PlcpErrorFreeSec,
--           lpDS3TestCustomizedPattern,
--           lpSdhPathStorageType,
--           lpJT2CellTransmitCellUtilization,
--           lpX21DataTransferLineState,
--           lpX21ActualLinkMode,
--           lpDS1ChanTestCauseOfTermination,
--           lpE3CommentText,
--           lpHssiTestOperationalState,
--           lpAvailabilityStatus,
--           lpE1ErroredSec,
--           lpDS3PathSevErroredSec,
--           lpV35TestCauseOfTermination,
--           lpSdhUnknownStatus,
--           lpE1TestType,
--           lpDS3DS1ChanTestUsageState,
--           lpSonetLineUnavailSec,
--           lpDS3DS1OperationalState,
--           lpE1TestFrmPatternType,
--           lpX21TestDisplayInterval,
--           lpDS1TestBytesTx,
--           lpE3StorageType,
--           lpHssiStorageType,
--           lpSonetSectSevErroredFrmSec,
--           lpE1ChanTcStorageType,
--           lpV35StandbyStatus,
--           lpDS3DS1TestDisplayInterval,
--           lpSdhLineUnavailSec,
--           lpE3PathSevErroredSec,
--           lpSonetPathAdminState,
--           lpDS1ChanTimeslots,
--           lpJT2TestFrmPatternType,
--           lpMsgBlockUsage,
--           lpDS3DS1AdminState,
--           lpX21TestErroredFrmRx,
--           lpE3AdminState,
--           lpActiveCard,
--           lpSdhTestDuration,
--           lpSdhTxRdi,
--           lpJT2CellReceiveCellUtilization,
--           lpDS3DS1TestErroredFrmRx,
--           lpE1DspRowStatus,
--           lpSdhTestCauseOfTermination,
--           lpE1ChanSnmpOperStatus,
--           lpE1StorageType,
--           lpE3LineSevErroredSec,
--           lpE1UnavailSec,
--           lpJT2FrameErrors,
--           lpX21TestCauseOfTermination,
--           lpX21AvailabilityStatus,
--           lpDS3TestComponentName,
--           lpDS1IfAdminStatus,
--           lpDS3TestPurpose,
--           lpDS3TestBitsRx,
--           lpDS3DS1TestCauseOfTermination,
--           lpDS1ChanControlStatus,
--           lpSonetVendor,
--           lpDS3DS1TxAisAlarm,
--           lpE3PlcpComponentName,
--           lpE1AdminState,
--           lpJT2AvailabilityStatus,
--           lpE3TestStorageType,
--           lpV35ControlStatus,
--           lpSdhTxAis,
--           lpE3TestTimeRemaining,
--           lpSonetTestFrmPatternType,
--           lpDS3DS1ChanTestTimeRemaining,
--           lpE1TestTimeRemaining,
--           lpSdhPathAvailabilityStatus,
--           lpDS3DS1ChanTestType,
--           lpDS1ChanCellSevErroredSec,
--           lpDS3CellTransmitCellUtilization,
--           lpSonetTestComponentName,
--           lpDS3DS1TestPurpose,
--           lpE1Crc4Mode,
--           lpSdhFarEndLineUnavailSec,
--           lpSdhSectCodeViolations,
--           lpDS1TestPurpose,
--           lpSonetTestOperationalState,
--           lpSdhPathRowStatus,
--           lpSonetPathUnknownStatus,
--           lpE1ChanVendor,
--           lpSdhTestFrmTx,
--           lpSdhPathCellSevErroredSec,
--           lpE1TestStorageType,
--           lpSonetErrorFreeSec,
--           lpJT2RxAisPhysicalAlarm,
--           lpSonetRxRfiAlarm,
--           lpE3TestRowStatus,
--           lpSonetTestFrmSize,
--           lpDS3DS1ChanCommentText,
--           lpE3AlarmStatus,
--           lpDS1ChanCellCorrectableHeaderErrors,
--           lpSonetPathFarEndPathCodeViolations,
--           lpDS3DS1ChanIfAdminStatus,
--           lpHssiOperationalState,
--           lpV35LinkMode,
--           lpDS1ChanTcEgressConditioning,
--           lpE1TestPurpose,
--           lpX21ControlStatus,
--           lpSonetUnusableTxClockRefAlarm,
--           lpE1ChanOperationalState,
--           lpUnknownStatus,
--           lpDS3DS1ChanTestBitsRx,
--           lpDS3DS1ChanStorageType,
--           lpE3RunningTime,
--           lpHssiTestBytesRx,
--           lpHssiTestAdminState,
--           lpDS3DS1ControlStatus,
--           lpX21LineSpeed,
--           lpV35TestElapsedTime,
--           lpSdhTestDisplayInterval,
--           lpSonetUsageState,
--           lpE3ClockingSource,
--           lpDS3CellReceiveCellUtilization,
--           lpSdhPathIfIndex,
--           lpSonetComponentName,
--           lpE1AlarmStatus,
--           lpJT2TestPurpose,
--           lpSonetFarEndLineFailures,
--           lpDS3DS1ChanAdminState,
--           lpSdhPathPathErroredSec,
--           lpE3Mapping,
--           lpHssiStandbyStatus,
--           lpDS1ControlStatus,
--           lpE3G832FarEndSefAisSec,
--           lpDS1TestFrmPatternType,
--           lpHssiTestBitErrorRate,
--           lpSdhTestErroredFrmRx,
--           lpE1RunningTime,
--           lpCustomerIdentifier,
--           lpSdhLosAlarm,
--           lpDS3CBitFarEndAlarm,
--           lpX21LinkMode,
--           lpE3PlcpUnavailSec,
--           lpSonetRxAisAlarm,
--           lpSonetPathControlStatus,
--           lpDS3CbitParity,
--           lpE1ChanTestOperationalState,
--           lpE3CellSevErroredSec,
--           lpSdhCommentText,
--           lpDS3CBitFarEndErrorFreeSec,
--           lpX21TestElapsedTime,
--           lpJT2CellRowStatus,
--           lpDS1ChanTestBitErrorRate,
--           lpDS1ComponentName,
--           lpV35TestErroredFrmRx,
--           lpJT2CellUncorrectableHecErrors,
--           lpJT2TestFrmSize,
--           lpDS1TestDataStartDelay,
--           lpSdhFarEndLineCodeViolations,
--           lpSonetTxAis,
--           lpV35TestBitErrorRate,
--           lpJT2TestUsageState,
--           lpDS3DS1TestBitErrorRate,
--           lpDS1ChanCellAlarmActDelay,
--           lpDS3DS1ChanTestPurpose,
--           lpDS3PlcpFarEndCodingViolations,
--           lpE1ChanProceduralStatus,
--           lpE3Vendor,
--           lpE3RxAisAlarm,
--           lpDS1ChanCellRowStatus,
--           lpJT2RxRaiAlarm,
--           lpSdhStorageType,
--           lpJT2SevErroredSec,
--           lpDS1DspStorageType,
--           lpJT2TestBytesRx,
--           lpDS3PlcpCodingViolations,
--           lpE3PlcpRxRaiAlarm,
--           lpE3IfIndex,
--           lpSonetPathRxRfiAlarm,
--           lpDS3DS1ChanAlarmStatus,
--           lpSdhTestBitsRx,
--           lpE3PathUnavailSec,
--           lpSdhPathCellComponentName,
--           lpE1ChanActualChannelSpeed,
--           lpE1ChanCellAlarmActDelay,
--           lpE3RxRaiAlarm,
--           lpJT2ErroredSec,
--           lpE1RaiClearAlarmTime,
--           lpDS1TestComponentName,
--           lpDS3DS1CommentText,
--           lpX21TestBitErrorRate,
--           lpSonetPathFarEndPathErrorFreeSec,
--           lpDS3DS1ChanTestBytesRx,
--           lpE1ChanCellCorrectSingleBitHeaderErrors,
--           lpX21RowStatus,
--           lpSdhPathAlarmStatus,
--           lpE1IfIndex,
--           lpSdhTestFrmSize,
--           lpE1ChanTimeslotDataRate,
--           lpE1TxMultifrmRaiAlarm,
--           lpDS3UsageState,
--           lpSdhControlStatus,
--           lpSonetPathPathErrorFreeSec,
--           lpE3RowStatus,
--           lpHssiTestStorageType,
--           lpE1ChanTcRowStatus,
--           lpSonetPathIfAdminStatus,
--           lpE1RxAisAlarm,
--           lpE3Framing,
--           lpE1ChanTimeslots,
--           lpE1ChanTestCustomizedPattern,
--           lpJT2StandbyStatus,
--           lpE3PathSefAisSec,
--           lpV35ActualTxLineSpeed,
--           lpLogicalProcessorType,
--           lpE3LinkAlarmScanInterval,
--           lpHssiTestDisplayInterval,
--           lpDS1AlarmStatus,
--           lpE3LineErroredSec,
--           lpDS3CellLcdAlarm,
--           lpDS1ChanApplicationFramerName,
--           lpE1RxMultifrmRaiAlarm,
--           lpDS1UsageState,
--           lpDS3DS1ChanCellSevErroredSec,
--           lpEngDsAgentQueueSize,
--           lpE1RowStatus,
--           lpSonetCommentText,
--           lpE3LineLosSec,
--           lpHssiAlarmStatus,
--           lpV35ApplicationFramerName,
--           lpE3PlcpErroredSec,
--           lpDS1RaiAlarmType,
--           lpSdhPathPathUnavailSec,
--           lpDS3CBitRowStatus,
--           lpJT2TestElapsedTime,
--           lpSdhCustomerIdentifier,
--           lpE3TestElapsedTime,
--           lpDS1TxRaiAlarm,
--           lpDS1AvailabilityStatus,
--           lpE3PlcpSevErroredFramingSec,
--           lpE1ChanIfAdminStatus,
--           lpDS1ChanTestBitsTx,
--           lpE1ChanTestBytesTx,
--           lpMemoryUsageAvgMaxValue,
--           lpX21StandbyStatus,
--           lpSdhTestUsageState,
--           lpDS1TestFrmSize,
--           lpDS3DS1ChanTestFrmSize,
--           lpDS1RxAisAlarm,
--           lpDS3DS1StandbyStatus,
--           lpE1ChanTestDisplayInterval,
--           lpSonetPathCellTransmitCellUtilization,
--           lpDS3PathFailures,
--           lpHssiTestDataStartDelay,
--           lpE3PathErroredSec,
--           lpSonetFarEndLineSevErroredSec,
--           lpDS3DS1CrcErrors,
--           lpDS3LineLosSec,
--           lpDS3PlcpFarEndSevErroredSec,
--           lpJT2TestTimeRemaining,
--           lpDS1TestUsageState,
--           lpX21ApplicationFramerName,
--           lpE1TestRowStatus,
--           lpDS1ChanIfIndex,
--           lpHssiTestFrmRx,
--           lpSonetPathFarEndPathUnavailSec,
--           lpE1AvailabilityStatus,
--           lpV35TestBitsRx }
-- STATUS  mandatory
-- DESCRIPTION
--   "A list of all current accessible leaf objects."

logicalProcessorGroup OBJECT IDENTIFIER ::= { logicalProcessorMIB 1 }
logicalProcessorGroupBE OBJECT IDENTIFIER ::= { logicalProcessorGroup 5 }
logicalProcessorGroupBE01 OBJECT IDENTIFIER ::= { logicalProcessorGroupBE 2 }
logicalProcessorGroupBE01A OBJECT IDENTIFIER ::= { logicalProcessorGroupBE01 2 }



-- Agent-Capabilities Statement:

-- PRODUCT-RELEASE "Passport Release 7.0 LogicalProcessor."
-- STATUS          mandatory
-- DESCRIPTION     "LogicalProcessor MIB: MIB Version BE01A,
--                  Software Version BG00S4C."
-- SUPPORTS        Nortel-Magellan-Passport-LogicalProcessorMIB
--    INCLUDES     { logicalProcessorGroupBE01A }

logicalProcessorCapabilities OBJECT IDENTIFIER ::= { logicalProcessorMIB 3 }
logicalProcessorCapabilitiesBE OBJECT IDENTIFIER ::= { logicalProcessorCapabilities 5 }
logicalProcessorCapabilitiesBE01 OBJECT IDENTIFIER ::= { logicalProcessorCapabilitiesBE 2 }
logicalProcessorCapabilitiesBE01A OBJECT IDENTIFIER ::= { logicalProcessorCapabilitiesBE01 2 }





END
