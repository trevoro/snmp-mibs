-- *****************************************************************
-- NMS-EPON-Pon.MIB:  NMS LLID Pon MIB file
-- AUG 2009
-- *****************************************************************
--

NMS-EPON-PON-QOS-POLICY DEFINITIONS ::= BEGIN

            IMPORTS
            IpAddress
				FROM RFC1155-SMI
		    OBJECT-TYPE
				FROM RFC-1212
            DisplayString
				FROM RFC1213-MIB
		    nmsEPONGroup
				FROM NMS-SMI
		    TruthValue,RowStatus,PhysAddress,DisplayString,QosPolicy
		    	FROM SNMPv2-TC;
          
                  nmsEponPonQosPolicy        OBJECT IDENTIFIER ::= { nmsEPONGroup 104}
             
nmsEponPonQosPolicyTable	OBJECT-TYPE
		SYNTAX		SEQUENCE OF NmsEponPonQosPolicyEntry
		MAX-ACCESS	not-accessible
		STATUS		current
		DESCRIPTION	"A list of nmsEponPonQosPolicyEntry entries. 
				 The port-based security mac address information."
					::= { nmsEponPonQosPolicy 1 }		
	                       
		nmsEponPonQosPolicyEntry	OBJECT-TYPE
				SYNTAX		NmsEponPonQosPolicyEntry
				MAX-ACCESS	not-accessible
				STATUS		current
				DESCRIPTION	
							"Policy Map Apply operation.(PonIfIndex_PonQosPolicy)to Apply a  
		                   Policy Map.For example,'07_q1'will apply the policy map 'q1' to Pon 7.
		                   For 3305, the EPON will return a error symbol to indicate  a unsuccessful operation. "
				INDEX		{ PonIfIndex,PonQosPolicy}
				::= { nmsEponPonQosPolicyTable 1 }
       
		NmsEponPonQosPolicyEntry	::= SEQUENCE { 
                   	ponIfIndex						INTEGER,                   
		       		ponQosPolicy				DisplayString,
		            ponQosPolicyCreate		DisplayString, 
                    ponQosPolicyDel			TruthValue
  				}
		  
               ponIfIndex OBJECT-TYPE
                   SYNTAX  INTEGER
                   ACCESS  read-only
                   STATUS  current
                   DESCRIPTION
                           "LLID interface id, unique in system."
                   ::= { nmsEponPonQosPolicyEntry 1 } 
               
               ponQosPolicy OBJECT-TYPE
                   SYNTAX  DisplayString
                   ACCESS  read-only
                   STATUS  current
                   DESCRIPTION
                           "A unique string for each Policy Map up to 20 characters. 
 							This string is part of index of Table."
                   ::= { nmsEponPonQosPolicyEntry 2 } 

               ponQosPolicyCreate OBJECT-TYPE
                   SYNTAX  DisplayString
                   ACCESS  read-write
                   STATUS  current
                   DESCRIPTION
		                   "Policy Map Apply operation.(PonIfIndex_PonQosPolicy)to Apply a  
		                   Policy Map.For example,'07_q1'will apply the policy map 'q1' to Pon 7.
		                   For 3305 ,the EPON will return a error symbol to indicate 
		                   a unsuccessful operation. " 
		           ::= { nmsEponPonQosPolicyEntry 3 }  
               ponQosPolicyDel OBJECT-TYPE
                   SYNTAX  TruthValue
                   ACCESS  read-write
                   STATUS  current
                   DESCRIPTION
                           "Pon  Policy Map delete flag,True(1) will delete the Policy Map."
                   ::= { nmsEponPonQosPolicyEntry 4} 
             
             

              	
END
