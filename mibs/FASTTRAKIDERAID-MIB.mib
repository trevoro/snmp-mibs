-- MIB generated by miftomib version 1.0a

FASTTRAKIDERAID-MIB DEFINITIONS ::= BEGIN

-- This component represents the configuration of the FastTrak IDERAID 
-- Controller manufactured by Promise Technology, Inc.

IMPORTS
	TRAP-TYPE FROM RFC-1215
    OBJECT-TYPE
    FROM RFC-1212
    enterprises
    FROM RFC1155-SMI
    DisplayString
    FROM RFC1213-MIB;

DmiInteger			::= INTEGER
DmiDisplaystring	::= DisplayString
DmiDateX			::= OCTET STRING (SIZE (28))
DmiComponentIndex	::= INTEGER

promise               	OBJECT IDENTIFIER ::= {enterprises 7933}
intel	             	OBJECT IDENTIFIER ::= {promise 343}
fasttrak		      	OBJECT IDENTIFIER ::= {intel 1}
isc3xtraps          	OBJECT IDENTIFIER ::= {fasttrak 1}
dmtfGroups          	OBJECT IDENTIFIER ::= {isc3xtraps 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines the attributes common to all components.
 This group is required."
	::= {dmtfGroups 1}

eComponentid OBJECT-TYPE
	SYNTAX		SComponentid
	ACCESS		not-accessible
	STATUS		mandatory
	DESCRIPTION	""
	INDEX		{DmiComponentIndex}
	::= {tComponentid 1}

a1Manufacturer OBJECT-TYPE
	SYNTAX		DmiDisplaystring
	ACCESS		read-only
	STATUS		mandatory
	DESCRIPTION	"Manufacturer of this system."
	::= {eComponentid 1}

a1Product OBJECT-TYPE
	SYNTAX		DmiDisplaystring
	ACCESS		read-only
	STATUS		mandatory
	DESCRIPTION	"Product name for this system."
	::= {eComponentid 2}

a1Version OBJECT-TYPE
	SYNTAX		DmiDisplaystring
	ACCESS		read-only
	STATUS		mandatory
	DESCRIPTION	"Version number of this system."
	::= {eComponentid 3}

a1SerialNumber OBJECT-TYPE
	SYNTAX		DmiDisplaystring
	ACCESS		read-only
	STATUS		mandatory
	DESCRIPTION	"Serial number for this system."
	::= {eComponentid 4}

a1Installation OBJECT-TYPE
	SYNTAX		DmiDateX
	ACCESS		read-only
	STATUS		mandatory
	DESCRIPTION	"The time and date when this component was installed."
	::= {eComponentid 5}

a1Verify OBJECT-TYPE
	SYNTAX		INTEGER {
		vAnErrorOccurredCheckStatusCode         	(0),
		vThisComponentDoesNotExist              	(1),
		vVerificationIsNotSupported             	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is still installed and working."
	::= {eComponentid 6}

SDiskController ::= SEQUENCE {
	a45DiskControllerIndex                  	DmiInteger,
	a45FruGroupIndex                        	DmiInteger,
	a45OperationalGroupIndex                	DmiInteger,
	a45SystemSlotIndex                      	DmiInteger,
	a45DiskControllerIdentification         	DmiDisplaystring,
	a45ControllerSoftwareRevisionLevel      	DmiDisplaystring,
	a45ControllerChannelCount               	DmiInteger,
	a45ControllerMaximumDevices             	DmiInteger
}

tDiskController OBJECT-TYPE
	SYNTAX		SEQUENCE OF SDiskController
	ACCESS		not-accessible
	STATUS		mandatory
	DESCRIPTION	"This group defines the disk controller in this system."
	::= {dmtfGroups 45}

eDiskController OBJECT-TYPE
	SYNTAX		SDiskController
	ACCESS		not-accessible
	STATUS		mandatory
	DESCRIPTION	""
	INDEX		{DmiComponentIndex, a45DiskControllerIndex}
	::= {tDiskController 1}

a45DiskControllerIndex OBJECT-TYPE
	SYNTAX		DmiInteger
	ACCESS		read-only
	STATUS		mandatory
	DESCRIPTION	"Index value used by the system to identify the disk controller."
	::= {eDiskController 1}

a45FruGroupIndex OBJECT-TYPE
	SYNTAX		DmiInteger
	ACCESS		read-only
	STATUS		mandatory
	DESCRIPTION	"If this is a Field Replaceable Unit or if it is part of another
FRU, this provides an index into the FRU table; 'value = -1' indicates that
the group is not a FRU."
	::= {eDiskController 2}

a45OperationalGroupIndex OBJECT-TYPE
	SYNTAX		DmiInteger
	ACCESS		read-only
	STATUS		mandatory
	DESCRIPTION	"The index into the Operational State table for this device."
	::= {eDiskController 3}

a45SystemSlotIndex OBJECT-TYPE
	SYNTAX		DmiInteger
	ACCESS		read-only
	STATUS		mandatory
	DESCRIPTION	"Index value in System Slot table of disk Controller. 0 =
no slot"
	::= {eDiskController 4}

a45DiskControllerIdentification OBJECT-TYPE
	SYNTAX		DmiDisplaystring
	ACCESS		read-only
	STATUS		mandatory
	DESCRIPTION	"Name, brand and hardware revision level of the disk controller."
	::= {eDiskController 5}

a45ControllerSoftwareRevisionLevel OBJECT-TYPE
	SYNTAX		DmiDisplaystring
	ACCESS		read-only
	STATUS		mandatory
	DESCRIPTION	"Level and version of the software associated with this controlle
."
	::= {eDiskController 6}

a45ControllerChannelCount OBJECT-TYPE
	SYNTAX		DmiInteger
	ACCESS		read-only
	STATUS		mandatory
	DESCRIPTION	"The number of channels supported by this controller. 0x80000000
= Unknown"
	::= {eDiskController 7}

a45ControllerMaximumDevices OBJECT-TYPE
	SYNTAX		DmiInteger
	ACCESS		read-only
	STATUS		mandatory
	DESCRIPTION	"The maximum number of devices for all channels which can
be controlled by this disk controller. 0x80000000 = Unknown "
	::= {eDiskController 8}

SDisks ::= SEQUENCE {
	a49StorageType                          	DmiInteger,
	a49DiskIndex                            	DmiInteger,
	a49StorageInterfaceType                 	DmiInteger,
	a49InterfaceDescription                 	DmiDisplaystring,
	a49MediaLoaded                          	DmiInteger,
	a49RemovableDrive                       	DmiInteger,
	a49RemovableMedia                       	DmiInteger,
	a49DeviceId                             	DmiInteger,
	a49LogicalUnitNumber                    	DmiInteger,
	a49NumberOfPhysicalCylinders            	DmiInteger,
	a49NumberOfPhysicalSectorsPerTrack      	DmiInteger,
	a49NumberOfPhysicalHeads                	DmiInteger,
	a49PhysicalCylinderForWritePrecompensati	DmiInteger,
	a49PhysicalCylinderForLandingZone       	DmiInteger,
	a49SectorSize                           	DmiInteger,
	a49TotalPhysicalSize                    	DmiInteger,
	a49NumberOfCurrentBadBlocksOrSectors    	DmiInteger,
	a49Partitions                           	DmiInteger,
	a49PhysicalLocation                     	DmiInteger,
	a49FruGroupIndex                        	DmiInteger,
	a49OperationalGroupIndex                	DmiInteger,
	a49SecuritySettings                     	DmiInteger
}

tDisks OBJECT-TYPE
	SYNTAX		SEQUENCE OF SDisks
	ACCESS		not-accessible
	STATUS		mandatory
	DESCRIPTION	"This group defines the physical attributes of disk mass storage
devices in this system."
	::= {dmtfGroups 49}

eDisks OBJECT-TYPE
	SYNTAX		SDisks
	ACCESS		not-accessible
	STATUS		mandatory
	DESCRIPTION	""
	INDEX		{DmiComponentIndex, a49StorageType, a49DiskIndex}
	::= {tDisks 1}

a49StorageType OBJECT-TYPE
	SYNTAX		INTEGER {
		vOther                                  	(1),
		vUnknown                                	(2),
		vHardDisk                               	(3),
		vFloppyDisk                             	(4),
		vOpticalRom                             	(5),
		vOpticalWorm                            	(6),
		vOpticalRw                              	(7),
		vCompactDisk                            	(8),
		vFlashDisk                              	(9),
		vBernoulli                              	(10),
		vOpticalFloppyDisk                      	(11),
		vDigitalVersatileDiskDvdDrive           	(12),
		vDigitalVersatileDiskDvdRamDrive        	(13)
	}
	ACCESS		read-only
	STATUS		mandatory
	DESCRIPTION	"The type of this mass storage device."
	::= {eDisks 1}

a49DiskIndex OBJECT-TYPE
	SYNTAX		DmiInteger
	ACCESS		read-only
	STATUS		mandatory
	DESCRIPTION	"An index into the disk table."
	::= {eDisks 2}

a49StorageInterfaceType OBJECT-TYPE
	SYNTAX		INTEGER {
		vOther                                  	(1),
		vUnknown                                	(2),
		vScsi                                   	(3),
		vEsdi                                   	(4),
		vIde                                    	(5),
		vCmd                                    	(6),
		vIpi                                    	(7),
		vSt506                                  	(8),
		vDssi                                   	(9),
		vParallelPort                           	(10),
		vHippi                                  	(11),
		vQic2                                   	(12),
		vFloppyDiskInterface                    	(13),
		vPcmcia                                 	(14),
		vEnhancedAtaide                         	(15)
	}
	ACCESS		read-only
	STATUS		mandatory
	DESCRIPTION	"The interface used by this mass storage device."
	::= {eDisks 3}

a49InterfaceDescription OBJECT-TYPE
	SYNTAX		DmiDisplaystring
	ACCESS		read-only
	STATUS		mandatory
	DESCRIPTION	"A longer description of the mass storage interface.  For
example, SCSI2 fast wide."
	::= {eDisks 4}

a49MediaLoaded OBJECT-TYPE
	SYNTAX		INTEGER {
		vFalse                                  	(0),
		vTrue                                   	(1)
	}
	ACCESS		read-only
	STATUS		mandatory
	DESCRIPTION	"If true, the media is loaded."
	::= {eDisks 5}

a49RemovableDrive OBJECT-TYPE
	SYNTAX		INTEGER {
		vFalse                                  	(0),
		vTrue                                   	(1)
	}
	ACCESS		read-only
	STATUS		mandatory
	DESCRIPTION	"If true, this drive is removable."
	::= {eDisks 6}

a49RemovableMedia OBJECT-TYPE
	SYNTAX		INTEGER {
		vFalse                                  	(0),
		vTrue                                   	(1)
	}
	ACCESS		read-only
	STATUS		mandatory
	DESCRIPTION	"If true, the media in this drive is removable."
	::= {eDisks 7}

a49DeviceId OBJECT-TYPE
	SYNTAX		DmiInteger
	ACCESS		read-only
	STATUS		mandatory
	DESCRIPTION	"The SCSI address of this device."
	::= {eDisks 8}

a49LogicalUnitNumber OBJECT-TYPE
	SYNTAX		DmiInteger
	ACCESS		read-only
	STATUS		mandatory
	DESCRIPTION	"The logical unit number of this SCSI device."
	::= {eDisks 9}

a49NumberOfPhysicalCylinders OBJECT-TYPE
	SYNTAX		DmiInteger
	ACCESS		read-only
	STATUS		mandatory
	DESCRIPTION	"The number of reported physical cylinders on this device."
	::= {eDisks 10}

a49NumberOfPhysicalSectorsPerTrack OBJECT-TYPE
	SYNTAX		DmiInteger
	ACCESS		read-only
	STATUS		mandatory
	DESCRIPTION	"The number of reported physical sectors per track for this
device."
	::= {eDisks 11}

a49NumberOfPhysicalHeads OBJECT-TYPE
	SYNTAX		DmiInteger
	ACCESS		read-only
	STATUS		mandatory
	DESCRIPTION	"The number of reported physical heads for this device."
	::= {eDisks 12}

a49PhysicalCylinderForWritePrecompensati OBJECT-TYPE
	SYNTAX		DmiInteger
	ACCESS		read-only
	STATUS		mandatory
	DESCRIPTION	"Specifies the physical cylinder used for write precompensation
on this device."
	::= {eDisks 13}

a49PhysicalCylinderForLandingZone OBJECT-TYPE
	SYNTAX		DmiInteger
	ACCESS		read-only
	STATUS		mandatory
	DESCRIPTION	"The physical landing zone cylinder of this device."
	::= {eDisks 14}

a49SectorSize OBJECT-TYPE
	SYNTAX		DmiInteger
	ACCESS		read-only
	STATUS		mandatory
	DESCRIPTION	"The size in bytes of the physical disk sector or logical
block as reported by the disk."
	::= {eDisks 15}

a49TotalPhysicalSize OBJECT-TYPE
	SYNTAX		DmiInteger
	ACCESS		read-only
	STATUS		mandatory
	DESCRIPTION	"The total size in kilobytes (1024 bytes) of this device that
is available to users"
	::= {eDisks 16}

a49NumberOfCurrentBadBlocksOrSectors OBJECT-TYPE
	SYNTAX		DmiInteger
	ACCESS		read-only
	STATUS		mandatory
	DESCRIPTION	"The number of current bad blocks or sectors to include total
of both factory assigned and grown defects."
	::= {eDisks 17}

a49Partitions OBJECT-TYPE
	SYNTAX		DmiInteger
	ACCESS		read-only
	STATUS		mandatory
	DESCRIPTION	"The number of partitions on this storage unit."
	::= {eDisks 18}

a49PhysicalLocation OBJECT-TYPE
	SYNTAX		INTEGER {
		vOther                                  	(1),
		vUnknown                                	(2),
		vInternal                               	(3),
		vExternal                               	(4)
	}
	ACCESS		read-only
	STATUS		mandatory
	DESCRIPTION	"The physical location of this disk drive assembly relative
to the system enclosure."
	::= {eDisks 19}

a49FruGroupIndex OBJECT-TYPE
	SYNTAX		DmiInteger
	ACCESS		read-only
	STATUS		mandatory
	DESCRIPTION	"If this is a Field Replaceable Unit or if it is part of another
FRU, this provides an index into the FRU table; 'value = -1' indicates that
the group is not a FRU."
	::= {eDisks 20}

a49OperationalGroupIndex OBJECT-TYPE
	SYNTAX		DmiInteger
	ACCESS		read-only
	STATUS		mandatory
	DESCRIPTION	"The index into the Operational State table for this device."
	::= {eDisks 21}

a49SecuritySettings OBJECT-TYPE
	SYNTAX		INTEGER {
		vOther                                  	(1),
		vUnknown                                	(2),
		vNone                                   	(3),
		vRead-only                              	(4),
		vLockoutEnabled                         	(5),
		vBoot-bypass                            	(6),
		vBoot-bypass-Read-only                  	(7)
	}
	ACCESS		read-only
	STATUS		mandatory
	DESCRIPTION	"Enum describing the current hardware security settings on
this device"
	::= {eDisks 22}

SMassStoreArrayInfoTable ::= SEQUENCE {
	a85LogicalDriveIndex                    	DmiInteger,
	a85DriveArrayLevel                      	DmiInteger,
	a85DriveArrayRedundancyStatus           	DmiInteger,
	a85DriveArrayOperationInProgress        	DmiInteger
}

tMassStoreArrayInfoTable OBJECT-TYPE
	SYNTAX		SEQUENCE OF SMassStoreArrayInfoTable
	ACCESS		not-accessible
	STATUS		mandatory
	DESCRIPTION	"This table is a parallel table to the Mass Store Logical
Drives Table; it has entries keyed by the same unique index as is used for
the logical drives table. This table has one entry corresponding to each
entry in the Mass Store Logical Drives Table whose 'Drive Array' field is
set to TRUE."
	::= {dmtfGroups 85}

eMassStoreArrayInfoTable OBJECT-TYPE
	SYNTAX		SMassStoreArrayInfoTable
	ACCESS		not-accessible
	STATUS		mandatory
	DESCRIPTION	""
	INDEX		{DmiComponentIndex, a85LogicalDriveIndex}
	::= {tMassStoreArrayInfoTable 1}

a85LogicalDriveIndex OBJECT-TYPE
	SYNTAX		DmiInteger
	ACCESS		read-only
	STATUS		mandatory
	DESCRIPTION	"This is the same index as the 'Logical Drive Index' field
in the Mass Store Logical Drives Table. "
	::= {eMassStoreArrayInfoTable 1}

a85DriveArrayLevel OBJECT-TYPE
	SYNTAX		INTEGER {
		vOther                                  	(1),
		vUnknown                                	(2),
		vRaid0                                  	(3),
		vRaid1                                  	(4),
		vRaid2                                  	(5),
		vRaid3                                  	(6),
		vRaid4                                  	(7),
		vRaid5                                  	(8),
		vRaid7                                  	(9),
		vRaid10                                 	(10)
	}
	ACCESS		read-only
	STATUS		mandatory
	DESCRIPTION	"This attribute is an Enum of the different possible types
of drive arrays that could compose the logical drive represented by the correspo
ding entry in the Mass Store Logical Drives Table."
	::= {eMassStoreArrayInfoTable 2}

a85DriveArrayRedundancyStatus OBJECT-TYPE
	SYNTAX		INTEGER {
		vOther                                  	(1),
		vUnknown                                	(2),
		vFullyRedundant                         	(3),
		vDegradedRedundancy                     	(4),
		vRedundancyLost                         	(5),
		vNotApplicableUnitNotRedundant          	(6),
		vUnitFailed                             	(7)
	}
	ACCESS		read-only
	STATUS		mandatory
	DESCRIPTION	"This attribute identifies which of the different states of
the available redundancy in the drive array currently applies."
	::= {eMassStoreArrayInfoTable 5}

a85DriveArrayOperationInProgress OBJECT-TYPE
	SYNTAX		INTEGER {
		vOther                                  	(1),
		vUnknown                                	(2),
		vVerify                                 	(3),
		vRebuild                                	(5),
		vNone                                   	(6)
	}
	ACCESS		read-only
	STATUS		mandatory
	DESCRIPTION	"This value of this attribute describes whether the drive
array is currently undergoing array operations of some sort."
	::= {eMassStoreArrayInfoTable 6}

SMassStoreLogicalDrivesTable ::= SEQUENCE {
	a86LogicalDriveIndex                    	DmiInteger,
	a86TopOfHierarchy                       	DmiInteger,
	a86DriveArray                           	DmiInteger,
	a86LogicalDriveSizeInKb                 	DmiInteger,
	a86LogicalDriveBlockSizeInBytes         	DmiInteger,
	a86LogicalDriveNameString               	DmiDisplaystring
}

tMassStoreLogicalDrivesTable OBJECT-TYPE
	SYNTAX		SEQUENCE OF SMassStoreLogicalDrivesTable
	ACCESS		not-accessible
	STATUS		mandatory
	DESCRIPTION	"This table describes the logical drives contained in this
component. Logical drives are typically composed of one or more other logical
drives or physical segments. Each entry of this table contains information
about the size of a logical drive, its string name as set by driver software,
and a boolean that describes whether this logical drive is at the top of
the logical drive hierarchy or not."
	::= {dmtfGroups 86}

eMassStoreLogicalDrivesTable OBJECT-TYPE
	SYNTAX		SMassStoreLogicalDrivesTable
	ACCESS		not-accessible
	STATUS		mandatory
	DESCRIPTION	""
	INDEX		{DmiComponentIndex, a86LogicalDriveIndex}
	::= {tMassStoreLogicalDrivesTable 1}

a86LogicalDriveIndex OBJECT-TYPE
	SYNTAX		DmiInteger
	ACCESS		read-only
	STATUS		mandatory
	DESCRIPTION	"A unique index (key) into the Mass Store Logical Drives Table."
	::= {eMassStoreLogicalDrivesTable 1}

a86TopOfHierarchy OBJECT-TYPE
	SYNTAX		INTEGER {
		vFalse                                  	(0),
		vTrue                                   	(1)
	}
	ACCESS		read-only
	STATUS		mandatory
	DESCRIPTION	"This attribute identifies whether the logical drive represented
by this entry is a part of some higher order logical drive or not. If the
value of this boolean attribute is TRUE, then this means that this logical
drive is not a constituent part of any other logical drive in this component."
	::= {eMassStoreLogicalDrivesTable 2}

a86DriveArray OBJECT-TYPE
	SYNTAX		INTEGER {
		vFalse                                  	(0),
		vTrue                                   	(1)
	}
	ACCESS		read-only
	STATUS		mandatory
	DESCRIPTION	"This boolean attribute identifies whether the logical drive
represented by this table entry is composed of an array of drives or not.
If the value of this attribute is TRUE, then the entry with the same index
(as this entry) in the Mass Store Array Info Table will give information
about the drive array that comprises this logical drive"
	::= {eMassStoreLogicalDrivesTable 3}

a86LogicalDriveSizeInKb OBJECT-TYPE
	SYNTAX		DmiInteger
	ACCESS		read-only
	STATUS		mandatory
	DESCRIPTION	"This attribute holds the size of this logical drive in kilobytes"
	::= {eMassStoreLogicalDrivesTable 4}

a86LogicalDriveBlockSizeInBytes OBJECT-TYPE
	SYNTAX		DmiInteger
	ACCESS		read-only
	STATUS		mandatory
	DESCRIPTION	"This attribute holds the size of the allocatable unit of
storage on this logical drive. The size of the allocatable unit is given
in bytes"
	::= {eMassStoreLogicalDrivesTable 5}

a86LogicalDriveNameString OBJECT-TYPE
	SYNTAX		DmiDisplaystring
	ACCESS		read-write
	STATUS		mandatory
	DESCRIPTION	"This attribute is simply a container for a string name for
the logical drive.  The instrumentation code does not assign or manipulate
this attribute. It is simply a convenience provided so that driver software
may put in this container the string name by which it refers to this logical
drive."
	::= {eMassStoreLogicalDrivesTable 6}

SMassStoreMappingTable ::= SEQUENCE {
	a87MappingIndex                         	DmiInteger,
	a87ParentDrive                          	DmiInteger,
	a87ChildSegment                         	DmiInteger
}

tMassStoreMappingTable OBJECT-TYPE
	SYNTAX		SEQUENCE OF SMassStoreMappingTable
	ACCESS		not-accessible
	STATUS		mandatory
	DESCRIPTION	"This table represents mappings between logical drives and
logical or physical drive segments. Each entry in this table describes *one*
such mapping. A logical drive may be composed of one, *or more*, such mappings.
A segment may be a part of a physical or logical drive or, in the degenerate
case, the entire drive may be one segment. The table also contains two fields,
namely: (a) 'Parent Drive' a unique index into the Mass Store Logical Drives
Table describing the logical drive involved in the mapping, "
	::= {dmtfGroups 87}

eMassStoreMappingTable OBJECT-TYPE
	SYNTAX		SMassStoreMappingTable
	ACCESS		not-accessible
	STATUS		mandatory
	DESCRIPTION	""
	INDEX		{DmiComponentIndex, a87MappingIndex}
	::= {tMassStoreMappingTable 1}

a87MappingIndex OBJECT-TYPE
	SYNTAX		DmiInteger
	ACCESS		read-only
	STATUS		mandatory
	DESCRIPTION	"Unique index into the Mass Store Mapping Table"
	::= {eMassStoreMappingTable 1}

a87ParentDrive OBJECT-TYPE
	SYNTAX		DmiInteger
	ACCESS		read-only
	STATUS		mandatory
	DESCRIPTION	"Unique index into the Mass Store Logical Drives Table of
the entry that represents the parent drive in this mapping."
	::= {eMassStoreMappingTable 2}

a87ChildSegment OBJECT-TYPE
	SYNTAX		DmiInteger
	ACCESS		read-only
	STATUS		mandatory
	DESCRIPTION	"This field contains the index of the logical or physical
segment that is one of the constituents of the parent logical drive referenced
by the attribute 'Parent Drive'.This index is a key into the Mass Store Segment
Table."
	::= {eMassStoreMappingTable 3}

SMassStoreSegmentTable ::= SEQUENCE {
	a88SegmentIndex                         	DmiInteger,
	a88SegmentType                          	DmiInteger,
	a88SegmentStart                         	DmiInteger,
	a88SegmentLength                        	DmiInteger,
	a88SegmentAllocationUnit                	DmiInteger,
	a88SegmentAllocationState               	DmiInteger,
	a88DriveKey1                            	DmiInteger,
	a88DriveKey2                            	DmiInteger
}

tMassStoreSegmentTable OBJECT-TYPE
	SYNTAX		SEQUENCE OF SMassStoreSegmentTable
	ACCESS		not-accessible
	STATUS		mandatory
	DESCRIPTION	"This table describes the various segments on the various
physical or logical drives in the component. In some cases a segment may
represent an entire drive. In other cases there may be multiple segments
on a drive."
	::= {dmtfGroups 88}

eMassStoreSegmentTable OBJECT-TYPE
	SYNTAX		SMassStoreSegmentTable
	ACCESS		not-accessible
	STATUS		mandatory
	DESCRIPTION	""
	INDEX		{DmiComponentIndex, a88SegmentIndex}
	::= {tMassStoreSegmentTable 1}

a88SegmentIndex OBJECT-TYPE
	SYNTAX		DmiInteger
	ACCESS		read-only
	STATUS		mandatory
	DESCRIPTION	"This is a unique index for this segment and is used as a
key into this table"
	::= {eMassStoreSegmentTable 1}

a88SegmentType OBJECT-TYPE
	SYNTAX		INTEGER {
		vPhysical                               	(1),
		vLogical                                	(2)
	}
	ACCESS		read-only
	STATUS		mandatory
	DESCRIPTION	"Describes whether the segment is a physical segment on a
physical drive or a logical segment on a logical drive. If the value of this
attribute is 'Physical' then the physical drive is identified in the Disks
table by Drive Key 1 and Drive Key 2 attributes. If the value of this attribute
is 'Logical' then the logical drive is identified in the Mass Store Logical
Drives table by the Drive Key 2 attribute and the Drive Key 1 attribute is
irrelevant"
	::= {eMassStoreSegmentTable 2}

a88SegmentStart OBJECT-TYPE
	SYNTAX		DmiInteger
	ACCESS		read-only
	STATUS		mandatory
	DESCRIPTION	"This is the index of the allocation unit on the drive at
which the media extent corresponding to this segment starts."
	::= {eMassStoreSegmentTable 3}

a88SegmentLength OBJECT-TYPE
	SYNTAX		DmiInteger
	ACCESS		read-only
	STATUS		mandatory
	DESCRIPTION	"This is the length of the segment in allocation units inclusive
of the starting allocation unit whose index is contained in the attribute
'Segment Start'."
	::= {eMassStoreSegmentTable 4}

a88SegmentAllocationUnit OBJECT-TYPE
	SYNTAX		INTEGER {
		vOther                                  	(1),
		vUnknown                                	(2),
		vPhysicalSector                         	(3),
		vLogicalBlock                           	(4)
	}
	ACCESS		read-only
	STATUS		mandatory
	DESCRIPTION	"The value of this attribute identifies the type of unit of
space that can be allocated on the drive."
	::= {eMassStoreSegmentTable 5}

a88SegmentAllocationState OBJECT-TYPE
	SYNTAX		INTEGER {
		vOther                                  	(1),
		vUnknown                                	(2),
		vAllocated                              	(3),
		vAvailable                              	(4),
		vDefective                              	(5),
		vReserved1                              	(6),
		vSpare                                  	(7)
	}
	ACCESS		read-only
	STATUS		mandatory
	DESCRIPTION	"The value of this attribute identifies the current allocation
state of the segment represented by this table entry. NOTE: Reserved = This
segment is reserved for vendor use (DO NOT USE this segment for other purposes);
Spare = This segment is currently in use being held in reserve for hot sparing."
	::= {eMassStoreSegmentTable 6}

a88DriveKey1 OBJECT-TYPE
	SYNTAX		INTEGER {
		vOther                                  	(1),
		vUnknown                                	(2),
		vHardDisk                               	(3),
		vFloppyDisk                             	(4),
		vOpticalRom                             	(5),
		vOpticalWorm                            	(6),
		vOpticalRw                              	(7),
		vCompactDisk                            	(8),
		vFlashDisk                              	(9),
		vBernoulli                              	(10),
		vOpticalFloppyDisk                      	(11)
	}
	ACCESS		read-only
	STATUS		mandatory
	DESCRIPTION	"If Segment Type is 'Physical' this is one of two keys used
to identify a specific disk in the Disks group. If the Segment Type is 'Logical'
this attribute is unused and its value is irrelevant."
	::= {eMassStoreSegmentTable 7}

a88DriveKey2 OBJECT-TYPE
	SYNTAX		DmiInteger
	ACCESS		read-only
	STATUS		mandatory
	DESCRIPTION	"(A) If the value of the attribute Segment Type is 'Physical'
then this attribute holds the second of two keys that identify the physical
drive in the Disks table group. (B) If the value of the Segment Type is 'Logical
 then this is the single integer key that identifies the logical drive in
the Mass Store Logical Drives table."
	::= {eMassStoreSegmentTable 8}

SMiftomib ::= SEQUENCE {
	a99MibName                              	DmiDisplaystring,
	a99MibOid                               	DmiDisplaystring,
	a99DisableTrap                          	DmiInteger
}

tMiftomib OBJECT-TYPE
	SYNTAX		SEQUENCE OF SMiftomib
	ACCESS		not-accessible
	STATUS		mandatory
	DESCRIPTION	"This group defines attributes required for DMI to
SNMP translati
n."
	::= {dmtfGroups 99}

eMiftomib OBJECT-TYPE
	SYNTAX		SMiftomib
	ACCESS		not-accessible
	STATUS		mandatory
	DESCRIPTION	""
	INDEX		{DmiComponentIndex}
	::= {tMiftomib 1}

a99MibName OBJECT-TYPE
	SYNTAX		DmiDisplaystring
	ACCESS		read-only
	STATUS		mandatory
	DESCRIPTION	"The MIB name that defines this MIF"
	::= {eMiftomib 1}

a99MibOid OBJECT-TYPE
	SYNTAX		DmiDisplaystring
	ACCESS		read-only
	STATUS		mandatory
	DESCRIPTION	"The MIB Object Identifier that corresponds to this MIF"
	::= {eMiftomib 2}

a99DisableTrap OBJECT-TYPE
	SYNTAX		DmiInteger
	ACCESS		read-write
	STATUS		mandatory
	DESCRIPTION	"This attribute can be changed to disable sending of traps
from this component"
	::= {eMiftomib 3}

SEventState ::= SEQUENCE {
	a100EventIndex                          	DmiInteger,
	a100EventGenerationGroupClass           	DmiDisplaystring,
	a100EventType                           	DmiInteger,
	a100CurrentState                        	DmiInteger,
	a100AssociatedGroupObject               	DmiDisplaystring
}

tEventState OBJECT-TYPE
	SYNTAX		SEQUENCE OF SEventState
	ACCESS		not-accessible
	STATUS		mandatory
	DESCRIPTION	"This table holds the current state of each state-based event"
	::= {dmtfGroups 100}

eEventState OBJECT-TYPE
	SYNTAX		SEventState
	ACCESS		not-accessible
	STATUS		mandatory
	DESCRIPTION	""
	INDEX		{DmiComponentIndex, a100EventIndex}
	::= {tEventState 1}

a100EventIndex OBJECT-TYPE
	SYNTAX		DmiInteger
	ACCESS		read-only
	STATUS		mandatory
	DESCRIPTION	"A unique index into the Event State table"
	::= {eEventState 1}

a100EventGenerationGroupClass OBJECT-TYPE
	SYNTAX		DmiDisplaystring
	ACCESS		read-only
	STATUS		mandatory
	DESCRIPTION	"The Class String of the event generator group within the
generatingComponent"
	::= {eEventState 2}

a100EventType OBJECT-TYPE
	SYNTAX		DmiInteger
	ACCESS		read-only
	STATUS		mandatory
	DESCRIPTION	"Integer value that identifies one of the event types enumeratedi
 the associated Event Generation group"
	::= {eEventState 3}

a100CurrentState OBJECT-TYPE
	SYNTAX		INTEGER {
		vOk                                     	(4),
		vNon-critical                           	(8),
		vCritical                               	(16),
		vNon-recoverable                        	(32)
	}
	ACCESS		read-only
	STATUS		mandatory
	DESCRIPTION	"The current state of the Event type identified by the Event
Typeattribute in this row"
	::= {eEventState 4}

a100AssociatedGroupObject OBJECT-TYPE
	SYNTAX		DmiDisplaystring
	ACCESS		read-only
	STATUS		mandatory
	DESCRIPTION	"A list of integer keys that identify the instance of theAssociat
d Group that actually generated the state-based event.The list of integer
keys are represented in the value of thisattribute as a string containing
a comma-separated list ofintegers. The management application must parse
this string toobtain the list of integer keys."
	::= {eEventState 5}

SEventGenerationForDiskController ::= SEQUENCE {
	a238EventType                           	DmiInteger,
	a238EventSeverity                       	DmiInteger,
	a238IsEventState-based                  	DmiInteger,
	a238EventStateKey                       	DmiInteger,
	a238AssociatedGroup                     	DmiDisplaystring,
	a238EventSystem                         	DmiInteger,
	a238EventSubsystem                      	DmiInteger
}

tEventGenerationForDiskController OBJECT-TYPE
	SYNTAX		SEQUENCE OF SEventGenerationForDiskController
	ACCESS		not-accessible
	STATUS		mandatory
	DESCRIPTION	""
	::= {dmtfGroups 238}

eEventGenerationForDiskController OBJECT-TYPE
	SYNTAX		SEventGenerationForDiskController
	ACCESS		not-accessible
	STATUS		mandatory
	DESCRIPTION	""
	INDEX		{DmiComponentIndex, a238AssociatedGroup}
	::= {tEventGenerationForDiskController 1}

a238EventType OBJECT-TYPE
	SYNTAX		INTEGER {
		vInitializationFailure                  	(1),
		vConfigurationError                     	(2)
	}
	ACCESS		read-only
	STATUS		mandatory
	DESCRIPTION	"The type of event that has occurred."
	::= {eEventGenerationForDiskController 1}

a238EventSeverity OBJECT-TYPE
	SYNTAX		INTEGER {
		vMonitor                                	(1),
		vInformation                            	(2),
		vOk                                     	(4),
		vNon-critical1                          	(8),
		vCritical                               	(16),
		vNon-recoverable1                       	(32)
	}
	ACCESS		read-only
	STATUS		mandatory
	DESCRIPTION	"The severity of this event."
	::= {eEventGenerationForDiskController 2}

a238IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationForDiskController 3}

a238EventStateKey OBJECT-TYPE
	SYNTAX		DmiInteger
	ACCESS		read-only
	STATUS		mandatory
	DESCRIPTION	"A unique, single integer key into the EventState group if
this is a state-based Event.  If this is not a state-based Event then this
attribute's value is not defined."
	::= {eEventGenerationForDiskController 4}

a238AssociatedGroup OBJECT-TYPE
	SYNTAX		DmiDisplaystring
	ACCESS		read-only
	STATUS		mandatory
	DESCRIPTION	"The class name of the group that is associated with the events
defined in this EventGeneration group."
	::= {eEventGenerationForDiskController 5}

a238EventSystem OBJECT-TYPE
	SYNTAX		INTEGER {
		vOther                                  	(0),
		vUnknown                                	(1)
	}
	ACCESS		read-only
	STATUS		mandatory
	DESCRIPTION	"The major functional aspect of the product causing the fault."
	::= {eEventGenerationForDiskController 6}

a238EventSubsystem OBJECT-TYPE
	SYNTAX		INTEGER {
		vOther                                  	(0),
		vUnknown                                	(1)
	}
	ACCESS		read-only
	STATUS		mandatory
	DESCRIPTION	"The minor functional aspect of the product causing the fault."
	::= {eEventGenerationForDiskController 7}

SEventGenerationForDisks ::= SEQUENCE {
	a239EventType                           	DmiInteger,
	a239EventSeverity                       	DmiInteger,
	a239IsEventState-based                  	DmiInteger,
	a239EventStateKey                       	DmiInteger,
	a239AssociatedGroup                     	DmiDisplaystring,
	a239EventSystem                         	DmiInteger,
	a239EventSubsystem                      	DmiInteger
}

tEventGenerationForDisks OBJECT-TYPE
	SYNTAX		SEQUENCE OF SEventGenerationForDisks
	ACCESS		not-accessible
	STATUS		mandatory
	DESCRIPTION	""
	::= {dmtfGroups 239}

eEventGenerationForDisks OBJECT-TYPE
	SYNTAX		SEventGenerationForDisks
	ACCESS		not-accessible
	STATUS		mandatory
	DESCRIPTION	""
	INDEX		{DmiComponentIndex, a239AssociatedGroup}
	::= {tEventGenerationForDisks 1}

a239EventType OBJECT-TYPE
	SYNTAX		INTEGER {
		vPhysicalDeviceStatusChange             	(1),
		vInitializationFailure                  	(2),
		vConfigurationError                     	(3)
	}
	ACCESS		read-only
	STATUS		mandatory
	DESCRIPTION	"The type of event that has occurred."
	::= {eEventGenerationForDisks 1}

a239EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForDisks 2}

a239IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationForDisks 3}

a239EventStateKey OBJECT-TYPE
	SYNTAX		DmiInteger
	ACCESS		read-only
	STATUS		mandatory
	DESCRIPTION	"A unique, single integer key into the Event State group if
this is a state-based Event.  If this is not a state-based Event then this
attribute's value is not defined."
	::= {eEventGenerationForDisks 4}

a239AssociatedGroup OBJECT-TYPE
	SYNTAX		DmiDisplaystring
	ACCESS		read-only
	STATUS		mandatory
	DESCRIPTION	"The class name of the group that is associated with the events
defined in this EventGeneration group."
	::= {eEventGenerationForDisks 5}

a239EventSystem OBJECT-TYPE
	SYNTAX		INTEGER {
		vOther                                  	(0),
		vUnknown                                	(1)
	}
	ACCESS		read-only
	STATUS		mandatory
	DESCRIPTION	"The major functional aspect of the product causing the fault."
	::= {eEventGenerationForDisks 6}

a239EventSubsystem OBJECT-TYPE
	SYNTAX		INTEGER {
		vOther                                  	(0),
		vUnknown                                	(1)
	}
	ACCESS		read-only
	STATUS		mandatory
	DESCRIPTION	"The minor functional aspect of the product causing the fault."
	::= {eEventGenerationForDisks 7}

SEventGenerationForMassStoreLogicalDrive ::= SEQUENCE {
	a244EventType                           	DmiInteger,
	a244EventSeverity                       	DmiInteger,
	a244IsEventState-based                  	DmiInteger,
	a244EventStateKey                       	DmiInteger,
	a244AssociatedGroup                     	DmiDisplaystring,
	a244EventSystem                         	DmiInteger,
	a244EventSubsystem                      	DmiInteger
}

tEventGenerationForMassStoreLogicalDrive OBJECT-TYPE
	SYNTAX		SEQUENCE OF SEventGenerationForMassStoreLogicalDrive
	ACCESS		not-accessible
	STATUS		mandatory
	DESCRIPTION	""
	::= {dmtfGroups 244}

eEventGenerationForMassStoreLogicalDrive OBJECT-TYPE
	SYNTAX		SEventGenerationForMassStoreLogicalDrive
	ACCESS		not-accessible
	STATUS		mandatory
	DESCRIPTION	""
	INDEX		{DmiComponentIndex, a244AssociatedGroup}
	::= {tEventGenerationForMassStoreLogicalDrive 1}

a244EventType OBJECT-TYPE
	SYNTAX		INTEGER {
		vPhysicalDeviceStatusChange             	(1),
		vHotSpareActivated                      	(2),
		vLogicalDeviceStatusChange              	(3),
		vInitializationFailure                  	(4),
		vConfigurationError                     	(5)
	}
	ACCESS		read-only
	STATUS		mandatory
	DESCRIPTION	"The type of event that has occurred."
	::= {eEventGenerationForMassStoreLogicalDrive 1}

a244EventSeverity OBJECT-TYPE
	SYNTAX		INTEGER {
		vMonitor                                	(1),
		vInformation                            	(2),
		vOk                                     	(4),
		vNon-critical                           	(8),
		vCritical                               	(16),
		vNon-recoverable                        	(32)
	}
	ACCESS		read-only
	STATUS		mandatory
	DESCRIPTION	"The severity of this event."
	::= {eEventGenerationForMassStoreLogicalDrive 2}

a244IsEventState-based OBJECT-TYPE
	SYNTAX		INTEGER {
		vFalse                                  	(0),
		vTrue                                   	(1)
	}
	ACCESS		read-only
	STATUS		mandatory
	DESCRIPTION	"The value of this attribute determines whether the Event
being reported is a state-based Event or not. If the value of this attribute
is TRUE then the Event is state-based. Otherwise the Event is not state-based."
	::= {eEventGenerationForMassStoreLogicalDrive 3}

a244EventStateKey OBJECT-TYPE
	SYNTAX		DmiInteger
	ACCESS		read-only
	STATUS		mandatory
	DESCRIPTION	"A unique, single integer key into the Event State group if
this is a state-based Event.  If this is not a state-based Event then this
attribute's value is not defined."
	::= {eEventGenerationForMassStoreLogicalDrive 4}

a244AssociatedGroup OBJECT-TYPE
	SYNTAX		DmiDisplaystring
	ACCESS		read-only
	STATUS		mandatory
	DESCRIPTION	"The class name of the group that is associated with the events
defined in this EventGeneration group."
	::= {eEventGenerationForMassStoreLogicalDrive 5}

a244EventSystem OBJECT-TYPE
	SYNTAX		INTEGER {
		vOther                                  	(0),
		vUnknown                                	(1)
	}
	ACCESS		read-only
	STATUS		mandatory
	DESCRIPTION	"The major functional aspect of the product causing the fault."
	::= {eEventGenerationForMassStoreLogicalDrive 6}

a244EventSubsystem OBJECT-TYPE
	SYNTAX		INTEGER {
		vOther                                  	(0),
		vUnknown                                	(1)
	}
	ACCESS		read-only
	STATUS		mandatory
	DESCRIPTION	"The minor functional aspect of the product causing the fault."
	::= {eEventGenerationForMassStoreLogicalDrive 7}

-- Here is the TRAP definition for the MIB
-- Append this to the MIB produced by MIFTOMIB
-- DO NOT CHANGE ANYTHING in this definition, SNMP-DMI translator only
--         handles this specific format of the TRAP
-- changing this format WILL cause trnaslator to fail

tTrapGroup OBJECT-TYPE
    SYNTAX        SEQUENCE OF STrapGroup
    ACCESS        not-accessible
    STATUS        mandatory
    DESCRIPTION    "This group defines attributes needed for Trap
            definition. This group does not exist in MIF file"
    ::= {dmtfGroups 9999}

STrapGroup ::= SEQUENCE {
    a9999ErrorTime              DisplayString,
    a9999ErrorStatus            DmiInteger,
    a9999ErrorGroupId           DmiInteger,
    a9999ErrorInstanceId        DmiInteger,
    a9999ComponentId            DmiInteger,
    a9999GroupId                DmiInteger,
    a9999InstanceId             DmiInteger,
    a9999VendorCode1            DmiInteger,
    a9999VendorCode2            DmiInteger,
    a9999VendorText             OCTET STRING,
    a9999ParentGroupId          DmiInteger,
    a9999ParentInstanceId       DmiInteger
}

eTrapGroup OBJECT-TYPE
    SYNTAX        STrapGroup
    ACCESS        not-accessible
    STATUS        mandatory
    DESCRIPTION    ""
    INDEX        {DmiComponentIndex}
    ::= {tTrapGroup 1}

a9999ErrorTime OBJECT-TYPE
    SYNTAX        DisplayString
    ACCESS        read-only
    STATUS        mandatory
    DESCRIPTION    "The Date & Time when the error occured"
    ::= {eTrapGroup 1}

a9999ErrorStatus OBJECT-TYPE
    SYNTAX        DmiInteger
    ACCESS        read-only
    STATUS        mandatory
    DESCRIPTION    "Error Status Code"
    ::= {eTrapGroup 2}

a9999ErrorGroupId OBJECT-TYPE
    SYNTAX        DmiInteger
    ACCESS        read-only
    STATUS        mandatory
    DESCRIPTION    "Group ID of the errorControl Group"
    ::= {eTrapGroup 3}

a9999ErrorInstanceId OBJECT-TYPE
    SYNTAX        DmiInteger
    ACCESS        read-only
    STATUS        mandatory
    DESCRIPTION    "Instance ID of the errorControl Group"
    ::= {eTrapGroup 4}

a9999ComponentId OBJECT-TYPE
    SYNTAX        DmiInteger
    ACCESS        read-only
    STATUS        mandatory
    DESCRIPTION    "Component ID of the component that caused this error"
    ::= {eTrapGroup 5}

a9999GroupId OBJECT-TYPE
    SYNTAX        DmiInteger
    ACCESS        read-only
    STATUS        mandatory
    DESCRIPTION    "Group ID of the Group that caused this error"
    ::= {eTrapGroup 6}

a9999InstanceId OBJECT-TYPE
    SYNTAX        DmiInteger
    ACCESS        read-only
    STATUS        mandatory
    DESCRIPTION    "Instance ID of the Group that caused this error"
    ::= {eTrapGroup 7}

a9999VendorCode1 OBJECT-TYPE
    SYNTAX        DmiInteger
    ACCESS        read-only
    STATUS        mandatory
    DESCRIPTION    "Vendor specific code 1"
    ::= {eTrapGroup 8}

a9999VendorCode2 OBJECT-TYPE
    SYNTAX        DmiInteger
    ACCESS        read-only
    STATUS        mandatory
    DESCRIPTION    "Vendor specific code 2"
    ::= {eTrapGroup 9}

a9999VendorText OBJECT-TYPE
    SYNTAX        OCTET STRING
    ACCESS        read-only
    STATUS        mandatory
    DESCRIPTION    "Vendor specific octet string info"
    ::= {eTrapGroup 10}

a9999ParentGroupId OBJECT-TYPE
    SYNTAX        DmiInteger
    ACCESS        read-only
    STATUS        mandatory
    DESCRIPTION    "Group ID of parent of Group that caused this error"
    ::= {eTrapGroup 11}

a9999ParentInstanceId OBJECT-TYPE
    SYNTAX        DmiInteger
    ACCESS        read-only
    STATUS        mandatory
    DESCRIPTION    "Instance ID of parent of Group that caused this error"
    ::= {eTrapGroup 12}

dmtfEventError TRAP-TYPE
    ENTERPRISE eTrapGroup
    VARIABLES  { a9999ErrorTime,
                 a9999ErrorStatus,
                 a9999ErrorGroupId,
                 a9999ErrorInstanceId,
                 a9999ComponentId,
                 a9999GroupId,
                 a9999InstanceId,
                 a9999VendorCode1,
                 a9999VendorCode2,
                 a9999VendorText,
                 a9999ParentGroupId,
                 a9999ParentInstanceId}

    DESCRIPTION "DMI Service Layer generated event for FastTrak IDE RAID"

    --NMS trap annotation

    --#TYPE       "DMI FastTrak IDE RAID Error Event"
    --#SUMMARY    "Event Data: (%s,%d,%d,%d) (%d,%d,%d,%d,%d) (%d,%d)"
    --#ARGUMENTS  {0, 1, 2, 3, 4, 5, 6, 7, 8, 10, 11}
    --#SEVERITY   CRITICAL
    --#TIMEINDEX  12
    --#STATE      DEGRADED
    ::= 1
END
