DNSSERVEREXT-MIB

   --FORCE-INCLUDE <mib.h>
   --FORCE-INCLUDE <snmpdefs.h>
   --FORCE-INCLUDE <snmpstat.h>
   --FORCE-INCLUDE "mibproto.h"
 
   DEFINITIONS ::= BEGIN

	IMPORTS
		MODULE-IDENTITY, OBJECT-TYPE, IpAddress, Integer32
			FROM SNMPv2-SMI
		DisplayString, RowStatus
			FROM SNMPv2-TC
		dnsServerExt
			FROM APENT-MIB;


    apDnsServerMib MODULE-IDENTITY
	   LAST-UPDATED "9806122000Z" -- Fri June 12 20:00:00 EST 1997
	   ORGANIZATION "ArrowPoint Communications Inc."
	   CONTACT-INFO
	   "Postal:               ArrowPoint Communications Inc.
				                 50 Nagog Park
				                 Acton, Massachusetts 01720
	   Tel:                   +1 978-206-3000  option 1
	   E-Mail:                support@arrowpoint.com"
       DESCRIPTION
	"This MIB module describes the ArrowPoint enterprise
	 MIB support for DNS Server"
      ::= { dnsServerExt 1}


--arrowpoint
-- apmgmt
--   apDnsServerExt
--     apDnsServerExt Scalars

-- Dns Server configuration information

apDnsServerEnable OBJECT-TYPE
	SYNTAX      INTEGER {
                             disable(0),
                             enable(1)
                            }
	MAX-ACCESS  read-write
	STATUS      current
	DESCRIPTION
	       "Parameter to enable or disable DNS Server functionality."
	::= {dnsServerExt 2}


apDnsServerBufferCount OBJECT-TYPE
	SYNTAX      INTEGER    ( 2..1000 )
	MAX-ACCESS  read-write
	STATUS      current
	DESCRIPTION
	       "The number of buffers allocated for Query Responses"
	DEFVAL {10}
	::= {dnsServerExt 3}

apDnsServerResponderTasks OBJECT-TYPE
	SYNTAX      INTEGER    ( 1..250 )
	MAX-ACCESS  read-write
	STATUS      current
	DESCRIPTION
	       "The number of Tasks to handle DNS Responses"
	DEFVAL {2}
	::= {dnsServerExt 4}

apDnsPeerRcvEntries OBJECT-TYPE
	SYNTAX      INTEGER    ( 128..1024 )
	MAX-ACCESS  read-write
	STATUS      current
	DESCRIPTION
	       "The number of DNS entries which can be received from a peer"
	DEFVAL {128}
	::= {dnsServerExt 5}

apDnsPeerSndEntries OBJECT-TYPE
	SYNTAX      INTEGER    ( 128..1024 )
	MAX-ACCESS  read-write
	STATUS      current
	DESCRIPTION
	       "The number of DNS entries which can be sent to a peer"
	DEFVAL {128}
	::= {dnsServerExt 6}

apDnsPeerReportInterval OBJECT-TYPE
	SYNTAX      INTEGER    ( 5..120 )
	MAX-ACCESS  read-write
	STATUS      current
	DESCRIPTION
	       "The number of seconds between generation of DNS peer load reports"
	DEFVAL {5}
	::= {dnsServerExt 7}

apDnsAclIndex OBJECT-TYPE
	SYNTAX      INTEGER    ( 0..99 )
	MAX-ACCESS  read-write
	STATUS      current
	DESCRIPTION
	       "The Acl which has been applied to DNS resolutions, zero means no Acl"
	DEFVAL {0}
	::= {dnsServerExt 8}

-- Proximity configuration information
apProximityType OBJECT-TYPE
	SYNTAX      INTEGER {
                             pdns(2),
                             pdb(3)
                            }
	MAX-ACCESS  read-write
	STATUS      current
	DESCRIPTION
	       "Parameter to specify PDB or PDNS functionality."
	::= {dnsServerExt 9}

apProximityEnable OBJECT-TYPE
	SYNTAX      INTEGER {
                             disable(0),
                             enable(1)
                            }
	MAX-ACCESS  read-write
	STATUS      current
	DESCRIPTION
	       "Parameter to enable or disable PDB / PDNS functionality."
	::= {dnsServerExt 10}

apProximityZone OBJECT-TYPE
	SYNTAX      INTEGER    ( 0..15 )
	MAX-ACCESS  read-write
	STATUS      current
	DESCRIPTION
	       "The local proximity zone index"
	DEFVAL {0}
	::= {dnsServerExt 11}

apProximityDescription OBJECT-TYPE
	SYNTAX      DisplayString(SIZE (0..20))
	MAX-ACCESS  read-create
	STATUS      current
	DESCRIPTION
	       "A name which identifies this proximity zone"
	DEFVAL {'0'h}
	::= {dnsServerExt 12}

apProximityZoneMax OBJECT-TYPE
	SYNTAX      INTEGER {
                             tier1(6),
                             tier2(16)
                            }
	MAX-ACCESS  read-write
	STATUS      current
	DESCRIPTION
	       "The maximum number of proximity zones allowed"
	DEFVAL {tier1}
	::= {dnsServerExt 13}

apProximityPDBIpAddr OBJECT-TYPE
	SYNTAX      IpAddress
	MAX-ACCESS  read-create
	STATUS      current
	DESCRIPTION
	       "The Interface IP Address of the PDB"
	DEFVAL {0}
	::= {dnsServerExt 14}

apProximityRecordTable OBJECT-TYPE
	SYNTAX          SEQUENCE OF APProximityRecordEntry
	MAX-ACCESS      not-accessible
	STATUS          current
	DESCRIPTION
		"A list of Proximity domain name records."
	::= {dnsServerExt 15}

apProximityRecordEntry OBJECT-TYPE
	SYNTAX          APProximityRecordEntry
	MAX-ACCESS      not-accessible
	STATUS          current
	DESCRIPTION
		"Proximity domain name record information."
		
	INDEX   { apProximityRecordName }
	::= { apProximityRecordTable 1 }

APProximityRecordEntry ::=
       SEQUENCE {
		apProximityRecordName              DisplayString,
	        apProximityRecordType              INTEGER,
	        apProximityRecordAddr              IpAddress,
                apProximityRecordTtl               Integer32,
	        apProximityRecordKalType           INTEGER,
	        apProximityRecordKalAddr           IpAddress,
	        apProximityRecordKalThreshold      INTEGER,
	        apProximityRecordRtnSingleArec     INTEGER,
		apProximityRecordStatus            RowStatus
                }

apProximityRecordName OBJECT-TYPE
	SYNTAX          DisplayString (SIZE(1..31))
	MAX-ACCESS      read-create
	STATUS          current
	DESCRIPTION     
			"The dns name for this Proximity record."
	::= {apProximityRecordEntry 1}

apProximityRecordType OBJECT-TYPE
	SYNTAX      INTEGER {
						typeA(1),
						typeNS(2)
			    }
	MAX-ACCESS  read-create
	STATUS      current
	DESCRIPTION
	       "Determines if this record is of type NS or A."
	::= {apProximityRecordEntry 2}

apProximityRecordAddr OBJECT-TYPE
	SYNTAX      IpAddress
	MAX-ACCESS  read-create
	STATUS      current
	DESCRIPTION
	       "The Interface IP Address of Peer"
	::= {apProximityRecordEntry 3}

apProximityRecordTtl OBJECT-TYPE
	SYNTAX          Integer32
	MAX-ACCESS      read-create
	STATUS  	current
	DESCRIPTION
	       "The Time to Live Value returned in DNS Responses"
	DEFVAL { 0 }
	::= {apProximityRecordEntry 4}

apProximityRecordKalType OBJECT-TYPE
	SYNTAX      INTEGER {
						kal-none(0)                           ,
						kal-icmp(1)                        ,
						kal-ap(2)                              
			    }
	MAX-ACCESS  read-create
	STATUS      current
	DESCRIPTION
	       "The type of keepalive performed on this record"
	DEFVAL { kal-icmp }
	::= {apProximityRecordEntry 5}

apProximityRecordKalAddr OBJECT-TYPE
	SYNTAX      IpAddress
	MAX-ACCESS  read-create
	STATUS      current
	DESCRIPTION
	       "The IP Address of interface to send AP keepalive messages"
	::= {apProximityRecordEntry 6}

apProximityRecordKalThreshold OBJECT-TYPE
	SYNTAX          INTEGER (2..254)
	MAX-ACCESS      read-create
	STATUS 		current
	DESCRIPTION     
		"The record is considered DOWN when the load number is greater than this value."
	DEFVAL { 254 }
	::= {apProximityRecordEntry 7}

apProximityRecordRtnSingleArec OBJECT-TYPE
	SYNTAX      INTEGER {
						multiple(0)                                                 ,
						single(1)                                         
			    }
	MAX-ACCESS  read-create
	STATUS      current
	DESCRIPTION
	       "Determines if multiple A records will be returned in a Response for this DNS name."
	DEFVAL { single }
	::= {apProximityRecordEntry 8}

apProximityRecordStatus OBJECT-TYPE
	SYNTAX          RowStatus
	MAX-ACCESS      read-create
	STATUS          current
	DESCRIPTION      
		"Status entry for this row "
	::= {apProximityRecordEntry 9}
END
