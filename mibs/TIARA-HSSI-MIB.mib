-- *****************************************************************
-- tiaranet-hssi.mib:  Tiara Networks HSSI MIB
--
-- Oct,1st 1999, kumar
--
-- Copyright (c) 1998-2000 by Tiara Networks, Inc.
-- All rights reserved.
--
-- *****************************************************************

TIARA-HSSI-MIB DEFINITIONS ::= BEGIN

IMPORTS
    MODULE-IDENTITY, 
	OBJECT-TYPE,
    Integer32,
	Counter32                 FROM SNMPv2-SMI
    TruthValue                  FROM SNMPv2-TC
    TRAP-TYPE                   FROM RFC-1215
    tiaraInterfaces             FROM TIARA-NETWORKS-SMI;

tiaraHssiMib MODULE-IDENTITY
    LAST-UPDATED "0008180000Z"
    ORGANIZATION "Tiara Networks Inc."
    CONTACT-INFO
                "       Tiara Networks
                        Customer Support

               		525 Race Street, Suite 100,
                        San Jose, CA 95126
                        USA

                   	Tel: +1 408-216-4700
                   	Fax: +1 408-216-4701

                		Email: support@tiaranetworks.com"

    DESCRIPTION
            "  MIB definitions for Tiara HSSI modules."
    REVISION "0008180000Z"
    DESCRIPTION
            "Initial revision."
    ::= { tiaraInterfaces 2 }

-- hssiConfigTable definitions.

hssiConfigTable   OBJECT-TYPE
    SYNTAX        SEQUENCE OF HssiConfigTableEntry
    MAX-ACCESS    not-accessible
    STATUS        current
    DESCRIPTION   "The HSSI interface configurable parameters are 
			listed in this table."
    ::= {tiaraHssiMib 1}

hssiConfigTableEntry OBJECT-TYPE
    SYNTAX        HssiConfigTableEntry
    MAX-ACCESS    not-accessible
    STATUS        current
    DESCRIPTION   "HSSI table entry."
    INDEX {hssiIfIndex}
    ::= {hssiConfigTable 1}

HssiConfigTableEntry ::= SEQUENCE {
    hssiIfIndex                  INTEGER,
    hssiConfigClockRate          Integer32 (1000000 .. 52000000),
    hssiConfigClockSource        INTEGER,
    hssiConfigTxClockSource      INTEGER,
    hssiConfigRxClockSource      INTEGER,
    hssiConfigMode               INTEGER,
    hssiConfigDataMode           INTEGER,
    hssiConfigCRC                INTEGER,
    hssiConfigProcessCtrlSignal  INTEGER,
    hssiDteLoopback              TruthValue,
    hssiDceLoopbackTest          INTEGER
    }

hssiIfIndex 	OBJECT-TYPE
    SYNTAX      	INTEGER
    MAX-ACCESS  	not-accessible
    STATUS      	current
    DESCRIPTION
            "An integer value that is an index in the entries of the
            ifTable (MIB-II) with a HSSI interface type."
    ::= { hssiConfigTableEntry 1 }

hssiConfigClockRate OBJECT-TYPE
    SYNTAX          Integer32(1000000 .. 52000000)
    MAX-ACCESS      read-write
    STATUS          current
    DESCRIPTION    "Configures the clock rate (in Hertz) for the 
			 HSSI interface."
    DEFVAL {52000000}
    ::= {hssiConfigTableEntry 2}   

hssiConfigClockSource 	OBJECT-TYPE
    SYNTAX         	INTEGER
                   	{ internal(1),
                     	line (2)
                   	}
    MAX-ACCESS     	read-write 
    STATUS         	current 
    DESCRIPTION    "Configures the clock source for the HSSI 
			 interface to either internal or line."

    DEFVAL 			{line}
    ::= {hssiConfigTableEntry 3}

hssiConfigTxClockSource OBJECT-TYPE
    SYNTAX            	INTEGER
                   	{ normalinternal(1),
                     	  normalterminal (2),
                     	  invertedinternal (3),
                     	  invertedterminal (4)
                   	}
    MAX-ACCESS     	read-write 
    STATUS         	current 
    DESCRIPTION    "Configures the transmit clock source for the HSSI 
			 interface to either internal or terminal. This 
			 variable is valid only for the HSSI interface on 
			 the USSI card."

    ::= {hssiConfigTableEntry 4}
   
hssiConfigRxClockSource OBJECT-TYPE
    SYNTAX            	INTEGER
                   	{ normalinternal(1),
                     	  normalterminal (2),
                     	  invertedinternal (3),
                     	  invertedterminal (4)
                   	}
    MAX-ACCESS     	read-write 
    STATUS         	current 
    DESCRIPTION    "Configures the receive clock source for the HSSI 
			 interface to either internal or terminal. This 
			 variable is valid only for the HSSI interface 
			 on the USSI card"

    ::= {hssiConfigTableEntry 5}

hssiConfigMode 	OBJECT-TYPE   
    SYNTAX        INTEGER
                  { dce(1),
                    dte(2)
                  }
    MAX-ACCESS    read-write
    STATUS        current
    DESCRIPTION    "Configures the mode for the HSSI to either DCE 
			 or DTE."

    DEFVAL {dte}
    ::= {hssiConfigTableEntry 6}

hssiConfigDataMode OBJECT-TYPE   
    SYNTAX         INTEGER
                   { normal(1),
                     inverted(2)
                   }
    MAX-ACCESS     read-write
    STATUS         current
    DESCRIPTION    "Configures the data mode for the HSSI interface. 
			 This variable is valid only for the HSSI 
			 interface on the USSI card."

    DEFVAL {normal}
    ::= {hssiConfigTableEntry 7}

hssiConfigCRC OBJECT-TYPE   
    SYNTAX         INTEGER
                   { crc16(1),
                     crc32(2)
                   }
    MAX-ACCESS     read-write
    STATUS         current
    DESCRIPTION    "Configures the cyclic redundancy check for the 
			 HSSI interface to either 16 or 32 bits."

    DEFVAL {crc32}
    ::= {hssiConfigTableEntry 8}

hssiConfigProcessCtrlSignal OBJECT-TYPE   
    SYNTAX         INTEGER
                   { ignore(1),
                     process(2)
                   }
    MAX-ACCESS     read-write
    STATUS         current
    DESCRIPTION    "Configures the processing of control signals 
			 (CA/TA) for the HSSI interface. This variable 
			 is valid only for the HSSI interface on the  
			 USSI card."

    DEFVAL {process}
    ::= {hssiConfigTableEntry 9}
   
hssiDteLoopback OBJECT-TYPE
    SYNTAX         TruthValue
    MAX-ACCESS     read-write
    STATUS         current
    DESCRIPTION    "Configures the local DTE for loopback operation:

			 TRUE  : request local DTE to go into line loopback
			 FALSE : request local DTE to abandon line loopback

			 These commands are valid only if the HSSI adaptor 
			 is in DCE mode and connected to a local DTE. Since  
			 the local DTE has a greater loopback priority 
			 than the local DCE, a loopback request initiated 
			 by the DCE will be ignored if the DTE simultaneously 
			 requests the DCE to loopback. Similarly, the DTE 
			 will abort a loopback already initiated by the DCE 
			 when the DTE requests the DCE to loopback."

    ::= {hssiConfigTableEntry 10}

hssiDceLoopbackTest OBJECT-TYPE   
    SYNTAX         INTEGER
                   { noTest (1),
                     line(2),
                     cable(3),
                     remote(4)
                   }
    MAX-ACCESS     read-write
    STATUS         current
    DESCRIPTION    "Configures the local/remote DCE for loopback 
			 operation. Three DCE loopback modes are available: 
			 line, cable, and remote. Use noTest to abandon any 
			 of the DCE loopbacks. If the DCE is already in any 
			 one of the loopback modes, then noTest must be issued 
			 to abort the current test before initiating another 
			 loopback request. These commands are valid only if 
			 the HSSI adaptor is in DTE mode and it connected 
			 to a DCE."

    ::= {hssiConfigTableEntry 11}

-- hssiStatsTable definition.

hssiStatsTable    OBJECT-TYPE
    SYNTAX        SEQUENCE OF HssiStatsTableEntry
    MAX-ACCESS    not-accessible
    STATUS        current
    DESCRIPTION   "The HSSI interface status parameters are listed in 
			this table."
    ::= {tiaraHssiMib 3}

hssiStatsTableEntry 	OBJECT-TYPE
    SYNTAX        	HssiStatsTableEntry
    MAX-ACCESS    	not-accessible
    STATUS        	current
    DESCRIPTION   	"HSSI Statistics table entry."
    INDEX 			{hssiIfIndex}
    ::= {hssiStatsTable 1}

HssiStatsTableEntry ::= SEQUENCE {
    hssiStatsAlarmStatus    BITS,
    hssiStatsFramesIn       Counter32,
    hssiStatsFramesOut      Counter32,
    hssiStatsOctetsIn       Counter32,
    hssiStatsOctetsOut      Counter32,
    hssiStatsCRCErrors      Counter32
    }

hssiStatsAlarmStatus OBJECT-TYPE
    SYNTAX         BITS
                    {
                        hssi-no-alarms(0),
                        hssi-alarms-CA(1),
                        hssi-alarms-ST(2),
                        hssi-alarms-TM(3),
                        hssi-alarms-LC(4),
                        hssi-alarms-TA(5),
                        hssi-alarms-LALB(6)
                    }
    MAX-ACCESS     read-only
    STATUS         current
    DESCRIPTION    "Specifies the status of the HSSI alarm. If 
			 the particular bit is set, then it indicates 
			 that the alarm is in ON state. Alarm bits 
			 are mode dependent; they are interpreted	as 
			 follows:

                   hssi-alarms-CA   - CA not received from DCE 
						  (HSSI is DTE)
                   hssi-alarms-ST   - HSSI adaptor driving ST 
						  (HSSI is DCE)
                   hssi-alarms-TM   - TM received from DCE (HSSI 
						  is DTE)
                   hssi-alarms-LC   - HSSI adaptor detects LC 
						  (HSSI is DTE)
                   hssi-alarms-LC   - HSSI adaptor driving LC 
					  	  (HSSI is DCE)
                   hssi-alarms-TA   - TA not received from DTE 
						  (HSSI is DCE)
                   hssi-alarms-LALB - HSSI adaptor detects LA 
						  and/or LB (HSSI is DCE)
                   hssi-alarms-LALB - HSSI adaptor driving LA 
						  and/or LB (HSSI is DTE)
					"

    ::= {hssiStatsTableEntry 1}

hssiStatsFramesIn  OBJECT-TYPE
    SYNTAX         Counter32
    MAX-ACCESS     read-only
    STATUS         current
    DESCRIPTION    "Specifies the number of incoming frames."

    ::= {hssiStatsTableEntry 2}


hssiStatsFramesOut OBJECT-TYPE
    SYNTAX         Counter32
    MAX-ACCESS     read-only
    STATUS         current
    DESCRIPTION    "Specifies the number of outgoing frames."

    ::= {hssiStatsTableEntry 3}

hssiStatsOctetsIn  OBJECT-TYPE
    SYNTAX         Counter32
    MAX-ACCESS     read-only
    STATUS         current
    DESCRIPTION    "Specifies the number of incoming octets."

    ::= {hssiStatsTableEntry 4}

hssiStatsOctetsOut OBJECT-TYPE
    SYNTAX         Counter32
    MAX-ACCESS     read-only
    STATUS         current
    DESCRIPTION    "Specifies the number of outgoing octets."

    ::= {hssiStatsTableEntry 5}

hssiStatsCRCErrors OBJECT-TYPE
    SYNTAX         Counter32
    MAX-ACCESS     read-only
    STATUS         current
    DESCRIPTION    "Specifies the number of CRC errors that have been 
                    identified."

    ::= {hssiStatsTableEntry 6}

-- HSSI trap variables assignment.

hssiTraps OBJECT IDENTIFIER ::= {tiaraHssiMib 2}
hssiTrapVariables OBJECT IDENTIFIER ::= {hssiTraps 1}

-- HSSI alarm trap variable definitions.

hssiAlarmType  	  OBJECT-TYPE
    SYNTAX          INTEGER
                    {
                      hssi-alarm-CA (1),
                      hssi-alarm-ST (2),
                      hssi-alarm-TM (3),
                      hssi-alarm-LC (4),
                      hssi-alarm-TA (5),
                      hssi-alarm-LALB (6)
                    }
    MAX-ACCESS      not-accessible
    STATUS          current


    DESCRIPTION    "Specifies the type of alarm generated by the agent 
			 for the HSSI interface. Alarms are mode dependent; 
			 they are interpreted as follows:

                   hssi-alarms-CA 	- CA not received from DCE 
			 			  (HSSI is DTE)
                   hssi-alarms-ST   - HSSI adaptor driving ST 
			 			  (HSSI is DCE)
                   hssi-alarms-TM   - TM received from DCE (HSSI 
						  is DTE)
                   hssi-alarms-LC   - HSSI adaptor detects LC 
						  (HSSI is DTE)
                   hssi-alarms-LC   - HSSI adaptor driving LC 
						  (HSSI is DCE)
                   hssi-alarms-TA   - TA not received from DTE 
						  (HSSI is DCE)
                   hssi-alarms-LALB - HSSI adaptor detects LA 
						  and/or LB (HSSI is DCE)
                   hssi-alarms-LALB - HSSI adaptor driving LA 
						  and/or LB (HSSI is DTE)
					"

    ::= {hssiTrapVariables 1}

hssiAlarmOnTrap  TRAP-TYPE
    ENTERPRISE       hssiTraps
    VARIABLES        {
                       hssiIfIndex,
                       hssiAlarmType
                     }
    DESCRIPTION      "HSSI alarm traps for the Alarm-On state."
             --#TYPE "HSSI Alarm On state"
             --#SUMMARY "HSSI Alarm On trap sent from Interface index: %s with the Alarm type: %s"
             --#ARGUMENTS {0,1}
             --#SEVERITY MAJOR
    ::= 1 

hssiAlarmOffTrap  TRAP-TYPE
    ENTERPRISE       hssiTraps
    VARIABLES        {
                       hssiIfIndex,
                       hssiAlarmType
                     }
    DESCRIPTION      "HSSI alarm traps for the Alarm-Off state."
             --#TYPE "HSSI Alarm Off state"
             --#SUMMARY "HSSI Alarm Off trap sent from Interface index: %s with the Alarm type: %s"
             --#ARGUMENTS {0,1}
             --#SEVERITY NORMAL        
   
    ::= 2 


END
