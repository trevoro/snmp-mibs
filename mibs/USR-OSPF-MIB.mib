USR-OSPF-MIB DEFINITIONS ::= BEGIN
	IMPORTS
                MODULE-IDENTITY, OBJECT-TYPE, Integer32, IpAddress
				FROM SNMPv2-SMI
		 common, UsrConfigStatus
				FROM USR-DEFINITIONS-MIB
		TEXTUAL-CONVENTION, RowStatus, DisplayString
				FROM SNMPv2-TC;
usrOspf MODULE-IDENTITY
        LAST-UPDATED "200102151935Z" -- February 15, 19:35, 2001
        ORGANIZATION "CommWorks Corporation, a 3Com company"
        CONTACT-INFO "Customer Support"
        DESCRIPTION
       "The MIB module to describe the enterprise specific
        objects for the OSPF Protocol"
    ::= { common 63 }
TOSType ::= TEXTUAL-CONVENTION
    STATUS      current
    DESCRIPTION
       "Type of Service is defined as a mapping to the IP Type of
       Service Flags as defined in the IP Forwarding Table MIB
       +-----+-----+-----+-----+-----+-----+-----+-----+
       |                 |                       |     |
       |   PRECEDENCE    |    TYPE OF SERVICE    |  0  |
       |                 |                       |     |
       +-----+-----+-----+-----+-----+-----+-----+-----+
                IP TOS                IP TOS
           Field     Policy      Field     Policy
           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22
           1 1 0 0  ==>  24      1 1 0 1  ==>  26
           1 1 1 0  ==>  28      1 1 1 1  ==>  30
       The remaining values are left for future definition."
    SYNTAX      Integer32 (0..30)
-- Begin IP policy object definitions here...
--
--      The OSPF Export Policy Table
--
--
--  Rip gateway and interface have been removed from the
--  the ospf export policy table. To add them back in
--  modify the table using the commented out
--  items at the bottom of this file.
--
    usrOspfExportPolicyTable OBJECT-TYPE
        SYNTAX   SEQUENCE OF UsrOspfExportPolicyEntry
        MAX-ACCESS   not-accessible
        STATUS   current
        DESCRIPTION
	            "A set of export policies for OSPF."
      ::= { usrOspf 1 }
    usrOspfExportPolicyEntry OBJECT-TYPE
        SYNTAX  UsrOspfExportPolicyEntry
        MAX-ACCESS   not-accessible
        STATUS   current
        DESCRIPTION
           ""
       REFERENCE
          ""
      INDEX { 
	usrOspfExportPolicyNet,
	usrOspfExportPolicyMask,
	usrOspfExportPolicyRouteSource
	}
      ::= { usrOspfExportPolicyTable 1 }
UsrOspfExportPolicyEntry ::= SEQUENCE {
      usrOspfExportPolicyNet			IpAddress,
      usrOspfExportPolicyMask			IpAddress,
      usrOspfExportPolicyRouteSource		INTEGER,
      usrOspfExportPolicyAction			INTEGER,
      usrOspfExportPolicyMetric			Integer32 (0..16777215),
      usrOspfExportPolicyMetricType		INTEGER,
      usrOspfExportPolicyTag			Integer32 (0..2147483647),
      usrOspfExportPolicyStatus                 RowStatus
}
usrOspfExportPolicyNet OBJECT-TYPE
        SYNTAX		IpAddress
        MAX-ACCESS   	read-only
        STATUS   	current
        DESCRIPTION
           "Specifies the network address which will match this policy."
::= { usrOspfExportPolicyEntry 1 }
usrOspfExportPolicyMask OBJECT-TYPE
        SYNTAX		IpAddress
        MAX-ACCESS   	read-only
        STATUS   	current
        DESCRIPTION
           "The network mask to be applied to the network address to
            specify a specific address or range of addresses for this policy."
::= { usrOspfExportPolicyEntry 2 }
usrOspfExportPolicyRouteSource OBJECT-TYPE
        SYNTAX		INTEGER {  
				any(0),
                        	local(1),
                              	static(2),
                 	      	rip(8)
			}
        MAX-ACCESS	read-only
        STATUS		current
        DESCRIPTION
           "Identifies the source of the routing information: local,
            static, or RIP."
	DEFVAL		{ 0 }
::= { usrOspfExportPolicyEntry 3 }
--	As part of NSSA development two new CLI commands are added
--	to delete all OSPF send and receive policies, where the 
--	source will be 'any' and the policy will be 'zero' in 
--	order to distinguish between all policy deletion and one policy.
usrOspfExportPolicyAction OBJECT-TYPE
	SYNTAX		INTEGER {
                        	advertise(1),
                              	doNotAdvertise(2)
			}
        MAX-ACCESS   	read-create
        STATUS   	current
        DESCRIPTION
           "The action to take with this export policy. If the action
            is propagate, the route or routes described by the entry are included
            in the local OSPF updates if they exist in the routing table. If the
            action is ignore, the route or routes described are not advertised in
            the local OSPF updates."
	DEFVAL		{ 1 }
       --CONFIGURABLE
::= { usrOspfExportPolicyEntry 4 }
usrOspfExportPolicyMetric OBJECT-TYPE
        SYNTAX   	Integer32 (0..16777215) 
        MAX-ACCESS   	read-create
        STATUS   	current
        DESCRIPTION
           "The metric to be used when advertising the route(s)
            described by this policy. A metric value of 0 will cause the 
            metric that is inserted into the AS External Links advertisement 
            to be taken from the associated route entry in the routing table.
            For all other valid metric values, the value is directly inserted
            into the AS External Links advertisement."
	DEFVAL		{ 0 }
       --CONFIGURABLE
::= { usrOspfExportPolicyEntry 5 }
usrOspfExportPolicyMetricType OBJECT-TYPE
        SYNTAX   	INTEGER {
                        	comparableCost(1), -- external type I
                              	nonComparable(2)  -- external type II
			}
        MAX-ACCESS   	read-create
        STATUS   	current
        DESCRIPTION
           "This variable describes the external type of metric that the
            export policy will advertise an external route as. Essentially
            this variable determines if the E Bit in an AS External Links
            Advertisement is set or not. A selection of external type II
            will cause the E bit to be set to 1. An external route tagged
            as an external type II indicates that the external cost to
            the route is all that should be associated with it's cost metric.
            A route tagged as external type I indicates that the
            internal cost to the Autonomous System Border Router as well
            as the external cost of the route should be associated with
            the route's cost metric."
	DEFVAL		{ 1 }
       --CONFIGURABLE
::= { usrOspfExportPolicyEntry 6 }
usrOspfExportPolicyTag OBJECT-TYPE
        SYNTAX   	Integer32 (0..2147483647)
        MAX-ACCESS   	read-create
        STATUS   	current
        DESCRIPTION
           "The routing tag to be used when exporting the route(s)
described by this policy entry."
	DEFVAL		{ 0 }
       --CONFIGURABLE
::= { usrOspfExportPolicyEntry 7}
usrOspfExportPolicyStatus OBJECT-TYPE
        SYNTAX   	RowStatus
        MAX-ACCESS   	read-create
        STATUS   	current
        DESCRIPTION
           "The administrative status of the export policy entry."
       --CONFIGURABLE
::= { usrOspfExportPolicyEntry 8}
--
--      The OSPF Import Policy Table
--
usrOspfImportPolicyTable OBJECT-TYPE
        SYNTAX   	SEQUENCE OF UsrOspfImportPolicyEntry
        MAX-ACCESS   	not-accessible
        STATUS   	current
        DESCRIPTION
	"A set of OSPF import policies."
::= { usrOspf 2 }
usrOspfImportPolicyEntry OBJECT-TYPE
        SYNTAX   	UsrOspfImportPolicyEntry
        MAX-ACCESS   	not-accessible
        STATUS   	current
        DESCRIPTION
           "An entry for an OSPF Import Policy"
      INDEX {usrOspfImportPolicyNet }
::= { usrOspfImportPolicyTable 1 }
UsrOspfImportPolicyEntry ::= SEQUENCE {
	usrOspfImportPolicyNet		                IpAddress,
	usrOspfImportPolicyMask		                IpAddress,
	usrOspfImportPolicyAction	                INTEGER,
	usrOspfImportPolicyRoutingPreference	        INTEGER,
        usrOspfImportPolicyStatus                       RowStatus
}
usrOspfImportPolicyNet OBJECT-TYPE
        SYNTAX		IpAddress
        MAX-ACCESS   	read-only
        STATUS   	current
        DESCRIPTION
           "The network address of the destination or set of
destinations for which this import policy is being defined."
::= { usrOspfImportPolicyEntry 1 }
usrOspfImportPolicyMask OBJECT-TYPE
        SYNTAX   	IpAddress
        MAX-ACCESS   	read-only
        STATUS   	current
        DESCRIPTION
           "The network mask for the destination or set of
            destinations for which this import policy is being defined."
::= { usrOspfImportPolicyEntry 2 }
usrOspfImportPolicyAction OBJECT-TYPE
        SYNTAX   	INTEGER {
                        	accept(1),
	                 	ignore(2)
			}
        MAX-ACCESS   	read-create
        STATUS   	current
        DESCRIPTION
           "The action to take with this import policy. If the action
            is accept, the route or routes described by the entry are included 
            in the routing table when received in peer OSPF updates. If the action 
            is ignore, the route or routes described are filtered from received 
            OSPF updates."
       --CONFIGURABLE
::= { usrOspfImportPolicyEntry 3 }
usrOspfImportPolicyRoutingPreference OBJECT-TYPE
        SYNTAX 	INTEGER  {
	            routingPreference0 (1),   -- same routing preference as OSPF 
                                              --    internal routes
                    routingPreference1 (2),   -- same routing preference as OSPF 
                                              --    external type 1 routes
                    routingPreference2 (3),   -- same routing preference as OSPF
                                              --    external type 2 routes
                    routingPreference3 (4)    -- route will never be used for
                                              --    forwarding
                  }
        MAX-ACCESS   	read-create
        STATUS   	current
        DESCRIPTION
           "The routing preference to associate with this route. A routing preference
            of routingPreference0 is more preferred than a preference equal to
            routingPreference1. A routing preference of routingPreference1 is more 
            preferred than a preference equal to routingPreference2. A routing
            preference of routingPreference3 will cause a route to never be used
	    in forwarding. It will be present in the routing table but will never
            make it into the forwarding table."
       --CONFIGURABLE
::= { usrOspfImportPolicyEntry 4 }
usrOspfImportPolicyStatus OBJECT-TYPE
        SYNTAX   	RowStatus
        MAX-ACCESS   	read-create
        STATUS   	current
        DESCRIPTION
           "The administrative status of the import policy entry."
       --CONFIGURABLE
::= { usrOspfImportPolicyEntry 5}
--      The OSPF Area Table
    usrOspfAreaTable OBJECT-TYPE
        SYNTAX   SEQUENCE OF UsrOspfAreaEntry
        MAX-ACCESS   not-accessible
        STATUS   current
        DESCRIPTION
           "NOT IMPLEMENTED!
           Information describing the configured  parame-
           ters  and cumulative statistics of the router's
           attached areas."
       REFERENCE
          "OSPF Version 2, Section 6  The Area Data Struc-
          ture"
       ::= { usrOspf 3 }
    usrOspfAreaEntry OBJECT-TYPE
        SYNTAX  UsrOspfAreaEntry
        MAX-ACCESS   not-accessible
        STATUS   current
        DESCRIPTION
           "Information describing the configured  parame-
           ters  and  cumulative  statistics of one of the
           router's attached areas."
      INDEX { 
	usrOspfAreaId
	}
      ::= { usrOspfAreaTable 1 }
UsrOspfAreaEntry ::= SEQUENCE {
      usrOspfAreaId		IpAddress,
      usrOspfAreaType	        INTEGER
}
    usrOspfAreaId OBJECT-TYPE
        SYNTAX       IpAddress
        MAX-ACCESS   read-only
        STATUS   current
        DESCRIPTION
           "A 32-bit integer uniquely identifying an area.
           Area ID 0.0.0.0 is used for the OSPF backbone."
       REFERENCE
          "OSPF Version 2, Appendix C.2 Area parameters"
      ::= { usrOspfAreaEntry 1 }
    usrOspfAreaType OBJECT-TYPE
        SYNTAX   INTEGER    {
                    transit (1),
                    stub (2)
                  }
        MAX-ACCESS   read-write
        STATUS   current
        DESCRIPTION
           "The area's support for determining if the Type is Stub or Transit."
       REFERENCE
          "OSPF Version 2, Appendix C.2 Area parameters"
      DEFVAL { transit }
      ::= { usrOspfAreaEntry 2 }
usrOspfVersion OBJECT-TYPE
	SYNTAX      DisplayString
	MAX-ACCESS      read-only
	STATUS      current
	DESCRIPTION
		"The current software version of the OSPF Process."
::= { usrOspf 4 }
usrOspfConfigFileName OBJECT-TYPE
	SYNTAX      DisplayString
	MAX-ACCESS      read-only
	STATUS      current
	DESCRIPTION		
		"The name of a ConfigFile to read/write  permanent database records."
::= { usrOspf 5 }
usrOspfCFMStatusFlag  OBJECT-TYPE
	SYNTAX	  UsrConfigStatus
	MAX-ACCESS      read-write
	STATUS      current
	DESCRIPTION
		"Setting the value of this object to `save' causes the values
		 of the OSPF Group to be written out to the current config
		 file. While the new data is being written, the config process
		 will set the value of this flag to `saving''. Any
		 attempts to set the value while it is  not `normal'
		 (i.e. the file is currently being written to the
		 ConfigFile) will result in a badValue error being
		 returned. Setting the value to `normal' will result in no
		 action."
::= { usrOspf 6 }
--      The OSPF Default Area ID
usrOspfDefaultAreaId OBJECT-TYPE
    SYNTAX       IpAddress
    MAX-ACCESS   read-write
    STATUS   current
    DESCRIPTION
           "A 32-bit integer uniquely identifying an area.
           Area ID 0.0.0.0 is used for the OSPF backbone.  This area ID is used 
           to create the default area when the ospf base is created"
    DEFVAL   { '00000000'H }    -- 0.0.0.0
    --CONFIGURABLE
::= { usrOspf 7 }
--      The OSPF Host Table
    usrOspfHostTable OBJECT-TYPE
        SYNTAX   SEQUENCE OF UsrOspfHostEntry
        MAX-ACCESS   not-accessible
        STATUS   current
        DESCRIPTION
           "The list of Hosts, and their metrics, that the
            router will advertise as host routes."
       REFERENCE
          "OSPF Version 2, Section C.6  The Host route parameters"
::= { usrOspf 8 }
    usrOspfHostEntry OBJECT-TYPE
        SYNTAX  UsrOspfHostEntry
        MAX-ACCESS   not-accessible
        STATUS   current
        DESCRIPTION
           "A metric to be advertised, for a given type of service,
            when a given host is reachable."
      INDEX { 
	usrOspfHostIpAddress, usrOspfHostIpTOS
	}
      ::= { usrOspfHostTable 1 }
UsrOspfHostEntry ::= SEQUENCE {
      usrOspfHostIpAddress	IpAddress,
      usrOspfHostIpTOS	        TOSType,
      usrOspfHostIpMask	        IpAddress
}
    usrOspfHostIpAddress OBJECT-TYPE
        SYNTAX       IpAddress
        MAX-ACCESS   read-only
        STATUS   current
        DESCRIPTION
           "The IP Address of the Host."
       REFERENCE
          "OSPF Version 2, Appendix C.6 Host route parameters"
      ::= { usrOspfHostEntry 1 }
    usrOspfHostIpTOS OBJECT-TYPE
        SYNTAX       TOSType
        MAX-ACCESS   read-only
        STATUS   current
        DESCRIPTION
           "The Type of Service of the route being config-
           ured."
        REFERENCE
          "OSPF Version 2, Appendix C.6 Host route parame-
          ters"
	::= { usrOspfHostEntry 2 }
    usrOspfHostIpMask OBJECT-TYPE
        SYNTAX       IpAddress
        MAX-ACCESS   read-only
        STATUS   current
        DESCRIPTION
           "The IP Mask of the Host."
       REFERENCE
          "The IP Mask of the Host entry - enterprise specific 
           object"
      ::= { usrOspfHostEntry 3 }
--      The OSPF Cryptographic Key Table
    usrOspfCryptoKeyTable OBJECT-TYPE
        SYNTAX   SEQUENCE OF UsrOspfCryptoKeyEntry
        MAX-ACCESS   not-accessible
        STATUS   current
        DESCRIPTION
           "The list of OSPF Cryptographic Authentication Keys 
            per OSPF Interface that will be used to generating/
            verifying Cryptographic authentication."
       REFERENCE
          "OSPF Version 2, Appendix D. Authentication"
      ::= { usrOspf 9 }
    usrOspfCryptoKeyEntry OBJECT-TYPE
        SYNTAX   UsrOspfCryptoKeyEntry
        MAX-ACCESS   not-accessible
        STATUS   current
        DESCRIPTION
           "The information regarding a single OSPF Cryptographic
            Authentication Key."
       INDEX { usrOspfIfIpAddress, usrOspfAddressLessIf, usrOspfCryptoKeyId }
       ::= { usrOspfCryptoKeyTable 1 }
UsrOspfCryptoKeyEntry ::=
    SEQUENCE {
        usrOspfIfIpAddress
            IpAddress,
        usrOspfAddressLessIf
            Integer32,
        usrOspfCryptoKeyId
            Integer32 (0..'FF'h),
        usrOspfCryptoKey
            OCTET STRING,
        usrOspfCryptoKeyStatus
            RowStatus,
        usrOspfCryptoAlgo
            Integer32,
        usrOspfCryptoKeyStartAccept
            Integer32,
        usrOspfCryptoKeyStartGenerate
            Integer32,
        usrOspfCryptoKeyStopGenerate
            Integer32,
        usrOspfCryptoKeyStopAccept
            Integer32
              }
    usrOspfIfIpAddress OBJECT-TYPE
        SYNTAX   IpAddress
        MAX-ACCESS   read-only
        STATUS   current
        DESCRIPTION
           "The IP address of this OSPF interface."
       ::= { usrOspfCryptoKeyEntry 1 }
    usrOspfAddressLessIf OBJECT-TYPE
        SYNTAX   Integer32
        MAX-ACCESS   read-only
        STATUS   current
        DESCRIPTION
           "For the purpose of easing  the  instancing  of
           addressed   and  addressless  interfaces;  This
           variable takes the value 0 on  interfaces  with
           IP  Addresses,  and  the corresponding value of
           ifIndex for interfaces having no IP Address."
       ::= { usrOspfCryptoKeyEntry 2 }
    usrOspfCryptoKeyId OBJECT-TYPE
        SYNTAX   Integer32 (0..'FF'h)
        MAX-ACCESS   read-only
        STATUS   current
        DESCRIPTION
           "The Key ID of this cryptographic key.    This 
            field identifies the algorithm and secret key 
            used to create the message digest appended to 
            the OSPF packet. Key Identifiers are unique
            per-interface (or equivalently, per-subnet)."
       ::= { usrOspfCryptoKeyEntry 3 }
    usrOspfCryptoKey OBJECT-TYPE
        SYNTAX   OCTET STRING (SIZE (0..256))
        MAX-ACCESS   read-create
        STATUS   current
        DESCRIPTION
           "The Cryptographic Authentication Key.  If the 
            Authentication Type is Cryptographic,  and the 
            key length is shorter than 16 octets, the agent
            will left adjust and zero fill to 16 octets.
            When read, usrOspfCryptoKey always returns an 
            Octet String of length zero."
       --CONFIGURABLE
      ::= { usrOspfCryptoKeyEntry 4 }
    usrOspfCryptoKeyStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       --CONFIGURABLE
      ::= { usrOspfCryptoKeyEntry 5 }
    usrOspfCryptoAlgo OBJECT-TYPE
        SYNTAX   Integer32
                    -- md5 (0)
        MAX-ACCESS   read-create
        STATUS   current
        DESCRIPTION
           "This field identifies the algorithm used to create
           message digest."
      DEFVAL { 0 }
       --CONFIGURABLE
      ::= { usrOspfCryptoKeyEntry 6 }
    usrOspfCryptoKeyStartAccept OBJECT-TYPE
        SYNTAX   Integer32
        MAX-ACCESS   read-create
        STATUS   current
        DESCRIPTION
           "The time that the router will start accepting 
           packets that have been created with the given key.
           The time is expressed as a number of seconds since
           the Epoch, 00:00:00 GMT, on January 1, 1995"
       --CONFIGURABLE
      ::= { usrOspfCryptoKeyEntry 7 }
    usrOspfCryptoKeyStartGenerate OBJECT-TYPE
        SYNTAX   Integer32
        MAX-ACCESS   read-create
        STATUS   current
        DESCRIPTION
           "The time that the router will start using the 
           key for packet generation.
           The time is expressed as a number of seconds since
           the Epoch, 00:00:00 GMT, on January 1, 1995"
       --CONFIGURABLE
      ::= { usrOspfCryptoKeyEntry 8 }
    usrOspfCryptoKeyStopGenerate OBJECT-TYPE
        SYNTAX   Integer32
        MAX-ACCESS   read-create
        STATUS   current
        DESCRIPTION
           "The time that the router will stop using the 
           key for packet generation.
           The time is expressed as a number of seconds since
           the Epoch, 00:00:00 GMT, on January 1, 1995.
           The value 0HFFFFFFFF stands for infinity."
       --CONFIGURABLE
      ::= { usrOspfCryptoKeyEntry 9 }
    usrOspfCryptoKeyStopAccept OBJECT-TYPE
        SYNTAX   Integer32
        MAX-ACCESS   read-create
        STATUS   current
        DESCRIPTION
           "The time that the router will stop accepting 
           packets that have been created with the given key.
           The time is expressed as a number of seconds since
           the Epoch, 00:00:00 GMT, on January 1, 1995
           The value 0HFFFFFFFF stands for infinity."
       --CONFIGURABLE
      ::= { usrOspfCryptoKeyEntry 10 }
--      OSPF Default Area
usrOspfDefaultAreaStatus OBJECT-TYPE
        SYNTAX   RowStatus
        MAX-ACCESS   read-create
        STATUS   current
        DESCRIPTION
           "This variable is used to delete the ospf default
            area."
::= { usrOspf 10 }
END     -- End of USR-OSPF-MIB DEFINITIONS
-- Commented out items for ospf send policy table. To restore
-- the ospf send policy rip gateway and rip interface cut and
-- and paste these items back into the table. Within the table
-- they followed the export policy action. Adjust usrOspfExportPolicyEntry
-- numbers accordingly for ospf send metric, metric type, and tag
-- after reinserting rip gateway and interface.
--
--      INDEX { 
--	usrOspfExportPolicyRouteSource, 
--	usrOspfExportPolicyNet,
--	usrOspfExportPolicyMask,
--	usrOspfExportPolicyFromRIPGateway,
--	usrOspfExportPolicyReceivedOnRIPInterface 
--	}
--
-- UsrOspfExportPolicyEntry ::= SEQUENCE {
--      usrOspfExportPolicyRouteSource		INTEGER,
--      usrOspfExportPolicyNet			IpAddress,
--      usrOspfExportPolicyMask			IpAddress,
--      usrOspfExportPolicyAction		INTEGER,
--      usrOspfExportPolicyFromRIPGateway		IpAddress,
--      usrOspfExportPolicyReceivedOnRIPInterface	IpAddress,
--      usrOspfExportPolicyMetric			Integer32,
--      usrOspfExportPolicyMetricType		INTEGER,
--      usrOspfExportPolicyTag			Integer32,
--      usrOspfExportPolicyStatus               RowStatus
-- }
--
-- usrOspfExportPolicyFromRIPGateway OBJECT-TYPE
--        SYNTAX   	IpAddress
--        MAX-ACCESS   	read-only
--        STATUS   	current
--        DESCRIPTION
--           "This attribute applies when the route to be exported is a
-- RIP route. If this attribute is defined, then only RIP updates
-- received from the specified RIP gateway are eligible for export. Any
-- RIP gateway can be specified using 0.0.0.0 as the address."
-- ::= { usrOspfExportPolicyEntry 5 }
--
-- usrOspfExportPolicyReceivedOnRIPInterface OBJECT-TYPE
--        SYNTAX   	IpAddress
--        MAX-ACCESS   	read-only
--        STATUS   	current
--        DESCRIPTION
--           "This attribute applies when the route described by this
-- policy is a RIP route. If this attribute is defined, then only RIP
-- updates received on the specified interface are eligible for
-- export. Use 0.0.0.0 to indicate that this policy applies to RIP
-- updates received on any interface."
-- ::= { usrOspfExportPolicyEntry 6 }
--
-- ************************************************************************
--
--    usr_fr_ext.mib - The Frame Relay enterprise specific MIB module
--                     This MIB module when used in conjunction with
--                     rfc2115.mib obsoletes previously used usr_fr.mib 
--
--
-- Author:         <Cezary Wierucki>
--
