XEDIA-IPBACKUP-MIB DEFINITIONS ::= BEGIN

IMPORTS 
        MODULE-IDENTITY, OBJECT-TYPE,
        Integer32, IpAddress     FROM SNMPv2-SMI    -- RFC1442
        MODULE-COMPLIANCE, OBJECT-GROUP     FROM SNMPv2-CONF
        TEXTUAL-CONVENTION                  FROM SNMPv2-TC     -- RFC1443
        ifIndex                             FROM RFC1213-MIB
        xediaMibs                           FROM XEDIA-REG
        ;    

xediaIpBackupMIB MODULE-IDENTITY
    LAST-UPDATED "9802232155Z" -- February 23,1998
    ORGANIZATION "Xedia Corp."
    CONTACT-INFO
        "support@xedia.com"
    DESCRIPTION
        "This module defines additional objects for management of IP 
        Backup in Xedia devices, above and beyond what is defined in the
        for the VRRP (or other implemented backup procedures)."
    ::= { xediaMibs 15 }

-- *******************************************************************
--  Textual Conventions
-- *******************************************************************

    BackupId ::= TEXTUAL-CONVENTION
        STATUS       current
        DESCRIPTION
            "A unique number that serves to identify an instance of
            IP backup.  This is equivalent to the type 'VrId' defined
            for VRRP."
        SYNTAX      Integer32 (1..255)

-- Top-level organization of the MIB

xipbackupObjects          OBJECT IDENTIFIER ::= { xediaIpBackupMIB 1 }
xipbackupConformance      OBJECT IDENTIFIER ::= { xediaIpBackupMIB 2 }

xipbackupGeneral          OBJECT IDENTIFIER ::= { xipbackupObjects 1 }

--
-- An IP Backup  on/off control
--
xipbackupAdminStatus OBJECT-TYPE
    SYNTAX      INTEGER {
                    enabled(1),
                    disabled(2)
                }
    MAX-ACCESS  read-write
    STATUS      current
    DESCRIPTION
        "The administrative status of IP Backup for the IP router. It is the 
        desired state of IP Backup for the router.  The value 'enabled(1)' 
	indicates that the IP Backup process should be active in the router, 
	while 'disabled(2)' indicates that IP Backup should not be active for 
        the router."
    DEFVAL      { disabled }
    ::= { xipbackupGeneral 1 }

--
-- An IP Backup  on/off control
--
xipbackupBridgeAdminStatus OBJECT-TYPE
    SYNTAX      INTEGER {
                    enabled(1),
                    disabled(2)
                }
    MAX-ACCESS  read-write
    STATUS      current
    DESCRIPTION
        "The administrative status of IP Backup for the bridge. It is the
        desired state of IP Backup for the bridge.  The value 'enabled(1)' 
        indicates that the IP Backup process should be active in the router,
        while 'disabled(2)' indicates that IP Backup should not be active for
        the bridge.  The bridge will not forward frames if this value is 
        enabled unless it has achieved the master state through the IP Backup
        protocol."
    DEFVAL      { disabled }
    ::= { xipbackupGeneral 2 }


-- *******************************************************************
-- xipbackupInst - IPBackup instance Table
-- proprietary extensions to vrrpOperTable
-- an ipbackup instance is the same as a VRRP VR (virtual router)
-- *******************************************************************

    xipbackupInstTable OBJECT-TYPE
        SYNTAX       SEQUENCE OF XipbackupInstEntry
        MAX-ACCESS   not-accessible
        STATUS       current
        DESCRIPTION
            "The information associated with a backup instance.  This
             typically augments the vrrpOperTable."
        ::= { xipbackupObjects 2 }

    xipbackupInstEntry OBJECT-TYPE
        SYNTAX       XipbackupInstEntry
        MAX-ACCESS   not-accessible
        STATUS       current
        DESCRIPTION
          "An entry in the table, containing the operational
           characteristics of a backup instance.  A given 
           backup instance is identifed by a combination
           of the IF index and instance ID.  This table typically
           augments the VRRP vrrpOperTable where vrid = instance ID."
        INDEX    { ifIndex, xipbackupInstId }
        ::= { xipbackupInstTable 1 }

    XipbackupInstEntry ::=
        SEQUENCE {
            xipbackupInstId
                BackupId,
            xipbackupInstTrackIp
                IpAddress,
            xipbackupInstInitializeCode
                INTEGER
    }

    xipbackupInstId OBJECT-TYPE
        SYNTAX       BackupId
        MAX-ACCESS   not-accessible
        STATUS       current
        DESCRIPTION
            "This object contains the backup instance identifier."
        ::= { xipbackupInstEntry 1 }

    xipbackupInstTrackIp OBJECT-TYPE
        SYNTAX       IpAddress
        MAX-ACCESS   read-write
        STATUS       current
        DESCRIPTION
           "An IP address to be 'tracked' by this backup instance.
            If this value is set, a backup instance (virtual router)
            cannot become Master if this interface is not up."
        DEFVAL      { 0 }
        ::= { xipbackupInstEntry 2 }

    xipbackupInstInitializeCode OBJECT-TYPE
        SYNTAX       INTEGER {
            ready(1),
            globalDisabled(2),
            instanceDisabled(3),
            rowStatusNotActive(4),
            noAssociatedIpAddr(5),
            noAddressOnSubnet(6),
            trackedIpDown(7),
            interfaceDown(8),
            bridgeDown(9)
        }
        MAX-ACCESS   read-only
        STATUS       current
        DESCRIPTION
            "The reason, if any, that this virtual router has not
             progressed past the Initialize state.  If multiple reasons,
             are present, only one value is shown and correcting
             that condition or configuration will reveal the
             remaining reason(s).  If the virtual router may enter the
             Master or Backup state, the value shown is 'ready'."
        ::= { xipbackupInstEntry 3  }


-- ****************************************************************
-- Conformance Information
-- ****************************************************************
 
xipbackupCompliances OBJECT IDENTIFIER ::= { xipbackupConformance 1 }
xipbackupGroups      OBJECT IDENTIFIER ::= { xipbackupConformance 2 }
 
--
-- Compliance Statements
--
 
xipbackupCompliance MODULE-COMPLIANCE
    STATUS      current
    DESCRIPTION
        "The compliance statement for all agents that support this
        MIB. A compliant agent implements all objects defined in this
        MIB."
    MODULE  -- this module
    MANDATORY-GROUPS {
        xipbackupAllGroup
    }
    ::= { xipbackupCompliances 1 }
 
--
-- Object Groups
--
 
xipbackupAllGroup OBJECT-GROUP
    OBJECTS {
        xipbackupAdminStatus,
        xipbackupBridgeAdminStatus,
        xipbackupInstTrackIp,
        xipbackupInstInitializeCode
    }
    STATUS      current
    DESCRIPTION
        "The set of all accessible objects in this MIB."
    ::= { xipbackupGroups 1 }

END
