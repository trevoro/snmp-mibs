ACC-XBR DEFINITIONS ::= BEGIN

    IMPORTS
		OBJECT-TYPE, IpAddress, TimeTicks, Gauge, Counter FROM RFC1155-SMI
		TRAP-TYPE FROM RFC-1215
        accTrapLogSeqNum FROM ACC-SYSTEM
	 accBRG, DisplayString, RowStatus, IfIndex, SmdsAddress
             FROM ACC-MIB;
-- Translation Bridging Group
   accXBr         OBJECT IDENTIFIER ::= { accBRG 34 }
	accXBridge	OBJECT IDENTIFIER ::= { accXBr 1 }
	  accXBridgeStatus	OBJECT-TYPE   
		SYNTAX INTEGER {
			enabled(1),
			disabled(2)
			}
		ACCESS	read-write
		STATUS	mandatory
		DESCRIPTION
				 " Status of translation bridging."
		::= { accXBridge 1 }
	  accXBridgeRingId	OBJECT-TYPE   
        SYNTAX INTEGER
		ACCESS	read-write
		STATUS	mandatory
		DESCRIPTION
				 " Translation bridging ring ID."
		::= { accXBridge 2 }

END
