--
-- 
--	INTEL CORPORATION PROPRIETARY INFORMATION
--
--	This software is supplied under the terms of a license agreement or
--	comment "nondisclosure agreement with Intel Corporation and may not be copied
--	or disclosed except in accordance with the terms of that agreement.
--
--	Copyright (c) 1999 Intel Corporation. All Rights Reserved.
--
--
--
--

	MIB-INTEL-IP DEFINITIONS ::= BEGIN

	IMPORTS
		IpAddress
			FROM RFC1155-SMI
		OBJECT-TYPE
			FROM RFC-1212

		mib2ext
			FROM INTEL-GEN-MIB;

	ipr  OBJECT IDENTIFIER ::= { mib2ext 38 }


	RowStatus ::= INTEGER { active(1), notInService(2), notReady(3),
				createAndGo(4), createAndWait(5), destroy(6) }

	--
	-- The IP routing table 
	--

	rtIpRouteTable OBJECT-TYPE
		SYNTAX  SEQUENCE OF RtIpRouteEntry
		ACCESS  not-accessible
		STATUS  optional
		DESCRIPTION
			"This entity's IP Routing table."
		::= { ipr 1 }

	rtIpRouteEntry OBJECT-TYPE
		SYNTAX  RtIpRouteEntry
		ACCESS  not-accessible
		STATUS  optional
		DESCRIPTION
			"A route to a particular destination."
		INDEX   { 
			  rtIpRouteChassis,
			  rtIpRouteModule,
			  rtIpRouteInst,
			  rtIpRouteDest, 
			  rtIpRouteMask,
			  rtIpRouteIfIndex,
			  rtIpRouteNextHop
			}
		::= { rtIpRouteTable 1 }

	RtIpRouteEntry ::=
		SEQUENCE {
		rtIpRouteChassis
			INTEGER,
		rtIpRouteModule
			INTEGER,
		rtIpRouteInst
			INTEGER,
		rtIpRouteDest
			IpAddress,
		rtIpRouteMask
			IpAddress,
		rtIpRouteIfIndex
			INTEGER,
		rtIpRouteNextHop
			IpAddress,
		rtIpRoutePref
			INTEGER,
		rtIpRouteMetric
			INTEGER,
		rtIpRouteProto
			INTEGER,
		rtIpRouteAge
			INTEGER
		}

	rtIpRouteChassis OBJECT-TYPE
		SYNTAX  INTEGER
		ACCESS  read-only
		STATUS  optional
		DESCRIPTION
			"Chassis number in stack that contains the module."
		::= { rtIpRouteEntry 1 }

	rtIpRouteModule OBJECT-TYPE
		SYNTAX  INTEGER
		ACCESS  read-only
		STATUS  optional
		DESCRIPTION
			"Module number in the chassis."
		::= { rtIpRouteEntry 2 }

	rtIpRouteInst OBJECT-TYPE
		SYNTAX  INTEGER
		ACCESS  read-only
		STATUS  optional
		DESCRIPTION
			"Routing table instance number."
		::= { rtIpRouteEntry 3 }

	rtIpRouteDest OBJECT-TYPE
		SYNTAX  IpAddress
		ACCESS  read-only
		STATUS  optional
		DESCRIPTION
			"The destination IP address of this route."
		::= { rtIpRouteEntry 4 }

	rtIpRouteMask OBJECT-TYPE
		SYNTAX  IpAddress
		ACCESS  read-only
		STATUS  optional
		DESCRIPTION
			"Indicate the mask to be logical-ANDed with the
			destination address before being compared to the
			value in the rtIpRouteDest field."
		::= { rtIpRouteEntry 5 }

	rtIpRouteIfIndex OBJECT-TYPE
		SYNTAX  INTEGER
		ACCESS  read-only
		STATUS  optional
		DESCRIPTION
			"The interface that the frame is forwarded on."
		::= { rtIpRouteEntry 6 }

	rtIpRouteNextHop OBJECT-TYPE
		SYNTAX  IpAddress
		ACCESS  read-only
		STATUS  optional
		DESCRIPTION
			"The IP address of the next hop of this route."
		::= { rtIpRouteEntry 7 }

	rtIpRoutePref OBJECT-TYPE
		SYNTAX  INTEGER
		ACCESS  read-only
		STATUS  optional
		DESCRIPTION
			"The preference value for this route."
		::= { rtIpRouteEntry 8 }

	rtIpRouteMetric OBJECT-TYPE
		SYNTAX  INTEGER
		ACCESS  read-only
		STATUS  optional
		DESCRIPTION
			"The routing metric for this route.  The
			semantics of this metric are determined by the
			routing-protocol specified in the route's
			rtIpRouteProto value."
		::= { rtIpRouteEntry 9 }

	rtIpRouteProto OBJECT-TYPE
		SYNTAX  INTEGER {
			direct(1),
			static(2),
			ospf(3),
			rip(4),
			other(5),
			all(6)
		}
		ACCESS  read-only
		STATUS  optional
		DESCRIPTION
			"The routing mechanism via which this route was
			learned."
		::= { rtIpRouteEntry 10 }

	rtIpRouteAge OBJECT-TYPE
		SYNTAX  INTEGER
		ACCESS  read-only
		STATUS  optional
		DESCRIPTION
			"The number of seconds since this route was last 
			updated or otherwise detemined to be correct. Note
			that no semantics of 'too old' can be implied except
			through knowledge of the routing protocol by which the
			route was learned."
		::= { rtIpRouteEntry 11 }


        --
        -- The table of all alternative RTEs 
        --

        rtIpRteTable OBJECT-TYPE
		SYNTAX  SEQUENCE OF RtIpRteEntry
		ACCESS  not-accessible
		STATUS  optional
		DESCRIPTION
			"The list of all routing table entries (RTE).
			There may be several entries describing a route to the 
			same destination (entries with the same IP address and 
			mask but different preference, protocol or metric). 
			Forwarding engine uses only the best one - this one 
			which can be found in the Routing Table. All other 
			entries as well the best one are available in 
			rtIpRteTable.
			If for some reason the best entry has been lost then 
			the best one will be chosen from other entries to the 
			same destination."
		::= { ipr 2 }

        rtIpRteEntry OBJECT-TYPE
		SYNTAX  RtIpRteEntry
		ACCESS  not-accessible
		STATUS  optional
		DESCRIPTION
			"A route to a particular destination."
		INDEX   { 
			  rtIpRteChassis,
			  rtIpRteModule,
			  rtIpRteInst,
			  rtIpRteDest,
		          rtIpRteMask, 
		          rtIpRtePref,
			  rtIpRteProto,
		          rtIpRteIfIndex,
		          rtIpRteNextHop
		        }
		::= { rtIpRteTable 1 }

        RtIpRteEntry ::=
		SEQUENCE {
		rtIpRteChassis
			INTEGER,
		rtIpRteModule
			INTEGER,
		rtIpRteInst
			INTEGER,
		rtIpRteDest
			IpAddress,
		rtIpRteMask
			IpAddress,
		rtIpRtePref
			INTEGER,
		rtIpRteProto
			INTEGER,
		rtIpRteIfIndex
			INTEGER,
		rtIpRteNextHop
			IpAddress,
		rtIpRteState
			INTEGER,
		rtIpRteAge
			INTEGER,
		rtIpRteMetric
			INTEGER
		}

        rtIpRteChassis OBJECT-TYPE
		SYNTAX  INTEGER
		ACCESS  read-only
		STATUS  optional
		DESCRIPTION
			"Chassis number in stack that contains the module."
		::= { rtIpRteEntry 1 }

        rtIpRteModule OBJECT-TYPE
		SYNTAX  INTEGER
		ACCESS  read-only
		STATUS  optional
		DESCRIPTION
			"Module number in the chassis."
		::= { rtIpRteEntry 2 }

        rtIpRteInst OBJECT-TYPE
		SYNTAX  INTEGER
		ACCESS  read-only
		STATUS  optional
		DESCRIPTION
			"Alternative routing table instance number."
		::= { rtIpRteEntry 3 }

        rtIpRteDest OBJECT-TYPE
		SYNTAX  IpAddress
		ACCESS  read-only
		STATUS  optional
		DESCRIPTION
			"The destination IP address of this route."
		::= { rtIpRteEntry 4 }

        rtIpRteMask OBJECT-TYPE
		SYNTAX  IpAddress
		ACCESS  read-only
		STATUS  optional
		DESCRIPTION
			"Indicate the mask to be logical-ANDed with the
			destination address before being compared to the
			value in the rtIpRteDest field."
		::= { rtIpRteEntry 5 }

        rtIpRtePref OBJECT-TYPE
		SYNTAX  INTEGER
		ACCESS  read-only
		STATUS  optional
		DESCRIPTION
			"The preference value for this route."
		::= { rtIpRteEntry 6 }

        rtIpRteProto OBJECT-TYPE
		SYNTAX  INTEGER {
			direct(1),
			static(2),
			ospf(3),
			rip(4),
			other(5),
			all(6)
		}
		ACCESS  read-only
		STATUS  optional
		DESCRIPTION
			"The routing mechanism via which this route was
			learned."
		::= { rtIpRteEntry 7 }

        rtIpRteIfIndex OBJECT-TYPE
		SYNTAX  INTEGER
		ACCESS  read-only
		STATUS  optional
		DESCRIPTION
			"The interface that the frame is forwarded on."
		::= { rtIpRteEntry 8 }

        rtIpRteNextHop OBJECT-TYPE
		SYNTAX  IpAddress
		ACCESS  read-only
		STATUS  optional
		DESCRIPTION
			"The IP address of the next hop of this route."
		::= { rtIpRteEntry 9 }

         rtIpRteState OBJECT-TYPE
		SYNTAX  INTEGER {
			active(1),
			inactive(2)
		}
		ACCESS  read-write
		STATUS  optional
		DESCRIPTION
			"The state of the route."
		::= { rtIpRteEntry 10 }

	rtIpRteAge OBJECT-TYPE
		SYNTAX  INTEGER
		ACCESS  read-only
		STATUS  optional
		DESCRIPTION
			"The number of seconds since this route was last 
			updated or otherwise detemined to be correct. Note
			that no semantics of 'too old' can be implied except
			through knowledge of the routing protocol by which the
			route was learned."
		::= { rtIpRteEntry 11 }

	rtIpRteMetric OBJECT-TYPE
		SYNTAX  INTEGER
		ACCESS  read-write
		STATUS  optional
		DESCRIPTION
			"The metric of the alternative route."
		::= { rtIpRteEntry 12 }

        --
        -- The table of all static routes
        --

        rtIpStaticRouteTable OBJECT-TYPE
		SYNTAX  SEQUENCE OF RtIpStaticRouteEntry
		ACCESS  not-accessible
		STATUS  optional
		DESCRIPTION
			"A table of all configured static routes."
		::= { ipr 3 }

        rtIpStaticRouteEntry OBJECT-TYPE
		SYNTAX  RtIpStaticRouteEntry
		ACCESS  not-accessible
		STATUS  optional
		DESCRIPTION
			"An entry describing a single static route."
		INDEX   { 
			  rtIpStRtChassis,
			  rtIpStRtModule,
			  rtIpStRtInst,
			  rtIpStRtDest,
		          rtIpStRtMask,
			  rtIpStRtPref,
			  rtIpStRtIfIndex,
			  rtIpStRtNextHop
			}
		::= { rtIpStaticRouteTable 1 }

        RtIpStaticRouteEntry ::=
		SEQUENCE {
		rtIpStRtChassis
			INTEGER,
		rtIpStRtModule
			INTEGER,
		rtIpStRtInst
			INTEGER,
		rtIpStRtDest
			IpAddress,
		rtIpStRtMask
			IpAddress,
		rtIpStRtPref
			INTEGER,
		rtIpStRtIfIndex
			INTEGER,
		rtIpStRtNextHop
			IpAddress,
		rtIpStRtMetric
			INTEGER,
		rtIpStRtStatus
			RowStatus,
		rtIpStRtState
			INTEGER
		}

        rtIpStRtChassis OBJECT-TYPE
		SYNTAX  INTEGER
		ACCESS  read-write
		STATUS  optional
		DESCRIPTION
			"Chassis number in stack that contains the module."
		::= { rtIpStaticRouteEntry 1 }

        rtIpStRtModule OBJECT-TYPE
		SYNTAX  INTEGER
		ACCESS  read-write
		STATUS  optional
		DESCRIPTION
			"Module number in the chassis."
		::= { rtIpStaticRouteEntry 2 }

        rtIpStRtInst OBJECT-TYPE
		SYNTAX  INTEGER
		ACCESS  read-write
		STATUS  optional
		DESCRIPTION
			"Static routing table instance number."
		::= { rtIpStaticRouteEntry 3 }

        rtIpStRtDest OBJECT-TYPE
		SYNTAX  IpAddress
		ACCESS  read-write
		STATUS  optional
		DESCRIPTION
			"The destination IP address of this route."
		::= { rtIpStaticRouteEntry 4 }

        rtIpStRtMask OBJECT-TYPE
		SYNTAX  IpAddress
		ACCESS  read-write
		STATUS  optional
		DESCRIPTION
			"The destination IP mask of this route."
		::= { rtIpStaticRouteEntry 5 }

        rtIpStRtPref OBJECT-TYPE
		SYNTAX  INTEGER
		ACCESS  read-write
		STATUS  optional
		DESCRIPTION
			"The preference value for this route. This value 
			should be unique (neither other static routes to the 
			same destination nor other protocols can use this 
			value)."
		::= { rtIpStaticRouteEntry 6 }

        rtIpStRtIfIndex OBJECT-TYPE
		SYNTAX  INTEGER
		ACCESS  read-write
		STATUS  optional
		DESCRIPTION
			"The interface that the frame is forwarded on."
		::= { rtIpStaticRouteEntry 7 }

        rtIpStRtNextHop OBJECT-TYPE
		SYNTAX  IpAddress
		ACCESS  read-write
		STATUS  optional
		DESCRIPTION
			"The IP address of the next hop of this route."
		::= { rtIpStaticRouteEntry 8 }

        rtIpStRtMetric OBJECT-TYPE
		SYNTAX  INTEGER
		ACCESS  read-write
		STATUS  optional
		DESCRIPTION
			"The routing metric for this route."
		::= { rtIpStaticRouteEntry 9 }

        rtIpStRtStatus OBJECT-TYPE
		SYNTAX	RowStatus
		ACCESS  read-write
		STATUS  optional
		DESCRIPTION
			"The status of the route. Setting it to 'destroy'(6) 
			removes the static route from router's configuration."
		::= { rtIpStaticRouteEntry 10 }

        rtIpStRtState OBJECT-TYPE
		SYNTAX  INTEGER {
			active(1),
			inactive(2)
		}
		ACCESS  read-write
		STATUS  optional
		DESCRIPTION
			"The current state of the route."
		::= { rtIpStaticRouteEntry 11 }

	END
