-- 
-- SNMP MIB for WaveLAN  (Version 2.1, 7-Mar-97)
-- 
-- 
-- Copyright (c) 1997 by Lucent Technologies Inc..
-- All rights reserved.  Distribution of this document is authorized
-- on condition that this copyright notice is included.
-- This Lucent Technologies SNMP Management Information
-- Base Specification (Specification) embodies 
-- Lucent Technologies' proprietary intellectual
-- property. Lucent Technologies retains all title and
-- ownership in the Specification, including any revisions.
-- 
-- It is Lucent Technologies intent to encourage the widespread
-- use of this Specification in connection with the management of
-- WaveLAN products. Lucent Technologies grants 
-- vendors, end-users, and other interested parties a 
-- non-exclusive license to use this Specification in connection 
-- with the management of WaveLAN products.
-- 
-- This Specification is provided "AS IS", and makes no 
-- warranty, either express or implied, as to the use,
-- operation, condition, or performance of the Specification.
-- 
-- WaveLAN and WavePOINT are trademarks of
-- Lucent Technologies.
-- 


WaveLAN-MIB
-- { iso org(3) dod(6) internet(1) private(4) enterprises(1) 
--	att-2(74) att-mgmt(2) }

DEFINITIONS ::= BEGIN

IMPORTS
	enterprises, Counter FROM RFC1155-SMI
	OBJECT-TYPE FROM RFC-1212
	DisplayString FROM RFC1213-MIB;

att-2		OBJECT IDENTIFIER ::= { enterprises 74 }
att-mgmt	OBJECT IDENTIFIER ::= { att-2 2 }
wavelan	OBJECT IDENTIFIER ::= { att-mgmt 21 }

-- Interfaces supporting this MIB should specify this 'wavelan'
-- Object Identifier in ifSpecific.

wavelanInterface	OBJECT IDENTIFIER ::= { wavelan 1 }

-- 
-- The WaveLAN (Interface) MIB consists of the following groups:
-- 
-- the Generic WaveLAN Interface group, mandatory,
-- containing:
-- 	wliNicTable	OBJECT IDENTIFIER ::= { wavelanInterface 1 }
-- 	wliPhyTable	OBJECT IDENTIFIER ::= { wavelanInterface 2 }
-- 	wliMacTable	OBJECT IDENTIFIER ::= { wavelanInterface 3 }
-- 	wliDriverTable	OBJECT IDENTIFIER ::= { wavelanInterface 4 }
-- 	wliEncTable	OBJECT IDENTIFIER ::= { wavelanInterface 5 }
-- 
-- the Multicast Delay group, optional:
-- 	wliMcastDelayTable	OBJECT IDENTIFIER ::= { wavelanInterface 6 }


-- 
-- The Generic WaveLAN Interface group
-- 
-- Implementation of this group is mandatory
-- 

-- 
-- WaveLAN Interface NIC information
-- 

wliNicTable OBJECT-TYPE
	SYNTAX  SEQUENCE OF WliNicEntry
	ACCESS  not-accessible
	STATUS  mandatory
	DESCRIPTION
		"Network Interface Card information for a
		collection of WaveLAN interfaces attached to a
		particular system."
	::= { wavelanInterface 1 }

wliNicEntry OBJECT-TYPE
	SYNTAX  WliNicEntry
	ACCESS  not-accessible
	STATUS  mandatory
	DESCRIPTION
		"Network Interface Card information for a
		particular WaveLAN interface."
	INDEX   { wliNicIndex }
	::= { wliNicTable 1 }

WliNicEntry ::= SEQUENCE {
	wliNicIndex
		INTEGER,
	wliNicBusType
		INTEGER,
	wliNicSlot
		INTEGER,
	wliNicIrq
		INTEGER,
	wliNicError
		Counter,
	wliNicOutOfRxResource
		Counter
   }

wliNicIndex OBJECT-TYPE
	SYNTAX  INTEGER
	ACCESS  read-only
	STATUS  mandatory
	DESCRIPTION
		"An index value that uniquely identifies a WaveLAN
		network interface this NIC information applies to.
		The interface associated with a particular
		value of this index is the same interface
		as identified by the same value of ifIndex."
	::= { wliNicEntry 1 }

wliNicBusType OBJECT-TYPE
	SYNTAX  INTEGER  {
			xtBus(1),
			isaBus(2),
			mcBus(3),
			pcmcia2Bus(4),
			wavepointBus(5)
		}
	ACCESS  read-only
	STATUS  mandatory
	DESCRIPTION
		"The bus-type supported by this NIC."
	::= { wliNicEntry 2 }

wliNicSlot OBJECT-TYPE
	SYNTAX  INTEGER  (1..8)
	ACCESS  read-only
	STATUS  mandatory
	DESCRIPTION
		"The I/O Base Address (ISA/AT) or Slot Number (MC)
		or Socket Number (PCMCIA) used by this NIC.
		For ISA/AT (and alike) Base Addresses, the following
		values are used:
		1='0300'H, 2='0390'H, 3='03C0'H, 4='03E0'H"
	::= { wliNicEntry 3 }

wliNicIrq OBJECT-TYPE
	SYNTAX  INTEGER  (0..15)
	ACCESS  read-only
	STATUS  mandatory
	DESCRIPTION
		"The Interrupt Request Number (IRQ) used by this NIC."
	::= { wliNicEntry 4 }

wliNicError OBJECT-TYPE
	SYNTAX  Counter
	ACCESS  read-only
	STATUS  mandatory
	DESCRIPTION
		"A counter for miscellaneous board errors.
		It indicates (intermittent) NIC hardware problems."
	::= { wliNicEntry 5 }

wliNicOutOfRxResource OBJECT-TYPE
	SYNTAX  Counter
	ACCESS  read-only
	STATUS  mandatory
	DESCRIPTION
		"A counter for the number of times the 
		NIC is out of resources for the receiver, 
		causing the receiver to be switched off temporarily."
	::= { wliNicEntry 6 }

-- 
-- WaveLAN Interface PHY information
-- 

wliPhyTable OBJECT-TYPE
	SYNTAX  SEQUENCE OF WliPhyEntry
	ACCESS  not-accessible
	STATUS  mandatory
	DESCRIPTION
		"PHY status information and control variables for a
		collection of WaveLAN interfaces attached to a
		particular system."
	::= { wavelanInterface 2 }

wliPhyEntry OBJECT-TYPE
	SYNTAX  WliPhyEntry
	ACCESS  not-accessible
	STATUS  mandatory
	DESCRIPTION
		"PHY status information and control variables for a
		particular WaveLAN interface."
	INDEX   { wliPhyIndex }
	::= { wliPhyTable 1 }

WliPhyEntry ::= SEQUENCE {
	wliPhyIndex
		INTEGER,
	wliPhyDsp
		INTEGER,
	wliPhyFrequency
		INTEGER,
	wliPhyNwid
		OCTET STRING  (SIZE  (2)),
	wliPhyRfSilenceLevel
		INTEGER,
	wliPhyOwnNwid
		Counter,
	wliPhyOtherNwid
		Counter,
	wliPhyLowSnr
		Counter,
	wliPhyGoodSnr
		Counter,
	wliPhyExcellentSnr
		Counter
   }

wliPhyIndex OBJECT-TYPE
	SYNTAX  INTEGER
	ACCESS  read-only
	STATUS  mandatory
	DESCRIPTION
		"An index value that uniquely identifies a WaveLAN
		network interface this PHY information applies to.
		The interface associated with a particular
		value of this index is the same interface
		as identified by the same value of ifIndex."
	::= { wliPhyEntry 1 }

wliPhyDsp OBJECT-TYPE
	SYNTAX  INTEGER  {
			icarus(1),
			daedalus(2)
		}
	ACCESS  read-only
	STATUS  mandatory
	DESCRIPTION
		"The Digital Signal Processor on the board."
	::= { wliPhyEntry 2 }

wliPhyFrequency OBJECT-TYPE
	SYNTAX  INTEGER  {
			f915Mhz(1),
			f2425Mhz(2),
			f2460Mhz(3),
			f2484Mhz(4),
			f2430Mhz(5),	-- actually 2430.5 MHz
			f2412Mhz(6),
			f2422Mhz(7),
			f2432Mhz(8),
			f2442Mhz(9),
			f2452Mhz(10),
			f2462Mhz(11)
		}
	ACCESS  read-only
	STATUS  mandatory
	DESCRIPTION
		"The mid-point of the frequency band
		this WaveLAN NIC operates in."
	::= { wliPhyEntry 3 }

wliPhyNwid OBJECT-TYPE
	SYNTAX  OCTET STRING  (SIZE  (2))
	ACCESS  read-write
	STATUS  mandatory
	DESCRIPTION
		"The WaveLAN Network ID (NWID) this RF-modem
		is currently configured for."
	::= { wliPhyEntry 4 }

wliPhyRfSilenceLevel OBJECT-TYPE
	SYNTAX  INTEGER  (0..36)
	ACCESS  read-only
	STATUS  mandatory
	DESCRIPTION
		"The RF Silence Level as currently read from
		the RF modem."
	::= { wliPhyEntry 5 }

wliPhyOwnNwid OBJECT-TYPE
	SYNTAX  Counter
	ACCESS  read-only
	STATUS  mandatory
	DESCRIPTION
		"Own NWID counter; the number of frames
		received with the configured NWID."
	::= { wliPhyEntry 6 }

wliPhyOtherNwid OBJECT-TYPE
	SYNTAX  Counter
	ACCESS  read-only
	STATUS  mandatory
	DESCRIPTION
		"Other NWID counter; the number of frames
		received with different NWID than configured."
	::= { wliPhyEntry 7 }

wliPhyLowSnr OBJECT-TYPE
	SYNTAX  Counter
	ACCESS  read-only
	STATUS  mandatory
	DESCRIPTION
		"The number of times the Signal to Noise Ratio
		(sample) of a frame reception was low."
	::= { wliPhyEntry 8 }

wliPhyGoodSnr OBJECT-TYPE
	SYNTAX  Counter
	ACCESS  read-only
	STATUS  mandatory
	DESCRIPTION
		"The number of times the Signal to Noise Ratio
		(sample) of a frame reception was good."
	::= { wliPhyEntry 9 }

wliPhyExcellentSnr OBJECT-TYPE
	SYNTAX  Counter
	ACCESS  read-only
	STATUS  mandatory
	DESCRIPTION
		"The number of times the Signal to Noise Ratio
		(sample) of a frame reception was excellent."
	::= { wliPhyEntry 10 }

-- 
-- WaveLAN Interface MAC information
-- 

wliMacTable OBJECT-TYPE
	SYNTAX  SEQUENCE OF WliMacEntry
	ACCESS  not-accessible
	STATUS  mandatory
	DESCRIPTION
		"MAC status information and control variables for a
		collection of WaveLAN interfaces attached to a
		particular system."
	::= { wavelanInterface 3 }

wliMacEntry OBJECT-TYPE
	SYNTAX  WliMacEntry
	ACCESS  not-accessible
	STATUS  mandatory
	DESCRIPTION
		"MAC status information and control variables for a
		particular WaveLAN interface."
	INDEX   { wliMacIndex }
	::= { wliMacTable 1 }

WliMacEntry ::= SEQUENCE {
	wliMacIndex
		INTEGER,
	wliMacAddressSelect
		INTEGER,
	wliMacCaDefers
		Counter,
	wliMacDeferredTransmissions
		Counter,
	wliMacFCSErrors
		Counter,
	wliMacFrameTooLongs
		Counter,
	wliMacFrameTooShorts
		Counter,
	wliMacDeferLimits
		Counter
   }

wliMacIndex OBJECT-TYPE
	SYNTAX  INTEGER
	ACCESS  read-only
	STATUS  mandatory
	DESCRIPTION
		"An index value that uniquely identifies a WaveLAN
		network interface this MAC information applies to.
		The interface associated with a particular
		value of this index is the same interface
		as identified by the same value of ifIndex."
	::= { wliMacEntry 1 }

wliMacAddressSelect OBJECT-TYPE
	SYNTAX  INTEGER  {
			universal(1),
			local(2)
		}
	ACCESS  read-only
	STATUS  mandatory
	DESCRIPTION
		"MAC Address type select."
	::= { wliMacEntry 2 }

wliMacCaDefers OBJECT-TYPE
	SYNTAX  Counter
	ACCESS  read-only
	STATUS  mandatory
	DESCRIPTION
		"CSMA/CA Defer counter."
	::= { wliMacEntry 3 }

wliMacDeferredTransmissions OBJECT-TYPE
	SYNTAX  Counter
	ACCESS  read-only
	STATUS  mandatory
	DESCRIPTION
		"A counter for the number of frames
		for which the transmission attempt is
		delayed because the medium is busy.
		(same as dot3StatsDeferredTransmissions)"
	::= { wliMacEntry 4 }

wliMacFCSErrors OBJECT-TYPE
	SYNTAX  Counter
	ACCESS  read-only
	STATUS  mandatory
	DESCRIPTION
		"A counter for the number of frames
		received that do not pass the FCS check
		and/or that are not an integral number of
		octets in length.
		WaveLAN hardware does not distinguish
		between FCS errors and Alignment errors.
		(same as dot3StatsFCSErrors +
			dot3StatsAlignmentErrors)"
	::= { wliMacEntry 5 }

wliMacFrameTooLongs OBJECT-TYPE
	SYNTAX  Counter
	ACCESS  read-only
	STATUS  mandatory
	DESCRIPTION
		"A counter for the number of frames
		received that exceed the maximum
		permitted frame size for the medium 
		(1518 bytes).
		(same as dot3StatsFrameTooLongs)"
	::= { wliMacEntry 6 }

wliMacFrameTooShorts OBJECT-TYPE
	SYNTAX  Counter
	ACCESS  read-only
	STATUS  mandatory
	DESCRIPTION
		"A counter for the number of frames
		received that are shorter than the 
		minimum permitted frame size for 
		the medium (64 bytes)"
	::= { wliMacEntry 7 }

wliMacDeferLimits OBJECT-TYPE
	SYNTAX  Counter
	ACCESS  read-only
	STATUS  mandatory
	DESCRIPTION
		"The number of times a frame 
		is not transmitted because the 
		CSMA/CA defer limit is reached "
	::= { wliMacEntry 8 }

-- 
-- WaveLAN Interface Driver information
-- 

wliDriverTable OBJECT-TYPE
	SYNTAX  SEQUENCE OF WliDriverEntry
	ACCESS  not-accessible
	STATUS  mandatory
	DESCRIPTION
		"Driver information for a collection of WaveLAN
		interfaces attached to a particular system."
	::= { wavelanInterface 4 }

wliDriverEntry OBJECT-TYPE
	SYNTAX  WliDriverEntry
	ACCESS  not-accessible
	STATUS  mandatory
	DESCRIPTION
		"Driver information for a particular WaveLAN interface."
	INDEX   { wliDriverIndex }
	::= { wliDriverTable 1 }

WliDriverEntry ::= SEQUENCE {
	wliDriverIndex
		INTEGER,
	wliDriverName
		DisplayString,
	wliDriverVersion
		DisplayString
   }

wliDriverIndex OBJECT-TYPE
	SYNTAX  INTEGER
	ACCESS  read-only
	STATUS  mandatory
	DESCRIPTION
		"An index value that uniquely identifies a WaveLAN
		network interface this driver information applies to.
		The interface associated with a particular
		value of this index is the same interface
		as identified by the same value of ifIndex."
	::= { wliDriverEntry 1 }

wliDriverName OBJECT-TYPE
	SYNTAX  DisplayString  (SIZE  (7))
	ACCESS  read-only
	STATUS  mandatory
	DESCRIPTION
		"The name of the software driver for this
		WaveLAN network interface."
	::= { wliDriverEntry 2 }

wliDriverVersion OBJECT-TYPE
	SYNTAX  DisplayString  (SIZE  (0..8))
	ACCESS  read-only
	STATUS  mandatory
	DESCRIPTION
		"The version number of the software driver.
		A text string as 'mm.nn.pp', where
		mm = major release number
		nn = point release number
		pp = optional patch number"
	::= { wliDriverEntry 3 }

-- 
-- WaveLAN Interface Encryption information
-- 

wliEncTable OBJECT-TYPE
	SYNTAX  SEQUENCE OF WliEncEntry
	ACCESS  not-accessible
	STATUS  mandatory
	DESCRIPTION
		"Encryption status information and control variables for
		a collection of WaveLAN interfaces attached to a
		particular system."
	::= { wavelanInterface 5 }

wliEncEntry OBJECT-TYPE
	SYNTAX  WliEncEntry
	ACCESS  not-accessible
	STATUS  mandatory
	DESCRIPTION
		"Encryption status information and control variables for
		a particular WaveLAN interface."
	INDEX   { wliEncIndex }
	::= { wliEncTable 1 }

WliEncEntry ::= SEQUENCE {
	wliEncIndex
		INTEGER,
	wliEncInstalled
		INTEGER,
	wliEncSelect
		INTEGER,
	wliEncKey
		OCTET STRING  (SIZE  (8))
   }

wliEncIndex OBJECT-TYPE
	SYNTAX  INTEGER
	ACCESS  read-only
	STATUS  mandatory
	DESCRIPTION
		"An index value that uniquely identifies a WaveLAN
		network interface this encryption information applies to.
		The interface associated with a particular
		value of this index is the same interface
		as identified by the same value of ifIndex."
	::= { wliEncEntry 1 }

wliEncInstalled OBJECT-TYPE
	SYNTAX  INTEGER  {
			none(1),
			des(2),
			aes(3)
		}
	ACCESS  read-only
	STATUS  mandatory
	DESCRIPTION
		"Which encryption option is installed."
	::= { wliEncEntry 2 }

wliEncSelect OBJECT-TYPE
	SYNTAX  INTEGER  {
			disabled(1),
			enabled(2)
		}
	ACCESS  read-only
	STATUS  mandatory
	DESCRIPTION
		"Whether encryption is enabled or disabled."
	::= { wliEncEntry 3 }

wliEncKey OBJECT-TYPE
	SYNTAX  OCTET STRING  (SIZE  (8))
	ACCESS  write-only
	STATUS  mandatory
	DESCRIPTION
		"The encryption key."
	::= { wliEncEntry 4 }

-- 
-- WaveLAN Interface Multicast Delay group
-- 
-- Implementation of this group is optional

wliMcastDelayTable OBJECT-TYPE
	SYNTAX  SEQUENCE OF WliMcastDelayEntry
	ACCESS  not-accessible
	STATUS  mandatory
	DESCRIPTION
		"Information about the Multicast Delay
		feature for a collection of WaveLAN
		interfaces attached to a particular system."
	::= { wavelanInterface 6 }

wliMcastDelayEntry OBJECT-TYPE
	SYNTAX  WliMcastDelayEntry
	ACCESS  not-accessible
	STATUS  mandatory
	DESCRIPTION
		"Information about the Multicast Delay
		feature for a particular WaveLAN interface."
	INDEX   { wliMcastDelayIndex }
	::= { wliMcastDelayTable 1 }

WliMcastDelayEntry ::= SEQUENCE {
	wliMcastDelayIndex
		INTEGER,
	wliMcastNumberOfAps
		INTEGER  (0..10),
	wliMcastApSequenceNumber
		INTEGER  (1..10),
	wliMcastRepeatCount
		INTEGER  (0..10)
   }

wliMcastDelayIndex OBJECT-TYPE
	SYNTAX  INTEGER
	ACCESS  read-only
	STATUS  mandatory
	DESCRIPTION
		"An index value that uniquely identifies a WaveLAN
		network interface this Multicast Delay information
		applies to.  The interface associated with a
		particular value of this index is the same interface
		as identified by the same value of wliIndex (and ifIndex)."
	::= { wliMcastDelayEntry 1 }

wliMcastNumberOfAps OBJECT-TYPE
	SYNTAX  INTEGER  (0..10)
	ACCESS  read-write
	STATUS  mandatory
	DESCRIPTION
		"The total number of Access Points in the coverage 
		area. Together with wliMcastApSequenceNumber 
		this is used to determine the delays before 
		and after the transmission of each multicast frame. 
		This results in a transmission slot 
		per Access Point per multicast frame. 
		0 means: no multicast delay specified 
		(use default mechanism)."
	::= { wliMcastDelayEntry 2 }

wliMcastApSequenceNumber OBJECT-TYPE
	SYNTAX  INTEGER  (1..10)
	ACCESS  read-write
	STATUS  mandatory
	DESCRIPTION
		"The sequence number of this Access Point in the 
		coverage area. Together with wliMcastNumberOfAps 
		this is used to determine the delays before 
		and after the transmission of each multicast frame. 
		This results in a transmission slot 
		per Access Point per multicast frame."
	::= { wliMcastDelayEntry 3 }

wliMcastRepeatCount OBJECT-TYPE
	SYNTAX  INTEGER  (0..10)
	ACCESS  read-write
	STATUS  mandatory
	DESCRIPTION
		"The number of times a multicast frame
		transmission is to be repeated."
	::= { wliMcastDelayEntry 4 }


END
