PANDATEL-MODEM-MIB DEFINITIONS ::= BEGIN

 -- This is the basic private mib group section for the
 -- modem boards system by PANDATEL AG.
 -- Any special modems will have their own individual subtrees.
 -- These must be hanged in at the mdmSpecific section (see below).

 -- This mib section will be completed when necessary.

 -- Ver.1.16    Dec.18.2000

        IMPORTS
	TRAP-TYPE FROM RFC-1215
                enterprises, Counter, IpAddress, Gauge, TimeTicks
                        FROM RFC1155-SMI
                DisplayString
                        FROM RFC1213-MIB
                OBJECT-TYPE
                        FROM RFC-1212;

 -- ********************* THE MAIN STRUCTURE ********************

pandatel              OBJECT IDENTIFIER ::= { enterprises 760 }

mibs                  OBJECT IDENTIFIER ::= { pandatel 1 }

products              OBJECT IDENTIFIER ::= { mibs 1 }

wan-products          OBJECT IDENTIFIER ::= { products 2 }

 -- ********************* THE MDM-MGMT SUBTREE *******************

mdm-mgmt               OBJECT IDENTIFIER ::= { wan-products 1 }

 -- for information: the sub sections

 -- mdmGroup               OBJECT IDENTIFIER ::= { mdm-mgmt 1 }

 -- mdmRackTable           OBJECT IDENTIFIER ::= { mdm-mgmt 2 }

 -- mdmModemTable          OBJECT IDENTIFIER ::= { mdm-mgmt 3 }

 -- mdmVerInfoTable        OBJECT IDENTIFIER ::= { mdm-mgmt 4 }

 -- mdmPortTable           OBJECT IDENTIFIER ::= { mdm-mgmt 5 }

 -- mdmPortSignalTable     OBJECT IDENTIFIER ::= { mdm-mgmt 6 }

 -- mdmBERTTable           OBJECT IDENTIFIER ::= { mdm-mgmt 7 }

 -- mdmRemoteAccess        OBJECT IDENTIFIER ::= { mdm-mgmt 9 }

   -- remModemTable          OBJECT IDENTIFIER ::= { mdmRemoteAccess 3 }

   -- remVerInfoTable        OBJECT IDENTIFIER ::= { mdmRemoteAccess 4 }

   -- remPortTable           OBJECT IDENTIFIER ::= { mdmRemoteAccess 5 }

   -- remPortSignalTable     OBJECT IDENTIFIER ::= { mdmRemoteAccess 6 }

 -- mdmSpecifics           OBJECT IDENTIFIER ::= { mdm-mgmt 10 }

 -- mdmMgmtIfGroup         OBJECT IDENTIFIER ::= { mdm-mgmt 20 }

 -- * * * * * * * * *  Basic Info and Config Group  * * * * * * * * * *

mdmGroup               OBJECT IDENTIFIER ::= { mdm-mgmt 1 }

mdmInstalledRacks OBJECT-TYPE
        SYNTAX  INTEGER
        ACCESS  read-only
        STATUS  mandatory
        DESCRIPTION
                "This is the number of currently installed modem racks."
        ::= { mdmGroup 1 }

mdmInstalledModems OBJECT-TYPE
        SYNTAX  INTEGER
        ACCESS  read-only
        STATUS  mandatory
        DESCRIPTION
                "This is the number of currently installed modems"
        ::= { mdmGroup 2 }

mdmLoopModeTraps OBJECT-TYPE
        SYNTAX  INTEGER {
                disable   (2),
                enable    (3)
                }
        ACCESS  read-write
        STATUS  mandatory
        DESCRIPTION
                "This enables or disables traps generated by a Loop Mode
                 status change at any local modem port of one of the
                 installed modems (values: disable, enable)."
        ::= { mdmGroup 3 }

mdmCurrentDate OBJECT-TYPE
        SYNTAX  DisplayString
        ACCESS  read-write
        STATUS  mandatory
        DESCRIPTION
                "This indicate the current date as 'mm/dd/yy'.
                 The date will be used for local management."
        ::= { mdmGroup 13 }

mdmCurrentTime OBJECT-TYPE
        SYNTAX  DisplayString
        ACCESS  read-write
        STATUS  mandatory
        DESCRIPTION
                "This indicate the current time as 'hh:mm:ss'.
                 The time will be used for local management."
        ::= { mdmGroup 14 }

 -- * * * * * * * * * *  Basic Modem Rack Table  * * * * * * * * * * *

mdmRackTable OBJECT-TYPE
        SYNTAX  SEQUENCE OF RackEntry
        ACCESS  not-accessible
        STATUS  mandatory
        DESCRIPTION
                "Table which contains information about the installed racks."
        ::= { mdm-mgmt 2 }

rackEntry OBJECT-TYPE
        SYNTAX  RackEntry
        ACCESS  not-accessible
        STATUS  mandatory
        DESCRIPTION
                "The index of the table."
        INDEX   { rackRack }
        ::= { mdmRackTable 1 }

RackEntry ::= SEQUENCE {
        rackRack
                INTEGER,
        rackType
                INTEGER,
        rackDescription
                DisplayString,
        rackModemSlots
                INTEGER,
        rackModems
                INTEGER,
        rackPowerSupplySlots
                INTEGER,
        rackPowerSupplies
                INTEGER
        }

rackRack OBJECT-TYPE
        SYNTAX  INTEGER
        ACCESS  read-only
        STATUS  mandatory
        DESCRIPTION
                "The index of this particular modem rack in the stack.
                 The index of the rack which contains the agent should
                 have the number 1."
        ::= { rackEntry 1 }

rackType OBJECT-TYPE
        SYNTAX  INTEGER {
                other               (1),
                rack-10s-3hu        (2),
                rack-12s-3hu        (3),
                rack-10s-6hu        (4),
                rack-6s-9s-6hu      (5),
                device-stack-15s    (6),
                rack-8s-4hu         (7),
                rack-10s-2c-6hu     (8),
                hs-rack-10s-3hu     (9),
				rack-8s-2c-6hu     (10), 
				hs-rack-3s-1c-3hu  (11), 
				rack-1s-1c-1hu     (12), 
				rack-3s-1c-1hu     (13) 
        }
        ACCESS  read-only
        STATUS  mandatory
        DESCRIPTION
                "This entry shows the type number of the rack."
        ::= { rackEntry 2 }

rackDescription OBJECT-TYPE
        SYNTAX  DisplayString
        ACCESS  read-only
        STATUS  mandatory
        DESCRIPTION
                "A verbal description of the modem rack."
        ::= { rackEntry 3 }

rackModemSlots OBJECT-TYPE
        SYNTAX  INTEGER
        ACCESS  read-only
        STATUS  mandatory
        DESCRIPTION
                "This entry shows the number of slots for modem cards in
                 the rack."
        ::= { rackEntry 4 }

rackModems OBJECT-TYPE
        SYNTAX  INTEGER
        ACCESS  read-only
        STATUS  mandatory
        DESCRIPTION
                "This entry shows the number of modems currently installed
                 in the rack."
        ::= { rackEntry 5 }

rackPowerSupplySlots OBJECT-TYPE
        SYNTAX  INTEGER {
                unknown     (999)
        }
        ACCESS  read-only
        STATUS  mandatory
        DESCRIPTION
                "This entry shows the number of slots for power supplies in
                 the rack."
        ::= { rackEntry 6 }

rackPowerSupplies OBJECT-TYPE
        SYNTAX  INTEGER {
                unknown     (999)
        }
        ACCESS  read-only
        STATUS  mandatory
        DESCRIPTION
                "This entry shows the number of power supplies currently installed
                 in the rack."
        ::= { rackEntry 7 }

 -- * * * * * * * * * *  Basic Modem Module Table  * * * * * * * * * * *

mdmModemTable OBJECT-TYPE
        SYNTAX  SEQUENCE OF ModemEntry
        ACCESS  not-accessible
        STATUS  mandatory
        DESCRIPTION
                "Table which contains general information about the installed
                 modems."
        ::= { mdm-mgmt 3 }

modemEntry OBJECT-TYPE
        SYNTAX  ModemEntry
        ACCESS  not-accessible
        STATUS  mandatory
        DESCRIPTION
                "The index of the table."
        INDEX   { mdmRack, mdmModem }
        ::= { mdmModemTable 1 }

ModemEntry ::= SEQUENCE {
        mdmRack
                INTEGER,
        mdmModem
                INTEGER,
        mdmDescription
                DisplayString,
        mdmUserName
                DisplayString,
        mdmSelfTest
                INTEGER,
        mdmSelfTestResult
                INTEGER,
        mdmRemoteAccessStatus
                INTEGER,
        mdmInterfacePorts
                INTEGER,
        mdmLinePorts
                INTEGER
        }

mdmRack OBJECT-TYPE
        SYNTAX  INTEGER
        ACCESS  read-only
        STATUS  mandatory
        DESCRIPTION
                "The index of the rack where the modem is installed."
        ::= { modemEntry 1 }

mdmModem OBJECT-TYPE
        SYNTAX  INTEGER
        ACCESS  read-only
        STATUS  mandatory
        DESCRIPTION
                "The index of this particular modem in the rack. The value
                 corresponds with the slot where the modem is inserted."
        ::= { modemEntry 2 }

mdmDescription OBJECT-TYPE
        SYNTAX  DisplayString
        ACCESS  read-only
        STATUS  mandatory
        DESCRIPTION
                "A verbal description of the modem."
        ::= { modemEntry 3 }

mdmUserName OBJECT-TYPE
        SYNTAX  DisplayString
        ACCESS  read-write
        STATUS  mandatory
        DESCRIPTION
                "A verbal description of the modem which can be changed
                 by the manager."
        ::= { modemEntry 4 }

mdmSelfTest OBJECT-TYPE
        SYNTAX  INTEGER {
                start          (1),
                cancel         (2)
        }
        ACCESS  read-write
        STATUS  mandatory
        DESCRIPTION
                "This entry enables the execution of a selftest. Write
                 requests with values other than 'start' or 'cancel' will be
                 rejected. The result will be found in mdmSelfTestResult."
        ::= { modemEntry 5 }

mdmSelfTestResult OBJECT-TYPE
        SYNTAX  INTEGER {
                started        (3),
                running        (4),
                ram-error      (5),
                rom-error      (6),
                eeprom-error   (7),
                line-if-error  (8),
                -- further tests will be added here
                other-error    (97),
                never-started  (98),
                cancelled      (99),
                ok             (100)
        }
        ACCESS  read-only
        STATUS  mandatory
        DESCRIPTION
                "This entry shows the result status of the last
                 modem-dependent self test. After start, the status may
                 change to 'running' before the first error that occured
                 is displayed. If no error was detected the status changes
                 to 'ok'."
        ::= { modemEntry 6 }

mdmRemoteAccessStatus OBJECT-TYPE
        SYNTAX  INTEGER {
                access    (2),
                no-access (3)
        }
        ACCESS  read-only
        STATUS  mandatory
        DESCRIPTION
                "This entry shows the access status to the remote counterpart
                 of the modem. The standard value depends on the device.
                 Some remote modems are always accessible, others are not
                 accessible or can be switched to both modes (see
                 'mdmForcedRemoteAccess' in the specific modem MIB)."
        ::= { modemEntry 7 }

mdmInterfacePorts OBJECT-TYPE
        SYNTAX  INTEGER
        ACCESS  read-only
        STATUS  mandatory
        DESCRIPTION
                "This entry indicates the number of interface ports of the
                 modem. An interface port connects an external device."
        ::= { modemEntry 8 }

mdmLinePorts OBJECT-TYPE
        SYNTAX  INTEGER
        ACCESS  read-only
        STATUS  mandatory
        DESCRIPTION
                "This entry indicates the number of line ports of the modem.
                 A line port connects a remote modem."
        ::= { modemEntry 9 }

 -- * * * * * * * * * *  Modem Version Info Table  * * * * * * * * * * *

-- This table contains version info data about the installed modems.

mdmVerInfoTable OBJECT-TYPE
        SYNTAX  SEQUENCE OF VerInfoEntry
        ACCESS  not-accessible
        STATUS  mandatory
        DESCRIPTION
                "Table which contains information about the installed
                 modems' versions."
        ::= { mdm-mgmt 4 }

verInfoEntry OBJECT-TYPE
        SYNTAX  VerInfoEntry
        ACCESS  not-accessible
        STATUS  mandatory
        DESCRIPTION
                "The index of the table."
        INDEX   { viRack, viModem }
        ::= { mdmVerInfoTable 1 }

VerInfoEntry ::= SEQUENCE {
        viRack
                INTEGER,
        viModem
                INTEGER,
        viType
                INTEGER,
        viFirmwVer
                DisplayString,
        viUnitRel
                DisplayString,
        viArtNo
                DisplayString,
        viFrontVer
                INTEGER,
        viSerialNumber
                DisplayString
        }

viRack OBJECT-TYPE
        SYNTAX  INTEGER
        ACCESS  read-only
        STATUS  mandatory
        DESCRIPTION
                "The index of the rack where the modem is installed."
        ::= { verInfoEntry 1 }

viModem OBJECT-TYPE
        SYNTAX  INTEGER
        ACCESS  read-only
        STATUS  mandatory
        DESCRIPTION
                "The index of this particular modem in the rack.
                 The value corresponds with the slot where the modem is
                 inserted."

        ::= { verInfoEntry 2 }

viType OBJECT-TYPE
        SYNTAX  INTEGER {
                not-present (0),
                other       (1),
                fhfl        (101),
                fhfl-f      (102),
                fhfl-s      (103),
                gm-h        (201),
                gm-f        (202),
                gm-d        (203),
                gm-s        (204),
                gm-s-f      (205),
                gm-d-f      (206), 
                bm-p        (301),
                bm-z        (302),
                gx          (401),
                fobus       (501),
                fx          (502),
                fx-i	    (503),
                fx-ig	    (504),
                os  	    (505),
                fx-g	    (506),
                fx-ih	    (507),
                fme         (601),
                inax        (701),
                emx         (801),
                cmx-ie      (802),
                etc         (901)
                -- further modem families will be added here
        }
        ACCESS  read-only
        STATUS  mandatory
        DESCRIPTION
                "This entry indicates the type of the modem."
        ::= { verInfoEntry 3 }

viFirmwVer OBJECT-TYPE
        SYNTAX  DisplayString
        ACCESS  read-only
        STATUS  mandatory
        DESCRIPTION
                "This entry indicates the firmware revision of the modem."
        ::= { verInfoEntry 4 }

viUnitRel OBJECT-TYPE
        SYNTAX  DisplayString
        ACCESS  read-only
        STATUS  mandatory
        DESCRIPTION
                "This entry indicates the hardware version and revision of
                 the modem."
        ::= { verInfoEntry 5 }

viArtNo OBJECT-TYPE
        SYNTAX  DisplayString
        ACCESS  read-only
        STATUS  mandatory
        DESCRIPTION
                "This entry indicates the article number of the modem."
        ::= { verInfoEntry 6 }

viFrontVer OBJECT-TYPE
        SYNTAX  INTEGER {
                other       (1)
        }
        ACCESS  read-only
        STATUS  mandatory
        DESCRIPTION
                "For factory purposes only."
        ::= { verInfoEntry 7 }

viSerialNumber OBJECT-TYPE
        SYNTAX  DisplayString
        ACCESS  read-only
        STATUS  mandatory
        DESCRIPTION
                "This entry indicates the serial number of the modem."
        ::= { verInfoEntry 8 }

 -- * * * * * * * * * * *  Modem Port Table  * * * * * * * * * * * *

mdmPortTable OBJECT-TYPE
        SYNTAX  SEQUENCE OF PortEntry
        ACCESS  not-accessible
        STATUS  mandatory
        DESCRIPTION
                "Table which contains information about all ports."
        ::= { mdm-mgmt 5 }

portEntry OBJECT-TYPE
        SYNTAX  PortEntry
        ACCESS  not-accessible
        STATUS  mandatory
        DESCRIPTION
                "The index of the table."
        INDEX   { portRack, portModem, portPort }
        ::= { mdmPortTable 1 }

PortEntry ::= SEQUENCE {
        portRack
                INTEGER,
        portModem
                INTEGER,
        portPort
                INTEGER,
        portType
                INTEGER,
        portInterfaceType
                INTEGER,
        portConnector
                INTEGER,
        portLoopMode
                INTEGER
        }

portRack OBJECT-TYPE
        SYNTAX  INTEGER
        ACCESS  read-only
        STATUS  mandatory
        DESCRIPTION
                "The index of the rack where the modem to which this port
                 belongs is installed."
        ::= { portEntry 1 }

portModem OBJECT-TYPE
        SYNTAX  INTEGER
        ACCESS  read-only
        STATUS  mandatory
        DESCRIPTION
                "The index of the modem to which this port belongs."
        ::= { portEntry 2 }

portPort OBJECT-TYPE
        SYNTAX  INTEGER
        ACCESS  read-only
        STATUS  mandatory
        DESCRIPTION
                "The index of the port."
        ::= { portEntry 3 }

portType OBJECT-TYPE
        SYNTAX  INTEGER {
                other               (1),
                interface-port      (2),
                line-port           (3),
                vt100-mgmt-port     (4),
                outband-mgmt-port   (5),
                backup-port         (6)
        }
        ACCESS  read-only
        STATUS  mandatory
        DESCRIPTION
                "This entry indicates the type of the port."
        ::= { portEntry 4 }

portInterfaceType OBJECT-TYPE
        SYNTAX  INTEGER {
                other               (1),
                v24                 (2),
                v35                 (3),
                v36                 (4),
                x21                 (5),
                rs485               (6),
                g703-e1t1           (7),
                g703-e2t2           (8),
                g703-64k            (9),
                i430                (10),
                store-loop          (11),
                intercom            (12),
                fo-e1t1             (13),
                s0                  (14),
                hdsl                (15),
                no-module           (17),
                atm-26mb            (18),
                g703-e3             (19),
                g703-t3             (20),
                sts-1               (21),
                hssi                (22),
                bm                  (34),
                g703-t1             (39),
                g703-t2             (40),
                eth-bridge          (48),
                g703-e1             (55),
                g703-e2             (56),
                sts-3               (66),	
                stm-1               (67), 
                sm-fiber-820nm      (130),
                sm-fiber-1300nm     (131),
                sm-fiber-1550nm     (132),
                mm-fiber-820nm      (133),
                mm-fiber-1300nm     (134),
                mm-fiber-1550nm     (135),
                sm-fiber-1530-33nm  (136),
                sm-fiber-1531-12nm  (137),
                sm-fiber-1531-90nm  (138),
                sm-fiber-1532-68nm  (139),
                sm-fiber-1533-47nm  (140),
                sm-fiber-1534-25nm  (141),
                sm-fiber-1535-04nm  (142),
                sm-fiber-1535-82nm  (143),
                sm-fiber-1536-61nm  (144),
                sm-fiber-1537-40nm  (145),
                sm-fiber-1538-19nm  (146),
                sm-fiber-1538-98nm  (147),
                sm-fiber-1539-77nm  (148),
                sm-fiber-1540-56nm  (149),
                sm-fiber-1541-35nm  (150),
                sm-fiber-1542-14nm  (151),
                sm-fiber-1542-94nm  (152),
                sm-fiber-1543-73nm  (153),
                sm-fiber-1544-53nm  (154),
                sm-fiber-1545-32nm  (155),
                sm-fiber-1546-12nm  (156),
                sm-fiber-1546-92nm  (157),
                sm-fiber-1547-72nm  (158),
                sm-fiber-1548-51nm  (159),
                sm-fiber-1549-32nm  (160),
                sm-fiber-1550-12nm  (161),
                sm-fiber-1550-92nm  (162),
                sm-fiber-1551-72nm  (163),
                sm-fiber-1552-52nm  (164),
                sm-fiber-1553-33nm  (165),
                sm-fiber-1554-13nm  (166),
                sm-fiber-1554-94nm  (167),
                sm-fiber-1555-75nm  (168),
                sm-fiber-1556-55nm  (169),
                sm-fiber-1557-36nm  (170),
                sm-fiber-1558-17nm  (171),
                sm-fiber-1558-98nm  (172),
                sm-fiber-1559-79nm  (173),
                sm-fiber-1560-61nm  (174),
                sm-fiber-1561-42nm  (175),
                sm-fiber-1562-23nm  (176),
                sm-fiber-1563-05nm  (177),
                sm-fiber-1563-86nm  (178),
                sm-fiber-1564-68nm  (179),
                sm-fiber-1565-50nm  (180),
                sm-1300-1550nm      (181),
                sm-1550-1300nm      (182),
                mm-820-1300nm       (183),
                mm-1300-820nm       (184),
                sm-fiber-1480nm     (185),
                sm-fiber-1510nm     (186),
                sm-fiber-1538nm     (187),
				sm-fiber-1553nm     (188),
                sm-mm-fiber-1310nm  (189),
				-- add further types here
                missing             (999)
        }
        ACCESS  read-only
        STATUS  mandatory
        DESCRIPTION
                "This entry indicates the type of interface of the port."
        ::= { portEntry 5 }

portConnector OBJECT-TYPE
        SYNTAX  INTEGER {
                other            (1),     -- other
                single-fiber     (2),     -- fiber optic single
                dual-fiber       (3),     -- fiber optic pair
                bnc              (4),     -- BNC
                dpc              (5),     -- DPC
                rj45             (7),     -- twisted pair
                ics              (8),     -- IBM type 1
                mic              (9),     -- FDDI
                db-9-f          (10),     -- sub-d 9 female
                db-9-m          (11),     -- sub-d 9 male
                db-15-f         (12),     -- sub-d 15 female
                db-15-m         (13),     -- sub-d 15 male
                db-25-f         (14),     -- sub-d 25 female
                db-25-m         (15),     -- sub-d 25 male
                db-37-f         (16),     -- sub-d 37 female
                db-37-m         (17),     -- sub-d 37 male
                winch-f         (18),     -- winchester female
                winch-m         (19),     -- winchester male
                mini-c          (20),     -- 8pin mini C
                minimicro       (21),     --
                escon           (22),     -- ESCON fiber pair
                e2000           (23),     -- E2000 fiber connector
                single-sc       (24),
                single-fc       (25),
                single-st       (26),
                dual-sc         (27),
                dual-fc         (28),
                dual-st         (29),
                single-sc-apc   (30),
                single-fc-apc   (31),
                dual-sc-apc     (32),
                dual-fc-apc     (33),
                single-lc       (34),
                single-lc-apc   (35),
                dual-lc         (36),
                dual-lc-apc     (37),
                mt-rj           (38),
                single-sc-45    (39),
                dual-sc-45      (40),
                -- add further port connector types here
                unknown        (997),     -- type cannot be decided
                virtual        (998),     -- virtual, for further use
                not-installed  (999)      -- currently not installed
        }
        ACCESS  read-only
        STATUS  mandatory
        DESCRIPTION
                "This entry indicates the connector type of the port."
        ::= { portEntry 6 }

portLoopMode OBJECT-TYPE
        SYNTAX  INTEGER {
                other        (1),
                remote       (2),
                digital      (3),
                line         (4),
                off         (99)
        }
        ACCESS  read-write
        STATUS  mandatory
        DESCRIPTION
                "This entry indicates the loop mode of the port."
        ::= { portEntry 7 }

 -- * * * * * * * *  Modem Port Signal Status Table  * * * * * * * * *

mdmPortSignalTable OBJECT-TYPE
        SYNTAX  SEQUENCE OF PortSignalEntry
        ACCESS  not-accessible
        STATUS  mandatory
        DESCRIPTION
                "Table which contains information about all port status
                 signals."
        ::= { mdm-mgmt 6 }

portSignalEntry OBJECT-TYPE
        SYNTAX  PortSignalEntry
        ACCESS  not-accessible
        STATUS  mandatory
        DESCRIPTION
                "The index of the table."
        INDEX   { psignalRack, psignalModem, psignalPort, psignalType }
        ::= { mdmPortSignalTable 1 }

PortSignalEntry ::= SEQUENCE {
        psignalRack
                INTEGER,
        psignalModem
                INTEGER,
        psignalPort
                INTEGER,
        psignalType
                INTEGER,
        psignalStatus
                INTEGER,
        psignalTrap
                INTEGER
        }

psignalRack OBJECT-TYPE
        SYNTAX  INTEGER
        ACCESS  read-only
        STATUS  mandatory
        DESCRIPTION
                "The index of the rack where the modem is installed
                 to which the port belongs that provides the signal."
        ::= { portSignalEntry 1 }

psignalModem OBJECT-TYPE
        SYNTAX  INTEGER
        ACCESS  read-only
        STATUS  mandatory
        DESCRIPTION
                "The index of the modem to which the port belongs that
                 provides the signal."
        ::= { portSignalEntry 2 }

psignalPort OBJECT-TYPE
        SYNTAX  INTEGER
        ACCESS  read-only
        STATUS  mandatory
        DESCRIPTION
                "The index of the port that provides the signal."
        ::= { portSignalEntry 3 }

psignalType OBJECT-TYPE
        SYNTAX  INTEGER {
                other           (1),
                link            (2),
                rts             (3),
                dcd             (4),
                dtr             (5),
                dsr             (6),
                c               (7),
                i               (8),
                fsync           (9),
                ais             (10),
                lay1            (11),
                bond            (12),
                laser-status    (13),
                ta              (14),
                ca              (15),
                eclk            (16),
                laser-tx        (17),
                laser-temp      (18),
                cr              (20),
                rd              (26),
                td              (27)
        }
        ACCESS  read-only
        STATUS  mandatory
        DESCRIPTION
                "This entry indicates the signal type."
        ::= { portSignalEntry 4 }

psignalStatus OBJECT-TYPE
        SYNTAX  INTEGER {
                other   (1),
                up      (2),
                down    (3),
                on      (4),
                off     (5),
                yes     (6),
                no      (7),
                ok      (8),
                fail    (9),
                active  (10),
                traffic (11),
                space   (12),
                mark    (13),
                high    (14),
                low     (15),
                sync    (16)
        }
        ACCESS  read-only
        STATUS  mandatory
        DESCRIPTION
                "This entry indicates the current status of the signal."
        ::= { portSignalEntry 5 }

psignalTrap OBJECT-TYPE
        SYNTAX  INTEGER {
                other   (1),
                disable (2),
                enable  (3)
        }
        ACCESS  read-write
        STATUS  mandatory
        DESCRIPTION
                "This enables or disables traps. If Trap is enabled each
                 transition of the signal status may cause a trap
                 portSignalStatusGood/portSignalStatusBad."
        ::= { portSignalEntry 6 }

 -- * * * * * * * * *  Bit Error Rate Test Table  * * * * * * * * * * *

mdmBERTTable OBJECT-TYPE
        SYNTAX  SEQUENCE OF BERTEntry
        ACCESS  not-accessible
        STATUS  mandatory
        DESCRIPTION
                "Table which contains information about all performable
                 bit error rate tests."
        ::= { mdm-mgmt 7 }

bertEntry OBJECT-TYPE
        SYNTAX  BERTEntry
        ACCESS  not-accessible
        STATUS  mandatory
        DESCRIPTION
                "The index of thetable."
        INDEX   { bertRack, bertModem }
        ::= { mdmBERTTable 1 }

BERTEntry ::= SEQUENCE {
        bertRack
                INTEGER,
        bertModem
                INTEGER,
        bertPort
                INTEGER,
        bertBERTest
                INTEGER,
        bertStatus
                INTEGER,
        bertRunTime
                Counter,
        bertInErrorTime
                Counter,
        bertErrorFreeTime
                Counter,
        bertKbitsRecWrapped
                Counter,
        bertKbitsReceived
                Counter,
        bertErrors
                Counter,
        bertSyncLosts
                Counter,
        bertSyncStatus
                INTEGER,
        bertBitErrorRate
                DisplayString
        }

bertRack OBJECT-TYPE
        SYNTAX  INTEGER
        ACCESS  read-only
        STATUS  mandatory
        DESCRIPTION
                "The index of the rack where the modem is installed."
        ::= { bertEntry 1 }

bertModem OBJECT-TYPE
        SYNTAX  INTEGER
        ACCESS  read-only
        STATUS  mandatory
        DESCRIPTION
                "The index of this particular modem in the rack. The value
                 corresponds with the slot where the modem is inserted."
        ::= { bertEntry 2 }

bertPort OBJECT-TYPE
        SYNTAX  INTEGER
        ACCESS  read-write
        STATUS  mandatory
        DESCRIPTION
                "The index of the port where the BER test will be performed.
                 The modem can only perform one test at a time. The test can
                 only be performed on a subset of ports, usually the line
                 ports. Write requests with different port numbers will be
                 rejected. Write requests with valid line port numbers will
                 be rejected while the BER test is running."
        ::= { bertEntry 3 }

bertBERTest OBJECT-TYPE
        SYNTAX  INTEGER {
                start           (3),
                stop            (5)
        }
        ACCESS  read-write
        STATUS  mandatory
        DESCRIPTION
                "This entry enables the execution of a BER test. Write
                requests with values other than 'start' or 'stop' will be
                rejected."
        ::= { bertEntry 4 }

bertStatus OBJECT-TYPE
        SYNTAX  INTEGER {
                other           (1),
                never-started   (2),
                start           (3),
                running         (4),
                stopped         (6),
                start-failed    (7)
        }
        ACCESS  read-only
        STATUS  mandatory
        DESCRIPTION
                "This entry indicates the status of the BER test."
        ::= { bertEntry 5 }

bertRunTime OBJECT-TYPE
        SYNTAX  Counter
        ACCESS  read-only
        STATUS  mandatory
        DESCRIPTION
                "This entry indicates the duration of the BER test in seconds."
        ::= { bertEntry 6 }

bertInErrorTime OBJECT-TYPE
        SYNTAX  Counter
        ACCESS  read-only
        STATUS  mandatory
        DESCRIPTION
                "This entry shows the duration of erroneous test transmission
                 in seconds."
        ::= { bertEntry 7 }

bertErrorFreeTime OBJECT-TYPE
        SYNTAX  Counter
        ACCESS  read-only
        STATUS  mandatory
        DESCRIPTION
                "This entry shows the duration of error-free test
                 transmission in seconds."
        ::= { bertEntry 8 }

bertKbitsRecWrapped OBJECT-TYPE
        SYNTAX  Counter
        ACCESS  read-only
        STATUS  mandatory
        DESCRIPTION
                "This is the number the bertKbitsReceived counter
                 has wrapped."
        ::= { bertEntry 9 }

bertKbitsReceived OBJECT-TYPE
        SYNTAX  Counter
        ACCESS  read-only
        STATUS  mandatory
        DESCRIPTION
                "This entry indicates the number of Kbits received during
                 the test. When the counter wraps the bertKbitRecWrapped
                 increases by one."
        ::= { bertEntry 10 }

bertErrors OBJECT-TYPE
        SYNTAX  Counter
        ACCESS  read-only
        STATUS  mandatory
        DESCRIPTION
                "This entry indicates the number of errors detected during
                 the test."
        ::= { bertEntry 11 }

bertSyncLosts OBJECT-TYPE
        SYNTAX  Counter
        ACCESS  read-only
        STATUS  mandatory
        DESCRIPTION
                "This entry indicates the number of pattern sync losts
                 detected during the test."
        ::= { bertEntry 12 }

bertSyncStatus OBJECT-TYPE
        SYNTAX  INTEGER {
                other   (1),
                in-sync (2),
                no-sync (3)
        }
        ACCESS  read-only
        STATUS  mandatory
        DESCRIPTION
                "This entry indicates the current pattern sync status."
        ::= { bertEntry 13 }

bertBitErrorRate OBJECT-TYPE
        SYNTAX  DisplayString
        ACCESS  read-only
        STATUS  mandatory
        DESCRIPTION
                "This entry indicates the bit error rate. It is provided as
                 a string in the format 'd.ddE+/-dd'. Float scanf routines
                 are capable of interpreting the string in the correct
                 manner."
        ::= { bertEntry 14 }

 -- * * * * * * * * * * *  Remote Modem Access Group  * * * * * * * * * * * *

mdmRemoteAccess         OBJECT IDENTIFIER ::= { mdm-mgmt 9 }

-- Group of tables which contain information about the remote modems.

 -- * * * * * * * * * *  Remote Modem Module Table  * * * * * * * * * * *

remModemTable OBJECT-TYPE
        SYNTAX  SEQUENCE OF RemModemEntry
        ACCESS  not-accessible
        STATUS  mandatory
        DESCRIPTION
                "Table which contains general information about all
                 counterparts of the installed modems."
        ::= { mdmRemoteAccess 3 }

rmodemEntry OBJECT-TYPE
        SYNTAX  RemModemEntry
        ACCESS  not-accessible
        STATUS  mandatory
        DESCRIPTION
                "The index of the table."
        INDEX   { rmdmRack, rmdmModem }
        ::= { remModemTable 1 }

RemModemEntry ::= SEQUENCE {
        rmdmRack
                INTEGER,
        rmdmModem
                INTEGER,
        rmdmDescription
                DisplayString,
        rmdmUserName
                DisplayString,
        rmdmSelfTest
                INTEGER,
        rmdmSelfTestResult
                INTEGER,
        rmdmRemoteAccessStatus
                INTEGER,
        rmdmInterfacePorts
                INTEGER,
        rmdmLinePorts
                INTEGER
        }

rmdmRack OBJECT-TYPE
        SYNTAX  INTEGER
        ACCESS  read-only
        STATUS  mandatory
        DESCRIPTION
                "This entry indicates the index of the rack where the modem
                 is installed that the remote modem is linked to."
        ::= { rmodemEntry 1 }

rmdmModem OBJECT-TYPE
        SYNTAX  INTEGER
        ACCESS  read-only
        STATUS  mandatory
        DESCRIPTION
                "The index of the modem that the remote modem is linked to."
        ::= { rmodemEntry 2 }

rmdmDescription OBJECT-TYPE
        SYNTAX  DisplayString
        ACCESS  read-only
        STATUS  mandatory
        DESCRIPTION
                "A verbal description of the remote modem."
        ::= { rmodemEntry 3 }

rmdmUserName OBJECT-TYPE
        SYNTAX  DisplayString
        ACCESS  read-write
        STATUS  mandatory
        DESCRIPTION
                "A verbal description of the remote modem which can be
                 changed by the manager."
        ::= { rmodemEntry 4 }

rmdmSelfTest OBJECT-TYPE
        SYNTAX  INTEGER {
                start          (1),
                cancel         (2)
        }
        ACCESS  read-write
        STATUS  mandatory
        DESCRIPTION
                "This entry enables the execution of a selftest. Write
                 requests with values other than 'start' or 'cancel' will be
                 rejected. The result will be found in SelfTestResult."
        ::= { rmodemEntry 5 }

rmdmSelfTestResult OBJECT-TYPE
        SYNTAX  INTEGER {
                started        (3),
                running        (4),
                ram-error      (5),
                rom-error      (6),
                eeprom-error   (7),
                line-if-error  (8),
                -- further tests will be added here
                other-error    (97),
                never-started  (98),
                cancelled      (99),
                ok             (100)
        }
        ACCESS  read-only
        STATUS  mandatory
        DESCRIPTION
                "This indicates the result status of the last modem-dependent
                 self test. After start, the status may change to 'running'
                 before the first error that occured displays. If no error was
                 detected the status changes to 'ok'."
        ::= { rmodemEntry 6 }

rmdmRemoteAccessStatus OBJECT-TYPE
        SYNTAX  INTEGER {
                access    (2),
                no-access (3)
        }
        ACCESS  read-only
        STATUS  mandatory
        DESCRIPTION
                "This entry shows the access status of the modem. The
                 standard value depends on the device. Some modems are always
                 accessible, others are not accessible or can be switched to
                 both modes (see 'mdmForcedRemoteAccess' in the specific
                 modem MIB)."
        ::= { rmodemEntry 7 }

rmdmInterfacePorts OBJECT-TYPE
        SYNTAX  INTEGER
        ACCESS  read-only
        STATUS  mandatory
        DESCRIPTION
                "This entry indicates the number of interface ports of the
                 remote modem. An interface port connects an external device."
        ::= { rmodemEntry 8 }

rmdmLinePorts OBJECT-TYPE
        SYNTAX  INTEGER
        ACCESS  read-only
        STATUS  mandatory
        DESCRIPTION
                "This entry indicates the number of line ports of the modem.
                 A line port connects the local counterpart of the remote modem."
        ::= { rmodemEntry 9 }

 -- * * * * * * * * *  Remote Modem Version Info Table  * * * * * * * * *

remVerInfoTable OBJECT-TYPE
        SYNTAX  SEQUENCE OF RemVerInfoEntry
        ACCESS  not-accessible
        STATUS  mandatory
        DESCRIPTION
                "Table which contains information about the remote modems'
                 versions."
        ::= { mdmRemoteAccess 4 }

remVerInfoEntry OBJECT-TYPE
        SYNTAX  RemVerInfoEntry
        ACCESS  not-accessible
        STATUS  mandatory
        DESCRIPTION
                "The index of the table."
        INDEX   { rviRack, rviModem }
        ::= { remVerInfoTable 1 }

RemVerInfoEntry ::= SEQUENCE {
        rviRack
                INTEGER,
        rviModem
                INTEGER,
        rviType
                INTEGER,
        rviFirmwVer
                DisplayString,
        rviUnitRel
                DisplayString,
        rviArtNo
                DisplayString,
        rviFrontVer
                INTEGER,
        rviSerialNumber
                DisplayString
        }

rviRack OBJECT-TYPE
        SYNTAX  INTEGER
        ACCESS  read-only
        STATUS  mandatory
        DESCRIPTION
                "The index of the rack where the modem is installed that the
                 remote modem is linked to."
        ::= { remVerInfoEntry 1 }

rviModem OBJECT-TYPE
        SYNTAX  INTEGER
        ACCESS  read-only
        STATUS  mandatory
        DESCRIPTION
                "The index of the modem that the remote modem is linked to."
        ::= { remVerInfoEntry 2 }

rviType OBJECT-TYPE
        SYNTAX  INTEGER {
                not-present (0),
                other       (1),
                fhfl        (101),
                fhfl-f      (102),
                fhfl-s	    (103),	
                gm-h        (201),
                gm-f        (202),
                gm-d        (203),
                gm-s        (204),
                gm-s-f      (205),
                gm-d-f      (206),
                bm-p        (301),
                bm-z        (302),
                gx          (401),
                fobus       (501),
                fx          (502),
                fx-i        (503),	
 	            fx-ig       (504),	
 	            fx-g        (506),	
 	            fx-ih       (507),	
                fme         (601),
                inax        (701),
                emx         (801),         
                cmx-ie      (802),         
                etc         (901)         
                -- further modem families will be added here
        }
        ACCESS  read-only
        STATUS  mandatory
        DESCRIPTION
                "This entry indicates the type of the remote modem."
        ::= { remVerInfoEntry 3 }

rviFirmwVer OBJECT-TYPE
        SYNTAX  DisplayString
        ACCESS  read-only
        STATUS  mandatory
        DESCRIPTION
                "This entry indicates the firmware revision of the remote
                 modem."
        ::= { remVerInfoEntry 4 }

rviUnitRel OBJECT-TYPE
        SYNTAX  DisplayString
        ACCESS  read-only
        STATUS  mandatory
        DESCRIPTION
                "This entry indicates the hardware version and revision of
                 the remote modem."
        ::= { remVerInfoEntry 5 }

rviArtNo OBJECT-TYPE
        SYNTAX  DisplayString
        ACCESS  read-only
        STATUS  mandatory
        DESCRIPTION
                "This entry indicates the article number of the remote modem."
        ::= { remVerInfoEntry 6 }

rviFrontVer OBJECT-TYPE
        SYNTAX  INTEGER {
                other       (1)
        }
        ACCESS  read-only
        STATUS  mandatory
        DESCRIPTION
                "For factory purposes only."
        ::= { remVerInfoEntry 7 }

rviSerialNumber OBJECT-TYPE
        SYNTAX  DisplayString
        ACCESS  read-only
        STATUS  mandatory
        DESCRIPTION
                "This entry indicates the serial number of the remote modem."
        ::= { remVerInfoEntry 8 }

 -- * * * * * * * * * *  Remote Modem Port Table  * * * * * * * * * * *

remPortTable OBJECT-TYPE
        SYNTAX  SEQUENCE OF RemPortEntry
        ACCESS  not-accessible
        STATUS  mandatory
        DESCRIPTION
                "Table which contains information about all ports of the
                 remote modem."
        ::= { mdmRemoteAccess 5 }

remPortEntry OBJECT-TYPE
        SYNTAX  RemPortEntry
        ACCESS  not-accessible
        STATUS  mandatory
        DESCRIPTION
                "The index of the table."
        INDEX   { rportRack, rportModem, rportPort }
        ::= { remPortTable 1 }

RemPortEntry ::= SEQUENCE {
        rportRack
                INTEGER,
        rportModem
                INTEGER,
        rportPort
                INTEGER,
        rportType
                INTEGER,
        rportInterfaceType
                INTEGER,
        rportConnector
                INTEGER,
        rportLoopMode
                INTEGER
        }

rportRack OBJECT-TYPE
        SYNTAX  INTEGER
        ACCESS  read-only
        STATUS  mandatory
        DESCRIPTION
                "The index of the rack where the local counterpart of the
                 remote modem is installed to which this port belongs."
        ::= { remPortEntry 1 }

rportModem OBJECT-TYPE
        SYNTAX  INTEGER
        ACCESS  read-only
        STATUS  mandatory
        DESCRIPTION
                "The index of the local counterpart of the remote modem to
                 which this port belongs."
        ::= { remPortEntry 2 }

rportPort OBJECT-TYPE
        SYNTAX  INTEGER
        ACCESS  read-only
        STATUS  mandatory
        DESCRIPTION
                "The index of the port."
        ::= { remPortEntry 3 }

rportType OBJECT-TYPE
        SYNTAX  INTEGER {
                other               (1),
                interface-port      (2),
                line-port           (3),
                vt100-mgmt-port     (4),
                outband-mgmt-port   (5),
                backup-port         (6)
        }
        ACCESS  read-only
        STATUS  mandatory
        DESCRIPTION
                "This entry indicates the type of the port."
        ::= { remPortEntry 4 }

rportInterfaceType OBJECT-TYPE
        SYNTAX  INTEGER {
                other               (1),
                v24                 (2),
                v35                 (3),
                v36                 (4),
                x21                 (5),
                rs485               (6),
                g703-e1t1           (7),
                g703-e2t2           (8),
                g703-64k            (9),
                i430                (10),
                store-loop          (11),
                intercom            (12),
                fo-e1t1             (13),
                s0                  (14),
                hdsl                (15),
                no-module           (17),
                atm-26mb            (18),
                g703-e3             (19),
                g703-t3             (20),
                sts-1               (21),
                hssi                (22),
                bm                  (34),
                g703-t1             (39),
                g703-t2             (40),
                eth-bridge          (48),
                g703-e1             (55),
                g703-e2             (56),
                sts-3		        (66),	
                stm-1		        (67), 
                sm-fiber-820nm      (130),
                sm-fiber-1300nm     (131),
                sm-fiber-1550nm     (132),
                mm-fiber-820nm      (133),
                mm-fiber-1300nm     (134),
                mm-fiber-1550nm     (135),
                sm-fiber-1530-33nm  (136),
                sm-fiber-1531-12nm  (137),
                sm-fiber-1531-90nm  (138),
                sm-fiber-1532-68nm  (139),
                sm-fiber-1533-47nm  (140),
                sm-fiber-1534-25nm  (141),
                sm-fiber-1535-04nm  (142),
                sm-fiber-1535-82nm  (143),
                sm-fiber-1536-61nm  (144),
                sm-fiber-1537-40nm  (145),
                sm-fiber-1538-19nm  (146),
                sm-fiber-1538-98nm  (147),
                sm-fiber-1539-77nm  (148),
                sm-fiber-1540-56nm  (149),
                sm-fiber-1541-35nm  (150),
                sm-fiber-1542-14nm  (151),
                sm-fiber-1542-94nm  (152),
                sm-fiber-1543-73nm  (153),
                sm-fiber-1544-53nm  (154),
                sm-fiber-1545-32nm  (155),
                sm-fiber-1546-12nm  (156),
                sm-fiber-1546-92nm  (157),
                sm-fiber-1547-72nm  (158),
                sm-fiber-1548-51nm  (159),
                sm-fiber-1549-32nm  (160),
                sm-fiber-1550-12nm  (161),
                sm-fiber-1550-92nm  (162),
                sm-fiber-1551-72nm  (163),
                sm-fiber-1552-52nm  (164),
                sm-fiber-1553-33nm  (165),
                sm-fiber-1554-13nm  (166),
                sm-fiber-1554-94nm  (167),
                sm-fiber-1555-75nm  (168),
                sm-fiber-1556-55nm  (169),
                sm-fiber-1557-36nm  (170),
                sm-fiber-1558-17nm  (171),
                sm-fiber-1558-98nm  (172),
                sm-fiber-1559-79nm  (173),
                sm-fiber-1560-61nm  (174),
                sm-fiber-1561-42nm  (175),
                sm-fiber-1562-23nm  (176),
                sm-fiber-1563-05nm  (177),
                sm-fiber-1563-86nm  (178),
                sm-fiber-1564-68nm  (179),
                sm-fiber-1565-50nm  (180),
                sm-1300-1550nm      (181),
                sm-1550-1300nm      (182),
                mm-820-1300nm       (183),
                mm-1300-820nm       (184),
                sm-fiber-1480nm     (185),
                sm-fiber-1510nm     (186),
                sm-fiber-1538nm     (187),
                sm-fiber-1553nm     (188),
                sm-mm-fiber-1310nm  (189),
                -- add further types here
                missing             (999)
        }
        ACCESS  read-only
        STATUS  mandatory
        DESCRIPTION
                "This entry indicates the type of interface of the port."
        ::= { remPortEntry 5 }

rportConnector OBJECT-TYPE
        SYNTAX  INTEGER {
                other            (1),     -- other
                single-fiber     (2),     -- fiber optic single
                dual-fiber       (3),     -- fiber optic pair
                bnc              (4),     -- BNC
                dpc              (5),     -- DPC
                rj45             (7),     -- twisted pair
                ics              (8),     -- IBM type 1
                mic              (9),     -- FDDI
                db-9-f          (10),     -- sub-d 9 female
                db-9-m          (11),     -- sub-d 9 male
                db-15-f         (12),     -- sub-d 15 female
                db-15-m         (13),     -- sub-d 15 male
                db-25-f         (14),     -- sub-d 25 female
                db-25-m         (15),     -- sub-d 25 male
                db-37-f         (16),     -- sub-d 37 female
                db-37-m         (17),     -- sub-d 37 male
                winch-f         (18),     -- winchester female
                winch-m         (19),     -- winchester male
                mini-c          (20),     -- 8pin mini C
                minimicro       (21),     --
                escon           (22),     -- ESCON fiber pair
                e2000           (23),     -- E2000 fiber connector
                single-sc       (24),
                single-fc       (25),
                single-st       (26),
                dual-sc         (27),
                dual-fc         (28),
                dual-st         (29),
                single-sc-apc   (30),
                single-fc-apc   (31),
                dual-sc-apc     (32),
                dual-fc-apc     (33),
                single-lc       (34),
                single-lc-apc   (35),
                dual-lc         (36),
                dual-lc-apc     (37),
                mt-rj           (38),
                single-sc-45    (39),
                dual-sc-45      (40),
                -- add further port connector types here
                unknown        (997),     -- type cannot be decided
                virtual        (998),     -- virtual, for further use
                not-installed  (999)      -- currently not installed
        }
        ACCESS  read-only
        STATUS  mandatory
        DESCRIPTION
                "This entry indicates the connector type of the port."
        ::= { remPortEntry 6 }

rportLoopMode OBJECT-TYPE
        SYNTAX  INTEGER {
                other        (1),
                remote       (2),
                digital      (3),
                line         (4),
                off         (99)
        }
        ACCESS  read-write
        STATUS  mandatory
        DESCRIPTION
                "This entry indicates the loop mode of the port (remote,
                 digital, line, off)."
        ::= { remPortEntry 7 }

 -- * * * * * *  Remote Modem Port Signal Status Table  * * * * * * *

remPortSignalTable OBJECT-TYPE
        SYNTAX  SEQUENCE OF RemPortSignalEntry
        ACCESS  not-accessible
        STATUS  mandatory
        DESCRIPTION
                "Table which contains information about all port status
                 signals."
        ::= { mdmRemoteAccess 6 }

remPortSignalEntry OBJECT-TYPE
        SYNTAX  RemPortSignalEntry
        ACCESS  not-accessible
        STATUS  mandatory
        DESCRIPTION
                "The index of the table."
        INDEX   { rpsignalRack, rpsignalModem, rpsignalPort, rpsignalType }
        ::= { remPortSignalTable 1 }

RemPortSignalEntry ::= SEQUENCE {
        rpsignalRack
                INTEGER,
        rpsignalModem
                INTEGER,
        rpsignalPort
                INTEGER,
        rpsignalType
                INTEGER,
        rpsignalStatus
                INTEGER
        }

rpsignalRack OBJECT-TYPE
        SYNTAX  INTEGER
        ACCESS  read-only
        STATUS  mandatory
        DESCRIPTION
                "The index of the rack where the local counterpart of the
                 remote modem is installed."
        ::= { remPortSignalEntry 1 }

rpsignalModem OBJECT-TYPE
        SYNTAX  INTEGER
        ACCESS  read-only
        STATUS  mandatory
        DESCRIPTION
                "The index of the local counterpart of the remote modem."
        ::= { remPortSignalEntry 2 }

rpsignalPort OBJECT-TYPE
        SYNTAX  INTEGER
        ACCESS  read-only
        STATUS  mandatory
        DESCRIPTION
                "The index of the port at the remote modem that provides the
                 signal."
        ::= { remPortSignalEntry 3 }

rpsignalType OBJECT-TYPE
        SYNTAX  INTEGER {
                other           (1),
                link            (2),
                rts             (3),
                dcd             (4),
                dtr             (5),
                dsr             (6),
                c               (7),
                i               (8),
                fsync           (9),
                ais             (10),
                lay1            (11),
                bond            (12),
                laser-status    (13),
                ta              (14),
                ca              (15),
                eclk            (16),
                laser-tx        (17),
                laser-temp      (18),
                cr              (20),
                rd              (26),
                td              (27)
        }
        ACCESS  read-only
        STATUS  mandatory
        DESCRIPTION
                "This entry indicates the signal type."
        ::= { remPortSignalEntry 4 }

rpsignalStatus OBJECT-TYPE
        SYNTAX  INTEGER {
                other   (1),
                up      (2),
                down    (3),
                on      (4),
                off     (5),
                yes     (6),
                no      (7),
                ok      (8),
                fail    (9),
                active  (10),
                traffic (11),
                space   (12),
                mark    (13),
                high    (14),
                low     (15),
                sync    (16)
        }
        ACCESS  read-only
        STATUS  mandatory
        DESCRIPTION
                "This entry indicates the current status of the signal."
        ::= { remPortSignalEntry 5 }

 -- * * * * * * * *  Further modem specific MIBs  * * * * * * * * * *

mdmSpecifics           OBJECT IDENTIFIER ::= { mdm-mgmt 10 }

-- Group of MIBs which contain information the specific features of an
-- installed unit (see specific modem MIB description).

 -- * * * * * * * * *  SNMP Interface Group  * * * * * * * * * * * * *

mdmMgmtIfGroup       OBJECT IDENTIFIER ::= { mdm-mgmt 20 }

-- Group of variables describing the SNMP interface settings of the agent.

mdmIfType OBJECT-TYPE
        SYNTAX  INTEGER {
                other       (1),
                v24         (2),
                v35         (4),
                x21         (5),
                ethernet    (6),
                missing     (999)
        }
        ACCESS  read-only
        STATUS  mandatory
        DESCRIPTION
                "This variable shows the agent's interface type."
        ::= { mdmMgmtIfGroup 1 }

mdmIfProtocol OBJECT-TYPE
        SYNTAX  INTEGER {
                other       (1),
                slip        (2),
                ppp-async   (3),
                ppp-sync    (4),
                ethernetII  (5)
        }
        ACCESS  read-only
        STATUS  mandatory
        DESCRIPTION
                "This variable shows the agent's protocol type."
        ::= { mdmMgmtIfGroup 2 }

mdmIfDataRate OBJECT-TYPE
        SYNTAX  INTEGER
        ACCESS  read-only
        STATUS  mandatory
        DESCRIPTION
                "This variable shows the agent's data rate in bps."
        ::= { mdmMgmtIfGroup 3 }

mdmIfDialEnable OBJECT-TYPE
        SYNTAX  INTEGER {
                other       (1),
                disable     (2),
                enable      (3)
        }
        ACCESS  read-write
        STATUS  mandatory
        DESCRIPTION
                "This variable enables the initialization of a dial modem in
                 case of alarm. The following variables (5 to 10) are active
                 only if this variable is enabled."
        ::= { mdmMgmtIfGroup 4 }

mdmIfInitString OBJECT-TYPE
        SYNTAX  DisplayString
        ACCESS  read-write
        STATUS  mandatory
        DESCRIPTION
                "This variable defines an init string which is generated in
                 case of alarm to configure an external Hayes compatible
                 modem."
        ::= { mdmMgmtIfGroup 5 }

mdmIfDialString OBJECT-TYPE
        SYNTAX  DisplayString
        ACCESS  read-write
        STATUS  mandatory
        DESCRIPTION
                "This variable defines a modem command which is generated in
                 case of alarm to dial-up a remote NMS station. If the dial
                 string is not defined neither the init string nor the dial
                 string is generated."
        ::= { mdmMgmtIfGroup 6 }

mdmIfSendTTL OBJECT-TYPE
        SYNTAX  INTEGER
        ACCESS  read-write
        STATUS  mandatory
        DESCRIPTION
                "This variable defines the TTL (time to live) in seconds.
                 After that time the generated traps will be deleted from
                 the buffer. If the value is '0' the traps will remain in the
                 buffer."
        ::= { mdmMgmtIfGroup 7 }

mdmIfDialTimeout OBJECT-TYPE
        SYNTAX  INTEGER
        ACCESS  read-write
        STATUS  mandatory
        DESCRIPTION
                "This variable defines a dial timeout for the modem in
                 seconds."
        ::= { mdmMgmtIfGroup 8 }

mdmIfRedialPause OBJECT-TYPE
        SYNTAX  INTEGER
        ACCESS  read-write
        STATUS  mandatory
        DESCRIPTION
                "This variable defines the duration of a redial pause in
                 seconds."
        ::= { mdmMgmtIfGroup 9 }

mdmIfIdlePeriodBeforeDisconnect OBJECT-TYPE
        SYNTAX  INTEGER
        ACCESS  read-write
        STATUS  mandatory
        DESCRIPTION
                "This variable defines the period of time before
                 disconnecting in seconds. If the value is '0' the modem will
                 remain connected."
        ::= { mdmMgmtIfGroup 10 }

 -- * * * * * * * * * * * * * * * * * * * * * * * * * * * * * * * * * 
-- Group of MIBs which contain information the specific features of an
-- installed unit (see specific modem MIB description).

 -- * * * * * * * * * * * * *   TRAPS  * * * * * * * * * * * * * * * *
rackAdded TRAP-TYPE
        ENTERPRISE  mdm-mgmt
        VARIABLES   { rackType }
        DESCRIPTION
                "This trap will be sent when a rack is
                 added to the managed chassis.
                 The rack index of the new rack is sent along with
                 this trap."
        REFERENCE
                "PANDATEL-MODEM-MIB, RackAdded event notification."
        ::= 1

rackRemoved TRAP-TYPE
        ENTERPRISE  mdm-mgmt
        VARIABLES   { rackType }
        DESCRIPTION
                "This trap will be sent when a rack is
                 removed from the managed chassis.
                 The rack index of the removed rack is sent along
                 with this trap."
        REFERENCE
                "PANDATEL-MODEM-MIB, RackRemoved event notification."
        ::= 2

modemAdded TRAP-TYPE
        ENTERPRISE  mdm-mgmt
        VARIABLES   { viType }
        DESCRIPTION
                "This trap will be sent when a modem is added.
                 The rack number and the index of the new modem is sent
                 along with this trap."
        REFERENCE
                "PANDATEL-MODEM-MIB, ModemAdded event notification."
        ::= 3

modemRemoved TRAP-TYPE
        ENTERPRISE  mdm-mgmt
        VARIABLES   { viType }
        DESCRIPTION
                "This trap will be sent when a modem in one
                 of the slots is removed.
                 The rack number and the index of the removed modem is
                 sent along with this trap."
        REFERENCE
                "PANDATEL-MODEM-MIB, ModemRemoved event notification."
        ::= 4

portLoopEnabled TRAP-TYPE
        ENTERPRISE  mdm-mgmt
        VARIABLES   { portLoopMode }
        DESCRIPTION
                "This trap will be sent when a modem in one
                 of the slots enables a Loop.
                 The rack number, index of the modem, and port number
                 is sent along with this trap."
        REFERENCE
                "PANDATEL-MODEM-MIB, PortLoopEnabled event notification."
        ::= 5

portLoopDisabled TRAP-TYPE
        ENTERPRISE  mdm-mgmt
        VARIABLES   { portLoopMode }
        DESCRIPTION
                "This trap will be sent when a modem in one
                 of the slots disables a Loop.
                 The rack number, index of the modem, and port number
                 is sent along with this trap."
        REFERENCE
                "PANDATEL-MODEM-MIB, PortLoopDisabled event notification."
        ::= 6

portSignalStatusGood TRAP-TYPE
        ENTERPRISE  mdm-mgmt
        VARIABLES   { psignalType }
        DESCRIPTION
                "This will be sent when a
                 status signal of a modem port enters the 'good' status.
                 The rack number, index of the modem, and port number
                 is sent along with this trap."
        REFERENCE
                "PANDATEL-MODEM-MIB, PortSignalStatusGood event notification."
        ::= 7

portSignalStatusBad TRAP-TYPE
        ENTERPRISE  mdm-mgmt
        VARIABLES   { psignalType }
        DESCRIPTION
                "This trap will be sent when a
                 status signal of a modem port enters the 'bad' status.
                 The rack number, index of the modem, and port number
                 is sent along with this trap."
        REFERENCE
                "PANDATEL-MODEM-MIB, PortSignalStatusBad event notification."
        ::= 8

portBackupEnabled TRAP-TYPE
        ENTERPRISE  mdm-mgmt
        VARIABLES   { portPort, portPort }
        DESCRIPTION
                "This trap will be sent when a modem in one of the slots
                 enters a backup status. The first port indicates the active
                 data port, the second the inactive port.
                 The rack number, index of the modem, and port number is
                 sent along with this trap."
        REFERENCE
                "PANDATEL-MODEM-MIB, PortBackupEnabled event notification."
        ::= 9

portBackupDisabled TRAP-TYPE
        ENTERPRISE  mdm-mgmt
        VARIABLES   { portPort, portPort }
        DESCRIPTION
                "This trap will be sent when a modem in one of the slots
                 leaves a backup status. The first port indicates the active
                 data port, the second the inactive port.
                 The rack number, index of the modem, and port number is
                 sent along with this trap."
        REFERENCE
                "PANDATEL-MODEM-MIB, PortBackupDisabled event notification."
        ::= 10

portBackupAvailable TRAP-TYPE
        ENTERPRISE  mdm-mgmt
        VARIABLES   { portPort }
        DESCRIPTION
                "This trap will be sent when a second link can be used as backup.
                 The rack number, index of the modem, and port number is
                 sent along with this trap."
        REFERENCE
                "PANDATEL-MODEM-MIB, PortBackupAvailable event notification."
        ::= 11

portBackupNotAvailable TRAP-TYPE
        ENTERPRISE  mdm-mgmt
        VARIABLES   { portPort }
        DESCRIPTION
                "This trap will be sent when there is no second link available as backup.
                 The rack number, index of the modem, and port number is
                 sent along with this trap."
        REFERENCE
                "PANDATEL-MODEM-MIB, PortBackupNotAvailable event notification."
        ::= 12

portDataPortChanged TRAP-TYPE
        ENTERPRISE  mdm-mgmt
        VARIABLES   { portPort, portPort }
        DESCRIPTION
                "This trap will be sent when the line port used for data transmission
                 is changed. The first port indicates the active
                 data port, the second the inactive port.
                 The rack number, index of the modem, and port number is
                 sent along with this trap."
        REFERENCE
                "PANDATEL-MODEM-MIB, DataPortChanged event notification."
        ::= 13

 -- *********************** CHASSIS-MIB OIDS ************************

mdm-oid                 OBJECT IDENTIFIER ::= { mdmSpecifics 10000 }

comp-id                 OBJECT IDENTIFIER ::= { mdm-oid 1}
device-id               OBJECT IDENTIFIER ::= { mdm-oid 2}
slot-id                 OBJECT IDENTIFIER ::= { mdm-oid 3}
port-id                 OBJECT IDENTIFIER ::= { mdm-oid 4}
psupply-id              OBJECT IDENTIFIER ::= { mdm-oid 5}
psonoff-id              OBJECT IDENTIFIER ::= { mdm-oid 6}
fanonoff-id             OBJECT IDENTIFIER ::= { mdm-oid 7}

rack-other              OBJECT IDENTIFIER ::= { comp-id 1 }
rack-10s-3hu            OBJECT IDENTIFIER ::= { comp-id 2 }
rack-12s-3hu            OBJECT IDENTIFIER ::= { comp-id 3 }
rack-10s-6hu            OBJECT IDENTIFIER ::= { comp-id 4 }
rack-6s-9s-6hu          OBJECT IDENTIFIER ::= { comp-id 5 }
device-stack-15s        OBJECT IDENTIFIER ::= { comp-id 6 }
rack-8s-4hu             OBJECT IDENTIFIER ::= { comp-id 7 }
rack-10s-2c-6hu         OBJECT IDENTIFIER ::= { comp-id 8 }
hs-rack-10s-3hu         OBJECT IDENTIFIER ::= { comp-id 9 }
rack-8s-2c-6hu          OBJECT IDENTIFIER ::= { comp-id 10 }
hs-rack-3s-1c-3hu       OBJECT IDENTIFIER ::= { comp-id 11 }
rack-1s-1c-1hu          OBJECT IDENTIFIER ::= { comp-id 12 }
rack-3s-1c-1hu          OBJECT IDENTIFIER ::= { comp-id 13 }

otherModem              OBJECT IDENTIFIER ::= { device-id 1 }
cms-snmp-master         OBJECT IDENTIFIER ::= { device-id 10001 }
cms-slave               OBJECT IDENTIFIER ::= { device-id 10002 }
cms-intelligent-slave   OBJECT IDENTIFIER ::= { device-id 10003 }
rc-control				OBJECT IDENTIFIER ::= { device-id 10004 }

-- All Modem deviceIDs are handled by specialized MIBs.

modemSlot               OBJECT IDENTIFIER ::= { slot-id 1 }
mgmtSlot                OBJECT IDENTIFIER ::= { slot-id 2 }
modemAddr               OBJECT IDENTIFIER ::= { slot-id 3 }
mgmtAddr                OBJECT IDENTIFIER ::= { slot-id 4 }
wdmSlot                 OBJECT IDENTIFIER ::= { slot-id 5 }
controlSlot             OBJECT IDENTIFIER ::= { slot-id 6 }
psupplySlot             OBJECT IDENTIFIER ::= { slot-id 10 }

otherPort               OBJECT IDENTIFIER ::= { port-id 1 }
interfacePort           OBJECT IDENTIFIER ::= { port-id 2 }
linePort                OBJECT IDENTIFIER ::= { port-id 3 }
vt100mgmtPort           OBJECT IDENTIFIER ::= { port-id 4 }
outbandmgmtPort         OBJECT IDENTIFIER ::= { port-id 5 }
backupPort              OBJECT IDENTIFIER ::= { port-id 6 }
rs485Port               OBJECT IDENTIFIER ::= { port-id 7 }

ps-other                OBJECT IDENTIFIER ::= { psupply-id 1 }
p-ac-x-5v-20a           OBJECT IDENTIFIER ::= { psupply-id 2 }
p-ac-x-5v-30a           OBJECT IDENTIFIER ::= { psupply-id 3 }
p-dc-48v-5v-18a         OBJECT IDENTIFIER ::= { psupply-id 4 }
p-dc-24v-5v-15a         OBJECT IDENTIFIER ::= { psupply-id 5 }
p-dc-48v-5v-30a         OBJECT IDENTIFIER ::= { psupply-id 6 }
b-ac-x-5v-6a            OBJECT IDENTIFIER ::= { psupply-id 7 }
b-dc-48v-5v-lc          OBJECT IDENTIFIER ::= { psupply-id 8 }
b-dc-48v-5v-hc          OBJECT IDENTIFIER ::= { psupply-id 9 }
b-dc-24v-5v-su          OBJECT IDENTIFIER ::= { psupply-id 10 }
p-ac-x-3v-20a           OBJECT IDENTIFIER ::= { psupply-id 11 }
p-dc-48v-5v-20a         OBJECT IDENTIFIER ::= { psupply-id 12 }
p-dc-5v-3v-4a           OBJECT IDENTIFIER ::= { psupply-id 13 }
p-dc-5v-5v-5a           OBJECT IDENTIFIER ::= { psupply-id 14 }

pS1-PS2-other		    OBJECT IDENTIFIER ::= { psonoff-id 1 }
pS1-on-PS2-off		    OBJECT IDENTIFIER ::= { psonoff-id 2 } 
pS1-on-PS2-on		    OBJECT IDENTIFIER ::= { psonoff-id 3 } 

fAN1-FAN2-other		    OBJECT IDENTIFIER ::= { fanonoff-id 1 }
fAN1-off-FAN2-off	    OBJECT IDENTIFIER ::= { fanonoff-id 2 } 
fAN1-on-FAN2-off	    OBJECT IDENTIFIER ::= { fanonoff-id 3 } 
fAN1-off-FAN2-on	    OBJECT IDENTIFIER ::= { fanonoff-id 4 } 
fAN1-on-FAN2-on		    OBJECT IDENTIFIER ::= { fanonoff-id 5 } 

END
