Wellfleet-RIP6-MIB DEFINITIONS ::= BEGIN

    IMPORTS
      Counter
        FROM RFC1155-SMI
      OBJECT-TYPE
        FROM RFC-1212
      DisplayString
        FROM RFC1213-MIB
      wfIpv6RoutingGroup, wfIpv6PolicyGroup   
	FROM Wellfleet-IPV6-MIB;

    wfRipv6Group  		OBJECT IDENTIFIER ::= { wfIpv6RoutingGroup 2 }

    wfRipv6IfTable OBJECT-TYPE
        SYNTAX	SEQUENCE OF WfRipv6IfEntry
        ACCESS	not-accessible
        STATUS	mandatory
        DESCRIPTION
                "The list of configured RIPv6 interfaces"
        ::= { wfRipv6Group 1 }

    wfRipv6IfEntry OBJECT-TYPE
        SYNTAX	WfRipv6IfEntry
        ACCESS	not-accessible
        STATUS	mandatory
        DESCRIPTION
                "A description of a RIPv6 interface"
        INDEX	{ wfRipv6IntfIndex }
        ::= { wfRipv6IfTable 1 }

    WfRipv6IfEntry ::= SEQUENCE {
    	    wfRipv6IntfCreate
    		INTEGER,
    	    wfRipv6IntfEnable
    		INTEGER,
    	    wfRipv6IntfState
    		INTEGER,
    	    wfRipv6IntfIndex
    		INTEGER,    		
    	    wfRipv6IntfSupply
    		INTEGER,
    	    wfRipv6IntfListen
    		INTEGER,
    	    wfRipv6IntfDefaultRouteSupply
    		INTEGER,
    	    wfRipv6IntfDefaultRouteListen
    		INTEGER,
    	    wfRipv6IntfPoisonedReversed
    		INTEGER,
    	    wfRipv6IntfBroadcastTimer
    		INTEGER,
    	    wfRipv6IntfTimeoutTimer
    		INTEGER,
    	    wfRipv6IntfHolddownTimer
    		INTEGER,
    	    wfRipv6IntfTriggeredUpdates
    		INTEGER,
    	    wfRipv6IntfDiameter
    		INTEGER
        }

    wfRipv6IntfCreate OBJECT-TYPE
        SYNTAX	INTEGER {
    		    created(1),
    		    deleted(2)
    		}
        ACCESS	read-write
        STATUS	mandatory
        DESCRIPTION
                "Create/Delete parameter. Default is created.
                Users perform a set operation on this
                object in order to create/delete an RIPv6 Interface instance."
        DEFVAL	{ created }
        ::= { wfRipv6IfEntry 1 }

    wfRipv6IntfEnable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable a RIPv6 interface."
        DEFVAL	{ enabled }
        ::= { wfRipv6IfEntry 2 }

    wfRipv6IntfState OBJECT-TYPE
        SYNTAX	INTEGER {
    		    up(1),
    		    down(2)
    		}
        ACCESS	read-only
        STATUS	mandatory
        DESCRIPTION
                "The current state of RIPv6 on this interface."
        DEFVAL	{ down }
        ::= { wfRipv6IfEntry 3 }

    wfRipv6IntfIndex OBJECT-TYPE
        SYNTAX	INTEGER
        ACCESS	read-only
        STATUS	mandatory
        DESCRIPTION
                "The index corresponding to the IPv6 interface with the same 
	         index to run RIPv6 on."
        ::= { wfRipv6IfEntry 4 }

    wfRipv6IntfSupply OBJECT-TYPE
        SYNTAX	INTEGER {
    		    enabled(1),
    		    disabled(2)
    		}
        ACCESS	read-write
        STATUS	mandatory
        DESCRIPTION
                "Transmit RIPv6 packets."
        DEFVAL	{ enabled }
        ::= { wfRipv6IfEntry 5 }

    wfRipv6IntfListen OBJECT-TYPE
        SYNTAX	INTEGER {
    		    enabled(1),
    		    disabled(2)
    		}
        ACCESS	read-write
        STATUS	mandatory
        DESCRIPTION
                "Whether to listen to RIPv6 packets"
        DEFVAL	{ enabled }
        ::= { wfRipv6IfEntry 6 }

    wfRipv6IntfDefaultRouteSupply OBJECT-TYPE
        SYNTAX	INTEGER {
    		    enabled(1),
    		    disabled(2),
    		    generated(3)
    		}
        ACCESS	read-write
        STATUS	mandatory
        DESCRIPTION
                "Transmit the default route, ::0, in RIPv6 packets."
        DEFVAL	{ disabled }
        ::= { wfRipv6IfEntry 7 }

    wfRipv6IntfDefaultRouteListen OBJECT-TYPE
        SYNTAX	INTEGER {
    		    enabled(1),
    		    disabled(2)
    		}
        ACCESS	read-write
        STATUS	mandatory
        DESCRIPTION
                "Receive the default route, ::0, in RIPv6 packets."
        DEFVAL	{ disabled }
        ::= { wfRipv6IfEntry 8 }

    wfRipv6IntfPoisonedReversed OBJECT-TYPE
        SYNTAX	INTEGER {
    		    poisoned(1),
    		    actual(2),
    		    split(3)
    		}
        ACCESS	read-write
        STATUS	mandatory
        DESCRIPTION
                "Specifies how the router advertises routes
                it has learned from a neighboring router in
                periodic updates subsequently sent to the
                neighbor. If 'Poisoned', the node implements
                poisoned reverse. The router now advertises
                routes learned from a neighbor in RIPv6 updates
                subsequently sent to that neighbor with a
                hop count of wfRipv6BaseDiameter
                plus 1, (thus declaring the destination
                unreachable). If 'Split', the router
                implements a split-horizon, and omits routes
                learned from a neighbor in RIPv6 updates
                subsequently sent to that neighbor.  If
                'Actual', the learned cost of the route
                is advertised."
        DEFVAL	{ poisoned }
        ::= { wfRipv6IfEntry 9 }

    wfRipv6IntfBroadcastTimer OBJECT-TYPE
        SYNTAX	INTEGER(0..86400)
        ACCESS	read-write
        STATUS	mandatory
        DESCRIPTION
                "This parameter allows the user to configure the
                frequency of full RIPv6 updates.  The default is
                per the standard.  The minimum is every
                5 seconds, with a maximum of 24 hours."
        DEFVAL	{ 30 }
        ::= { wfRipv6IfEntry 10 }

    wfRipv6IntfTimeoutTimer OBJECT-TYPE
        SYNTAX	INTEGER(15..259200)
        ACCESS	read-write
        STATUS	mandatory
        DESCRIPTION
                "This parameter allows the user to configure the
                time period which RIPv6 will wait before timing out
                a route.  This time is typically 3 x the broadcast
                timer.  The default is 90 seconds with a maximum of 
                72 hours."

        DEFVAL	{ 90 }
        ::= { wfRipv6IfEntry 11 }

    wfRipv6IntfHolddownTimer OBJECT-TYPE
        SYNTAX	INTEGER(15..259200)
        ACCESS	read-write
        STATUS	mandatory
        DESCRIPTION
                "This parameter allows the user to configure the
                time period which unreachable routes will be held in
                the Routing Pool.  This time is typically 3 x the broadcast
                timer.  It allows RIPv6 to advertise the unreachable routes
                to help convergence time." 
        DEFVAL	{ 90 }
        ::= { wfRipv6IfEntry 12 }

    wfRipv6IntfTriggeredUpdates OBJECT-TYPE
        SYNTAX	INTEGER {
    		    enabled(1),
    		    disabled(2)
    		}
        ACCESS	read-write
        STATUS	mandatory
        DESCRIPTION
                "This parameter allows the user to configure triggered
                updates.  By default this parameter is disabled to
                conform with previous release action."
        DEFVAL	{ disabled }
        ::= { wfRipv6IfEntry 13 }


    wfRipv6IntfDiameter OBJECT-TYPE
        SYNTAX  INTEGER(0..15)
        ACCESS  read-write
        STATUS  mandatory
        DESCRIPTION
                "The Diameter of the RIPv6 network from wfRipv6BaseDiameter."
	::= { wfRipv6IfEntry 14 }


    wfRipv6IfStatsTable OBJECT-TYPE
        SYNTAX	SEQUENCE OF WfRipv6IfStatsEntry
        ACCESS	not-accessible
        STATUS	mandatory
        DESCRIPTION
                "RIPv6 interface statistics"
        ::= { wfRipv6Group 2 }

    wfRipv6IfStatsEntry OBJECT-TYPE
        SYNTAX	WfRipv6IfStatsEntry
        ACCESS	not-accessible
        STATUS	mandatory
        DESCRIPTION
                "A RIPv6 interface statistics"
        INDEX	{ wfRipv6IfStatsIntfIndex }
        ::= { wfRipv6IfStatsTable 1 }

    WfRipv6IfStatsEntry ::= SEQUENCE {
    	    wfRipv6IfStatsIntfIndex
    		INTEGER,
    	    wfRipv6IfStatsInMsgs
    		Counter,
    	    wfRipv6IfStatsInRequests
    		Counter,
    	    wfRipv6IfStatsInResponses
    		Counter,
	    wfRipv6IfStatsInBadResponses
		Counter,
	    wfRipv6IfStatsInBadRoutes
		Counter,
    	    wfRipv6IfStatsOutMsgs
    		Counter,
    	    wfRipv6IfStatsOutRequests
    		Counter,
    	    wfRipv6IfStatsOutResponses
    		Counter,
    	    wfRipv6IfStatsOutFullUpdates
    		Counter,
    	    wfRipv6IfStatsOutTriggeredUpdates
    		Counter, 
	    wfRipv6IfStatsOutRoutesAdvertised
		Counter
        }

    wfRipv6IfStatsIntfIndex OBJECT-TYPE
        SYNTAX	INTEGER
        ACCESS	read-only
        STATUS	mandatory
        DESCRIPTION
                "The Interface Index that this interface runs over"
        ::= { wfRipv6IfStatsEntry 1 }

    wfRipv6IfStatsInMsgs OBJECT-TYPE
        SYNTAX	Counter
        ACCESS	read-only
        STATUS	mandatory
        DESCRIPTION
                "The total number of RIPv6 messages received on this
	 	 interface."
        ::= { wfRipv6IfStatsEntry 2 }

    wfRipv6IfStatsInRequests OBJECT-TYPE
        SYNTAX	Counter
        ACCESS	read-only
        STATUS	mandatory
        DESCRIPTION
                "The number of RIPv6 Requests received on this interface."
        ::= { wfRipv6IfStatsEntry 3 }

    wfRipv6IfStatsInResponses OBJECT-TYPE
        SYNTAX	Counter
        ACCESS	read-only
        STATUS	mandatory
        DESCRIPTION
                "The number of RIPv6 Responses received on this interface."
        ::= { wfRipv6IfStatsEntry 4 }

    wfRipv6IfStatsInBadResponses OBJECT-TYPE
        SYNTAX	Counter
        ACCESS	read-only
        STATUS	mandatory
        DESCRIPTION
                "The number of RIPv6 Pkts received on this interface that
	         were discarded."
        ::= { wfRipv6IfStatsEntry 5 }

    wfRipv6IfStatsInBadRoutes OBJECT-TYPE
        SYNTAX	Counter
        ACCESS	read-only
        STATUS	mandatory
        DESCRIPTION
                "The number of RIPv6 RTES received on this interface that 
	         were ignored."
        ::= { wfRipv6IfStatsEntry 6 }

    wfRipv6IfStatsOutMsgs OBJECT-TYPE
        SYNTAX	Counter
        ACCESS	read-only
        STATUS	mandatory
        DESCRIPTION
                "The total number of RIPv6 messages transmitted on this 
		 interface."
        ::= { wfRipv6IfStatsEntry 7 }

    wfRipv6IfStatsOutRequests OBJECT-TYPE
        SYNTAX	Counter
        ACCESS	read-only
        STATUS	mandatory
        DESCRIPTION
                "The number of RIPv6 Requests transmitted out this 
		interface."
        ::= { wfRipv6IfStatsEntry 8 }

    wfRipv6IfStatsOutResponses OBJECT-TYPE
        SYNTAX	Counter
        ACCESS	read-only
        STATUS	mandatory
        DESCRIPTION
                "The number of RIPv6 Responses sent out this interface."
        ::= { wfRipv6IfStatsEntry 9 }

    wfRipv6IfStatsOutFullUpdates OBJECT-TYPE
        SYNTAX	Counter
        ACCESS	read-only
        STATUS	mandatory
        DESCRIPTION
                "The number of RIPv6 Responses sent out this interface
		that contain a full update of the routing table information."
        ::= { wfRipv6IfStatsEntry 10 }

    wfRipv6IfStatsOutTriggeredUpdates OBJECT-TYPE
        SYNTAX	Counter
        ACCESS	read-only
        STATUS	mandatory
        DESCRIPTION
                "The number of RIPv6 Responses sent out this interface
		that contain incremental updates of the routing table 
		information."
        ::= { wfRipv6IfStatsEntry 11 }

    wfRipv6IfStatsOutRoutesAdvertised OBJECT-TYPE
        SYNTAX	Counter
        ACCESS	read-only
        STATUS	mandatory
        DESCRIPTION
                "The number of RIPv6 Routes advertised out this interface."
        ::= { wfRipv6IfStatsEntry 12 }


    wfRip6AcceptTable OBJECT-TYPE
        SYNTAX	SEQUENCE OF WfRip6AcceptEntry
        ACCESS	not-accessible
        STATUS	mandatory
        DESCRIPTION
                "The Table of Rip6 Accept Policy Rules"
        ::= { wfIpv6PolicyGroup 1 }

    wfRip6AcceptEntry OBJECT-TYPE
        SYNTAX	WfRip6AcceptEntry
        ACCESS	not-accessible
        STATUS	mandatory
        DESCRIPTION
                "An entry in the Rip6 Accept Rule Table"
        INDEX	{ wfRip6AcceptIndex }
        ::= { wfRip6AcceptTable 1 }


    WfRip6AcceptEntry ::= SEQUENCE {
    	    wfRip6AcceptDelete
    		INTEGER,
    	    wfRip6AcceptDisable
    		INTEGER,
    	    wfRip6AcceptIndex
    		INTEGER,
    	    wfRip6AcceptName
    		DisplayString,
    	    wfRip6AcceptPrefixes
    		OCTET STRING,
    	    wfRip6AcceptAction
    		INTEGER,
    	    wfRip6AcceptPreference
    		INTEGER,
    	    wfRip6AcceptPrecedence
    		INTEGER,
    	    wfRip6AcceptInject
    		OCTET STRING,
    	    wfRip6AcceptGateway
    		OCTET STRING,
    	    wfRip6AcceptInterface
    		OCTET STRING,
    	    wfRip6AcceptLog
    		INTEGER
        }

    wfRip6AcceptDelete OBJECT-TYPE
        SYNTAX	INTEGER {
    		    created(1),
    		    deleted(2)
    		}
        ACCESS	read-write
        STATUS	mandatory
        DESCRIPTION
                "Create/Delete parameter."
        DEFVAL	{ created }
        ::= { wfRip6AcceptEntry 1 }

    wfRip6AcceptDisable OBJECT-TYPE
        SYNTAX	INTEGER {
    		    enabled(1),
    		    disabled(2)
    		}
        ACCESS	read-write
        STATUS	mandatory
        DESCRIPTION
                "Enable/Disable parameter."
        DEFVAL	{ enabled }
        ::= { wfRip6AcceptEntry 2 }

    wfRip6AcceptIndex OBJECT-TYPE
        SYNTAX	INTEGER
        ACCESS	read-only
        STATUS	mandatory
        DESCRIPTION
                "Rule index number"
        ::= { wfRip6AcceptEntry 3 }

    wfRip6AcceptName OBJECT-TYPE
        SYNTAX	DisplayString
        ACCESS	read-write
        STATUS	mandatory
        DESCRIPTION
                "Rule name - user specified name for this rule"
        ::= { wfRip6AcceptEntry 4 }

    wfRip6AcceptPrefixes OBJECT-TYPE
        SYNTAX	OCTET STRING
        ACCESS	read-write
        STATUS	mandatory
        DESCRIPTION
                "Prefix identification list. This identifies which
                prefixes will match this rule.  If non-null, The octet
                string contains one or more 3-tuples of this form:

                 first octet:  exact (1) or range (2)
                 next 16 octets: prefix
                 next octet: prefix length

                An entry with an 'exact' tag means to only match the
                specific network advertisement (prefix and length).  An
                entry with a 'range' tag means to match any prefix
                that falls in the range indicated by the prefix and length.

                An 'exact' encoding of ::0/128 means 'match the
                default route.  A 'range' encoding of ::0/0 means
                'match any route'.

                A null string also means 'match any route'."
        ::= { wfRip6AcceptEntry 5 }

    wfRip6AcceptAction OBJECT-TYPE
        SYNTAX	INTEGER {
    		    accept(1),
    		    ignore(3)
    		}
        ACCESS	read-write
        STATUS	mandatory
        DESCRIPTION
                "action. 'accept' means that the route should be
                considered for inclusion in the routing table.  'ignore'
                means don't consider the route"
        DEFVAL	{ accept }
        ::= { wfRip6AcceptEntry 6 }

    wfRip6AcceptPreference OBJECT-TYPE
        SYNTAX	INTEGER(0..15)
        ACCESS	read-write
        STATUS	mandatory
        DESCRIPTION
                "preference. This is a metric to be used to compare
                the route to other routes to the same destination.  A
                value of 15 is 'most preferred'.  This parameter only has
                meaning if the action is 'accept'."
        DEFVAL	{ 1 }
        ::= { wfRip6AcceptEntry 7 }

    wfRip6AcceptPrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfRip6AcceptEntry 8 }

    wfRip6AcceptInject OBJECT-TYPE
        SYNTAX	OCTET STRING
        ACCESS	read-write
        STATUS	mandatory
        DESCRIPTION
                "prefix injection list. this octet string should only be
                non-null if the action is 'accept' and if it is desired to
                insert prefixes into the routing table that differ from
                the actual advertised prefixes.  For instance, if a number of
                prefixes in a certain range are learned, an aggregate
                advertisement could be inserted instead of the individual
                prefixes.

                If non-null, The octet string contains one or more 2-tuples
                of this form:

                 first 16 octets: prefix
                 next octet: prefix length

                Upon receiving a route that matches this filter, all prefixes
                in this list will be considered for inclusion in the routing
                table.  If the list is null, the actual received network is
                considered.

                An encoding of ffff:ffff:ffff:ffff:ffff:ffff:ffff:ffff/128 
	        means 'match the actual received prefix.'  This allows 
	        insertion of an aggregate or default along with the actual
	        prefix.

                This will only be used for routes received via RIPv6."
        ::= { wfRip6AcceptEntry 9 }

    wfRip6AcceptGateway OBJECT-TYPE
        SYNTAX	OCTET STRING
        ACCESS	read-write
        STATUS	mandatory
        DESCRIPTION
                "RIPv6 gateway list. This octet string contains the addresses
                of one or more routers that could send RIPv6 updates to this
                router.  If a router address is included in this list,
                this filter applies to RIPv6 advertisements from that router.

                If non-null, The octet string contains one or more 2-tuples
                of this form:

                 first 4 octets: interface index
                 next 16 octets: router address (::0 means any address)

	         If null, this filter applies to RIPv6 updates from any router."

        ::= { wfRip6AcceptEntry 10 }

    wfRip6AcceptInterface OBJECT-TYPE
        SYNTAX	OCTET STRING
        ACCESS	read-write
        STATUS	mandatory
        DESCRIPTION
                "RIPv6 interface list. This octet string contains the
                addresses of one or more interfaces on this router.  If an
                interface address is included in this list, this filter
                applies to RIPv6 advertisements received on that interface.

                If non-null, The octet string contains one or more 4-octet
                interface indexes.  If null, this filter applies to RIPv6 updates
                received on any interface."

        ::= { wfRip6AcceptEntry 11 }

    wfRip6AcceptLog OBJECT-TYPE
        SYNTAX	INTEGER {
    		    true(1),
    		    false(2)
    		}
        ACCESS	read-write
        STATUS	mandatory
        DESCRIPTION
                "Log Action. If 'true(1), a log event is generated
                 when a prefix matches this filter rule; if 'false(2)',
                 no logging is done."
        DEFVAL	{ false }
        ::= { wfRip6AcceptEntry 12 }



    wfRip6AnnounceTable OBJECT-TYPE
        SYNTAX	SEQUENCE OF WfRip6AnnounceEntry
        ACCESS	not-accessible
        STATUS	mandatory
        DESCRIPTION
                "The Table of RIPv6 Announce Route Policy Rules"
        ::= { wfIpv6PolicyGroup 2 }

    wfRip6AnnounceEntry OBJECT-TYPE
        SYNTAX	WfRip6AnnounceEntry
        ACCESS	not-accessible
        STATUS	mandatory
        DESCRIPTION
                "An entry in the RIPv6 Announce Rule Table"
        INDEX	{ wfRip6AnnounceIndex }
        ::= { wfRip6AnnounceTable 1 }

    WfRip6AnnounceEntry ::= SEQUENCE {
    	    wfRip6AnnounceDelete
    		INTEGER,
    	    wfRip6AnnounceDisable
    		INTEGER,
    	    wfRip6AnnounceIndex
    		INTEGER,
    	    wfRip6AnnounceName
    		DisplayString,
    	    wfRip6AnnouncePrefixes
    		OCTET STRING,
    	    wfRip6AnnounceAction
    		INTEGER,
    	    wfRip6AnnouncePrecedence
    		INTEGER,
    	    wfRip6AnnounceRouteSource
    		INTEGER,
    	    wfRip6AnnounceExtRouteSource
    		INTEGER,
    	    wfRip6AnnounceAdvertise
    		OCTET STRING,
    	    wfRip6AnnounceRipGateway
    		OCTET STRING,
    	    wfRip6AnnounceInterface
    		OCTET STRING,
    	    wfRip6AnnounceRipMetric
    		INTEGER
        }

    wfRip6AnnounceDelete OBJECT-TYPE
        SYNTAX	INTEGER {
    		    created(1),
    		    deleted(2)
    		}
        ACCESS	read-write
        STATUS	mandatory
        DESCRIPTION
                "Create/Delete parameter."
        DEFVAL	{ created }
        ::= { wfRip6AnnounceEntry 1 }

    wfRip6AnnounceDisable OBJECT-TYPE
        SYNTAX	INTEGER {
    		    enabled(1),
    		    disabled(2)
    		}
        ACCESS	read-write
        STATUS	mandatory
        DESCRIPTION
                "Enable/Disable parameter."
        DEFVAL	{ enabled }
        ::= { wfRip6AnnounceEntry 2 }

    wfRip6AnnounceIndex OBJECT-TYPE
        SYNTAX	INTEGER
        ACCESS	read-only
        STATUS	mandatory
        DESCRIPTION
                "Rule index number"
        ::= { wfRip6AnnounceEntry 3 }

    wfRip6AnnounceName OBJECT-TYPE
        SYNTAX	DisplayString
        ACCESS	read-write
        STATUS	mandatory
        DESCRIPTION
                "Rule name - user specified name for this rule"
        ::= { wfRip6AnnounceEntry 4 }

    wfRip6AnnouncePrefixes OBJECT-TYPE
        SYNTAX	OCTET STRING
        ACCESS	read-write
        STATUS	mandatory
        DESCRIPTION
                "Prefix identification list. This identifies which
                Prefixes will match this rule.  If non-null, The octet
                string contains one or more 3-tuples of this form:

                 first octet:  exact (1) or range (2)
                 next 16 octets: prefix
                 next octet: prefix length

                An entry with an 'exact' tag means to only match the
                specific prefix advertisement (prefix & length).  An
                entry with a 'range' tag means to match any prefix that
                falls in the range indicated by the prefix and length.

                An 'exact' encoding of ::0/0 means 'match the
                default route.  A 'range' encoding of ::0/0 means
                'match any route'.

                A null string also means 'match any route'."
        ::= { wfRip6AnnounceEntry 5 }

    wfRip6AnnounceAction OBJECT-TYPE
        SYNTAX	INTEGER {
    		    announce(2),
    		    ignore(3)
    		}
        ACCESS	read-write
        STATUS	mandatory
        DESCRIPTION
                "action. 'announce' means that the route should be
                advertised.  'ignore' means don't advertise the route."
        DEFVAL	{ announce }
        ::= { wfRip6AnnounceEntry 6 }

    wfRip6AnnouncePrecedence OBJECT-TYPE
        SYNTAX	INTEGER
        ACCESS	read-write
        STATUS	mandatory
        DESCRIPTION
                "precedence. This is a metric to be used to compare
                this policy rule to other rules that a given route may
                match.  A rule with a higher precedence value will be
                chosen over one with a smaller value.  In the case of
                a tie, the rule index is used (larger wins)."
        ::= { wfRip6AnnounceEntry 7 }

    wfRip6AnnounceRouteSource OBJECT-TYPE
        SYNTAX	INTEGER
        ACCESS	read-write
        STATUS	mandatory
        DESCRIPTION
                "route source. This parameter can contain one or more
                route source identifiers.  If the route source is in this
                bit map, then a route from that source that meets the other
                criteria of this filter will match the filter.

                bit 0                                bit 31
                +---------------------------------------+
                |                                       |
                +---------------------------------------+

                bit31  DIRECT
                bit30  STATIC
                bit29  RIP
                bit28  OSPF
                bit27  BGP
		"
        DEFVAL	{ 63 }
        ::= { wfRip6AnnounceEntry 8 }

    wfRip6AnnounceExtRouteSource OBJECT-TYPE
        SYNTAX	INTEGER
        ACCESS	read-write
        STATUS	mandatory
        DESCRIPTION
                "external route source. This parameter can contain one
                or more external route source identifiers.  If the external
                route source is in this bit map, then a route from that
                external source that meets the other criteria of this
                filter will match the filter.
                
                bit 0                                bit 31
                +---------------------------------------+
                |                                       |
                +---------------------------------------+

                bit31  DIRECT
                bit30  STATIC
                bit29  RIP
                bit28  OSPF
                bit27  BGP
                "
        DEFVAL	{ 63 }
        ::= { wfRip6AnnounceEntry 9 }

    wfRip6AnnounceAdvertise OBJECT-TYPE
        SYNTAX	OCTET STRING
        ACCESS	read-write
        STATUS	mandatory
        DESCRIPTION
                "network advertisement list. this octet string should
                only be non-null if the action is 'announce' and if it is
                desired to advertise networks that differ from the actual
                network in the routing table.  For instance, if a number of
                networks in a certain range are in the table, an aggregate
                could be advertised instead of the individual networks.

                If non-null, The octet string contains one or more 2-tuples
                of this form:

                 first 16 octets: prefix
                 next octet: length

                Upon receiving a route that matches this filter, all prefixes
                in this list will be advertised.  If the list is null, the
                actual prefix is advertised.

                An encoding of ffff:ffff:ffff:ffff:ffff:ffff:ffff:ffff/128 
	        means 'match the actual prefix.'  This allows advertisement
	        of an aggregate or default along with the actual prefix."
        ::= { wfRip6AnnounceEntry 10 }

    wfRip6AnnounceRipGateway OBJECT-TYPE
        SYNTAX	OCTET STRING
        ACCESS	read-write
        STATUS	mandatory
        DESCRIPTION
                "from RIPv6' gateway list. Only applicable for RIPv6 sourced
                routes and if RIPv6 is included as a route source.  This octet
                string contains the addresses of one or more routers that could
                send RIPv6 updates to this router.  If a router address is
                included in this list, this filter applies to RIPv6
                advertisements from that router.

                If non-null, The octet string contains one or more 2-tuples
                of this form:

                 first 4 octets: interface index
                 next 16 octets: router address (::0 means any address)

                If null, this filter applies to RIPv6 updates from any router."

        ::= { wfRip6AnnounceEntry 11 }

    wfRip6AnnounceInterface OBJECT-TYPE
        SYNTAX	OCTET STRING
        ACCESS	read-write
        STATUS	mandatory
        DESCRIPTION
                "RIPv6 outbound interface list. This is a list of outgoing RIPv6
                interfaces.  If an interface appears in this list, the filter
                applies to RIPv6 advertisements sent via that interface.

                If non-null, The octet string contains one or more 4-octet
                interface indexes.  If null, this filter applies to RIPv6 updates
                received on any interface."

        ::= { wfRip6AnnounceEntry 12 }

    wfRip6AnnounceRipMetric OBJECT-TYPE
        SYNTAX	INTEGER(0..15)
        ACCESS	read-write
        STATUS	mandatory
        DESCRIPTION
                "RIPv6 metric. Only valid if the action is 'propagate'.
                This is an optional export metric to use when advertising
                a route that matches this filter.  If zero, the routing table
                metric calculated for RIPv6 plus the interface cost is used."
        ::= { wfRip6AnnounceEntry 13 }


-- RIPv6 Log Event Management table

    wfRipv6Log	OBJECT IDENTIFIER ::= { wfRipv6Group 3 }

    wfRipv6LogDelete OBJECT-TYPE
        SYNTAX	INTEGER {
    		    created(1),
    		    deleted(2)
    		}
        ACCESS	read-write
        STATUS	mandatory
        DESCRIPTION
                "Create/Delete parameter. Default is created.
                Users perform a set operation on this
                object in order to create/delete wfRipv6Log mib object."
        DEFVAL	{ created }
        ::= { wfRipv6Log 1 }

    wfRipv6LogDisable OBJECT-TYPE
        SYNTAX	INTEGER {
    		    enabled(1),
    		    disabled(2)
    		}
        ACCESS	read-write
        STATUS	mandatory
        DESCRIPTION
                "Enable/Disable parameter. Default is enabled."
        DEFVAL	{ enabled }
        ::= { wfRipv6Log 2 }

    wfRipv6LogLevel OBJECT-TYPE
        SYNTAX	INTEGER {
    		    debug(1),
    		    trace(2),
    		    info(3),
    		    warning(4),
    		    fault(5)
    		}
        ACCESS	read-write
        STATUS	mandatory
        DESCRIPTION
                "RIP6 log event level.
		 Setting log to a specific level enables logging Ripv6
		 events of this level and higher."
        DEFVAL	{ info }
        ::= { wfRipv6Log 3 }

    wfRipv6LogEvent OBJECT-TYPE
        SYNTAX	INTEGER (0..255)
        ACCESS	read-write
        STATUS	mandatory
        DESCRIPTION
                "Indicates whether a log message which corresponds
                 to the value of this attributes should be
                 sent to the log.

                 It affects wfRipv6LogCodes only. In order to save combined
                 list of messages you have to set wfRipv6LogCfgEvents directly
                 as copy of wfRipv6LogEvents."
        DEFVAL	{ 0 }
        ::= { wfRipv6Log 4 }

    wfRipv6LogEventDisable OBJECT-TYPE
        SYNTAX	INTEGER {
    		    enabled(1),
    		    disabled(2)
    		}
        ACCESS	read-write
        STATUS	mandatory
        DESCRIPTION
                "Indicates whether a log event defined in wfRipv6LogEvent
                 is to be logged."
        DEFVAL	{ enabled }
        ::= { wfRipv6Log 5 }

    wfRipv6LogEvents OBJECT-TYPE
        SYNTAX	OCTET STRING
        ACCESS	read-only
        STATUS	mandatory
        DESCRIPTION
                "Vector of enabled debug messages (to check only).
                 Messages are identified via the string of bits
                 contained within this attribute. The first octet
                 contains bits 0 to 7, the second octet contains
                 bits 8 to 15, and so on, with the most significant
                 bit referring to the lowest bit number in the octet
                 (e.g., the MSB of the first octet refers to bit 0).
                 If a bit, i, is present and set, then the DEBUG log
                 message with the code (i) is enabled."
        ::= { wfRipv6Log 6 }

    wfRipv6LogCfgEvents OBJECT-TYPE
        SYNTAX	OCTET STRING
        ACCESS	read-write
        STATUS	mandatory
        DESCRIPTION
                "User-defined vector of enabled debug messages upon boot.
                Coded as instance above"
        ::= { wfRipv6Log 7 }

-- RIPv6 Base attributes

    wfRipv6Base		  OBJECT IDENTIFIER ::= { wfRipv6Group 4}

    wfRipv6BaseDelete OBJECT-TYPE
        SYNTAX	INTEGER {
    		    created(1),
    		    deleted(2)
    		}
        ACCESS	read-write
        STATUS	mandatory
        DESCRIPTION
                "Create/Delete parameter. Default is created.
                Users perform a set operation on this
                object in order to create/delete RIPv6."
        DEFVAL	{ created }
        ::= { wfRipv6Base 1 }

    wfRipv6BaseDisable OBJECT-TYPE
        SYNTAX	INTEGER {
    		    enabled(1),
    		    disabled(2)
    		}
        ACCESS	read-write
        STATUS	mandatory
        DESCRIPTION
                "Enable/Disable parameter. Default is enabled.
                Users perform a set operation on this
                object in order to enable/disable RIPv6."
        DEFVAL	{ enabled }
        ::= { wfRipv6Base 2 }

    wfRipv6BaseState OBJECT-TYPE
        SYNTAX	INTEGER {
    		    up(1),
    		    down(2)
    		}
        ACCESS	read-only
        STATUS	mandatory
        DESCRIPTION
                "The current state of the entire RIPv6."
        DEFVAL	{ down }
        ::= { wfRipv6Base 3 }

    wfRipv6BaseDiameter OBJECT-TYPE
        SYNTAX	INTEGER(0..15)
        ACCESS	read-write
        STATUS	mandatory
        DESCRIPTION
                "The Diameter of the RIPv6 network.  1 less than 'infinity"
        DEFVAL	{ 15 }
        ::= { wfRipv6Base 4 }


    END  -- Wellfleet-RIP6-MIB
