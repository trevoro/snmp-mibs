CODIMA-GLOBAL-REG DEFINITIONS ::= BEGIN

IMPORTS
     enterprises,
     MODULE-IDENTITY,
     OBJECT-IDENTITY
          FROM SNMPv2-SMI;

codima OBJECT-IDENTITY
     STATUS current
     DESCRIPTION
          "The root of the sub-tree assigned to CODIMA
          Technologies Ltd."
     ::= { enterprises 226 }

codimaReg OBJECT-IDENTITY
     STATUS current
     DESCRIPTION
          "Sub-tree for registrations, which includes modules."
     ::= { codima 1 }

codimaModules OBJECT-IDENTITY
     STATUS current
     DESCRIPTION
          "Sub-tree to register the values assigned to modules
          with the MODULE-IDENTITY construct."
     ::= { codimaReg 1 }

codimaRegMIB MODULE-IDENTITY
     LAST-UPDATED "200305291550Z"
     ORGANIZATION "CODIMA Technologies Ltd"
     CONTACT-INFO
          "mailto:support@codimaTech.com
          http://www.codiamTech.com"
     DESCRIPTION
          "Global registration MIB module for the CODIMA
          framework."
     REVISION "200305291550Z"
     DESCRIPTION
          "Initial version"
     ::= { codimaModules 1 }

networkManagementProducts OBJECT-IDENTITY
     STATUS current
     DESCRIPTION
          "Computer Network Management product lines."
     ::= { codimaReg 2 }

expressConsoleManagerReg OBJECT-IDENTITY
     STATUS current
     DESCRIPTION
          "The CODIMA Express Console Manager.
          A software console that allows a network manager to remotely 
          manage from a central point any number of Express Probes. 
          The software resides on the PC and uses any Network Adapter
          (including PCMCIA) to access the functionality of the Express 
          Probes. 
          Note: The Console Manager has no local monitoring and 
          analysis capability unless it is combined with an S-Probe. 
          All monitoring and analysis is undertaken by the Express 
          Probes associated with the Console Manager."
     ::= { networkManagementProducts 1 }

expressFoundationManagerReg OBJECT-IDENTITY
     STATUS current
     DESCRIPTION
          "The CODIMA Express Foundation Manager.
          The foundation for the Express network management 
          architecture. As well as providing a console for any number 
          of Express Probes and any SNMP-compliant nodes, 
          the Express Foundation Manager can manage and 
          troubleshoot its local segment using the built in 
          Express Card"
     ::= { networkManagementProducts 2 }

expressFProbeReg OBJECT-IDENTITY
     STATUS current
     DESCRIPTION
          "The CODIMA Express F-Probe.
          A hardware probe that can be placed anywhere on your Fast 
          Ethernet or Ethernet network to either locally manage or 
          remote manage (via the Express Foundation Manager or 
          Express Console Manager) a network segment."
     ::= { networkManagementProducts 3 }

expressSProbeReg OBJECT-IDENTITY
     STATUS current
     DESCRIPTION
          "The CODIMA Express S-Probe.
          A software probe that can be placed anywhere on your 1Gb, 
          100Mb or 10Mb Ethernet network to either locally manage 
          or remotely manage (via the Express Foundation Manager 
          or Express Console Manager) a network segment."
     ::= { networkManagementProducts 4 }

expressPortableAnalyzerReg OBJECT-IDENTITY
     STATUS current
     DESCRIPTION
          "The CODIMA Express Portable Analyzer.
          On-the-spot troubleshooting and diagnostic tool for the 
          travelling network technician. If required, the Express Portable 
          Analyzer can be left at a remote site and managed remotely 
          by the Express Foundation Manager and/or Express Console 
          Manager. The built-in Express 10/100 card provides full-line 
          rate performance for monitoring, capturing and filtering."
     ::= { networkManagementProducts 5 }

expressDeveloperReg OBJECT-IDENTITY
     STATUS current
     DESCRIPTION
          "The CODIMA Express Developer Version.
          For internal development use only."
     ::= { networkManagementProducts 6 }

codimaGeneric OBJECT-IDENTITY
     STATUS current
     DESCRIPTION
          "Sub-tree for company-wide object and event definitions."
     ::= { codima 2 }

codimaProducts OBJECT-IDENTITY
     STATUS current
     DESCRIPTION
          "Sub-tree for product specific object and event definitions."
     ::= { codima 3 }

codimaCaps OBJECT-IDENTITY
     STATUS current
     DESCRIPTION
          "Sub-tree for agent profiles."
     ::= { codima 4 }

codimaReqs OBJECT-IDENTITY
     STATUS current
     DESCRIPTION
          "Sub-tree for management application requirements."
     ::= { codima 5 }

codimaExpr OBJECT-IDENTITY
     STATUS current
     DESCRIPTION
          "Sub-tree for experimental definitions."
     ::= { codima 6 }

END
