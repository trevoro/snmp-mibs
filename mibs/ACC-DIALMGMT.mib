ACC-DIALMGMT DEFINITIONS ::= BEGIN

    IMPORTS
	 OBJECT-TYPE, Counter, TimeTicks, IpAddress FROM RFC1155-SMI
	 TRAP-TYPE FROM RFC-1215
         accTrapLogSeqNum FROM ACC-SYSTEM
	 accBRG, DisplayString, RowStatus, IfIndex, SmdsAddress
             FROM ACC-MIB;
-- Dial Management Group
    accDialMgmt		OBJECT IDENTIFIER ::= { accBRG 80 }
    -- Line Groups MIB
    accLineGroups	OBJECT IDENTIFIER ::= { accDialMgmt 2 }
	-- Line Group Table
	accLineGroupTable OBJECT-TYPE
	    SYNTAX SEQUENCE OF AccLineGroupEntry
	    ACCESS not-accessible
	    STATUS mandatory
	    DESCRIPTION
	    " Table of line groups  "
	    ::= { accLineGroups 1 }
	accLineGroupEntry OBJECT-TYPE
	    SYNTAX AccLineGroupEntry
	    ACCESS not-accessible
	    STATUS mandatory
	    DESCRIPTION
	    " An entry in the line group table "
	    INDEX { accLineGroupIndex }
	    ::= { accLineGroupTable 1 }
	AccLineGroupEntry ::= SEQUENCE {
	    accLineGroupIndex INTEGER,
	    accLineGroupType INTEGER,
	    accLineGroupEntryStatus INTEGER,
	    accLineGroupAdminStatus INTEGER,
	    accLineGroupOperStatus INTEGER,
	    accLineGroupLineCount INTEGER,
	    accLineGroupBaseLic INTEGER,
	    accLineGroupSignalGroup INTEGER,
	    accLineGroupCdnGroup INTEGER,
	    accLineGroupIpAddress OCTET STRING,
	    accLineGroupUdpPort INTEGER,
	    accLineGroupDefaultTos INTEGER,
	    accLineGroupMsgLevel INTEGER,
	    accLineGroupActiveLines Counter,
	    accLineGroupLineStatus INTEGER,
	    accLineGroupAvailableLines Counter
	    }
	accLineGroupIndex OBJECT-TYPE
	    SYNTAX INTEGER
	    ACCESS read-only
	    STATUS mandatory
	    DESCRIPTION
	    " Line group index "
	    ::= { accLineGroupEntry 1 }
	accLineGroupType OBJECT-TYPE
	    SYNTAX INTEGER {
		vna (1)
	    }
	    ACCESS read-write
	    STATUS mandatory
	    DESCRIPTION
	    " Line group type "
	    ::= { accLineGroupEntry 2 }
	accLineGroupEntryStatus OBJECT-TYPE
	    SYNTAX INTEGER {
		add (1),
		delete (2)
	    }
	    ACCESS read-write
	    STATUS mandatory
	    DESCRIPTION
	    " The modification status of this table entry "
	    ::= { accLineGroupEntry 3 }
	accLineGroupAdminStatus OBJECT-TYPE
	    SYNTAX INTEGER {
		enabled (1),
		disabled (2),
		drained (3)
	    }
	    ACCESS read-write
	    STATUS mandatory
	    DESCRIPTION
	    " The administrative status of this line group "
	    ::= { accLineGroupEntry 4 }
	accLineGroupOperStatus OBJECT-TYPE
	    SYNTAX INTEGER {
		deactivated (1),
		activating (2),
		activated (3),
		deactivating (4)
	    }
	    ACCESS read-only
	    STATUS mandatory
	    DESCRIPTION
	    " The operational status of this line group "
	    ::= { accLineGroupEntry 5 }
	accLineGroupLineCount OBJECT-TYPE
	    SYNTAX INTEGER
	    ACCESS read-write
	    STATUS mandatory
	    DESCRIPTION
	    " The number of lines configured for this line group "
	    ::= { accLineGroupEntry 6 }
	accLineGroupBaseLic OBJECT-TYPE
	    SYNTAX INTEGER
	    ACCESS read-write
	    STATUS mandatory
	    DESCRIPTION
	    " The base line identification code for the lines in this
              line group "
	    ::= { accLineGroupEntry 7 }
	accLineGroupSignalGroup OBJECT-TYPE
	    SYNTAX INTEGER
	    ACCESS read-write
	    STATUS mandatory
	    DESCRIPTION
	    " The signal group to be used for signaling calls on this
              line group "
	    ::= { accLineGroupEntry 8 }
	accLineGroupCdnGroup OBJECT-TYPE
	    SYNTAX INTEGER
	    ACCESS read-write
	    STATUS mandatory
	    DESCRIPTION
	    " The called number group to be used for calls arriving on
              this line group "
	    ::= { accLineGroupEntry 9 }
	accLineGroupIpAddress OBJECT-TYPE
	    SYNTAX OCTET STRING
	    ACCESS read-write
	    STATUS mandatory
	    DESCRIPTION
	    " The local IP address for lines on this line group "
	    ::= { accLineGroupEntry 10 }
	accLineGroupUdpPort OBJECT-TYPE
	    SYNTAX INTEGER
	    ACCESS read-write
	    STATUS mandatory
	    DESCRIPTION
	    " The base UDP port for lines on this line group "
	    ::= { accLineGroupEntry 11 }
	accLineGroupDefaultTos OBJECT-TYPE
	    SYNTAX INTEGER {
		normal (1),
		low-delay (2)
	    }
	    ACCESS read-write
	    STATUS mandatory
	    DESCRIPTION
	    " The default type of service to use for media on this line
              group "
	    ::= { accLineGroupEntry 12 }
	accLineGroupMsgLevel OBJECT-TYPE
	    SYNTAX INTEGER
	    ACCESS read-write
	    STATUS mandatory
	    DESCRIPTION
	    " The debug message level for activity associated with this 
	      line group "
	    ::= { accLineGroupEntry 13 }
	accLineGroupActiveLines OBJECT-TYPE
	    SYNTAX Counter
	    ACCESS read-only
	    STATUS mandatory
	    DESCRIPTION
	    " The number of lines which are busy with calls on this line
	      group "
	    ::= { accLineGroupEntry 14 }
	accLineGroupLineStatus OBJECT-TYPE
	    SYNTAX INTEGER {
		unallocated (1),
		allocated (2)
	    }
	    ACCESS read-only
	    STATUS mandatory
	    DESCRIPTION
	    " The status of the line identification codes for lines on 
	      this line group "
	    ::= { accLineGroupEntry 15 }
	accLineGroupAvailableLines OBJECT-TYPE
	    SYNTAX Counter
	    ACCESS read-only
	    STATUS mandatory
	    DESCRIPTION
	    " The number of lines available for new calls on this 
              line group "
	    ::= { accLineGroupEntry 16 }
	-- Line Group Media Table
	accLineGroupMediaTable OBJECT-TYPE
	    SYNTAX SEQUENCE OF AccLineGroupMediaEntry
	    ACCESS not-accessible
	    STATUS mandatory
	    DESCRIPTION
	    " The list of preferred media types to be used for calls on 
	      this a group "
	    ::= { accLineGroups 2 }
	accLineGroupMediaEntry OBJECT-TYPE
	    SYNTAX AccLineGroupMediaEntry
	    ACCESS not-accessible
	    STATUS mandatory
	    DESCRIPTION
	    " An entry in the line group media table "
	    INDEX { accLineGroupMediaIndex, accLineGroupMediaPreference }
	    ::= { accLineGroupMediaTable 1 }
	AccLineGroupMediaEntry ::= SEQUENCE {
	    accLineGroupMediaIndex INTEGER,
	    accLineGroupMediaPreference INTEGER,
	    accLineGroupMediaType INTEGER,
	    accLineGroupMediaStatus INTEGER,
	    accLineGroupMediaCodecType INTEGER,
	    accLineGroupMediaPayldType INTEGER,
	    accLineGroupMediaPayldTos INTEGER
	    }
	accLineGroupMediaIndex OBJECT-TYPE
	    SYNTAX INTEGER
	    ACCESS read-only
	    STATUS mandatory
	    DESCRIPTION
	    " The line group that this entry in the media table refers to "
	    ::= { accLineGroupMediaEntry 1 }
	accLineGroupMediaPreference OBJECT-TYPE
	    SYNTAX INTEGER
	    ACCESS read-only
	    STATUS mandatory
	    DESCRIPTION
	    " The preference number for this media type "
	    ::= { accLineGroupMediaEntry 2 }
	accLineGroupMediaType OBJECT-TYPE
	    SYNTAX INTEGER {
		audio (1),
		video (2),
		data (3)
	    }
	    ACCESS read-only
	    STATUS mandatory
	    DESCRIPTION
	    " The type of media "
	    ::= { accLineGroupMediaEntry 3 }
	accLineGroupMediaStatus OBJECT-TYPE
	    SYNTAX INTEGER {
		add (1),
		delete (2)
	    }
	    ACCESS read-write
	    STATUS mandatory
	    DESCRIPTION
	    " The modification status of this entry in the table "
	    ::= { accLineGroupMediaEntry 4 }
	accLineGroupMediaCodecType OBJECT-TYPE
	    SYNTAX INTEGER {
		g-711 (1)
	    }
	    ACCESS read-write
	    STATUS mandatory
	    DESCRIPTION
	    " The codec type for this media preference "
	    ::= { accLineGroupMediaEntry 5 }
	accLineGroupMediaPayldType OBJECT-TYPE
	    SYNTAX INTEGER {
		udp (1),
		rtp (2)
	    }
	    ACCESS read-write
	    STATUS mandatory
	    DESCRIPTION
	    " The payload type for this media preference "
	    ::= { accLineGroupMediaEntry 6 }
	accLineGroupMediaPayldTos OBJECT-TYPE
	    SYNTAX INTEGER {
		normal (1),
		low-delay (2)
	    }
	    ACCESS read-write
	    STATUS mandatory
	    DESCRIPTION
	    " The type of service for this media preference "
	    ::= { accLineGroupMediaEntry 7 }
    -- Signaling Groups MIB
    accSignalingGroups	OBJECT IDENTIFIER ::= { accDialMgmt 1 }
	accSignalGroupTable OBJECT-TYPE
	    SYNTAX SEQUENCE OF AccSignalGroupEntry
	    ACCESS not-accessible
	    STATUS mandatory
	    DESCRIPTION
	    "  "
	    ::= { accSignalingGroups 1 }
	accSignalGroupEntry OBJECT-TYPE
	    SYNTAX AccSignalGroupEntry
	    ACCESS not-accessible
	    STATUS mandatory
	    DESCRIPTION
	    "  "
	    INDEX { accSignalGroupIndex }
	    ::= { accSignalGroupTable 1 }
	AccSignalGroupEntry ::= SEQUENCE {
	    accSignalGroupIndex INTEGER,
	    accSignalGroupType INTEGER,
	    accSignalGroupEntryStatus INTEGER,
	    accSignalGroupAdminStatus INTEGER,
	    accSignalGroupAuthName OCTET STRING,
	    accSignalGroupAuthPassword OCTET STRING,
	    accSignalGroupOperStatus INTEGER,
	    accSignalGroupPollInterval TimeTicks,
	    accSignalGroupWaitInterval TimeTicks,
	    accSignalGroupRetryCount INTEGER,
	    accSignalGroupRetryInterval TimeTicks,
	    accSignalGroupRetryBackoff TimeTicks,
	    accSignalGroupPriIpAddress OCTET STRING,
	    accSignalGroupPriTcpPort INTEGER,
	    accSignalGroupSecIpAddress OCTET STRING,
	    accSignalGroupSecTcpPort INTEGER,
	    accSignalGroupCdnGroup INTEGER,
	    accSignalGroupLastCause INTEGER,
	    accSignalGroupMsgLevel INTEGER
	    }
	accSignalGroupIndex OBJECT-TYPE
	    SYNTAX INTEGER
	    ACCESS read-only
	    STATUS mandatory
	    DESCRIPTION
	    " Signal Group  "
	    ::= { accSignalGroupEntry 1 }
	accSignalGroupType OBJECT-TYPE
	    SYNTAX INTEGER {
		vna (2)
	    }
	    ACCESS read-write
	    STATUS mandatory
	    DESCRIPTION
	    " Group Type  "
	    ::= { accSignalGroupEntry 2 }
	accSignalGroupEntryStatus OBJECT-TYPE
	    SYNTAX INTEGER {
		add (1),
		delete (2)
	    }
	    ACCESS read-write
	    STATUS mandatory
	    DESCRIPTION
	    " Entry Status  "
	    ::= { accSignalGroupEntry 3 }
	accSignalGroupAdminStatus OBJECT-TYPE
	    SYNTAX INTEGER {
		enabled (1),
		disabled (2),
		drained (3)
	    }
	    ACCESS read-write
	    STATUS mandatory
	    DESCRIPTION
	    " Admin Status  "
	    ::= { accSignalGroupEntry 4 }
	accSignalGroupAuthName OBJECT-TYPE
	    SYNTAX OCTET STRING
	    ACCESS read-write
	    STATUS mandatory
	    DESCRIPTION
	    " Auth Name  "
	    ::= { accSignalGroupEntry 5 }
	accSignalGroupAuthPassword OBJECT-TYPE
	    SYNTAX OCTET STRING
	    ACCESS read-write
	    STATUS mandatory
	    DESCRIPTION
	    " Auth Password  "
	    ::= { accSignalGroupEntry 6 }
	accSignalGroupOperStatus OBJECT-TYPE
	    SYNTAX INTEGER {
		deactivated (1),
		activating (2),
		activated (3),
		established (4),
		engaged (5),
		draining (6),
		releasing (7),
		deactivating (8)
	    }
	    ACCESS read-only
	    STATUS mandatory
	    DESCRIPTION
	    " Oper Status  "
	    ::= { accSignalGroupEntry 7 }
	accSignalGroupPollInterval OBJECT-TYPE
	    SYNTAX TimeTicks
	    ACCESS read-write
	    STATUS mandatory
	    DESCRIPTION
	    " Poll Interval  "
	    ::= { accSignalGroupEntry 8 }
	accSignalGroupWaitInterval OBJECT-TYPE
	    SYNTAX TimeTicks
	    ACCESS read-write
	    STATUS mandatory
	    DESCRIPTION
	    " Wait Interval  "
	    ::= { accSignalGroupEntry 9 }
	accSignalGroupRetryCount OBJECT-TYPE
	    SYNTAX INTEGER
	    ACCESS read-write
	    STATUS mandatory
	    DESCRIPTION
	    " Retry Count  "
	    ::= { accSignalGroupEntry 10 }
	accSignalGroupRetryInterval OBJECT-TYPE
	    SYNTAX TimeTicks
	    ACCESS read-write
	    STATUS mandatory
	    DESCRIPTION
	    " Retry Interval  "
	    ::= { accSignalGroupEntry 11 }
	accSignalGroupRetryBackoff OBJECT-TYPE
	    SYNTAX TimeTicks
	    ACCESS read-write
	    STATUS mandatory
	    DESCRIPTION
	    " Retry Backoff  "
	    ::= { accSignalGroupEntry 12 }
	accSignalGroupPriIpAddress OBJECT-TYPE
	    SYNTAX OCTET STRING
	    ACCESS read-write
	    STATUS mandatory
	    DESCRIPTION
	    " Pri Addr  "
	    ::= { accSignalGroupEntry 13 }
	accSignalGroupPriTcpPort OBJECT-TYPE
	    SYNTAX INTEGER
	    ACCESS read-write
	    STATUS mandatory
	    DESCRIPTION
	    " Pri Port  "
	    ::= { accSignalGroupEntry 14 }
	accSignalGroupSecIpAddress OBJECT-TYPE
	    SYNTAX OCTET STRING
	    ACCESS read-write
	    STATUS mandatory
	    DESCRIPTION
	    " Alt Addr  "
	    ::= { accSignalGroupEntry 15 }
	accSignalGroupSecTcpPort OBJECT-TYPE
	    SYNTAX INTEGER
	    ACCESS read-write
	    STATUS mandatory
	    DESCRIPTION
	    " Alt Port  "
	    ::= { accSignalGroupEntry 16 }
	accSignalGroupCdnGroup OBJECT-TYPE
	    SYNTAX INTEGER
	    ACCESS read-write
	    STATUS mandatory
	    DESCRIPTION
	    " Number Group  "
	    ::= { accSignalGroupEntry 17 }
	accSignalGroupLastCause OBJECT-TYPE
	    SYNTAX INTEGER {
		unassigned-number (1),
		no-route-to-transit-network (2),
		no-route-to-destination (3),
		channel-unacceptable (6),
		call-awarded-being-delivered (7),
		normal-call-clearing (16),
		user-busy (17),
		no-user-responding (18),
		user-alerted-no-answer (19),
		call-rejected (21),
		number-changed (22),
		non-selected-user-clearing (26),
		destination-out-of-order (27),
		invalid-number-format (28),
		facility-rejected (29),
		response-to-status-enquiry (30),
		normal-clearing-unspecified (31),
		no-circuit-or-channel-available (34),
		network-out-of-order (38),
		temporary-failure (41),
		network-congestion (42),
		access-information-discarded (43),
		requested-channel-not-available (44),
		ciruit-or-channel-preempted (45),
		resources-unavailable (47),
		quality-of-service-unavailable (49),
		facility-not-subscribed (50),
		outgoing-call-barred (52),
		incoming-call-barred (54),
		bearer-capability-not-authorized (57),
		bearer-capability-not-available (58),
		service-not-available (63),
		bearer-capability-not-implemented (65),
		channel-not-implemented (66),
		facility-not-implemented (69),
		restricted-digital-information-only (70),
		service-not-implemented (79),
		invalid-call-reference (81),
		channel-does-not-exist (82),
		call-identity-non-existent (83),
		call-identity-in-use (84),
		no-call-suspended (85),
		suspended-call-cleared (86),
		incompatible-destination (88),
		invalid-transit-network (91),
		invalid-message-unspecified (95),
		manditory-information-element-missing (96),
		message-nonexistent-or-not-supported (97),
		incompatible-or-nonexistent-message (98),
		information-element-not-implemented (99),
		invalid-information-element-contents (100),
		message-incompatible-with-call-state (101),
		timer-expiration (102),
		information-element-length-error (103),
		protocol-error-unspecified (111),
		interworking-unspecified (127)
	    }
	    ACCESS read-only
	    STATUS mandatory
	    DESCRIPTION
	    " Last Cause  "
	    ::= { accSignalGroupEntry 18 }
	accSignalGroupMsgLevel OBJECT-TYPE
	    SYNTAX INTEGER
	    ACCESS read-write
	    STATUS mandatory
	    DESCRIPTION
	    " Message Level  "
	    ::= { accSignalGroupEntry 19 }
	-- Signaling Group Statistics Table
	accSignalGroupStatTable OBJECT-TYPE
	    SYNTAX SEQUENCE OF AccSignalGroupStatEntry
	    ACCESS not-accessible
	    STATUS mandatory
	    DESCRIPTION
	    "  "
	    ::= { accSignalingGroups 2 }
	accSignalGroupStatEntry OBJECT-TYPE
	    SYNTAX AccSignalGroupStatEntry
	    ACCESS not-accessible
	    STATUS mandatory
	    DESCRIPTION
	    "  "
	    INDEX { accSignalGroupStatIndex }
	    ::= { accSignalGroupStatTable 1 }
	AccSignalGroupStatEntry ::= SEQUENCE {
	    accSignalGroupStatIndex INTEGER,
	    accSignalGroupInMessages Counter,
	    accSignalGroupInOctets Counter,
	    accSignalGroupInErrors Counter,
	    accSignalGroupOutMessages Counter,
	    accSignalGroupOutOctets Counter,
	    accSignalGroupOutErrors Counter,
	    accSignalGroupOriginatedCalls Counter,
	    accSignalGroupOfferedCalls Counter,
	    accSignalGroupRoutedCalls Counter,
	    accSignalGroupAcceptedCalls Counter,
	    accSignalGroupConnectedCalls Counter,
	    accSignalGroupClearedCalls Counter
	    }
	accSignalGroupStatIndex OBJECT-TYPE
	    SYNTAX INTEGER
	    ACCESS read-only
	    STATUS mandatory
	    DESCRIPTION
	    " Signal Group  "
	    ::= { accSignalGroupStatEntry 1 }
	accSignalGroupInMessages OBJECT-TYPE
	    SYNTAX Counter
	    ACCESS read-only
	    STATUS mandatory
	    DESCRIPTION
	    " Incoming Msgs  "
	    ::= { accSignalGroupStatEntry 2 }
	accSignalGroupInOctets OBJECT-TYPE
	    SYNTAX Counter
	    ACCESS read-only
	    STATUS mandatory
	    DESCRIPTION
	    " Incoming Octets  "
	    ::= { accSignalGroupStatEntry 3 }
	accSignalGroupInErrors OBJECT-TYPE
	    SYNTAX Counter
	    ACCESS read-only
	    STATUS mandatory
	    DESCRIPTION
	    " Incoming Errors  "
	    ::= { accSignalGroupStatEntry 4 }
	accSignalGroupOutMessages OBJECT-TYPE
	    SYNTAX Counter
	    ACCESS read-only
	    STATUS mandatory
	    DESCRIPTION
	    " Outgoing Msgs  "
	    ::= { accSignalGroupStatEntry 5 }
	accSignalGroupOutOctets OBJECT-TYPE
	    SYNTAX Counter
	    ACCESS read-only
	    STATUS mandatory
	    DESCRIPTION
	    " Outgoing Octets  "
	    ::= { accSignalGroupStatEntry 6 }
	accSignalGroupOutErrors OBJECT-TYPE
	    SYNTAX Counter
	    ACCESS read-only
	    STATUS mandatory
	    DESCRIPTION
	    " Outgoing Errors  "
	    ::= { accSignalGroupStatEntry 7 }
	accSignalGroupOriginatedCalls OBJECT-TYPE
	    SYNTAX Counter
	    ACCESS read-only
	    STATUS mandatory
	    DESCRIPTION
	    " Calls Orig  "
	    ::= { accSignalGroupStatEntry 8 }
	accSignalGroupOfferedCalls OBJECT-TYPE
	    SYNTAX Counter
	    ACCESS read-only
	    STATUS mandatory
	    DESCRIPTION
	    " Calls Offered  "
	    ::= { accSignalGroupStatEntry 9 }
	accSignalGroupRoutedCalls OBJECT-TYPE
	    SYNTAX Counter
	    ACCESS read-only
	    STATUS mandatory
	    DESCRIPTION
	    " Calls Routed  "
	    ::= { accSignalGroupStatEntry 10 }
	accSignalGroupAcceptedCalls OBJECT-TYPE
	    SYNTAX Counter
	    ACCESS read-only
	    STATUS mandatory
	    DESCRIPTION
	    " Calls Accepted  "
	    ::= { accSignalGroupStatEntry 11 }
	accSignalGroupConnectedCalls OBJECT-TYPE
	    SYNTAX Counter
	    ACCESS read-only
	    STATUS mandatory
	    DESCRIPTION
	    " Calls Connected  "
	    ::= { accSignalGroupStatEntry 12 }
	accSignalGroupClearedCalls OBJECT-TYPE
	    SYNTAX Counter
	    ACCESS read-only
	    STATUS mandatory
	    DESCRIPTION
	    " Calls Cleared  "
	    ::= { accSignalGroupStatEntry 13 }
	-- Signaling Group Call Table
	accSignalGroupCallTable OBJECT-TYPE
	    SYNTAX SEQUENCE OF AccSignalGroupCallEntry
	    ACCESS not-accessible
	    STATUS mandatory
	    DESCRIPTION
	    "  "
	    ::= { accSignalingGroups 3 }
	accSignalGroupCallEntry OBJECT-TYPE
	    SYNTAX AccSignalGroupCallEntry
	    ACCESS not-accessible
	    STATUS mandatory
	    DESCRIPTION
	    "  "
	    INDEX { accSignalGroupCallIndex }
	    ::= { accSignalGroupCallTable 1 }
	AccSignalGroupCallEntry ::= SEQUENCE {
	    accSignalGroupCallIndex INTEGER,
	    accSignalGroupCallIdent INTEGER,
	    accSignalGroupCallDirection INTEGER,
	    accSignalGroupCallDialEndpt INTEGER,
	    accSignalGroupCallChannelId INTEGER,
	    accSignalGroupCallTermEndpt INTEGER,
	    accSignalGroupCallState INTEGER,
	    accSignalGroupCallCause INTEGER,
	    accSignalGroupCallCdNumber OCTET STRING,
	    accSignalGroupCallCgNumber OCTET STRING,
	    accSignalGroupCallInfoType INTEGER,
	    accSignalGroupCallInfoMode INTEGER,
	    accSignalGroupCallInfoRate INTEGER,
	    accSignalGroupCallL1Proto INTEGER,
	    accSignalGroupCallL1Framing INTEGER,
	    accSignalGroupCallUserRate INTEGER,
	    accSignalGroupCallDuration TimeTicks
	    }
	accSignalGroupCallIndex OBJECT-TYPE
	    SYNTAX INTEGER
	    ACCESS read-only
	    STATUS mandatory
	    DESCRIPTION
	    " Signal Group  "
	    ::= { accSignalGroupCallEntry 1 }
	accSignalGroupCallIdent OBJECT-TYPE
	    SYNTAX INTEGER
	    ACCESS read-only
	    STATUS mandatory
	    DESCRIPTION
	    " CallId  "
	    ::= { accSignalGroupCallEntry 2 }
	accSignalGroupCallDirection OBJECT-TYPE
	    SYNTAX INTEGER {
		incoming (1),
		outgoing (2)
	    }
	    ACCESS read-only
	    STATUS mandatory
	    DESCRIPTION
	    " Direction  "
	    ::= { accSignalGroupCallEntry 3 }
	accSignalGroupCallDialEndpt OBJECT-TYPE
	    SYNTAX INTEGER
	    ACCESS read-only
	    STATUS mandatory
	    DESCRIPTION
	    " DialEndpt  "
	    ::= { accSignalGroupCallEntry 4 }
	accSignalGroupCallChannelId OBJECT-TYPE
	    SYNTAX INTEGER
	    ACCESS read-only
	    STATUS mandatory
	    DESCRIPTION
	    " Channel Id  "
	    ::= { accSignalGroupCallEntry 5 }
	accSignalGroupCallTermEndpt OBJECT-TYPE
	    SYNTAX INTEGER
	    ACCESS read-only
	    STATUS mandatory
	    DESCRIPTION
	    " Term Endpt  "
	    ::= { accSignalGroupCallEntry 6 }
	accSignalGroupCallState OBJECT-TYPE
	    SYNTAX INTEGER {
		initiated (1),
		sending (2),
		proceeding (3),
		delivered (4),
		offered (6),
		alerting (7),
		answered (8),
		routing (9),
		connected (10),
		disconn-req (11),
		disconn-ind (12),
		suspend (15),
		resume (17),
		releasing (19),
		receiving (25),
		busy (99)
	    }
	    ACCESS read-only
	    STATUS mandatory
	    DESCRIPTION
	    " State  "
	    ::= { accSignalGroupCallEntry 7 }
	accSignalGroupCallCause OBJECT-TYPE
	    SYNTAX INTEGER {
		unassigned-number (1),
		no-route-to-transit-network (2),
		no-route-to-destination (3),
		channel-unacceptable (6),
		call-awarded-being-delivered (7),
		normal-call-clearing (16),
		user-busy (17),
		no-user-responding (18),
		user-alerted-no-answer (19),
		call-rejected (21),
		number-changed (22),
		non-selected-user-clearing (26),
		destination-out-of-order (27),
		invalid-number-format (28),
		facility-rejected (29),
		response-to-status-enquiry (30),
		normal-clearing-unspecified (31),
		no-circuit-or-channel-available (34),
		network-out-of-order (38),
		temporary-failure (41),
		network-congestion (42),
		access-information-discarded (43),
		requested-channel-not-available (44),
		ciruit-or-channel-preempted (45),
		resources-unavailable (47),
		quality-of-service-unavailable (49),
		facility-not-subscribed (50),
		outgoing-call-barred (52),
		incoming-call-barred (54),
		bearer-capability-not-authorized (57),
		bearer-capability-not-available (58),
		service-not-available (63),
		bearer-capability-not-implemented (65),
		channel-not-implemented (66),
		facility-not-implemented (69),
		restricted-digital-information-only (70),
		service-not-implemented (79),
		invalid-call-reference (81),
		channel-does-not-exist (82),
		call-identity-non-existent (83),
		call-identity-in-use (84),
		no-call-suspended (85),
		suspended-call-cleared (86),
		incompatible-destination (88),
		invalid-transit-network (91),
		invalid-message-unspecified (95),
		manditory-information-element-missing (96),
		message-nonexistent-or-not-supported (97),
		incompatible-or-nonexistent-message (98),
		information-element-not-implemented (99),
		invalid-information-element-contents (100),
		message-incompatible-with-call-state (101),
		timer-expiration (102),
		information-element-length-error (103),
		protocol-error-unspecified (111),
		interworking-unspecified (127)
	    }
	    ACCESS read-only
	    STATUS mandatory
	    DESCRIPTION
	    " Cause  "
	    ::= { accSignalGroupCallEntry 8 }
	accSignalGroupCallCdNumber OBJECT-TYPE
	    SYNTAX OCTET STRING
	    ACCESS read-only
	    STATUS mandatory
	    DESCRIPTION
	    " Cd Number  "
	    ::= { accSignalGroupCallEntry 9 }
	accSignalGroupCallCgNumber OBJECT-TYPE
	    SYNTAX OCTET STRING
	    ACCESS read-only
	    STATUS mandatory
	    DESCRIPTION
	    " Cg Number  "
	    ::= { accSignalGroupCallEntry 10 }
	accSignalGroupCallInfoType OBJECT-TYPE
	    SYNTAX INTEGER {
		speech (1),
		udi (2),
		rdi (3),
		audio3 (4),
		audio7 (5),
		video (6)
	    }
	    ACCESS read-only
	    STATUS mandatory
	    DESCRIPTION
	    " Info Type  "
	    ::= { accSignalGroupCallEntry 11 }
	accSignalGroupCallInfoMode OBJECT-TYPE
	    SYNTAX INTEGER {
		circuit (1),
		packet (2)
	    }
	    ACCESS read-only
	    STATUS mandatory
	    DESCRIPTION
	    " Info Mode  "
	    ::= { accSignalGroupCallEntry 12 }
	accSignalGroupCallInfoRate OBJECT-TYPE
	    SYNTAX INTEGER
	    ACCESS read-only
	    STATUS mandatory
	    DESCRIPTION
	    " Info Rate  "
	    ::= { accSignalGroupCallEntry 13 }
	accSignalGroupCallL1Proto OBJECT-TYPE
	    SYNTAX INTEGER {
		v-110 (1),
		g-711mu (2),
		g-711a (3),
		g-721 (4),
		g-722 (5),
		h-261 (6),
		non-ccitt (7),
		v-120 (8),
		x-31 (9)
	    }
	    ACCESS read-only
	    STATUS mandatory
	    DESCRIPTION
	    " L1 Proto  "
	    ::= { accSignalGroupCallEntry 14 }
	accSignalGroupCallL1Framing OBJECT-TYPE
	    SYNTAX INTEGER {
		sync (1),
		async (2)
	    }
	    ACCESS read-only
	    STATUS mandatory
	    DESCRIPTION
	    " L1 Framing  "
	    ::= { accSignalGroupCallEntry 15 }
	accSignalGroupCallUserRate OBJECT-TYPE
	    SYNTAX INTEGER
	    ACCESS read-only
	    STATUS mandatory
	    DESCRIPTION
	    " User Rate  "
	    ::= { accSignalGroupCallEntry 16 }
	accSignalGroupCallDuration OBJECT-TYPE
	    SYNTAX TimeTicks
	    ACCESS read-only
	    STATUS mandatory
	    DESCRIPTION
	    " Duration  "
	    ::= { accSignalGroupCallEntry 17 }
	-- Signal group media table
	accSignalGroupMediaTable OBJECT-TYPE
	    SYNTAX SEQUENCE OF AccSignalGroupMediaEntry
	    ACCESS not-accessible
	    STATUS mandatory
	    DESCRIPTION
	    " Table of media parameters for each call on the given
	      signal group "
	    ::= { accSignalingGroups 4 }
	accSignalGroupMediaEntry OBJECT-TYPE
	    SYNTAX AccSignalGroupMediaEntry
	    ACCESS not-accessible
	    STATUS mandatory
	    DESCRIPTION
	    " An entry in the signal group media table "
	    INDEX { accSignalGroupMediaIndex }
	    ::= { accSignalGroupMediaTable 1 }
	AccSignalGroupMediaEntry ::= SEQUENCE {
	    accSignalGroupMediaIndex INTEGER,
	    accSignalGroupMediaIdent INTEGER,
	    accSignalGroupMediaType INTEGER,
	    accSignalGroupMediaCodecType INTEGER,
	    accSignalGroupMediaPayldType INTEGER,
	    accSignalGroupMediaPayldTos INTEGER,
	    accSignalGroupMediaFrameSize INTEGER,
	    accSignalGroupMediaIpAddress OCTET STRING,
	    accSignalGroupMediaUdpPort INTEGER,
	    accSignalGroupMediaSilSupr INTEGER,
	    accSignalGroupMediaDtmfSupr INTEGER,
	    accSignalGroupMediaXmitSupr INTEGER,
	    accSignalGroupMediaRecvSupr INTEGER,
	    accSignalGroupMediaEchoSupr INTEGER
	    }
	accSignalGroupMediaIndex OBJECT-TYPE
	    SYNTAX INTEGER
	    ACCESS read-only
	    STATUS mandatory
	    DESCRIPTION
	    " The index of the signal group for which this entry in 
	      the table applies "
	    ::= { accSignalGroupMediaEntry 1 }
	accSignalGroupMediaIdent OBJECT-TYPE
	    SYNTAX INTEGER
	    ACCESS read-only
	    STATUS mandatory
	    DESCRIPTION
	    " The call id of the call for which this entry in the table
	      applies "
	    ::= { accSignalGroupMediaEntry 2 }
	accSignalGroupMediaType OBJECT-TYPE
	    SYNTAX INTEGER {
		audio (1),
		video (2),
		data (3)
	    }
	    ACCESS read-only
	    STATUS mandatory
	    DESCRIPTION
	    " The media type for this call "
	    ::= { accSignalGroupMediaEntry 3 }
	accSignalGroupMediaCodecType OBJECT-TYPE
	    SYNTAX INTEGER {
		g-711 (1),
		sx7300 (2),
		g-723-1m (3),
		g-722 (4),
		fax-g3 (5),
		g-729a (6),
		g-726 (7),
		g-723-1a (8)
	    }
	    ACCESS read-only
	    STATUS mandatory
	    DESCRIPTION
	    " The codec type for this call "
	    ::= { accSignalGroupMediaEntry 4 }
	accSignalGroupMediaPayldType OBJECT-TYPE
	    SYNTAX INTEGER {
		udp (1),
		rtp (2),
		tcp (3)
	    }
	    ACCESS read-only
	    STATUS mandatory
	    DESCRIPTION
	    " The payload type for this call "
	    ::= { accSignalGroupMediaEntry 5 }
	accSignalGroupMediaPayldTos OBJECT-TYPE
	    SYNTAX INTEGER {
		normal (1),
		low-delay (2)
	    }
	    ACCESS read-only
	    STATUS mandatory
	    DESCRIPTION
	    " The type of service used for this call "
	    ::= { accSignalGroupMediaEntry 6 }
	accSignalGroupMediaFrameSize OBJECT-TYPE
	    SYNTAX INTEGER
	    ACCESS read-only
	    STATUS mandatory
	    DESCRIPTION
	    " The frame size used for this call "
	    ::= { accSignalGroupMediaEntry 7 }
	accSignalGroupMediaIpAddress OBJECT-TYPE
	    SYNTAX OCTET STRING
	    ACCESS read-only
	    STATUS mandatory
	    DESCRIPTION
	    " The peer IP address for the media stream of this call "
	    ::= { accSignalGroupMediaEntry 8 }
	accSignalGroupMediaUdpPort OBJECT-TYPE
	    SYNTAX INTEGER
	    ACCESS read-only
	    STATUS mandatory
	    DESCRIPTION
	    " The peer UDP port for the media stream of this call "
	    ::= { accSignalGroupMediaEntry 9 }
	accSignalGroupMediaSilSupr OBJECT-TYPE
	    SYNTAX INTEGER {
		enabled (1),
		disabled (2)
	    }
	    ACCESS read-only
	    STATUS mandatory
	    DESCRIPTION
	    " The status of silence suppression for this call "
	    ::= { accSignalGroupMediaEntry 10 }
	accSignalGroupMediaDtmfSupr OBJECT-TYPE
	    SYNTAX INTEGER {
		enabled (1),
		disabled (2)
	    }
	    ACCESS read-only
	    STATUS mandatory
	    DESCRIPTION
	    " The status of DTMF suppression for this call "
	    ::= { accSignalGroupMediaEntry 11 }
	accSignalGroupMediaXmitSupr OBJECT-TYPE
	    SYNTAX INTEGER {
		enabled (1),
		disabled (2)
	    }
	    ACCESS read-only
	    STATUS mandatory
	    DESCRIPTION
	    " The status of receive suppression for this call "
	    ::= { accSignalGroupMediaEntry 12 }
	accSignalGroupMediaRecvSupr OBJECT-TYPE
	    SYNTAX INTEGER {
		enabled (1),
		disabled (2)
	    }
	    ACCESS read-only
	    STATUS mandatory
	    DESCRIPTION
	    " The status of transmit suppression for this call "
	    ::= { accSignalGroupMediaEntry 13 }
	accSignalGroupMediaEchoSupr OBJECT-TYPE
	    SYNTAX INTEGER {
		enabled (1),
		disabled (2)
	    }
	    ACCESS read-only
	    STATUS mandatory
	    DESCRIPTION
	    " The status of echo suppression for this call "
	    ::= { accSignalGroupMediaEntry 14 }
-- DL2 signaling Group
    accDl2 	OBJECT IDENTIFIER ::= { accBRG 70 }
        -- First a branch for system level objects
        accDl2Sys	OBJECT IDENTIFIER ::= { accDl2 1 }
	    accDl2SysCICBase	OBJECT-TYPE	
		SYNTAX	INTEGER (0..3600)
		ACCESS	read-write
		STATUS  mandatory
		DESCRIPTION
		  "Base value for DL2 circuit CICs for this system"
		::= { accDl2Sys 1 }
	    accDl2SysEvenTCPPort	OBJECT-TYPE	
		SYNTAX	INTEGER (1..65535)
		ACCESS	read-write
		STATUS  mandatory
		DESCRIPTION
		  "TCP port to use for DL2 signaling for even numbered CICs"
		::= { accDl2Sys 2 }
	    accDl2SysOddTCPPort	OBJECT-TYPE	
		SYNTAX	INTEGER (1..65535)
		ACCESS	read-write
		STATUS  mandatory
		DESCRIPTION
		  "TCP port to use for DL2 signaling for odd numbered CICs"
		::= { accDl2Sys 3 }
	    accDl2SysRetrasnsmitTime	OBJECT-TYPE	
		SYNTAX	INTEGER (4..60)
		ACCESS	read-write
		STATUS  mandatory
		DESCRIPTION
		  "Value in seconds to use for DL2 restransmit timers
		  (T1, T12, T14, T16 & T22)."
		::= { accDl2Sys 4 }
	    accDl2SysCircuitTimeout	OBJECT-TYPE	
		SYNTAX	INTEGER (60..900)
		ACCESS	read-write
		STATUS  mandatory
		DESCRIPTION
		  "Value in seconds to use for DL2 circuit timeout
		  (T5, T13, T15, T17 & T23)."
		::= { accDl2Sys 5 }
	    accDl2SysT7	OBJECT-TYPE	
		SYNTAX	INTEGER (20..30)
		ACCESS	read-write
		STATUS  mandatory
		DESCRIPTION
		  "Value in seconds to use for DL2 T7 timer"
		::= { accDl2Sys 6 }
	    accDl2SysT9	OBJECT-TYPE	
		SYNTAX	INTEGER (60..240)
		ACCESS	read-write
		STATUS  mandatory
		DESCRIPTION
		  "Value in seconds to use for DL2 T9 timer"
		::= { accDl2Sys 7 }
	    accDl2SysTestEvenAddr	OBJECT-TYPE	
		SYNTAX	IpAddress
		ACCESS	read-write
		STATUS  mandatory
		DESCRIPTION
		  "Address to establish back-to-back test DL2 TCP
		  connections with for even CIC signaling channel."
		::= { accDl2Sys 8 }
	    accDl2SysTestOddAddr	OBJECT-TYPE	
		SYNTAX	IpAddress
		ACCESS	read-write
		STATUS  mandatory
		DESCRIPTION
		  "Address to establish back-to-back test DL2 TCP
		  connections with for odd CIC signaling channel."
		::= { accDl2Sys 9 }
	    accDl2SysCompletedCalls	OBJECT-TYPE	
		SYNTAX	Counter
		ACCESS	read-only
		STATUS  mandatory
		DESCRIPTION
		  "Count of calls completed using DL2 signaling."
		::= { accDl2Sys 10 }
	    accDl2SysClearedCalls	OBJECT-TYPE	
		SYNTAX	Counter
		ACCESS	read-only
		STATUS  mandatory
		DESCRIPTION
		  "Count of DL2 signaled calls cleared."
		::= { accDl2Sys 11 }
	    accDl2SysOriginatedCalls	OBJECT-TYPE	
		SYNTAX	Counter
		ACCESS	read-only
		STATUS  mandatory
		DESCRIPTION
		  "Count of calls originated on DL2 signal interfaces."
		::= { accDl2Sys 12 }
	    accDl2SysRoutedCalls	OBJECT-TYPE	
		SYNTAX	Counter
		ACCESS	read-only
		STATUS  mandatory
		DESCRIPTION
		  "Count of DL2 calls originated that have been routed 
		  by the network."
		::= { accDl2Sys 13 }
	    accDl2SysOfferedCalls	OBJECT-TYPE	
		SYNTAX	Counter
		ACCESS	read-only
		STATUS  mandatory
		DESCRIPTION
		  "Count of DL2 calls offered in the incoming direction."
		::= { accDl2Sys 14 }
	    accDl2SysAcceptedCalls	OBJECT-TYPE	
		SYNTAX	Counter
		ACCESS	read-only
		STATUS  mandatory
		DESCRIPTION
		  "Count of DL2 calls offered that have been accepted."
		::= { accDl2Sys 15 }
	    accDl2SysRetransmissions	OBJECT-TYPE	
		SYNTAX	Counter
		ACCESS	read-only
		STATUS  mandatory
		DESCRIPTION
		  "Count of DL2 signaling messages that required
		  retransmission by the signaling protocol becasue the
		  appropriate response was not received within the
		  retransmit period."
		::= { accDl2Sys 16 }
	    accDl2SysTimeouts	OBJECT-TYPE	
		SYNTAX	Counter
		ACCESS	read-only
		STATUS  mandatory
		DESCRIPTION
		  "Count of DL2 circuit timeouts."
		::= { accDl2Sys 17 }
	    accDl2SysUnexpEvents	OBJECT-TYPE	
		SYNTAX	Counter
		ACCESS	read-only
		STATUS  mandatory
		DESCRIPTION
		  "Count of unexpected DL2 signaling messages."
		::= { accDl2Sys 18 }
	    accDl2SysBadMessages	OBJECT-TYPE	
		SYNTAX	Counter
		ACCESS	read-only
		STATUS  mandatory
		DESCRIPTION
		  "Count of unknown DL2 message types reveiced."
		::= { accDl2Sys 19 }
	    accDl2SysBadCICs	OBJECT-TYPE	
		SYNTAX	Counter
		ACCESS	read-only
		STATUS  mandatory
		DESCRIPTION
		  "Count of signaling messages received that contain
		  CICs not configured on this unit."
		::= { accDl2Sys 20 }
	-- End of system level objects
	-- Branch for per-interface objects 
	accDl2InfcTable	OBJECT-TYPE
	    SYNTAX	SEQUENCE OF AccDl2InfcEntry
	    ACCESS	not-accessible
	    STATUS	mandatory
	    DESCRIPTION
	      " DL2 interface table containing parameter and status
		information for each DL2 interface on this router."
	    ::= { accDl2 2 }
	accDl2InfcEntry	OBJECT-TYPE
	    SYNTAX	AccDl2InfcEntry
	    ACCESS      not-accessible
	    STATUS      mandatory
    	    DESCRIPTION
	      " Configuration and status objects for a particular
		DL2 interface."
	    INDEX { accDl2InfcIndex }
	    ::= { accDl2InfcTable 1 }
	AccDl2InfcEntry	::= SEQUENCE {
	    accDl2InfcIndex		INTEGER,
	    accDl2InfcAdminStatus	INTEGER,
	    accDl2InfcCDNG    		INTEGER,
	    accDl2InfcCICBase		INTEGER,
	    accDl2InfcMsgLvl     	INTEGER
	    }
	    accDl2InfcIndex		OBJECT-TYPE
		SYNTAX	INTEGER
		ACCESS	read-only
		STATUS	mandatory
		DESCRIPTION
		  "ifIndex for this DL2 interface."
		::= { accDl2InfcEntry 1 }
	    accDl2InfcAdminStatus		OBJECT-TYPE
		SYNTAX	INTEGER {
		    enabled(1),
		    disabled(2),
		    drained(3)
		    }
		ACCESS	read-write
		STATUS	mandatory
		DESCRIPTION
		  "Admin status of this DL2 interface."
		::= { accDl2InfcEntry 2 }
	    accDl2InfcCDNG		OBJECT-TYPE
		SYNTAX	INTEGER (0..127)
		ACCESS	read-write
		STATUS	mandatory
		DESCRIPTION
		  "Called Number Group to use for calls on this interface."
		::= { accDl2InfcEntry 3 }
	    accDl2InfcCICBase		OBJECT-TYPE
		SYNTAX	INTEGER (0..4064)
		ACCESS	read-write
		STATUS	mandatory
		DESCRIPTION
		  "CIC base to use for circuits on this interface."
		::= { accDl2InfcEntry 4 }
	    accDl2InfcMsgLvl	OBJECT-TYPE
		SYNTAX	INTEGER(1..7)
		ACCESS	read-write
		STATUS	mandatory
		DESCRIPTION
		  "Maintainance message level."
		::= { accDl2InfcEntry 5 }
	-- End of Branch for per-interface DL2 objects 
	-- Branch for per-circuit objects 
	accDl2CrctTable	OBJECT-TYPE
	    SYNTAX	SEQUENCE OF AccDl2CrctEntry
	    ACCESS	not-accessible
	    STATUS	mandatory
	    DESCRIPTION
	      " DL2 circuit table containing parameter and status
		information for each DL2 circuit on this router."
	    ::= { accDl2 3 }
	accDl2CrctEntry	OBJECT-TYPE
	    SYNTAX	AccDl2CrctEntry
	    ACCESS      not-accessible
	    STATUS      mandatory
    	    DESCRIPTION
	      " Configuration and status objects for a particular
		DL2 circuit."
	    INDEX { accDl2CrctIndex }
	    ::= { accDl2CrctTable 1 }
	AccDl2CrctEntry	::= SEQUENCE {
	    accDl2CrctIndex		INTEGER,
	    accDl2CrctInfc		INTEGER,
	    accDl2CrctTimeslot 		INTEGER,
	    accDl2CrctStatus		INTEGER,
	    accDl2CrctState     	INTEGER
	    }
	    accDl2CrctIndex		OBJECT-TYPE
		SYNTAX	INTEGER
		ACCESS	read-only
		STATUS	mandatory
		DESCRIPTION
		  "CIC for this DL2 circuit."
		::= { accDl2CrctEntry 1 }
	    accDl2CrctInfc		OBJECT-TYPE
		SYNTAX	INTEGER 
		ACCESS	read-only
		STATUS	mandatory
		DESCRIPTION
		  "ifIndex of interface this circuit is on."
		::= { accDl2CrctEntry 2 }
	    accDl2CrctTimeslot		OBJECT-TYPE
		SYNTAX	INTEGER
		ACCESS	read-only
		STATUS	mandatory
		DESCRIPTION
		  "Timeslot this circuit is on within the DL2 interface."
		::= { accDl2CrctEntry 3 }
	    accDl2CrctStatus		OBJECT-TYPE
		SYNTAX	INTEGER {
			blocked(1),
			unblocked(2),
			reset(3)
			}
		ACCESS	read-write
		STATUS	mandatory
		DESCRIPTION
		  "Status of this circuit."
		::= { accDl2CrctEntry 4 }
	    accDl2CrctState	OBJECT-TYPE
		SYNTAX	INTEGER {
			active (1),
			idle (2)
			}
		ACCESS	read-only
		STATUS	mandatory
		DESCRIPTION
		  "Indicates whether this circuit currently bears a call."
		::= { accDl2CrctEntry 5 }
	-- End of Branch for per-circuit DL2 objects 
	-- Branch for per-call objects 
	accDl2CallTable	OBJECT-TYPE
	    SYNTAX	SEQUENCE OF AccDl2CallEntry
	    ACCESS	not-accessible
	    STATUS	mandatory
	    DESCRIPTION
	      " DL2 call table containing parameter and status
		information for each current DL2 call on this router."
	    ::= { accDl2 4 }
	accDl2CallEntry	OBJECT-TYPE
	    SYNTAX	AccDl2CallEntry
	    ACCESS      not-accessible
	    STATUS      mandatory
    	    DESCRIPTION
	      " Status objects for a particular DL2 call."
	    INDEX { accDl2CallIndex }
	    ::= { accDl2CallTable 1 }
	AccDl2CallEntry	::= SEQUENCE {
	    accDl2CallIndex		INTEGER,
	    accDl2CallInfc		INTEGER,
	    accDl2CallTimeslot 		INTEGER,
	    accDl2CallEndpoint 		INTEGER,
	    accDl2CallType		INTEGER,
	    accDl2CallDirection		INTEGER,
	    accDl2CallAddress		OCTET STRING,
	    accDl2CallState     	INTEGER,
	    accDl2CallDuration     	TimeTicks
	    }
	    accDl2CallIndex		OBJECT-TYPE
		SYNTAX	INTEGER
		ACCESS	read-only
		STATUS	mandatory
		DESCRIPTION
		  "CIC this call is established over."
		::= { accDl2CallEntry 1 }
	    accDl2CallInfc		OBJECT-TYPE
		SYNTAX	INTEGER 
		ACCESS	read-only
		STATUS	mandatory
		DESCRIPTION
		  "ifIndex of interface this call is on."
		::= { accDl2CallEntry 2 }
	    accDl2CallTimeslot		OBJECT-TYPE
		SYNTAX	INTEGER
		ACCESS	read-only
		STATUS	mandatory
		DESCRIPTION
		  "Timeslot this call is on within the DL2 interface."
		::= { accDl2CallEntry 3 }
	    accDl2CallEndpoint		OBJECT-TYPE
		SYNTAX	INTEGER
		ACCESS	read-write
		STATUS	mandatory
		DESCRIPTION
		  "ifIndex of the endpoint used to terminate this call."
		::= { accDl2CallEntry 4 }
	    accDl2CallType	OBJECT-TYPE
		SYNTAX	INTEGER {
			data (1),
			audio (2),
			voice (3)
			}
		ACCESS	read-only
		STATUS	mandatory
		DESCRIPTION
		  "Information transfer type for this call."
		::= { accDl2CallEntry 5 }
	    accDl2CallDirection	OBJECT-TYPE
		SYNTAX	INTEGER {
			incoming (1),
			outgoing (2)
			}
		ACCESS	read-only
		STATUS	mandatory
		DESCRIPTION
		  "Direction of call."
		::= { accDl2CallEntry 6 }
	    accDl2CallAddress		OBJECT-TYPE
		SYNTAX	OCTET STRING 
		ACCESS	read-only
		STATUS	mandatory
		DESCRIPTION
		  "Remote address for this call."
		::= { accDl2CallEntry 7 }
	    accDl2CallState		OBJECT-TYPE
		SYNTAX	INTEGER {
			incoming(1),
			outgoing(2),
			routing(3),
			active(4),
			releasing(5)
			}
		ACCESS	read-only
		STATUS	mandatory
		DESCRIPTION
		  "State the signaling manager is in for this call."
		::= { accDl2CallEntry 8 }
	    accDl2CallDuration		OBJECT-TYPE
		SYNTAX	TimeTicks
		ACCESS	read-only
		STATUS	mandatory
		DESCRIPTION
		  "Amount of time this call has been active."
		::= { accDl2CallEntry 9 }
	-- End of Branch for per-call DL2 objects 
    -- End of Branch for DL2 signaling objects
-- START CFG_TRAP_ENHANCEMENTS
-- Dm Traps Branch Enterprise
      accDmTraps OBJECT IDENTIFIER      ::= { accDialMgmt 3 }
        accDmTrapMsg     OBJECT-TYPE
        SYNTAX          DisplayString
        ACCESS          read-only
        STATUS          mandatory
        DESCRIPTION
        " Enterprise Trap Message for Dm"
      ::= { accDmTraps 1 }
-- END CFG_TRAP_ENHANCEMENTS

        accDmT7Trap TRAP-TYPE
        ENTERPRISE   accDmTraps 
        VARIABLES  { accDmTrapMsg ,
                      accTrapLogSeqNum}
        DESCRIPTION
                "On receiving a CON message from AXE, stops T7, and 
		forwards the connect indication  to CM. This is indicated 
		by this trap.
SEVERITY-DEFAULT: Warning 
EVENTTYPE-DEFAULT: 10 
ADDITIONAL-TEXT-VARIABLES: { accTrapLogSeqNum,accDmTrapMsg }
PCAUSE-DEFAULT: 46 " 
 
        ::= 1
        accDmT9Trap TRAP-TYPE
        ENTERPRISE   accDmTraps 
        VARIABLES  { accDmTrapMsg ,
                      accTrapLogSeqNum}
        DESCRIPTION
                "On expiration of T9, sends REL message to AXE, 
		Releases Conf. to CM, and starts T1 and T5. This is 
		the communicated by this trap.
SEVERITY-DEFAULT: Warning 
EVENTTYPE-DEFAULT: 10 
ADDITIONAL-TEXT-VARIABLES: { accTrapLogSeqNum,accDmTrapMsg }
PCAUSE-DEFAULT: 46 " 
 
        ::= 2
        accDmT5Trap TRAP-TYPE
        ENTERPRISE   accDmTraps 
        VARIABLES  { accDmTrapMsg ,
                      accTrapLogSeqNum}
        DESCRIPTION
                "On expiration of T5, stops T1, sends RSC to AXE.  
		Sends Release Conf. to CM, sets call out of order.  
		Starts T16 and T17. This is the sequence which causes 
		this trap.
SEVERITY-DEFAULT: Warning 
EVENTTYPE-DEFAULT: 10 
ADDITIONAL-TEXT-VARIABLES: { accTrapLogSeqNum,accDmTrapMsg }
PCAUSE-DEFAULT: 46 " 
 
        ::= 3
        accDmT17Trap TRAP-TYPE
        ENTERPRISE   accDmTraps 
        VARIABLES  { accDmTrapMsg ,
                      accTrapLogSeqNum}
        DESCRIPTION
                "On expiration of T17, stops T16, retransmits RSC, 
		starts T17 and generates this trap.
SEVERITY-DEFAULT: Warning 
EVENTTYPE-DEFAULT: 10 
ADDITIONAL-TEXT-VARIABLES: { accTrapLogSeqNum,accDmTrapMsg }
PCAUSE-DEFAULT: 46 " 
 
        ::= 4
        accDmCmStaleCallCntxtTrap TRAP-TYPE
        ENTERPRISE   accDmTraps 
        VARIABLES  { accDmTrapMsg ,
                      accTrapLogSeqNum}
        DESCRIPTION
                "This trap is generated indicating that CM has sent 
		a stale call context.
SEVERITY-DEFAULT: Warning 
EVENTTYPE-DEFAULT: 10 
ADDITIONAL-TEXT-VARIABLES: { accTrapLogSeqNum,accDmTrapMsg }
PCAUSE-DEFAULT: 46 " 
 
        ::= 5
        accDmCallCicTrap TRAP-TYPE
        ENTERPRISE   accDmTraps 
        VARIABLES  { accDmTrapMsg ,
                      accTrapLogSeqNum}
        DESCRIPTION
                "If the call received on a CIC whose state is Out 
		of Service, then this trap is generated.
SEVERITY-DEFAULT: Minor 
EVENTTYPE-DEFAULT: 10 
ADDITIONAL-TEXT-VARIABLES: { accTrapLogSeqNum,accDmTrapMsg }
PCAUSE-DEFAULT: 56 " 
 
        ::= 6
        accDmIamTrap TRAP-TYPE
        ENTERPRISE   accDmTraps 
        VARIABLES  { accDmTrapMsg ,
                      accTrapLogSeqNum}
        DESCRIPTION
                "We have received an IAM on a CIC that is already 
		processing a call, then it is ignored. The trap informs 
		the same.
SEVERITY-DEFAULT: Warning 
EVENTTYPE-DEFAULT: 10 
ADDITIONAL-TEXT-VARIABLES: { accTrapLogSeqNum,accDmTrapMsg }
PCAUSE-DEFAULT: 4 " 
 
        ::= 7
        accDmInvMessTypeTrap TRAP-TYPE
        ENTERPRISE   accDmTraps 
        VARIABLES  { accDmTrapMsg ,
                      accTrapLogSeqNum}
        DESCRIPTION
                "Invalid Message <messageType> 
SEVERITY-DEFAULT: Warning 
EVENTTYPE-DEFAULT: 10 
ADDITIONAL-TEXT-VARIABLES: { accTrapLogSeqNum,accDmTrapMsg }
PCAUSE-DEFAULT: 46 " 
 
        ::= 8
        accDmIamToAxeTrap TRAP-TYPE
        ENTERPRISE   accDmTraps 
        VARIABLES  { accDmTrapMsg ,
                      accTrapLogSeqNum}
        DESCRIPTION
                "Unable to send an IAM message to AXE 
SEVERITY-DEFAULT: Warning 
EVENTTYPE-DEFAULT: 10 
ADDITIONAL-TEXT-VARIABLES: { accTrapLogSeqNum,accDmTrapMsg }
PCAUSE-DEFAULT: 46 " 
 
        ::= 9
        accDmBCBAllocTrap TRAP-TYPE
        ENTERPRISE   accDmTraps 
        VARIABLES  { accDmTrapMsg ,
                      accTrapLogSeqNum}
        DESCRIPTION
                "Can't allocate blocking control block due 
		to memory shortage.
SEVERITY-DEFAULT: Minor 
EVENTTYPE-DEFAULT: 10 
ADDITIONAL-TEXT-VARIABLES: { accTrapLogSeqNum,accDmTrapMsg }
PCAUSE-DEFAULT: 32 " 
 
        ::= 10
        accDmInvUbaTrap TRAP-TYPE
        ENTERPRISE   accDmTraps 
        VARIABLES  { accDmTrapMsg ,
                      accTrapLogSeqNum}
        DESCRIPTION
                "Invalid UBA.
SEVERITY-DEFAULT: Warning 
EVENTTYPE-DEFAULT: 10 
ADDITIONAL-TEXT-VARIABLES: { accTrapLogSeqNum,accDmTrapMsg }
PCAUSE-DEFAULT: 46 " 
 
        ::= 11
        accDmCcbTrap TRAP-TYPE
        ENTERPRISE   accDmTraps 
        VARIABLES  { accDmTrapMsg ,
                      accTrapLogSeqNum}
        DESCRIPTION
                "dl2_startTimer: CCB not present 
SEVERITY-DEFAULT: Minor 
EVENTTYPE-DEFAULT: 10 
ADDITIONAL-TEXT-VARIABLES: { accTrapLogSeqNum,accDmTrapMsg }
PCAUSE-DEFAULT: 56 " 
 
        ::= 12
        accDmBcbTrap TRAP-TYPE
        ENTERPRISE   accDmTraps 
        VARIABLES  { accDmTrapMsg ,
                      accTrapLogSeqNum}
        DESCRIPTION
                "dl2_startTimer: BCB not present 
SEVERITY-DEFAULT: Minor 
EVENTTYPE-DEFAULT: 10 
ADDITIONAL-TEXT-VARIABLES: { accTrapLogSeqNum,accDmTrapMsg }
PCAUSE-DEFAULT: 56 " 
 
        ::= 13
        accDmInvTmrIdTrap TRAP-TYPE
        ENTERPRISE   accDmTraps 
        VARIABLES  { accDmTrapMsg ,
                      accTrapLogSeqNum}
        DESCRIPTION
                "dl2_startTimer: Invalid timer ID 
SEVERITY-DEFAULT: Warning 
EVENTTYPE-DEFAULT: 10 
ADDITIONAL-TEXT-VARIABLES: { accTrapLogSeqNum,accDmTrapMsg }
PCAUSE-DEFAULT: 46 " 
 
        ::= 14
        accDmStopTmrCCBTrap TRAP-TYPE
        ENTERPRISE   accDmTraps 
        VARIABLES  { accDmTrapMsg ,
                      accTrapLogSeqNum}
        DESCRIPTION
                "dl2_stopTimer: CCB not present 
SEVERITY-DEFAULT: Minor 
EVENTTYPE-DEFAULT: 10 
ADDITIONAL-TEXT-VARIABLES: { accTrapLogSeqNum,accDmTrapMsg }
PCAUSE-DEFAULT: 56 " 
 
        ::= 15
       accDmStopTmrBCBTrap TRAP-TYPE
       ENTERPRISE   accDmTraps 
       VARIABLES  { accDmTrapMsg ,
                     accTrapLogSeqNum}
       DESCRIPTION
                "dl2_stopTimer: BCB not present 
SEVERITY-DEFAULT: Minor 
EVENTTYPE-DEFAULT: 10 
ADDITIONAL-TEXT-VARIABLES: { accTrapLogSeqNum,accDmTrapMsg }
PCAUSE-DEFAULT: 56 " 
 
        ::= 16
        accDmInvStopTmrIdTrap TRAP-TYPE
        ENTERPRISE   accDmTraps 
        VARIABLES  { accDmTrapMsg ,
                      accTrapLogSeqNum}
        DESCRIPTION
                "dl2_stopTimer: Invalid TimerId 
SEVERITY-DEFAULT: Warning 
EVENTTYPE-DEFAULT: 10 
ADDITIONAL-TEXT-VARIABLES: { accTrapLogSeqNum,accDmTrapMsg }
PCAUSE-DEFAULT: 46 " 
 
        ::= 17
        accDmNonTestCallTrap TRAP-TYPE
        ENTERPRISE   accDmTraps 
        VARIABLES  { accDmTrapMsg ,
                      accTrapLogSeqNum}
        DESCRIPTION
                "Non-Test Call Rejected 
SEVERITY-DEFAULT: Warning 
EVENTTYPE-DEFAULT: 2 
ADDITIONAL-TEXT-VARIABLES: { accTrapLogSeqNum,accDmTrapMsg }
PCAUSE-DEFAULT: 4 " 
 
        ::= 18
        accDmT13Trap TRAP-TYPE
        ENTERPRISE   accDmTraps 
        VARIABLES  { accDmTrapMsg ,
                      accTrapLogSeqNum}
        DESCRIPTION
                "T13 Expired - Giving Up 
SEVERITY-DEFAULT: Warning 
EVENTTYPE-DEFAULT: 2 
ADDITIONAL-TEXT-VARIABLES: { accTrapLogSeqNum,accDmTrapMsg }
PCAUSE-DEFAULT: 166 " 
 
        ::= 19
        accDmT15Trap TRAP-TYPE
        ENTERPRISE   accDmTraps 
        VARIABLES  { accDmTrapMsg ,
                      accTrapLogSeqNum}
        DESCRIPTION
                "T15 Expired - Giving Up 
SEVERITY-DEFAULT: Warning 
EVENTTYPE-DEFAULT: 2 
ADDITIONAL-TEXT-VARIABLES: { accTrapLogSeqNum,accDmTrapMsg }
PCAUSE-DEFAULT: 166 " 
 
        ::= 20
        accDmCbAllocTrap TRAP-TYPE
        ENTERPRISE   accDmTraps 
        VARIABLES  { accDmTrapMsg ,
                      accTrapLogSeqNum}
        DESCRIPTION
                "Failed to allocate control block 
SEVERITY-DEFAULT: Minor 
EVENTTYPE-DEFAULT: 10 
ADDITIONAL-TEXT-VARIABLES: { accTrapLogSeqNum,accDmTrapMsg }
PCAUSE-DEFAULT: 46 " 
 
        ::= 21
        accDmMblkTrap TRAP-TYPE
        ENTERPRISE   accDmTraps 
        VARIABLES  { accDmTrapMsg ,
                      accTrapLogSeqNum}
        DESCRIPTION
                "cant get mblk 
SEVERITY-DEFAULT: Minor 
EVENTTYPE-DEFAULT: 10 
ADDITIONAL-TEXT-VARIABLES: { accTrapLogSeqNum,accDmTrapMsg }
PCAUSE-DEFAULT: 56 " 
 
        ::= 22
        accDmFsmEvntTrap TRAP-TYPE
        ENTERPRISE   accDmTraps 
        VARIABLES  { accDmTrapMsg ,
                      accTrapLogSeqNum}
        DESCRIPTION
                "Illegal FSM event 
SEVERITY-DEFAULT: Minor 
EVENTTYPE-DEFAULT: 10 
ADDITIONAL-TEXT-VARIABLES: { accTrapLogSeqNum,accDmTrapMsg }
PCAUSE-DEFAULT: 46 " 
 
        ::= 23
        accDmCicBaseRangeTrap TRAP-TYPE
        ENTERPRISE   accDmTraps 
        VARIABLES  { accDmTrapMsg ,
                      accTrapLogSeqNum}
        DESCRIPTION
                " 
SEVERITY-DEFAULT: Minor 
EVENTTYPE-DEFAULT: 10 
ADDITIONAL-TEXT-VARIABLES: { accTrapLogSeqNum,accDmTrapMsg }
PCAUSE-DEFAULT: 46 " 
 
        ::= 24  
        accDmDisblLineGrpTrap TRAP-TYPE
        ENTERPRISE   accDmTraps 
        VARIABLES  { accDmTrapMsg,
			accLineGroupIndex,
			accLineGroupAdminStatus ,
    accTrapLogSeqNum}
        DESCRIPTION
                " Disable line group before deleting media preference entry 
SEVERITY-DEFAULT: Warning 
EVENTTYPE-DEFAULT: 10 
ADDITIONAL-TEXT-VARIABLES: { accTrapLogSeqNum,accDmTrapMsg }
PCAUSE-DEFAULT: 7 " 
 
        ::= 25
        accDmLGrpNmsModifyTrap TRAP-TYPE
        ENTERPRISE   accDmTraps 
        VARIABLES  { accDmTrapMsg,
                        accLineGroupIndex,
                        accLineGroupAdminStatus ,
                         accTrapLogSeqNum}
        DESCRIPTION
                " Disable line group before modifying media preference entry 
SEVERITY-DEFAULT: Warning 
EVENTTYPE-DEFAULT: 10 
ADDITIONAL-TEXT-VARIABLES: { accTrapLogSeqNum,accDmTrapMsg }
PCAUSE-DEFAULT: 7 " 
 
        ::= 26
        accDmLGrpLicRangeTrap TRAP-TYPE
        ENTERPRISE   accDmTraps 
        VARIABLES  { accDmTrapMsg,
                        accLineGroupBaseLic,
                        accLineGroupLineCount ,
                         accTrapLogSeqNum}
        DESCRIPTION
                " LIC range is not available 
SEVERITY-DEFAULT: Minor 
EVENTTYPE-DEFAULT: 10 
ADDITIONAL-TEXT-VARIABLES: { accTrapLogSeqNum,accDmTrapMsg }
PCAUSE-DEFAULT: 56 " 
 
        ::= 27
        accDmLGrpNoLinesTrap TRAP-TYPE
        ENTERPRISE   accDmTraps 
        VARIABLES  { accDmTrapMsg,
                        accLineGroupIndex,
                        accLineGroupAdminStatus,
                        accLineGroupOperStatus ,
                         accTrapLogSeqNum}
        DESCRIPTION
                " Unable to activate line group : no lines assigned 
SEVERITY-DEFAULT: Minor 
EVENTTYPE-DEFAULT: 10 
ADDITIONAL-TEXT-VARIABLES: { accTrapLogSeqNum,accDmTrapMsg }
PCAUSE-DEFAULT: 56 " 
 
        ::= 28
        accDmLGrpDuplicatesTrap TRAP-TYPE
        ENTERPRISE   accDmTraps 
        VARIABLES  { accDmTrapMsg,
                        accLineGroupIndex,
                        accLineGroupAdminStatus,
                        accLineGroupOperStatus ,
                         accTrapLogSeqNum}
        DESCRIPTION
                " Unable to activate line group : duplicate media entries 
SEVERITY-DEFAULT: Minor 
EVENTTYPE-DEFAULT: 10 
ADDITIONAL-TEXT-VARIABLES: { accTrapLogSeqNum,accDmTrapMsg }
PCAUSE-DEFAULT: 253 " 
 
        ::= 29
        accDmLGrpNoSgrpTrap TRAP-TYPE
        ENTERPRISE   accDmTraps 
        VARIABLES  { accDmTrapMsg,
                        accLineGroupIndex,
                        accLineGroupAdminStatus,
                        accLineGroupOperStatus ,
                         accTrapLogSeqNum}
        DESCRIPTION
                " Unable to activate line group : no signaling group 
SEVERITY-DEFAULT: Minor 
EVENTTYPE-DEFAULT: 10 
ADDITIONAL-TEXT-VARIABLES: { accTrapLogSeqNum,accDmTrapMsg }
PCAUSE-DEFAULT: 56 " 
 
        ::= 30
        accDmSGrpNmsDeleteTrap TRAP-TYPE
        ENTERPRISE   accDmTraps 
        VARIABLES  { accDmTrapMsg,
                        accSignalGroupIndex,
                        accSignalGroupAdminStatus ,
                         accTrapLogSeqNum}
        DESCRIPTION
                " Disable signaling group before deleting 
SEVERITY-DEFAULT: Warning 
EVENTTYPE-DEFAULT: 10 
ADDITIONAL-TEXT-VARIABLES: { accTrapLogSeqNum,accDmTrapMsg }
PCAUSE-DEFAULT: 7 "  
 
        ::= 31
        accDmSGrpNmsModifyTrap TRAP-TYPE
        ENTERPRISE   accDmTraps 
        VARIABLES  { accDmTrapMsg,
                        accSignalGroupIndex,
                        accSignalGroupAdminStatus ,
                         accTrapLogSeqNum}
        DESCRIPTION
                " Disable signaling group before modifying 
SEVERITY-DEFAULT: Warning 
EVENTTYPE-DEFAULT: 10 
ADDITIONAL-TEXT-VARIABLES: { accTrapLogSeqNum,accDmTrapMsg }
PCAUSE-DEFAULT: 7 " 
 
        ::= 32
        accDmSGrpEstablishedTrap TRAP-TYPE
        ENTERPRISE   accDmTraps 
        VARIABLES  { accDmTrapMsg,
                        accSignalGroupIndex,
                        accSignalGroupAdminStatus, 
                        accSignalGroupOperStatus ,
                         accTrapLogSeqNum}
        DESCRIPTION
                " Signaling channel established 
SEVERITY-DEFAULT: Warning 
EVENTTYPE-DEFAULT: 2 
ADDITIONAL-TEXT-VARIABLES: { accTrapLogSeqNum,accDmTrapMsg }
PCAUSE-DEFAULT: 4 " 
 
        ::= 33
        accDmSGrpReleasedTrap TRAP-TYPE
        ENTERPRISE   accDmTraps 
        VARIABLES  { accDmTrapMsg,
                        accSignalGroupIndex,
                        accSignalGroupAdminStatus, 
                        accSignalGroupOperStatus ,
                         accTrapLogSeqNum}
        DESCRIPTION
                " Signaling channel released 
SEVERITY-DEFAULT: Warning 
EVENTTYPE-DEFAULT: 2 
ADDITIONAL-TEXT-VARIABLES: { accTrapLogSeqNum,accDmTrapMsg }
PCAUSE-DEFAULT: 4 " 
 
        ::= 34
        accDmSGrpDrainTmoutTrap TRAP-TYPE
        ENTERPRISE   accDmTraps 
        VARIABLES  { accDmTrapMsg,
                        accSignalGroupIndex,
                        accSignalGroupAdminStatus, 
                        accSignalGroupOperStatus ,
                         accTrapLogSeqNum}
        DESCRIPTION
                " Drain time-out, releasing signaling channel 
SEVERITY-DEFAULT: Warning 
EVENTTYPE-DEFAULT: 2 
ADDITIONAL-TEXT-VARIABLES: { accTrapLogSeqNum,accDmTrapMsg }
PCAUSE-DEFAULT: 166 " 
 
        ::= 35
        accDmVdmStaleCmTrap TRAP-TYPE
        ENTERPRISE   accDmTraps 
        VARIABLES  { accDmTrapMsg ,
                      accTrapLogSeqNum}
        DESCRIPTION
                " Stale call context from CM 
SEVERITY-DEFAULT: Minor 
EVENTTYPE-DEFAULT: 10 
ADDITIONAL-TEXT-VARIABLES: { accTrapLogSeqNum,accDmTrapMsg }
PCAUSE-DEFAULT: 46 " 
 
        ::= 36
        accDmVdmBadCmMsgTrap TRAP-TYPE
        ENTERPRISE   accDmTraps 
        VARIABLES  { accDmTrapMsg ,
                      accTrapLogSeqNum}
        DESCRIPTION
                " Unexpected event in state 
SEVERITY-DEFAULT: Minor 
EVENTTYPE-DEFAULT: 10 
ADDITIONAL-TEXT-VARIABLES: { accTrapLogSeqNum,accDmTrapMsg }
PCAUSE-DEFAULT: 46 " 
 
        ::= 37
        accDmStaleDiaConTrap TRAP-TYPE
        ENTERPRISE   accDmTraps 
        VARIABLES  { accDmTrapMsg ,
                      accTrapLogSeqNum}
        DESCRIPTION
                "Stale dial context for event 
SEVERITY-DEFAULT: Minor 
EVENTTYPE-DEFAULT: 10 
ADDITIONAL-TEXT-VARIABLES: { accTrapLogSeqNum,accDmTrapMsg }
PCAUSE-DEFAULT: 46 " 
 
        ::= 38
        accDmOutGngCallRfsdTrap TRAP-TYPE
        ENTERPRISE   accDmTraps 
        VARIABLES  { accDmTrapMsg ,
                      accTrapLogSeqNum}
        DESCRIPTION
                "Outgoing call refused
SEVERITY-DEFAULT: Minor 
EVENTTYPE-DEFAULT: 2 
ADDITIONAL-TEXT-VARIABLES: { accTrapLogSeqNum,accDmTrapMsg }
PCAUSE-DEFAULT: 4 " 
 
        ::= 39
        accDmCallRfsdTrap TRAP-TYPE
        ENTERPRISE   accDmTraps 
        VARIABLES  { accDmTrapMsg ,
                      accTrapLogSeqNum}
        DESCRIPTION
                "Call refused (momentary resource shortage) 
SEVERITY-DEFAULT: Minor 
EVENTTYPE-DEFAULT: 2 
ADDITIONAL-TEXT-VARIABLES: { accTrapLogSeqNum,accDmTrapMsg }
PCAUSE-DEFAULT: 4 " 
 
        ::= 40
        accDmUnblRgstrTrap TRAP-TYPE
        ENTERPRISE   accDmTraps 
        VARIABLES  { accDmTrapMsg ,
                      accTrapLogSeqNum}
        DESCRIPTION
                "Unable to register 
SEVERITY-DEFAULT: Minor 
EVENTTYPE-DEFAULT: 10 
ADDITIONAL-TEXT-VARIABLES: { accTrapLogSeqNum,accDmTrapMsg }
PCAUSE-DEFAULT: 46 " 
 
        ::= 41
        accDmMnyPSTNIFsTrap TRAP-TYPE
        ENTERPRISE   accDmTraps 
        VARIABLES  { accDmTrapMsg ,
                      accTrapLogSeqNum}
        DESCRIPTION
                "Too many PSTN interfaces installed 
SEVERITY-DEFAULT: Minor 
EVENTTYPE-DEFAULT: 10 
ADDITIONAL-TEXT-VARIABLES: { accTrapLogSeqNum,accDmTrapMsg }
PCAUSE-DEFAULT: 43 " 
 
        ::= 42
        accDmR2regInitTrap TRAP-TYPE
        ENTERPRISE   accDmTraps 
        VARIABLES  { accDmTrapMsg ,
                      accTrapLogSeqNum}
        DESCRIPTION
                "Problem initializing r2reg fsm 
SEVERITY-DEFAULT: Minor 
EVENTTYPE-DEFAULT: 10 
ADDITIONAL-TEXT-VARIABLES: { accTrapLogSeqNum,accDmTrapMsg }
PCAUSE-DEFAULT: 46 " 
 
        ::= 43
        accDmDTMFInitTrap TRAP-TYPE
        ENTERPRISE   accDmTraps 
        VARIABLES  { accDmTrapMsg ,
                      accTrapLogSeqNum}
        DESCRIPTION
                "Problem initializing DTMF reg fsm 
SEVERITY-DEFAULT: Minor 
EVENTTYPE-DEFAULT: 10 
ADDITIONAL-TEXT-VARIABLES: { accTrapLogSeqNum,accDmTrapMsg }
PCAUSE-DEFAULT: 46 " 
 
        ::= 44
        accDmCallCtxInit TRAP-TYPE
        ENTERPRISE   accDmTraps 
        VARIABLES  { accDmTrapMsg ,
                      accTrapLogSeqNum}
        DESCRIPTION
                "Can't find callctx to init 
SEVERITY-DEFAULT: Minor 
EVENTTYPE-DEFAULT: 10 
ADDITIONAL-TEXT-VARIABLES: { accTrapLogSeqNum,accDmTrapMsg }
PCAUSE-DEFAULT: 56 " 
 
        ::= 45
        accDmPulDiaTrap TRAP-TYPE
        ENTERPRISE   accDmTraps 
        VARIABLES  { accDmTrapMsg ,
                      accTrapLogSeqNum}
        DESCRIPTION
                "Pulse dialing outbound call addr info 
SEVERITY-DEFAULT: Warning 
EVENTTYPE-DEFAULT: 10 
ADDITIONAL-TEXT-VARIABLES: { accTrapLogSeqNum,accDmTrapMsg }
PCAUSE-DEFAULT: 0 " 
 
        ::= 46
        accDmDSPDiaTrap TRAP-TYPE
        ENTERPRISE   accDmTraps 
        VARIABLES  { accDmTrapMsg ,
                      accTrapLogSeqNum}
        DESCRIPTION
                "DSP dialing outbound call addr 
SEVERITY-DEFAULT: Warning 
EVENTTYPE-DEFAULT: 10 
ADDITIONAL-TEXT-VARIABLES: { accTrapLogSeqNum,accDmTrapMsg }
PCAUSE-DEFAULT: 0 " 
 
        ::= 47
        accDmTestCallActvTrap TRAP-TYPE
        ENTERPRISE   accDmTraps 
        VARIABLES  { accDmTrapMsg ,
                      accTrapLogSeqNum}
        DESCRIPTION
                "Test call already active on this port 
SEVERITY-DEFAULT: Warning 
EVENTTYPE-DEFAULT: 2 
ADDITIONAL-TEXT-VARIABLES: { accTrapLogSeqNum,accDmTrapMsg }
PCAUSE-DEFAULT: 4 " 
 
        ::= 48
        accDmNoTestCallTrap TRAP-TYPE
        ENTERPRISE   accDmTraps 
        VARIABLES  { accDmTrapMsg ,
                      accTrapLogSeqNum}
        DESCRIPTION
                "No test call to clear on this port 
SEVERITY-DEFAULT: Warning 
EVENTTYPE-DEFAULT: 10 
ADDITIONAL-TEXT-VARIABLES: { accTrapLogSeqNum,accDmTrapMsg }
PCAUSE-DEFAULT: 56 " 
 
        ::= 49
        accDmNoActvCallTrap TRAP-TYPE
        ENTERPRISE   accDmTraps 
        VARIABLES  { accDmTrapMsg ,
                      accTrapLogSeqNum}
        DESCRIPTION
                "No active call on this endpoint 
SEVERITY-DEFAULT: Warning 
EVENTTYPE-DEFAULT: 10 
ADDITIONAL-TEXT-VARIABLES: { accTrapLogSeqNum,accDmTrapMsg }
PCAUSE-DEFAULT: 56 " 
 
        ::= 50
        accDmNoPdngCallTrap TRAP-TYPE
        ENTERPRISE   accDmTraps 
        VARIABLES  { accDmTrapMsg ,
                      accTrapLogSeqNum}
        DESCRIPTION
                "No pending call to answer on this port 
SEVERITY-DEFAULT: Warning 
EVENTTYPE-DEFAULT: 10 
ADDITIONAL-TEXT-VARIABLES: { accTrapLogSeqNum,accDmTrapMsg }
PCAUSE-DEFAULT: 56 " 
 
        ::= 51
        accDmNoDiaParamTrap TRAP-TYPE
        ENTERPRISE   accDmTraps 
        VARIABLES  { accDmTrapMsg ,
                      accTrapLogSeqNum}
        DESCRIPTION
                "No dial parameters for this endpoint 
SEVERITY-DEFAULT: Warning 
EVENTTYPE-DEFAULT: 10 
ADDITIONAL-TEXT-VARIABLES: { accTrapLogSeqNum,accDmTrapMsg }
PCAUSE-DEFAULT: 56 " 
 
        ::= 52
        accDmISDNDiaInvdTrap TRAP-TYPE
        ENTERPRISE   accDmTraps 
        VARIABLES  { accDmTrapMsg ,
                      accTrapLogSeqNum}
        DESCRIPTION
                "ISDN dial procedure is invalid for this port
SEVERITY-DEFAULT: Minor 
EVENTTYPE-DEFAULT: 10 
ADDITIONAL-TEXT-VARIABLES: { accTrapLogSeqNum,accDmTrapMsg }
PCAUSE-DEFAULT: 46 " 
 
        ::= 53
        accDmPSTNDiaInvldTrap TRAP-TYPE
        ENTERPRISE   accDmTraps 
        VARIABLES  { accDmTrapMsg ,
                      accTrapLogSeqNum}
        DESCRIPTION
                "PSTN dial procedure is invalid for this port
SEVERITY-DEFAULT: Minor 
EVENTTYPE-DEFAULT: 10 
ADDITIONAL-TEXT-VARIABLES: { accTrapLogSeqNum,accDmTrapMsg }
PCAUSE-DEFAULT: 46 " 
 
        ::= 54
        accDmTstngNotSpprtdTrap TRAP-TYPE
        ENTERPRISE   accDmTraps 
        VARIABLES  { accDmTrapMsg ,
                      accTrapLogSeqNum}
        DESCRIPTION
                "Testing not supported for configured dial procedure
SEVERITY-DEFAULT: Warning 
EVENTTYPE-DEFAULT: 10 
ADDITIONAL-TEXT-VARIABLES: { accTrapLogSeqNum,accDmTrapMsg }
PCAUSE-DEFAULT: 7 " 
 
        ::= 55
        accDmCmndSpprtNonISDNTrap TRAP-TYPE
        ENTERPRISE   accDmTraps 
        VARIABLES  { accDmTrapMsg ,
                      accTrapLogSeqNum}
        DESCRIPTION
                "Command not supported for non-ISDN interfaces
SEVERITY-DEFAULT: Warning 
EVENTTYPE-DEFAULT: 10 
ADDITIONAL-TEXT-VARIABLES: { accTrapLogSeqNum,accDmTrapMsg }
PCAUSE-DEFAULT: 7 " 
 
        ::= 56
        accDmNotValdFITTrap TRAP-TYPE
        ENTERPRISE   accDmTraps 
        VARIABLES  { accDmTrapMsg ,
                      accTrapLogSeqNum}
        DESCRIPTION
                "This port is not a valid FIT endpoint
SEVERITY-DEFAULT: Warning 
EVENTTYPE-DEFAULT: 10 
ADDITIONAL-TEXT-VARIABLES: { accTrapLogSeqNum,accDmTrapMsg }
PCAUSE-DEFAULT: 7 " 
 
        ::= 57
        accDmResrcShortageTrap TRAP-TYPE
        ENTERPRISE   accDmTraps 
        VARIABLES  { accDmTrapMsg ,
                      accTrapLogSeqNum}
        DESCRIPTION
                " Indicates that there is a resource shortage.
SEVERITY-DEFAULT: Minor 
EVENTTYPE-DEFAULT: 10 
ADDITIONAL-TEXT-VARIABLES: { accTrapLogSeqNum,accDmTrapMsg }
PCAUSE-DEFAULT: 43 " 
 
        ::= 58
        accDmPrvntReinitPpIndTrap TRAP-TYPE
        ENTERPRISE   accDmTraps 
        VARIABLES  { accDmTrapMsg ,
                      accTrapLogSeqNum}
        DESCRIPTION
                " LDSP has already been allocated for this call.
SEVERITY-DEFAULT: Warning 
EVENTTYPE-DEFAULT: 10 
ADDITIONAL-TEXT-VARIABLES: { accTrapLogSeqNum,accDmTrapMsg }
PCAUSE-DEFAULT: 46 " 
 
        ::= 59
        accDmLdspAllocTrap TRAP-TYPE
        ENTERPRISE   accDmTraps 
        VARIABLES  { accDmTrapMsg ,
                      accTrapLogSeqNum}
        DESCRIPTION
                " LDSP alloc failed.
SEVERITY-DEFAULT: Minor 
EVENTTYPE-DEFAULT: 10 
ADDITIONAL-TEXT-VARIABLES: { accTrapLogSeqNum,accDmTrapMsg }
PCAUSE-DEFAULT: 46 " 
 
        ::= 60
        accDmRegFsmTrap TRAP-TYPE
        ENTERPRISE   accDmTraps 
        VARIABLES  { accDmTrapMsg ,
                      accTrapLogSeqNum}
        DESCRIPTION
                " 
SEVERITY-DEFAULT: Minor 
EVENTTYPE-DEFAULT: 10 
ADDITIONAL-TEXT-VARIABLES: { accTrapLogSeqNum,accDmTrapMsg }
PCAUSE-DEFAULT: 46 " 
 
        ::= 61
END
