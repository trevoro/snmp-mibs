NETWORK-ALCHEMY-CONFIG-MIB DEFINITIONS ::= BEGIN

-- Title:		    Network Alchemy Crypto Cluster MIB
-- Date:		    September 6, 2000
-- Author:		    Jonny Larson (jlarson@network-alchemy.com)
-- Location:		    Santa Cruz, CA

IMPORTS  netalModules, config       FROM NETAL-SMI
         MODULE-IDENTITY, OBJECT-TYPE, NOTIFICATION-TYPE, IpAddress
             FROM SNMPv2-SMI;

networkAlchemyConfigMIB MODULE-IDENTITY
    LAST-UPDATED "0003140000Z"
    ORGANIZATION "Network Alchemy, Inc."
    CONTACT-INFO 
		 "	Network Alchemy
			Customer Support

		  Postal: 1538 Pacific Av.
			Santa Cruz, CA 95060
			USA
	          E-Mail: snmp-contact@network-alchemy.com"

    DESCRIPTION "Crypto Cluster Configuration MIB module."
    REVISION "0008300000Z"
    DESCRIPTION "Placeholder for the HP Open View NNM SNMP browser."
    ::= { netalModules 6 }

configDirtyBit OBJECT-TYPE
    SYNTAX        INTEGER  { no(0), yes(1) }
    MAX-ACCESS    read-only
    STATUS        current
    DESCRIPTION   "Says whether the configuration has been changed via a set
		  on any of the writable SNMP variables."
    ::= { config 1 }

configCommit OBJECT-TYPE
    SYNTAX      INTEGER  { no(0), yes(1) }
    MAX-ACCESS	read-write
    STATUS      current
    DESCRIPTION "When an SNMP management station sets (changes) a configuration parameter
		 via an SNMP set operation, the SNMP agent code will set a dirt bit.  The
		 management station can then submit a set operation on this configCommit
		 variable to write the configuration to flash, thereby committing the
		 change.

		 Performing a read on this variable will return the value of the config
		 dirty bit."
    ::= { config 2 }

END
