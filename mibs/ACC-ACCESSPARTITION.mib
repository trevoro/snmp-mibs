ACC-ACCESSPARTITION DEFINITIONS ::= BEGIN

    IMPORTS
	 OBJECT-TYPE, IpAddress, Gauge, Counter, TimeTicks FROM RFC1155-SMI
	 TRAP-TYPE FROM RFC-1215
        accTrapLogSeqNum FROM ACC-SYSTEM
	accBRG, DisplayString, RowStatus, IfIndex, SmdsAddress
             FROM ACC-MIB;

-- Access Partition Group
    accAccessPartition OBJECT IDENTIFIER ::= { accBRG 63 }
	-- The Access Partition Parameter Group
	-- Configuration parameters, operational parameters and statistics
	-- maintained for each Access Partition.
	accAccessPartitionTable OBJECT-TYPE
	    SYNTAX SEQUENCE OF AccAccessPartitionEntry
	    ACCESS not-accessible
	    STATUS mandatory
	    DESCRIPTION
	       "The Access Partition Table"
	    ::= { accAccessPartition 1 }
	accAccessPartitionEntry OBJECT-TYPE
	    SYNTAX AccAccessPartitionEntry
	    ACCESS not-accessible
	    STATUS mandatory
	    DESCRIPTION
	       "An entry in the Access Partition Table"
	    INDEX { accAccessPartitionName }
	    ::= { accAccessPartitionTable 1 }
	AccAccessPartitionEntry ::= SEQUENCE {
	    accAccessPartitionName        	DisplayString,
	    accAccessPartitionCustomerId  	DisplayString,
	    accAccessPartitionAdminState  	INTEGER,
	    accAccessPartitionMsgLevel    	INTEGER,
	    accAccessPartitionPortLimit   	INTEGER,
	    accAccessPartitionIpAddrPri   	IpAddress,
	    accAccessPartitionIpAddrSec   	IpAddress,
	    accAccessPartitionRoutePolicy 	INTEGER,
	    accAccessPartitionBusyCount   	Gauge,
	    accAccessPartitionNumAccepts   	Counter,
	    accAccessPartitionNumRejects   	Counter,
	    accAccessPartitionNumActive   	Gauge,
	    accAccessPartitionAuthFails    	Counter,
	    accAccessPartitionConnectTime 	TimeTicks,
	    accAccessPartitionInOctets    	Counter,
	    accAccessPartitionOutOctets   	Counter,
	    accAccessPartitionInPackets   	Counter,
	    accAccessPartitionOutPackets  	Counter,
	    accAccessPartitionEntryStatus 	INTEGER,
	    accAccessPartitionNumDiscards  	Counter,
	    accAccessPartitionNumDirects   	Counter,
	    accAccessPartitionNumFunnels   	Counter,
	    accAccessPartitionProxyServer 	DisplayString,
	    accAccessPartitionIngrFiltState 	INTEGER,
	    accAccessPartitionDnsServPri   	IpAddress,
	    accAccessPartitionDnsServSec   	IpAddress,
	    accAccessPartitionNbnsServPri   	IpAddress,
	    accAccessPartitionNbnsServSec   	IpAddress,
            accAccessPartitionIpPool            DisplayString,
	    accAccessPartitionProxyIpPool 	DisplayString,
	    accAccessPartitionProxyIpRouter 	DisplayString
	}
	accAccessPartitionName OBJECT-TYPE
	    SYNTAX DisplayString -- (SIZE (1..16))
	    ACCESS read-only
	    STATUS mandatory
	    DESCRIPTION
	       "The name of the access partition.  This name serves as the 
	        handle for accessing information in the Access Partition 
	        Table."
	    ::= { accAccessPartitionEntry 1 }
	accAccessPartitionCustomerId OBJECT-TYPE
	    SYNTAX DisplayString -- (SIZE (0..32))
	    ACCESS read-write
	    STATUS mandatory
	    DESCRIPTION
	       "An arbitrary string describing the customer to whom this 
	        access partition is assigned."
	    ::= { accAccessPartitionEntry 2 }
	accAccessPartitionAdminState OBJECT-TYPE
	    SYNTAX INTEGER {
		enabled(1),
		disabled(2),
		drained(3)
	    }
	    ACCESS read-write
	    STATUS mandatory
	    DESCRIPTION
	       "The administrative state of this partition.  If the 
	        administrative state is set to disabled, no new connections 
	        will be allowed using this access partition, and all existing 
	        connections using the partition will be terminated.  If the 
	        administrative state is set to drained, no new connections 
	        will be accepted, but existing connections will be 
	        maintained."
	    ::= { accAccessPartitionEntry 3 }
	accAccessPartitionMsgLevel OBJECT-TYPE
	    SYNTAX INTEGER (1..7)
	    ACCESS read-write
	    STATUS mandatory
	    DESCRIPTION
	       "The current severity level of trap messages that may be 
	        generated regarding events associated with this access 
	        partition.  Only trap messages whose serverity level is less 
	        than or equal to the current setting of this object will be 
	        displayed."
	    ::= { accAccessPartitionEntry 4 }
	accAccessPartitionPortLimit OBJECT-TYPE
	    SYNTAX INTEGER (0..65535)
	    ACCESS read-write
	    STATUS mandatory
	    DESCRIPTION
	       "The maximum number of physical port connections that 
	        may be simultaneously served by this access partition.  Each 
	        physical link in a multilink bundle counts as one connection.  
	        A value of zero indicates there is no limit to the number of 
	        simultaneous connections."
	    ::= { accAccessPartitionEntry 5 }
	accAccessPartitionIpAddrPri OBJECT-TYPE
	    SYNTAX IpAddress
	    ACCESS read-write
	    STATUS mandatory
	    DESCRIPTION
	       "The IP address of the primary home gateway into the 
	        customer's network.  All incoming packets from user 
	        connections belonging to this partition will be routed to the 
	        IP home gateway address instead of the destination address 
	        in the IP packet header."
	    ::= { accAccessPartitionEntry 6 }
	accAccessPartitionIpAddrSec OBJECT-TYPE
	    SYNTAX IpAddress
	    ACCESS read-write
	    STATUS mandatory
	    DESCRIPTION
	       "The IP address of the secondary home gateway into the 
	        customer's network.  If the primary home gateway is not 
	        reachable, the secondary home gateway will be used in its 
	        place."
	    ::= { accAccessPartitionEntry 7 }
	accAccessPartitionRoutePolicy OBJECT-TYPE
	    SYNTAX INTEGER {
		funnel(1),
		direct(2)
	    }
	    ACCESS read-write
	    STATUS mandatory
	    DESCRIPTION
	       "The route policy for this access partition.  If the route 
	        policy is 'funnel' (the default), then all incoming user 
	        packets will be routed (i.e., funneled) to the IP home 
	        gateway.  If the route policy is 'route', then destinations that 
	        are reachable via another port belonging to the same access 
	        partition will be routed to directly."
	    ::= { accAccessPartitionEntry 8 }
	accAccessPartitionBusyCount OBJECT-TYPE
	    SYNTAX Gauge
	    ACCESS read-only
	    STATUS mandatory
	    DESCRIPTION
	       "The number of internal resources currently bound to this 
	        access partition.  If the busy count is non-zero, the access 
	        partition entry cannot be removed."
	    ::= { accAccessPartitionEntry 9 }
	accAccessPartitionNumAccepts OBJECT-TYPE
	    SYNTAX Counter
	    ACCESS read-only
	    STATUS mandatory
	    DESCRIPTION
	       "The number of incoming or outgoing connection requests 
	        accepted for this access partition."
	    ::= { accAccessPartitionEntry 10 }
	accAccessPartitionNumRejects OBJECT-TYPE
	    SYNTAX Counter
	    ACCESS read-only
	    STATUS mandatory
	    DESCRIPTION
	       "The number of incoming or outgoing connection requests 
	        rejected for this access partition."
	    ::= { accAccessPartitionEntry 11 }
	accAccessPartitionNumActive OBJECT-TYPE
	    SYNTAX Gauge
	    ACCESS read-only
	    STATUS mandatory
	    DESCRIPTION
	       "The current number of connected physical ports belonging 
	        to this access partition.  Each physical link in a multilink 
	        bundle counts as one connection."
	    ::= { accAccessPartitionEntry 12 }
	accAccessPartitionAuthFails OBJECT-TYPE
	    SYNTAX Counter
	    ACCESS read-only
	    STATUS mandatory
	    DESCRIPTION
	       "The number of connection requests rejected due to an 
	        authentication failure."
	    ::= { accAccessPartitionEntry 13 }
	accAccessPartitionConnectTime OBJECT-TYPE
	    SYNTAX TimeTicks
	    ACCESS read-only
	    STATUS mandatory
	    DESCRIPTION
	       "The total amount of connect time accumulated for this 
	        access partition."
	    ::= { accAccessPartitionEntry 14 }
	accAccessPartitionInOctets OBJECT-TYPE
	    SYNTAX Counter
	    ACCESS read-only
	    STATUS mandatory
	    DESCRIPTION
	       "The total number octets input from connections belonging 
	        to this access partition."
	    ::= { accAccessPartitionEntry 15 }
	accAccessPartitionOutOctets OBJECT-TYPE
	    SYNTAX Counter
	    ACCESS read-only
	    STATUS mandatory
	    DESCRIPTION
	       "The total number octets output to connections belonging to 
	        this access partition."
	    ::= { accAccessPartitionEntry 16 }
	accAccessPartitionInPackets OBJECT-TYPE
	    SYNTAX Counter
	    ACCESS read-only
	    STATUS mandatory
	    DESCRIPTION
	       "The total number packets input from connections belonging 
	        to this access partition."
	    ::= { accAccessPartitionEntry 17 }
	accAccessPartitionOutPackets OBJECT-TYPE
	    SYNTAX Counter
	    ACCESS read-only
	    STATUS mandatory
	    DESCRIPTION
	       "The total number packets output to connections belonging 
	        to this access partition."
	    ::= { accAccessPartitionEntry 18 }
	accAccessPartitionEntryStatus OBJECT-TYPE
	    SYNTAX INTEGER {
		add(1),
		delete(2)
	    }
	    ACCESS read-write
	    STATUS mandatory
	    DESCRIPTION
	       "The modification status of this access partition entry.  
	        Setting the status to add causes a new entry to be added.  
	        Setting the status to deleete causes an existing entry to be 
	        deleted."
	    ::= { accAccessPartitionEntry 19 }
	accAccessPartitionNumDiscards OBJECT-TYPE
	    SYNTAX Counter
	    ACCESS read-only
	    STATUS mandatory
	    DESCRIPTION
	       "The total number of packets discarded because of an 
	        unreachable destination or IP home gateway."
	    ::= { accAccessPartitionEntry 20 }
	accAccessPartitionNumDirects OBJECT-TYPE
	    SYNTAX Counter
	    ACCESS read-only
	    STATUS mandatory
	    DESCRIPTION
	       "The total number packets routed directly to the normal IP 
	        destination address."
	    ::= { accAccessPartitionEntry 21 }
	accAccessPartitionNumFunnels OBJECT-TYPE
	    SYNTAX Counter
	    ACCESS read-only
	    STATUS mandatory
	    DESCRIPTION
	       "The total number packets funneled to the primary or 
	        secondary IP home gateway address."
	    ::= { accAccessPartitionEntry 22 }
	accAccessPartitionProxyServer OBJECT-TYPE
	    SYNTAX DisplayString -- (SIZE (0..16))
	    ACCESS read-write
	    STATUS mandatory
	    DESCRIPTION
	       "The name of an access partition that will provide the 
                Radius authenticationand accounting feature on behalf 
		of this partition.
	        If no proxy server is configured, only Radius 
	        accounting and authentication servers associated with this 
	        access partition will be used."
	    ::= { accAccessPartitionEntry 23 }
	accAccessPartitionIngrFiltState OBJECT-TYPE
	    SYNTAX INTEGER {
			    disabled(1),
			    enabled(2)
		   	   }
	    ACCESS read-write
	    STATUS obsolete
	    DESCRIPTION
	       "The administrative status of ingress filtering on this
	       partition"
	    ::= { accAccessPartitionEntry 24 }
	accAccessPartitionDnsServPri OBJECT-TYPE
	    SYNTAX IpAddress
	    ACCESS read-write
	    STATUS obsolete
	    DESCRIPTION
	       "The IP address of the primary DNS server of the 
	        customer's network." 
	    ::= { accAccessPartitionEntry 25 }
	accAccessPartitionDnsServSec OBJECT-TYPE
	    SYNTAX IpAddress
	    ACCESS read-write
	    STATUS obsolete
	    DESCRIPTION
	       "The IP address of the secondary DNS server of the 
	        customer's network." 
	    ::= { accAccessPartitionEntry 26 }
	accAccessPartitionNbnsServPri OBJECT-TYPE
	    SYNTAX IpAddress
	    ACCESS read-write
	    STATUS obsolete
	    DESCRIPTION
	       "The IP address of the primary NBNS server of the 
	        customer's network." 
	    ::= { accAccessPartitionEntry 27 }
	accAccessPartitionNbnsServSec OBJECT-TYPE
	    SYNTAX IpAddress
	    ACCESS read-write
	    STATUS obsolete
	    DESCRIPTION
	       "The IP address of the secondary NBNS server of the 
	        customer's network." 
	    ::= { accAccessPartitionEntry 28 }
        accAccessPartitionIpPool OBJECT-TYPE
            SYNTAX DisplayString --(Size(1..16))
            ACCESS read-write
            STATUS obsolete
            DESCRIPTION
               "The access partition name to which the ip address pool
                is assigned."
            ::= { accAccessPartitionEntry 29 }
        accAccessPartitionProxyIpPool OBJECT-TYPE
            SYNTAX DisplayString -- (SIZE (0..16))
            ACCESS read-write
            STATUS mandatory
            DESCRIPTION
               "The name of an access partition that will provide the Ip
		pool management on behalf of this partition. 
		If no proxy ip pool is configured, only the ip pools 
                associated with this access partition will be used."
            ::= { accAccessPartitionEntry 30 }
        accAccessPartitionProxyIpRouter OBJECT-TYPE 
            SYNTAX DisplayString -- (SIZE (0..16)) 
            ACCESS read-write 
            STATUS mandatory 
            DESCRIPTION    
               "The name of an access partition that will provide the Ip 
                routing on behalf of this partition. 
                If no proxy ip router is configured, only the ip routes 
                associated with this access partition will be used."
            ::= { accAccessPartitionEntry 31 } 
	-- The Access Partition Port Group
	-- Access partition information maintained on a per-port basis.
	accAccessPartitionPortTable OBJECT-TYPE
	    SYNTAX SEQUENCE OF AccAccessPartitionPortEntry
	    ACCESS not-accessible
	    STATUS mandatory
	    DESCRIPTION
	       "The Access Partition Port Table"
	    ::= { accAccessPartition 2 }
	accAccessPartitionPortEntry OBJECT-TYPE
	    SYNTAX AccAccessPartitionPortEntry
	    ACCESS not-accessible
	    STATUS mandatory
	    DESCRIPTION
	       "An entry in the Access Partition Port Table"
            INDEX { accAccessPartitionIfIndex }
	    ::= { accAccessPartitionPortTable 1 }
	AccAccessPartitionPortEntry ::= SEQUENCE {
	    accAccessPartitionIfIndex        INTEGER,
	    accAccessPartitionConfiguredName DisplayString,
	    accAccessPartitionActiveName     DisplayString,
	    accAccessPartitionActiveCustomer DisplayString
	}
	accAccessPartitionIfIndex OBJECT-TYPE
	    SYNTAX INTEGER (1..'7fffffff'h)
	    ACCESS read-only
	    STATUS mandatory
	    DESCRIPTION
	       "The interface index of the physical port associated with this 
	        entry."
	    ::= { accAccessPartitionPortEntry 1 }
	accAccessPartitionConfiguredName OBJECT-TYPE
	    SYNTAX DisplayString -- (SIZE (0..16))
	    ACCESS read-only
	    STATUS mandatory
	    DESCRIPTION
	       "The name of the access partition configured for this 
	        physical port.  The access partition name is acquired from 
	        the service profile manually configured for the same 
	        physical port."
	    ::= { accAccessPartitionPortEntry 2 }
	accAccessPartitionActiveName OBJECT-TYPE
	    SYNTAX DisplayString -- (SIZE (0..16))
	    ACCESS read-only
	    STATUS mandatory
	    DESCRIPTION
	       "The name of the access partition currently active for this 
	        physical port.  The access partition name is acquired from 
	        the service profile dynamically assigned to the physical 
	        port."
	    ::= { accAccessPartitionPortEntry 3 }
	accAccessPartitionActiveCustomer OBJECT-TYPE
	    SYNTAX DisplayString -- (SIZE (0..32))
	    ACCESS read-only
	    STATUS mandatory
	    DESCRIPTION
	       "The customer identifier string obtained from the active 
	        access partition."
	    ::= { accAccessPartitionPortEntry 4 }
-- START CFG_TRAP_ENHANCEMENTS
accAccessPartitionTraps OBJECT IDENTIFIER ::= { accAccessPartition 3 }
        accAccessPartitionTrapMsg OBJECT-TYPE
            SYNTAX DisplayString 
            ACCESS read-only
            STATUS mandatory
            DESCRIPTION
		"Access Partition Trap Message "
            ::= { accAccessPartitionTraps 1 }
-- END MANILA_NEW

        accAPDelApTrap TRAP-TYPE
        ENTERPRISE   accAccessPartitionTraps 
        VARIABLES  { accAccessPartitionTrapMsg,
                     accAccessPartitionName ,
                      accTrapLogSeqNum}
        DESCRIPTION 
		"This trap indicates  that the access partition to be 
		deleted is still in use.  Probably, some users are 
		still connected and the access partition is active.
SEVERITY-DEFAULT: Warning 
EVENTTYPE-DEFAULT: 10 
ADDITIONAL-TEXT-VARIABLES: { accTrapLogSeqNum,accAccessPartitionTrapMsg }
PCAUSE-DEFAULT: 7 " 
 
	::= 1
END
