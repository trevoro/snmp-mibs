Nortel-Magellan-Passport-FrTraceRcvrMIB
DEFINITIONS ::= BEGIN



IMPORTS

      OBJECT-TYPE
   FROM RFC-1212

      passportMIBs
   FROM Nortel-Magellan-Passport-UsefulDefinitionsMIB

      RowPointer,
      DisplayString,
      StorageType,
      RowStatus,
      Integer32,
      Unsigned32
   FROM Nortel-Magellan-Passport-StandardTextualConventionsMIB

      AsciiString,
      Hex,
      NonReplicated,
      HexString,
      EnterpriseDateAndTime,
      DigitString
   FROM Nortel-Magellan-Passport-TextualConventionsMIB

      traceSessionIndex,
      traceRcvrIndex,
      traceSession,
      traceIndex,
      traceRcvr
   FROM Nortel-Magellan-Passport-TraceBaseMIB;




-- LAST-UPDATED   "9903220000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FrTraceRcvr Enterprise MIB."

frTraceRcvrMIB OBJECT IDENTIFIER ::= { passportMIBs 139 }










-- Trace Rcvr/<string> FrameRelay
-- This component identifies the access method used by the receiver of 
-- the trace data as Frame Relay.

traceRcvrFr OBJECT IDENTIFIER ::= { traceRcvr 3 }



traceRcvrFrRowStatusTable OBJECT-TYPE
   SYNTAX     SEQUENCE OF TraceRcvrFrRowStatusEntry
   ACCESS     not-accessible
   STATUS     mandatory
   DESCRIPTION
     "This entry controls the addition and deletion of 
      traceRcvrFr components."
::= { traceRcvrFr 1 }

traceRcvrFrRowStatusEntry OBJECT-TYPE
   SYNTAX     TraceRcvrFrRowStatusEntry
   ACCESS     not-accessible
   STATUS     mandatory
   DESCRIPTION
     "A single entry in the table represents a single 
      traceRcvrFr component."
   INDEX {
      traceIndex,
      traceRcvrIndex,
      traceRcvrFrIndex }
::= { traceRcvrFrRowStatusTable 1 }

TraceRcvrFrRowStatusEntry ::= SEQUENCE {
   traceRcvrFrRowStatus
      RowStatus,
   traceRcvrFrComponentName
      DisplayString,
   traceRcvrFrStorageType
      StorageType,
   traceRcvrFrIndex
      NonReplicated }

traceRcvrFrRowStatus OBJECT-TYPE
   SYNTAX     RowStatus 
   ACCESS     read-write
   STATUS     mandatory
   DESCRIPTION
     "This variable is used as the basis for SNMP naming of
      traceRcvrFr components.
      These components can be added and deleted."
::= { traceRcvrFrRowStatusEntry 1 }

traceRcvrFrComponentName OBJECT-TYPE
   SYNTAX     DisplayString 
   ACCESS     read-only
   STATUS     mandatory
   DESCRIPTION
     "This variable provides the component's string name for
      use with the ASCII Console Interface"
::= { traceRcvrFrRowStatusEntry 2 }

traceRcvrFrStorageType OBJECT-TYPE
   SYNTAX     StorageType 
   ACCESS     read-only
   STATUS     mandatory
   DESCRIPTION
     "This variable represents the storage type value for the
      traceRcvrFr tables."
::= { traceRcvrFrRowStatusEntry 4 }

traceRcvrFrIndex OBJECT-TYPE
   SYNTAX     NonReplicated 
   ACCESS     not-accessible
   STATUS     mandatory
   DESCRIPTION
     "This variable represents the index for the traceRcvrFr tables."
::= { traceRcvrFrRowStatusEntry 10 }


-- Trace Rcvr/<string> Fr DataNetworkAddress
-- This component defines the calling end of the trace connection. It 
-- includes the set of attributes which apply to a Vc connection to a 
-- Frame Relay trace receiver.

traceRcvrFrDna OBJECT IDENTIFIER ::= { traceRcvrFr 2 }



traceRcvrFrDnaRowStatusTable OBJECT-TYPE
   SYNTAX     SEQUENCE OF TraceRcvrFrDnaRowStatusEntry
   ACCESS     not-accessible
   STATUS     mandatory
   DESCRIPTION
     "This entry controls the addition and deletion of 
      traceRcvrFrDna components."
::= { traceRcvrFrDna 1 }

traceRcvrFrDnaRowStatusEntry OBJECT-TYPE
   SYNTAX     TraceRcvrFrDnaRowStatusEntry
   ACCESS     not-accessible
   STATUS     mandatory
   DESCRIPTION
     "A single entry in the table represents a single 
      traceRcvrFrDna component."
   INDEX {
      traceIndex,
      traceRcvrIndex,
      traceRcvrFrIndex,
      traceRcvrFrDnaIndex }
::= { traceRcvrFrDnaRowStatusTable 1 }

TraceRcvrFrDnaRowStatusEntry ::= SEQUENCE {
   traceRcvrFrDnaRowStatus
      RowStatus,
   traceRcvrFrDnaComponentName
      DisplayString,
   traceRcvrFrDnaStorageType
      StorageType,
   traceRcvrFrDnaIndex
      NonReplicated }

traceRcvrFrDnaRowStatus OBJECT-TYPE
   SYNTAX     RowStatus 
   ACCESS     read-only
   STATUS     mandatory
   DESCRIPTION
     "This variable is used as the basis for SNMP naming of
      traceRcvrFrDna components.
      These components cannot be added nor deleted."
::= { traceRcvrFrDnaRowStatusEntry 1 }

traceRcvrFrDnaComponentName OBJECT-TYPE
   SYNTAX     DisplayString 
   ACCESS     read-only
   STATUS     mandatory
   DESCRIPTION
     "This variable provides the component's string name for
      use with the ASCII Console Interface"
::= { traceRcvrFrDnaRowStatusEntry 2 }

traceRcvrFrDnaStorageType OBJECT-TYPE
   SYNTAX     StorageType 
   ACCESS     read-only
   STATUS     mandatory
   DESCRIPTION
     "This variable represents the storage type value for the
      traceRcvrFrDna tables."
::= { traceRcvrFrDnaRowStatusEntry 4 }

traceRcvrFrDnaIndex OBJECT-TYPE
   SYNTAX     NonReplicated 
   ACCESS     not-accessible
   STATUS     mandatory
   DESCRIPTION
     "This variable represents the index for the traceRcvrFrDna tables."
::= { traceRcvrFrDnaRowStatusEntry 10 }

traceRcvrFrDnaAddressTable OBJECT-TYPE
   SYNTAX     SEQUENCE OF TraceRcvrFrDnaAddressEntry
   ACCESS     not-accessible
   STATUS     mandatory
   DESCRIPTION
     "This group contains attributes common to all Dnas. This group is 
      composed of two attributes which define a Dna. These attributes are 
      used to interpret the format of the address digits."
::= { traceRcvrFrDna 10 }

traceRcvrFrDnaAddressEntry OBJECT-TYPE
   SYNTAX     TraceRcvrFrDnaAddressEntry
   ACCESS     not-accessible
   STATUS     mandatory
   DESCRIPTION
     "An entry in the traceRcvrFrDnaAddressTable."
   INDEX {
      traceIndex,
      traceRcvrIndex,
      traceRcvrFrIndex,
      traceRcvrFrDnaIndex }
::= { traceRcvrFrDnaAddressTable 1 }

TraceRcvrFrDnaAddressEntry ::= SEQUENCE {
   traceRcvrFrDnaNumberingPlanIndicator
      INTEGER,
   traceRcvrFrDnaDataNetworkAddress
      DigitString }

traceRcvrFrDnaNumberingPlanIndicator OBJECT-TYPE
   SYNTAX     INTEGER  {
                 x121(0),
                 e164(1) }
   ACCESS     read-write
   STATUS     mandatory
   DESCRIPTION
     "This attribute specifies the Numbering Plan Indicator (NPI) of the 
      Dna that is entered. The address may belong to an E.164 or X.121 
      plan."
   DEFVAL     { x121 }
::= { traceRcvrFrDnaAddressEntry 1 }

traceRcvrFrDnaDataNetworkAddress OBJECT-TYPE
   SYNTAX     DigitString (SIZE (1..15))
   ACCESS     read-write
   STATUS     mandatory
   DESCRIPTION
     "The Dna attribute contains digits which form a unique identifier for 
      the calling end of the trace connection. Dna digits are selected and 
      assigned by network operators. The maximum Dna length is 15 
      digits."
::= { traceRcvrFrDnaAddressEntry 2 }

traceRcvrFrDnaOutgoingOptionsTable OBJECT-TYPE
   SYNTAX     SEQUENCE OF TraceRcvrFrDnaOutgoingOptionsEntry
   ACCESS     not-accessible
   STATUS     mandatory
   DESCRIPTION
     "This group defines the call options for outgoing calls."
::= { traceRcvrFrDna 11 }

traceRcvrFrDnaOutgoingOptionsEntry OBJECT-TYPE
   SYNTAX     TraceRcvrFrDnaOutgoingOptionsEntry
   ACCESS     not-accessible
   STATUS     mandatory
   DESCRIPTION
     "An entry in the traceRcvrFrDnaOutgoingOptionsTable."
   INDEX {
      traceIndex,
      traceRcvrIndex,
      traceRcvrFrIndex,
      traceRcvrFrDnaIndex }
::= { traceRcvrFrDnaOutgoingOptionsTable 1 }

TraceRcvrFrDnaOutgoingOptionsEntry ::= SEQUENCE {
   traceRcvrFrDnaOutCalls
      INTEGER,
   traceRcvrFrDnaOutDefaultPriority
      INTEGER,
   traceRcvrFrDnaOutIntl
      INTEGER,
   traceRcvrFrDnaOutDefaultPathReliability
      INTEGER,
   traceRcvrFrDnaOutPathReliabilityOverRide
      INTEGER,
   traceRcvrFrDnaOutPathReliabilitySignal
      INTEGER,
   traceRcvrFrDnaOutAccess
      INTEGER }

traceRcvrFrDnaOutCalls OBJECT-TYPE
   SYNTAX     INTEGER  {
                 disallowed(0),
                 allowed(1) }
   ACCESS     read-only
   STATUS     mandatory
   DESCRIPTION
     "This attribute specifies that outgoing calls (from the DTE to the 
      network) can be made using this particular Dna component."
   DEFVAL     { allowed }
::= { traceRcvrFrDnaOutgoingOptionsEntry 1 }

traceRcvrFrDnaOutDefaultPriority OBJECT-TYPE
   SYNTAX     INTEGER  {
                 normal(0),
                 high(1) }
   ACCESS     read-write
   STATUS     mandatory
   DESCRIPTION
     "If this attribute is set to normal, then the default priority for 
      outgoing calls (from the DTE to the network) using this particular 
      Dna is normal priority when the priority is not specified in the call. 
      If this attribute is set to high then the default priority for outgoing 
      calls using this particular Dna is high priority."
   DEFVAL     { high }
::= { traceRcvrFrDnaOutgoingOptionsEntry 7 }

traceRcvrFrDnaOutIntl OBJECT-TYPE
   SYNTAX     INTEGER  {
                 disallowed(0),
                 allowed(1) }
   ACCESS     read-only
   STATUS     mandatory
   DESCRIPTION
     "This attribute specifies that outgoing international calls (from the 
      DTE to the network) can be made using this particular Dna.
      
      This attribute also controls access to another numbering plan, and 
      specifies that cross-numbering plan calls are allowed."
   DEFVAL     { allowed }
::= { traceRcvrFrDnaOutgoingOptionsEntry 8 }

traceRcvrFrDnaOutDefaultPathReliability OBJECT-TYPE
   SYNTAX     INTEGER  {
                 high(0),
                 normal(1) }
   ACCESS     read-only
   STATUS     mandatory
   DESCRIPTION
     "This attribute specifies the default reliability class of routing for all 
      calls (from the DTE to the network) using this particular Dna. The 
      chosen default reliability class of routing normally applies to all 
      packets (including the call packets) travelling into the network.
      A value of high specifies that packets are to be overflowed or 
      retransmitted at various routing levels. Typically high reliability 
      results in duplication and disordering of packets in the network, 
      when errors are detected or during link congestion. The VC handles 
      the duplication and disordering to ensure that packets are delivered 
      to the interface in the proper sequence and without duplication."
   DEFVAL     { high }
::= { traceRcvrFrDnaOutgoingOptionsEntry 14 }

traceRcvrFrDnaOutPathReliabilityOverRide OBJECT-TYPE
   SYNTAX     INTEGER  {
                 no(0),
                 yes(1) }
   ACCESS     read-only
   STATUS     mandatory
   DESCRIPTION
     "This attribute specifies that the called end of the connection will not 
      use the calling end provisioning data for reliability class of routing 
      to override the provisioning data at the called end."
   DEFVAL     { no }
::= { traceRcvrFrDnaOutgoingOptionsEntry 15 }

traceRcvrFrDnaOutPathReliabilitySignal OBJECT-TYPE
   SYNTAX     INTEGER  {
                 disallowed(0),
                 allowed(1) }
   ACCESS     read-only
   STATUS     mandatory
   DESCRIPTION
     "This attribute specifies that reliability routing signaling is not used."
   DEFVAL     { disallowed }
::= { traceRcvrFrDnaOutgoingOptionsEntry 16 }

traceRcvrFrDnaOutAccess OBJECT-TYPE
   SYNTAX     INTEGER  {
                 disallowed(0),
                 allowed(1) }
   ACCESS     read-write
   STATUS     mandatory
   DESCRIPTION
     "This attribute is an extension of the Closed User Group (CUG) 
      facility. If this attribute is set to a value of allowed, it specifies that 
      outgoing calls (from the DTE to the network) to the open (non-
      CUG) part of the network are permitted. It also permits outgoing 
      calls to interfaces that have Incoming Access capabilities. If set to a 
      value of disallowed, then such calls cannot be made using this Dna 
      (the calls will be cleared by the local DCE).
      This attribute corresponds to the ITU-T 'Closed User Group with 
      Outgoing Access' feature."
   DEFVAL     { disallowed }
::= { traceRcvrFrDnaOutgoingOptionsEntry 17 }

traceRcvrFrDnaIncomingOptionsTable OBJECT-TYPE
   SYNTAX     SEQUENCE OF TraceRcvrFrDnaIncomingOptionsEntry
   ACCESS     not-accessible
   STATUS     mandatory
   DESCRIPTION
     "This group defines the call options for incoming calls."
::= { traceRcvrFrDna 12 }

traceRcvrFrDnaIncomingOptionsEntry OBJECT-TYPE
   SYNTAX     TraceRcvrFrDnaIncomingOptionsEntry
   ACCESS     not-accessible
   STATUS     mandatory
   DESCRIPTION
     "An entry in the traceRcvrFrDnaIncomingOptionsTable."
   INDEX {
      traceIndex,
      traceRcvrIndex,
      traceRcvrFrIndex,
      traceRcvrFrDnaIndex }
::= { traceRcvrFrDnaIncomingOptionsTable 1 }

TraceRcvrFrDnaIncomingOptionsEntry ::= SEQUENCE {
   traceRcvrFrDnaIncCalls
      INTEGER }

traceRcvrFrDnaIncCalls OBJECT-TYPE
   SYNTAX     INTEGER  {
                 disallowed(0),
                 allowed(1) }
   ACCESS     read-only
   STATUS     mandatory
   DESCRIPTION
     "This attribute specifies that incoming calls (from the network to the 
      DTE) cannot be made to this Dna."
   DEFVAL     { disallowed }
::= { traceRcvrFrDnaIncomingOptionsEntry 1 }

traceRcvrFrDnaCallOptionsTable OBJECT-TYPE
   SYNTAX     SEQUENCE OF TraceRcvrFrDnaCallOptionsEntry
   ACCESS     not-accessible
   STATUS     mandatory
   DESCRIPTION
     "The CallOptions group defines additional options for calls which 
      are not specific to the direction of the call."
::= { traceRcvrFrDna 13 }

traceRcvrFrDnaCallOptionsEntry OBJECT-TYPE
   SYNTAX     TraceRcvrFrDnaCallOptionsEntry
   ACCESS     not-accessible
   STATUS     mandatory
   DESCRIPTION
     "An entry in the traceRcvrFrDnaCallOptionsTable."
   INDEX {
      traceIndex,
      traceRcvrIndex,
      traceRcvrFrIndex,
      traceRcvrFrDnaIndex }
::= { traceRcvrFrDnaCallOptionsTable 1 }

TraceRcvrFrDnaCallOptionsEntry ::= SEQUENCE {
   traceRcvrFrDnaPacketSizes
      OCTET STRING,
   traceRcvrFrDnaDefaultRecvFrmNetworkPacketSize
      INTEGER,
   traceRcvrFrDnaDefaultSendToNetworkPacketSize
      INTEGER,
   traceRcvrFrDnaCugFormat
      INTEGER }

traceRcvrFrDnaPacketSizes OBJECT-TYPE
   SYNTAX     OCTET STRING (SIZE (2))
   ACCESS     read-only
   STATUS     mandatory
   DESCRIPTION
     "This attribute specifies the allowable packet sizes supported for calls 
      using this Dna.

      Description of bits:
      n16(0)
      n32(1)
      n64(2)
      n128(3)
      n256(4)
      n512(5)
      n1024(6)
      n2048(7)
      n4096(8)"
   DEFVAL     { '0100'H }
::= { traceRcvrFrDnaCallOptionsEntry 2 }

traceRcvrFrDnaDefaultRecvFrmNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute specifies the default local receive packet size from 
      network to DTE for calls using this particular Dna."
   DEFVAL     { n2048 }
::= { traceRcvrFrDnaCallOptionsEntry 3 }

traceRcvrFrDnaDefaultSendToNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute specifies the default local send packet size from DTE 
      to network for all calls using this particular Dna."
   DEFVAL     { n2048 }
::= { traceRcvrFrDnaCallOptionsEntry 4 }

traceRcvrFrDnaCugFormat OBJECT-TYPE
   SYNTAX     INTEGER  {
                 basic(0),
                 extended(1) }
   ACCESS     read-only
   STATUS     mandatory
   DESCRIPTION
     "This attribute specifies the format to signal CUG indices as basic or 
      extended. A basic CUG index format is two digits long. An 
      extended CUG index format is four digits long."
   DEFVAL     { basic }
::= { traceRcvrFrDnaCallOptionsEntry 10 }


-- Trace Rcvr/<string> Fr Dna ClosedUserGroup
-- The ClosedUserGroup component defines options associated with a 
-- national or international closed user group identifier. When a Dna is 
-- defined with a Cug, calls to other Dnas which do not have the same 
-- Cug interlockCode defined are refused. When a Dna is not defined 
-- with a Cug, calls to other Dnas which have any Cug interlockCode 
-- defined are refused. The Dna attributes outAccess and incAccess 
-- can override these rules.
-- If this component is present, the Frame Relay interface which 
-- connects to the Frame Relay trace receiver must be provisioned 
-- with the same Cug interlockCode.

traceRcvrFrDnaCug OBJECT IDENTIFIER ::= { traceRcvrFrDna 2 }



traceRcvrFrDnaCugRowStatusTable OBJECT-TYPE
   SYNTAX     SEQUENCE OF TraceRcvrFrDnaCugRowStatusEntry
   ACCESS     not-accessible
   STATUS     mandatory
   DESCRIPTION
     "This entry controls the addition and deletion of 
      traceRcvrFrDnaCug components."
::= { traceRcvrFrDnaCug 1 }

traceRcvrFrDnaCugRowStatusEntry OBJECT-TYPE
   SYNTAX     TraceRcvrFrDnaCugRowStatusEntry
   ACCESS     not-accessible
   STATUS     mandatory
   DESCRIPTION
     "A single entry in the table represents a single 
      traceRcvrFrDnaCug component."
   INDEX {
      traceIndex,
      traceRcvrIndex,
      traceRcvrFrIndex,
      traceRcvrFrDnaIndex,
      traceRcvrFrDnaCugIndex }
::= { traceRcvrFrDnaCugRowStatusTable 1 }

TraceRcvrFrDnaCugRowStatusEntry ::= SEQUENCE {
   traceRcvrFrDnaCugRowStatus
      RowStatus,
   traceRcvrFrDnaCugComponentName
      DisplayString,
   traceRcvrFrDnaCugStorageType
      StorageType,
   traceRcvrFrDnaCugIndex
      Integer32 }

traceRcvrFrDnaCugRowStatus OBJECT-TYPE
   SYNTAX     RowStatus 
   ACCESS     read-write
   STATUS     mandatory
   DESCRIPTION
     "This variable is used as the basis for SNMP naming of
      traceRcvrFrDnaCug components.
      These components can be added and deleted."
::= { traceRcvrFrDnaCugRowStatusEntry 1 }

traceRcvrFrDnaCugComponentName OBJECT-TYPE
   SYNTAX     DisplayString 
   ACCESS     read-only
   STATUS     mandatory
   DESCRIPTION
     "This variable provides the component's string name for
      use with the ASCII Console Interface"
::= { traceRcvrFrDnaCugRowStatusEntry 2 }

traceRcvrFrDnaCugStorageType OBJECT-TYPE
   SYNTAX     StorageType 
   ACCESS     read-only
   STATUS     mandatory
   DESCRIPTION
     "This variable represents the storage type value for the
      traceRcvrFrDnaCug tables."
::= { traceRcvrFrDnaCugRowStatusEntry 4 }

traceRcvrFrDnaCugIndex OBJECT-TYPE
   SYNTAX     Integer32 (1..1)
   ACCESS     not-accessible
   STATUS     mandatory
   DESCRIPTION
     "This variable represents the index for the traceRcvrFrDnaCug tables."
::= { traceRcvrFrDnaCugRowStatusEntry 10 }

traceRcvrFrDnaCugCugOptionsTable OBJECT-TYPE
   SYNTAX     SEQUENCE OF TraceRcvrFrDnaCugCugOptionsEntry
   ACCESS     not-accessible
   STATUS     mandatory
   DESCRIPTION
     "Attributes in this group define ClosedUserGroup options associated 
      with interlockCode. Dnas with the same CUG (interlockCode) can 
      make calls within this group. Various combinations of attributes are 
      defined under this option which permit or prevent calls in the same 
      CUG group."
::= { traceRcvrFrDnaCug 10 }

traceRcvrFrDnaCugCugOptionsEntry OBJECT-TYPE
   SYNTAX     TraceRcvrFrDnaCugCugOptionsEntry
   ACCESS     not-accessible
   STATUS     mandatory
   DESCRIPTION
     "An entry in the traceRcvrFrDnaCugCugOptionsTable."
   INDEX {
      traceIndex,
      traceRcvrIndex,
      traceRcvrFrIndex,
      traceRcvrFrDnaIndex,
      traceRcvrFrDnaCugIndex }
::= { traceRcvrFrDnaCugCugOptionsTable 1 }

TraceRcvrFrDnaCugCugOptionsEntry ::= SEQUENCE {
   traceRcvrFrDnaCugType
      INTEGER,
   traceRcvrFrDnaCugDnic
      DigitString,
   traceRcvrFrDnaCugInterlockCode
      Unsigned32,
   traceRcvrFrDnaCugPreferential
      INTEGER,
   traceRcvrFrDnaCugOutCalls
      INTEGER,
   traceRcvrFrDnaCugIncCalls
      INTEGER,
   traceRcvrFrDnaCugPrivileged
      INTEGER }

traceRcvrFrDnaCugType OBJECT-TYPE
   SYNTAX     INTEGER  {
                 national(0),
                 international(1) }
   ACCESS     read-write
   STATUS     mandatory
   DESCRIPTION
     "This attribute specifies the CUG type as either national or 
      international. A national CUG has significance within the local 
      network only. An international CUG has significance across 
      network boundaries."
   DEFVAL     { national }
::= { traceRcvrFrDnaCugCugOptionsEntry 1 }

traceRcvrFrDnaCugDnic OBJECT-TYPE
   SYNTAX     DigitString (SIZE (4))
   ACCESS     read-write
   STATUS     mandatory
   DESCRIPTION
     "This attribute specifies the Data Network ID Code of the network 
      that is administering the international CUG. This attribute is not 
      used for a national CUG and should be left at its default value.
      The dnic value is not an arbitrary number. It is assigned by 
      international agreement and controlled by ITU-T."
   DEFVAL     { '30303030'H }  -- "0000"
::= { traceRcvrFrDnaCugCugOptionsEntry 2 }

traceRcvrFrDnaCugInterlockCode OBJECT-TYPE
   SYNTAX     Unsigned32 (0..65535)
   ACCESS     read-write
   STATUS     mandatory
   DESCRIPTION
     "This attribute specifies a numeric identifier of a national or 
      international closed user group. It is an arbitrary number. This 
      attribute may also be called CUG in some descriptions. Dnas 
      defined with this number can only make calls to Dnas defined with 
      the same interlockCode."
   DEFVAL     { 0 }
::= { traceRcvrFrDnaCugCugOptionsEntry 3 }

traceRcvrFrDnaCugPreferential OBJECT-TYPE
   SYNTAX     INTEGER  {
                 no(0),
                 yes(1) }
   ACCESS     read-only
   STATUS     mandatory
   DESCRIPTION
     "This attribute specifies that this Cug is to be used on all outgoing 
      calls to the Frame Relay trace receiver."
   DEFVAL     { yes }
::= { traceRcvrFrDnaCugCugOptionsEntry 4 }

traceRcvrFrDnaCugOutCalls OBJECT-TYPE
   SYNTAX     INTEGER  {
                 disallowed(0),
                 allowed(1) }
   ACCESS     read-only
   STATUS     mandatory
   DESCRIPTION
     "This attribute specifies that outgoing calls (from the DTE into the 
      network) can be made using this particular Cug."
   DEFVAL     { allowed }
::= { traceRcvrFrDnaCugCugOptionsEntry 5 }

traceRcvrFrDnaCugIncCalls OBJECT-TYPE
   SYNTAX     INTEGER  {
                 disallowed(0),
                 allowed(1) }
   ACCESS     read-only
   STATUS     mandatory
   DESCRIPTION
     "This attribute specifies that incoming calls (from the network to the 
      DTE) cannot be accepted using this Cug."
   DEFVAL     { disallowed }
::= { traceRcvrFrDnaCugCugOptionsEntry 6 }

traceRcvrFrDnaCugPrivileged OBJECT-TYPE
   SYNTAX     INTEGER  {
                 no(0),
                 yes(1) }
   ACCESS     read-only
   STATUS     mandatory
   DESCRIPTION
     "This attribute specifies that this Cug is privileged. For a call 
      between two closed user group Dnas to connect, at least one Dna 
      must have a privileged Cug."
   DEFVAL     { yes }
::= { traceRcvrFrDnaCugCugOptionsEntry 7 }


-- Trace Rcvr/<string> Fr DirectCall
-- This component defines direct call options for the call to the Frame 
-- Relay trace receiver. The connection is initiated on receipt of a Start 
-- FrUni/n Trace command.

traceRcvrFrDc OBJECT IDENTIFIER ::= { traceRcvrFr 3 }



traceRcvrFrDcRowStatusTable OBJECT-TYPE
   SYNTAX     SEQUENCE OF TraceRcvrFrDcRowStatusEntry
   ACCESS     not-accessible
   STATUS     mandatory
   DESCRIPTION
     "This entry controls the addition and deletion of 
      traceRcvrFrDc components."
::= { traceRcvrFrDc 1 }

traceRcvrFrDcRowStatusEntry OBJECT-TYPE
   SYNTAX     TraceRcvrFrDcRowStatusEntry
   ACCESS     not-accessible
   STATUS     mandatory
   DESCRIPTION
     "A single entry in the table represents a single 
      traceRcvrFrDc component."
   INDEX {
      traceIndex,
      traceRcvrIndex,
      traceRcvrFrIndex,
      traceRcvrFrDcIndex }
::= { traceRcvrFrDcRowStatusTable 1 }

TraceRcvrFrDcRowStatusEntry ::= SEQUENCE {
   traceRcvrFrDcRowStatus
      RowStatus,
   traceRcvrFrDcComponentName
      DisplayString,
   traceRcvrFrDcStorageType
      StorageType,
   traceRcvrFrDcIndex
      NonReplicated }

traceRcvrFrDcRowStatus OBJECT-TYPE
   SYNTAX     RowStatus 
   ACCESS     read-only
   STATUS     mandatory
   DESCRIPTION
     "This variable is used as the basis for SNMP naming of
      traceRcvrFrDc components.
      These components cannot be added nor deleted."
::= { traceRcvrFrDcRowStatusEntry 1 }

traceRcvrFrDcComponentName OBJECT-TYPE
   SYNTAX     DisplayString 
   ACCESS     read-only
   STATUS     mandatory
   DESCRIPTION
     "This variable provides the component's string name for
      use with the ASCII Console Interface"
::= { traceRcvrFrDcRowStatusEntry 2 }

traceRcvrFrDcStorageType OBJECT-TYPE
   SYNTAX     StorageType 
   ACCESS     read-only
   STATUS     mandatory
   DESCRIPTION
     "This variable represents the storage type value for the
      traceRcvrFrDc tables."
::= { traceRcvrFrDcRowStatusEntry 4 }

traceRcvrFrDcIndex OBJECT-TYPE
   SYNTAX     NonReplicated 
   ACCESS     not-accessible
   STATUS     mandatory
   DESCRIPTION
     "This variable represents the index for the traceRcvrFrDc tables."
::= { traceRcvrFrDcRowStatusEntry 10 }

traceRcvrFrDcOptionsTable OBJECT-TYPE
   SYNTAX     SEQUENCE OF TraceRcvrFrDcOptionsEntry
   ACCESS     not-accessible
   STATUS     mandatory
   DESCRIPTION
     "The Options group defines attributes associated with the SVC direct 
      call."
::= { traceRcvrFrDc 10 }

traceRcvrFrDcOptionsEntry OBJECT-TYPE
   SYNTAX     TraceRcvrFrDcOptionsEntry
   ACCESS     not-accessible
   STATUS     mandatory
   DESCRIPTION
     "An entry in the traceRcvrFrDcOptionsTable."
   INDEX {
      traceIndex,
      traceRcvrIndex,
      traceRcvrFrIndex,
      traceRcvrFrDcIndex }
::= { traceRcvrFrDcOptionsTable 1 }

TraceRcvrFrDcOptionsEntry ::= SEQUENCE {
   traceRcvrFrDcRemoteNpi
      INTEGER,
   traceRcvrFrDcRemoteDna
      DigitString,
   traceRcvrFrDcType
      INTEGER,
   traceRcvrFrDcUserData
      HexString }

traceRcvrFrDcRemoteNpi OBJECT-TYPE
   SYNTAX     INTEGER  {
                 x121(0),
                 e164(1) }
   ACCESS     read-write
   STATUS     mandatory
   DESCRIPTION
     "This attribute indicates the numbering plan used for the remoteDna."
   DEFVAL     { x121 }
::= { traceRcvrFrDcOptionsEntry 3 }

traceRcvrFrDcRemoteDna OBJECT-TYPE
   SYNTAX     DigitString (SIZE (1..15))
   ACCESS     read-write
   STATUS     mandatory
   DESCRIPTION
     "This attribute specifies the Data Network Address of the remote end 
      of the connection. This is the DNA of the Frame Relay trace 
      receiver which will receive the trace data."
::= { traceRcvrFrDcOptionsEntry 4 }

traceRcvrFrDcType OBJECT-TYPE
   SYNTAX     INTEGER  {
                 switched(0),
                 permanentMaster(1),
                 permanentSlave(2),
                 permanentBackupSlave(3) }
   ACCESS     read-only
   STATUS     mandatory
   DESCRIPTION
     "This attribute specifies the type of call as switched. For a switched 
      call, no information is defined at the remote end about the local end 
      of the connection."
   DEFVAL     { switched }
::= { traceRcvrFrDcOptionsEntry 6 }

traceRcvrFrDcUserData OBJECT-TYPE
   SYNTAX     HexString (SIZE (0..16))
   ACCESS     read-write
   STATUS     mandatory
   DESCRIPTION
     "This attribute contains the user data. It is a 0 to 16 byte length string 
      which is appended to the call request packet that is presented to the 
      called (destination) DTE."
   DEFVAL     { ''H }  -- ""
::= { traceRcvrFrDcOptionsEntry 8 }

-- 
-- *** THIS SUBTREE CURRENTLY NOT IMPLEMENTED ***
-- 

-- Trace Session/<n> FrameRelay
-- This component identifies the access method used by the receiver of 
-- the trace data as Frame Relay.

traceSessionFr OBJECT IDENTIFIER ::= { traceSession 3 }



traceSessionFrRowStatusTable OBJECT-TYPE
   SYNTAX     SEQUENCE OF TraceSessionFrRowStatusEntry
   ACCESS     not-accessible
   STATUS     mandatory
   DESCRIPTION
     "*** THIS TABLE CURRENTLY NOT IMPLEMENTED ***

      This entry controls the addition and deletion of 
      traceSessionFr components."
::= { traceSessionFr 1 }

traceSessionFrRowStatusEntry OBJECT-TYPE
   SYNTAX     TraceSessionFrRowStatusEntry
   ACCESS     not-accessible
   STATUS     mandatory
   DESCRIPTION
     "A single entry in the table represents a single 
      traceSessionFr component."
   INDEX {
      traceIndex,
      traceSessionIndex,
      traceSessionFrIndex }
::= { traceSessionFrRowStatusTable 1 }

TraceSessionFrRowStatusEntry ::= SEQUENCE {
   traceSessionFrRowStatus
      RowStatus,
   traceSessionFrComponentName
      DisplayString,
   traceSessionFrStorageType
      StorageType,
   traceSessionFrIndex
      NonReplicated }

traceSessionFrRowStatus OBJECT-TYPE
   SYNTAX     RowStatus 
   ACCESS     read-only
   STATUS     mandatory
   DESCRIPTION
     "This variable is used as the basis for SNMP naming of
      traceSessionFr components.
      These components cannot be added nor deleted."
::= { traceSessionFrRowStatusEntry 1 }

traceSessionFrComponentName OBJECT-TYPE
   SYNTAX     DisplayString 
   ACCESS     read-only
   STATUS     mandatory
   DESCRIPTION
     "This variable provides the component's string name for
      use with the ASCII Console Interface"
::= { traceSessionFrRowStatusEntry 2 }

traceSessionFrStorageType OBJECT-TYPE
   SYNTAX     StorageType 
   ACCESS     read-only
   STATUS     mandatory
   DESCRIPTION
     "This variable represents the storage type value for the
      traceSessionFr tables."
::= { traceSessionFrRowStatusEntry 4 }

traceSessionFrIndex OBJECT-TYPE
   SYNTAX     NonReplicated 
   ACCESS     not-accessible
   STATUS     mandatory
   DESCRIPTION
     "This variable represents the index for the traceSessionFr tables."
::= { traceSessionFrRowStatusEntry 10 }

-- 
-- *** THIS SUBTREE CURRENTLY NOT IMPLEMENTED ***
-- 

-- This component defines attributes collected by Frame Relay Vc.

traceSessionFrVc OBJECT IDENTIFIER ::= { traceSessionFr 2 }



traceSessionFrVcRowStatusTable OBJECT-TYPE
   SYNTAX     SEQUENCE OF TraceSessionFrVcRowStatusEntry
   ACCESS     not-accessible
   STATUS     mandatory
   DESCRIPTION
     "*** THIS TABLE CURRENTLY NOT IMPLEMENTED ***

      This entry controls the addition and deletion of 
      traceSessionFrVc components."
::= { traceSessionFrVc 1 }

traceSessionFrVcRowStatusEntry OBJECT-TYPE
   SYNTAX     TraceSessionFrVcRowStatusEntry
   ACCESS     not-accessible
   STATUS     mandatory
   DESCRIPTION
     "A single entry in the table represents a single 
      traceSessionFrVc component."
   INDEX {
      traceIndex,
      traceSessionIndex,
      traceSessionFrIndex,
      traceSessionFrVcIndex }
::= { traceSessionFrVcRowStatusTable 1 }

TraceSessionFrVcRowStatusEntry ::= SEQUENCE {
   traceSessionFrVcRowStatus
      RowStatus,
   traceSessionFrVcComponentName
      DisplayString,
   traceSessionFrVcStorageType
      StorageType,
   traceSessionFrVcIndex
      NonReplicated }

traceSessionFrVcRowStatus OBJECT-TYPE
   SYNTAX     RowStatus 
   ACCESS     read-only
   STATUS     mandatory
   DESCRIPTION
     "This variable is used as the basis for SNMP naming of
      traceSessionFrVc components.
      These components cannot be added nor deleted."
::= { traceSessionFrVcRowStatusEntry 1 }

traceSessionFrVcComponentName OBJECT-TYPE
   SYNTAX     DisplayString 
   ACCESS     read-only
   STATUS     mandatory
   DESCRIPTION
     "This variable provides the component's string name for
      use with the ASCII Console Interface"
::= { traceSessionFrVcRowStatusEntry 2 }

traceSessionFrVcStorageType OBJECT-TYPE
   SYNTAX     StorageType 
   ACCESS     read-only
   STATUS     mandatory
   DESCRIPTION
     "This variable represents the storage type value for the
      traceSessionFrVc tables."
::= { traceSessionFrVcRowStatusEntry 4 }

traceSessionFrVcIndex OBJECT-TYPE
   SYNTAX     NonReplicated 
   ACCESS     not-accessible
   STATUS     mandatory
   DESCRIPTION
     "This variable represents the index for the traceSessionFrVc tables."
::= { traceSessionFrVcRowStatusEntry 10 }

traceSessionFrVcCadTable OBJECT-TYPE
   SYNTAX     SEQUENCE OF TraceSessionFrVcCadEntry
   ACCESS     not-accessible
   STATUS     mandatory
   DESCRIPTION
     "*** THIS TABLE CURRENTLY NOT IMPLEMENTED ***

      This group represents operational call data related to Frame Relay 
      Vc. It can be displayed only for Frame Relay Vc which is created by 
      application."
::= { traceSessionFrVc 10 }

traceSessionFrVcCadEntry OBJECT-TYPE
   SYNTAX     TraceSessionFrVcCadEntry
   ACCESS     not-accessible
   STATUS     mandatory
   DESCRIPTION
     "An entry in the traceSessionFrVcCadTable."
   INDEX {
      traceIndex,
      traceSessionIndex,
      traceSessionFrIndex,
      traceSessionFrVcIndex }
::= { traceSessionFrVcCadTable 1 }

TraceSessionFrVcCadEntry ::= SEQUENCE {
   traceSessionFrVcType
      INTEGER,
   traceSessionFrVcState
      INTEGER,
   traceSessionFrVcPreviousState
      INTEGER,
   traceSessionFrVcDiagnosticCode
      Unsigned32,
   traceSessionFrVcPreviousDiagnosticCode
      Unsigned32,
   traceSessionFrVcCalledNpi
      INTEGER,
   traceSessionFrVcCalledDna
      DigitString,
   traceSessionFrVcCalledLcn
      Unsigned32,
   traceSessionFrVcCallingNpi
      INTEGER,
   traceSessionFrVcCallingDna
      DigitString,
   traceSessionFrVcCallingLcn
      Unsigned32,
   traceSessionFrVcAccountingEnabled
      INTEGER,
   traceSessionFrVcFastSelectCall
      INTEGER,
   traceSessionFrVcPathReliability
      INTEGER,
   traceSessionFrVcAccountingEnd
      INTEGER,
   traceSessionFrVcPriority
      INTEGER,
   traceSessionFrVcSegmentSize
      Unsigned32,
   traceSessionFrVcMaxSubnetPktSize
      Unsigned32,
   traceSessionFrVcRcosToNetwork
      INTEGER,
   traceSessionFrVcRcosFromNetwork
      INTEGER,
   traceSessionFrVcEmissionPriorityToNetwork
      INTEGER,
   traceSessionFrVcEmissionPriorityFromNetwork
      INTEGER,
   traceSessionFrVcDataPath
      AsciiString }

traceSessionFrVcType OBJECT-TYPE
   SYNTAX     INTEGER  {
                 svc(0),
                 pvc(1),
                 spvc(2) }
   ACCESS     read-only
   STATUS     mandatory
   DESCRIPTION
     "This attribute displays the type of call, pvc,svc or spvc."
::= { traceSessionFrVcCadEntry 1 }

traceSessionFrVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { traceSessionFrVcCadEntry 2 }

traceSessionFrVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { traceSessionFrVcCadEntry 3 }

traceSessionFrVcDiagnosticCode OBJECT-TYPE
   SYNTAX     Unsigned32 (0..255)
   ACCESS     read-only
   STATUS     mandatory
   DESCRIPTION
     "This attribute displays the internal substate of call control. It is used 
      to further refine state of call processing."
::= { traceSessionFrVcCadEntry 4 }

traceSessionFrVcPreviousDiagnosticCode OBJECT-TYPE
   SYNTAX     Unsigned32 (0..255)
   ACCESS     read-only
   STATUS     mandatory
   DESCRIPTION
     "This attribute displays the internal substate of call control. It is used 
      to further refine state of call processing."
::= { traceSessionFrVcCadEntry 5 }

traceSessionFrVcCalledNpi OBJECT-TYPE
   SYNTAX     INTEGER  {
                 x121(0),
                 e164(1) }
   ACCESS     read-only
   STATUS     mandatory
   DESCRIPTION
     "This attribute displays the Numbering Plan Indicator (NPI) of the 
      called end."
::= { traceSessionFrVcCadEntry 6 }

traceSessionFrVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { traceSessionFrVcCadEntry 7 }

traceSessionFrVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { traceSessionFrVcCadEntry 8 }

traceSessionFrVcCallingNpi OBJECT-TYPE
   SYNTAX     INTEGER  {
                 x121(0),
                 e164(1) }
   ACCESS     read-only
   STATUS     mandatory
   DESCRIPTION
     "This attribute displays the Numbering Plan Indicator (NPI) of the 
      calling end."
::= { traceSessionFrVcCadEntry 9 }

traceSessionFrVcCallingDna OBJECT-TYPE
   SYNTAX     DigitString (SIZE (1..15))
   ACCESS     read-only
   STATUS     mandatory
   DESCRIPTION
     "This attribute displays the Data Network Address (Dna) of the 
      calling end."
::= { traceSessionFrVcCadEntry 10 }

traceSessionFrVcCallingLcn OBJECT-TYPE
   SYNTAX     Unsigned32 (1..65535)
   ACCESS     read-only
   STATUS     mandatory
   DESCRIPTION
     "This attribute displays the Logical Channel Number of the calling 
      end."
::= { traceSessionFrVcCadEntry 11 }

traceSessionFrVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { traceSessionFrVcCadEntry 12 }

traceSessionFrVcFastSelectCall OBJECT-TYPE
   SYNTAX     INTEGER  {
                 no(0),
                 yes(1) }
   ACCESS     read-only
   STATUS     mandatory
   DESCRIPTION
     "This attribute displays that this is a fast select call."
::= { traceSessionFrVcCadEntry 13 }

traceSessionFrVcPathReliability OBJECT-TYPE
   SYNTAX     INTEGER  {
                 high(0),
                 normal(1) }
   ACCESS     read-only
   STATUS     mandatory
   DESCRIPTION
     "This attribute displays the path reliability."
::= { traceSessionFrVcCadEntry 19 }

traceSessionFrVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { traceSessionFrVcCadEntry 20 }

traceSessionFrVcPriority OBJECT-TYPE
   SYNTAX     INTEGER  {
                 normal(0),
                 high(1) }
   ACCESS     read-only
   STATUS     mandatory
   DESCRIPTION
     "This attribute displays whether the call is a normal or a high 
      priority call."
::= { traceSessionFrVcCadEntry 21 }

traceSessionFrVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { traceSessionFrVcCadEntry 22 }

traceSessionFrVcMaxSubnetPktSize OBJECT-TYPE
   SYNTAX     Unsigned32 (0..4096)
   ACCESS     read-only
   STATUS     mandatory
   DESCRIPTION
     "This attribute indicates the maximum packet size allowed on the Vc."
::= { traceSessionFrVcCadEntry 27 }

traceSessionFrVcRcosToNetwork OBJECT-TYPE
   SYNTAX     INTEGER  {
                 throughput(0),
                 delay(1),
                 multimedia(2) }
   ACCESS     read-only
   STATUS     mandatory
   DESCRIPTION
     "This attribute indicates the routing metric routing class of service to
      the network."
::= { traceSessionFrVcCadEntry 28 }

traceSessionFrVcRcosFromNetwork OBJECT-TYPE
   SYNTAX     INTEGER  {
                 throughput(0),
                 delay(1),
                 multimedia(2) }
   ACCESS     read-only
   STATUS     mandatory
   DESCRIPTION
     "This attribute displays the routing metric Routing Class of Service 
      from the Network."
::= { traceSessionFrVcCadEntry 29 }

traceSessionFrVcEmissionPriorityToNetwork OBJECT-TYPE
   SYNTAX     INTEGER  {
                 normal(0),
                 high(1),
                 interrupting(2) }
   ACCESS     read-only
   STATUS     mandatory
   DESCRIPTION
     "This attribute displays the network internal emission priotity to the 
      network."
::= { traceSessionFrVcCadEntry 30 }

traceSessionFrVcEmissionPriorityFromNetwork OBJECT-TYPE
   SYNTAX     INTEGER  {
                 normal(0),
                 high(1),
                 interrupting(2) }
   ACCESS     read-only
   STATUS     mandatory
   DESCRIPTION
     "This attribute displays the network internal emission priotity from 
      the network."
::= { traceSessionFrVcCadEntry 31 }

traceSessionFrVcDataPath OBJECT-TYPE
   SYNTAX     AsciiString (SIZE (0..32))
   ACCESS     read-only
   STATUS     mandatory
   DESCRIPTION
     "This attribute indicates the data path used by the connection. The 
      data path is provisioned in Dna and DirectCall components. The 
      displayed value of this attribute can be different from the 
      provisioned value.
      
      If the connection is using dprsOnly data path, the string 
      dprsOnly is displayed. (dynamic packet routing system)
      
      If the connection is using dprsMcsOnly data path, the string 
      dprsMcsOnly is displayed.
      
      If the connection is using dprsMcsFirst data path, the string 
      dprsMcsFirst is displayed."
::= { traceSessionFrVcCadEntry 32 }

traceSessionFrVcIntdTable OBJECT-TYPE
   SYNTAX     SEQUENCE OF TraceSessionFrVcIntdEntry
   ACCESS     not-accessible
   STATUS     mandatory
   DESCRIPTION
     "*** THIS TABLE CURRENTLY NOT IMPLEMENTED ***

      This group defines display of interval data collected by Vc. Data in 
      this group is variable and may depend on time when this display 
      command is issued."
::= { traceSessionFrVc 11 }

traceSessionFrVcIntdEntry OBJECT-TYPE
   SYNTAX     TraceSessionFrVcIntdEntry
   ACCESS     not-accessible
   STATUS     mandatory
   DESCRIPTION
     "An entry in the traceSessionFrVcIntdTable."
   INDEX {
      traceIndex,
      traceSessionIndex,
      traceSessionFrIndex,
      traceSessionFrVcIndex }
::= { traceSessionFrVcIntdTable 1 }

TraceSessionFrVcIntdEntry ::= SEQUENCE {
   traceSessionFrVcCallReferenceNumber
      Hex,
   traceSessionFrVcElapsedTimeTillNow
      Unsigned32,
   traceSessionFrVcSegmentsRx
      Unsigned32,
   traceSessionFrVcSegmentsSent
      Unsigned32,
   traceSessionFrVcStartTime
      EnterpriseDateAndTime }

traceSessionFrVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { traceSessionFrVcIntdEntry 1 }

traceSessionFrVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { traceSessionFrVcIntdEntry 2 }

traceSessionFrVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { traceSessionFrVcIntdEntry 3 }

traceSessionFrVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { traceSessionFrVcIntdEntry 4 }

traceSessionFrVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { traceSessionFrVcIntdEntry 5 }

traceSessionFrVcFrdTable OBJECT-TYPE
   SYNTAX     SEQUENCE OF TraceSessionFrVcFrdEntry
   ACCESS     not-accessible
   STATUS     mandatory
   DESCRIPTION
     "*** THIS TABLE CURRENTLY NOT IMPLEMENTED ***

      This group defines Frame Relay attributes collected by Frame Relay 
      Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods. 
      Frame Relay Vc uses a best effort data packet delivery protocol and 
      a different packet segmentation and combination methods from the 
      General Vc. The Frame Relay Vc uses the same call setup and 
      control mechanism (e.g. the support of non-flow control data 
      packets) as in a General Vc. Most General Vc statistics and internal 
      variables are used in a Frame Relay Vc and are displayed by 
      software developers"
::= { traceSessionFrVc 12 }

traceSessionFrVcFrdEntry OBJECT-TYPE
   SYNTAX     TraceSessionFrVcFrdEntry
   ACCESS     not-accessible
   STATUS     mandatory
   DESCRIPTION
     "An entry in the traceSessionFrVcFrdTable."
   INDEX {
      traceIndex,
      traceSessionIndex,
      traceSessionFrIndex,
      traceSessionFrVcIndex }
::= { traceSessionFrVcFrdTable 1 }

TraceSessionFrVcFrdEntry ::= SEQUENCE {
   traceSessionFrVcFrmCongestedToSubnet
      Unsigned32,
   traceSessionFrVcCannotForwardToSubnet
      Unsigned32,
   traceSessionFrVcNotDataXferToSubnet
      Unsigned32,
   traceSessionFrVcOutOfRangeFrmFromSubnet
      Unsigned32,
   traceSessionFrVcCombErrorsFromSubnet
      Unsigned32,
   traceSessionFrVcDuplicatesFromSubnet
      Unsigned32,
   traceSessionFrVcNotDataXferFromSubnet
      Unsigned32,
   traceSessionFrVcFrmLossTimeouts
      Unsigned32,
   traceSessionFrVcOoSeqByteCntExceeded
      Unsigned32,
   traceSessionFrVcPeakOoSeqPktCount
      Unsigned32,
   traceSessionFrVcPeakOoSeqFrmForwarded
      Unsigned32,
   traceSessionFrVcSendSequenceNumber
      Unsigned32,
   traceSessionFrVcPktRetryTimeouts
      Unsigned32,
   traceSessionFrVcPeakRetryQueueSize
      Unsigned32,
   traceSessionFrVcSubnetRecoveries
      Unsigned32,
   traceSessionFrVcOoSeqPktCntExceeded
      Unsigned32,
   traceSessionFrVcPeakOoSeqByteCount
      Unsigned32 }

traceSessionFrVcFrmCongestedToSubnet OBJECT-TYPE
   SYNTAX     Unsigned32 (0..5000)
   ACCESS     read-only
   STATUS     mandatory
   DESCRIPTION
     "This attribute displays the number of frames from link discarded 
      due to lack of resources. It keeps track of the number of frames 
      from link that have to be discarded. The discard reasons include 
      insufficient memory for splitting the frame into smaller subnet 
      packet size."
::= { traceSessionFrVcFrdEntry 2 }

traceSessionFrVcCannotForwardToSubnet OBJECT-TYPE
   SYNTAX     Unsigned32 (0..5000)
   ACCESS     read-only
   STATUS     mandatory
   DESCRIPTION
     "This attribute displays the number of discarded packets that can not 
      be forwarded into the subnet because of subnet congestion.
      Number of frames from link discarded due to failure in forwarding 
      a packet from Vc into the subnet.- This attribute is increased when 
      packet forwarding fails to forward a packet into the subnet. If a 
      frame is split into multiple subnet packets and a partial packet has 
      to be discarded, all subsequent partial packets that have not yet been 
      delivered to the subnet will be discarded as well."
::= { traceSessionFrVcFrdEntry 3 }

traceSessionFrVcNotDataXferToSubnet OBJECT-TYPE
   SYNTAX     Unsigned32 (0..5000)
   ACCESS     read-only
   STATUS     mandatory
   DESCRIPTION
     "This attribute records the number of frames from link discarded 
      when the Vc tries to recover from internal path failure."
::= { traceSessionFrVcFrdEntry 4 }

traceSessionFrVcOutOfRangeFrmFromSubnet OBJECT-TYPE
   SYNTAX     Unsigned32 (0..5000)
   ACCESS     read-only
   STATUS     mandatory
   DESCRIPTION
     "This attribute displays the number of frames from subnet discarded 
      due to out of sequence range for arriving too late."
::= { traceSessionFrVcFrdEntry 5 }

traceSessionFrVcCombErrorsFromSubnet OBJECT-TYPE
   SYNTAX     Unsigned32 (0..5000)
   ACCESS     read-only
   STATUS     mandatory
   DESCRIPTION
     "This attribute records the number of subnet packets discarded at the 
      sink Vc due to the Vc segmentation and combination protocol error. 
      Usually, this occurs when the subnet discards packets and thus this 
      statistics can be used to guest the number of subnet packets that are 
      not delivered to the Vc. It cannot be used as an actual measure 
      because some subnet packets may have been delivered to Vc but 
      have to be discarded because these are partial packets to a frame in 
      which some other partial packets have not been properly delivered 
      to Vc"
::= { traceSessionFrVcFrdEntry 6 }

traceSessionFrVcDuplicatesFromSubnet OBJECT-TYPE
   SYNTAX     Unsigned32 (0..5000)
   ACCESS     read-only
   STATUS     mandatory
   DESCRIPTION
     "This attribute displays the number of subnet packets discarded due 
      to duplication. Although packets are not retransmitted by the Frame 
      Relay Vc, it is possible for the subnet to retransmit packets. When 
      packets are out-of-sequenced and copies of the same packets arrive, 
      then this attribute is increased."
::= { traceSessionFrVcFrdEntry 7 }

traceSessionFrVcNotDataXferFromSubnet OBJECT-TYPE
   SYNTAX     Unsigned32 (0..5000)
   ACCESS     read-only
   STATUS     mandatory
   DESCRIPTION
     "This attribute displays the number of subnet packets discarded when 
      data transfer is suspended in Vc recovery."
::= { traceSessionFrVcFrdEntry 8 }

traceSessionFrVcFrmLossTimeouts OBJECT-TYPE
   SYNTAX     Unsigned32 (0..5000)
   ACCESS     read-only
   STATUS     mandatory
   DESCRIPTION
     "This attribute displays the number of lost frame timer expiries.
      When this count is excessive, the network is very congested and 
      packets have been discarded in the subnet."
::= { traceSessionFrVcFrdEntry 9 }

traceSessionFrVcOoSeqByteCntExceeded OBJECT-TYPE
   SYNTAX     Unsigned32 (0..5000)
   ACCESS     read-only
   STATUS     mandatory
   DESCRIPTION
     "This attribute displays the number times that the out of sequence 
      byte threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { traceSessionFrVcFrdEntry 10 }

traceSessionFrVcPeakOoSeqPktCount OBJECT-TYPE
   SYNTAX     Unsigned32 (0..5000)
   ACCESS     read-only
   STATUS     mandatory
   DESCRIPTION
     "This attribute displays the frame relay peak packet count of the out 
      of sequence queue. This attribute records the maximum queue 
      length of the out-of-sequenced queue. The counter can be used to 
      deduce the message buffer requirement on a Vc."
::= { traceSessionFrVcFrdEntry 11 }

traceSessionFrVcPeakOoSeqFrmForwarded OBJECT-TYPE
   SYNTAX     Unsigned32 (0..5000)
   ACCESS     read-only
   STATUS     mandatory
   DESCRIPTION
     "This attribute displays the frame relay peak size of the 
      sequence packet queue. The subnet may deliver packets out-of-
      sequenced. These packets are then queued in an out-of-sequenced 
      queue, waiting for a packet with the expected sequence number to 
      come. When that packet arrives, this attribute records the maximum 
      number of packets that were out-of-sequenced, but now have 
      become in-sequenced. The statistics is used to measure expected 
      queue size due to normal subnet packet disorder (not due to subnet 
      packet discard). Current implementation also uses this statistics to 
      set a maximum size for the out-of-sequenced queue."
::= { traceSessionFrVcFrdEntry 12 }

traceSessionFrVcSendSequenceNumber OBJECT-TYPE
   SYNTAX     Unsigned32 (0..5000)
   ACCESS     read-only
   STATUS     mandatory
   DESCRIPTION
     "This attribute displays the Vc internal packet's send sequence 
      number. Note that a 'packet' in this context, may be either a user 
      data packet, or an OAM frame."
::= { traceSessionFrVcFrdEntry 13 }

traceSessionFrVcPktRetryTimeouts OBJECT-TYPE
   SYNTAX     Unsigned32 (0..5000)
   ACCESS     read-only
   STATUS     mandatory
   DESCRIPTION
     "This attribute displays the number of packets which have 
      retransmission time-outs. When this count is excessive, the network 
      is very congested and packets have been discarded in the subnet."
::= { traceSessionFrVcFrdEntry 15 }

traceSessionFrVcPeakRetryQueueSize OBJECT-TYPE
   SYNTAX     Unsigned32 (0..5000)
   ACCESS     read-only
   STATUS     mandatory
   DESCRIPTION
     "This attribute displays the peak size of retransmission queue.
      This attribute is used as an indicator of the acknowledgment 
      behavior across the subnet. Records the largest body of 
      unacknowledged packets."
::= { traceSessionFrVcFrdEntry 16 }

traceSessionFrVcSubnetRecoveries OBJECT-TYPE
   SYNTAX     Unsigned32 (0..5000)
   ACCESS     read-only
   STATUS     mandatory
   DESCRIPTION
     "This attribute displays the number of successful Vc recovery 
      attempts."
::= { traceSessionFrVcFrdEntry 17 }

traceSessionFrVcOoSeqPktCntExceeded OBJECT-TYPE
   SYNTAX     Unsigned32 (0..255)
   ACCESS     read-only
   STATUS     mandatory
   DESCRIPTION
     "This attribute displays the number times that the out of sequence 
      packet threshold is exceeded. When the threshold is exceeded, this 
      condition is treated as if the loss frame timer has expired and all 
      frames queued at the sink Vc are delivered to the AP. We need to 
      keep this count to examine if the threshold is engineered properly. 
      This should be used in conjunction with the peak value of out-of-
      sequenced queue and the number of times the loss frame timer has 
      expired. This count should be relatively small when compared with 
      loss frame timer expiry count."
::= { traceSessionFrVcFrdEntry 19 }

traceSessionFrVcPeakOoSeqByteCount OBJECT-TYPE
   SYNTAX     Unsigned32 (0..50000)
   ACCESS     read-only
   STATUS     mandatory
   DESCRIPTION
     "This attribute displays the frame relay peak byte count of the out of 
      sequence queue. This attribute records the maximum queue length 
      of the out-of-sequenced queue. The counter can be used to deduce 
      the message buffer requirement on a Vc."
::= { traceSessionFrVcFrdEntry 20 }

traceSessionFrVcDmepTable OBJECT-TYPE
   SYNTAX     SEQUENCE OF TraceSessionFrVcDmepEntry
   ACCESS     not-accessible
   STATUS     mandatory
   DESCRIPTION
     "*** THIS TABLE CURRENTLY NOT IMPLEMENTED ***

      This attribute displays the data path used by the connection. Data 
      path is provisioned in Dna and DirectCall components.
      
      If the connection is using dprsOnly data path, this attribute is 
      empty.
      
      If the connection is using dprsMcsOnly or dprsMcsFirst data path, 
      this attribute displays component name of the dprsMcsEndPoint."
::= { traceSessionFrVc 417 }

traceSessionFrVcDmepEntry OBJECT-TYPE
   SYNTAX     TraceSessionFrVcDmepEntry
   ACCESS     not-accessible
   STATUS     mandatory
   DESCRIPTION
     "An entry in the traceSessionFrVcDmepTable."
   INDEX {
      traceIndex,
      traceSessionIndex,
      traceSessionFrIndex,
      traceSessionFrVcIndex,
      traceSessionFrVcDmepValue }
::= { traceSessionFrVcDmepTable 1 }

TraceSessionFrVcDmepEntry ::= SEQUENCE {
   traceSessionFrVcDmepValue
      RowPointer }

traceSessionFrVcDmepValue OBJECT-TYPE
   SYNTAX     RowPointer 
   ACCESS     read-only
   STATUS     mandatory
   DESCRIPTION
     "This variable represents both the value and the index for the
      traceSessionFrVcDmepTable."
::= { traceSessionFrVcDmepEntry 1 }




-- 
-- Version and Compliance statements
-- 



-- Object-Group Statement:
-- A list of all current accessible leaf objects.

-- OBJECTS { traceRcvrFrDnaCugComponentName,
--           traceSessionFrVcPreviousDiagnosticCode,
--           traceRcvrFrDnaCugDnic,
--           traceSessionFrVcFastSelectCall,
--           traceSessionFrVcCallingLcn,
--           traceSessionFrVcOutOfRangeFrmFromSubnet,
--           traceRcvrFrDcType,
--           traceSessionFrVcPeakOoSeqPktCount,
--           traceRcvrFrDnaCugInterlockCode,
--           traceSessionFrVcPriority,
--           traceSessionFrVcType,
--           traceRcvrFrDnaComponentName,
--           traceSessionFrVcCalledNpi,
--           traceSessionFrVcElapsedTimeTillNow,
--           traceSessionFrVcAccountingEnabled,
--           traceSessionFrComponentName,
--           traceSessionFrVcSegmentsSent,
--           traceSessionFrVcNotDataXferToSubnet,
--           traceRcvrFrDnaCugOutCalls,
--           traceSessionFrVcPreviousState,
--           traceRcvrFrDcRowStatus,
--           traceSessionFrVcSubnetRecoveries,
--           traceRcvrFrDnaOutCalls,
--           traceRcvrFrDnaOutPathReliabilityOverRide,
--           traceSessionFrVcCalledDna,
--           traceRcvrFrRowStatus,
--           traceRcvrFrDcRemoteDna,
--           traceRcvrFrDnaOutPathReliabilitySignal,
--           traceSessionFrVcOoSeqByteCntExceeded,
--           traceRcvrFrDcRemoteNpi,
--           traceSessionFrVcOoSeqPktCntExceeded,
--           traceSessionFrVcRcosToNetwork,
--           traceSessionFrVcPeakRetryQueueSize,
--           traceSessionFrVcSegmentSize,
--           traceRcvrFrDnaCugPreferential,
--           traceRcvrFrDnaNumberingPlanIndicator,
--           traceRcvrFrDnaOutAccess,
--           traceSessionFrVcEmissionPriorityFromNetwork,
--           traceRcvrFrDnaPacketSizes,
--           traceRcvrFrDcComponentName,
--           traceRcvrFrDnaDefaultRecvFrmNetworkPacketSize,
--           traceSessionFrVcComponentName,
--           traceSessionFrVcDataPath,
--           traceSessionFrVcCombErrorsFromSubnet,
--           traceSessionFrVcCallingDna,
--           traceSessionFrVcCallingNpi,
--           traceSessionFrVcPeakOoSeqFrmForwarded,
--           traceSessionFrVcSegmentsRx,
--           traceRcvrFrComponentName,
--           traceSessionFrVcPktRetryTimeouts,
--           traceRcvrFrDnaCugStorageType,
--           traceSessionFrVcSendSequenceNumber,
--           traceRcvrFrDnaDataNetworkAddress,
--           traceRcvrFrDnaOutIntl,
--           traceSessionFrVcPathReliability,
--           traceSessionFrVcCannotForwardToSubnet,
--           traceSessionFrVcAccountingEnd,
--           traceRcvrFrDnaCugFormat,
--           traceRcvrFrDcUserData,
--           traceSessionFrVcNotDataXferFromSubnet,
--           traceRcvrFrDnaStorageType,
--           traceRcvrFrDnaCugType,
--           traceSessionFrStorageType,
--           traceSessionFrVcDmepValue,
--           traceSessionFrVcFrmCongestedToSubnet,
--           traceSessionFrVcCallReferenceNumber,
--           traceRcvrFrDnaOutDefaultPriority,
--           traceRcvrFrDnaOutDefaultPathReliability,
--           traceRcvrFrDnaIncCalls,
--           traceSessionFrVcState,
--           traceSessionFrVcRowStatus,
--           traceSessionFrVcCalledLcn,
--           traceSessionFrVcRcosFromNetwork,
--           traceRcvrFrDnaCugIncCalls,
--           traceRcvrFrDnaCugRowStatus,
--           traceSessionFrVcDuplicatesFromSubnet,
--           traceSessionFrVcMaxSubnetPktSize,
--           traceSessionFrVcStartTime,
--           traceSessionFrVcEmissionPriorityToNetwork,
--           traceSessionFrVcDiagnosticCode,
--           traceRcvrFrStorageType,
--           traceRcvrFrDnaRowStatus,
--           traceRcvrFrDnaCugPrivileged,
--           traceSessionFrVcFrmLossTimeouts,
--           traceRcvrFrDcStorageType,
--           traceSessionFrRowStatus,
--           traceRcvrFrDnaDefaultSendToNetworkPacketSize,
--           traceSessionFrVcPeakOoSeqByteCount,
--           traceSessionFrVcStorageType }
-- STATUS  mandatory
-- DESCRIPTION
--   "A list of all current accessible leaf objects."

frTraceRcvrGroup OBJECT IDENTIFIER ::= { frTraceRcvrMIB 1 }
frTraceRcvrGroupBE OBJECT IDENTIFIER ::= { frTraceRcvrGroup 5 }
frTraceRcvrGroupBE01 OBJECT IDENTIFIER ::= { frTraceRcvrGroupBE 2 }
frTraceRcvrGroupBE01A OBJECT IDENTIFIER ::= { frTraceRcvrGroupBE01 2 }



-- Agent-Capabilities Statement:

-- PRODUCT-RELEASE "Passport Release 7.0 FrTraceRcvr."
-- STATUS          mandatory
-- DESCRIPTION     "FrTraceRcvr MIB: MIB Version BE01A,
--                  Software Version BG00S4C."
-- SUPPORTS        Nortel-Magellan-Passport-FrTraceRcvrMIB
--    INCLUDES     { frTraceRcvrGroupBE01A }

frTraceRcvrCapabilities OBJECT IDENTIFIER ::= { frTraceRcvrMIB 3 }
frTraceRcvrCapabilitiesBE OBJECT IDENTIFIER ::= { frTraceRcvrCapabilities 5 }
frTraceRcvrCapabilitiesBE01 OBJECT IDENTIFIER ::= { frTraceRcvrCapabilitiesBE 2 }
frTraceRcvrCapabilitiesBE01A OBJECT IDENTIFIER ::= { frTraceRcvrCapabilitiesBE01 2 }





END
