--      Date: Aug 23, 1999
--
--      user load, total load, unavailability become strings
--      also max/min user load, max/min total load become strings
--      in order to return 2 decimal places.
--
--
LINK-PROBE-MIB DEFINITIONS ::= BEGIN

IMPORTS
	Counter, IpAddress, enterprises, Gauge      FROM RFC1155-SMI
	DisplayString           FROM RFC1213-MIB
	OBJECT-TYPE             FROM RFC-1212
	sysName                 FROM RFC1213-MIB
	TRAP-TYPE FROM RFC-1215;

netQuest	OBJECT IDENTIFIER ::={ enterprises 568 }

link-probe  OBJECT IDENTIFIER ::={ netQuest 8 }


-- Groups within the NetQuest LINK-PROBE MIB.

-- The probe configuration group

probeConfig     OBJECT IDENTIFIER ::={ link-probe 1 }


-- The probe statistics group

probeStat       OBJECT IDENTIFIER ::={ link-probe 2 }


-- The probe performance group

probePerform     OBJECT IDENTIFIER ::={ link-probe 3 }

-- The traffic shape group

probeTrafficShape  OBJECT IDENTIFIER ::={ link-probe 4 }


-- The probe historical performance group

probeHistorical     OBJECT IDENTIFIER ::={ link-probe 5 }

-- The probe interval start time group

probeIntervalStartTime  OBJECT IDENTIFIER ::={ link-probe 6 }

-- Dial Backup Unit Configuration Group

dbuConfigGroup		OBJECT IDENTIFIER ::={ link-probe 7 }

-- Device Status Group

deviceStatusGroup	OBJECT IDENTIFIER ::={ link-probe 8 }

-- Trap Acknowledge Group

trapAcknowledgeGroup	OBJECT IDENTIFIER ::={ link-probe 9 }

--
-- Subgroup in link probe configuration
--
-- 1. Channel Configuration
-- 2. LMI Configuration
-- 3. Probe Function Configuration
-- 4. Trap Threshold Configuration
-- 5. PVC configuration
-- 6. File Update Configuration
-- 7. Network Management Configuration

chan-config OBJECT IDENTIFIER ::={ probeConfig 1 }

lmi-config OBJECT IDENTIFIER ::={ probeConfig 2 }

pro-fun-config OBJECT IDENTIFIER ::={ probeConfig 3 }

trap-config OBJECT IDENTIFIER ::={ probeConfig 4 }

pvc-config  OBJECT IDENTIFIER ::={ probeConfig 5 }

file-download-config  OBJECT IDENTIFIER ::={ probeConfig 6 }

net-management-config  OBJECT IDENTIFIER ::={ probeConfig 7 }

--
--      CHANNEL CONFIGURATION GROUP
--
--

	lmi-Operation OBJECT-TYPE
		SYNTAX INTEGER {
			off(1),
			on(2)
			}
		ACCESS read-write
		STATUS mandatory
		DESCRIPTION
		" LMI operation, on -- enabled,  off -- disabled "
		::= { chan-config 1 }

	lmi-DLCI OBJECT-TYPE
		SYNTAX INTEGER {
			pvc-0(1),
                        pvc-1023(2)
			}
		ACCESS read-write
		STATUS mandatory
		DESCRIPTION
		" LMI DLCI can just take two values: DLCI 0 or DLCI 1023,
		  default is 0."
		::= { chan-config 2 }

	inband-IP-DLCI OBJECT-TYPE
		SYNTAX INTEGER (16..991)
                ACCESS read-write
		STATUS mandatory
		DESCRIPTION
		" valid Inband IP DLCI ranges from 16 to 991, read only
		  object"
		::= { chan-config 3 }

	ip-Encapsu OBJECT-TYPE
		SYNTAX INTEGER {
			raw-ip(1),
			ietf-ip(2),
			snap-ip(3)
			}
		ACCESS read-write
		STATUS mandatory
		DESCRIPTION
		" Indicate which IP DLCI Encapsulation method"
		::= { chan-config 4 }

	interface-Speed OBJECT-TYPE
		SYNTAX INTEGER {
	    n64-kbps(1),
	    n128-kbps(2),
	    n192-kbps(3),
	    n256-kbps(4),
	    n320-kbps(5),
	    n384-kbps(6),
	    n448-kbps(7),
	    n512-kbps(8),
	    n576-kbps(9),
	    n640-kbps(10),
	    n704-kbps(11),
	    n768-kbps(12),
	    n832-kbps(13),
	    n896-kbps(14),
	    n960-kbps(15),
	   n1024-kbps(16),
	   n1088-kbps(17),
	   n1152-kbps(18),
	   n1216-kbps(19),
	   n1280-kbps(20),
	   n1344-kbps(21),
	   n1408-kbps(22),
	   n1472-kbps(23),
	   n1536-kbps(24),
	   n1600-kbps(25),
	   n1664-kbps(26),
	   n1728-kbps(27),
	   n1792-kbps(28),
	   n1856-kbps(29),
	   n1920-kbps(30),
	   n1984-kbps(31),
	   n2048-kbps(32)
			}
		ACCESS read-write
		STATUS mandatory
		DESCRIPTION
		" Interface Speed is n*8 kpbs, the default value is
		  64 kbps. "
		::={ chan-config 5 }

	nvram-update OBJECT-TYPE
		SYNTAX INTEGER {
			write-to-nvram(1),
			restoreParam(2)
			}
		ACCESS write-only
		STATUS mandatory
		DESCRIPTION
		" This object lets the user decide if he (she) wants to write the
		  just modified parameters in channel configuration group to nvram,
		  if he chose 'write', these parameters will be updated; and if he
		  chose 'restore', the modifications are lost."
		::={ chan-config 6 }


--
-- LMI Configuration Group
--

	lmi-type OBJECT-TYPE
		SYNTAX INTEGER {
			annex-a(1),
                        annex-d(2),
                        lmi-rev1(3)
		}
		ACCESS read-write
		STATUS mandatory
		DESCRIPTION
		" This object identifies the LMI type the network is currently
		  using, read/write object."
		::= { lmi-config 1 }

	max-Info-Length OBJECT-TYPE
		SYNTAX INTEGER ( 400..4000 )
		ACCESS read-write
		STATUS mandatory
		DESCRIPTION
		" Maximum supported frame information length ranges from
		  400 to 4000, the default value is 4000."
		::= { lmi-config 2 }

	n391-Counter OBJECT-TYPE
		SYNTAX INTEGER ( 1..255 )
		ACCESS read-write
		STATUS mandatory
		DESCRIPTION
		" N391 Counter ranges from 1 to 255, the default value is 6."
		::= { lmi-config 3 }

	n392-Net-Counter OBJECT-TYPE
		SYNTAX INTEGER ( 1..10 )
		ACCESS read-write
		STATUS mandatory
		DESCRIPTION
		" N392 Net Counter ranges from 1 to 10, the default
		  value is 3."
		::= { lmi-config 4 }

	n392-User-Counter OBJECT-TYPE
		SYNTAX INTEGER ( 1..10 )
		ACCESS read-write
		STATUS mandatory
		DESCRIPTION
		" N392 User Counter ranges from 1 to 10, the default
		  value is 3."
		::= { lmi-config 5 }

	n393-Net-Counter OBJECT-TYPE
		SYNTAX INTEGER ( 1..10 )
		ACCESS read-write
		STATUS mandatory
		DESCRIPTION
		" N393 Net Counter ranges from 1 to 10, the default
		  value is 4."
		::= { lmi-config 6 }

	n393-User-Counter OBJECT-TYPE
		SYNTAX INTEGER ( 1..10 )
		ACCESS read-write
		STATUS mandatory
		DESCRIPTION
		" N393 User Counter ranges from 1 to 10, the default
		  value is 4."
		::= { lmi-config 7 }

	t391-Timer OBJECT-TYPE
		SYNTAX INTEGER ( 5..30 )
		ACCESS read-write
		STATUS mandatory
		DESCRIPTION
		" T391 Timer ranges from 5 to 30, the default value is 10,
		  which would always less than or equal to T392 Timer."
		::= { lmi-config 8 }

	t392-Timer OBJECT-TYPE
		SYNTAX INTEGER ( 5..30 )
		ACCESS read-write
		STATUS mandatory
		DESCRIPTION
		" T392 Timer ranges from 5 to 30, the default value is 15.
		  which should always greater than T391 Timer."
		::= { lmi-config 9 }

	lMI-Controller OBJECT-TYPE
		SYNTAX INTEGER {
			update-para(1),
			restoreParam(2)
		}
		ACCESS write-only
		STATUS mandatory
		DESCRIPTION
		" This object lets the user decide if he (she) wants
		  to update the just modified LMI parameters, only when
		  the user chooses to update will the new parameters be
		  accepted by the system. If the user selects the
		  restoreParam value then the LMI parameters will revert
		  to the previous values, and the modifications are lost."
		::= { lmi-config 10 }


--
-- Probe Function Configuration Group
--

        softwareVersion OBJECT-TYPE
                SYNTAX DisplayString (SIZE (0..10))
                ACCESS read-only
		STATUS mandatory
		DESCRIPTION
                " This object displays the software version we are currently
                  running, so according to the version number, the user can
                  determine which version is newer."
                ::={ pro-fun-config 1 }


	probe-Mode OBJECT-TYPE
		SYNTAX INTEGER {
			generator(1),
                        responder(2),
			both(3),
			disabled(4)
			}
		ACCESS read-write
		STATUS mandatory
		DESCRIPTION
		" Probe mode defines whether the link probe is generator,
		  responder, both or disabled. "
                ::={ pro-fun-config 2 }

	poll-Period OBJECT-TYPE
		SYNTAX INTEGER ( 1..60 )
		ACCESS read-write
		STATUS mandatory
		DESCRIPTION
		" poll period defines the frequency of sending the polling frame
		  by the link probe. The value is between 1 to 60 sec.  The poll
		  period applies to all PVCs that are to be probed. "
                ::={ pro-fun-config 3 }

	sys-current-time OBJECT-TYPE
		SYNTAX DisplayString (SIZE (0..255))
		ACCESS read-write
		STATUS mandatory
		DESCRIPTION
		" sys-current-time displays the system current time
		  with 4 digits year, 2 digits month, 2 digits date and
                  hours, minutes and seconds, which are each 2 digits. If the
		  user wants to set the current time, he (she) must follow
		  the correct formats."
                ::={ pro-fun-config 4 }

	current-intv-start-time OBJECT-TYPE
		SYNTAX DisplayString (SIZE (0..255))
		ACCESS read-only
		STATUS mandatory
		DESCRIPTION
		" current-intv-start-time displays the current interval starting
		  time with 4 digits year, 2 digits month, 2 digits date and
                  hours, minutes and seconds, which are each 2 digits."
                ::={ pro-fun-config 5 }


	pvc-Count OBJECT-TYPE
		SYNTAX INTEGER ( 1..20 )
		ACCESS read-only
		STATUS mandatory
		DESCRIPTION
		" PVC count defines the total number of PVCs which are to be
		  probed. The value is between 1 to 20. "
                ::={ pro-fun-config 6 }

	probeTokenSize OBJECT-TYPE
		SYNTAX INTEGER ( 19..4096 )
		ACCESS read-write
		STATUS mandatory
		DESCRIPTION
		" This object defines the probe token size."
                ::={ pro-fun-config 7 }

	pvc-add OBJECT-TYPE
		SYNTAX INTEGER ( 16..991 )
		ACCESS write-only
		STATUS mandatory
		DESCRIPTION
		" This object allows the user to add a PVC to the existing PVC
                  table, the added PVC must not exist before it is added."
                ::={ pro-fun-config 8 }

	pvc-delete OBJECT-TYPE
		SYNTAX INTEGER ( 16..991 )
		ACCESS write-only
		STATUS mandatory
		DESCRIPTION
		" This object allows the user to delete a PVC from the existing PVC
		  table, the deleted PVC must exist before it was deleted."
                ::={ pro-fun-config 9 }


	pvc-Table OBJECT-TYPE
		SYNTAX SEQUENCE OF PVC-Entry
		ACCESS not-accessible
		STATUS mandatory
		DESCRIPTION
		" PVC table, which lists PVCs that currently are probed. "
                ::={ pro-fun-config 10 }

	pvc-Entry OBJECT-TYPE
		SYNTAX PVC-Entry
		ACCESS not-accessible
		STATUS mandatory
		DESCRIPTION
		" Identifies an entry (row) in PVC table."
		INDEX { pvc-Table-Index }
		::={ pvc-Table 1 }

	PVC-Entry ::=
		SEQUENCE {
		  pvc-Table-Index
			INTEGER,
		  pvc-Operation
                        INTEGER,
                  pvc-Remote-IpAddress
                        IpAddress
		  }

	  pvc-Table-Index OBJECT-TYPE
		SYNTAX INTEGER ( 16..991 )
		ACCESS read-only
		STATUS mandatory
		DESCRIPTION
		" Identifies an entry (row) in PVC table. "
		::={ pvc-Entry 1 }

	pvc-Operation OBJECT-TYPE
		SYNTAX INTEGER {
			pvc-not-probed(1),
			pvc-in-waiting(2),
			pvc-probed(3)
			}
		ACCESS read-write
		STATUS mandatory
		DESCRIPTION
                " This object identifies the three possible states which a pvc
                  can be in, '1' means we are just collecting the statistical data
		  for this PVC, '2' means we are not just collecting statistic
		  data for this PVC, but also put it into a pending table waiting
		  for probe, '3' means this PVC is used for both collecting
		  statistic data and probing.  Even though we can view three
                  states for this PVC, we can just set '1' or '2' for this PVC."
		::={ pvc-Entry 2 }

        pvc-Remote-IpAddress OBJECT-TYPE
                SYNTAX IpAddress
                ACCESS read-only
		STATUS mandatory
		DESCRIPTION
                "This object defines the IP address of the remote probe used
                 with IP monitoring."
                ::={ pvc-Entry 3 }


        alternateVersion OBJECT-TYPE
                SYNTAX DisplayString (SIZE (0..10))
                ACCESS read-only
		STATUS mandatory
		DESCRIPTION
                " This object displays the software version we are not currently
                  running, so according to the version number, the user can
                  determine which version is newer."
                ::={ pro-fun-config 11 }


        bypassStatus OBJECT-TYPE
		SYNTAX INTEGER {
                        bypass-off(1),
                        bypass-on(2),
                        bypass-auto(3)
			}
		ACCESS read-write
		STATUS mandatory
		DESCRIPTION
                " This object identifies the three possible states which data bypass
                  can be in. '1' means frame relay data bypass is off.
                   '2' means frame relay data bypass is on.
                  '3' means frame relay data bypass is on and was set on
                  automatically because there was no DCD and no RTS.
                  State '1' can only be set if state is '2'.
                  State '2' can only be set if state is '1'.
                  State '3' cannot be set manually."
                ::={ pro-fun-config 12 }


--
-- Trap Threshold Configuration Group
--
	trapCtlGlobal OBJECT-TYPE
		SYNTAX INTEGER {
			enable(1),
			disable(2)
			}
		ACCESS read-write
		STATUS mandatory
		DESCRIPTION
		" This object is used to enable or disable system traps. Only when
		  it is enabled, the standard traps, such as cold start trap, warm
                  start trap; and enterprise specific traps can be sent."
		::={ trap-config 1 }

	trapCtlSpecific OBJECT-TYPE
		SYNTAX INTEGER (0..65535)
		ACCESS read-write
		STATUS mandatory
		DESCRIPTION
                "This parameter is a bitmap for the 16 enterprise specific traps,
                 zero means all the traps are disabled and 0xffff means all
		 the traps are enabled.  The following lists
                 the 16 bits which are defined:

		 1st bit = pvcNotAvailDCE-trap;
		 2nd bit = pvcNotAvailDTE-trap;
		 3rd bit = pvcAveRTD-trap;
		 4th bit = frChanUtilizeToDTE-trap;
		 5th bit = frChanUtilizeToDCE-trap;
		 6th bit = pvcBecn-trap;
		 7th bit = pvcFecn-trap;
		 8th bit = pvcUtilToDTE-trap;
		 9th bit = pvcUtilToDCE-trap;
		 10th bit = pvcCIRExceed-trap;
		 11th bit = pvcEIRExceed-trap;
		 12th bit = pvcLossFrameTx-trap;
		 13th bit = pvcLossFrameRx-trap;
		 14th bit = all real-time exception and endOfException traps;
                 15th bit = pvcStatusChange;
                 16th bit = dbuTrapsEnable;  "

		::={ trap-config 2 }

	pvcNotAvailThreshDCE OBJECT-TYPE
		SYNTAX INTEGER (0..100)
		ACCESS read-write
		STATUS mandatory
		DESCRIPTION
                "This parameter defines the allowed maximum PVC not availability
                 threshold within current time interval due to a network fault.
                 It is expressed as a percentage of full interval time. If the
                 actual average value is more than this threshold, a trap will
                 be sent at the end of the interval. "
		::={ trap-config 3 }

	pvcNotAvailThreshDTE OBJECT-TYPE
		SYNTAX INTEGER (0..100)
		ACCESS read-write
		STATUS mandatory
		DESCRIPTION
                "This parameter defines the allowed maximum PVC not availability
                 threshold within current time interval due to the local DTE fault.
                 It is expressed as a percentage of full interval time. If the actual
                 average value is more than this threshold, a trap will be sent at
                 the end of the interval. "
		::={ trap-config 4 }

	pvcAveRTDThresh OBJECT-TYPE
		SYNTAX INTEGER (0..500)
		ACCESS read-write
		STATUS mandatory
		DESCRIPTION
                "This parameter defines the allowed maximum PVC round trip time delay
                 (milliseconds) within the current time interval. If the actual average
                 round trip delay is more than this threshold, a trap will be sent at
                 the end of the interval. "
		::={ trap-config 5 }

	frChanUtilizThreshToDTE OBJECT-TYPE
		SYNTAX INTEGER (0..2048)
		ACCESS read-write
		STATUS mandatory
		DESCRIPTION
		"This parameter defines the maximum allowed frame relay channel
		 utilization to the DTE direction. It is expressed in percentage.
                 If the actual average utilization is more than this threshold,
                 a trap will be sent at the end of the interval. "
		::={ trap-config 6 }

	frChanUtilizThreshToDCE OBJECT-TYPE
		SYNTAX INTEGER (0..2048)
		ACCESS read-write
		STATUS mandatory
		DESCRIPTION
                "This parameter defines the maximum allowed frame relay channel
                 utilization to the DCE direction. It is expressed in percentage.
                 If the actual average utilization is more than this threshold,
                 a trap will be sent at the end of the interval. "
		::={ trap-config 7 }

	pvcBecnThresh OBJECT-TYPE
		SYNTAX INTEGER (0..2048)
		ACCESS read-write
		STATUS mandatory
		DESCRIPTION
                "This parameter defines the maximum allowed BECNs for a PVC
                 within current interval. If the actual BECNs are more than this
                 threshold, a trap will be sent at the end of the interval. "
		::={ trap-config 8 }

	pvcFecnThresh OBJECT-TYPE
		SYNTAX INTEGER (0..2048)
		ACCESS read-write
		STATUS mandatory
		DESCRIPTION
                "This parameter defines the maximum allowed FECNs for a PVC
                 within current interval. If the actual FECNs are more than this
                 threshold, a trap will be sent at the end of the interval. "
		::={ trap-config 9 }

	pvcUtilToDTEThresh OBJECT-TYPE
		SYNTAX INTEGER (0..2048)
		ACCESS read-write
		STATUS mandatory
		DESCRIPTION
                "This parameter defines the maximum allowed PVC utilization to DTE
                 within current interval. If the actual average utilization is more
                 than this threshold, a trap will be sent at the end of the interval. "
		::={ trap-config 10 }

	pvcUtilToDCEThresh OBJECT-TYPE
		SYNTAX INTEGER (0..2048)
		ACCESS read-write
		STATUS mandatory
		DESCRIPTION
                "This parameter defines the maximum allowed PVC utilization to DCE
                 within current interval. If the actual average utilization is more
                 than this threshold, a trap will be sent at the end of the interval. "
		::={ trap-config 11 }

        chanLoadToDTEThresh-realTime OBJECT-TYPE
                SYNTAX INTEGER (0..2048)
		ACCESS read-write
		STATUS mandatory
		DESCRIPTION
                "This parameter defines the maximum allowed real-time channel
                 load to the DTE direction (calculated within every TC). It is
                 expressed in percentage. If the actual load is more than this
                 threshold, an exception trap will be sent immediately. "
                ::={ trap-config 12 }

        chanLoadToDCEThresh-realTime OBJECT-TYPE
                SYNTAX INTEGER (0..2048)
		ACCESS read-write
		STATUS mandatory
		DESCRIPTION
                "This parameter defines the maximum allowed real-time channel
                 load to the DCE direction (calculated within every TC). It is
                 expressed in percentage. If the actual load is more than this,
                 threshold, an exception trap will be sent immediately. "
                ::={ trap-config 13 }

        chanLoadThreshToDTE-realTimeRange OBJECT-TYPE
                SYNTAX INTEGER (0..100)
		ACCESS read-write
		STATUS mandatory
		DESCRIPTION
                "This parameter defines the variation range for real-time channel
                 load to the DTE exception trap. If within the current TC interval,
                 the variation of the actual utilization is more than that range
                 compared with previous trap value, another exception trap will be
                 sent immediately. This variation range is defined in percentage. "
                ::={ trap-config 14 }

        chanLoadThreshToDCE-realTimeRange OBJECT-TYPE
                SYNTAX INTEGER (0..100)
		ACCESS read-write
		STATUS mandatory
		DESCRIPTION
                "This parameter defines the variation range for real-time channel
                 load to the DCE exception trap. If within the current TC interval,
                 the variation of the actual utilization is more than that range
                 compared with previous trap value, another exception trap will be
                 sent immediately. This variation range is defined in percentage. "
                ::={ trap-config 15 }

        pvcRTDThresh-realTime OBJECT-TYPE
                SYNTAX INTEGER (0..2048)
		ACCESS read-write
		STATUS mandatory
		DESCRIPTION
                "This parameter defines the maximum allowed real-time PVC
                 Round Trip Delay in msec., it is calculated as the same frequency
                 as the Probe Polls (1 to 60 sec.). If the actual RTD is more than
                 this threshold, an exception trap will be sent immediately. "
                ::={ trap-config 16 }

        pvcRTDThresh-realTimeRange OBJECT-TYPE
                SYNTAX INTEGER (0..100)
		ACCESS read-write
		STATUS mandatory
		DESCRIPTION
                "This parameter defines the variation range for real-time PVC
                 RTD exception trap. If the variation of the current RTD value
                 is more than this range compared with previous trap value, another
                 exception trap or endOfException will be sent immediately. This
                 variation range is defined in percentage. "
                ::={ trap-config 17 }

        pvcLoadToDTEThresh-realTime OBJECT-TYPE
                SYNTAX INTEGER (0..2048)
		ACCESS read-write
		STATUS mandatory
		DESCRIPTION
                "This parameter defines the maximum allowed real-time PVC
                 load to the DTE direction (calculated within every TC). It is
                 expressed in percentage. If the actual load is more than this
                 threshold, an exception trap will be sent immediately. "
                ::={ trap-config 18 }

        pvcLoadToDCEThresh-realTime OBJECT-TYPE
                SYNTAX INTEGER (0..2048)
		ACCESS read-write
		STATUS mandatory
		DESCRIPTION
                "This parameter defines the maximum allowed real-time PVC
                 load to the DCE direction (calculated within every TC). It is
                 expressed in percentage. If the actual load is more than this
                 threshold, an exception trap will be sent immediately. "
                ::={ trap-config 19 }

        pvcLoadToDTEThresh-realTimeRange OBJECT-TYPE
                SYNTAX INTEGER (0..100)
		ACCESS read-write
		STATUS mandatory
		DESCRIPTION
                "This parameter defines the variation range for real-time PVC
                 load to the DTE exception trap. If within the current TC interval,
                 the variation of the actual utilization is more than that range
                 compared with previous trap value, another exception trap will be
                 sent immediately. This variation range is defined in percentage. "
                ::={ trap-config 20 }

        pvcLoadToDCEThresh-realTimeRange OBJECT-TYPE
                SYNTAX INTEGER (0..100)
		ACCESS read-write
		STATUS mandatory
		DESCRIPTION
                "This parameter defines the variation range for real-time PVC
                 load to the DCE exception trap. If within the current TC interval,
                 the variation of the actual utilization is more than that range
                 compared with previous trap value, another exception trap will be
                 sent immediately. This variation range is defined in percentage. "
                ::={ trap-config 21 }

--
-- PVC Configuration Group
--

	pvcTC OBJECT-TYPE
		SYNTAX INTEGER (0..100)
		ACCESS read-write
		STATUS mandatory
		DESCRIPTION
                "This parameter defines the committed rate measurement
                 time interval (in 1/10 second) which can be calculated as
                 Bc/CIR.  For example, if we want TC to be 1 sec., this object
                 should be set as 10."
		::={ pvc-config 1 }

	pvcCirEir-Table OBJECT-TYPE
		SYNTAX SEQUENCE OF PvcCirEir-Entry
		ACCESS not-accessible
		STATUS mandatory
		DESCRIPTION
                " PVC table, which lists PVCs for which the statistical data
		  are collected. "
		::={ pvc-config 2 }

	pvcCirEir-Entry OBJECT-TYPE
		SYNTAX PvcCirEir-Entry
		ACCESS not-accessible
		STATUS mandatory
		DESCRIPTION
		" Identifies an entry (row) in PVC CIR/EIR table."
		INDEX { pvcCirEir-Table-Index }
		::={ pvcCirEir-Table 1 }

	PvcCirEir-Entry ::=
		SEQUENCE {
		  pvcCirEir-Table-Index
			    INTEGER,
		  pvcCirToDTE
		      INTEGER,
		  pvcCirToDCE
		      INTEGER,
		  pvcEirToDTE
		      INTEGER,
		  pvcEirToDCE
		      INTEGER
		  }

	pvcCirEir-Table-Index OBJECT-TYPE
		SYNTAX INTEGER ( 16..991 )
		ACCESS read-only
		STATUS mandatory
		DESCRIPTION
		" Identifies an entry (row) in PVC table. "
		::={ pvcCirEir-Entry    1 }

	pvcCirToDTE OBJECT-TYPE
		SYNTAX INTEGER (1..2048000)
		ACCESS read-write
		STATUS mandatory
		DESCRIPTION
		"This parameter defines the committed information rate (bps)
		 under normal condition in the direction of to DTE. "
		::={ pvcCirEir-Entry    2 }

	pvcCirToDCE OBJECT-TYPE
		SYNTAX INTEGER (1..2048000)
		ACCESS read-write
		STATUS mandatory
		DESCRIPTION
		"This parameter defines the committed information rate (bps)
		 under normal condition in the direction of to DCE. "
		::={ pvcCirEir-Entry    3 }

	pvcEirToDTE OBJECT-TYPE
		SYNTAX INTEGER (0..2048000)
		ACCESS read-write
		STATUS mandatory
		DESCRIPTION
		"This parameter defines the maximum transfer information rate
		 (bps) which the network is accepting in the direction of
		 to DTE. "
		::={ pvcCirEir-Entry    4 }

	pvcEirToDCE OBJECT-TYPE
		SYNTAX INTEGER (0..2048000)
		ACCESS read-write
		STATUS mandatory
		DESCRIPTION
		"This parameter defines the maximum transfer information rate
		 (bps) which the network is accepting in the direction of
		 to DCE. "
		::={ pvcCirEir-Entry    5 }

--
-- file-download-config group
--
-- This group is to define some parameters used by TFTP, whenever the NMS wants
-- to update the agents current software, he needs to setup the IP address that
-- the agent has to down load software from, the name of the file and the format
-- of the file and the tftp action.
--

        sourceIpAddress OBJECT-TYPE
                SYNTAX IpAddress
		ACCESS read-write
		STATUS mandatory
		DESCRIPTION
                "This object defines the IP address of the place where the
                 updated file would store, currently we use a long integer
                 to display."
                ::={ file-download-config 1 }

        sourceFileName OBJECT-TYPE
                SYNTAX DisplayString (SIZE (0..10))
		ACCESS read-write
		STATUS mandatory
		DESCRIPTION
                "This object defines the name of the updated file."
                ::={ file-download-config 2 }

        sourceFileMode OBJECT-TYPE
                SYNTAX INTEGER {
                        netAscii(1)
                }
		ACCESS read-write
		STATUS mandatory
		DESCRIPTION
                "This object defines the mode of the updated file."
                ::={ file-download-config 3 }

        tftpAction OBJECT-TYPE
                SYNTAX INTEGER {
                        getfile(1)
                }
                ACCESS write-only
		STATUS mandatory
		DESCRIPTION
                "This object defines the action we will take of TFTP."
                ::={ file-download-config 4 }

        changeVersion OBJECT-TYPE
                SYNTAX INTEGER {
                        sameVersion(1),
                        switchVersion(2)
                }
                ACCESS read-write
		STATUS mandatory
		DESCRIPTION
                "This object is related to the next software reset object, the user
                 can change the version of software and reset it.  If in the middle
                 of a TFTP transfer, this object cannot be set.  It also
                 cannot be set to switchVersion if there is no other
                 version to which to switch.  An undefined value of 0 is also
                 sameVersion."
                ::={ file-download-config 5 }

        softwareReset OBJECT-TYPE
                SYNTAX INTEGER {
                        reset(1)
                }
                ACCESS write-only
		STATUS mandatory
		DESCRIPTION
                "This object is related to the previous software version object, the
                 user can choose the version of software and reset it. If in the middle
                 of a TFTP transfer, this object can not be set."
                ::={ file-download-config 6 }

        tftpState  OBJECT-TYPE
                SYNTAX INTEGER {
                        idle-ok(1),
                        active(2),
                        idle-failed(3)
                }
                ACCESS read-only
		STATUS mandatory
		DESCRIPTION
                "This object defines the current state of the TFTP download."
                ::={ file-download-config 7 }



--
-- net-management-config group
--
-- This group is to define some parameters used by network management to
-- determine the IP network interface.
--
        ipInterface OBJECT-TYPE
                SYNTAX INTEGER {
                        pppIpInterface(1),
                        ethernetIpInterface(2),
                        privateInbandIpInterface(3),
                        userInbandIpInterface(4),
                        isdnIpInterface(5)
                }
                ACCESS read-write
		STATUS mandatory
		DESCRIPTION
                "This object defines the type of IP interface currently used in
                 the system. pppIpInterface is an asynchronous ppp interface and
                 isdnIpInterface is a synchronous ppp interface."
                ::={ net-management-config 1 }

        inbandIpAddress OBJECT-TYPE
                SYNTAX IpAddress
                ACCESS read-only
		STATUS mandatory
		DESCRIPTION
                "This object defines the IP address of the probe over the
                 inband interface.  Even though separate from outbandIpAddress,
                 this address only used when ipInterface is inbandIpInterface."
                ::={ net-management-config 2 }

        outbandIpAddress OBJECT-TYPE
                SYNTAX IpAddress
                ACCESS read-only
		STATUS mandatory
		DESCRIPTION
                "This object defines the IP address of the probe over the
                 current out of band interface: asynchronous ppp, ethernet,
                 or synchronous ppp over ISDN."
                ::={ net-management-config 3 }

        routerIpAddress OBJECT-TYPE
                SYNTAX IpAddress
                ACCESS read-only
		STATUS mandatory
		DESCRIPTION
                "This object defines the default gateway or next-hop IP address
                 which is used when no route is found."
                ::={ net-management-config 4 }

        subnetmaskIpAddress OBJECT-TYPE
                SYNTAX IpAddress
                ACCESS read-only
		STATUS mandatory
		DESCRIPTION
                "This object defines the network Id portion of our inbandIpAddress
                 or outbandIpAddress."
                ::={ net-management-config 5 }


--
--      LINK PROBE STATISTICS GROUP
--      four sub-groups are defined in this group
--      1. Channel statistics for current interval
--      2. Channel statistics interval table
--      3. PVC statistics current interval table
--      4. PVC statistics interval table
--

--
--      The following chStCurrent group contains various statistics being
--      collected for the current 15 minutes interval.
--

chStCurrent OBJECT IDENTIFIER ::={ probeStat 1 }

	dte-frames-ch-curr OBJECT-TYPE
		SYNTAX Counter
		ACCESS read-only
		STATUS mandatory
		DESCRIPTION
		" Identifies total frames received from DTE device within
		  current 15 minutes interval. "
		::={ chStCurrent 1 }

	dce-frames-ch-curr OBJECT-TYPE
		SYNTAX Counter
		ACCESS read-only
		STATUS mandatory
		DESCRIPTION
		" Identifies total frames received from DCE device within
		  current 15 minutes interval. "
		::={ chStCurrent 2 }

	dte-octets-ch-curr OBJECT-TYPE
		SYNTAX Counter
		ACCESS read-only
		STATUS mandatory
		DESCRIPTION
		" Identifies total octets received from DTE device within
		  current 15 minutes interval. "
		::={ chStCurrent 3 }

	dce-octets-ch-curr OBJECT-TYPE
		SYNTAX Counter
		ACCESS read-only
		STATUS mandatory
		DESCRIPTION
		" Identifies total octets received from DTE device within
		  current 15 minutes interval. "
		::={ chStCurrent 4 }

	lmi-enq-tx-ch-curr OBJECT-TYPE
		SYNTAX Counter
		ACCESS read-only
		STATUS mandatory
		DESCRIPTION
		" Identifies the total number of LMI enquiries sent to DCE
		  within current 15 minutes interval. "
		::={ chStCurrent 5 }

	lmi-resp-tx-ch-curr OBJECT-TYPE
		SYNTAX Counter
		ACCESS read-only
		STATUS mandatory
		DESCRIPTION
		" Identifies the total number of LMI responses sent to DTE
		  within current 15 minutes interval. "
		::={ chStCurrent 6 }

	lmi-enq-rx-ch-curr OBJECT-TYPE
		SYNTAX Counter
		ACCESS read-only
		STATUS mandatory
		DESCRIPTION
		" Identifies the total number of LMI enquiries from the DTE
		  within current 15  minutes interval. "
		::={ chStCurrent 7 }

      lmi-resp-rx-ch-curr OBJECT-TYPE
		SYNTAX Counter
		ACCESS read-only
		STATUS mandatory
		DESCRIPTION
		" Identifies the total number of LMI status responses received
		  from the DCE within current 15 minutes interval. "
		::={ chStCurrent 8 }


	fecn-frames-ch-curr OBJECT-TYPE
		SYNTAX Counter
		ACCESS read-only
		STATUS mandatory
		DESCRIPTION
		" Identifies total number of frames with FECN  set received
		  within current 15 minutes interval. "
		::={ chStCurrent 9 }

	becn-frames-ch-curr OBJECT-TYPE
		SYNTAX Counter
		ACCESS read-only
		STATUS mandatory
		DESCRIPTION
		" Identifies total number of frames with BECN  set received
		  within current 15 minutes interval. "
		::={ chStCurrent 10 }

	ip-tx-ch-curr OBJECT-TYPE
		SYNTAX Counter
		ACCESS read-only
		STATUS mandatory
		DESCRIPTION
		" Identifies total number of IP packets sent on inband DLCI
		  within current 15 minutes interval. "
		::={ chStCurrent 11 }

	ip-rx-ch-curr OBJECT-TYPE
		SYNTAX Counter
		ACCESS read-only
		STATUS mandatory
		DESCRIPTION
		" Identifies total number of IP packets received on inband
		  DLCI within current 15 minutes interval. "
		::={ chStCurrent 12 }

	poll-tx-ch-curr OBJECT-TYPE
		SYNTAX Counter
		ACCESS read-only
		STATUS mandatory
		DESCRIPTION
		" Identifies total number of probe polls sent to DCE within
		  current 15 minutes interval. "
		::={ chStCurrent 13 }


	resp-tx-ch-curr OBJECT-TYPE
		SYNTAX Counter
		ACCESS read-only
		STATUS mandatory
		DESCRIPTION
		" Identifies total number of probe responses sent to DCE
		  within current 15 minutes interval. "
		::={ chStCurrent 14 }

	poll-rx-ch-curr OBJECT-TYPE
		SYNTAX Counter
		ACCESS read-only
		STATUS mandatory
		DESCRIPTION
		" Identifies total number of probe polls received from DCE
		  within current 15 minutes interval. "
		::={ chStCurrent 15 }

	resp-rx-ch-curr OBJECT-TYPE
		SYNTAX Counter
		ACCESS read-only
		STATUS mandatory
		DESCRIPTION
		" Identifies total number of probe responses received from
		  DCE within current 15 minutes interval. "
		::={ chStCurrent 16 }



--
--      The channel statistic interval table contains various statistics
--      collected over the previous 24 hours of operation.  The past
--      24 hours are broken into 96 completed 15-minute intervals.
--      A -1 value indicates interval is prior to system power-on.  This
--      does not apply to indices, such as PVC and interval number.
--


	chStInterval-Table OBJECT-TYPE
		SYNTAX SEQUENCE OF ChStInterval-Entry
		ACCESS not-accessible
		STATUS mandatory
		DESCRIPTION
		" probe statistic table, row 1 to row 96,
		  which defines the time interval for every 15
		  minutes. "
		::={ probeStat 2 }

	chStInterval-Entry OBJECT-TYPE
		SYNTAX ChStInterval-Entry
		ACCESS not-accessible
		STATUS mandatory
		DESCRIPTION
		" Identifies an entry (row) in probe statistic table."
		INDEX { chStIntv-index }
		::={ chStInterval-Table 1 }

	ChStInterval-Entry ::=
		SEQUENCE {
		  chStIntv-index
			INTEGER,
		  dte-frames-ch-intv
			Counter,
		  dce-frames-ch-intv
			Counter,
		  dte-octets-ch-intv
			Counter,
		  dce-octets-ch-intv
			Counter,
		  lmi-enq-tx-ch-intv
			Counter,
		  lmi-resp-tx-ch-intv
			Counter,
		  lmi-enq-rx-ch-intv
			Counter,
		  lmi-resp-rx-ch-intv
			Counter,
		  fecn-frames-ch-intv
			Counter,
		  becn-frames-ch-intv
			Counter,
		  ip-tx-ch-intv
			Counter,
		  ip-rx-ch-intv
			Counter,
		  poll-tx-ch-intv
			Counter,
		  resp-tx-ch-intv
			Counter,
		  poll-rx-ch-intv
			Counter,
		  resp-rx-ch-intv
			Counter

		}

	chStIntv-index OBJECT-TYPE
		SYNTAX INTEGER ( 1..96 )
		ACCESS read-only
		STATUS mandatory
		DESCRIPTION
		" Identifies an entry (row) in channel statistic table,
		  1-96 time intervals. "
		::={ chStInterval-Entry 1 }

	dte-frames-ch-intv OBJECT-TYPE
		SYNTAX Counter
		ACCESS read-only
		STATUS mandatory
		DESCRIPTION
		" Identifies total frames received from DTE device within a 15
		  minutes interval. "
		::={ chStInterval-Entry 2 }

	dce-frames-ch-intv OBJECT-TYPE
		SYNTAX Counter
		ACCESS read-only
		STATUS mandatory
		DESCRIPTION
		" Identifies total frames received from DCE device within a 15
		  minutes interval. "
		::={ chStInterval-Entry 3 }

	dte-octets-ch-intv OBJECT-TYPE
		SYNTAX Counter
		ACCESS read-only
		STATUS mandatory
		DESCRIPTION
		" Identifies total octets received from DTE device within a 15
		  minutes interval. "
		::={ chStInterval-Entry 4 }

	dce-octets-ch-intv OBJECT-TYPE
		SYNTAX Counter
		ACCESS read-only
		STATUS mandatory
		DESCRIPTION
		" Identifies total octets received from DTE device within a 15
		  minutes interval. "
		::={ chStInterval-Entry 5 }

	lmi-enq-tx-ch-intv OBJECT-TYPE
		SYNTAX Counter
		ACCESS read-only
		STATUS mandatory
		DESCRIPTION
		" Identifies the total number of LMI enquiries sent to DCE
		  within a 15 minutes interval. "
		::={ chStInterval-Entry 6 }

	lmi-resp-tx-ch-intv OBJECT-TYPE
		SYNTAX Counter
		ACCESS read-only
		STATUS mandatory
		DESCRIPTION
		" Identifies the total number of LMI responses send to
		  DTE within a 15 minutes interval. "
		::={ chStInterval-Entry 7 }


	lmi-enq-rx-ch-intv OBJECT-TYPE
		SYNTAX Counter
		ACCESS read-only
		STATUS mandatory
		DESCRIPTION
		" Identifies the total number of LMI enquiries received
		  within a 15 minutes interval. "
		::={ chStInterval-Entry 8 }

      lmi-resp-rx-ch-intv OBJECT-TYPE
		SYNTAX Counter
		ACCESS read-only
		STATUS mandatory
		DESCRIPTION
		" Identifies the total number of LMI status responses received
		  from the DCE within a 15 minutes interval. "
		::={ chStInterval-Entry 9 }


	fecn-frames-ch-intv OBJECT-TYPE
		SYNTAX Counter
		ACCESS read-only
		STATUS mandatory
		DESCRIPTION
		" Identifies total number of frames with FECN  set received within a 15
		  minutes interval. "
		::={ chStInterval-Entry 10 }

	becn-frames-ch-intv OBJECT-TYPE
		SYNTAX Counter
		ACCESS read-only
		STATUS mandatory
		DESCRIPTION
		" Identifies total number of frames with BECN  set received within a 15
		  minutes interval. "
		::={ chStInterval-Entry 11 }

	ip-tx-ch-intv OBJECT-TYPE
		SYNTAX Counter
		ACCESS read-only
		STATUS mandatory
		DESCRIPTION
		" Identifies total number of IP packets sent on inband DLCI
		  within a 15 minutes interval. "
		::={ chStInterval-Entry 12 }

	ip-rx-ch-intv OBJECT-TYPE
		SYNTAX Counter
		ACCESS read-only
		STATUS mandatory
		DESCRIPTION
		" Identifies total number of IP packets received on inband
		  DLCI within a 15 minutes interval. "
		::={ chStInterval-Entry 13 }

	poll-tx-ch-intv OBJECT-TYPE
		SYNTAX Counter
		ACCESS read-only
		STATUS mandatory
		DESCRIPTION
		" Identifies total number of probe polls sent to DCE within
		  a 15 minutes interval. "
		::={ chStInterval-Entry 14 }

	resp-tx-ch-intv OBJECT-TYPE
		SYNTAX Counter
		ACCESS read-only
		STATUS mandatory
		DESCRIPTION
		" Identifies total number of probe response sent to DCE within
		  a 15 minutes interval. "
		::={ chStInterval-Entry 15 }

	poll-rx-ch-intv OBJECT-TYPE
		SYNTAX Counter
		ACCESS read-only
		STATUS mandatory
		DESCRIPTION
		" Identifies total number of probe polls received from DCE
		  within a 15 minutes interval. "
		::={ chStInterval-Entry 16 }

	resp-rx-ch-intv OBJECT-TYPE
		SYNTAX Counter
		ACCESS read-only
		STATUS mandatory
		DESCRIPTION
		" Identifies total number of probe responses received from
		  DCE within a 15 minutes interval. "
		::={ chStInterval-Entry 17 }



--
--      The  current PVC statistic table contains various statistics being
--      collected by each PVC for the current 15 minutes interval.
--

	pvcStCurrent-Table OBJECT-TYPE
		SYNTAX SEQUENCE OF PVCStCurrent-entry
		ACCESS not-accessible
		STATUS mandatory
		DESCRIPTION
		" PVC statistic table."
		::={ probeStat 3 }

	pvcStCurrent-Entry OBJECT-TYPE
		SYNTAX PVCStCurrent-entry
		ACCESS not-accessible
		STATUS mandatory
		DESCRIPTION
		" Identifies an entry (row) in PVC statistic table"
		INDEX { pvc-number-index-curr }
		::={ pvcStCurrent-Table 1 }

	PVCStCurrent-entry ::=
		SEQUENCE {
		  pvc-number-index-curr
			INTEGER,
		  dte-frames-pvc-curr
			Counter,
		  dce-frames-pvc-curr
			Counter,
		  dte-octets-pvc-curr
			Counter,
		  dce-octets-pvc-curr
			Counter,
		  dte-frames-with-DE-pvc-curr
			Counter,
		  dce-frames-with-DE-pvc-curr
			Counter,
		  fecn-frames-pvc-curr
			Counter,
		  becn-frames-pvc-curr
			Counter,
		  poll-tx-pvc-curr
			Counter,
		  resp-tx-pvc-curr
			Counter,
		  poll-rx-pvc-curr
			Counter,
		  resp-rx-pvc-curr
			Counter,
		  pvc-loop-curr
                        INTEGER,
                  ip-poll-tx-pvc-curr
			Counter,
                  ip-resp-tx-pvc-curr
			Counter,
                  ip-poll-rx-pvc-curr
			Counter,
                  ip-resp-rx-pvc-curr
                        Counter,
                  ipRtrRxLatTxPvcCurr
			Counter,
                  ipRtrRxLatRxPvcCurr
			Counter,
                  ipRtrTxLatTxPvcCurr
			Counter,
                  ipRtrTxLatRxPvcCurr
			Counter
		}

	 pvc-number-index-curr OBJECT-TYPE
		SYNTAX INTEGER ( 16..991 )
		ACCESS read-only
		STATUS mandatory
		DESCRIPTION
		" Index in PVC statistics table, which identifies
		  the PVC number, up to 20 PVCs can exist. "
		::={ pvcStCurrent-Entry 1 }

	dte-frames-pvc-curr OBJECT-TYPE
		SYNTAX Counter
		ACCESS read-only
		STATUS mandatory
		DESCRIPTION
		" Identifies total frames received from DTE device for a
		  specific PVC within current 15 minutes interval. "
		::={ pvcStCurrent-Entry 2 }

	dce-frames-pvc-curr OBJECT-TYPE
		SYNTAX Counter
		ACCESS read-only
		STATUS mandatory
		DESCRIPTION
		" Identifies total frames received from DCE device for a
		  specific PVC within current 15 minutes interval. "
		::={ pvcStCurrent-Entry 3 }

	dte-octets-pvc-curr OBJECT-TYPE
		SYNTAX Counter
		ACCESS read-only
		STATUS mandatory
		DESCRIPTION
		" Identifies total octets received from DTE device for a
		  specific PVC within current 15 minutes interval. "
		::={ pvcStCurrent-Entry 4 }

	dce-octets-pvc-curr OBJECT-TYPE
		SYNTAX Counter
		ACCESS read-only
		STATUS mandatory
		DESCRIPTION
		" Identifies total octets received from DTE device for a
		  specific PVC within current 15 minutes interval. "
		::={ pvcStCurrent-Entry 5 }

	dte-frames-with-DE-pvc-curr OBJECT-TYPE
		SYNTAX Counter
		ACCESS read-only
		STATUS mandatory
		DESCRIPTION
		" Identifies total frames with DE bit set received from DTE device
		  for a specific PVC within current 15 minutes interval. "
		::={ pvcStCurrent-Entry 6 }

	dce-frames-with-DE-pvc-curr OBJECT-TYPE
		SYNTAX Counter
		ACCESS read-only
		STATUS mandatory
		DESCRIPTION
		" Identifies total frames with DE bit set received from DCE device
		  for a specific PVC within current 15 minutes interval. "
		::={ pvcStCurrent-Entry 7 }

	fecn-frames-pvc-curr OBJECT-TYPE
		SYNTAX Counter
		ACCESS read-only
		STATUS mandatory
		DESCRIPTION
		" Identifies total number of frames for a specific PVC
		  with FECN  set received within current 15 minutes interval. "
		::={ pvcStCurrent-Entry 8 }

	becn-frames-pvc-curr OBJECT-TYPE
		SYNTAX Counter
		ACCESS read-only
		STATUS mandatory
		DESCRIPTION
		" Identifies total number of frames for a specific PVC
		  with BECN  set received within current 15 minutes interval. "
		::={ pvcStCurrent-Entry 9 }

	poll-tx-pvc-curr OBJECT-TYPE
		SYNTAX Counter
		ACCESS read-only
		STATUS mandatory
		DESCRIPTION
		" Identifies total number of probe polls sent to DCE within
		  current 15  minutes interval. "
		::={ pvcStCurrent-Entry 10 }

	resp-tx-pvc-curr OBJECT-TYPE
		SYNTAX Counter
		ACCESS read-only
		STATUS mandatory
		DESCRIPTION
		" Identifies total number of probe responses sent to DCE
		  within current 15  minutes interval. "
		::={ pvcStCurrent-Entry 11 }

	poll-rx-pvc-curr OBJECT-TYPE
		SYNTAX Counter
		ACCESS read-only
		STATUS mandatory
		DESCRIPTION
		" Identifies total number of probe polls received from DCE
		  on a specific PVC within current 15 minutes interval. "
		::={ pvcStCurrent-Entry 12 }

	resp-rx-pvc-curr OBJECT-TYPE
		SYNTAX Counter
		ACCESS read-only
		STATUS mandatory
		DESCRIPTION
		" Identifies total number of probe responses received from DCE
		  on a specific PVC within current 15 minutes interval. "
		::={ pvcStCurrent-Entry 13 }


      pvc-loop-curr OBJECT-TYPE
		SYNTAX INTEGER {
			loopback(1),
			no-loopback(2)
		}
		ACCESS read-only
		STATUS mandatory
		DESCRIPTION
		" Identifies whether the specific PVC has been found to be in a loop
		  back state by link probe's generator process. "
		::={ pvcStCurrent-Entry 14 }

        ip-poll-tx-pvc-curr OBJECT-TYPE
		SYNTAX Counter
		ACCESS read-only
		STATUS mandatory
		DESCRIPTION
                " Identifies total number of probe IP polls sent to ethernet within
		  current 15  minutes interval. "
                ::={ pvcStCurrent-Entry 15 }

        ip-resp-tx-pvc-curr OBJECT-TYPE
		SYNTAX Counter
		ACCESS read-only
		STATUS mandatory
		DESCRIPTION
                " Identifies total number of probe IP responses sent to ethernet
		  within current 15  minutes interval. "
                ::={ pvcStCurrent-Entry 16 }

        ip-poll-rx-pvc-curr OBJECT-TYPE
		SYNTAX Counter
		ACCESS read-only
		STATUS mandatory
		DESCRIPTION
                " Identifies total number of probe IP polls received from ethernet
		  on a specific PVC within current 15 minutes interval. "
                ::={ pvcStCurrent-Entry 17 }

        ip-resp-rx-pvc-curr OBJECT-TYPE
		SYNTAX Counter
		ACCESS read-only
		STATUS mandatory
		DESCRIPTION
                " Identifies total number of probe IP responses received from
                  ethernet on a specific PVC within current 15 minutes interval. "
                ::={ pvcStCurrent-Entry 18 }

        ipRtrRxLatTxPvcCurr OBJECT-TYPE
		SYNTAX Counter
		ACCESS read-only
		STATUS mandatory
		DESCRIPTION
                " Identifies total number of Router Receive Latency IP
		  packets transmitted out the To-Dte port within current
		  15 minute interval. "
                ::={ pvcStCurrent-Entry 19 }

        ipRtrRxLatRxPvcCurr OBJECT-TYPE
		SYNTAX Counter
		ACCESS read-only
		STATUS mandatory
		DESCRIPTION
                " Identifies total number of Router Receive Latency IP
		  packets received at the Ethernet port within current
		  15 minute interval. "
                ::={ pvcStCurrent-Entry 20 }

        ipRtrTxLatTxPvcCurr OBJECT-TYPE
		SYNTAX Counter
		ACCESS read-only
		STATUS mandatory
		DESCRIPTION
                " Identifies total number of Router Transmit Latency IP
		  packets transmitted out the Ethernet port within current
		  15 minute interval. "
                ::={ pvcStCurrent-Entry 21 }

        ipRtrTxLatRxPvcCurr OBJECT-TYPE
		SYNTAX Counter
		ACCESS read-only
		STATUS mandatory
		DESCRIPTION
                " Identifies total number of Router Transmit Latency IP
		  packets received at the To-Dte port within current
		  15 minute interval. "
                ::={ pvcStCurrent-Entry 22 }

--
--      The PVC statistic interval table contains various statistics
--    collected for each PVC over the previous 24 hours of operation.
--      The past 24 hours are broken into 96 completed 15-minute intervals.
--      A -1 value indicates interval is prior to system power-on.  This
--      does not apply to indices, such as PVC and interval number.
--

	pvcStInterval-Table OBJECT-TYPE
		SYNTAX SEQUENCE OF PVCStInterval-entry
		ACCESS not-accessible
		STATUS mandatory
		DESCRIPTION
		" PVC statistic interval table: "
		::={ probeStat 4 }

	pvcStInterval-Entry OBJECT-TYPE
		SYNTAX PVCStInterval-entry
		ACCESS not-accessible
		STATUS mandatory
		DESCRIPTION
		" Identifies an entry (row) in pvc statistic table"
		INDEX { pvc-number-index-intv, pvcStIntv-index }
		::={ pvcStInterval-Table 1 }

	PVCStInterval-entry ::=
		SEQUENCE {
		  pvc-number-index-intv
			INTEGER,
		  pvcStIntv-index
			INTEGER,
		  dte-frames-pvc-intv
			Counter,
		  dce-frames-pvc-intv
			Counter,
		  dte-octets-pvc-intv
			Counter,
		  dce-octets-pvc-intv
			Counter,
		  dte-frames-with-DE-pvc-intv
			Counter,
		  dce-frames-with-DE-pvc-intv
			Counter,
		  fecn-frames-pvc-intv
			Counter,
		  becn-frames-pvc-intv
			Counter,
		  poll-tx-pvc-intv
			Counter,
		  resp-tx-pvc-intv
			Counter,
		  poll-rx-pvc-intv
			Counter,
		  resp-rx-pvc-intv
			Counter,
                  pvc-loop-intv
                        INTEGER,
                  ip-poll-tx-pvc-intv
			Counter,
                  ip-resp-tx-pvc-intv
			Counter,
                  ip-poll-rx-pvc-intv
			Counter,
                  ip-resp-rx-pvc-intv
                        Counter,
                  ipRtrRxLatTxPvcIntv
			Counter,
                  ipRtrRxLatRxPvcIntv
			Counter,
                  ipRtrTxLatTxPvcIntv
			Counter,
                  ipRtrTxLatRxPvcIntv
			Counter

		}

	   pvc-number-index-intv OBJECT-TYPE
		SYNTAX INTEGER ( 16..991 )
		ACCESS read-only
		STATUS mandatory
		DESCRIPTION
                " The index value which uniquely identifies the PVC
		  number to which this entry is applicable. "
		::={ pvcStInterval-Entry 1 }

	pvcStIntv-index OBJECT-TYPE
		SYNTAX INTEGER ( 1..96 )
		ACCESS read-only
		STATUS mandatory
		DESCRIPTION
		" A number between 1 and 96, where 1 is the most recently
		  completed 15 minutes interval and 96 is the least recently
		 completed 15 minutes interval. "
		::={ pvcStInterval-Entry 2 }


	dte-frames-pvc-intv OBJECT-TYPE
		SYNTAX Counter
		ACCESS read-only
		STATUS mandatory
		DESCRIPTION
		" Identifies total frames received from DTE device for a
		  specific PVC within a 15 minutes interval. "
		::={ pvcStInterval-Entry 3 }

	dce-frames-pvc-intv OBJECT-TYPE
		SYNTAX Counter
		ACCESS read-only
		STATUS mandatory
		DESCRIPTION
		" Identifies total frames received from DCE device for a
		  specific PVC within a 15 minutes interval. "
		::={ pvcStInterval-Entry 4 }

	dte-octets-pvc-intv OBJECT-TYPE
		SYNTAX Counter
		ACCESS read-only
		STATUS mandatory
		DESCRIPTION
		" Identifies total octets received from DTE device for a
		  specific PVC within a 15 minutes interval. "
		::={ pvcStInterval-Entry 5 }

	dce-octets-pvc-intv OBJECT-TYPE
		SYNTAX Counter
		ACCESS read-only
		STATUS mandatory
		DESCRIPTION
		" Identifies total octets received from DTE device for a
		  specific PVC within a 15 minutes interval. "
		::={ pvcStInterval-Entry 6 }

	dte-frames-with-DE-pvc-intv OBJECT-TYPE
		SYNTAX Counter
		ACCESS read-only
		STATUS mandatory
		DESCRIPTION
		" Identifies the frames with DE bit set received from DTE device
		  for a specific PVC within a 15 minutes interval. "
		::={ pvcStInterval-Entry 7 }

	dce-frames-with-DE-pvc-intv OBJECT-TYPE
		SYNTAX Counter
		ACCESS read-only
		STATUS mandatory
		DESCRIPTION
		" Identifies the frames with DE bit set received from DCE device
		  for a specific PVC within a 15 minutes interval. "
		::={ pvcStInterval-Entry 8 }

	  fecn-frames-pvc-intv OBJECT-TYPE
		SYNTAX Counter
		ACCESS read-only
		STATUS mandatory
		DESCRIPTION
		" Identifies total number of frames for a specific PVC
		  with FECN  set received within a 15 minutes interval. "
		::={ pvcStInterval-Entry 9 }

	  becn-frames-pvc-intv OBJECT-TYPE
		SYNTAX Counter
		ACCESS read-only
		STATUS mandatory
		DESCRIPTION
		" Identifies total number of frames for a specific PVC
		  with BECN  set received within a 15 minutes interval. "
		::={ pvcStInterval-Entry 10 }

	  poll-tx-pvc-intv OBJECT-TYPE
		SYNTAX Counter
		ACCESS read-only
		STATUS mandatory
		DESCRIPTION
		" Identifies total number of probe polls sent to DCE within
		  a 15 minutes interval. "
		::={ pvcStInterval-Entry 11 }

	  resp-tx-pvc-intv OBJECT-TYPE
		SYNTAX Counter
		ACCESS read-only
		STATUS mandatory
		DESCRIPTION
		" Identifies total number of probe responses sent to DCE
		  within a 15 minutes interval. "
		::={ pvcStInterval-Entry 12 }

	  poll-rx-pvc-intv OBJECT-TYPE
		SYNTAX Counter
		ACCESS read-only
		STATUS mandatory
		DESCRIPTION
		" Identifies total number of probe polls received from DCE
		  on a specific PVC within a 15 minutes interval. "
		::={ pvcStInterval-Entry 13 }

	  resp-rx-pvc-intv OBJECT-TYPE
		SYNTAX Counter
		ACCESS read-only
		STATUS mandatory
		DESCRIPTION
		" Identifies total number of probe responses received from
		  DCE on a specific PVC within a 15 minutes interval. "
		::={ pvcStInterval-Entry 14 }

	pvc-loop-intv OBJECT-TYPE
		SYNTAX INTEGER
		ACCESS read-only
		STATUS mandatory
		DESCRIPTION
		" Identifies whether the specific PVC has been found to be in a loop
		  back state by link probe's generator process. "
		::={ pvcStInterval-Entry 15 }

          ip-poll-tx-pvc-intv OBJECT-TYPE
		SYNTAX Counter
		ACCESS read-only
		STATUS mandatory
		DESCRIPTION
                " Identifies total number of probe IP polls sent to ethernet within
		  a 15 minutes interval. "
                ::={ pvcStInterval-Entry 16 }

          ip-resp-tx-pvc-intv OBJECT-TYPE
		SYNTAX Counter
		ACCESS read-only
		STATUS mandatory
		DESCRIPTION
                " Identifies total number of probe IP responses sent to ethernet
		  within a 15 minutes interval. "
                ::={ pvcStInterval-Entry 17 }

          ip-poll-rx-pvc-intv OBJECT-TYPE
		SYNTAX Counter
		ACCESS read-only
		STATUS mandatory
		DESCRIPTION
                " Identifies total number of probe IP polls received from ethernet
		  on a specific PVC within a 15 minutes interval. "
                ::={ pvcStInterval-Entry 18 }

          ip-resp-rx-pvc-intv OBJECT-TYPE
		SYNTAX Counter
		ACCESS read-only
		STATUS mandatory
		DESCRIPTION
                " Identifies total number of probe IP responses received from
                  ethernet on a specific PVC within a 15 minutes interval. "
                ::={ pvcStInterval-Entry 19 }

        ipRtrRxLatTxPvcIntv OBJECT-TYPE
		SYNTAX Counter
		ACCESS read-only
		STATUS mandatory
		DESCRIPTION
                " Identifies total number of Router Receive Latency IP
		  packets transmitted out the To-Dte port within a
		  15 minute interval. "
                ::={ pvcStInterval-Entry 20 }

        ipRtrRxLatRxPvcIntv OBJECT-TYPE
		SYNTAX Counter
		ACCESS read-only
		STATUS mandatory
		DESCRIPTION
                " Identifies total number of Router Receive Latency IP
		  packets received at the Ethernet port within a
		  15 minute interval. "
                ::={ pvcStInterval-Entry 21 }

        ipRtrTxLatTxPvcIntv OBJECT-TYPE
		SYNTAX Counter
		ACCESS read-only
		STATUS mandatory
		DESCRIPTION
                " Identifies total number of Router Transmit Latency IP
		  packets transmitted out the Ethernet port within a
		  15 minute interval. "
                ::={ pvcStInterval-Entry 22 }

        ipRtrTxLatRxPvcIntv OBJECT-TYPE
		SYNTAX Counter
		ACCESS read-only
		STATUS mandatory
		DESCRIPTION
                " Identifies total number of Router Transmit Latency IP
		  packets received at the To-Dte port within a
		  15 minute interval. "
                ::={ pvcStInterval-Entry 23 }

--
-- Subgroup in probe performance group
--
-- 1. Channel Performance Current 15 Minutes Data
-- 2. Channel Performance Historical Data (up to 96 15-min. interval)
-- 3. PVC performance Current 15 Minutes Data
-- 4. PVC Performance Historical Data (up to 96 15-min. interval)
--


--
-- 1. Current Channel Performance Group displays the statistical data which
--    measure the channel performance within the latest 15 minutes.
--

chanPerfCurr OBJECT IDENTIFIER ::={ probePerform 1 }

	chan-unvail-toDte-curr OBJECT-TYPE
                SYNTAX DisplayString (SIZE (0..6))
		ACCESS read-only
		STATUS mandatory
		DESCRIPTION
		" This object identifies the channel unavailability due to remote
                  DTE fault within the latest 15 minutes. This statistical data is
		  calculated by the channel unavailable time over the full time
		  interval."
		::={ chanPerfCurr 1 }

	chan-unavail-toDce-curr OBJECT-TYPE
                SYNTAX DisplayString (SIZE (0..6))
		ACCESS read-only
		STATUS mandatory
		DESCRIPTION
		" This object identifies the channel unavailability due to local
                  DTE fault within the latest 15 minutes. This statistical data is
		  calculated by the channel unavailable time over the full time
		  interval."
		::={ chanPerfCurr 2 }

	chan-user-load-tx-curr OBJECT-TYPE
                SYNTAX DisplayString (SIZE (0..6))
		ACCESS read-only
		STATUS mandatory
		DESCRIPTION
		" channel average user tx load within the latest 15 minutes,
                  this statistical data is calculated by user data octets sent
		  by the channel within the 15 minutes over the total channel
		  available load ( which depends on physical interface speed). "
		::={ chanPerfCurr 3 }

	chan-user-load-rx-curr OBJECT-TYPE
                SYNTAX DisplayString (SIZE (0..6))
		ACCESS read-only
		STATUS mandatory
		DESCRIPTION
		" channel average user rx load within the latest 15 minutes,
                  this statistical data is calculated by user data octets received
		  by the channel within the 15 minutes over the total channel
		  available load ( which depends on physical interface speed). "
		::={ chanPerfCurr 4 }

	chan-total-load-tx-curr OBJECT-TYPE
                SYNTAX DisplayString (SIZE (0..6))
		ACCESS read-only
		STATUS mandatory
		DESCRIPTION
		" channel total tx load within the latest 15 minutes,
                  this statistical data is calculated by the total data octets
		  sent by the channel within the 15 minutes over the channel
		  available load ( which depends on physical interface speed). "
		::={ chanPerfCurr 5 }

	chan-total-load-rx-curr OBJECT-TYPE
                SYNTAX DisplayString (SIZE (0..6))
		ACCESS read-only
		STATUS mandatory
		DESCRIPTION
		" channel total rx load within the latest 15 minutes,
                  this statistical data is calculated by total data octets received
		  by the channel within the 15 minutes over the channel total
		  available load ( which depends on physical interface speed). "
		::={ chanPerfCurr 6 }


--
-- 2. Channel Performance Interval Group displays the statistical data which
--    measure the channel performance over the previous 24 hours of operation.
--    The past 24 hours are broken into 96 completed 15 minutes intervals.
--    A -1 value indicates interval is prior to system power-on.  This
--    does not apply to indices, such as PVC and interval number.
--

	chanPerfIntv-Table OBJECT-TYPE
		SYNTAX SEQUENCE OF ChanPerfIntv-Entry
		ACCESS not-accessible
		STATUS mandatory
		DESCRIPTION
		" Probe channel performance table, which displays
                  the performance statistical data based on the probe
		  channel within previous 24 hours."
		::={ probePerform 2 }

	chanPerfIntv-Entry OBJECT-TYPE
		SYNTAX ChanPerfIntv-Entry
		ACCESS not-accessible
		STATUS mandatory
		DESCRIPTION
		" Identifies an entry (row) in probe channel performance
		  table."
		INDEX { chanPerfIntv-index }
		::={ chanPerfIntv-Table 1 }

	ChanPerfIntv-Entry ::=
		SEQUENCE {
		  chanPerfIntv-index
			      INTEGER,
		  chan-unavail-toDte-intv
                        DisplayString,
		  chan-unavail-toDce-intv
                        DisplayString,
		  chan-user-load-tx-intv
                        DisplayString,
		  chan-user-load-rx-intv
                        DisplayString,
		  chan-total-load-tx-intv
                        DisplayString,
		  chan-total-load-rx-intv
                        DisplayString,
                  chan-min-user-load-tx-intv
                        DisplayString,
                  chan-min-user-load-tx-time-intv
                        DisplayString,
                  chan-min-user-load-rx-intv
                        DisplayString,
                  chan-min-user-load-rx-time-intv
                        DisplayString,
                  chan-min-total-load-tx-intv
                        DisplayString,
                  chan-min-total-load-tx-time-intv
                        DisplayString,
                  chan-min-total-load-rx-intv
                        DisplayString,
                  chan-min-total-load-rx-time-intv
                        DisplayString,
                  chan-max-user-load-tx-intv
                        DisplayString,
                  chan-max-user-load-tx-time-intv
                        DisplayString,
                  chan-max-user-load-rx-intv
                        DisplayString,
                  chan-max-user-load-rx-time-intv
                        DisplayString,
                  chan-max-total-load-tx-intv
                        DisplayString,
                  chan-max-total-load-tx-time-intv
                        DisplayString,
                  chan-max-total-load-rx-intv
                        DisplayString,
                  chan-max-total-load-rx-time-intv
                        DisplayString

		}

	chanPerfIntv-index OBJECT-TYPE
		SYNTAX INTEGER (1..96)
		ACCESS read-only
		STATUS mandatory
		DESCRIPTION
		" Identifies an entry (row) in historical PVC performance table,
		  total 96 time intervals, where 1 is the most recently completed
		  15 minutes interval and 96 is the least recently completed 15
		  minutes interval (assuming that all 96 intervals are valid).  "
		::={ chanPerfIntv-Entry 1 }

	chan-unavail-toDte-intv OBJECT-TYPE
                SYNTAX DisplayString (SIZE (0..6))
		ACCESS read-only
		STATUS mandatory
		DESCRIPTION
		" This object identifies the channel unavailability due to remote
                  DTE fault within a 15 minutes interval. This statistical data is
		  calculated by the channel unavailable time over the full time
		  interval."
		::={ chanPerfIntv-Entry 2 }

	chan-unavail-toDce-intv OBJECT-TYPE
                SYNTAX DisplayString (SIZE (0..6))
		ACCESS read-only
		STATUS mandatory
		DESCRIPTION
		" This object identifies the channel unavailability due to local
                  DTE fault within a 15 minutes interval. This statistical data is
		  calculated by the channel unavailable time over the full time
		  interval."
		::={ chanPerfIntv-Entry 3 }

	chan-user-load-tx-intv OBJECT-TYPE
                SYNTAX DisplayString (SIZE (0..6))
		ACCESS read-only
		STATUS mandatory
		DESCRIPTION
		" channel average user tx load within a 15 minutes interval,
                  this statistical data is calculated by user data octets sent by
		  the channel within the 15 minutes over the total channel
		  available load ( which depends on physical interface speed). "
		::={ chanPerfIntv-Entry 4 }

	chan-user-load-rx-intv OBJECT-TYPE
                SYNTAX DisplayString (SIZE (0..6))
		ACCESS read-only
		STATUS mandatory
		DESCRIPTION
		" channel average user rx load within a 15 minutes interval,
                  this statistical data is calculated by user data octets received
		  by the channel within the 15 minutes over the total channel
		  available load( which depends on physical interface speed). "
		::={ chanPerfIntv-Entry 5 }

	chan-total-load-tx-intv OBJECT-TYPE
                SYNTAX DisplayString (SIZE (0..6))
		ACCESS read-only
		STATUS mandatory
		DESCRIPTION
		" channel total tx load within a 15 minutes interval,
                  this statistical data is calculated by the total data octets
		  sent by the channel within the 15 minutes over the total
		  channel available load ( which depends on physical interface speed). "
		::={ chanPerfIntv-Entry 6 }

	chan-total-load-rx-intv OBJECT-TYPE
                SYNTAX DisplayString (SIZE (0..6))
		ACCESS read-only
		STATUS mandatory
		DESCRIPTION
		" Channel total rx load within a 15 minutes interval,
                  this statistical data is calculated by the total data octets
		  received by the channel within the 15 minutes over the total channel
		  available load ( which depends on physical interface speed). "
		::={ chanPerfIntv-Entry 7 }

        chan-min-user-load-tx-intv OBJECT-TYPE
                SYNTAX DisplayString (SIZE (0..6))
		ACCESS read-only
		STATUS mandatory
		DESCRIPTION
                " Minimum chan-user-load-tx within a 15 minutes interval. "
                ::={ chanPerfIntv-Entry 8 }

        chan-min-user-load-tx-time-intv OBJECT-TYPE
		SYNTAX DisplayString (SIZE (0..255))
		ACCESS read-only
		STATUS mandatory
		DESCRIPTION
                " Timestamp of when the minimum chan-user-load-tx
                  within a 15 minutes interval occurred. "
                ::={ chanPerfIntv-Entry 9 }

        chan-min-user-load-rx-intv OBJECT-TYPE
                SYNTAX DisplayString (SIZE (0..6))
		ACCESS read-only
		STATUS mandatory
		DESCRIPTION
                " Minimum chan-user-load-rx within a 15 minutes interval. "
                ::={ chanPerfIntv-Entry 10 }

        chan-min-user-load-rx-time-intv OBJECT-TYPE
		SYNTAX DisplayString (SIZE (0..255))
		ACCESS read-only
		STATUS mandatory
		DESCRIPTION
                " Timestamp of when the minimum chan-user-load-rx
                  within a 15 minutes interval occurred. "
                ::={ chanPerfIntv-Entry 11 }

        chan-min-total-load-tx-intv OBJECT-TYPE
                SYNTAX DisplayString (SIZE (0..6))
		ACCESS read-only
		STATUS mandatory
		DESCRIPTION
                " Minimum chan-total-load-tx within a 15 minutes interval. "
                ::={ chanPerfIntv-Entry 12 }

        chan-min-total-load-tx-time-intv OBJECT-TYPE
		SYNTAX DisplayString (SIZE (0..255))
		ACCESS read-only
		STATUS mandatory
		DESCRIPTION
                " Timestamp of when the minimum chan-total-load-tx
                  within a 15 minutes interval occurred. "
                ::={ chanPerfIntv-Entry 13 }

        chan-min-total-load-rx-intv OBJECT-TYPE
                SYNTAX DisplayString (SIZE (0..6))
		ACCESS read-only
		STATUS mandatory
		DESCRIPTION
                " Minimum chan-total-load-rx within a 15 minutes interval. "
                ::={ chanPerfIntv-Entry 14 }

        chan-min-total-load-rx-time-intv OBJECT-TYPE
		SYNTAX DisplayString (SIZE (0..255))
		ACCESS read-only
		STATUS mandatory
		DESCRIPTION
                " Timestamp of when the minimum chan-total-load-rx
                  within a 15 minutes interval occurred. "
                ::={ chanPerfIntv-Entry 15 }

        chan-max-user-load-tx-intv OBJECT-TYPE
                SYNTAX DisplayString (SIZE (0..6))
		ACCESS read-only
		STATUS mandatory
		DESCRIPTION
                " Maximum chan-user-load-tx within a 15 minutes interval. "
                ::={ chanPerfIntv-Entry 16 }

        chan-max-user-load-tx-time-intv OBJECT-TYPE
		SYNTAX DisplayString (SIZE (0..255))
		ACCESS read-only
		STATUS mandatory
		DESCRIPTION
                " Timestamp of when the maximum chan-user-load-tx
                  within a 15 minutes interval occurred. "
                ::={ chanPerfIntv-Entry 17 }

        chan-max-user-load-rx-intv OBJECT-TYPE
                SYNTAX DisplayString (SIZE (0..6))
		ACCESS read-only
		STATUS mandatory
		DESCRIPTION
                " Maximum chan-user-load-rx within a 15 minutes interval. "
                ::={ chanPerfIntv-Entry 18 }

        chan-max-user-load-rx-time-intv OBJECT-TYPE
		SYNTAX DisplayString (SIZE (0..255))
		ACCESS read-only
		STATUS mandatory
		DESCRIPTION
                " Timestamp of when the maximum chan-user-load-rx
                  within a 15 minutes interval occurred. "
                ::={ chanPerfIntv-Entry 19 }

        chan-max-total-load-tx-intv OBJECT-TYPE
                SYNTAX DisplayString (SIZE (0..6))
		ACCESS read-only
		STATUS mandatory
		DESCRIPTION
                " Maximum chan-total-load-tx within a 15 minutes interval. "
                ::={ chanPerfIntv-Entry 20 }

        chan-max-total-load-tx-time-intv OBJECT-TYPE
                SYNTAX DisplayString (SIZE (0..6))
		ACCESS read-only
		STATUS mandatory
		DESCRIPTION
                " Timestamp of when the maximum chan-total-load-tx
                  within a 15 minutes interval occurred. "
                ::={ chanPerfIntv-Entry 21 }

        chan-max-total-load-rx-intv OBJECT-TYPE
                SYNTAX DisplayString (SIZE (0..6))
		ACCESS read-only
		STATUS mandatory
		DESCRIPTION
                " Maximum chan-total-load-rx within a 15 minutes interval. "
                ::={ chanPerfIntv-Entry 22 }

        chan-max-total-load-rx-time-intv OBJECT-TYPE
		SYNTAX DisplayString (SIZE (0..255))
		ACCESS read-only
		STATUS mandatory
		DESCRIPTION
                " Timestamp of when the maximum chan-total-load-rx
                  within a 15 minutes interval occurred. "
                ::={ chanPerfIntv-Entry 23 }

--
-- 3. Current PVC Performance Table displays the statistical data
--    for every PVC within the current 15 minutes.
--

       pvcPerfCurr-Table OBJECT-TYPE
	    SYNTAX SEQUENCE OF PvcPerfCurr-Entry
		ACCESS not-accessible
		STATUS mandatory

		DESCRIPTION
		" PVC performance table, which displays
                  the performance statistical data based on
		  each PVC."
		::={ probePerform 3 }

	pvcPerfCurr-Entry OBJECT-TYPE
	    SYNTAX PvcPerfCurr-Entry
		ACCESS not-accessible
		STATUS mandatory
		DESCRIPTION
		" Identifies an entry (row) in pvc statistic table"
		INDEX { pvcPerfCurr-num-index}
		::={ pvcPerfCurr-Table 1 }

	PvcPerfCurr-Entry ::=
		SEQUENCE {
		  pvcPerfCurr-num-index
			      INTEGER,
		  pvc-tx-time-curr
			INTEGER,
		  pvc-unavail-toDte
                        DisplayString,
		  pvc-unavail-toDce
                        DisplayString,
		  pvc-user-load-tx-curr
                        DisplayString,
		  pvc-user-load-rx-curr
                        DisplayString,
		  pvc-total-load-tx-curr
                        DisplayString,
		  pvc-total-load-rx-curr
                        DisplayString,
		  pvc-CIR-toNet-exceed-curr
			INTEGER,
		  pvc-EIR-toNet-exceed-curr
			INTEGER,
		  pvc-loss-frame-tx-curr
			INTEGER,
		  pvc-loss-frame-rx-curr
                        INTEGER,
                  pvc-ip-tx-time-curr
                        INTEGER,
                  pvcIpRtrRxLatTxTimeCurr
                        INTEGER,
                  pvcIpRtrTxLatTxTimeCurr
                        INTEGER
		}

	pvcPerfCurr-num-index OBJECT-TYPE
		SYNTAX INTEGER ( 16..991 )
		ACCESS read-only
		STATUS mandatory
		DESCRIPTION
                " The index value which uniquely identifies the PVC
		  number to which this entry is applicable. "
		::={ pvcPerfCurr-Entry 1 }

	pvc-tx-time-curr OBJECT-TYPE
                SYNTAX INTEGER
		ACCESS read-only
		STATUS mandatory
		DESCRIPTION
		" Probe token average round trip time within the latest
                  15 minutes for a specific PVC.  A -1 value indicates
                  data is Not-Avail. "
		::={ pvcPerfCurr-Entry 2 }

	pvc-unavail-toDte OBJECT-TYPE
                SYNTAX DisplayString (SIZE (0..6))
		ACCESS read-only
		STATUS mandatory
		DESCRIPTION
		" This object identifies the PVC average unavailability
                  within the latest 15 minutes. This statistical data is
		  calculated by a PVC unavailable time due to the network
		  or remote DTE fault over the full time interval."
		::={ pvcPerfCurr-Entry 3 }

	pvc-unavail-toDce OBJECT-TYPE
                SYNTAX DisplayString (SIZE (0..6))
		ACCESS read-only
		STATUS mandatory
		DESCRIPTION
		" This object identifies the PVC average unavailability
                  within the latest 15 minutes. This statistical data is
		  calculated by a PVC unavailable time due to the local
		  DTE fault over the full time interval."
		::={ pvcPerfCurr-Entry 4 }


	pvc-user-load-tx-curr OBJECT-TYPE
                SYNTAX DisplayString (SIZE (0..6))
		ACCESS read-only
		STATUS mandatory
		DESCRIPTION
		" This object identifies the PVC average user tx load within the
                  latest 15 minutes.  This statistical data is calculated by
		  user data octets sent by a specific PVC within the 15 minutes
		  over the PVC total available load.
		  Note: If the CIR is correctly defined for this PVC, PVC available
                        load will depend on CIR, otherwise, it will get it from
                        interface speed. "
		::={ pvcPerfCurr-Entry 5 }

	pvc-user-load-rx-curr OBJECT-TYPE
                SYNTAX DisplayString (SIZE (0..6))
		ACCESS read-only
		STATUS mandatory
		DESCRIPTION
		" This object identifies the PVC average user rx load within the
                  latest 15 minutes.  This statistical data is calculated by
		  user data octets received by a specific PVC within the 15 minutes
		  over the PVC total available load.
		  Note: If the CIR is correctly defined for this PVC, PVC available
                        load will depend on CIR, otherwise, it will get it from
                        interface speed. "
		::={ pvcPerfCurr-Entry 6 }

	pvc-total-load-tx-curr OBJECT-TYPE
                SYNTAX DisplayString (SIZE (0..6))
		ACCESS read-only
		STATUS mandatory
		DESCRIPTION
		" This object identifies the PVC total tx load within the
                  latest 15 minutes.  This statistical data is calculated by
		  total data octets sent by a specific PVC within the 15 minutes
		  over the PVC total available load.
		  Note: If the CIR is correctly defined for this PVC, PVC available
                        load will depend on CIR, otherwise, it will get it from
                        interface speed. "
		::={ pvcPerfCurr-Entry 7 }

	pvc-total-load-rx-curr OBJECT-TYPE
                SYNTAX DisplayString (SIZE (0..6))
		ACCESS read-only
		STATUS mandatory
		DESCRIPTION
		" This object identifies the PVC total rx load within the
                  latest 15 minutes.  This statistical data is calculated by
		  total data octets received by a specific PVC within the 15 minutes
		  over the PVC total available load.
		  Note: If the CIR is correctly defined for this PVC, PVC available
                        load will depend on CIR, otherwise, it will get it from
                        interface speed. "
		::={ pvcPerfCurr-Entry 8 }

	pvc-CIR-toNet-exceed-curr OBJECT-TYPE
		SYNTAX INTEGER
		ACCESS read-only
		STATUS mandatory
		DESCRIPTION
		" This object identifies the number of exceeding CIR times that the
		  network detected within the current interval. The measurement is
		  done for every Tc, and the direction is to the network."
		::={ pvcPerfCurr-Entry 9 }

	pvc-EIR-toNet-exceed-curr OBJECT-TYPE
		SYNTAX INTEGER
		ACCESS read-only
		STATUS mandatory
		DESCRIPTION
		" This object identifies the number of exceeding EIR times that the
		  network detected within the current interval. The measurement is
		  done for every Tc, and the direction is to the network."
		::={ pvcPerfCurr-Entry 10 }

	pvc-loss-frame-tx-curr OBJECT-TYPE
                SYNTAX INTEGER
		ACCESS read-only
		STATUS mandatory
		DESCRIPTION
		" This object identifies the percentage of tx loss of frames within
                  the total tx frames for this PVC.  A -1 value indicates
                  data is Not-Avail. "

		::={ pvcPerfCurr-Entry 11 }

	pvc-loss-frame-rx-curr OBJECT-TYPE
                SYNTAX INTEGER
		ACCESS read-only
		STATUS mandatory
		DESCRIPTION
		" This object identifies the percentage of rx loss of frames within
                  the total rx frames for this PVC.  A -1 value indicates
                  data is Not-Avail. "

		::={ pvcPerfCurr-Entry 12 }

        pvc-ip-tx-time-curr OBJECT-TYPE
                SYNTAX INTEGER
		ACCESS read-only
		STATUS mandatory
		DESCRIPTION
                " Probe token average round trip time via ethernet and using UDP/IP
                  packets within the latest 15 minutes for a specific PVC.
                  A -1 value indicates data is Not-Avail. "
                ::={ pvcPerfCurr-Entry 13 }

        pvcIpRtrRxLatTxTimeCurr OBJECT-TYPE
                SYNTAX INTEGER
		ACCESS read-only
		STATUS mandatory
		DESCRIPTION
                " Router Receive Latency IP Packet average round trip time
		  from first byte transmitted out the To-Dte port, to the
		  last byte received on the Ethernet port,
		  within the latest 15 minutes for a specific PVC.
                  A -1 value indicates data is Not-Avail. "
                ::={ pvcPerfCurr-Entry 14 }

        pvcIpRtrTxLatTxTimeCurr OBJECT-TYPE
                SYNTAX INTEGER
		ACCESS read-only
		STATUS mandatory
		DESCRIPTION
                " Router Transmit Latency IP Packet average round trip time
		  from first byte transmitted out the Ethernet port, to the
		  last byte received on the To-Dte port,
		  within the latest 15 minutes for a specific PVC.
                  A -1 value indicates data is Not-Avail. "
                ::={ pvcPerfCurr-Entry 15 }

--
-- 4. PVC Performance Interval Table displays the statistical data
--    for every PVC over the previous 24 hours of operation.
--    The past 24 hours are broken into 96 completed 15 minutes
--    intervals.
--    A -1 value indicates interval is prior to system power-on.  This
--    does not apply to indices, such as PVC and interval number.
--

pvcPerfIntv-Table OBJECT-TYPE
		SYNTAX SEQUENCE OF PvcPerfIntv-Entry
		ACCESS not-accessible
		STATUS mandatory
		DESCRIPTION
		" PVC performance interval table, which displays
                  the performance statistical data based on  each
		  PVC in previous 24 hours."
		::={ probePerform 4 }

	pvcPerfIntv-Entry OBJECT-TYPE
		SYNTAX PvcPerfIntv-Entry
		ACCESS not-accessible
		STATUS mandatory
		DESCRIPTION
		" Identifies an entry (row) in pvc statistic table"
		INDEX { pvcPerfIntv-num-index, pvcPerf-intv-index }
		::={ pvcPerfIntv-Table 1 }

        PvcPerfIntv-Entry ::=
		SEQUENCE {
		  pvcPerfIntv-num-index
			INTEGER,
		  pvcPerf-intv-index
                        INTEGER,
		  pvc-tx-time-intv
			INTEGER,
		  pvc-unavail-toDte-intv
                        DisplayString,
		  pvc-unavail-toDce-intv
                        DisplayString,
		  pvc-user-load-tx-intv
                        DisplayString,
		  pvc-user-load-rx-intv
                        DisplayString,
		  pvc-total-load-tx-intv
                        DisplayString,
		  pvc-total-load-rx-intv
                        DisplayString,
		  pvc-CIR-toNet-exceed-intv
			INTEGER,
		  pvc-EIR-toNet-exceed-intv
			INTEGER,
		  pvc-loss-frame-tx-intv
			INTEGER,
		  pvc-loss-frame-rx-intv
                        INTEGER,
                  pvc-ip-tx-time-intv
                        INTEGER,
                  pvcIpRtrRxLatTxTimeIntv
                        INTEGER,
                  pvcIpRtrTxLatTxTimeIntv
                        INTEGER,
                  pvc-min-tx-time-intv
                        INTEGER,
                  pvc-min-tx-time-time-intv
                        DisplayString,
                  pvc-min-user-load-tx-intv
                        DisplayString,
                  pvc-min-user-load-tx-time-intv
                        DisplayString,
                  pvc-min-user-load-rx-intv
                        DisplayString,
                  pvc-min-user-load-rx-time-intv
                        DisplayString,
                  pvc-min-total-load-tx-intv
                        DisplayString,
                  pvc-min-total-load-tx-time-intv
                        DisplayString,
                  pvc-min-total-load-rx-intv
                        DisplayString,
                  pvc-min-total-load-rx-time-intv
                        DisplayString,
                  pvc-min-ip-tx-time-intv
                        INTEGER,
                  pvc-min-ip-tx-time-time-intv
                        DisplayString,
                  pvc-max-tx-time-intv
                        INTEGER,
                  pvc-max-tx-time-time-intv
                        DisplayString,
                  pvc-max-user-load-tx-intv
                        DisplayString,
                  pvc-max-user-load-tx-time-intv
                        DisplayString,
                  pvc-max-user-load-rx-intv
                        DisplayString,
                  pvc-max-user-load-rx-time-intv
                        DisplayString,
                  pvc-max-total-load-tx-intv
                        DisplayString,
                  pvc-max-total-load-tx-time-intv
                        DisplayString,
                  pvc-max-total-load-rx-intv
                        DisplayString,
                  pvc-max-total-load-rx-time-intv
                        DisplayString,
                  pvc-max-ip-tx-time-intv
                        INTEGER,
                  pvc-max-ip-tx-time-time-intv
                        DisplayString

		}

	pvcPerfIntv-num-index OBJECT-TYPE
		SYNTAX INTEGER ( 16..991 )
		ACCESS read-only
		STATUS mandatory
		DESCRIPTION
                " The index value which uniquely identifies the PVC
		  number to which this entry is applicable. "
		::={ pvcPerfIntv-Entry 1 }

	pvcPerf-intv-index OBJECT-TYPE
		SYNTAX INTEGER (1..96)
		ACCESS read-only
		STATUS mandatory
		DESCRIPTION
                " Identifies an entry (row) in PVC performance table, with
		  total 96 time intervals, where 1 is the most recently completed
		  15 minutes interval and 96 is the least recently completed 15
		  minutes interval (assuming that all 96 intervals are valid). "
		::={ pvcPerfIntv-Entry 2 }


	pvc-tx-time-intv OBJECT-TYPE
                SYNTAX INTEGER
		ACCESS read-only
		STATUS mandatory
		DESCRIPTION
		" Probe token average round trip time within a
                  15 minutes interval for a specific PVC.  A -1 value indicates
                  data is Not-Avail. "
		::={ pvcPerfIntv-Entry 3 }

	pvc-unavail-toDte-intv OBJECT-TYPE
                SYNTAX DisplayString (SIZE (0..6))
		ACCESS read-only
		STATUS mandatory
		DESCRIPTION
		" This object identifies the PVC average unavailability
                  within a 15 minutes interval. This statistical data is
		  calculated by a PVC unavailable time due to the network
		  or remote DTE fault over the full time interval."
		::={ pvcPerfIntv-Entry 4 }

	pvc-unavail-toDce-intv OBJECT-TYPE
                SYNTAX DisplayString (SIZE (0..6))
		ACCESS read-only
		STATUS mandatory
		DESCRIPTION
		" This object identifies the PVC average unavailability
                  within a 15 minutes interval. This statistical data is
		  calculated by a PVC unavailable time due to the local DTE
		  fault over the full time interval."
		::={ pvcPerfIntv-Entry 5 }

	pvc-user-load-tx-intv OBJECT-TYPE
                SYNTAX DisplayString (SIZE (0..6))
		ACCESS read-only
		STATUS mandatory
		DESCRIPTION
		" This object identifies the PVC average user tx load within
                  a 15 minutes interval.  This statistical data is calculated by
		  user data octets sent by a specific PVC within the 15 minutes
		  over the PVC total available load.
		  Note: If the CIR is correctly defined for this PVC, PVC available
                        load will depend on CIR, otherwise, it will get it from
                        interface speed. "
		::={ pvcPerfIntv-Entry 6 }

	pvc-user-load-rx-intv OBJECT-TYPE
                SYNTAX DisplayString (SIZE (0..6))
		ACCESS read-only
		STATUS mandatory
		DESCRIPTION
		" This object identifies the PVC average user rx load within
                  a 15 minutes interval.  This statistical data is calculated by
		  user data octets received by a specific PVC within the 15 minutes
		  over the PVC total available load.
		  Note: If the CIR is correctly defined for this PVC, PVC available
                        load will depend on CIR, otherwise, it will get it from
                        interface speed. "
		::={ pvcPerfIntv-Entry 7 }

	pvc-total-load-tx-intv OBJECT-TYPE
                SYNTAX DisplayString (SIZE (0..6))
		ACCESS read-only
		STATUS mandatory
		DESCRIPTION
		" This object identifies the PVC total tx load within
                  a 15 minutes interval.  This statistical data is calculated by
		  total data octets sent by a specific PVC within the 15 minutes
		  over the PVC total available load.
		  Note: If the CIR is correctly defined for this PVC, PVC available
                        load will depend on CIR, otherwise, it will get it from
                        interface speed. "
		::={ pvcPerfIntv-Entry 8 }

	pvc-total-load-rx-intv OBJECT-TYPE
                SYNTAX DisplayString (SIZE (0..6))
		ACCESS read-only
		STATUS mandatory
		DESCRIPTION
		" This object identifies the PVC total rx load within
                  a 15 minutes interval.  This statistical data is calculated by
		  total data octets received by a specific PVC within the 15 minutes
		  over the PVC total available load.
		  Note: If the CIR is correctly defined for this PVC, PVC available
                        load will depend on CIR, otherwise, it will get it from
                        interface speed. "
		::={ pvcPerfIntv-Entry 9 }

	pvc-CIR-toNet-exceed-intv OBJECT-TYPE
		SYNTAX INTEGER
		ACCESS read-only
		STATUS mandatory
		DESCRIPTION
		" This object identifies the number of exceeding CIR times that the
		  network detected within an interval. The measurement is
		  done for every Tc, and the direction is to the network."
		::={ pvcPerfIntv-Entry 10 }

	pvc-EIR-toNet-exceed-intv OBJECT-TYPE
		SYNTAX INTEGER
		ACCESS read-only
		STATUS mandatory
		DESCRIPTION
		" This object identifies the number of exceeding EIR times that the
		  network detected within an interval. The measurement is
		  done for every Tc, and the direction is to the network."
		::={ pvcPerfIntv-Entry 11 }

	pvc-loss-frame-tx-intv OBJECT-TYPE
		SYNTAX INTEGER {
			not-avail(255)
		}
		ACCESS read-only
		STATUS mandatory
		DESCRIPTION
		" This object identifies the percentage of tx loss of frames within
		  the total tx frames for this PVC in this interval."
		::={ pvcPerfIntv-Entry 12 }

	pvc-loss-frame-rx-intv OBJECT-TYPE
		SYNTAX INTEGER {
			not-avail(255)
		}
		ACCESS read-only
		STATUS mandatory
		DESCRIPTION
		" This object identifies the percentage of rx loss of frames within
		  the total rx frames for this PVC in this interval."
		::={ pvcPerfIntv-Entry 13 }

        pvc-ip-tx-time-intv OBJECT-TYPE
                SYNTAX INTEGER
		ACCESS read-only
		STATUS mandatory
		DESCRIPTION
                " Probe token average round trip time via ethernet and using UDP/IP
                  packets within a 15 minutes interval for a specific PVC.
                  A -1 value indicates data is Not-Avail. "
                ::={ pvcPerfIntv-Entry 14 }

        pvcIpRtrRxLatTxTimeIntv OBJECT-TYPE
                SYNTAX INTEGER
		ACCESS read-only
		STATUS mandatory
		DESCRIPTION
                " Router Receive Latency IP Packet average round trip time
		  from first byte transmitted out the To-Dte port, to the
		  last byte received on the Ethernet port,
		  within a 15 minute interval for a specific PVC.
                  A -1 value indicates data is Not-Avail. "
                ::={ pvcPerfIntv-Entry 15 }

        pvcIpRtrTxLatTxTimeIntv OBJECT-TYPE
                SYNTAX INTEGER
		ACCESS read-only
		STATUS mandatory
		DESCRIPTION
                " Router Transmit Latency IP Packet average round trip time
		  from first byte transmitted out the Ethernet port, to the
		  last byte received on the To-Dte port,
		  within a 15 minute interval for a specific PVC.
                  A -1 value indicates data is Not-Avail. "
                ::={ pvcPerfIntv-Entry 16 }

        pvc-min-tx-time-intv OBJECT-TYPE
                SYNTAX INTEGER
		ACCESS read-only
		STATUS mandatory
		DESCRIPTION
                " Minimum pvc-tx-time within a 15 minutes interval for a specific PVC."
                ::={ pvcPerfIntv-Entry 17 }

        pvc-min-tx-time-time-intv OBJECT-TYPE
		SYNTAX DisplayString (SIZE (0..255))
		ACCESS read-only
		STATUS mandatory
		DESCRIPTION
                " Timestamp of when the minimum pvc-tx-time
                  within a 15 minutes interval occurred."
                ::={ pvcPerfIntv-Entry 18 }

        pvc-min-user-load-tx-intv OBJECT-TYPE
                SYNTAX DisplayString (SIZE (0..6))
		ACCESS read-only
		STATUS mandatory
		DESCRIPTION
                " Minimum pvc-user-load-tx within a 15 minutes interval."
                ::={ pvcPerfIntv-Entry 19 }

        pvc-min-user-load-tx-time-intv OBJECT-TYPE
		SYNTAX DisplayString (SIZE (0..255))
		ACCESS read-only
		STATUS mandatory
		DESCRIPTION
                " Timestamp of when the minimum pvc-user-load-tx
                  within a 15 minutes interval occurred."
                ::={ pvcPerfIntv-Entry 20 }

        pvc-min-user-load-rx-intv OBJECT-TYPE
                SYNTAX DisplayString (SIZE (0..6))
		ACCESS read-only
		STATUS mandatory
		DESCRIPTION
                " Minimum pvc-user-load-rx within a 15 minutes interval."
                ::={ pvcPerfIntv-Entry 21 }

        pvc-min-user-load-rx-time-intv OBJECT-TYPE
		SYNTAX DisplayString (SIZE (0..255))
		ACCESS read-only
		STATUS mandatory
		DESCRIPTION
                " Timestamp of when the minimum pvc-user-load-rx
                  within a 15 minutes interval occurred."
                ::={ pvcPerfIntv-Entry 22 }

        pvc-min-total-load-tx-intv OBJECT-TYPE
                SYNTAX DisplayString (SIZE (0..6))
		ACCESS read-only
		STATUS mandatory
		DESCRIPTION
                " Minimum pvc-total-load-tx within a 15 minutes interval."
                ::={ pvcPerfIntv-Entry 23 }

        pvc-min-total-load-tx-time-intv OBJECT-TYPE
		SYNTAX DisplayString (SIZE (0..255))
		ACCESS read-only
		STATUS mandatory
		DESCRIPTION
                " Timestamp of when the minimum pvc-total-load-tx
                  within a 15 minutes interval occurred."
                ::={ pvcPerfIntv-Entry 24 }

        pvc-min-total-load-rx-intv OBJECT-TYPE
                SYNTAX DisplayString (SIZE (0..6))
		ACCESS read-only
		STATUS mandatory
		DESCRIPTION
                " Minimum pvc-total-load-rx within a 15 minutes interval."
                ::={ pvcPerfIntv-Entry 25 }

        pvc-min-total-load-rx-time-intv OBJECT-TYPE
		SYNTAX DisplayString (SIZE (0..255))
		ACCESS read-only
		STATUS mandatory
		DESCRIPTION
                " Timestamp of when the minimum pvc-total-load-rx
                  within a 15 minutes interval occurred."
                ::={ pvcPerfIntv-Entry 26 }

        pvc-min-ip-tx-time-intv OBJECT-TYPE
                SYNTAX INTEGER
		ACCESS read-only
		STATUS mandatory
		DESCRIPTION
                " Minimum pvc-ip-tx-time within a 15 minutes interval."
                ::={ pvcPerfIntv-Entry 27 }

        pvc-min-ip-tx-time-time-intv OBJECT-TYPE
		SYNTAX DisplayString (SIZE (0..255))
		ACCESS read-only
		STATUS mandatory
		DESCRIPTION
                " Timestamp of when the minimum pvc-ip-tx-time
                  within a 15 minutes interval occurred."
                ::={ pvcPerfIntv-Entry 28 }

        pvc-max-tx-time-intv OBJECT-TYPE
                SYNTAX INTEGER
		ACCESS read-only
		STATUS mandatory
		DESCRIPTION
                " Maximum pvc-tx-time within a 15 minutes interval."
                ::={ pvcPerfIntv-Entry 29 }

        pvc-max-tx-time-time-intv OBJECT-TYPE
		SYNTAX DisplayString (SIZE (0..255))
		ACCESS read-only
		STATUS mandatory
		DESCRIPTION
                " Timestamp of when the maximum pvc-tx-time
                  within a 15 minutes interval occurred."
                ::={ pvcPerfIntv-Entry 30 }

        pvc-max-user-load-tx-intv OBJECT-TYPE
                SYNTAX DisplayString (SIZE (0..6))
		ACCESS read-only
		STATUS mandatory
		DESCRIPTION
                " Maximum pvc-user-load-tx within a 15 minutes interval."
                ::={ pvcPerfIntv-Entry 31 }

        pvc-max-user-load-tx-time-intv OBJECT-TYPE
		SYNTAX DisplayString (SIZE (0..255))
		ACCESS read-only
		STATUS mandatory
		DESCRIPTION
                " Timestamp of when the maximum pvc-user-load-tx
                  within a 15 minutes interval occurred."
                ::={ pvcPerfIntv-Entry 32 }

        pvc-max-user-load-rx-intv OBJECT-TYPE
                SYNTAX DisplayString (SIZE (0..6))
		ACCESS read-only
		STATUS mandatory
		DESCRIPTION
                " Maximum pvc-user-load-rx within a 15 minutes interval."
                ::={ pvcPerfIntv-Entry 33 }

        pvc-max-user-load-rx-time-intv OBJECT-TYPE
		SYNTAX DisplayString (SIZE (0..255))
		ACCESS read-only
		STATUS mandatory
		DESCRIPTION
                " Timestamp of when the maximum pvc-user-load-rx
                  within a 15 minutes interval occurred."
                ::={ pvcPerfIntv-Entry 34 }

        pvc-max-total-load-tx-intv OBJECT-TYPE
                SYNTAX DisplayString (SIZE (0..6))
		ACCESS read-only
		STATUS mandatory
		DESCRIPTION
                " Maximum pvc-total-load-tx within a 15 minutes interval."
                ::={ pvcPerfIntv-Entry 35 }

        pvc-max-total-load-tx-time-intv OBJECT-TYPE
		SYNTAX DisplayString (SIZE (0..255))
		ACCESS read-only
		STATUS mandatory
		DESCRIPTION
                " Timestamp of when the maximum pvc-total-load-tx
                  within a 15 minutes interval occurred."
                ::={ pvcPerfIntv-Entry 36 }

        pvc-max-total-load-rx-intv OBJECT-TYPE
                SYNTAX DisplayString (SIZE (0..6))
		ACCESS read-only
		STATUS mandatory
		DESCRIPTION
                " Maximum pvc-total-load-rx within a 15 minutes interval."
                ::={ pvcPerfIntv-Entry 37 }

        pvc-max-total-load-rx-time-intv OBJECT-TYPE
		SYNTAX DisplayString (SIZE (0..255))
		ACCESS read-only
		STATUS mandatory
		DESCRIPTION
                " Timestamp of when the maximum pvc-total-load-rx
                  within a 15 minutes interval occurred."
                ::={ pvcPerfIntv-Entry 38 }

        pvc-max-ip-tx-time-intv OBJECT-TYPE
                SYNTAX INTEGER
		ACCESS read-only
		STATUS mandatory
		DESCRIPTION
                " Maximum pvc-ip-tx-time within a 15 minutes interval."
                ::={ pvcPerfIntv-Entry 39 }

        pvc-max-ip-tx-time-time-intv OBJECT-TYPE
		SYNTAX DisplayString (SIZE (0..255))
		ACCESS read-only
		STATUS mandatory
		DESCRIPTION
                " Timestamp of when the maximum pvc-ip-tx-time
                  within a 15 minutes interval occurred."
                ::={ pvcPerfIntv-Entry 40 }

--
-- 1. PVC traffic shape level threshold group displays the threshold value
--    for each level, right now 7 levels are defined, and they are read only
--    currently.
--

pvcShapeThresh OBJECT IDENTIFIER ::={ probeTrafficShape 1 }


	pvcShapeThreshLevel-1 OBJECT-TYPE
		SYNTAX INTEGER (0..100)
		ACCESS read-only
		STATUS mandatory
		DESCRIPTION
		"This parameter defines the maximum percentage of PVC traffic
		 (measured in TC) within this PVC CIR in shape level 1 (currently

		  is 10%). "
		::={ pvcShapeThresh 1 }

	pvcShapeThreshLevel-2 OBJECT-TYPE
		SYNTAX INTEGER (0..100)
		ACCESS read-only
		STATUS mandatory
		DESCRIPTION
		"This parameter defines the maximum percentage of PVC traffic
		 (measured in TC) within this PVC CIR in shape level 2 (currently
		  is 25%). "
		::={ pvcShapeThresh 2 }

	pvcShapeThreshLevel-3 OBJECT-TYPE
		SYNTAX INTEGER (0..100)
		ACCESS read-only
		STATUS mandatory
		DESCRIPTION
		"This parameter defines the maximum percentage of PVC traffic
		 (measured in TC) within this PVC CIR in shape level 3 (currently
		  is 45%). "
		::={ pvcShapeThresh 3 }

	pvcShapeThreshLevel-4 OBJECT-TYPE
		SYNTAX INTEGER (0..100)
		ACCESS read-only
		STATUS mandatory
		DESCRIPTION
		"This parameter defines the maximum percentage of PVC traffic
		 (measured in TC) within this PVC CIR in shape level 4 (currently
		  is 75%). "
		::={ pvcShapeThresh 4 }

	pvcShapeThreshLevel-5 OBJECT-TYPE
		SYNTAX INTEGER (0..100)
		ACCESS read-only
		STATUS mandatory
		DESCRIPTION
		"This parameter defines the maximum percentage of PVC traffic
		 (measured in TC) within this PVC CIR in shape level 5 (currently
		  is 90%). "
		::={ pvcShapeThresh 5 }

	pvcShapeThreshLevel-6 OBJECT-TYPE
		SYNTAX INTEGER (0..100)
		ACCESS read-only
		STATUS mandatory
		DESCRIPTION
		"This parameter defines the maximum percentage of PVC traffic
		 (measured in TC) within this PVC CIR in shape level 6 (currently
		  is 100%). "
		::={ pvcShapeThresh 6 }

	pvcShapeThreshLevel-7 OBJECT-TYPE
		SYNTAX INTEGER
		ACCESS read-only
		STATUS mandatory
		DESCRIPTION
		"This parameter defines the maximum percentage of PVC traffic
		 (measured in TC) within this PVC CIR in shape level 7 (currently
		  is more than 100%). "
		::={ pvcShapeThresh 7 }

--
-- 2. Current PVC traffic shape To DCE Table displays the traffic shape information
--    for every PVC within the current 15 minutes to the direction of DCE.
--

	pvcShapeCurrToDce-Table OBJECT-TYPE
		SYNTAX SEQUENCE OF PvcShapeCurrToDce-Entry
		ACCESS not-accessible
		STATUS mandatory
		DESCRIPTION
		" PVC current traffic shape to DCE table, which displays
		  the traffic shape information based on each PVC."
		::={ probeTrafficShape 2 }

	pvcShapeCurrToDce-Entry OBJECT-TYPE
		SYNTAX PvcShapeCurrToDce-Entry
		ACCESS not-accessible
		STATUS mandatory
		DESCRIPTION
		" Identifies an entry (row) in pvc current traffic shape to DCE table"
		INDEX { pvcShapeCurrToDce-index}
		::={ pvcShapeCurrToDce-Table 1 }

	PvcShapeCurrToDce-Entry ::=
		SEQUENCE {
		  pvcShapeCurrToDce-index
			      INTEGER,
		  pvcShapeCurrToDceLevel-1
			INTEGER,
		  pvcShapeCurrToDceLevel-2
			INTEGER,
		  pvcShapeCurrToDceLevel-3
			INTEGER,
		  pvcShapeCurrToDceLevel-4
			INTEGER,
		  pvcShapeCurrToDceLevel-5
			INTEGER,
		  pvcShapeCurrToDceLevel-6
			INTEGER,
		  pvcShapeCurrToDceLevel-7
			INTEGER
		}

	pvcShapeCurrToDce-index OBJECT-TYPE
		SYNTAX INTEGER ( 16..991 )
		ACCESS read-only
		STATUS mandatory
		DESCRIPTION
                " The index value which uniquely identifies the PVC
		  number to which this entry is applicable. "
		::={ pvcShapeCurrToDce-Entry 1 }

	pvcShapeCurrToDceLevel-1 OBJECT-TYPE
		SYNTAX INTEGER ( 0..100 )
		ACCESS read-only
		STATUS mandatory
		DESCRIPTION
		" This object identifies the percentage of traffic in level one
		  in current 15 minutes to the direction of DCE."
		::={ pvcShapeCurrToDce-Entry 2 }

	pvcShapeCurrToDceLevel-2 OBJECT-TYPE
		SYNTAX INTEGER ( 0..100 )
		ACCESS read-only
		STATUS mandatory
		DESCRIPTION
		" This object identifies the percentage of traffic in level two
		  in current 15 minutes to the direction of DCE."
		::={ pvcShapeCurrToDce-Entry 3 }

	pvcShapeCurrToDceLevel-3 OBJECT-TYPE
		SYNTAX INTEGER ( 0..100 )
		ACCESS read-only
		STATUS mandatory
		DESCRIPTION
		" This object identifies the percentage of traffic in level three
		  in current 15 minutes to the direction of DCE."
		::={ pvcShapeCurrToDce-Entry 4 }

	pvcShapeCurrToDceLevel-4 OBJECT-TYPE
		SYNTAX INTEGER ( 0..100 )
		ACCESS read-only
		STATUS mandatory
		DESCRIPTION
		" This object identifies the percentage of traffic in level four
		  in current 15 minutes to the direction of DCE."
		::={ pvcShapeCurrToDce-Entry 5 }

	pvcShapeCurrToDceLevel-5 OBJECT-TYPE
		SYNTAX INTEGER ( 0..100 )
		ACCESS read-only
		STATUS mandatory
		DESCRIPTION
		" This object identifies the percentage of traffic in level five
		  in current 15 minutes to the direction of DCE."
		::={ pvcShapeCurrToDce-Entry 6 }

	pvcShapeCurrToDceLevel-6 OBJECT-TYPE
		SYNTAX INTEGER ( 0..100 )
		ACCESS read-only
		STATUS mandatory
		DESCRIPTION
		" This object identifies the percentage of traffic in level six
		  in current 15 minutes to the direction of DCE."
		::={ pvcShapeCurrToDce-Entry 7 }

	pvcShapeCurrToDceLevel-7 OBJECT-TYPE
		SYNTAX INTEGER (0..100 )
		ACCESS read-only
		STATUS mandatory
		DESCRIPTION
		" This object identifies the percentage of traffic in level seven
		  in current 15 minutes to the direction of DCE."
		::={ pvcShapeCurrToDce-Entry 8 }


--
-- 3. Current PVC traffic shape To DTE Table displays the traffic shape information
--    for every PVC within the current 15 minutes to the direction of DTE.
--

pvcShapeCurrToDte-Table OBJECT-TYPE
		SYNTAX SEQUENCE OF PvcShapeCurrToDte-Entry
		ACCESS not-accessible
		STATUS mandatory
		DESCRIPTION
		" PVC current traffic shape table, which displays
		  the traffic shape information based on each PVC."
		::={ probeTrafficShape 3 }

	pvcShapeCurrToDte-Entry OBJECT-TYPE
		SYNTAX PvcShapeCurrToDte-Entry
		ACCESS not-accessible
		STATUS mandatory
		DESCRIPTION
		" Identifies an entry (row) in pvc current traffic shape to DTE table"
		INDEX { pvcShapeCurrToDte-index}
		::={ pvcShapeCurrToDte-Table 1 }

	PvcShapeCurrToDte-Entry ::=
		SEQUENCE {
		  pvcShapeCurrToDte-index
			INTEGER,
		  pvcShapeCurrToDteLevel-1
			INTEGER,
		  pvcShapeCurrToDteLevel-2
			INTEGER,
		  pvcShapeCurrToDteLevel-3
			INTEGER,
		  pvcShapeCurrToDteLevel-4
			INTEGER,
		  pvcShapeCurrToDteLevel-5
			INTEGER,
		  pvcShapeCurrToDteLevel-6
			INTEGER,
		  pvcShapeCurrToDteLevel-7
			INTEGER
		}

	pvcShapeCurrToDte-index OBJECT-TYPE
		SYNTAX INTEGER ( 16..991 )
		ACCESS read-only
		STATUS mandatory
		DESCRIPTION
                " The index value which uniquely identifies the PVC
		  number to which this entry is applicable. "
		::={ pvcShapeCurrToDte-Entry 1 }

	pvcShapeCurrToDteLevel-1 OBJECT-TYPE
		SYNTAX INTEGER ( 0..100 )
		ACCESS read-only
		STATUS mandatory
		DESCRIPTION
		" This object identifies the percentage of traffic in level one
		  in current 15 minutes to the direction of DTE."
		::={ pvcShapeCurrToDte-Entry 2 }

	pvcShapeCurrToDteLevel-2 OBJECT-TYPE
		SYNTAX INTEGER ( 0..100 )
		ACCESS read-only
		STATUS mandatory
		DESCRIPTION
		" This object identifies the percentage of traffic in level two
		  in current 15 minutes to the direction of DTE."
		::={ pvcShapeCurrToDte-Entry 3 }

	pvcShapeCurrToDteLevel-3 OBJECT-TYPE
		SYNTAX INTEGER ( 0..100 )
		ACCESS read-only
		STATUS mandatory
		DESCRIPTION
		" This object identifies the percentage of traffic in level three
		  in current 15 minutes to the direction of DTE."
		::={ pvcShapeCurrToDte-Entry 4 }

	pvcShapeCurrToDteLevel-4 OBJECT-TYPE
		SYNTAX INTEGER ( 0..100 )
		ACCESS read-only
		STATUS mandatory
		DESCRIPTION
		" This object identifies the percentage of traffic in level four
		  in current 15 minutes to the direction of DTE."
		::={ pvcShapeCurrToDte-Entry 5 }

	pvcShapeCurrToDteLevel-5 OBJECT-TYPE
		SYNTAX INTEGER ( 0..100 )
		ACCESS read-only
		STATUS mandatory
		DESCRIPTION
		" This object identifies the percentage of traffic in level five
		  in current 15 minutes to the direction of DTE."
		::={ pvcShapeCurrToDte-Entry 6 }

	pvcShapeCurrToDteLevel-6 OBJECT-TYPE
		SYNTAX INTEGER ( 0..100 )
		ACCESS read-only
		STATUS mandatory
		DESCRIPTION
		" This object identifies the percentage of traffic in level six
		  in current 15 minutes to the direction of DTE."
		::={ pvcShapeCurrToDte-Entry 7 }

	pvcShapeCurrToDteLevel-7 OBJECT-TYPE
		SYNTAX INTEGER ( 0..100 )
		ACCESS read-only
		STATUS mandatory
		DESCRIPTION
		" This object identifies the percentage of traffic in level seven
		  in current 15 minutes to the direction of DTE."
		::={ pvcShapeCurrToDte-Entry 8 }

--
-- 4. Interval PVC traffic shape To DCE Table displays the traffic shape information
--    for every PVC within the 24 hours to the direction of DCE.
--    A -1 value indicates interval is prior to system power-on.  This
--    does not apply to indices, such as PVC and interval number.
--

	pvcShapeIntvToDce-Table OBJECT-TYPE
		SYNTAX SEQUENCE OF PvcShapeIntvToDce-Entry
		ACCESS not-accessible
		STATUS mandatory
		DESCRIPTION
		" PVC shape to DCE interval table, which displays the pvc traffic shape
		  information to the direction of DCE within 24 hours. "
		::={ probeTrafficShape 4 }

	pvcShapeIntvToDce-Entry OBJECT-TYPE
		SYNTAX PvcShapeIntvToDce-Entry
		ACCESS not-accessible
		STATUS mandatory
		DESCRIPTION
		" Identifies an entry (row) in pvc traffic shape to DCE interval table"
		INDEX { pvcShapeIntvToDce-pvcIx, pvcShapeIntvToDce-intvIx }
		::={ pvcShapeIntvToDce-Table 1 }

	PvcShapeIntvToDce-Entry ::=
		SEQUENCE {
		  pvcShapeIntvToDce-pvcIx
			INTEGER,
		  pvcShapeIntvToDce-intvIx
			INTEGER,
		  pvcShapeIntvToDceLevel-1
			INTEGER,
		  pvcShapeIntvToDceLevel-2
			INTEGER,
		  pvcShapeIntvToDceLevel-3
			INTEGER,
		  pvcShapeIntvToDceLevel-4
			INTEGER,
		  pvcShapeIntvToDceLevel-5
			INTEGER,
		  pvcShapeIntvToDceLevel-6
			INTEGER,
		  pvcShapeIntvToDceLevel-7
			INTEGER
		}

	pvcShapeIntvToDce-pvcIx OBJECT-TYPE
		SYNTAX INTEGER ( 16..991 )
		ACCESS read-only
		STATUS mandatory
		DESCRIPTION
                " The index value which uniquely identifies the PVC
		  number to which this entry is applicable. "
		::={ pvcShapeIntvToDce-Entry 1 }

	pvcShapeIntvToDce-intvIx OBJECT-TYPE
		SYNTAX INTEGER ( 1..96 )
		ACCESS read-only
		STATUS mandatory
		DESCRIPTION
                " The index value which uniquely identifies the interval
		  number to which this entry is applicable. "
		::={ pvcShapeIntvToDce-Entry 2 }

	pvcShapeIntvToDceLevel-1 OBJECT-TYPE
		SYNTAX INTEGER ( 0..100 )
		ACCESS read-only
		STATUS mandatory
		DESCRIPTION
		" This object identifies the percentage of traffic in level one
		  within a specific 15-minutes interval in the direction of DCE."
		::={ pvcShapeIntvToDce-Entry 3 }

	pvcShapeIntvToDceLevel-2 OBJECT-TYPE
		SYNTAX INTEGER ( 0..100 )
		ACCESS read-only
		STATUS mandatory
		DESCRIPTION
		" This object identifies the percentage of traffic in level two
		  within a specific 15-minutes interval in the direction of DCE."
		::={ pvcShapeIntvToDce-Entry 4 }

	pvcShapeIntvToDceLevel-3 OBJECT-TYPE
		SYNTAX INTEGER ( 0..100 )
		ACCESS read-only
		STATUS mandatory
		DESCRIPTION
		" This object identifies the percentage of traffic in level three
		  within a specific 15-minutes interval in the direction of DCE."
		::={ pvcShapeIntvToDce-Entry 5 }

	pvcShapeIntvToDceLevel-4 OBJECT-TYPE
		SYNTAX INTEGER ( 0..100 )
		ACCESS read-only
		STATUS mandatory
		DESCRIPTION
		" This object identifies the percentage of traffic in level four
		  within a specific 15-minutes interval in the direction of DCE."
		::={ pvcShapeIntvToDce-Entry 6 }

	pvcShapeIntvToDceLevel-5 OBJECT-TYPE
		SYNTAX INTEGER ( 0..100 )
		ACCESS read-only
		STATUS mandatory
		DESCRIPTION
		" This object identifies the percentage of traffic in level five
		  within a specific 15-minutes interval in the direction of DCE."
		::={ pvcShapeIntvToDce-Entry 7 }

	pvcShapeIntvToDceLevel-6 OBJECT-TYPE
		SYNTAX INTEGER ( 0..100 )
		ACCESS read-only
		STATUS mandatory
		DESCRIPTION
		" This object identifies the percentage of traffic in level six
		  within a specific 15-minutes interval in the direction of DCE."
		::={ pvcShapeIntvToDce-Entry 8 }

	pvcShapeIntvToDceLevel-7 OBJECT-TYPE
		SYNTAX INTEGER ( 0..100 )
		ACCESS read-only
		STATUS mandatory
		DESCRIPTION
		" This object identifies the percentage of traffic in level seven
		  within a specific 15-minutes interval in the direction of DCE."
		::={ pvcShapeIntvToDce-Entry 9 }

--
-- 5. Interval PVC traffic shape To DTE Table displays the traffic information
--    for every PVC within the 24 hours to the direction of DTE.
--    A -1 value indicates interval is prior to system power-on.  This
--    does not apply to indices, such as PVC and interval number.
--

	pvcShapeIntvToDte-Table OBJECT-TYPE
		SYNTAX SEQUENCE OF PvcShapeIntvToDte-Entry
		ACCESS not-accessible
		STATUS mandatory
		DESCRIPTION
		" PVC shape to DTE interval table, which displays the pvc traffic
		  information to the direction of DTE within 24 hours. "
		::={ probeTrafficShape 5 }

	pvcShapeIntvToDte-Entry OBJECT-TYPE
		SYNTAX PvcShapeIntvToDte-Entry
		ACCESS not-accessible
		STATUS mandatory
		DESCRIPTION
		" Identifies an entry (row) in pvc traffic shape to DTE interval table"
		INDEX { pvcShapeIntvToDte-pvcIx, pvcShapeIntvToDte-intvIx }
		::={ pvcShapeIntvToDte-Table 1 }

	PvcShapeIntvToDte-Entry ::=
		SEQUENCE {
		  pvcShapeIntvToDte-pvcIx
			INTEGER,
		  pvcShapeIntvToDte-intvIx
			INTEGER,
		  pvcShapeIntvToDteLevel-1
			INTEGER,
		  pvcShapeIntvToDteLevel-2
			INTEGER,
		  pvcShapeIntvToDteLevel-3
			INTEGER,
		  pvcShapeIntvToDteLevel-4
			INTEGER,
		  pvcShapeIntvToDteLevel-5
			INTEGER,
		  pvcShapeIntvToDteLevel-6
			INTEGER,
		  pvcShapeIntvToDteLevel-7
			INTEGER
		}

	pvcShapeIntvToDte-pvcIx OBJECT-TYPE
		SYNTAX INTEGER ( 16..991 )
		ACCESS read-only
		STATUS mandatory
		DESCRIPTION
                " The index value which uniquely identifies the PVC
		  number to which this entry is applicable. "
		::={ pvcShapeIntvToDte-Entry 1 }

	pvcShapeIntvToDte-intvIx OBJECT-TYPE
		SYNTAX INTEGER ( 1..96 )
		ACCESS read-only
		STATUS mandatory
		DESCRIPTION
                " The index value which uniquely identifies the interval
		  number to which this entry is applicable. "
		::={ pvcShapeIntvToDte-Entry 2 }

	pvcShapeIntvToDteLevel-1 OBJECT-TYPE
		SYNTAX INTEGER ( 0..100 )
		ACCESS read-only
		STATUS mandatory
		DESCRIPTION
		" This object identifies the percentage of traffic in level one
		  within a specific 15-minutes interval in the direction of DTE."
		::={ pvcShapeIntvToDte-Entry 3 }

	pvcShapeIntvToDteLevel-2 OBJECT-TYPE
		SYNTAX INTEGER ( 0..100 )
		ACCESS read-only
		STATUS mandatory
		DESCRIPTION
		" This object identifies the percentage of traffic in level two
		  within a specific 15-minutes interval in the direction of DTE."
		::={ pvcShapeIntvToDte-Entry 4 }

	pvcShapeIntvToDteLevel-3 OBJECT-TYPE
		SYNTAX INTEGER ( 0..100 )
		ACCESS read-only
		STATUS mandatory
		DESCRIPTION
		" This object identifies the percentage of traffic in level three
		  within a specific 15-minutes interval in the direction of DTE."
		::={ pvcShapeIntvToDte-Entry 5 }

	pvcShapeIntvToDteLevel-4 OBJECT-TYPE
		SYNTAX INTEGER ( 0..100 )
		ACCESS read-only
		STATUS mandatory
		DESCRIPTION
		" This object identifies the percentage of traffic in level four
		  within a specific 15-minutes interval in the direction of DTE."
		::={ pvcShapeIntvToDte-Entry 6 }

	pvcShapeIntvToDteLevel-5 OBJECT-TYPE
		SYNTAX INTEGER ( 0..100 )
		ACCESS read-only
		STATUS mandatory
		DESCRIPTION
		" This object identifies the percentage of traffic in level five
		  within a specific 15-minutes interval in the direction of DTE."
		::={ pvcShapeIntvToDte-Entry 7 }

	pvcShapeIntvToDteLevel-6 OBJECT-TYPE
		SYNTAX INTEGER ( 0..100 )
		ACCESS read-only
		STATUS mandatory
		DESCRIPTION
		" This object identifies the percentage of traffic in level six
		  within a specific 15-minutes interval in the direction of DTE."
		::={ pvcShapeIntvToDte-Entry 8 }

	pvcShapeIntvToDteLevel-7 OBJECT-TYPE
		SYNTAX INTEGER ( 0..100 )
		ACCESS read-only
		STATUS mandatory
		DESCRIPTION
		" This object identifies the percentage of traffic in level seven
		  within a specific 15-minutes interval in the direction of DTE."
		::={ pvcShapeIntvToDte-Entry 9 }

--
--                           TRAP GENERATION GROUP
--
-- SYSTEM TRAP EVENTS
--
-- These are unsolicited messages sent by the SNMP Agent to alert the NMS
-- of critical System errors that would require immediate attention.
--

        pvcNotAvailDCE 	TRAP-TYPE
                ENTERPRISE  link-probe
                VARIABLES   { sysName, pvcPerfCurr-num-index, pvc-unavail-toDce,
                              pvcNotAvailThreshDCE, current-intv-start-time }
    	DESCRIPTION
            " This trap is generated when a PVC's unavailability is exceed the
              preset threshold due to the network fault."
    	::= 1

        pvcNotAvailDTE TRAP-TYPE
                ENTERPRISE  link-probe
                VARIABLES   { sysName, pvcPerfCurr-num-index, pvc-unavail-toDte,
                              pvcNotAvailThreshDTE, current-intv-start-time }
    	DESCRIPTION
            " This trap is generated when a PVC's unavailability is exceed the
              preset threshold due to the local DTE fault."
        ::= 2

        pvcRTD TRAP-TYPE
                ENTERPRISE  link-probe
                VARIABLES   { sysName, pvcPerfCurr-num-index, --pvc-RTD-curr,
                              pvcAveRTDThresh, current-intv-start-time }
    	DESCRIPTION
            " This trap is generated when a PVC's average round trap delay (RTD) is
              exceed the preset threshold."
        ::= 3

        frChanUtilizeToDTE TRAP-TYPE
                ENTERPRISE  link-probe
                VARIABLES   { sysName, frChanUtilizThreshToDTE,
                              chan-user-load-rx-curr, current-intv-start-time }
    	DESCRIPTION
            " This trap is generated when channel utilization to DTE direction
              is exceed the preset threshold."
        ::= 4

        frChanUtilizeToDCE TRAP-TYPE
                ENTERPRISE  link-probe
                VARIABLES   { sysName, frChanUtilizThreshToDCE,
                              chan-user-load-tx-curr, current-intv-start-time }
    	DESCRIPTION
            " This trap is generated when channel utilization to DCE direction
              is exceed the preset threshold."
        ::= 5

        pvcBecn TRAP-TYPE
                ENTERPRISE  link-probe
                VARIABLES   { sysName, pvc-number-index-curr, becn-frames-pvc-curr,
                              pvcBecnThresh, current-intv-start-time }
    	DESCRIPTION
            " This trap is generated when a PVC's BECNs is exceed
              the preset threshold within current interval."
        ::= 6

        pvcFecn TRAP-TYPE
                ENTERPRISE  link-probe
                VARIABLES   { sysName, pvc-number-index-curr, fecn-frames-pvc-curr,
                              pvcFecnThresh, current-intv-start-time }
    	DESCRIPTION
            " This trap is generated when a PVC's FECNs is exceed
              the preset threshold within current interval."
        ::= 7

        pvcUtilToDTE TRAP-TYPE
                ENTERPRISE  link-probe
                VARIABLES   { sysName, pvcPerfCurr-num-index, pvc-user-load-rx-curr,
                              pvcUtilToDTEThresh, current-intv-start-time }
    	DESCRIPTION
            " This trap is generated when a PVC's utilization is exceeding
              the preset threshold within current interval."
        ::= 8

        pvcUtilToDCE TRAP-TYPE
                ENTERPRISE  link-probe
                VARIABLES   { sysName, pvcPerfCurr-num-index, pvc-user-load-tx-curr,
                              pvcUtilToDCEThresh, current-intv-start-time }
    	DESCRIPTION
            " This trap is generated when a PVC's utilization is exceeding
              the preset threshold within current interval."
        ::= 9

        pvcCIRExceedToDTE TRAP-TYPE
                ENTERPRISE  link-probe
                VARIABLES   { sysName, pvcPerfCurr-num-index, pvc-CIR-toNet-exceed-curr,
                              pvcCirToDTE, current-intv-start-time }
    	DESCRIPTION
            " This trap is generated when the octets transmitted to the network
              direction is exceeding the CIR within current interval."
        ::= 10

        pvcEIRExceedToDTE TRAP-TYPE
                ENTERPRISE  link-probe
                VARIABLES   { sysName, pvcPerfCurr-num-index, pvc-EIR-toNet-exceed-curr,
                              pvcEirToDTE, current-intv-start-time }
    	DESCRIPTION
            " This trap is generated when the octets transmitted to the network
              direction is exceeding the EIR within current interval."
        ::= 11

        pvcLossFrameTx TRAP-TYPE
                ENTERPRISE  link-probe
                VARIABLES   { sysName, pvcPerfCurr-num-index, pvc-loss-frame-tx-curr,
                              current-intv-start-time }
    	DESCRIPTION
            " This trap is generated when frames were lost in the transmission
              direction within current interval."
        ::= 12

        pvcLossFrameRx TRAP-TYPE
                ENTERPRISE  link-probe
                VARIABLES   { sysName, pvcPerfCurr-num-index, pvc-loss-frame-rx-curr,
                              current-intv-start-time }
    	DESCRIPTION
            " This trap is generated when frames were lost in the receiving
              direction within current interval."
        ::= 13

        frChanUtilToDTE-exception TRAP-TYPE
                ENTERPRISE  link-probe
                VARIABLES   { sysName, chanLoadToDTEThresh-realTime,
                              --chan-load-toDTE-realTime,
										current-intv-start-time }
    	DESCRIPTION
            " This trap will be sent at any time in two cases:
              1. The channel utilization to DTE (measured in TC) is exceeding
                 the threshold if such trap never be sent in this interval or
                 the frChanUtilToDTE-endException trap was just sent;
              2. The variation of the channel utilization to DTE is exceeding
                 the trapRange if such trap has just be sent. "
        ::= 14

        frChanUtilToDCE-exception TRAP-TYPE
                ENTERPRISE  link-probe
                VARIABLES   { sysName, chanLoadToDCEThresh-realTime,
                              --chan-load-toDCE-realTime,
										current-intv-start-time }
    	DESCRIPTION
            " This trap will be sent at any time in two cases:
              1. The channel utilization to DCE (measured in TC) is exceeding
                 the threshold if such trap never be sent in this interval or
                 the frChanUtilToDTE-endException trap was just sent;
              2. The variation of the channel utilization to DCE is exceeding
                 the trapRange if such trap has just be sent. "
        ::= 15

        frChanUtilToDTE-endException TRAP-TYPE
                ENTERPRISE  link-probe
                VARIABLES   { sysName, chanLoadToDTEThresh-realTime,
                              --chan-load-toDTE-realTime,
										current-intv-start-time }
    	DESCRIPTION
            " This trap will be sent if the channel utilization to DTE (measured in TC)
              is changed back below the threshold."
        ::= 16

        frChanUtilToDCE-endException TRAP-TYPE
                ENTERPRISE  link-probe
                VARIABLES   { sysName, chanLoadToDTEThresh-realTime,
                              --chan-load-toDCE-realTime,
										current-intv-start-time }
    	DESCRIPTION
            " This trap will be sent if the channel utilization to DCE (measured in TC)
              is changed back below the threshold."
        ::= 17

        pvcRTD-exception TRAP-TYPE
                ENTERPRISE  link-probe
                VARIABLES   { sysName, pvcPerfCurr-num-index, pvcRTDThresh-realTime,
                              --pvc-RTD-realTime,
										current-intv-start-time }
    	DESCRIPTION
            " This trap will be sent at any time in two cases:
              1. The PVC RTD real time value (measured at every Poll interval) is
                 exceeding the threshold if such trap never be sent in this interval
                 or the pvcRTD-endException trap was just sent;
              2. The variation of the pvc-RTD-realTime is exceeding
                 the trapRange if such trap has just be sent. "
        ::= 18

        pvcRTD-endException TRAP-TYPE
                ENTERPRISE  link-probe
                VARIABLES   { sysName, pvcPerfCurr-num-index, pvcRTDThresh-realTime,
                              --pvc-RTD-realTime,
										current-intv-start-time }
    	DESCRIPTION
            " This trap will be sent if the PVC DTD real time (measured at every Poll
              interval) is changed back below the threshold."
        ::= 19

        pvcLoadToDTE-exception TRAP-TYPE
                ENTERPRISE  link-probe
                VARIABLES   { sysName, pvcPerfCurr-num-index, pvcLoadToDTEThresh-realTime,
                              --pvc-load-toDTE-realTime,
										current-intv-start-time }
    	DESCRIPTION
            " This trap will be sent at any time at these two cases:
              1. The PVC load to DTE real time value (measured in TC ) is
                 exceeding the threshold if such trap has never be sent in this
                 interval or the pvcLoadToDTE-endException trap was just sent;
              2. The variation of the pvc-load-toDTE-realTime is exceeding
                 the trapRange if such trap has just be sent. "
        ::= 20

        pvcLoadToDCE-exception TRAP-TYPE
                ENTERPRISE  link-probe
                VARIABLES   { sysName, pvcPerfCurr-num-index, pvcLoadToDCEThresh-realTime,
                              --pvc-load-toDCE-realTime,
										current-intv-start-time }
    	DESCRIPTION
            " This trap will be sent at any time at these two cases:
              1. The PVC load to DCE real time value (measured in TC, ) is
                 exceeding the threshold if such trap has never be sent in this
                 interval or the pvcLoadToDCE-endException trap was just sent;
              2. The variation of the pvc-load-toDCE-realTime is exceeding
                 the trapRange if such trap has just be sent. "
        ::= 21

        pvcLoadToDTE-endException TRAP-TYPE
                ENTERPRISE  link-probe
                VARIABLES   { sysName, pvcPerfCurr-num-index, pvcLoadToDTEThresh-realTime,
                              --pvc-load-toDTE-realTime,
										current-intv-start-time }
    	DESCRIPTION
            " This trap will be sent if the PVC load to DTE real time (measured in TC)
              is changed back below the threshold."
        ::= 22

        pvcLoadToDCE-endException TRAP-TYPE
                ENTERPRISE  link-probe
                VARIABLES   { sysName, pvcPerfCurr-num-index, pvcLoadToDCEThresh-realTime,
                              --pvc-load-toDCE-realTime,
										current-intv-start-time }
    	DESCRIPTION
            " This trap will be sent if the PVC load to DCE real time (measured in TC)
              is changed back below the threshold."
        ::= 23

        pvcStatusChangeAvail TRAP-TYPE
                ENTERPRISE  link-probe
                VARIABLES   { sysName, pvcPerfCurr-num-index,
                              current-intv-start-time }
    	DESCRIPTION
            " This trap is generated when a PVC status changes from unavailable to
              available."
        ::= 24

        pvcStatusChangeUnavail TRAP-TYPE
                ENTERPRISE  link-probe
                VARIABLES   { sysName, pvcPerfCurr-num-index,
                              current-intv-start-time }
    	DESCRIPTION
            " This trap is generated when a PVC status changes from available to
              unavailable, or from valid to invalid (PVC becomes deleted)."
        ::= 25

        dbuPvcStatusChangeBackedUp TRAP-TYPE
                ENTERPRISE  link-probe
                VARIABLES   { sysName, dbuPVCTableIndex,
                              sys-current-time }
    	DESCRIPTION
            " This trap is generated when a DBU PVC status changes
	      to backed-up."
        ::= 26

        dbuPvcStatusChangeNotBackedUp TRAP-TYPE
                ENTERPRISE  link-probe
                VARIABLES   { sysName, dbuPVCTableIndex,
                              sys-current-time }
    	DESCRIPTION
            " This trap is generated when a DBU PVC status changes
	      to not backed-up."
        ::= 27

        dbuBackupCallActivation TRAP-TYPE
                ENTERPRISE  link-probe
                VARIABLES   { sysName, dbuDialedIsdnAddress, sys-current-time }
    	DESCRIPTION
            " This trap is generated when a back-up call is activated."
        ::= 28

        dbuBackupCallDeactivation TRAP-TYPE
                ENTERPRISE  link-probe
                VARIABLES   { sysName, dbuDialedIsdnAddress, sys-current-time }
    	DESCRIPTION
            " This trap is generated when a back-up call is deactivated."
        ::= 29

        dbuBackupCallFailed TRAP-TYPE
                ENTERPRISE  link-probe
                VARIABLES   { sysName, dbuDialedIsdnAddress, sys-current-time }
    	DESCRIPTION
            " This trap is generated when a back-up call failed to activate."
        ::= 30

        dcdAlarmDetection TRAP-TYPE
                ENTERPRISE  link-probe
                VARIABLES   { sysName, sys-current-time }
    	DESCRIPTION
            " This trap is generated when a DCD alarm is detected."
        ::= 31

        cp3000Event TRAP-TYPE
                ENTERPRISE  link-probe
                VARIABLES   { sysName, sys-current-time, eventSubject,
			      pvcIdentifier, cp3000LogCode, cp3000LogSpeed,
			      cp3000LogDate, cp3000LogInfo }
    	DESCRIPTION
            " This trap is the CP-3000 compliant Log Event trap, generated
	      when a Device or PVC specific status change occurs."
        ::= 32

        bypassEnabled TRAP-TYPE
                ENTERPRISE  link-probe
                VARIABLES   { sysName, bypassStatus, sys-current-time }
    	DESCRIPTION
            " This trap is generated when frame relay automatically enables
              frame relay data BYPASS."
        ::= 33

--
-- Subgroups in probe historical group
--
-- 1. Real Time Historical Data (up to 12 15-min. interval)
-- 2. Channel Performance Historical Data (up to 12 15-min. interval)
-- 3. PVC Performance Historical Data (up to 12 15-min. interval)
-- 4. PVC Traffic Shape To DCE Historical Data (up to 12 15-min. interval)
-- 5. PVC Traffic Shape To DTE Historical Data (up to 12 15-min. interval)
--


--
-- 1. Real Time  Historical Subgroup displays the time associated with each
--    interval in the other subgroups of probe historical group.
--    Up to 3 hours from a previous power up of the system are broken into
--    12 completed 15 minute intervals.  Intervals are not necessarily
--    contiguous in time, but they are in time sequence.
--    Every 15 minutes, the first interval(s) of this subgroup is the same as
--    the first interval(s) of the corresponding data in other interval subgroups.
--    After the system is active for 3 hours, this subgroup is completely the
--    same as the first 12 intervals of the corresponding data in other
--    interval subgroups.
--

        histIntvStartTimeIntv-Table OBJECT-TYPE
                SYNTAX SEQUENCE OF HistIntvStartTimeIntv-Entry
		ACCESS not-accessible
		STATUS mandatory
		DESCRIPTION
                " Probe historical interval start time table, which displays
                  the interval starting time for each interval covering
                  an historical 3 hours."
                ::={ probeHistorical 1 }

        histIntvStartTimeIntv-Entry OBJECT-TYPE
                SYNTAX HistIntvStartTimeIntv-Entry
		ACCESS not-accessible
		STATUS mandatory
		DESCRIPTION
                " Identifies an entry (row) in probe interval start time
                  interval table."
                INDEX { histIntvStartTimeIntv-index }
                ::={ histIntvStartTimeIntv-Table 1 }

        HistIntvStartTimeIntv-Entry ::=
		SEQUENCE {
                  histIntvStartTimeIntv-index
                        INTEGER,
                  hist-intv-start-time
                        DisplayString

		}

        histIntvStartTimeIntv-index OBJECT-TYPE
                SYNTAX INTEGER (1..12)
		ACCESS read-only
		STATUS mandatory
		DESCRIPTION
		" Identifies an entry (row) in historical PVC performance table,
                  total 12 time intervals, where 1 is the most recently completed
                  15 minutes interval and 12 is the least recently completed 15
                  minutes interval (assuming that all 12 intervals are valid).  "
                ::={ histIntvStartTimeIntv-Entry 1 }

        hist-intv-start-time OBJECT-TYPE
		SYNTAX DisplayString (SIZE (0..255))
		ACCESS read-only
		STATUS mandatory
		DESCRIPTION
                " hist-intv-start-time displays the current interval starting
		  time with 4 digits year, 2 digits month, 2 digits date and
                  hours, minutes and seconds, which are each 2 digits."
                ::={ histIntvStartTimeIntv-Entry 2 }


--
-- 2. Channel Performance Historical Interval Table displays the statistical data
--    which measure the channel performance up to an historical 3 hours of
--    operation.  Up to 3 hours from a previous power up of the system are broken
--    into 12 completed 15 minute intervals.  Intervals are not necessarily
--    contiguous in time, but they are in time sequence.
--    Every 15 minutes, the first interval(s) of this subgroup is the same as
--    the first interval(s) of the corresponding data in other interval subgroups.
--    After the system is active for 3 hours, this subgroup is completely the
--    same as the first 12 intervals of the corresponding data in other
--    interval subgroups.
--

        histChanPerfIntv-Table OBJECT-TYPE
                SYNTAX SEQUENCE OF HistChanPerfIntv-Entry
		ACCESS not-accessible
		STATUS mandatory
		DESCRIPTION
		" Probe channel performance table, which displays
                  the performance statistical data based on the probe
                  channel covering an historical 3 hours."
                ::={ probeHistorical 2 }

        histChanPerfIntv-Entry OBJECT-TYPE
                SYNTAX HistChanPerfIntv-Entry
		ACCESS not-accessible
		STATUS mandatory
		DESCRIPTION
                " Identifies an entry (row) in probe historical channel
                  performance table."
                INDEX { histChanPerfIntv-index }
                ::={ histChanPerfIntv-Table 1 }

        HistChanPerfIntv-Entry ::=
		SEQUENCE {
                  histChanPerfIntv-index
                        INTEGER,
                  hist-chan-unavail-toDte-intv
                        DisplayString,
                  hist-chan-unavail-toDce-intv
                        DisplayString,
                  hist-chan-user-load-tx-intv
                        DisplayString,
                  hist-chan-user-load-rx-intv
                        DisplayString

		}

        histChanPerfIntv-index OBJECT-TYPE
                SYNTAX INTEGER (1..12)
		ACCESS read-only
		STATUS mandatory
		DESCRIPTION
		" Identifies an entry (row) in historical PVC performance table,
                  total 12 time intervals, where 1 is the most recently completed
                  15 minutes interval and 12 is the least recently completed 15
                  minutes interval (assuming that all 12 intervals are valid).  "
                ::={ histChanPerfIntv-Entry 1 }

        hist-chan-unavail-toDte-intv OBJECT-TYPE
                SYNTAX DisplayString (SIZE (0..6))
		ACCESS read-only
		STATUS mandatory
		DESCRIPTION
		" This object identifies the channel unavailability due to remote
                  DTE fault within a 15 minute interval. This statistical data is
		  calculated by the channel unavailable time over the full time
		  interval."
                ::={ histChanPerfIntv-Entry 2 }

        hist-chan-unavail-toDce-intv OBJECT-TYPE
                SYNTAX DisplayString (SIZE (0..6))
		ACCESS read-only
		STATUS mandatory
		DESCRIPTION
		" This object identifies the channel unavailability due to local
                  DTE fault within a 15 minutes interval. This statistical data is
		  calculated by the channel unavailable time over the full time
		  interval."
                ::={ histChanPerfIntv-Entry 3 }

        hist-chan-user-load-tx-intv OBJECT-TYPE
                SYNTAX DisplayString (SIZE (0..6))
		ACCESS read-only
		STATUS mandatory
		DESCRIPTION
                " channel average user tx load within a 15 minute interval,
                  this statistical data is calculated by user data octets sent by
		  the channel within the 15 minutes over the total channel
		  available load ( which depends on physical interface speed). "
                ::={ histChanPerfIntv-Entry 4 }

        hist-chan-user-load-rx-intv OBJECT-TYPE
                SYNTAX DisplayString (SIZE (0..6))
		ACCESS read-only
		STATUS mandatory
		DESCRIPTION
                " channel average user rx load within a 15 minute interval,
                  this statistical data is calculated by user data octets received
		  by the channel within the 15 minutes over the total channel
		  available load( which depends on physical interface speed). "
                ::={ histChanPerfIntv-Entry 5 }


--
-- 3. PVC Performance Historical Interval Table displays the statistical data
--    for every PVC over an historical 3 hours of operation.
--    Up to 3 hours from a previous power up of the system are broken
--    into 12 completed 15 minute intervals.  Intervals are not necessarily
--    contiguous in time, but they are in time sequence.
--    Every 15 minutes, the first interval(s) of this subgroup is the same as
--    the first interval(s) of the corresponding data in other interval subgroups.
--    After the system is active for 3 hours, this subgroup is completely the
--    same as the first 12 intervals of the corresponding data in other
--    interval subgroups.
--

histPvcPerfIntv-Table OBJECT-TYPE
                SYNTAX SEQUENCE OF HistPvcPerfIntv-Entry
		ACCESS not-accessible
		STATUS mandatory
		DESCRIPTION
		" PVC performance interval table, which displays
                  the performance statistical data based on each
                  PVC in an historical 3 hours."
                ::={ probeHistorical 3 }

        histPvcPerfIntv-Entry OBJECT-TYPE
                SYNTAX HistPvcPerfIntv-Entry
		ACCESS not-accessible
		STATUS mandatory
		DESCRIPTION
		" Identifies an entry (row) in pvc statistic table"
                INDEX { histPvcPerfIntv-num-index, histPvcPerf-intv-index }
                ::={ histPvcPerfIntv-Table 1 }

        HistPvcPerfIntv-Entry ::=
		SEQUENCE {
                  histPvcPerfIntv-num-index
			INTEGER,
                  histPvcPerf-intv-index
                        INTEGER,
                  hist-pvc-tx-time-intv
			INTEGER,
                  hist-pvc-unavail-toDte-intv
                        DisplayString,
                  hist-pvc-unavail-toDce-intv
                        DisplayString,
                  hist-pvc-user-load-tx-intv
                        DisplayString,
                  hist-pvc-user-load-rx-intv
                        DisplayString,
                  hist-pvc-CIR-toNet-exceed-intv
			INTEGER,
                  hist-pvc-loss-frame-tx-intv
			INTEGER,
                  hist-pvc-loss-frame-rx-intv
			INTEGER
		}

        histPvcPerfIntv-num-index OBJECT-TYPE
		SYNTAX INTEGER ( 16..991 )
		ACCESS read-only
		STATUS mandatory
		DESCRIPTION
                " The index value which uniquely identifies the PVC
		  number to which this entry is applicable. "
                ::={ histPvcPerfIntv-Entry 1 }

        histPvcPerf-intv-index OBJECT-TYPE
                SYNTAX INTEGER (1..12)
		ACCESS read-only
		STATUS mandatory
		DESCRIPTION
		" Identifies an entry (row) in historical PVC performance table,
                  total 12 time intervals, where 1 is the most recently completed
                  15 minutes interval and 12 is the least recently completed 15
                  minutes interval (assuming that all 12 intervals are valid). "
                ::={ histPvcPerfIntv-Entry 2 }


        hist-pvc-tx-time-intv OBJECT-TYPE
                SYNTAX INTEGER
		ACCESS read-only
		STATUS mandatory
		DESCRIPTION
		" Probe token average round trip time within a
                  15 minutes interval for a specific PVC.  A -1 value indicates
                  data is Not-Avail. "
                ::={ histPvcPerfIntv-Entry 3 }

        hist-pvc-unavail-toDte-intv OBJECT-TYPE
                SYNTAX DisplayString (SIZE (0..6))
		ACCESS read-only
		STATUS mandatory
		DESCRIPTION
		" This object identifies the PVC average unavailability
                  within a 15 minutes interval. This statistical data is
		  calculated by a PVC unavailable time due to the network
		  or remote DTE fault over the full time interval."
                ::={ histPvcPerfIntv-Entry 4 }

        hist-pvc-unavail-toDce-intv OBJECT-TYPE
                SYNTAX DisplayString (SIZE (0..6))
		ACCESS read-only
		STATUS mandatory
		DESCRIPTION
		" This object identifies the PVC average unavailability
                  within a 15 minutes interval. This statistical data is
		  calculated by a PVC unavailable time due to the local DTE
		  fault over the full time interval."
                ::={ histPvcPerfIntv-Entry 5 }

        hist-pvc-user-load-tx-intv OBJECT-TYPE
                SYNTAX DisplayString (SIZE (0..6))
		ACCESS read-only
		STATUS mandatory
		DESCRIPTION
		" This object identifies the PVC average user tx load within
                  a 15 minutes interval.  This statistical data is calculated by
		  user data octets sent by a specific PVC within the 15 minutes
		  over the PVC total available load.
		  Note: If the CIR is correctly defined for this PVC, PVC available
                        load will depend on CIR, otherwise, it will get it from
                        interface speed. "
                ::={ histPvcPerfIntv-Entry 6 }

        hist-pvc-user-load-rx-intv OBJECT-TYPE
                SYNTAX DisplayString (SIZE (0..6))
		ACCESS read-only
		STATUS mandatory
		DESCRIPTION
		" This object identifies the PVC average user rx load within
                  a 15 minutes interval.  This statistical data is calculated by
		  user data octets received by a specific PVC within the 15 minutes
		  over the PVC total available load.
		  Note: If the CIR is correctly defined for this PVC, PVC available
                        load will depend on CIR, otherwise, it will get it from
                        interface speed. "
                ::={ histPvcPerfIntv-Entry 7 }

        hist-pvc-CIR-toNet-exceed-intv OBJECT-TYPE
		SYNTAX INTEGER
		ACCESS read-only
		STATUS mandatory
		DESCRIPTION
		" This object identifies the number of exceeding CIR times that the
		  network detected within an interval. The measurement is
		  done for every Tc, and the direction is to the network."
                ::={ histPvcPerfIntv-Entry 8 }

        hist-pvc-loss-frame-tx-intv OBJECT-TYPE
		SYNTAX INTEGER {
                        no-resp(254),
			not-avail(255)
		}
		ACCESS read-only
		STATUS mandatory
		DESCRIPTION
		" This object identifies the percentage of tx loss of frames within
		  the total tx frames for this PVC in this interval."
                ::={ histPvcPerfIntv-Entry 9 }

        hist-pvc-loss-frame-rx-intv OBJECT-TYPE
		SYNTAX INTEGER {
                        no-resp(254),
			not-avail(255)
		}
		ACCESS read-only
		STATUS mandatory
		DESCRIPTION
		" This object identifies the percentage of rx loss of frames within
		  the total rx frames for this PVC in this interval."
                ::={ histPvcPerfIntv-Entry 10 }


--
-- 4. Interval PVC traffic shape To DCE Table displays the traffic shape information
--    for every PVC within an historical 3 hours to the direction of DCE.
--    Up to 3 hours from a previous power up of the system are broken
--    into 12 completed 15 minute intervals.  Intervals are not necessarily
--    contiguous in time, but they are in time sequence.
--    Every 15 minutes, the first interval(s) of this subgroup is the same as
--    the first interval(s) of the corresponding data in other interval subgroups.
--    After the system is active for 3 hours, this subgroup is completely the
--    same as the first 12 intervals of the corresponding data in other
--    interval subgroups.
--

        histPvcShapeIntvToDce-Table OBJECT-TYPE
                SYNTAX SEQUENCE OF HistPvcShapeIntvToDce-Entry
		ACCESS not-accessible
		STATUS mandatory
		DESCRIPTION
		" PVC shape to DCE interval table, which displays the pvc traffic shape
                  information to the direction of DCE over 3 previous hours. "
                ::={ probeHistorical 4 }

        histPvcShapeIntvToDce-Entry OBJECT-TYPE
                SYNTAX HistPvcShapeIntvToDce-Entry
		ACCESS not-accessible
		STATUS mandatory
		DESCRIPTION
		" Identifies an entry (row) in pvc traffic shape to DCE interval table"
                INDEX { histPvcShapeIntvToDce-pvcIx, histPvcShapeIntvToDce-intvIx }
                ::={ histPvcShapeIntvToDce-Table 1 }

        HistPvcShapeIntvToDce-Entry ::=
		SEQUENCE {
                  histPvcShapeIntvToDce-pvcIx
			INTEGER,
                  histPvcShapeIntvToDce-intvIx
			INTEGER,
                  histPvcShapeIntvToDceLevel-1
			INTEGER,
                  histPvcShapeIntvToDceLevel-2
			INTEGER,
                  histPvcShapeIntvToDceLevel-3
			INTEGER,
                  histPvcShapeIntvToDceLevel-4
			INTEGER,
                  histPvcShapeIntvToDceLevel-5
			INTEGER,
                  histPvcShapeIntvToDceLevel-6
			INTEGER,
                  histPvcShapeIntvToDceLevel-7
			INTEGER
		}

        histPvcShapeIntvToDce-pvcIx OBJECT-TYPE
		SYNTAX INTEGER ( 16..991 )
		ACCESS read-only
		STATUS mandatory
		DESCRIPTION
                " The index value which uniquely identifies the PVC
		  number to which this entry is applicable. "
                ::={ histPvcShapeIntvToDce-Entry 1 }

        histPvcShapeIntvToDce-intvIx OBJECT-TYPE
                SYNTAX INTEGER ( 1..12 )
		ACCESS read-only
		STATUS mandatory
		DESCRIPTION
                " The index value which uniquely identifies the interval
		  number to which this entry is applicable. "
                ::={ histPvcShapeIntvToDce-Entry 2 }

        histPvcShapeIntvToDceLevel-1 OBJECT-TYPE
		SYNTAX INTEGER ( 0..100 )
		ACCESS read-only
		STATUS mandatory
		DESCRIPTION
		" This object identifies the percentage of traffic in level one
		  within a specific 15-minutes interval in the direction of DCE."
                ::={ histPvcShapeIntvToDce-Entry 3 }

        histPvcShapeIntvToDceLevel-2 OBJECT-TYPE
		SYNTAX INTEGER ( 0..100 )
		ACCESS read-only
		STATUS mandatory
		DESCRIPTION
		" This object identifies the percentage of traffic in level two
		  within a specific 15-minutes interval in the direction of DCE."
                ::={ histPvcShapeIntvToDce-Entry 4 }

        histPvcShapeIntvToDceLevel-3 OBJECT-TYPE
		SYNTAX INTEGER ( 0..100 )
		ACCESS read-only
		STATUS mandatory
		DESCRIPTION
		" This object identifies the percentage of traffic in level three
		  within a specific 15-minutes interval in the direction of DCE."
                ::={ histPvcShapeIntvToDce-Entry 5 }

        histPvcShapeIntvToDceLevel-4 OBJECT-TYPE
		SYNTAX INTEGER ( 0..100 )
		ACCESS read-only
		STATUS mandatory
		DESCRIPTION
		" This object identifies the percentage of traffic in level four
		  within a specific 15-minutes interval in the direction of DCE."
                ::={ histPvcShapeIntvToDce-Entry 6 }

        histPvcShapeIntvToDceLevel-5 OBJECT-TYPE
		SYNTAX INTEGER ( 0..100 )
		ACCESS read-only
		STATUS mandatory
		DESCRIPTION
		" This object identifies the percentage of traffic in level five
		  within a specific 15-minutes interval in the direction of DCE."
                ::={ histPvcShapeIntvToDce-Entry 7 }

        histPvcShapeIntvToDceLevel-6 OBJECT-TYPE
		SYNTAX INTEGER ( 0..100 )
		ACCESS read-only
		STATUS mandatory
		DESCRIPTION
		" This object identifies the percentage of traffic in level six
		  within a specific 15-minutes interval in the direction of DCE."
                ::={ histPvcShapeIntvToDce-Entry 8 }

        histPvcShapeIntvToDceLevel-7 OBJECT-TYPE
		SYNTAX INTEGER ( 0..100 )
		ACCESS read-only
		STATUS mandatory
		DESCRIPTION
		" This object identifies the percentage of traffic in level seven
		  within a specific 15-minutes interval in the direction of DCE."
                ::={ histPvcShapeIntvToDce-Entry 9 }

--
-- 5. Interval PVC traffic shape To DTE Table displays the traffic shape information
--    for every PVC within an historical 3 hours to the direction of DTE.
--    Up to 3 hours from a previous power up of the system are broken
--    into 12 completed 15 minute intervals.  Intervals are not necessarily
--    contiguous in time, but they are in time sequence.
--    Every 15 minutes, the first interval(s) of this subgroup is the same as
--    the first interval(s) of the corresponding data in other interval subgroups.
--    After the system is active for 3 hours, this subgroup is completely the
--    same as the first 12 intervals of the corresponding data in other
--    interval subgroups.
--

        histPvcShapeIntvToDte-Table OBJECT-TYPE
                SYNTAX SEQUENCE OF HistPvcShapeIntvToDte-Entry
		ACCESS not-accessible
		STATUS mandatory
		DESCRIPTION
		" PVC shape to DTE interval table, which displays the pvc traffic
                  information to the direction of DTE over 3 previous hours. "
                ::={ probeHistorical 5 }

        histPvcShapeIntvToDte-Entry OBJECT-TYPE
                SYNTAX HistPvcShapeIntvToDte-Entry
		ACCESS not-accessible
		STATUS mandatory
		DESCRIPTION
		" Identifies an entry (row) in pvc traffic shape to DTE interval table"
                INDEX { histPvcShapeIntvToDte-pvcIx, histPvcShapeIntvToDte-intvIx }
                ::={ histPvcShapeIntvToDte-Table 1 }

        HistPvcShapeIntvToDte-Entry ::=
		SEQUENCE {
                  histPvcShapeIntvToDte-pvcIx
			INTEGER,
                  histPvcShapeIntvToDte-intvIx
			INTEGER,
                  histPvcShapeIntvToDteLevel-1
			INTEGER,
                  histPvcShapeIntvToDteLevel-2
			INTEGER,
                  histPvcShapeIntvToDteLevel-3
			INTEGER,
                  histPvcShapeIntvToDteLevel-4
			INTEGER,
                  histPvcShapeIntvToDteLevel-5
			INTEGER,
                  histPvcShapeIntvToDteLevel-6
			INTEGER,
                  histPvcShapeIntvToDteLevel-7
			INTEGER
		}

        histPvcShapeIntvToDte-pvcIx OBJECT-TYPE
		SYNTAX INTEGER ( 16..991 )
		ACCESS read-only
		STATUS mandatory
		DESCRIPTION
                " The index value which uniquely identifies the PVC
		  number to which this entry is applicable. "
                ::={ histPvcShapeIntvToDte-Entry 1 }

        histPvcShapeIntvToDte-intvIx OBJECT-TYPE
                SYNTAX INTEGER ( 1..12 )
		ACCESS read-only
		STATUS mandatory
		DESCRIPTION
                " The index value which uniquely identifies the interval
		  number to which this entry is applicable. "
                ::={ histPvcShapeIntvToDte-Entry 2 }

        histPvcShapeIntvToDteLevel-1 OBJECT-TYPE
		SYNTAX INTEGER ( 0..100 )
		ACCESS read-only
		STATUS mandatory
		DESCRIPTION
		" This object identifies the percentage of traffic in level one
		  within a specific 15-minutes interval in the direction of DTE."
                ::={ histPvcShapeIntvToDte-Entry 3 }

        histPvcShapeIntvToDteLevel-2 OBJECT-TYPE
		SYNTAX INTEGER ( 0..100 )
		ACCESS read-only
		STATUS mandatory
		DESCRIPTION
		" This object identifies the percentage of traffic in level two
		  within a specific 15-minutes interval in the direction of DTE."
                ::={ histPvcShapeIntvToDte-Entry 4 }

        histPvcShapeIntvToDteLevel-3 OBJECT-TYPE
		SYNTAX INTEGER ( 0..100 )
		ACCESS read-only
		STATUS mandatory
		DESCRIPTION
		" This object identifies the percentage of traffic in level three
		  within a specific 15-minutes interval in the direction of DTE."
                ::={ histPvcShapeIntvToDte-Entry 5 }

        histPvcShapeIntvToDteLevel-4 OBJECT-TYPE
		SYNTAX INTEGER ( 0..100 )
		ACCESS read-only
		STATUS mandatory
		DESCRIPTION
		" This object identifies the percentage of traffic in level four
		  within a specific 15-minutes interval in the direction of DTE."
                ::={ histPvcShapeIntvToDte-Entry 6 }

        histPvcShapeIntvToDteLevel-5 OBJECT-TYPE
		SYNTAX INTEGER ( 0..100 )
		ACCESS read-only
		STATUS mandatory
		DESCRIPTION
		" This object identifies the percentage of traffic in level five
		  within a specific 15-minutes interval in the direction of DTE."
                ::={ histPvcShapeIntvToDte-Entry 7 }

        histPvcShapeIntvToDteLevel-6 OBJECT-TYPE
		SYNTAX INTEGER ( 0..100 )
		ACCESS read-only
		STATUS mandatory
		DESCRIPTION
		" This object identifies the percentage of traffic in level six
		  within a specific 15-minutes interval in the direction of DTE."
                ::={ histPvcShapeIntvToDte-Entry 8 }

        histPvcShapeIntvToDteLevel-7 OBJECT-TYPE
		SYNTAX INTEGER ( 0..100 )
		ACCESS read-only
		STATUS mandatory
		DESCRIPTION
		" This object identifies the percentage of traffic in level seven
		  within a specific 15-minutes interval in the direction of DTE."
                ::={ histPvcShapeIntvToDte-Entry 9 }


--
-- Subgroups in probe interval start time group
--
-- 1. Real Time of Interval Data (up to 96 15-min. interval)
--


-- 1. Real Time  of Interval Subgroup displays the time associated with each
--    interval in the other  probe groups of statistics, performance, and
--    traffic shape.
--

        intvStartTimeIntv-Table OBJECT-TYPE
                SYNTAX SEQUENCE OF IntvStartTimeIntv-Entry
		ACCESS not-accessible
		STATUS mandatory
		DESCRIPTION
                " Probe interval start time table, which displays
                  the interval starting time for each interval covering
                  the last 24 hours."
                ::={ probeIntervalStartTime 1 }

        intvStartTimeIntv-Entry OBJECT-TYPE
                SYNTAX IntvStartTimeIntv-Entry
		ACCESS not-accessible
		STATUS mandatory
		DESCRIPTION
                " Identifies an entry (row) in probe interval start time
                  interval table."
                INDEX { intvStartTimeIntv-index }
                ::={ intvStartTimeIntv-Table 1 }

        IntvStartTimeIntv-Entry ::=
		SEQUENCE {
                  intvStartTimeIntv-index
                        INTEGER,
                  intv-start-time
                        DisplayString

		}

        intvStartTimeIntv-index OBJECT-TYPE
                SYNTAX INTEGER (1..96)
		ACCESS read-only
		STATUS mandatory
		DESCRIPTION
                " Identifies an entry (row) in interval start time table,
                  total 96 time intervals, where 1 is the most recently completed
                  15 minutes interval and 96 is the least recently completed 15
                  minutes interval.  "
                ::={ intvStartTimeIntv-Entry 1 }

        intv-start-time OBJECT-TYPE
		SYNTAX DisplayString (SIZE (0..255))
		ACCESS read-only
		STATUS mandatory
		DESCRIPTION
                " intv-start-time displays the current interval starting
		  time with 4 digits year, 2 digits month, 2 digits date and
                  hours, minutes and seconds, which are each 2 digits."
                ::={ intvStartTimeIntv-Entry 2 }

--
--  Dial Backup Unit Configuration Group
--

	dbuPVCTable OBJECT-TYPE
		SYNTAX SEQUENCE OF DbuPVCEntry
		ACCESS not-accessible
		STATUS mandatory
		DESCRIPTION
                " DBU PVC table. It contains PVC/DLCI Dial-Backup information "
		::={ dbuConfigGroup 1 }

	dbuPVCEntry OBJECT-TYPE
		SYNTAX DbuPVCEntry
		ACCESS not-accessible
		STATUS mandatory
		DESCRIPTION
		" Identifies an entry (row) in dbuPVCTable."
		INDEX { dbuPVCTableIndex }
                ::={ dbuPVCTable 1 }

	DbuPVCEntry ::=
		SEQUENCE {
		  dbuPVCTableIndex
		      INTEGER,
		  dbuRemotePVCDlci
		      INTEGER,
		  dbuIsdnAddress
		      DisplayString,
		  dbuPvcCir
		      INTEGER
		  }

	dbuPVCTableIndex OBJECT-TYPE
		SYNTAX INTEGER ( 16..991 )
		ACCESS read-only
		STATUS mandatory
		DESCRIPTION
		"Identifies an entry (row) in PVC table as the local
		 PVC (DLCI) Number. "
		::={ dbuPVCEntry 1 }

	dbuRemotePVCDlci OBJECT-TYPE
		SYNTAX INTEGER (16..991)
		ACCESS read-write
		STATUS mandatory
		DESCRIPTION
		"Defines the remote PVC's DLCI number the data is to be routed to. "
		::={ dbuPVCEntry 2 }

	dbuIsdnAddress OBJECT-TYPE
                SYNTAX DisplayString (SIZE (0..26))
		ACCESS read-write
		STATUS mandatory
		DESCRIPTION
		"Defines the ISDN Dialing Address to reach the PVC's backup site"
		::={ dbuPVCEntry 3 }

	dbuPvcCir OBJECT-TYPE
		SYNTAX INTEGER (0..2048000)
		ACCESS read-write
		STATUS mandatory
		DESCRIPTION
		"This parameter defines the maximum transfer information rate
		 (Bits Per Second) toward the backup PVC. "
		::={ dbuPVCEntry 4 }

	dbuMasterSlave OBJECT-TYPE
		SYNTAX INTEGER {
                        slave(1),
			master(2)
			}
		ACCESS read-write
		STATUS mandatory
		DESCRIPTION
		" Defines whether the DBU probe is a Master or Slave. "
                ::={ dbuConfigGroup 2 }

	dbuBackupType OBJECT-TYPE
		SYNTAX INTEGER {
			linkProbe(1),
                        dte2Dbu1(2),
                        dte2Dbu2(3),
			channelDbu(4),
                        pvcDbu(5),
                        channelDbu-noProbe(6),
                        pvcDbu-noProbe(7)
			}
		ACCESS read-write
		STATUS mandatory
		DESCRIPTION
		" Defines the type of backup. "
                ::={ dbuConfigGroup 3 }

	dbuPVCAdd OBJECT-TYPE
		SYNTAX INTEGER ( 16..991 )
		ACCESS write-only
		STATUS mandatory
		DESCRIPTION
		" This object allows the user to add a PVC to the existing PVC
                  table, the added PVC must not exist before it is added."
                ::={ dbuConfigGroup 4 }

	dbuPVCDelete OBJECT-TYPE
		SYNTAX INTEGER ( 16..991 )
		ACCESS write-only
		STATUS mandatory
		DESCRIPTION
		" This object allows the user to delete a PVC from the existing PVC
		  table, the PVC must exist before it is deleted."
                ::={ dbuConfigGroup 5 }

	dbuRecoverCount OBJECT-TYPE
		SYNTAX INTEGER ( 0..10 )
		ACCESS read-write
		STATUS mandatory
		DESCRIPTION
		" Number of LMI Active Occurrences to restore PVC
		  change request. The value is between 1 to 20. "
                ::={ dbuConfigGroup 6 }

	dbuDialedIsdnAddress OBJECT-TYPE
                SYNTAX DisplayString (SIZE (0..26))
		ACCESS read-only
		STATUS mandatory
		DESCRIPTION
		"Defines the Dialed ISDN Address for the most recent DBU call"
		::={ dbuConfigGroup 7 }
--
--  Device Status Group
--
	globalStatus OBJECT-TYPE
		SYNTAX INTEGER {
                        ready(1),
			connected(2),
			test(3),
			hwFailure(4)
			}
		ACCESS read-only
		STATUS mandatory
		DESCRIPTION
		" Defines device status as:
		    ready     = Device is operating normally.
		    connected = At least one PVC is in backup mode.
		    test      = Device is in test mode (Not implemented yet).
		    hwFailure = ISDN line is not operable due to a
				hardware failure."
		::={ deviceStatusGroup 1 }

	pvcStatusTable OBJECT-TYPE
		SYNTAX SEQUENCE OF PvcStatusEntry
		ACCESS not-accessible
		STATUS mandatory
		DESCRIPTION
                " Per PVC status table. The PVCs(DLCIs) monitored are
		  PVCs(DLCIs) defined by LMI messages from the network. "
		::={ deviceStatusGroup 2 }

	pvcStatusEntry OBJECT-TYPE
		SYNTAX PvcStatusEntry
		ACCESS not-accessible
		STATUS mandatory
		DESCRIPTION
		" Identifies an entry (row) in pvcStatusTable."
		INDEX { pvcStatusIndex }
                ::={ pvcStatusTable 1 }

	PvcStatusEntry ::=
		SEQUENCE {
		  pvcStatusIndex
		      INTEGER,
		  pvcStatus
		      INTEGER
		  }

	pvcStatusIndex OBJECT-TYPE
		SYNTAX INTEGER ( 16..991 )
		ACCESS read-only
		STATUS mandatory
		DESCRIPTION
		"Identifies an entry (row) in pvcStatusTable as the local
		 PVC (DLCI) Number. "
		::={ pvcStatusEntry 1 }

	pvcStatus OBJECT-TYPE
		SYNTAX INTEGER {
			pvcInactive(1),
                        pvcActive(2),
                        pvcConnected(3),
			pvcTest(4)
			}
		ACCESS read-only
		STATUS mandatory
		DESCRIPTION
		" Defines the PVC Status as:
		  pvcInactive  = Configured at the network, but not active.
		  pvcActive    = Configured at the network, and active.
		  pvcConnected = Pvc connected in backup mode.
		  pvcTest      = Pvc in test mode (Not yet implemented). "
                ::={ pvcStatusEntry 2 }

--
--  The following objects are placed in the Device status Group only
--  to define the types. they have no meaning when retrieved with a GET
--  command. they are only valid when attached as objects to CP-3000
--  Event Traps.(See cp3000Event in Trap section)
--
	eventSubject OBJECT-TYPE
		SYNTAX INTEGER {
                        device(1),
			pvc(2)
			}
		ACCESS read-only
		STATUS mandatory
		DESCRIPTION
		" Defines CP-3000 Log Events as:
		    device    = Device specific events.
		    pvc       = PVC specific events."

		::={ deviceStatusGroup 3 }

	pvcIdentifier OBJECT-TYPE
		SYNTAX INTEGER ( 16..991 )
		ACCESS read-only
		STATUS mandatory
		DESCRIPTION
		"Identifies the PVC Number for PVC specific events only.
		 This objects has no meaning for Device specific events. "
		::={ deviceStatusGroup 4 }

	cp3000LogCode OBJECT-TYPE
                SYNTAX DisplayString (SIZE (1..1))
		ACCESS read-only
		STATUS mandatory
		DESCRIPTION
		"CP-3000 ASCII Log Code for Device or PVC events"
		::={ deviceStatusGroup 5 }

	cp3000LogSpeed OBJECT-TYPE
                SYNTAX DisplayString (SIZE (1..1))
		ACCESS read-only
		STATUS mandatory
		DESCRIPTION
		"CP-3000 ASCII Log Code for ISDN Line Speed"
		::={ deviceStatusGroup 6 }

	cp3000LogDate OBJECT-TYPE
                SYNTAX DisplayString (SIZE (12..12))
		ACCESS read-only
		STATUS mandatory
		DESCRIPTION
		"Date and Time in ASCII format: YYMMDDhhmmss "
		::={ deviceStatusGroup 7 }

	cp3000LogInfo OBJECT-TYPE
                SYNTAX DisplayString (SIZE (15..15))
		ACCESS read-only
		STATUS mandatory
		DESCRIPTION
		"Need to ask what goes in here "
		::={ deviceStatusGroup 8 }

--
-- Trap Acknowledge Group
--

	trapAckEnable OBJECT-TYPE
		SYNTAX INTEGER {
                        enabled(1),
			disabled(2)
			}
		ACCESS read-write
		STATUS mandatory
		DESCRIPTION
		"Acknowledgement setting for CP-3000 Log Event Traps:
		    enabled  = NMS has to acknowledge traps received.
		    disabled = NMS doesn't need to acknowledge traps received."
		::={ trapAcknowledgeGroup 1 }

	trapAckTimeout OBJECT-TYPE
		SYNTAX INTEGER ( 5..120 )
		ACCESS read-write
		STATUS mandatory
		DESCRIPTION
		"Timeout value to retransmit a trap when trapAckEnable
		 object == enabled and no ACK received from NMS."
		::={ trapAcknowledgeGroup 2 }

	trapAckFromMngr OBJECT-TYPE
		SYNTAX INTEGER {
                        trapNotAcked(1),
			trapAcked(2)
			}
		ACCESS read-write
		STATUS mandatory
		DESCRIPTION
		"Trap Acknowledgement Indication: When trapAckEnable
		 object == enabled NMS has to ACK every trap received."
		::={ trapAcknowledgeGroup 3 }

        END
