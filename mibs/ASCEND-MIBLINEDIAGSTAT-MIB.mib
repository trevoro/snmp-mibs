--			Ascend miblinediagstat MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBLINEDIAGSTAT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfLineDiagStat  OBJECT IDENTIFIER ::= { configuration 146}

	-- The mibmibProfLineDiagStat table
	--
	-- This table contains parameters for the mibmibProfLineDiagStat profile
	--

    mibmibProfLineDiagStatTable	OBJECT-TYPE
	SYNTAX		SEQUENCE OF MibmibProfLineDiagStatEntry
	ACCESS		not-accessible
	STATUS		mandatory
	DESCRIPTION	"A list of mibmibProfLineDiagStat profile entries."
	::= { mibmibProfLineDiagStat 1 }

    mibmibProfLineDiagStatEntry	OBJECT-TYPE
	SYNTAX		MibmibProfLineDiagStatEntry
	ACCESS		not-accessible
	STATUS		mandatory
	DESCRIPTION	"A mibmibProfLineDiagStat entry containing objects that
			 maps to the parameters of mibmibProfLineDiagStat profile."
	INDEX		{ mibProfLineDiagStat-Shelf-o, mibProfLineDiagStat-Slot-o, mibProfLineDiagStat-Item-o }
	::= { mibmibProfLineDiagStatTable 1 }

    MibmibProfLineDiagStatEntry ::=
	SEQUENCE {
	    mibProfLineDiagStat-Shelf-o
		INTEGER,
	    mibProfLineDiagStat-Slot-o
		INTEGER,
	    mibProfLineDiagStat-Item-o
		INTEGER,
	    mibProfLineDiagStat-PhysicalAddress-Shelf
		INTEGER,
	    mibProfLineDiagStat-PhysicalAddress-Slot
		INTEGER,
	    mibProfLineDiagStat-PhysicalAddress-ItemNumber
		INTEGER,
	    mibProfLineDiagStat-BertOperationState
		INTEGER,
	    mibProfLineDiagStat-IdtOperationState
		INTEGER,
	    mibProfLineDiagStat-BertErrorCounter
		INTEGER,
	    mibProfLineDiagStat-IdtSendCount
		INTEGER,
	    mibProfLineDiagStat-IdtRecvCount
		INTEGER,
	    mibProfLineDiagStat-IdtErrorCounter
		INTEGER,
	    mibProfLineDiagStat-Action-o
		INTEGER
	}

    mibProfLineDiagStat-Shelf-o	OBJECT-TYPE
	SYNTAX	INTEGER
	ACCESS	read-only
	STATUS	mandatory
	DESCRIPTION	""
	::= { mibmibProfLineDiagStatEntry 1 }

    mibProfLineDiagStat-Slot-o	OBJECT-TYPE
	SYNTAX	INTEGER
	ACCESS	read-only
	STATUS	mandatory
	DESCRIPTION	""
	::= { mibmibProfLineDiagStatEntry 2 }

    mibProfLineDiagStat-Item-o	OBJECT-TYPE
	SYNTAX	INTEGER
	ACCESS	read-only
	STATUS	mandatory
	DESCRIPTION	""
	::= { mibmibProfLineDiagStatEntry 3 }

    mibProfLineDiagStat-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibmibProfLineDiagStatEntry 4 }

    mibProfLineDiagStat-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibmibProfLineDiagStatEntry 5 }

    mibProfLineDiagStat-PhysicalAddress-ItemNumber	OBJECT-TYPE
	SYNTAX	INTEGER
	ACCESS	read-write
	STATUS	mandatory
	DESCRIPTION	"A number that specifies an addressable entity within the context of shelf and slot."
	::= { mibmibProfLineDiagStatEntry 6 }

    mibProfLineDiagStat-BertOperationState	OBJECT-TYPE
	SYNTAX	INTEGER {
		    waitingFor511Sync (2),
		    localLoopActive (3),
		    active (4),
		    stopped (5),
		    loopBackSetup (6),
		    startUp (7),
		    dataOverflow (8),
		    n-511SyncLoss (9),
		    waitingForRemoteNodeToEnterBert (10),
		    waitingForBertTxToSettle (11),
		    waiting (12),
		    pendingActive (13),
		    waitForLoopBack (14)
		}
	ACCESS	read-only
	STATUS	mandatory
	DESCRIPTION	"State of the BER Test. If the state is WAITING_FOR_511_SYNC, the remote side has not started its BER Test. If the line is not in the port up state, then local loopback is enabled and the BER test is started."
	::= { mibmibProfLineDiagStatEntry 7 }

    mibProfLineDiagStat-IdtOperationState	OBJECT-TYPE
	SYNTAX	INTEGER {
		    active (2),
		    stopped (3)
		}
	ACCESS	read-only
	STATUS	mandatory
	DESCRIPTION	"State of the IDT Test."
	::= { mibmibProfLineDiagStatEntry 8 }

    mibProfLineDiagStat-BertErrorCounter	OBJECT-TYPE
	SYNTAX	INTEGER
	ACCESS	read-only
	STATUS	mandatory
	DESCRIPTION	"Number of errors encountered while the BER test has run."
	::= { mibmibProfLineDiagStatEntry 9 }

    mibProfLineDiagStat-IdtSendCount	OBJECT-TYPE
	SYNTAX	INTEGER
	ACCESS	read-only
	STATUS	mandatory
	DESCRIPTION	"Number of messages sent in idt test."
	::= { mibmibProfLineDiagStatEntry 10 }

    mibProfLineDiagStat-IdtRecvCount	OBJECT-TYPE
	SYNTAX	INTEGER
	ACCESS	read-only
	STATUS	mandatory
	DESCRIPTION	"Number of messages received in the idt test."
	::= { mibmibProfLineDiagStatEntry 11 }

    mibProfLineDiagStat-IdtErrorCounter	OBJECT-TYPE
	SYNTAX	INTEGER
	ACCESS	read-only
	STATUS	mandatory
	DESCRIPTION	"Number of errors encountered while the IDT test has run."
	::= { mibmibProfLineDiagStatEntry 12 }

    mibProfLineDiagStat-Action-o	OBJECT-TYPE
	SYNTAX	INTEGER {
		    noAction (1),
		    createProfile (2),
		    deleteProfile (3)
		}
	ACCESS	read-write
	STATUS	mandatory
	DESCRIPTION	""
	::= { mibmibProfLineDiagStatEntry 13 }

END
