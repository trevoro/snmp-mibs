Wellfleet-DECNET-MIB DEFINITIONS ::= BEGIN

-- Created by mdl2asn version 3.1
-- Creation date: Wed Aug 30 16:39:27 EDT 1995


    IMPORTS

      Counter, Opaque
        FROM RFC1155-SMI
      OBJECT-TYPE
        FROM RFC-1212
      DisplayString
        FROM RFC1213-MIB
      wfDecGroup
        FROM Wellfleet-COMMON-MIB;


    wfivRouteGroup	OBJECT IDENTIFIER ::= { wfDecGroup 1 }

    wfivRouteCreateDelete OBJECT-TYPE
        SYNTAX	INTEGER {
    		    create(1),
    		    delete(2)
    		}
        ACCESS	read-write
        STATUS	mandatory
        DESCRIPTION
                "'This value determines whether DECnet is configured on this slot.'"
        DEFVAL	{ create }
        ::= { wfivRouteGroup 1 }

    wfivRouteEnableDisable OBJECT-TYPE
        SYNTAX	INTEGER {
    		    enable(1),
    		    disable(2)
    		}
        ACCESS	read-write
        STATUS	mandatory
        DESCRIPTION
                "'This value determines whether DECnet is to startup.'"
        DEFVAL	{ enable }
        ::= { wfivRouteGroup 2 }

    wfivRouteState OBJECT-TYPE
        SYNTAX	INTEGER {
    		    notpresent(4),
    		    initializing(3),
    		    down(2),
    		    up(1)
    		}
        ACCESS	read-only
        STATUS	mandatory
        DESCRIPTION
                "'This value determines whether DECnet is to startup.'"
        DEFVAL	{ notpresent }
        ::= { wfivRouteGroup 3 }

    wfivRouteBroadcastRouteTimer OBJECT-TYPE
        SYNTAX	INTEGER(1..65535)
        ACCESS	read-write
        STATUS	mandatory
        DESCRIPTION
                "'This value determines the maximum time allowed between
                Routing updates on Ethernet circuits. When this timer expires
                before a routing update occurs, a routing update is forced.
                With a standard calculation, Routing also uses this timer to
                enforce a minimum delay between routing updates. Seconds is a
                decimal integer in the range 1-65535.'"
        DEFVAL	{ 180 }
        ::= { wfivRouteGroup 4 }

    wfivRouteRoutingVers OBJECT-TYPE
        SYNTAX	DisplayString
        ACCESS	read-only
        STATUS	mandatory
        DESCRIPTION
                "'This read-only parameter identifies the executor node's
                Routing version number. The format is the same as for the
                Network Management version number.'"
        ::= { wfivRouteGroup 5 }

    wfivRouteMaxAddr OBJECT-TYPE
        SYNTAX	INTEGER(1..1023)
        ACCESS	read-write
        STATUS	mandatory
        DESCRIPTION
                "'This value represents the largest node number and,
                therefore, number of nodes that can be known about
                by the executor node's home area. The number is an integer
                in the range 1-1023.'"
        DEFVAL	{ 1023 }
        ::= { wfivRouteGroup 6 }

    wfivRouteMaxBdcastNonRouters OBJECT-TYPE
        SYNTAX	INTEGER(0..1023)
        ACCESS	read-write
        STATUS	mandatory
        DESCRIPTION
                "'This value represents the maximum total number of nonrouters
                the executor node can have on its broadcast circuits for one slot.
                The number is an integer in the range 0-1023.'"
        DEFVAL	{ 64 }
        ::= { wfivRouteGroup 7 }

    wfivRouteMaxBdcastRouters OBJECT-TYPE
        SYNTAX	INTEGER(0..1023)
        ACCESS	read-write
        STATUS	mandatory
        DESCRIPTION
                "'This value represents the maximum total number of routers the
                executor node can have on its broadcast circuits for one slot.
                The number is an integer in the range 0-1023.'"
        DEFVAL	{ 32 }
        ::= { wfivRouteGroup 8 }

    wfivRouteMaxCircuits OBJECT-TYPE
        SYNTAX	INTEGER(1..65535)
        ACCESS	read-write
        STATUS	mandatory
        DESCRIPTION
                "'This value represents the maximum number of Routing circuits
                that the executor node can know about. The number is decimal
                in the range 1-65535. Wellfleet limits this to 1024'"
        DEFVAL	{ 1024 }
        ::= { wfivRouteGroup 9 }

    wfivRouteMaxCost OBJECT-TYPE
        SYNTAX	INTEGER(1..1022)
        ACCESS	read-write
        STATUS	mandatory
        DESCRIPTION
                "'This value represents the maximum total path cost allowed
                from the executor to any node within an area. The path cost is
                the sum of the circuit costs along a path between two nodes.
                This parameter defines the point where the executor node's
                Routing decision algorithm declares another node
                unreachable because the cost of the least costly path to the
                other node is excessive. For correct operation, this parameter
                must not be less than the maximum path cost of the network.
                The MAXIMUM COST number is decimal in the range
                1-1022.'"
        DEFVAL	{ 1022 }
        ::= { wfivRouteGroup 10 }

    wfivRouteMaxHops OBJECT-TYPE
        SYNTAX	INTEGER(1..30)
        ACCESS	read-write
        STATUS	mandatory
        DESCRIPTION
                "'This value represents the maximum number of routing hops
                allowable from the executor to any other reachable node within
                an area. (A hop is the logical distance over a circuit between
                two adjacent nodes.) This parameter defines the point where
                the executor node's Routing decision algorithm
                declares another node unreachable because the length of the
                shortest path between the two nodes is too long. For correct
                operation, this parameter must not be less than the network
                diameter. (The network diameter is the reachability distance
                between the two nodes of the network having the greatest
                reachability distance, where reachability distance is the
                length the shortest path between a given pair of nodes.) The
                MAXIMUM HOPS number is decimal in the range 1-30.'"
        DEFVAL	{ 30 }
        ::= { wfivRouteGroup 11 }

    wfivRouteMaxVisits OBJECT-TYPE
        SYNTAX	INTEGER(0..63)
        ACCESS	read-write
        STATUS	mandatory
        DESCRIPTION
                "'This value represents the maximum number of nodes a message
                coming into the executor node can have visited. If the message
                is not for this node and the MAXIMUM VISITS number is exceeded,
                the message is discarded. The MAXIMUM VISITS parameter defines
                the point where the packet lifetime control algorithm discards
                a packet that has traversed too many nodes. For correct
                operation, this parameter must not be less than the maximum
                path length of the network. (The maximum path length is the
                routing distance between the two nodes of the network having
                the greatest routing distance, where routing distance is the
                length of the least costly path between a given pair of nodes.)
                The MAXIMUM VISITS number is decimal in the range MAXIMUM HOPS
                to 63.'"
        DEFVAL	{ 63 }
        ::= { wfivRouteGroup 12 }

    wfivRouteAreaMaxCost OBJECT-TYPE
        SYNTAX	INTEGER(0..1022)
        ACCESS	read-write
        STATUS	mandatory
        DESCRIPTION
                "'This value represents the maximum total path cost allowed
                from the executor to any other level 2 routing node. The AREA
                MAXIMUM COST number is decimal in the range
                1-1022. This parameter is only applicable if the executor
                node is of type AREA.'"
        DEFVAL	{ 1022 }
        ::= { wfivRouteGroup 13 }

    wfivRouteAreaMaxHops OBJECT-TYPE
        SYNTAX	INTEGER(0..30)
        ACCESS	read-write
        STATUS	mandatory
        DESCRIPTION
                "'This value represents the maximum number of routing hops
                allowable from the executor to any other level 2 routing node.
                The AREA MAXIMUM HOPS number is decimal in the range
                1-30.This parameter is only applicable if the executor node
                is of type AREA.'"
        DEFVAL	{ 30 }
        ::= { wfivRouteGroup 14 }

    wfivRouteMaxArea OBJECT-TYPE
        SYNTAX	INTEGER(1..63)
        ACCESS	read-write
        STATUS	mandatory
        DESCRIPTION
                "'This value represents the largest area number and, therefore,
                number of areas that can be known about by the executor node's
                Routing. This parameter is only applicable if the executor
                node is of type AREA. The number is an integer in the range
                1-63.'"
        DEFVAL	{ 63 }
        ::= { wfivRouteGroup 15 }

    wfivRouteType OBJECT-TYPE
        SYNTAX	INTEGER {
    		    area(3),
    		    routingiv(4),
    		    nonroutingiv(5)
    		}
        ACCESS	read-write
        STATUS	mandatory
        DESCRIPTION
                "'This parameter indicates the type of the executor node. The
                node-type is one of the following:

                ROUTING III
                NONROUTING III
                ROUTING IV
                NONROUTING IV
                AREA

                A routing node has full routing capability. A nonrouting node
                contains a subset of the Routing modules. The III and
                IV indicate the DNA phase of the node. Nonrouting nodes can
                deliver and receive packets to and from any node, but cannot
                route packets from other nodes through to other nodes. An
                area node routes between areas. Refer to the Routing
                specification for details.

                For adjacent nodes, this is a read-only parameter that
                indicates the type of the reachable adjacent node.
                NOTE: The ROUTING III and NONROUTING III values are
                incremented by one compared to the standard DECnet values in
                order to maintain compliance with RFC 1155)'"
        DEFVAL	{ area }
        ::= { wfivRouteGroup 16 }

    wfivRouteNumAdjs OBJECT-TYPE
        SYNTAX	Counter
        ACCESS	read-only
        STATUS	mandatory
        DESCRIPTION
                "This value represents the total number of adjacencies learned by
                the router."
        ::= { wfivRouteGroup 17 }

    wfivRouteNumLvl1Rts OBJECT-TYPE
        SYNTAX	Counter
        ACCESS	read-only
        STATUS	mandatory
        DESCRIPTION
                "This value represents the total number of Level 1 Routes learned by
                the router."
        ::= { wfivRouteGroup 18 }

    wfivRouteNumAreas OBJECT-TYPE
        SYNTAX	Counter
        ACCESS	read-only
        STATUS	mandatory
        DESCRIPTION
                "This value represents the total number of Areas learned by
                the router."
        ::= { wfivRouteGroup 19 }

    wfivRouteLevel1Area OBJECT-TYPE
        SYNTAX	INTEGER(1..63)
        ACCESS	read-write
        STATUS	mandatory
        DESCRIPTION
                "DECnet Phase IV area number for all circuits if this is a
                LEVEL 1 ONLY router. Put here for site manager convenience."
        DEFVAL	{ 1 }
        ::= { wfivRouteGroup 20 }

    wfivTriggeredUpdates OBJECT-TYPE
        SYNTAX  INTEGER {
                    enable(1),
                    disable(2)
                }
        ACCESS  read-write
        STATUS  mandatory
        DESCRIPTION
                "This will turn triggered updates on or off, Undernormal
                  conditions this should always be on."
        DEFVAL  { enable }
        ::= { wfivRouteGroup 21 }

    wfivTriggeredInterval OBJECT-TYPE
        SYNTAX  INTEGER(1..65535)
        ACCESS  read-write
        STATUS  mandatory
        DESCRIPTION
                "This is the time interval between triggered updates, this
                 should always be 1 (second) unless you are told by Nortel
                 to set this differently."
        DEFVAL  { 1 }
        ::= { wfivRouteGroup 22 }



    wfivCircuitTable OBJECT-TYPE
        SYNTAX	SEQUENCE OF WfivCircuitEntry
        ACCESS	not-accessible
        STATUS	mandatory
        DESCRIPTION
                "' Table of DECnet Circuit Configuration and Counter Records'"
        ::= { wfDecGroup 2 }

    wfivCircuitEntry OBJECT-TYPE
        SYNTAX	WfivCircuitEntry
        ACCESS	not-accessible
        STATUS	mandatory
        DESCRIPTION
                "'Parameters information about all circuits currently known.
                NOTE: depending on the type of object being querried (e.g., a
                level 1 vs. a level 2 router or end system) some variables may
                not be present.'"
        INDEX	{ wfivCircuitID }
        ::= { wfivCircuitTable 1 }

    WfivCircuitEntry ::= SEQUENCE {
    	    wfivCircuitCreateDelete
    		INTEGER,
    	    wfivCircuitEnableDisable
    		INTEGER,
    	    wfivCircuitCommonState
    		INTEGER,
    	    wfivCircuitArea
    		INTEGER,
    	    wfivCircuitNodeid
    		INTEGER,
    	    wfivCircuitNodeAddr
    		DisplayString,
    	    wfivCircuitID
    		INTEGER,
    	    wfivCircuitCommonType
    		INTEGER,
    	    wfivCircuitExecCost
    		INTEGER,
    	    wfivCircuitExecHelloTimer
    		INTEGER,
    	    wfivCircuitDesigRouterNodeAddr
    		DisplayString,
    	    wfivCircuitMaxRouters
    		INTEGER,
    	    wfivCircuitRouterPri
    		INTEGER,
    	    wfivCircuitCountAgedPktLoss
    		Counter,
    	    wfivCircuitCountNodeUnrPktLoss
    		Counter,
    	    wfivCircuitCountOutRngePktLoss
    		Counter,
    	    wfivCircuitCountOverSzePktLoss
    		Counter,
    	    wfivCircuitCountPacketFmtErr
    		Counter,
    	    wfivCircuitCountPtlRteUpdtLoss
    		Counter,
    	    wfivCircuitCountTransitPksRecd
    		Counter,
    	    wfivCircuitCountTransitPkSent
    		Counter,
    	    wfivCircuitCountRtHelloSent
    		Counter,
    	    wfivCircuitCountRtHelloRcvd
    		Counter,
    	    wfivCircuitCountHelloSent
    		Counter,
    	    wfivCircuitCountHelloRcvd
    		Counter,
    	    wfivCircuitCountL1UpdSent
    		Counter,
    	    wfivCircuitCountL1UpdRcvd
    		Counter,
    	    wfivCircuitCountAreaUpdSent
    		Counter,
    	    wfivCircuitCountAreaUpdRcvd
    		Counter,
    	    wfivCircuitCountDropped
    		Counter,
    	    wfivCircuitAllEndnodesMac
    		OCTET STRING,
    	    wfivCircuitAllRoutersMac
    		OCTET STRING,
    	    wfivCircuitAllAreaRoutersMac
    		OCTET STRING,
    	    wfivCircuitHelloEnableDisable
    		INTEGER,
    	    wfivCircuitRtHelloEnableDisable
    		INTEGER,
    	    wfivCircuitL1UpdateEnableDisable
    		INTEGER,
    	    wfivCircuitAllEndnodesMacInUse
    		OCTET STRING,
    	    wfivCircuitAllRoutersMacInUse
    		OCTET STRING,
    	    wfivCircuitAllAreaRoutersMacInUse
    		OCTET STRING,
    	    wfivCircuitL2UpdateDisable
    		INTEGER,
    	    wfivCircuitLevel
    		INTEGER
        }

    wfivCircuitCreateDelete OBJECT-TYPE
        SYNTAX	INTEGER {
    		    create(1),
    		    delete(2)
    		}
        ACCESS	read-write
        STATUS	mandatory
        DESCRIPTION
                "'This value determines whether the circuit is configured'"
        DEFVAL	{ create }
        ::= { wfivCircuitEntry 1 }

    wfivCircuitEnableDisable OBJECT-TYPE
        SYNTAX	INTEGER {
    		    enable(1),
    		    disable(2)
    		}
        ACCESS	read-write
        STATUS	mandatory
        DESCRIPTION
                "'This value represents the circuit's Network Management
                operational state. NOTE: These values are incremented by one
                compared to the standard DECnet values in order to maintain
                compliance with RFC 1155.'"
        DEFVAL	{ enable }
        ::= { wfivCircuitEntry 2 }

    wfivCircuitCommonState OBJECT-TYPE
        SYNTAX	INTEGER {
    		    notpresent(4),
    		    initializing(3),
    		    down(2),
    		    up(1)
    		}
        ACCESS	read-only
        STATUS	mandatory
        DESCRIPTION
                "'This value represents the circuit's operational state.'"
        DEFVAL	{ down }
        ::= { wfivCircuitEntry 3 }

    wfivCircuitArea OBJECT-TYPE
        SYNTAX	INTEGER(1..63)
        ACCESS	read-write
        STATUS	mandatory
        DESCRIPTION
                "'DECnet Phase IV area number for this circuit.'"
        DEFVAL	{ 1 }
        ::= { wfivCircuitEntry 4 }

    wfivCircuitNodeid OBJECT-TYPE
        SYNTAX	INTEGER(1..1023)
        ACCESS	read-write
        STATUS	mandatory
        DESCRIPTION
                "'DECnet Phase IV node address for this circuit.'"
        DEFVAL	{ 1 }
        ::= { wfivCircuitEntry 5 }

    wfivCircuitNodeAddr OBJECT-TYPE
        SYNTAX	DisplayString
        ACCESS	read-only
        STATUS	mandatory
        DESCRIPTION
                "'The address of the adjacent node.'"
        ::= { wfivCircuitEntry 6 }

    wfivCircuitID OBJECT-TYPE
        SYNTAX	INTEGER
        ACCESS	read-only
        STATUS	mandatory
        DESCRIPTION
                "'A unique value for each known circuit.'"
        ::= { wfivCircuitEntry 7 }

    wfivCircuitCommonType OBJECT-TYPE
        SYNTAX	INTEGER {
    		    sync(1),
    		    x25(4),
    		    ethernet(6),
    		    fddi(15),
    		    smds(100),
    		    fr(101),
    		    atm(102),
    		    ring(103),
    		    ppp(104)
    		}
        ACCESS	read-only
        STATUS	mandatory
        DESCRIPTION
                "'Represents the type of the circuit. For X.25 circuits, the
                value must be set to X25. For DDCMP and Ethernet circuits it
                is read only and is the same value as the protocol of
                the associated line.
                NOTE: Values 1 - 5 are incremented by one compared to the
                standard DECnet values in order to maintain compliance with
                RFC 1155.'"
        ::= { wfivCircuitEntry 8 }

    wfivCircuitExecCost OBJECT-TYPE
        SYNTAX	INTEGER(1..63)
        ACCESS	read-write
        STATUS	mandatory
        DESCRIPTION
                "'This value represents the Routing cost of the circuit.
                Routing routes messages along the path between two nodes having
                the smallest cost. The cost is a decimal integer in the range
                1-63.'"
        DEFVAL	{ 10 }
        ::= { wfivCircuitEntry 9 }

    wfivCircuitExecHelloTimer OBJECT-TYPE
        SYNTAX	INTEGER(1..8191)
        ACCESS	read-write
        STATUS	mandatory
        DESCRIPTION
                "'This value determines the frequency of Routing Hello (T3) messages
                sent to the adjacent node on the circuit. Seconds is a decimal
                integer in the range 1-8191.'"
        DEFVAL	{ 15 }
        ::= { wfivCircuitEntry 10 }

    wfivCircuitDesigRouterNodeAddr OBJECT-TYPE
        SYNTAX	DisplayString
        ACCESS	read-only
        STATUS	mandatory
        DESCRIPTION
                "'This value is the address of the designated router.'"
        ::= { wfivCircuitEntry 11 }

    wfivCircuitMaxRouters OBJECT-TYPE
        SYNTAX	INTEGER(0..33)
        ACCESS	read-write
        STATUS	mandatory
        DESCRIPTION
                "'NR -This parameter is the maximum number of routers (including
                the executor itself) allowed on the circuit by Routing for
                circuits that are owned by the executor node. Number is a
                decimal integer in the range 1-33.'"
        DEFVAL	{ 33 }
        ::= { wfivCircuitEntry 12 }

    wfivCircuitRouterPri OBJECT-TYPE
        SYNTAX	INTEGER(0..127)
        ACCESS	read-write
        STATUS	mandatory
        DESCRIPTION
                "'This parameter is the priority that this router is to have in
                the selection of designated router for the circuit on circuits
                that are owned by the executor node. Number is a decimal
                integer in the range 0-127. The default value is 64.'"
        DEFVAL	{ 64 }
        ::= { wfivCircuitEntry 13 }

    wfivCircuitCountAgedPktLoss OBJECT-TYPE
        SYNTAX	Counter
        ACCESS	read-only
        STATUS	mandatory
        DESCRIPTION
                "'Aged packet loss.'"
        ::= { wfivCircuitEntry 14 }

    wfivCircuitCountNodeUnrPktLoss OBJECT-TYPE
        SYNTAX	Counter
        ACCESS	read-only
        STATUS	mandatory
        DESCRIPTION
                "'Node unreachable packet loss.'"
        ::= { wfivCircuitEntry 15 }

    wfivCircuitCountOutRngePktLoss OBJECT-TYPE
        SYNTAX	Counter
        ACCESS	read-only
        STATUS	mandatory
        DESCRIPTION
                "'Node out-of-range packet loss.'"
        ::= { wfivCircuitEntry 16 }

    wfivCircuitCountOverSzePktLoss OBJECT-TYPE
        SYNTAX	Counter
        ACCESS	read-only
        STATUS	mandatory
        DESCRIPTION
                "'Oversized packet loss.'"
        ::= { wfivCircuitEntry 17 }

    wfivCircuitCountPacketFmtErr OBJECT-TYPE
        SYNTAX	Counter
        ACCESS	read-only
        STATUS	mandatory
        DESCRIPTION
                "'Packet format errors.'"
        ::= { wfivCircuitEntry 18 }

    wfivCircuitCountPtlRteUpdtLoss OBJECT-TYPE
        SYNTAX	Counter
        ACCESS	read-only
        STATUS	mandatory
        DESCRIPTION
                "'Partial routing update loss.'"
        ::= { wfivCircuitEntry 19 }

    wfivCircuitCountTransitPksRecd OBJECT-TYPE
        SYNTAX	Counter
        ACCESS	read-only
        STATUS	mandatory
        DESCRIPTION
                "'Transit packets Received. This value is stored internally as
                a 32 bit value.'"
        ::= { wfivCircuitEntry 20 }

    wfivCircuitCountTransitPkSent OBJECT-TYPE
        SYNTAX	Counter
        ACCESS	read-only
        STATUS	mandatory
        DESCRIPTION
                "'Transit packets sent. This value is stored internally as
                a 32 bit value.'"
        ::= { wfivCircuitEntry 21 }

    wfivCircuitCountRtHelloSent OBJECT-TYPE
        SYNTAX	Counter
        ACCESS	read-only
        STATUS	mandatory
        DESCRIPTION
                "' Router Hellos Sent'"
        ::= { wfivCircuitEntry 22 }

    wfivCircuitCountRtHelloRcvd OBJECT-TYPE
        SYNTAX	Counter
        ACCESS	read-only
        STATUS	mandatory
        DESCRIPTION
                "' Router Hellos Received'"
        ::= { wfivCircuitEntry 23 }

    wfivCircuitCountHelloSent OBJECT-TYPE
        SYNTAX	Counter
        ACCESS	read-only
        STATUS	mandatory
        DESCRIPTION
                "' Endnode Hellos Sent'"
        ::= { wfivCircuitEntry 24 }

    wfivCircuitCountHelloRcvd OBJECT-TYPE
        SYNTAX	Counter
        ACCESS	read-only
        STATUS	mandatory
        DESCRIPTION
                "' Endnode Hellos Received'"
        ::= { wfivCircuitEntry 25 }

    wfivCircuitCountL1UpdSent OBJECT-TYPE
        SYNTAX	Counter
        ACCESS	read-only
        STATUS	mandatory
        DESCRIPTION
                "' Level 1 Routing Updates Sent'"
        ::= { wfivCircuitEntry 26 }

    wfivCircuitCountL1UpdRcvd OBJECT-TYPE
        SYNTAX	Counter
        ACCESS	read-only
        STATUS	mandatory
        DESCRIPTION
                "' Level 1 Routing Updates Received'"
        ::= { wfivCircuitEntry 27 }

    wfivCircuitCountAreaUpdSent OBJECT-TYPE
        SYNTAX	Counter
        ACCESS	read-only
        STATUS	mandatory
        DESCRIPTION
                "' Area Routing Updates Sent'"
        ::= { wfivCircuitEntry 28 }

    wfivCircuitCountAreaUpdRcvd OBJECT-TYPE
        SYNTAX	Counter
        ACCESS	read-only
        STATUS	mandatory
        DESCRIPTION
                "' Area Routing Updates Received'"
        ::= { wfivCircuitEntry 29 }

    wfivCircuitCountDropped OBJECT-TYPE
        SYNTAX	Counter
        ACCESS	read-only
        STATUS	mandatory
        DESCRIPTION
                "' Dropped Packets '"
        ::= { wfivCircuitEntry 30 }

    wfivCircuitAllEndnodesMac OBJECT-TYPE
        SYNTAX	OCTET STRING
        ACCESS	read-write
        STATUS	mandatory
        DESCRIPTION
                "'This parameter can be used to assign the AllEndnodes multicast
                MAC address value for use over WAN media (e.g. Frame Relay).'"
        ::= { wfivCircuitEntry 31 }

    wfivCircuitAllRoutersMac OBJECT-TYPE
        SYNTAX	OCTET STRING
        ACCESS	read-write
        STATUS	mandatory
        DESCRIPTION
                "'This parameter can be used to assign the AllRouters multicast
                MAC address value for use over WAN media (e.g. Frame Relay).'"
        ::= { wfivCircuitEntry 32 }

    wfivCircuitAllAreaRoutersMac OBJECT-TYPE
        SYNTAX	OCTET STRING
        ACCESS	read-write
        STATUS	mandatory
        DESCRIPTION
                "'This parameter can be used to assign the AllAreaRouters multicast
                MAC address value for use over WAN media (e.g. Frame Relay).'"
        ::= { wfivCircuitEntry 33 }

    wfivCircuitHelloEnableDisable OBJECT-TYPE
        SYNTAX	INTEGER {
    		    enable(1),
    		    disable(2)
    		}
        ACCESS	read-write
        STATUS	mandatory
        DESCRIPTION
                "' This parameter is used to disable to sending of Hellos
                to Endnodes. It would be used in conjunction with Static
                Adjacencies to limit the amount of data passed over a WAN
                link (e.g. Frame Relay).'"
        DEFVAL	{ enable }
        ::= { wfivCircuitEntry 34 }

    wfivCircuitRtHelloEnableDisable OBJECT-TYPE
        SYNTAX	INTEGER {
    		    enable(1),
    		    disable(2)
    		}
        ACCESS	read-write
        STATUS	mandatory
        DESCRIPTION
                "' This parameter is used to disable to sending of Hellos
                to Routers. It would be used in conjunction with Static
                Adjacencies to limit the amount of data passed over a WAN
                link (e.g. Frame Relay).'"
        DEFVAL	{ enable }
        ::= { wfivCircuitEntry 35 }

    wfivCircuitL1UpdateEnableDisable OBJECT-TYPE
        SYNTAX	INTEGER {
    		    enable(1),
    		    disable(2)
    		}
        ACCESS	read-write
        STATUS	mandatory
        DESCRIPTION
                "' This parameter is used to disable to sending of Level 1
                topology updates. It would be used in conjunction with Static
                Adjacencies to limit the amount of data passed over a WAN
                link (e.g. Frame Relay).'"
        DEFVAL	{ enable }
        ::= { wfivCircuitEntry 36 }

    wfivCircuitAllEndnodesMacInUse OBJECT-TYPE
        SYNTAX	OCTET STRING
        ACCESS	read-only
        STATUS	mandatory
        DESCRIPTION
                "'This parameter displays the AllEndnodes multicast
                MAC address value in use over WAN media (e.g. Frame Relay).'"
        ::= { wfivCircuitEntry 37 }

    wfivCircuitAllRoutersMacInUse OBJECT-TYPE
        SYNTAX	OCTET STRING
        ACCESS	read-only
        STATUS	mandatory
        DESCRIPTION
                "'This parameter displays the AllRouters multicast
                MAC address value in use over WAN media (e.g. Frame Relay).'"
        ::= { wfivCircuitEntry 38 }

    wfivCircuitAllAreaRoutersMacInUse OBJECT-TYPE
        SYNTAX	OCTET STRING
        ACCESS	read-only
        STATUS	mandatory
        DESCRIPTION
                "'This parameter displays the AllAreaRouters multicast
                MAC address value for use over WAN media (e.g. Frame Relay).'"
        ::= { wfivCircuitEntry 39 }

    wfivCircuitL2UpdateDisable OBJECT-TYPE
        SYNTAX	INTEGER {
    		    enable(1),
    		    disable(2)
    		}
        ACCESS	read-write
        STATUS	mandatory
        DESCRIPTION
                "' This parameter is used to disable to sending of Level 2
                topology updates. It would be used in conjunction with Static
                Adjacencies and Static Routes to limit the amount of data passed
                over a WANl link (e.g. Frame Relay).'"
        DEFVAL	{ enable }
        ::= { wfivCircuitEntry 40 }

    wfivCircuitLevel OBJECT-TYPE
        SYNTAX	INTEGER {
    		    level2(1),
    		    only(2)
    		}
        ACCESS	read-write
        STATUS	mandatory
        DESCRIPTION
                "' This parameter is used to indicate at the circuit level
                  whether the routing is LEVEL 1 only, or LEVEL 1 and LEVEL 2
                  routing.'"
        DEFVAL	{ level2 }
        ::= { wfivCircuitEntry 41 }

    wfivLevel1RouteTable OBJECT-TYPE
        SYNTAX	SEQUENCE OF WfivLevel1RouteEntry
        ACCESS	not-accessible
        STATUS	mandatory
        DESCRIPTION
                "' Table of Level 1 Routing Table Entries'"
        ::= { wfDecGroup 3 }

    wfivLevel1RouteEntry OBJECT-TYPE
        SYNTAX	WfivLevel1RouteEntry
        ACCESS	not-accessible
        STATUS	mandatory
        DESCRIPTION
                "'A Record in the Level 1 Routing Table'"
        INDEX	{ wfivLevel1AreaId,
    		  wfivLevel1NodeId }
        ::= { wfivLevel1RouteTable 1 }

    WfivLevel1RouteEntry ::= SEQUENCE {
    	    wfivLevel1AreaId
    		INTEGER,
    	    wfivLevel1NodeId
    		INTEGER,
    	    wfivLevel1RouteNodeAddr
    		DisplayString,
    	    wfivLevel1RouteCircuitID
    		INTEGER,
    	    wfivLevel1RouteCost
    		INTEGER,
    	    wfivLevel1RouteHops
    		INTEGER,
    	    wfivLevel1RouteNextNode
    		DisplayString,
    	    wfivLevel1RouteDynamic
    		INTEGER
        }

    wfivLevel1AreaId OBJECT-TYPE
        SYNTAX	INTEGER
        ACCESS	read-only
        STATUS	mandatory
        DESCRIPTION
                "'Area Id for this node'"
        ::= { wfivLevel1RouteEntry 1 }

    wfivLevel1NodeId OBJECT-TYPE
        SYNTAX	INTEGER
        ACCESS	read-only
        STATUS	mandatory
        DESCRIPTION
                "'Node Id for this node'"
        ::= { wfivLevel1RouteEntry 2 }

    wfivLevel1RouteNodeAddr OBJECT-TYPE
        SYNTAX	DisplayString
        ACCESS	read-only
        STATUS	mandatory
        DESCRIPTION
                "'This value is the address of the node about which routing
                information is contained in this level 1 routing table.'"
        ::= { wfivLevel1RouteEntry 3 }

    wfivLevel1RouteCircuitID OBJECT-TYPE
        SYNTAX	INTEGER
        ACCESS	read-only
        STATUS	mandatory
        DESCRIPTION
                "'This READ_ONLY parameter identifies the circuit used to get
                to a remote node. Circuit-id is an id-string. This parameter
                can be used when displaying a list of nodes to indicate that
                the display is to be restricted to those nodes adjacent on the
                specified circuit.'"
        ::= { wfivLevel1RouteEntry 4 }

    wfivLevel1RouteCost OBJECT-TYPE
        SYNTAX	INTEGER
        ACCESS	read-only
        STATUS	mandatory
        DESCRIPTION
                "'This READ_ONLY parameter represents the total cost over the
                current path to the destination node. Cost is a positive
                integer value associated with using a circuit. Routing routes
                messages (data) along the path between two nodes with the
                smallest cost. COST is kept on a remote node basis.'"
        ::= { wfivLevel1RouteEntry 5 }

    wfivLevel1RouteHops OBJECT-TYPE
        SYNTAX	INTEGER
        ACCESS	read-only
        STATUS	mandatory
        DESCRIPTION
                "'This READ_ONLY parameter represents the number of hops over
                to a destination node. A hop is Routing value representing
                the logical distance between two nodes in a network. HOPS is
                kept on a remote node basis.'"
        ::= { wfivLevel1RouteEntry 6 }

    wfivLevel1RouteNextNode OBJECT-TYPE
        SYNTAX	DisplayString
        ACCESS	read-only
        STATUS	mandatory
        DESCRIPTION
                "'This READ_ONLY value indicates the next node on the circuit
                used to get to the node under scrutiny (next hop).'"
        ::= { wfivLevel1RouteEntry 7 }

    wfivLevel1RouteDynamic OBJECT-TYPE
        SYNTAX	INTEGER {
    		    dynamic(1),
    		    static(2)
    		}
        ACCESS	read-write
        STATUS	mandatory
        DESCRIPTION
                "This READ_WRITE parameter will indicate the type of Level 1 route,
                whether it is a Dynamic or a Static route"
        ::= { wfivLevel1RouteEntry 8 }

    wfivAreaTable OBJECT-TYPE
        SYNTAX	SEQUENCE OF WfivAreaEntry
        ACCESS	not-accessible
        STATUS	mandatory
        DESCRIPTION
                "'Table of Area Routing Table Entries'"
        ::= { wfDecGroup 4 }

    wfivAreaEntry OBJECT-TYPE
        SYNTAX	WfivAreaEntry
        ACCESS	not-accessible
        STATUS	mandatory
        DESCRIPTION
                "'The area routing information.'"
        INDEX	{ wfivAreaNum }
        ::= { wfivAreaTable 1 }

    WfivAreaEntry ::= SEQUENCE {
    	    wfivAreaNum
    		INTEGER,
    	    wfivAreaState
    		INTEGER,
    	    wfivAreaCost
    		INTEGER,
    	    wfivAreaHops
    		INTEGER,
    	    wfivAreaCircuitID
    		INTEGER,
    	    wfivAreaNextNode
    		DisplayString,
    	    wfivAreaRouteDynamic
    		INTEGER
        }

    wfivAreaNum OBJECT-TYPE
        SYNTAX	INTEGER
        ACCESS	read-only
        STATUS	mandatory
        DESCRIPTION
                "'This value indicates the area number of this entry.'"
        ::= { wfivAreaEntry 1 }

    wfivAreaState OBJECT-TYPE
        SYNTAX	INTEGER {
    		    reachable(4),
    		    unreachable(5)
    		}
        ACCESS	read-only
        STATUS	mandatory
        DESCRIPTION
                "'This value indicates the state of the area'"
        ::= { wfivAreaEntry 2 }

    wfivAreaCost OBJECT-TYPE
        SYNTAX	INTEGER
        ACCESS	read-only
        STATUS	mandatory
        DESCRIPTION
                "'The total cost over the current path to the
                destination area. Cost is a value associated with
                using a circuit. Routing routes messages (data)
                along the path between 2 areas with the smallest
                cost.'"
        ::= { wfivAreaEntry 3 }

    wfivAreaHops OBJECT-TYPE
        SYNTAX	INTEGER
        ACCESS	read-only
        STATUS	mandatory
        DESCRIPTION
                "'The number of hops to a destination area. A hop is
                the routing value representing the logical distance
                between two areas in network.'"
        ::= { wfivAreaEntry 4 }

    wfivAreaCircuitID OBJECT-TYPE
        SYNTAX	INTEGER
        ACCESS	read-only
        STATUS	mandatory
        DESCRIPTION
                "'The circuit used to get to the remote area'"
        ::= { wfivAreaEntry 5 }

    wfivAreaNextNode OBJECT-TYPE
        SYNTAX	DisplayString
        ACCESS	read-only
        STATUS	mandatory
        DESCRIPTION
                "'The next node on the circuit used to get to the
                area under scrutiny.'"
        ::= { wfivAreaEntry 6 }

    wfivAreaRouteDynamic OBJECT-TYPE
        SYNTAX	INTEGER {
    		    dynamic(1),
    		    static(2)
    		}
        ACCESS	read-write
        STATUS	mandatory
        DESCRIPTION
                "This READ_WRITE parameter will indicate the type of Level 2 route,
                whether it is a Dynamic or a Static route"
        ::= { wfivAreaEntry 7 }

    wfivAdjTable OBJECT-TYPE
        SYNTAX	SEQUENCE OF WfivAdjEntry
        ACCESS	not-accessible
        STATUS	mandatory
        DESCRIPTION
                "Adjacency Table"
        ::= { wfDecGroup 5 }

    wfivAdjEntry OBJECT-TYPE
        SYNTAX	WfivAdjEntry
        ACCESS	not-accessible
        STATUS	mandatory
        DESCRIPTION
                "' Adjacency Table - the real index is the adjacency index'"
        INDEX	{ wfivAdjIndex }
        ::= { wfivAdjTable 1 }

    WfivAdjEntry ::= SEQUENCE {
    	    wfivAdjIndex
    		INTEGER,
    	    wfivAdjNodeAddr
    		DisplayString,
    	    wfivAdjBlockSize
    		INTEGER,
    	    wfivAdjListenTimer
    		INTEGER,
    	    wfivAdjCircuitID
    		INTEGER,
    	    wfivAdjType
    		INTEGER,
    	    wfivAdjState
    		INTEGER,
    	    wfivAdjPriority
    		INTEGER,
    	    wfivAdjClass
    		INTEGER
        }

    wfivAdjIndex OBJECT-TYPE
        SYNTAX	INTEGER
        ACCESS	read-only
        STATUS	mandatory
        DESCRIPTION
                "'Index in the Adjacency Table'"
        ::= { wfivAdjEntry 1 }

    wfivAdjNodeAddr OBJECT-TYPE
        SYNTAX	DisplayString
        ACCESS	read-only
        STATUS	mandatory
        DESCRIPTION
                "'The address of the adjacent node.'"
        ::= { wfivAdjEntry 2 }

    wfivAdjBlockSize OBJECT-TYPE
        SYNTAX	INTEGER
        ACCESS	read-only
        STATUS	mandatory
        DESCRIPTION
                "'This READ_ONLY parameter is the block size that was
                negotiated with the adjacent Routing layer during Routing
                initialization over a particular circuit. It includes the
                routing header, but excludes the data link header. This
                parameter is qualified by ADJACENT NODE.'"
        ::= { wfivAdjEntry 3 }

    wfivAdjListenTimer OBJECT-TYPE
        SYNTAX	INTEGER
        ACCESS	read-only
        STATUS	mandatory
        DESCRIPTION
                "'This READ_ONLY value determines the maximum time allowed to
                elapse before Routing receives some message (either a Hello
                message or a user message) from the adjacent node on the
                circuit. It was agreed during Routing initialization with the
                adjacent Routing layer. Seconds is a decimal integer in the
                range 1-65535. This parameter is qualified by ADJACENT NODE.'"
        ::= { wfivAdjEntry 4 }

    wfivAdjCircuitID OBJECT-TYPE
        SYNTAX	INTEGER
        ACCESS	read-only
        STATUS	mandatory
        DESCRIPTION
                "'A unique value for each known circuit.'"
        ::= { wfivAdjEntry 5 }

    wfivAdjType OBJECT-TYPE
        SYNTAX	INTEGER
        ACCESS	read-only
        STATUS	mandatory
        DESCRIPTION
                "'This parameter indicates the type of adjacency.

                For adjacent nodes, this is a READ_ONLY parameter that
                indicates the type of the reachable adjacent node.
                NOTE: The ROUTING III and NONROUTING III values are
                incremented by one compared to the standard DECnet values in
                order to maintain compliance with RFC 1155)
                ROUTING III (1),
                NONROUTING III (2),
                AREA (3),
                ROUTING IV (4),
                NONROUTING IV (5)'"
        ::= { wfivAdjEntry 6 }

    wfivAdjState OBJECT-TYPE
        SYNTAX	INTEGER {
    		    init(1),
    		    up(2)
    		}
        ACCESS	read-only
        STATUS	mandatory
        DESCRIPTION
                "'This value indicates the state of a router adjacency.
                On adjacencies over a circuit of type (wfivCircuitCommonType)
                Ethernet, CI, or FDDI, with an adjacent node of type
                (wfivAdjType) ROUTING IV or AREA, this variable is the state
                of the Ethernet Initialization Layer for this adjacency, and
                can have values INITIALIZING or UP. (See Section 9.1.1 of
                DECnet Phase IV Routing Layer Functional Specification.)

                On adjacencies over a circuit of type (wfivCircuitCommonType)
                Ethernet, CI, or FDDI, with an adjacent node of type
                (wfivAdjType) NONROUTING IV, this varaible will always take on
                the value UP.

                On adjacencies over a circuit of type (wfivCircuitCommonType)
                DDCMP POINT, DDCMP CONTROL, DDCMP TRIBUTARY, DDCMP DMC, or
                X.25, this variable is the state of the Routing Layer
                Initialization Circuit State. (See section 7.3, ibid.) It can
                have values between RUN and HALT.

                On adjacencies over a circuit of type (wfivCircuitCommonType)
                OTHER, this variable may be used in a manner consistent with
                the Initialization Layer used on that circuit.
                INITIALIZING (1), -- Ethernet one-way
                UP (2), -- Ethernet two-way
                RUN (3), -- The eight DDCMP/X.25 states
                CIRCUIT REJECTED (4),
                DATA LINK START (5),
                ROUTING LAYER INITIALIZE (6),
                ROUTING LAYER VERIFY (7),
                ROUTING LAYER COMPLETE (8),
                OFF (9),
                HALT (10)'"
        ::= { wfivAdjEntry 7 }

    wfivAdjPriority OBJECT-TYPE
        SYNTAX	INTEGER
        ACCESS	read-only
        STATUS	mandatory
        DESCRIPTION
                "'Priority assigned by the adjacent node for this circuit.'"
        ::= { wfivAdjEntry 8 }

    wfivAdjClass OBJECT-TYPE
        SYNTAX	INTEGER
        ACCESS	read-only
        STATUS	mandatory
        DESCRIPTION
                "'Specifies whether this adjacency is Static or Dynamic'"
        ::= { wfivAdjEntry 9 }

    wfivTrafficFilterTable OBJECT-TYPE
        SYNTAX	SEQUENCE OF WfivTrafficFilterEntry
        ACCESS	not-accessible
        STATUS	mandatory
        DESCRIPTION
                "DECNET Traffic Filters"
        ::= { wfDecGroup 6 }

    wfivTrafficFilterEntry OBJECT-TYPE
        SYNTAX	WfivTrafficFilterEntry
        ACCESS	not-accessible
        STATUS	mandatory
        DESCRIPTION
                "An entry in WfivTrafficFilterTable."
        INDEX	{ wfivTrafficFilterCircuit,
    		  wfivTrafficFilterRuleNumber,
    		  wfivTrafficFilterFragment }
        ::= { wfivTrafficFilterTable 1 }

    WfivTrafficFilterEntry ::= SEQUENCE {
    	    wfivTrafficFilterCreate
    		INTEGER,
    	    wfivTrafficFilterEnable
    		INTEGER,
    	    wfivTrafficFilterStatus
    		INTEGER,
    	    wfivTrafficFilterCounter
    		Counter,
    	    wfivTrafficFilterDefinition
    		Opaque,
    	    wfivTrafficFilterReserved
    		INTEGER,
    	    wfivTrafficFilterCircuit
    		INTEGER,
    	    wfivTrafficFilterRuleNumber
    		INTEGER,
    	    wfivTrafficFilterFragment
    		INTEGER,
    	    wfivTrafficFilterName
    		DisplayString
        }

    wfivTrafficFilterCreate OBJECT-TYPE
        SYNTAX	INTEGER {
    		    created(1),
    		    deleted(2)
    		}
        ACCESS	read-write
        STATUS	mandatory
        DESCRIPTION
                "Defines the existence of the traffic filter rule:
                created - traffic filter exists
                delete - traffic filter does not exist and can be deleted."
        DEFVAL	{ created }
        ::= { wfivTrafficFilterEntry 1 }

    wfivTrafficFilterEnable OBJECT-TYPE
        SYNTAX	INTEGER {
    		    enabled(1),
    		    disabled(2)
    		}
        ACCESS	read-write
        STATUS	mandatory
        DESCRIPTION
                "Defines whether or not the traffic filter rule should be used:
                enabled - activate the rule.
                disabled - inactivate the rule."
        DEFVAL	{ enabled }
        ::= { wfivTrafficFilterEntry 2 }

    wfivTrafficFilterStatus OBJECT-TYPE
        SYNTAX	INTEGER {
    		    active(1),
    		    error(2),
    		    inactive(3)
    		}
        ACCESS	read-only
        STATUS	mandatory
        DESCRIPTION
                "Defines the current status of the traffic filter:
                inactive - the rule is not in use.
                active - the rule is being used.
                error - the application detected an error in the rule."
        DEFVAL	{ inactive }
        ::= { wfivTrafficFilterEntry 3 }

    wfivTrafficFilterCounter OBJECT-TYPE
        SYNTAX	Counter
        ACCESS	read-only
        STATUS	mandatory
        DESCRIPTION
                "The number of received packets that have
                matched this rule."
        ::= { wfivTrafficFilterEntry 4 }

    wfivTrafficFilterDefinition OBJECT-TYPE
        SYNTAX	Opaque
        ACCESS	read-write
        STATUS	mandatory
        DESCRIPTION
                "The filter rule definition."
        ::= { wfivTrafficFilterEntry 5 }

    wfivTrafficFilterReserved OBJECT-TYPE
        SYNTAX	INTEGER
        ACCESS	read-only
        STATUS	mandatory
        DESCRIPTION
                "Reserved field."
        ::= { wfivTrafficFilterEntry 6 }

    wfivTrafficFilterCircuit OBJECT-TYPE
        SYNTAX	INTEGER
        ACCESS	read-only
        STATUS	mandatory
        DESCRIPTION
                "The ID of the Circuit to which the
                filter is applied."
        ::= { wfivTrafficFilterEntry 7 }

    wfivTrafficFilterRuleNumber OBJECT-TYPE
        SYNTAX	INTEGER
        ACCESS	read-only
        STATUS	mandatory
        DESCRIPTION
                "ID for the rule."
        ::= { wfivTrafficFilterEntry 8 }

    wfivTrafficFilterFragment OBJECT-TYPE
        SYNTAX	INTEGER
        ACCESS	read-only
        STATUS	mandatory
        DESCRIPTION
                "Fragment number - for large rules."
        ::= { wfivTrafficFilterEntry 9 }

    wfivTrafficFilterName OBJECT-TYPE
        SYNTAX	DisplayString
        ACCESS	read-write
        STATUS	mandatory
        DESCRIPTION
                "name of the rule number"
        ::= { wfivTrafficFilterEntry 10 }

    wfivStaticAdjTable OBJECT-TYPE
        SYNTAX	SEQUENCE OF WfivStaticAdjEntry
        ACCESS	not-accessible
        STATUS	mandatory
        DESCRIPTION
                "Static Adjacency Table"
        ::= { wfDecGroup 7 }

    wfivStaticAdjEntry OBJECT-TYPE
        SYNTAX	WfivStaticAdjEntry
        ACCESS	not-accessible
        STATUS	mandatory
        DESCRIPTION
                "' Static Adjacency Table '"
        INDEX	{ wfivStaticAdjCircuitID,
    		  wfivStaticAdjArea,
    		  wfivStaticAdjNodeid }
        ::= { wfivStaticAdjTable 1 }

    WfivStaticAdjEntry ::= SEQUENCE {
    	    wfivStaticAdjCreateDelete
    		INTEGER,
    	    wfivStaticAdjEnableDisable
    		INTEGER,
    	    wfivStaticAdjArea
    		INTEGER,
    	    wfivStaticAdjNodeid
    		INTEGER,
    	    wfivStaticAdjCircuitID
    		INTEGER,
    	    wfivStaticAdjNodeAddr
    		DisplayString,
    	    wfivStaticAdjType
    		INTEGER,
    	    wfivStaticAdjPriority
    		INTEGER,
    	    wfivStaticAdjDestMACAddr
    		OCTET STRING
        }

    wfivStaticAdjCreateDelete OBJECT-TYPE
        SYNTAX	INTEGER {
    		    create(1),
    		    delete(2)
    		}
        ACCESS	read-write
        STATUS	mandatory
        DESCRIPTION
                "'This value determines whether the static adjacency is configured'"
        DEFVAL	{ create }
        ::= { wfivStaticAdjEntry 1 }

    wfivStaticAdjEnableDisable OBJECT-TYPE
        SYNTAX	INTEGER {
    		    enable(1),
    		    disable(2)
    		}
        ACCESS	read-write
        STATUS	mandatory
        DESCRIPTION
                "'This value determines whether the static adjacency is active '"
        DEFVAL	{ enable }
        ::= { wfivStaticAdjEntry 2 }

    wfivStaticAdjArea OBJECT-TYPE
        SYNTAX	INTEGER
        ACCESS	read-only
        STATUS	mandatory
        DESCRIPTION
                "'DECnet Phase IV area number for this static Adjacency.'"
        ::= { wfivStaticAdjEntry 3 }

    wfivStaticAdjNodeid OBJECT-TYPE
        SYNTAX	INTEGER
        ACCESS	read-only
        STATUS	mandatory
        DESCRIPTION
                "'DECnet Phase IV node address for this static adjacency.'"
        ::= { wfivStaticAdjEntry 4 }

    wfivStaticAdjCircuitID OBJECT-TYPE
        SYNTAX	INTEGER
        ACCESS	read-only
        STATUS	mandatory
        DESCRIPTION
                "'The circuit used for this static adjacency.'"
        ::= { wfivStaticAdjEntry 5 }

    wfivStaticAdjNodeAddr OBJECT-TYPE
        SYNTAX	DisplayString
        ACCESS	read-only
        STATUS	mandatory
        DESCRIPTION
                "'The address of the adjacent node in display format.'"
        ::= { wfivStaticAdjEntry 6 }

    wfivStaticAdjType OBJECT-TYPE
        SYNTAX	INTEGER {
    		    area(3),
    		    routingiv(4),
    		    nonroutingiv(5)
    		}
        ACCESS	read-write
        STATUS	mandatory
        DESCRIPTION
                "' Specifies whether the static adjacency is to a router or end
                station.'"
        DEFVAL	{ area }
        ::= { wfivStaticAdjEntry 7 }

    wfivStaticAdjPriority OBJECT-TYPE
        SYNTAX	INTEGER
        ACCESS	read-write
        STATUS	mandatory
        DESCRIPTION
                "' Specifies the priority of the static adjacency if it's a
                router.'"
        ::= { wfivStaticAdjEntry 8 }

    wfivStaticAdjDestMACAddr OBJECT-TYPE
        SYNTAX	OCTET STRING
        ACCESS	read-write
        STATUS	mandatory
        DESCRIPTION
                "' Specifies the destination MAC address of the Static Adjacency
                if the circuit type is ATM, Frame Relay or SMDS.'"
        ::= { wfivStaticAdjEntry 9 }

    wfivStaticRouteTable OBJECT-TYPE
        SYNTAX	SEQUENCE OF WfivStaticRouteEntry
        ACCESS	not-accessible
        STATUS	mandatory
        DESCRIPTION
                "This table contains the list of all static routes"
        ::= { wfDecGroup 8 }

    wfivStaticRouteEntry OBJECT-TYPE
        SYNTAX	WfivStaticRouteEntry
        ACCESS	not-accessible
        STATUS	mandatory
        DESCRIPTION
                "This is the Static Route Entry for the Static Route Table"
        INDEX	{ wfivStaticRouteAreaId,
    		  wfivStaticRouteNodeId,
    		  wfivStaticRouteNextHopAreaId,
    		  wfivStaticRouteNextHopNodeId }
        ::= { wfivStaticRouteTable 1 }

    WfivStaticRouteEntry ::= SEQUENCE {
    	    wfivStaticRouteDelete
    		INTEGER,
    	    wfivStaticRouteDisable
    		INTEGER,
    	    wfivStaticRouteType
    		INTEGER,
    	    wfivStaticRouteAreaId
    		INTEGER,
    	    wfivStaticRouteNodeId
    		INTEGER,
    	    wfivStaticRouteCost
    		INTEGER,
    	    wfivStaticRouteNextHopAreaId
    		INTEGER,
    	    wfivStaticRouteNextHopNodeId
    		INTEGER
        }

    wfivStaticRouteDelete OBJECT-TYPE
        SYNTAX	INTEGER {
    		    created(1),
    		    deleted(2)
    		}
        ACCESS	read-write
        STATUS	mandatory
        DESCRIPTION
                "Create/Delete parameter for DECnet IV Static Route Record"
        DEFVAL	{ created }
        ::= { wfivStaticRouteEntry 1 }

    wfivStaticRouteDisable OBJECT-TYPE
        SYNTAX	INTEGER {
    		    enabled(1),
    		    disabled(2)
    		}
        ACCESS	read-write
        STATUS	mandatory
        DESCRIPTION
                "Enable/Disable parameter for this Static Route"
        DEFVAL	{ enabled }
        ::= { wfivStaticRouteEntry 2 }

    wfivStaticRouteType OBJECT-TYPE
        SYNTAX	INTEGER {
    		    l1(1),
    		    l2(2)
    		}
        ACCESS	read-write
        STATUS	mandatory
        DESCRIPTION
                "This parameter specifies whether this static route is for Level 1 or Level 2
                type of routing"
        DEFVAL	{ l2 }
        ::= { wfivStaticRouteEntry 3 }

    wfivStaticRouteAreaId OBJECT-TYPE
        SYNTAX	INTEGER
        ACCESS	read-only
        STATUS	mandatory
        DESCRIPTION
                "This specifies the area address of the static route. It is also a part of
                the inst_id"
        ::= { wfivStaticRouteEntry 4 }

    wfivStaticRouteNodeId OBJECT-TYPE
        SYNTAX	INTEGER
        ACCESS	read-only
        STATUS	mandatory
        DESCRIPTION
                "This specifies the node address of the static route. It is also a part of
                the inst_id"
        ::= { wfivStaticRouteEntry 5 }

    wfivStaticRouteCost OBJECT-TYPE
        SYNTAX	INTEGER(1..63)
        ACCESS	read-write
        STATUS	mandatory
        DESCRIPTION
                "This value is the cost to get to this address"
        DEFVAL	{ 10 }
        ::= { wfivStaticRouteEntry 6 }

    wfivStaticRouteNextHopAreaId OBJECT-TYPE
        SYNTAX	INTEGER
        ACCESS	read-only
        STATUS	mandatory
        DESCRIPTION
                "This is the area address of the next hop router that all data destined to
                wfivStaticRouteAreaId will be forwarded to"
        ::= { wfivStaticRouteEntry 7 }

    wfivStaticRouteNextHopNodeId OBJECT-TYPE
        SYNTAX	INTEGER
        ACCESS	read-only
        STATUS	mandatory
        DESCRIPTION
                "This is the node address of the next hop router that all data destined to
                wfivStaticRouteAddr will be forwarded to"
        ::= { wfivStaticRouteEntry 8 }

    wfivDecnetTrans	OBJECT IDENTIFIER ::= { wfDecGroup 9 }

    wfivDecnetTransPhase5Pkts OBJECT-TYPE
        SYNTAX	Counter
        ACCESS	read-only
        STATUS	mandatory
        DESCRIPTION
                "Number of successfully translated Phase 5 (CLNP) packets"
        ::= { wfivDecnetTrans 1 }

    wfivDecnetTransMtuFail OBJECT-TYPE
        SYNTAX	Counter
        ACCESS	read-only
        STATUS	mandatory
        DESCRIPTION
                "Number of times Phase 5 translation failed because the packet
                was larger than the Phase 4 MTU size."
        ::= { wfivDecnetTrans 2 }

    wfivDecnetTransUnrFail OBJECT-TYPE
        SYNTAX	Counter
        ACCESS	read-only
        STATUS	mandatory
        DESCRIPTION
                "Number of times Phase 4 failed to find a route to the
                destination."
        ::= { wfivDecnetTrans 3 }

    wfivDecnetTransNumPhase5Es OBJECT-TYPE
        SYNTAX	Counter
        ACCESS	read-only
        STATUS	mandatory
        DESCRIPTION
                "Number of Phase 5 ES Adjacencies announced by the Phase 5
                (OSI) router."
        ::= { wfivDecnetTrans 4 }

    wfivAggrStats	OBJECT IDENTIFIER ::= { wfDecGroup 10 }

    wfivAggrInPkts OBJECT-TYPE
        SYNTAX	Counter
        ACCESS	read-only
        STATUS	mandatory
        DESCRIPTION
                "The total number of packets received by the DECnet re-director"
        ::= { wfivAggrStats 1 }

    wfivAggrOutPkts OBJECT-TYPE
        SYNTAX	Counter
        ACCESS	read-only
        STATUS	mandatory
        DESCRIPTION
                "The total number of packets sent by the DECnet re-director"
        ::= { wfivAggrStats 2 }

    wfivAggrFormatErrs OBJECT-TYPE
        SYNTAX	Counter
        ACCESS	read-only
        STATUS	mandatory
        DESCRIPTION
                "The total number of packets received with format errors"
        ::= { wfivAggrStats 3 }

    wfivAggrDestUnreachables OBJECT-TYPE
        SYNTAX	Counter
        ACCESS	read-only
        STATUS	mandatory
        DESCRIPTION
                "The total number of packets received whose destinations
                were unreachable"
        ::= { wfivAggrStats 4 }

    wfivAggrRangeErrs OBJECT-TYPE
        SYNTAX	Counter
        ACCESS	read-only
        STATUS	mandatory
        DESCRIPTION
                "The total number of packet received with nodes out of range"
        ::= { wfivAggrStats 5 }

    wfivAggrOversizedPkts OBJECT-TYPE
        SYNTAX	Counter
        ACCESS	read-only
        STATUS	mandatory
        DESCRIPTION
                "The total number of oversized packets received."
        ::= { wfivAggrStats 6 }

    wfivAggrAgedPkts OBJECT-TYPE
        SYNTAX	Counter
        ACCESS	read-only
        STATUS	mandatory
        DESCRIPTION
                "The total number of packets aged out"
        ::= { wfivAggrStats 7 }

    wfivAggrFwdPkts OBJECT-TYPE
        SYNTAX	Counter
        ACCESS	read-only
        STATUS	mandatory
        DESCRIPTION
                "The total number of packets forwarded"
        ::= { wfivAggrStats 8 }

    END  -- Wellfleet-DECNET-MIB
