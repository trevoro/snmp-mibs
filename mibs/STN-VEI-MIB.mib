-- *****************************************************************
--
-- stn-vei.mib:  
--      Spring Tide Networks Network Virtual Ethernet Interface 
--                         (VEI) MIB File
--
--
--      Copyright (c) 2000 by Spring Tide Networks, Inc.
--                      ALL RIGHTS RESERVED       
--
-- *****************************************************************

-- MIB Object definitions for Spring Tide VEI

STN-VEI-MIB DEFINITIONS ::= BEGIN

    IMPORTS
        MODULE-IDENTITY,
        OBJECT-TYPE, 
        IpAddress,
        Counter32, 
        Gauge32,
        Integer32
                FROM SNMPv2-SMI

        DisplayString
                FROM SNMPv2-TC

        MODULE-COMPLIANCE
                FROM SNMPv2-CONF

        PhysAddress
                FROM RFC1213-MIB

        InterfaceIndex
                FROM IF-MIB

        stnRouterVEI
                FROM STN-ROUTER-MIB

        stnNotification
                FROM SPRING-TIDE-NETWORKS-SMI;


    stnVei MODULE-IDENTITY
        LAST-UPDATED    "0004060000Z"
        ORGANIZATION    "Spring Tide Networks"
        CONTACT-INFO
                "
                Spring Tide Networks, Inc.
                Customer Service

                Postal: 3 Clock Tower Place
                        Suite 200
                        Maynard, MA 01754 USA
                Tel:    +1 978 298 2000
                Email:  custserv@springtidenet.com
                "
        DESCRIPTION     "This MIB module describes managed objects of
                         Spring Tide Networks Virtual Ethernet Interface."
        ::= { stnRouterVEI 1 }


--
-- Top Level STN VEI MIB Objects
--

    stnVeiObjects       OBJECT IDENTIFIER ::= {stnVei 1}
    
--
-- STN VEI Layer 2 Table  
--   One entry for each VEI defined in the system.
--
    stnVeiL2Table OBJECT-TYPE
        SYNTAX		SEQUENCE OF StnVeiL2Entry
        MAX-ACCESS	not-accessible
        STATUS		current
        DESCRIPTION	"A list of VEI L2 entries."
        ::= { stnVeiObjects 1 }
 
    stnVeiL2Entry OBJECT-TYPE
        SYNTAX          StnVeiL2Entry
        MAX-ACCESS      not-accessible
        STATUS          current
        DESCRIPTION     "Entry contains information about a particular VEI L2."
        INDEX           { stnVeiL2IfIndex }
        ::= { stnVeiL2Table 1 }
 
    StnVeiL2Entry ::= SEQUENCE {
        stnVeiL2IfIndex                     InterfaceIndex,
        stnVeiL2ViId                        Integer32,
        stnVeiL2Name                        DisplayString,
        stnVeiL2Type                        INTEGER,
        stnVeiL2MacTtl                      Gauge32,
        stnVeiL2State                       INTEGER,              
        stnVeiL2RegisteredLowerLinks        Gauge32,
        stnVeiL2ActiveLowerLinks            Gauge32,
        stnVeiL2NoFreeEndStations           Counter32,
        stnVeiL2TxDestNotFound              Counter32,
        stnVeiL2TxArpRspDropNoEndStation    Counter32,
        stnVeiL2ActiveMultiCasts            Counter32,
        stnVeiL2MultiCastsDrop              Counter32
    }

    stnVeiL2IfIndex OBJECT-TYPE
        SYNTAX          InterfaceIndex
        MAX-ACCESS      read-only
        STATUS          current
        DESCRIPTION     "The ifIndex of the VEI Layer 2 Interface."
        ::= { stnVeiL2Entry 1 }

    stnVeiL2ViId OBJECT-TYPE
        SYNTAX          Integer32
        MAX-ACCESS      read-only
        STATUS          current
        DESCRIPTION     "The instance of the configuration record 
                         corresponding to this VEI."
        ::= { stnVeiL2Entry 2 }

    stnVeiL2Name OBJECT-TYPE
        SYNTAX          DisplayString (SIZE (1..32))
        MAX-ACCESS      read-only
        STATUS          current
        DESCRIPTION     "The name configured for this VEI."
        ::= { stnVeiL2Entry 3 }

    stnVeiL2Type OBJECT-TYPE
        SYNTAX          INTEGER {
                            atmBridgeEnetV2(1),
                            atmBridgeEnet8023(2)
                        }
        MAX-ACCESS      read-only
        STATUS          current
        DESCRIPTION     "The type of virtual ethernet interface.  
                        An atmBridgeEnetV2 VEI implements Ethernet V2 
                        PDUs encapsulated per RFC1483 over ATM AAL5. An
                        atmBridgeEnetV2 VEI implements Ethernet 802.3
                        PDUs encapsulated per RFC1483 over ATM AAL5."
        ::= { stnVeiL2Entry 4 }

    stnVeiL2MacTtl OBJECT-TYPE
        SYNTAX          Gauge32
        MAX-ACCESS      read-only
        STATUS          current
        DESCRIPTION     "The approximate time, in seconds, that a learned MAC 
			            address will be considered in-use by the VcLink it 
			            originated on.  Once this time has expired, the 
			            resources associated with the MAC database entry can 
			            be reclaimed for learning other MAC addresses if 
			necessary."
        ::= { stnVeiL2Entry 5 }

    stnVeiL2State OBJECT-TYPE
        SYNTAX          INTEGER {
                          up(1),       -- ready to pass packets
                          down(2),
                          testing(3)   -- in some test mode
                        }
        MAX-ACCESS      read-only
        STATUS          current
        DESCRIPTION     "The current operational state of the VEI."
        ::= { stnVeiL2Entry 6 }

    stnVeiL2RegisteredLowerLinks OBJECT-TYPE
        SYNTAX          Gauge32
        MAX-ACCESS      read-only
        STATUS          current
        DESCRIPTION     "The current number of VCLinks registered with the VEI."
        ::= { stnVeiL2Entry 7 }

    stnVeiL2ActiveLowerLinks OBJECT-TYPE
        SYNTAX          Gauge32
        MAX-ACCESS      read-only
        STATUS          current
        DESCRIPTION     "The current number of VCLinks actively carrying 
			            traffic for this VEI."
        ::= { stnVeiL2Entry 8 }

    stnVeiL2NoFreeEndStations OBJECT-TYPE
        SYNTAX          Counter32
        MAX-ACCESS      read-only
        STATUS          current
        DESCRIPTION     "The number of times that the VEI ran out of MAC 
			            address database entries when attempting to learn a 
			            new remote MAC address.  This indicates that the total 
			            number of remote MACs allowed on the VEI is greater 
			            than the system limit of 4096 per VEI."
        ::= { stnVeiL2Entry 9 }

    stnVeiL2TxDestNotFound OBJECT-TYPE
        SYNTAX          Counter32
        MAX-ACCESS      read-only
        STATUS          current
        DESCRIPTION     "The number of outgoing packets that were dropped 
			            because the VEI could not find a MAC address database
		                entry for the destination MAC address.  This indicates 
			            that the VEI has not learned the destination MAC 
			            address."
        ::= { stnVeiL2Entry 10 }

    stnVeiL2TxArpRspDropNoEndStation OBJECT-TYPE
        SYNTAX          Counter32
        MAX-ACCESS      read-only
        STATUS          current
        DESCRIPTION     "The number of outgoing ARP response packets dropped 
			            by the VEI because either the ARP's sending or target
		                MAC address is not in the MAC address database."
        ::= { stnVeiL2Entry 11 }

    stnVeiL2ActiveMultiCasts OBJECT-TYPE
        SYNTAX          Counter32
        MAX-ACCESS      read-only
        STATUS          current
        DESCRIPTION     "The current number of mulicast/broadcast transmit 
			            packets that the VEI is propagating across all active
		                VCLinks."
        ::= { stnVeiL2Entry 12 }

    stnVeiL2MultiCastsDrop OBJECT-TYPE
        SYNTAX          Counter32
        MAX-ACCESS      read-only
        STATUS          current
        DESCRIPTION     "The number of multicast/broadcast transmit packets 
			            that the VEI dropped due to resource limitations."
        ::= { stnVeiL2Entry 13 }


--
-- STN VEI Link Table  
--   One entry for each lower VcLink per VEI L2
--

    stnVeiLinkTable OBJECT-TYPE
        SYNTAX		SEQUENCE OF StnVeiLinkEntry
        MAX-ACCESS	not-accessible
        STATUS		current
        DESCRIPTION	"A list of the links configured for a VEI."
        ::= { stnVeiObjects 2 }
 
    stnVeiLinkEntry OBJECT-TYPE
        SYNTAX          StnVeiLinkEntry
        MAX-ACCESS      not-accessible
        STATUS          current
        DESCRIPTION     "Entry contains information about a particular VEI L2."
        INDEX           { stnVeiLinkVeiIfIndex, stnVeiLinkIfIndex }
        ::= { stnVeiLinkTable 1 }
 
    StnVeiLinkEntry ::= SEQUENCE {
        stnVeiLinkVeiIfIndex              InterfaceIndex,
        stnVeiLinkIfIndex                 InterfaceIndex,
        stnVeiLinkMaxEndStations          Gauge32,
        stnVeiLinkCurrentEndStations      Gauge32,
        stnVeiLinkLearnFailures           Counter32,
        stnVeiLinkMacRecycledLocal        Counter32,
        stnVeiLinkMacRecycledGlobal       Counter32,
        stnVeiLinkArpRspDropSameIface     Counter32,
        stnVeiLinkEndStationMoved         Counter32,
        stnVeiLinkPhysIfIndex             InterfaceIndex,
        stnVeiLinkVpi                     Integer32,
        stnVeiLinkVci                     Integer32
    }
    
    stnVeiLinkVeiIfIndex OBJECT-TYPE
        SYNTAX          InterfaceIndex
        MAX-ACCESS      read-only
        STATUS          current
        DESCRIPTION     "The IfIndex of the VEI for which this VcLink is 
			             configured."
        ::= { stnVeiLinkEntry 1 }

    stnVeiLinkIfIndex OBJECT-TYPE
        SYNTAX          InterfaceIndex
        MAX-ACCESS      read-only
        STATUS          current
        DESCRIPTION     "The IfIndex of this VcLink."
        ::= { stnVeiLinkEntry 2 }

    stnVeiLinkMaxEndStations OBJECT-TYPE
        SYNTAX          Gauge32
        MAX-ACCESS      read-only
        STATUS          current
        DESCRIPTION     "The maximum number of MAC address database entries 
			             that this VcLink service.  This limits the number of
		                 active endstations supported via this link."
        ::= { stnVeiLinkEntry 3 }

    stnVeiLinkCurrentEndStations OBJECT-TYPE
        SYNTAX          Gauge32
        MAX-ACCESS      read-only
        STATUS          current
        DESCRIPTION     "The current number of MAC address database entries in
			             use by this VcLink."
        ::= { stnVeiLinkEntry 4 }

    stnVeiLinkLearnFailures OBJECT-TYPE
        SYNTAX          Counter32
        MAX-ACCESS      read-only
        STATUS          current
        DESCRIPTION     "The number of receive packets discarded because the 
			             source MAC address did not appear in the MAC address 
			             database and could not be added (learned) due to 
			             resource limitations."
        ::= { stnVeiLinkEntry 5 }

    stnVeiLinkMacRecycledLocal OBJECT-TYPE
        SYNTAX          Counter32
        MAX-ACCESS      read-only
        STATUS          current
        DESCRIPTION     "The number of times a MAC address entry was reused to
			            learn a new MAC address on the same link.  The 
			            original MAC address is discarded on this event.  This 
			            occurs only when no traffic has been seen from the 
			            endstation corresponding to the MAC address entry 
			            after approximately stnVeiL2MacTtl seconds, and a new 
			            MAC address must be learned (added to the database) 
			            for this link.  This recycle only occurs if the VcLink 
			            is at its endstation limit (stnVeiLinkMaxEndStations) 
			            or a new MAC address database object cannot be 
			            allocated due to system resource limits."
        ::= { stnVeiLinkEntry 6 }

    stnVeiLinkMacRecycledGlobal OBJECT-TYPE
        SYNTAX          Counter32
        MAX-ACCESS      read-only
        STATUS          current
        DESCRIPTION     "The number of times a MAC address entry was removed 
			            from this link and reused by a different VcLink to
		                    learn a new MAC address.  This can only occur when:
			                1) no traffic has been seen from the endstation
			                   corresponding to the MAC address entry for 
			                   approximately twice stnVeiL2MacTtl seconds, AND
			                2) the total number of MAC address entries
			                   (stnVeiLinkMaxEndStations) for all VcLinks 
			                   under the VEI is greater than the per-VEI 
                               system limit (4096), AND
                            3) there are no free MAC address entries available.
			
			            When these conditions are true, then the VEI has been
		                    overprovisioned with respect to the number of MAC 
			            address entries. Recycling entries across VcLinks 
			            allow those VcLinks under high demand claim MAC 
			            address entries from VcLinks experiencing less activity."
        ::= { stnVeiLinkEntry 7 }

    stnVeiLinkArpRspDropSameIface OBJECT-TYPE
        SYNTAX          Counter32
        MAX-ACCESS      read-only
        STATUS          current
        DESCRIPTION     "The number of outgoing ARP Response packets that 
			            could be discarded because the target and source MAC
		                Addresses reside on the same VcLink.  In this case, no
			            ARP Proxy support is needed, and the packet can safely
			            be discarded."
        ::= { stnVeiLinkEntry 8 }

    stnVeiLinkEndStationMoved OBJECT-TYPE
        SYNTAX          Counter32
        MAX-ACCESS      read-only
        STATUS          current
        DESCRIPTION     "The number of times the VEI detected that a remote 
			            MAC address moved from this link and appeared on 
			            another."
        ::= { stnVeiLinkEntry 9 }

    stnVeiLinkPhysIfIndex OBJECT-TYPE
        SYNTAX          InterfaceIndex
        MAX-ACCESS      read-only
        STATUS          current
        DESCRIPTION     "The physical interface index represents the port and line card
                         used by this link. It is calculated based on the slot and 
                         port of the module."
        ::= { stnVeiLinkEntry 10 }

    stnVeiLinkVpi OBJECT-TYPE     
        SYNTAX          Integer32 
        MAX-ACCESS      read-only
        STATUS          current
        DESCRIPTION     "The VPI value of the PVC represented by this link."
        ::= { stnVeiLinkEntry 11 }

    stnVeiLinkVci OBJECT-TYPE     
        SYNTAX          Integer32 
        MAX-ACCESS      read-only
        STATUS          current
        DESCRIPTION     "The VCI value of the PVC represented by this link." 
        ::= { stnVeiLinkEntry 12 }

--
-- STN VEI Link MAC Table  
--   One entry for each Remote MAC address learned by a VEI's VcLink.
--

    stnVeiLinkMacTable OBJECT-TYPE
        SYNTAX		SEQUENCE OF StnVeiLinkMacEntry
        MAX-ACCESS	not-accessible
        STATUS		current
        DESCRIPTION	"A list of the remote MACs learned by a VEI VcLink."
        ::= { stnVeiObjects 3 }
 
    stnVeiLinkMacEntry OBJECT-TYPE
        SYNTAX          StnVeiLinkMacEntry
        MAX-ACCESS      not-accessible
        STATUS          current
        DESCRIPTION     "Entry contains information about a particular remote 
			            MAC learned on a VEI VcLink."
        INDEX           { stnVeiLinkMacVeiIfIndex, 
                          stnVeiLinkMacLinkIfIndex,
                          stnVeiLinkMacAddress }
        ::= { stnVeiLinkMacTable 1 }
 
    StnVeiLinkMacEntry ::= SEQUENCE {
        stnVeiLinkMacVeiIfIndex     InterfaceIndex,
        stnVeiLinkMacLinkIfIndex    InterfaceIndex,
        stnVeiLinkMacAddress        PhysAddress,
        stnVeiLinkMacAge            Gauge32,
        stnVeiLinkMacType           INTEGER 
    }

    stnVeiLinkMacVeiIfIndex OBJECT-TYPE
        SYNTAX          InterfaceIndex
        MAX-ACCESS      read-only
        STATUS          current
        DESCRIPTION     "The IfIndex of the VEI for the VcLink which owns the 
			            MAC database entry."
        ::= { stnVeiLinkMacEntry 1 }

    stnVeiLinkMacLinkIfIndex OBJECT-TYPE
        SYNTAX          InterfaceIndex
        MAX-ACCESS      read-only
        STATUS          current
        DESCRIPTION     "The IfIndex of the VcLink which owns the MAC database
			            entry."
        ::= { stnVeiLinkMacEntry 2 }

    stnVeiLinkMacAddress OBJECT-TYPE
        SYNTAX          PhysAddress
        MAX-ACCESS      read-only
        STATUS          current
        DESCRIPTION     "The MAC address of the remote endstation for which 
			            this database entry corresponds to."
        ::= { stnVeiLinkMacEntry 3 }

    stnVeiLinkMacAge OBJECT-TYPE
        SYNTAX          Gauge32
        MAX-ACCESS      read-only
        STATUS          current
        DESCRIPTION     "The approximate number of time periods that have 
			            passed since packets were received from the endstation
		                corresponding to this entry.  Each time period is
		                approximately one-half the value of stnVeiL2MacTtl for
			            this VEI. The current maximum for this value is 4.  If
			            the entry is statically configured, this value will 
			            always be zero."
        ::= { stnVeiLinkMacEntry 4 }

    stnVeiLinkMacType OBJECT-TYPE
        SYNTAX          INTEGER {
                            veiLinkMacLearned(1),
                            veiLinkMacStatic(2)
                        }
        MAX-ACCESS      read-only
        STATUS          current
        DESCRIPTION     "Indicates the type of MAC database entry. 
			            veiLinkMacLearned indicates that the entry was 
			            dynamically learned from the incoming packet flow.  
			            veiLinkMacStatic indicates that the entry is 
			            statically configured and will never age out."
        ::= { stnVeiLinkMacEntry 5 }

END
