----------------------------------------------------------------------------
-- MIB DEFINITION MODULE: GC555_OP GRETACODER 555 Enterprise MIB for Network Operators
--                  FILE: GC555_OP.MIB
------------------------------------------------------------------------------
-- COPYRIGHT (C) 1997 GRETACODER Data Systems AG, CH-8105 Regensdorf,
--                    Switzerland
-- This MIB file is to be used with GRETACODER 555 SW Version 2.1 or greater
--
-- Reproduction of this document is authorized on condition
-- that this copyright notice is included.
-- This GRETACODER Data Systems AG SNMP Management Information Base
-- Specification embodies GRETACODER Data Systems`s proprietary
-- intellectual property. GRETACODER Data Systems AG retains
-- all title and ownership in the Specification, including any
-- revisions.
--
-- This Specification is supplied "AS IS," and GRETACODER Data Systems AG
-- makes no warranty, either expressed or implied, as to the use,
-- operation, condition, or performance of the Specification.
-- This Specification will be expanded for future versions of the GRETACODER 555.
---
-- PREFIX:
-- SCCS:            Provisional Release V1.8p
--
------------------------------------------------------------------------------
-- HISTORY (DATE, NAME, CHANGES):
-- LAST CHANGED  WHO       WHAT
-- 970409        KPS       Pre-Release for GC555 Version 2.0 P5
-- 970410        KPS       Name of front panel lead changed
-- 970417        KPS       Cosmetic baud rate factor of 10 too high
-- 970421        KPS       Corrections for SMICNG compiler (except Unitstates)
-- 970507        KPS       Cosmetic & Frame relay Layer 2 MTU given discrete values
-- 970513        KPS       Corrections to FR Layer 1 T1 pulse forms and cosmetic
-- 970526/27/28  KPS       Cosmetic and release for V2.1
-- 970620        KPS       Cosmetic and release 1.6 for GC555 SW V2.1
-- 970625        KPS       Cosmetic error with comments for HP Openview compiler (Die Post)
-- 970918        kps       Change _ to - for WEISS compiler
-- 980324        KPS       Experimental:
--                         Application Configuration group added for cipher list

-- ORGANIZATION "GRETACODER Data Systems AG"
-- CONTACT-INFO
--              "GDS Customer Service
--               Postal: GRETACODER Data Systems AG
--                       Althardstrasse 150
--                       CH-8105 Regensdorf
--                       Switzerland
--
--               Tel:    +41 (0)1-871-11-23
--               Fax:    +41 (0)1-871-11-01
--               E-mail: mailgds@gds.ch"
--
--      DESCRIPTION
--               "The Network Operator Enterprise MIB for the GDS GRETACODER 555"
--      REVISION "June 1997"
--


------------------------------------------------------------------------------

	GDSFrameRelay-MIB DEFINITIONS ::= BEGIN

	IMPORTS
		enterprises, Counter, IpAddress
			FROM RFC1155-SMI
		DisplayString
			FROM RFC1213-MIB
		OBJECT-TYPE
			FROM RFC-1212;

		gds        OBJECT IDENTIFIER ::= { enterprises 1955 }
		seriesfr   OBJECT IDENTIFIER ::= { gds 5 }
		is-GDS-frame-relay-device5    OBJECT IDENTIFIER ::= { seriesfr 5 }

-- groups for the GRETACODER 555 and related devices MIB

		unit            OBJECT IDENTIFIER ::= { is-GDS-frame-relay-device5 1 }
		frame-relay     OBJECT IDENTIFIER ::= { is-GDS-frame-relay-device5 2 }
		configure       OBJECT IDENTIFIER ::= { is-GDS-frame-relay-device5 3 }

--------------------------------------------------------------------------------------

--  Unit group

	uVersion-Strings     OBJECT IDENTIFIER ::= { unit 1 }

	uMain-HW-Version OBJECT-TYPE
		SYNTAX DisplayString (SIZE (0..16))
		ACCESS read-only
		STATUS mandatory
		DESCRIPTION
			"The frame relay encryptor mainboard HW version."
		::= { uVersion-Strings 1 }

	uComm-HW-Version OBJECT-TYPE
		SYNTAX DisplayString (SIZE (0..16))
		ACCESS read-only
		STATUS mandatory
		DESCRIPTION
			"The frame relay encryptor commsboard HW version."
		::= { uVersion-Strings 2 }


	uMain-SW-Version OBJECT-TYPE
		SYNTAX DisplayString (SIZE (0..16))
		ACCESS read-only
		STATUS mandatory
		DESCRIPTION
			"The frame relay encryptor mainboard SW version.
			 Every effort will be made by GDS to make
			 the MIB backwards compatible to the frame relay
			 encryptor software. In case of doubt or queries
			 please quote the following release number.
			 Enterprise MIB Version Release V1.8p "
		::= { uVersion-Strings 3 }


	uComm-SW-Version OBJECT-TYPE
		SYNTAX DisplayString (SIZE (0..16))
		ACCESS read-only
		STATUS mandatory
		DESCRIPTION
			"The frame relay encryptor comms board SW version."
		::= { uVersion-Strings 4 }

	uAlgorithm OBJECT-TYPE
		SYNTAX DisplayString (SIZE (0..16))
		ACCESS read-only
		STATUS mandatory
		DESCRIPTION
			"The frame relay encryptor encryption algorithm DES or GDS."
		::= { uVersion-Strings 5 }

	uAccess-Table OBJECT-TYPE
		SYNTAX DisplayString (SIZE (0..16))
		ACCESS read-only
		STATUS mandatory
		DESCRIPTION
			"The frame relay encryptor access control table version."
		::= { uVersion-Strings 6 }


	uConfigured     OBJECT IDENTIFIER ::= { unit 2 }

	uOwn-SID OBJECT-TYPE
		SYNTAX INTEGER (0..65535)
		ACCESS read-only
		STATUS mandatory
		DESCRIPTION
			"The Station Identity of this frame relay encryptor ."
		::= { uConfigured 1 }

--       uClear-Bypass OBJECT-TYPE
--                SYNTAX INTEGER {
--                       disabled(1),
--                       enabled(2)
--                       }
--                ACCESS read-only
--                STATUS mandatory
--                DESCRIPTION
--                        "Whether SNMP messages received on the cipher port are
--                         allowed to pass through the frame relay encryptor  as clear text even
--                         if all other traffic has to be encrypted. Future use"
--                ::= { uConfigured 2 }


	uDynamic    OBJECT IDENTIFIER ::= { unit 3 }

	uCurrent-Date OBJECT-TYPE
		SYNTAX DisplayString (SIZE (8))
		ACCESS read-write
                STATUS mandatory
		DESCRIPTION
                        "The uCurrentTime indicates the current date of
                         the frame relay encryptor . Date is in the format dd/mm/yy."
		::= { uDynamic 1 }

        uCurrent-Time OBJECT-TYPE
		SYNTAX DisplayString (SIZE (5))
                ACCESS read-write
                STATUS mandatory
                DESCRIPTION
                        "The uCurrentTime indicates the current time of
                         the frame relay encryptor . Time is in the format hh:mm."
                ::= { uDynamic 2 }

        uDevice-State OBJECT-TYPE
                SYNTAX INTEGER {
------                 undefined(0) assumed since 0 is not allowed as a value
                       normal(1),
		       test-empty(2),
		       test-loaded(3),
                       failure(4),
		       fail-cipher-chip(5),
		       fail-lock-open(6),
		       fail-lock-open-and-cipher-chip(7)
                      }
                ACCESS read-only
		STATUS mandatory
                DESCRIPTION
			"The current state of the frame relay encryptor . There are two test
			 states: test-empty with no security parameters loaded
			 test-loaded which is entered with ³live³ parameters from
                         the live state "
                ::= { uDynamic 3 }

        uComms-State OBJECT-TYPE
                SYNTAX INTEGER {
------                 undefined(0) assumed since 0 is not allowed as a value
                       booting(1),
                       encrypting(2),
                       not-encrypting(3),
                       failure(4)
		      }
		ACCESS read-only
                STATUS mandatory
                DESCRIPTION
			"The current state of the frame relay encryptor comms board."
                ::= { uDynamic 4 }


        uNMS-State OBJECT-TYPE
		SYNTAX INTEGER {
------                 undefined(0) assumed since 0 is not allowed as a value
                       disabled(1),
                       read-only(2),
                       read-write(3)
                      }
                ACCESS read-only
                STATUS mandatory
                DESCRIPTION
                        "The current state of the SNMP agent for NMS requests.
                         Only in the writeenabled state are Sets allowed."
		::= { uDynamic 5 }

        uSM-State OBJECT-TYPE
                SYNTAX INTEGER {
                       ok(1),
                       removed(2),
		       failure(3)
                      }
                ACCESS read-only
		STATUS mandatory
                DESCRIPTION
			"The current state of the Right SM module. This should be
                        checked after parameter updates in the configure group
                        or the MIBII system group."
                ::= { uDynamic 6 }

        uReady-Alarm-Led OBJECT-TYPE
                SYNTAX INTEGER {
                       red-test-mode(1),
                       green-normal(2),
                       yellow-self-testing(3),
                       flashing-red-alarm(9),
                       flashing-yellow-user-logged-in(11)
                      }
		ACCESS read-only
		STATUS mandatory
                DESCRIPTION
                        "The state of the front panel LED
			 red:             GRETACODER is in Test Mode
			 green:           GRETACODER is in Normal Mode
			 yellow:          GRETACODER is performing a self test
			 blinking-red:    GRETACODER is in Failure state
			 blinking-yellow: GRETACODER MMI user is logged-in"
		::= { uDynamic 7 }

        uBackground  OBJECT IDENTIFIER ::= { unit 4 }

        uRAG-tests OBJECT-TYPE
                SYNTAX Counter
                ACCESS read-only
                STATUS mandatory
                DESCRIPTION
                        "The total number of Random Number Generator tests made
                         A test is made once per minute."
                ::= { uBackground 1 }

        uRAG-fails OBJECT-TYPE
                SYNTAX Counter
                ACCESS read-only
                STATUS mandatory
		DESCRIPTION
                        "The total number of Random Number Generator failures
                        recorded"
		::= { uBackground 2 }

	uRAG-threshold OBJECT-TYPE
                SYNTAX Counter
                ACCESS read-write
                STATUS mandatory
                DESCRIPTION
                        "The number of failures that should trigger a Trap.
                        Changing this value also clears the tests and fails
                        counters"
                ::= { uBackground 3 }


        Unit-States  ::= SEQUENCE {
          uOwn-SID        INTEGER,
--          uClear-Bypass   INTEGER,
	   uCurrent-Date   DisplayString,
            uCurrent-Time   DisplayString,
            uDevice-State   INTEGER,
            uComms-State    INTEGER,
            uNMS-State      INTEGER,
	    uSM-State       INTEGER,
            uReady-Alarm-Led INTEGER,
            uRAG-tests      Counter,
	    uRAG-fails      Counter,
            uRAG-threshold  Counter
         }

---------------------------------------

-- frame-relay group

-- The frame relay group provides statistics on
-- the frame relay ports.
--
-- The range of ifIndex
--

        reset-FR-statistic-counters  OBJECT-TYPE
                SYNTAX INTEGER
                        {
				no(1),
                                yes(2)
                        }
		ACCESS read-write
                STATUS mandatory
		DESCRIPTION
                        "This command clears all the frame relay statistical
                         counters for both ports."
                ::= { frame-relay 1 }

        fR-Traffic-Table  OBJECT-TYPE
                SYNTAX SEQUENCE OF FR-Traffic-Entry
                ACCESS not-accessible
                STATUS mandatory
                DESCRIPTION
                        "The Statistics Table for the frame relay encryptor ."
                ::= { frame-relay 2 }

	fR-Traffic-Entry  OBJECT-TYPE
		SYNTAX FR-Traffic-Entry
		ACCESS not-accessible
		STATUS mandatory
		DESCRIPTION
			""
		INDEX  { frPort-Index }
		::= { fR-Traffic-Table 1 }

	FR-Traffic-Entry ::= SEQUENCE
                {
                        frPort-Index
                                INTEGER,
                        frPort-Type
                                INTEGER,
                        frGood-Frames
                                Counter,
                        frBad-Frames
                                Counter,
                        frInactive-DLCI
                                Counter,
                        frReceived-FECN
                                Counter,
			frReceived-BECN
                                Counter,
                        frSent-Frames
				Counter,
                        frDropped-Frames
                                Counter
			}

	frPort-Index  OBJECT-TYPE
                SYNTAX INTEGER
                ACCESS read-only
                STATUS mandatory
                DESCRIPTION
                        "Port Number Index. The ifIndex Value of the
                         corresponding ifEntry from rfc1213."
                ::= { fR-Traffic-Entry 1 }

        frPort-Type  OBJECT-TYPE
                SYNTAX INTEGER
                        {
                                plain-port(1),
                                cipher-port(2)
			}
                ACCESS read-only
                STATUS mandatory
                DESCRIPTION
                        "Plain is on the local side, cipher the network"
		::= { fR-Traffic-Entry 2 }


        frGood-Frames  OBJECT-TYPE
                SYNTAX Counter
                ACCESS read-only
                STATUS mandatory
                DESCRIPTION
                        "The total number of frames received by the
                         frame relay encryptor  on a port."
                ::= { fR-Traffic-Entry 3 }

        frBad-Frames  OBJECT-TYPE
                SYNTAX Counter
                ACCESS read-only
                STATUS mandatory
                DESCRIPTION
                        "The number of bad frames received by the frame relay encryptor  on a
			 port. These are classified further in frRxErrTable."
                ::= { fR-Traffic-Entry 4 }

        frInactive-DLCI  OBJECT-TYPE
                SYNTAX Counter
		ACCESS read-only
                STATUS mandatory
		DESCRIPTION
                        "The number of illegal or unknown DLCIs
                         received by the frame relay encryptor  on a port."
                ::= { fR-Traffic-Entry 5 }

        frReceived-FECN  OBJECT-TYPE
                SYNTAX Counter
                ACCESS read-only
                STATUS mandatory
                DESCRIPTION
                        "The number of frames with a forward congestion
                         notification received by the frame relay encryptor  on a port."
                ::= { fR-Traffic-Entry 6 }

	frReceived-BECN  OBJECT-TYPE
                SYNTAX Counter
                ACCESS read-only
                STATUS mandatory
                DESCRIPTION
			"The number of frames with a backward congestion
                         notification received by the frame relay encryptor  on a port."
                ::= { fR-Traffic-Entry 7 }

        frSent-Frames  OBJECT-TYPE
                SYNTAX Counter
                ACCESS read-only
                STATUS mandatory
                DESCRIPTION
                        "The total number of frames transmitted by the
                         frame relay encryptor  on a port."
                ::= { fR-Traffic-Entry 8 }

        frDropped-Frames  OBJECT-TYPE
                SYNTAX Counter
                ACCESS read-only
                STATUS mandatory
                DESCRIPTION
                        "The total number of TX frames dropped by the
			 frame relay encryptor  on a port."
		::= { fR-Traffic-Entry 9 }


-- frame relay receive errors  ------
--

        fR-RX-Err-Table   OBJECT-TYPE
                SYNTAX SEQUENCE OF FR-RX-Err-Entry
                ACCESS not-accessible
                STATUS mandatory
                DESCRIPTION
                        "The receive error information for a frame relay encryptor  frame relay
                         port."
                ::= { frame-relay 3 }

        fR-RX-Err-Entry  OBJECT-TYPE
                SYNTAX FR-RX-Err-Entry
                ACCESS not-accessible
                STATUS mandatory
		DESCRIPTION
                        ""
                INDEX  { frRxErrIndex }
                ::= { fR-RX-Err-Table 1 }

	FR-RX-Err-Entry ::= SEQUENCE
                {
                        frRxErrIndex
                                INTEGER,
			frRxErrShort-Frames
                                Counter,
                        frRxErrAborted-Frames
                                Counter,
                        frRxErrResidual-Bits
                                Counter,
                        frRxErrOverruns
                                Counter,
                        frRxErrCRC-Errors
                                Counter
                }

        frRxErrIndex  OBJECT-TYPE
                SYNTAX INTEGER
                ACCESS read-only
                STATUS mandatory
		DESCRIPTION
                        " Port Number Index. The ifIndex Value of the
                         corresponding ifEntry from rfc1213."
		::= { fR-RX-Err-Entry 1 }

	frRxErrShort-Frames  OBJECT-TYPE
                SYNTAX Counter
                ACCESS read-only
                STATUS mandatory
                DESCRIPTION
                        " The number of short frames received."
                ::= { fR-RX-Err-Entry 2 }

        frRxErrAborted-Frames  OBJECT-TYPE
                SYNTAX Counter
                ACCESS read-only
                STATUS mandatory
                DESCRIPTION
                        " The number of aborted frames received."
		::= { fR-RX-Err-Entry 3 }

        frRxErrResidual-Bits  OBJECT-TYPE
                SYNTAX Counter
                ACCESS read-only
		STATUS mandatory
                DESCRIPTION
                        " The number of residual bit frames received."
                ::= { fR-RX-Err-Entry 4 }

	frRxErrOverruns  OBJECT-TYPE
                SYNTAX Counter
                ACCESS read-only
                STATUS mandatory
                DESCRIPTION
			" The number of overruns received."
		::= { fR-RX-Err-Entry 5 }

	frRxErrCRC-Errors  OBJECT-TYPE
		SYNTAX Counter
		ACCESS read-only
		STATUS mandatory
		DESCRIPTION
			" The number of CRC errors received."
		::= { fR-RX-Err-Entry 6 }
---------------------------------------
-- configure group for (weak authenticated) parameter changes
-- parameter information (pi)

        pi-FR-Layer1     OBJECT IDENTIFIER ::= { configure 1 }


        piFRInterface-Installed  OBJECT-TYPE
                SYNTAX INTEGER {
                       is-RS422(1),
                       is-V35(2),
                       is-T1(3),
                       is-E1(4),
                       is-X21(5),
                       is-undefined(6)
                       }
                ACCESS read-only
                STATUS mandatory
                DESCRIPTION
			" The type of Frame Relay Physical interface.
                          The following parameters are required for:
                          - RS422/V35/X21       clock source
                          - G703                        E1 impedance, framemode, timeslots
                          - T1                  T1 frame mode, timeslots."
		::= { pi-FR-Layer1 1 }


        piFRTX-Clock-Source OBJECT-TYPE
                SYNTAX INTEGER {
                       is-DCE(1),
		       is-DTE(2)
                       }
                ACCESS read-write
                STATUS mandatory
                DESCRIPTION
			" Required if the physical type is:
                          RS422
                          V.35
                          X.21"
                ::= { pi-FR-Layer1 2 }


        piFRE1-Plain-Port-Impedance  OBJECT-TYPE
                SYNTAX INTEGER {
		       is-75-OHMS-BNC(1),
                       is-120-OHMS-D-SUB(2)
                       }
		ACCESS read-write
                STATUS mandatory
		DESCRIPTION
                        " "
                ::= { pi-FR-Layer1 3 }

        piFRE1-Cipher-Port-Impedance OBJECT-TYPE
                SYNTAX INTEGER {
                       is-75-OHMS-BNC(1),
                       is-120-OHMS-D-SUB(2)
                       }
                ACCESS read-write
                STATUS mandatory
                DESCRIPTION
                        " "
                ::= { pi-FR-Layer1 4 }

        piFRE1-Framing-Mode OBJECT-TYPE
                SYNTAX INTEGER {
                       is-unframed(1),
                       is-G704(2)
		       }
                ACCESS read-write
                STATUS mandatory
                DESCRIPTION
                        " "
                ::= { pi-FR-Layer1 5 }

	piFRE1-Time-Slot-Options OBJECT-TYPE
                SYNTAX INTEGER {
--                     an-other-interface-is-installed(0),
                       all-slots-except-TS0(1),
                       all-slots-except-TS0-and-TS16(2)
		       }
                ACCESS read-write
                STATUS mandatory
                DESCRIPTION
                        " Required if the physical type is G703 (E1)
                          E1 time slot options available:
                                                Bit values shown in piFRE1-Time-Slots
                          all slots, except TS0               0xff, 0xff, 0xff, 0xfe
			  all slots, except TS0,TS16       0xff, 0xfe, 0xff, 0xfe"

                ::= { pi-FR-Layer1 6 }

        piFRE1-Time-Slots OBJECT-TYPE
		SYNTAX OCTET STRING (SIZE(4))
                ACCESS read-only
                STATUS mandatory
                DESCRIPTION
                        " An Octet bit string. Each bit defines an E1 time slot:
                          0= not used for frame relay
                          1=       used for frame relay"
                ::= { pi-FR-Layer1 7 }



        piFRT1-Plain-Port-Pulse OBJECT-TYPE
                SYNTAX INTEGER {
                       is-CSU(1),
		       is-CSU-T1C1(2),
                       is-DSX-1-0-40m(3),
                       is-DSX-1-40-80m(4),
                       is-DSX-1-80-120m(5),
                       is-DSX-1-120-160m(6),
		       is-DSX-1-160-200m(7)
                       }
                ACCESS read-write
                STATUS mandatory
                DESCRIPTION
                        " "
                ::= { pi-FR-Layer1 8 }

	piFRT1-Cipher-Port-Pulse OBJECT-TYPE
                SYNTAX INTEGER {
                       is-CSU(1),
                       is-CSU-T1C1(2),
                       is-DSX-1-0-40m(3),
		       is-DSX-1-40-80m(4),
                       is-DSX-1-80-120m(5),
                       is-DSX-1-120-160m(6),
                       is-DSX-1-160-200m(7)
                       }
                ACCESS read-write
                STATUS mandatory
		DESCRIPTION
                        " "
                ::= { pi-FR-Layer1 9 }

	piFRT1-Framing-Mode OBJECT-TYPE
		SYNTAX INTEGER {
                       is-unframed(1),
                       is-ESF(3),
                       is-D4(4)
                       }
                ACCESS read-write
                STATUS mandatory
                DESCRIPTION
                        " "
                ::= { pi-FR-Layer1 10}

        piFRT1-Time-Slot-Options OBJECT-TYPE
                SYNTAX INTEGER {
--                     an-other-interface-is-installed(0),
		       all-slots(1)
                       }
                ACCESS read-write
                STATUS mandatory
                DESCRIPTION
			" Required if the physical type is T1
                          T1 time slot options available:
                                        Bit values shown in piFRT1TimeSlots
                          all slots     0xff, 0xff, 0xff"
                ::= { pi-FR-Layer1 11}

        piFRT1-Time-Slots OBJECT-TYPE
                SYNTAX OCTET STRING (SIZE(3))
                ACCESS read-only
		STATUS mandatory
                DESCRIPTION
                        " An Octet bit string. Each bit defines a T1 time slot:
                          0= not used for frame relay
                          1=      used for frame relay"
		::= { pi-FR-Layer1 12}

        pi-FR-Layer2     OBJECT IDENTIFIER ::= { configure 2 }

        pi-FR-Logical-Interface-Type  OBJECT-TYPE
                SYNTAX INTEGER {
		       uni(1),
                       nni(2)
                      }
		ACCESS read-only
              STATUS mandatory
		DESCRIPTION
                      " The type of Frame Relay logical interface.
                                UNI = User to Network Interface
                                NNI = Network to Network Interface"
                ::= { pi-FR-Layer2 1 }

        pi-FR-Max-RX-Frame OBJECT-TYPE
                SYNTAX INTEGER {
                       size-256-bytes(256),
                       size-512-bytes(512),
                       size-1024-bytes(1024),
                       size-1600-bytes(1600),
                       size-2048-bytes(2048),
                       size-4096-bytes(4096)
		      }
                ACCESS read-write
                STATUS mandatory
                DESCRIPTION
                        " Maximum frame length in octets incoming"
		::= { pi-FR-Layer2 2 }

        pi-FR-Max-TX-Frame  OBJECT-TYPE
                SYNTAX INTEGER{
                       size-256-bytes(256),
                       size-512-bytes(512),
                       size-1024-bytes(1024),
                       size-1600-bytes(1600),
                       size-2048-bytes(2048),
                       size-4096-bytes(4096)
		      }
                ACCESS read-write
                STATUS mandatory
                DESCRIPTION
                        " Maximum frame length in octets outgoing"
		::= { pi-FR-Layer2 3 }

        pi-FR-LMI-support  OBJECT-TYPE
                SYNTAX INTEGER {
                       disabled(1),
		       standard-LMI(2),
                       is-ANSI-T1-617(3),
                       is-ITU-T-Q933(4)
		       }
                ACCESS read-write
		STATUS mandatory
		DESCRIPTION
                        " LMI version"
                ::= { pi-FR-Layer2 4 }

--      piFRSvcVers  OBJECT-TYPE
--              SYNTAX INTEGER {
--                  notused(1),
--                     ver1(2),
--                     ver2(3)
--                     }
--              ACCESS read-write
--              STATUS mandatory
--              DESCRIPTION
--                      " Only relevant for SVCs"
--              ::= { pi-FR-Layer2 5 }

--      piFREncoding OBJECT-TYPE
--              SYNTAX INTEGER {
--                     is-Q922-10b(1),
--                     is-Q922-nov(2),
--                     is-Q922-mar(3),
--                     is-Q921-13b(4)
--                     }
--              ACCESS read-write
--              STATUS mandatory
--              DESCRIPTION
--                      " DLCI encoding. For future use."
--              ::= { pi-FR-Layer2 6 }


	pi-FR-DLC-Ranges-Table   OBJECT-TYPE
		SYNTAX SEQUENCE OF Pi-FR-DLC-Ranges-Entry
                ACCESS not-accessible
		STATUS mandatory
		DESCRIPTION
			"The Table of Active DLCIs."
		::= { configure 3 }

	pi-FR-DLC-Ranges-Entry  OBJECT-TYPE
		SYNTAX Pi-FR-DLC-Ranges-Entry
		ACCESS not-accessible
		STATUS mandatory
		DESCRIPTION
			""
		INDEX  { piFRDLcRangeBand }
		::= { pi-FR-DLC-Ranges-Table 1 }

	Pi-FR-DLC-Ranges-Entry ::= SEQUENCE
		{
                        piFRDLcRangeBand
                                INTEGER,
                        piFRDLcRangeUse
                                INTEGER,
                        piFRDLcRangeMode
                                INTEGER,
                        piFRDLcRangeStart
                                INTEGER,
			piFRDLcRangeEnd-set-to-activate-changes
				INTEGER
                }

	piFRDLcRangeBand  OBJECT-TYPE
		SYNTAX INTEGER
		ACCESS read-only
		STATUS mandatory
		DESCRIPTION
			" The index number of this DLCI circuit band."
		::= { pi-FR-DLC-Ranges-Entry 1 }

	piFRDLcRangeUse OBJECT-TYPE
		SYNTAX INTEGER {
		       inactive(1),
			    pvc(2)
-- future use               svc(3)
		       }
		ACCESS read-write
		STATUS mandatory
		DESCRIPTION
			" The Type of use to be applied to the range defined in
			  piFRDLcRangeStart and piFRDLcRangeEnd"
		::= { pi-FR-DLC-Ranges-Entry 2 }

	piFRDLcRangeMode OBJECT-TYPE
		SYNTAX INTEGER{
		       bidirectional(1)
		       }
		ACCESS read-only
		STATUS mandatory
		DESCRIPTION
			" For future use"
		::= { pi-FR-DLC-Ranges-Entry 3 }

	piFRDLcRangeStart OBJECT-TYPE
		SYNTAX  INTEGER  (0..1023)
		ACCESS read-write
		STATUS mandatory
		DESCRIPTION
			" The first DLCI in this band"
		::= { pi-FR-DLC-Ranges-Entry 4 }

	piFRDLcRangeEnd-set-to-activate-changes  OBJECT-TYPE
		SYNTAX  INTEGER  (0..1023)
		ACCESS read-write
		STATUS mandatory
		DESCRIPTION
			" The last DLCI in this band
			  Setting this parameter activates the changes"
		::= { pi-FR-DLC-Ranges-Entry 5 }



-- Configure the auxillary ports used for SNMP
-- Port1 Ethernet
-- Port2 Future use async with dial up capability
-- Port3 Async  serial direct
--

	piRemotePorts     OBJECT IDENTIFIER ::= { configure 5 }


	pi-Remote-Port1     OBJECT IDENTIFIER ::= { piRemotePorts 1 }

        pi-Remote-Port1IP-Address  OBJECT-TYPE
		SYNTAX IpAddress
                ACCESS read-write
		STATUS mandatory
                DESCRIPTION
			"The IP address for 1, the Ethernet line "
		::= { pi-Remote-Port1 1 }

	pi-Remote-Port1Subnet-mask OBJECT-TYPE
                SYNTAX IpAddress
                ACCESS read-write
                STATUS mandatory
		DESCRIPTION
                        "The subnet mask associated with the IP address of
                         the 1 Ethernet line. The value of the mask is
                         an IP address with all the network bits set to 1
                         and all the host bits set to 0."
                ::= { pi-Remote-Port1 2 }

        pi-Remote-Port1Gateway-Address  OBJECT-TYPE
                SYNTAX IpAddress
                ACCESS read-write
                STATUS mandatory
		DESCRIPTION
                        "The Gateway IP address for 1. The gateway is on the
                         same network as the port, so the network bits must be
                         identical to the port Ipaddress"
		::= { pi-Remote-Port1 3 }

        piRemotePort2     OBJECT IDENTIFIER ::= { piRemotePorts 2 }

        pi-Remote-Port3     OBJECT IDENTIFIER ::= { piRemotePorts 3 }

        pi-Remote-Port3IP-Address  OBJECT-TYPE
                SYNTAX IpAddress
                ACCESS read-write
                STATUS mandatory
                DESCRIPTION
                        "The IP address for 1, the serial line "
                ::= { pi-Remote-Port3 1 }

	pi-Remote-Port3Subnet-mask OBJECT-TYPE
                SYNTAX IpAddress
                ACCESS read-write
                STATUS mandatory
                DESCRIPTION
			"The subnet mask associated with the IP address of
			 the 3 serial line. The value of the mask is
			 an IP address with all the network bits set to 1
                         and all the host bits set to 0."
		::= { pi-Remote-Port3 2 }

	pi-Remote-Port3Gateway-Address  OBJECT-TYPE
                SYNTAX IpAddress
                ACCESS read-write
		STATUS mandatory
		DESCRIPTION
			"The Gateway IP address for 3. The gateway is on the
			 same network as the port, so the network bits must be
			 identical to the port Ipaddress"
		::= { pi-Remote-Port3 3 }

	pi-Remote-Port3Data-link-protocol  OBJECT-TYPE
		SYNTAX INTEGER {
		       slip(28)  -- generic slip
		}
		ACCESS read-only
		STATUS mandatory
		DESCRIPTION
			"The type of Data link protocol. Currently only slip
			 is supported"
		::= { pi-Remote-Port3 4 }

	pi-Remote-Port3Baudrate  OBJECT-TYPE
		SYNTAX INTEGER {
		       baud-2400(1),
		       baud-4800(2),
		       baud-9600(3),
		       baud-19200(4),
		       baud-38400(5)
		}
		ACCESS read-write
		STATUS mandatory
		DESCRIPTION
			"The Baud rate for async port 3.
			 The other physical parameters are fixed as follows:
			 Character Length: 8 bits
			 Parity:           none
			 Stopbits:         1"
		::= { pi-Remote-Port3 5 }


--
--  Application Configuration group
--

	piApplication     OBJECT IDENTIFIER ::= { configure 6 }

	pi-App-DLC-Cipher-Table   OBJECT-TYPE
		SYNTAX SEQUENCE OF Pi-App-DLC-Cipher-Entry
		ACCESS not-accessible
		STATUS mandatory
		DESCRIPTION
			"The table of encrypted DLCIs port."
		::= { piApplication 1 }

	pi-App-DLC-Cipher-Entry  OBJECT-TYPE
		SYNTAX Pi-App-DLC-Cipher-Entry
		ACCESS not-accessible
		STATUS mandatory
		DESCRIPTION
			""
		INDEX  { piAppDLcCipherBand }
		::= { pi-App-DLC-Cipher-Table 1 }

	Pi-App-DLC-Cipher-Entry ::= SEQUENCE
		{
			piAppDLcCipherBand
				INTEGER,
			piAppDLcCipherUse
				INTEGER,
			piAppDLcCipherStart
				INTEGER,
			piAppDLcCipherEnd-set-to-activate-changes
				INTEGER
		}

	piAppDLcCipherBand  OBJECT-TYPE
		SYNTAX INTEGER
		ACCESS read-only
		STATUS mandatory
		DESCRIPTION
			" The index number of this DLCI circuit band."
		::= { pi-App-DLC-Cipher-Entry 1 }


	piAppDLcCipherUse OBJECT-TYPE
		SYNTAX INTEGER{
		       plain(1),
		       cipher(2)
		       }
		ACCESS read-write
		STATUS mandatory
		DESCRIPTION
			" The Type of use (plain or cipher) to be
			  applied to the range defined in
			  piAppDLcCipherStart and piAppDLcCipherEnd."
		::= { pi-App-DLC-Cipher-Entry 2 }

	piAppDLcCipherStart OBJECT-TYPE
		SYNTAX  INTEGER  (0..1023)
		ACCESS read-write
		STATUS mandatory
		DESCRIPTION
			" The first DLCI in this band"
		::= { pi-App-DLC-Cipher-Entry 3 }

	piAppDLcCipherEnd-set-to-activate-changes  OBJECT-TYPE
		SYNTAX  INTEGER  (0..1023)
		ACCESS read-write
		STATUS mandatory
		DESCRIPTION
			" The last DLCI in this band
			  Setting this parameter activates the changes"
		::= { pi-App-DLC-Cipher-Entry 4 }


------------------------------------------------------------------

	END
