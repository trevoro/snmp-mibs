--                      ADAPTEC ASM EXT STORAGE MGMT STN MIB
--                      LAST-UPDATED   "200410051842Z"
--                      ORGANIZATION   "Adaptec, Inc"
--
--                      EMAIL Contact:
--                         support@adaptec.com

--                      POSTAL Contact:
--                         ADAPTEC
--                         ORLANDO
--                         FLORIDA 32826

--                      VOICE Contact:
--                         +1 321-207-2000
--
--                      This is the MIB for Adaptec ASM Management Station.

--                      This document is Copyright (C) 2004 Adaptec, Inc.


ADAPTEC-ASM-EXT-STORAGE-MGMT-STN-MIB DEFINITIONS ::= BEGIN

    IMPORTS

      OBJECT-TYPE
            FROM RFC-1212
      TRAP-TYPE
            FROM RFC-1215
      Gauge, enterprises
            FROM RFC1155-SMI
      DisplayString
            -- FROM RFC1158-MIB;
            FROM RFC1213-MIB;

adaptec                        OBJECT IDENTIFIER ::= { enterprises 795 }

-- 16516 designates all MIBs associated with the ASM Ext Storage Mgmt Station
asmMgmtStation                 OBJECT IDENTIFIER ::= { adaptec 16516 }

-- Here are the particular products within the Management Station family of products.

--   Only the current Total Storage DS300/DS400 is specifically called out.
totalStorageDS300MIB           OBJECT IDENTIFIER ::= { asmMgmtStation 10 }

trapObjects                    OBJECT IDENTIFIER ::= { totalStorageDS300MIB 1 }

--
-- Trap variables
--
-- This variables cannot be accessed by SNMP GET,GET-NEXT,SET,...
-- They are only used by SNMP traps.
--

trapEventHost OBJECT-TYPE
    SYNTAX  DisplayString
    ACCESS  read-only
    STATUS  mandatory
    DESCRIPTION
    "The host on which the event ocurred."
    ::= { trapObjects 1 }

trapEventOrigin OBJECT-TYPE
    SYNTAX  DisplayString
    ACCESS  read-only
    STATUS  mandatory
    DESCRIPTION
    "The subsystem originating the event."
    ::= { trapObjects 2 }

trapEventDate OBJECT-TYPE
    SYNTAX  DisplayString
    ACCESS  read-only
    STATUS  mandatory
    DESCRIPTION
    "The date on which the event ocurred (YYYY-MM-DD format)."
    ::= { trapObjects 3 }

trapEventTime OBJECT-TYPE
    SYNTAX  DisplayString
    ACCESS  read-only
    STATUS  mandatory
    DESCRIPTION
    "The time at which the event ocurred (HH:MM:SS Z format)."
    ::= { trapObjects 4 }

trapEventLevel OBJECT-TYPE
    SYNTAX  DisplayString
    ACCESS  read-only
    STATUS  mandatory
    DESCRIPTION
    "The level of the event - Information, Warning, Error, Serious, Fatal."
    ::= { trapObjects 5 }

trapEventActive OBJECT-TYPE
    SYNTAX  INTEGER
    ACCESS  read-only
    STATUS  mandatory
    DESCRIPTION
    "If the event is active, value 1, else value 0."
    ::= { trapObjects 6 }

trapEventInfo OBJECT-TYPE
    SYNTAX  INTEGER
    ACCESS  read-only
    STATUS  mandatory
    DESCRIPTION
    "Information specific to the originator. If the top 8 bits are 0x00
    the remaining 24 bits contain a value in originator specific format.
    If the top 8 bits are 0x01 the remaining 24 bits identify a field
    replaceable unit by number."
    ::= { trapObjects 7 }

trapEventShortText OBJECT-TYPE
    SYNTAX  DisplayString
    ACCESS  read-only
    STATUS  mandatory
    DESCRIPTION
    "A short text description of the event."
    ::= { trapObjects 8 }

trapEventDescription OBJECT-TYPE
    SYNTAX  DisplayString
    ACCESS  read-only
    STATUS  mandatory
    DESCRIPTION
    "A longer description of the event."
    ::= { trapObjects 9 }

trapEventAgentSequence OBJECT-TYPE
    SYNTAX      INTEGER
    ACCESS      read-only
    STATUS      mandatory
    DESCRIPTION
        "Unique sequence number allocated for this occurence of the event by
        the agent."
    ::= { trapObjects 10 }

trapEventSANSequence OBJECT-TYPE
    SYNTAX      INTEGER
    ACCESS      read-only
    STATUS      mandatory
    DESCRIPTION
        "Unique sequence number allocated for this occurence of the event by
        the Shared Storage Manager."
    ::= { trapObjects 11 }

trapEventAgentID OBJECT-TYPE
    SYNTAX      DisplayString
    ACCESS      read-only
    STATUS      mandatory
    DESCRIPTION
        "Unique identifier for the agent logging the event"
    ::= { trapObjects 12 }

trapEventAgentType OBJECT-TYPE
    SYNTAX      INTEGER {
                    target(1),     -- storage controller
                    server(2),     -- file server
                    management(3)  -- management station
                }
    ACCESS      read-only
    STATUS      mandatory
    DESCRIPTION
        "The type of storage manager entity logging the event"
    ::= { trapObjects 13 }

trapEventCategory OBJECT-TYPE
    SYNTAX      DisplayString
    ACCESS      read-only
    STATUS      mandatory
    DESCRIPTION
        "If the agent type logging the event was a Windows file server, a
        string representation of the Windows event category, otherwise the
        empty string."
    ::= { trapObjects 14 }

trapEventType OBJECT-TYPE
    SYNTAX      Gauge
    ACCESS      read-only
    STATUS      mandatory
    DESCRIPTION
        "Unique identifier for the type of the event."
    ::= { trapObjects 15 }

trapEventControllerSN OBJECT-TYPE
    SYNTAX  DisplayString
    ACCESS  read-only
    STATUS  mandatory
    DESCRIPTION
    "Controller serial number on which the event ocurred."
    ::= { trapObjects 16 }

trapEventEnclosureSN OBJECT-TYPE
    SYNTAX  DisplayString
    ACCESS  read-only
    STATUS  mandatory
    DESCRIPTION
    "Enclosure serial number on which the event ocurred."
    ::= { trapObjects 17 }




managementServerEventTrap TRAP-TYPE
    ENTERPRISE totalStorageDS300MIB
    VARIABLES { trapEventHost, trapEventOrigin, trapEventDate,
                trapEventTime, trapEventLevel, trapEventActive,
                trapEventInfo, trapEventShortText, trapEventDescription,
                trapEventAgentSequence, trapEventSANSequence, trapEventAgentID,
                trapEventAgentType, trapEventCategory, trapEventType,
                trapEventControllerSN, trapEventEnclosureSN}
     DESCRIPTION
         "An eventTrap signifies that an event has been logged to the converter
         event logger. The variables encode the details of the event."
--#TYPE "Informational event from a management server or external storage."
--#SUMMARY "Entity %s reports %s (level %s)"
--#ARGUMENTS {0, 8, 4}
--#SEVERITY INFORMATIONAL
     ::= 1

END
