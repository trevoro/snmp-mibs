-- $Id: ps.mib,v 29.2.66.1 1999/11/23 03:18:00 brooksd Exp $

--
-- Aug 01, 1997 rm   Initial creation
--
-- Jan 29, 1999 mk   Changed defaults of powerSupplyStateTrapState
--                   and powerSupplyOperationalStateTrapState to enabled(1)
--
-- Nov 16, 1999 db   EOI 35393 Added powerSupplySerialNumber object


ASCEND-POWER-SUPPLY-MIB DEFINITIONS ::= BEGIN

    IMPORTS
            powerSupply
                FROM ASCEND-MIB
            OBJECT-TYPE
                FROM RFC-1212;

    powerSupplyCount OBJECT-TYPE
        SYNTAX  INTEGER
        ACCESS  read-only
        STATUS  mandatory
        DESCRIPTION
           "The number of entries in the powerSupplyTable."
       ::= { powerSupply 1 }

    powerSupplyTable OBJECT-TYPE
        SYNTAX  SEQUENCE OF PowerSupplyEntry
        ACCESS  not-accessible
        STATUS  mandatory
        DESCRIPTION
           "The power supply table."
       ::= { powerSupply 2 }

    powerSupplyEntry OBJECT-TYPE
        SYNTAX  PowerSupplyEntry
        ACCESS  not-accessible
        STATUS  mandatory
        DESCRIPTION
           "An entry in the power supply table."
       INDEX   { powerSupplyIndex }
       ::= { powerSupplyTable 1 }

    PowerSupplyEntry ::=
        SEQUENCE {
            powerSupplyIndex
                INTEGER,
            powerSupplyState
                INTEGER,
            powerSupplyOperationalState
                INTEGER,
	    powerSupplySerialNumber
                INTEGER
    }

    powerSupplyIndex OBJECT-TYPE
        SYNTAX  INTEGER
        ACCESS  read-only
        STATUS  mandatory
        DESCRIPTION
                "The index of the powerSupply entry."
       ::= { powerSupplyEntry 1 }

    powerSupplyState OBJECT-TYPE
        SYNTAX  INTEGER {
            other(1),
            present(2),
            absent(3)
        }
        ACCESS  read-only
        STATUS  mandatory
        DESCRIPTION
                "The state of the power supply module."
       ::= { powerSupplyEntry 2 }

    powerSupplyOperationalState OBJECT-TYPE
        SYNTAX  INTEGER {
            other(1),
            noFailure(2),
            failed(3)
        }
        ACCESS  read-only
        STATUS  mandatory
        DESCRIPTION
           "The operational state of the power supply module."
      ::= { powerSupplyEntry 3 }

    --  This object is supported only for the APX product line and
    --  was first added in TAOS version 8.0
    --  For non-supported platforms such as the TNT and absent power supplies
    --  of supported platforms, the value of zero (0) will be returned
    powerSupplySerialNumber OBJECT-TYPE
        SYNTAX  INTEGER
        ACCESS  read-only
        STATUS  mandatory
        DESCRIPTION
           "Serial number of the power supply module."
       ::= { powerSupplyEntry 4 }

    powerSupplyStateTrapState OBJECT-TYPE
        SYNTAX  INTEGER { enabled(1), disabled(2) }
        ACCESS   read-write
        STATUS   mandatory
        DESCRIPTION
           "This variable  indicates  whether  the  system
           produces the powerSupplyStateChange trap."
        DEFVAL { enabled }
     ::= { powerSupply 3 }

    powerSupplyOperationalStateTrapState OBJECT-TYPE
        SYNTAX  INTEGER { enabled(1), disabled(2) }
        ACCESS   read-write
        STATUS   mandatory
        DESCRIPTION
           "This variable  indicates  whether  the  system
           produces the powerSupplyOperationalStateChange trap."
        DEFVAL { enabled }
     ::= { powerSupply 4 }
END
