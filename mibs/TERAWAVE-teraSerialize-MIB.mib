TERAWAVE-teraSerialize-MIB DEFINITIONS ::= BEGIN
        -- Created by sml2mib compiler 
        IMPORTS

 enterprises,  OBJECT-TYPE,  Counter,  Gauge,  TimeTicks
        FROM RFC1155-SMI;

terawave OBJECT IDENTIFIER ::=  { enterprises 4513 }

     -- teraCardSerializeTable

teraCardSerializeTable OBJECT-TYPE
     SYNTAX SEQUENCE OF TeraCardSerializeTableEntryType
     ACCESS not-accessible
     STATUS mandatory
     DESCRIPTION
          " table teraCardSerializeTable"
     ::= { terawave 17 }

teraCardSerializeTableEntry OBJECT-TYPE
          SYNTAX TeraCardSerializeTableEntryType
          ACCESS not-accessible
          STATUS mandatory
          DESCRIPTION
               " table entry teraCardSerializeTableEntry "
          INDEX {                   teraInstallSlotNumber }
     ::= { teraCardSerializeTable 1 }

TeraCardSerializeTableEntryType ::= SEQUENCE {
          teraCardMfgName   
             OCTET STRING,
          teraCardMfgRevision   
             OCTET STRING,
          teraCardMfgSerial   
             INTEGER,
          teraCardMfgSWVersion   
             INTEGER,
          teraCardMfgDate   
             INTEGER,
          teraCardMfgPN   
             INTEGER,
          teraCardMfgInfo   
             OCTET STRING,
          teraCardMfgReservedCRC   
             INTEGER
}

teraCardMfgName OBJECT-TYPE
          SYNTAX OCTET STRING
          ACCESS read-write
          STATUS mandatory
          DESCRIPTION
               ""
          ::= { teraCardSerializeTableEntry 1 }

teraCardMfgRevision OBJECT-TYPE
          SYNTAX OCTET STRING
          ACCESS read-write
          STATUS mandatory
          DESCRIPTION
               ""
          ::= { teraCardSerializeTableEntry 2 }

teraCardMfgSerial OBJECT-TYPE
          SYNTAX INTEGER
          ACCESS read-write
          STATUS mandatory
          DESCRIPTION
               ""
          ::= { teraCardSerializeTableEntry 3 }

teraCardMfgSWVersion OBJECT-TYPE
          SYNTAX INTEGER
          ACCESS read-write
          STATUS mandatory
          DESCRIPTION
               ""
          ::= { teraCardSerializeTableEntry 4 }

teraCardMfgDate OBJECT-TYPE
          SYNTAX INTEGER
          ACCESS read-write
          STATUS mandatory
          DESCRIPTION
               ""
          ::= { teraCardSerializeTableEntry 5 }

teraCardMfgPN OBJECT-TYPE
          SYNTAX INTEGER
          ACCESS read-write
          STATUS mandatory
          DESCRIPTION
               ""
          ::= { teraCardSerializeTableEntry 6 }

teraCardMfgInfo OBJECT-TYPE
          SYNTAX OCTET STRING
          ACCESS read-write
          STATUS mandatory
          DESCRIPTION
               ""
          ::= { teraCardSerializeTableEntry 7 }

teraCardMfgReservedCRC OBJECT-TYPE
          SYNTAX INTEGER
          ACCESS read-write
          STATUS mandatory
          DESCRIPTION
               ""
          ::= { teraCardSerializeTableEntry 8 }

     -- teraEEPROMSerializeTable

teraEEPROMSerializeTable OBJECT-TYPE
     SYNTAX SEQUENCE OF TeraEEPROMSerializeTableEntryType
     ACCESS not-accessible
     STATUS mandatory
     DESCRIPTION
          " table teraEEPROMSerializeTable"
     ::= { terawave 21 }

teraEEPROMSerializeTableEntry OBJECT-TYPE
          SYNTAX TeraEEPROMSerializeTableEntryType
          ACCESS not-accessible
          STATUS mandatory
          DESCRIPTION
               " table entry teraEEPROMSerializeTableEntry "
          INDEX {                   teraInstallSlotNumber,                  ifIndex }
     ::= { teraEEPROMSerializeTable 1 }

TeraEEPROMSerializeTableEntryType ::= SEQUENCE {
          teraEEPROMMfgName   
             OCTET STRING,
          teraEEPROMMfgRevision   
             OCTET STRING,
          teraEEPROMMfgSerial   
             INTEGER,
          teraEEPROMMfgHWVersion   
             INTEGER,
          teraEEPROMMfgDate   
             INTEGER,
          teraEEPROMMfgPN   
             INTEGER,
          teraEEPROMMfgInfo   
             OCTET STRING,
          teraEEPROMMfgReservedCRC   
             INTEGER
}

teraEEPROMMfgName OBJECT-TYPE
          SYNTAX OCTET STRING
          ACCESS read-write
          STATUS mandatory
          DESCRIPTION
               ""
          ::= { teraEEPROMSerializeTableEntry 1 }

teraEEPROMMfgRevision OBJECT-TYPE
          SYNTAX OCTET STRING
          ACCESS read-write
          STATUS mandatory
          DESCRIPTION
               ""
          ::= { teraEEPROMSerializeTableEntry 2 }

teraEEPROMMfgSerial OBJECT-TYPE
          SYNTAX INTEGER
          ACCESS read-write
          STATUS mandatory
          DESCRIPTION
               ""
          ::= { teraEEPROMSerializeTableEntry 3 }

teraEEPROMMfgHWVersion OBJECT-TYPE
          SYNTAX INTEGER
          ACCESS read-write
          STATUS mandatory
          DESCRIPTION
               ""
          ::= { teraEEPROMSerializeTableEntry 4 }

teraEEPROMMfgDate OBJECT-TYPE
          SYNTAX INTEGER
          ACCESS read-write
          STATUS mandatory
          DESCRIPTION
               ""
          ::= { teraEEPROMSerializeTableEntry 5 }

teraEEPROMMfgPN OBJECT-TYPE
          SYNTAX INTEGER
          ACCESS read-write
          STATUS mandatory
          DESCRIPTION
               ""
          ::= { teraEEPROMSerializeTableEntry 6 }

teraEEPROMMfgInfo OBJECT-TYPE
          SYNTAX OCTET STRING
          ACCESS read-write
          STATUS mandatory
          DESCRIPTION
               ""
          ::= { teraEEPROMSerializeTableEntry 7 }

teraEEPROMMfgReservedCRC OBJECT-TYPE
          SYNTAX INTEGER
          ACCESS read-write
          STATUS mandatory
          DESCRIPTION
               ""
          ::= { teraEEPROMSerializeTableEntry 8 }

END
