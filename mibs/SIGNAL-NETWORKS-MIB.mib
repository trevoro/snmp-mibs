-- ******************************************************************
 -- Signal Networks enterprise MIB for ICM.
 -- Version : 1.0
 -- December 2006 
 -- Copyright (c) 2006 by Signal Networks. 
 -- All rights reserved. 
 -- Note : 
 -- ****************************************************************** 
 -- Modification History: 
 --
 -- version | Date    | reason for updation | name of the person 
 --   1.0   |01/12/06 | Original            | Sujith K.
 -- ****************************************************************** 

SIGNAL-NETWORKS-MIB DEFINITIONS ::= BEGIN

IMPORTS
	DisplayString, PhysAddress
		FROM RFC1213-MIB
	enterprises, Counter
		FROM RFC1155-SMI
	OBJECT-TYPE
		FROM RFC-1212
	TRAP-TYPE
		FROM RFC-1215;


signal-networks OBJECT IDENTIFIER ::= { enterprises 27243 } 


-- ICM group

icm	OBJECT IDENTIFIER ::= { signal-networks 1 }


-- System info for ICM

icm-system	OBJECT IDENTIFIER ::= { icm 1 }


-- ICM System group

	icmDescr OBJECT-TYPE
              SYNTAX  DisplayString (SIZE (0..255))
              ACCESS  read-only
              STATUS  mandatory
              DESCRIPTION
                      "A textual description of ICM.  This value
                      should include the full name and version
                      identification of the ICM's hardware type,
                      software operating-system, and networking
                      software.  It is mandatory that this only contain
                      printable ASCII characters."
              ::= { icm-system 1 }

         icmContact OBJECT-TYPE
              SYNTAX  DisplayString (SIZE (0..255))
              ACCESS  read-write
              STATUS  mandatory
              DESCRIPTION
                      "The textual identification of the contact person
                      for ICM, together with information on how to contact
                      this person."
              ::= { icm-system 2 }
END
