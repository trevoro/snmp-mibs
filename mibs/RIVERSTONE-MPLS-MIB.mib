RIVERSTONE-MPLS-MIB DEFINITIONS ::= BEGIN

--  This module provides authoritative definitions for Riverstone
--  Network's enterprise-specific SNMP API to manage MPLS module
--
--  This module will be extended, as required.
--  Riverstone Networks reserves the right to make changes in
--  specification and other information contained in this document
--  without prior notice.  The reader should consult Riverstone Networks
--  to determine whether any such changes have been made.
--
--  In no event shall Riverstone Networks be liable for any incidental,
--  indirect, special, or consequential damages whatsoever (including
--  but not limited to lost profits) arising out of or related to this
--  document or the information contained in it, even if Riverstone
--  Networks has been advised of, known, or should have known, the
--  possibility of such damages.
--
--  Riverstone grants vendors, end-users, and other interested parties
--  a non-exclusive license to use this Specification in connection
--  with the management of Riverstone's products.
 
IMPORTS
    OBJECT-TYPE, MODULE-IDENTITY, NOTIFICATION-TYPE
        FROM SNMPv2-SMI
    riverstoneMibs
        FROM RIVERSTONE-SMI-MIB
    TruthValue, RowPointer
        FROM SNMPv2-TC
    mplsXCOperStatus, mplsXCEntry
        FROM MPLS-LSR-MIB
    MODULE-COMPLIANCE, OBJECT-GROUP, NOTIFICATION-GROUP
        FROM SNMPv2-CONF;

rsMPLSMIB MODULE-IDENTITY  
    LAST-UPDATED "200205240000Z"  -- May 24, 2002
    ORGANIZATION "Riverstone Networks, Inc."
    CONTACT-INFO
    "Riverstone Networks, Inc
     5200 Great America Parkway
     Santa Clara, CA 95054
     (408) 878-6500
     nms-eng@riverstonenet.com
     http://www.riverstonenet.com"

    DESCRIPTION
         "This mib module defines an SNMP API to manage Riverstone's
          MPLS module"

 ::= { riverstoneMibs 39 }

-- The MPLS Management Group

rsMPLSObjects              OBJECT IDENTIFIER ::= { rsMPLSMIB 1 }
rsMPLSNotification         OBJECT IDENTIFIER ::= { rsMPLSMIB 2 }

rsMPLSNotificationControl  OBJECT IDENTIFIER ::= { rsMPLSNotification 1 }
rsMPLSNotifications        OBJECT IDENTIFIER ::= { rsMPLSNotification 2 }
rsMPLSNotifyPrefix         OBJECT IDENTIFIER ::= { rsMPLSNotifications 0 }

--  rsMPLSXCExtTable   -  Extends the mplsXCTable in LSR-MIB.

rsMPLSXCExtTable  OBJECT-TYPE
       SYNTAX        SEQUENCE OF RsMPLSXCExtEntry
       MAX-ACCESS    not-accessible
       STATUS        current
       DESCRIPTION
        "This table specifies extra parameters which might be of interest
         to a SNMP manager, which are not present in the mplsXCTable."
       ::=  { rsMPLSObjects 1 }

rsMPLSXCExtEntry  OBJECT-TYPE
       SYNTAX        RsMPLSXCExtEntry
       MAX-ACCESS    not-accessible
       STATUS        current
       DESCRIPTION
        "An entry in this table supplies additional necessary parameters 
         like whether rerouted or not, detour LSP, secondary LSP."
       AUGMENTS       { mplsXCEntry }
       ::=  { rsMPLSXCExtTable 1 }

RsMPLSXCExtEntry ::=  SEQUENCE {
       rsMPLSXCType                INTEGER,
       rsMPLSXCExtendedOperStatus  INTEGER,
       rsMPLSXCDetourXC            RowPointer,
       rsMPLSXCSecondaryXC         RowPointer
}

rsMPLSXCType OBJECT-TYPE
       SYNTAX   INTEGER {
                         unknown(1),        -- unable to determine
                         other(2),          -- none of the ones present
                         nonIngress(3),     -- Transit or Egress LSP 
                         primaryNoSecondary(4),  -- Primary without any secondary LSP
                         primary(5),        -- Primary with secondary LSP
                         secondary(6),      -- Secondary LSP
                         detour(7)          -- Detour LSP (for some other)
                      }
       MAX-ACCESS  read-only
       STATUS      current
       DESCRIPTION
        "This object reflects the type of the LSP.  In case of ingress,
         this reports whether it is a primary or secondary or detour for
         some other LSPs."
       ::=  { rsMPLSXCExtEntry 1 }

rsMPLSXCExtendedOperStatus OBJECT-TYPE
       SYNTAX   INTEGER {
                         up(1),             -- ready to pass packets
                         down(2),
                         testing(3),        -- in some test mode
                         unknown(4),        -- status cannot be determined
                                            -- for some reason.
                         dormant(5),
                         notPresent(6),     -- some component is missing
                         lowerLayerDown(7), -- down due to the state of
                                            -- lower layer interfaces
                         rerouted(8)        -- uses a detour LSP
                      }
       MAX-ACCESS  read-only
       STATUS      current
       DESCRIPTION
        "This object is the same as the mplsXCOperStatus during the normal
         operation.  If the LSP has a Detour (Fast Reroute LSP), this value
         is set to rerouted (8), when the detour is used for transmitting
         the data path.  At this time, the rsMPLSXCDetourXC will point to
         the cross-connect of the detour LSP.  The mplsOutSegmentTopLabel
         value of the outsegment of this LSP will be set to 0 (invalid
         label).

         When this LSP comes back up, again the value will change as 
         mplsXCOperStatus and the rsMPLSXCDetourXC will be set to 
         the ZeroDotZero OID.  Also the mplsOutSegmentTopLabel will
         be set to the proper value."
       ::=  { rsMPLSXCExtEntry 2 }

rsMPLSXCDetourXC OBJECT-TYPE
       SYNTAX   RowPointer
       MAX-ACCESS  read-only
       STATUS      current
       DESCRIPTION
        "A pointer to a conceptual row in the mplsXCTable.

         This object is set to the ZeroDotZero OID by default.  Whenever
         the LSP identified by this cross-connect uses a detour, this
         object is set to point to the cross-connect which acts as a
         detour for this LSP.  At this time, the rsMPLSExtOperStatus
         will set to the value of rerouted (8)."
       ::=  { rsMPLSXCExtEntry 3 }

rsMPLSXCSecondaryXC OBJECT-TYPE
       SYNTAX   RowPointer
       MAX-ACCESS  read-only
       STATUS      current
       DESCRIPTION
        "A pointer to a conceptual row in the mplsXCTable.

         This object is set to the ZeroDotZero OID by default.  This
         object is valid only in case of Ingress LSRs.

         If the LSP identified by this cross-connect is a primary, and 
         when this LSP goes down, and if there is a secondary LSP, this
         cross-connect is not torn down.  In stead, the mplsXCOperStatus
         will be set to down, the mplsOutSegmentTopLabel identified by
         the out segment of the cross-connect is set to 0 (invalid label).
         At this time, this object is set to point to the cross-connect
         which acts as the secondary LSP.

         Note that, this is the last resort.  First the mpls engine will
         try to use a detour.  If no detours are configured or up, then
         only will it use the secondary LSP."
       ::=  { rsMPLSXCExtEntry 4 }


--  Notifications

rsMPLSEnableNotifications  OBJECT-TYPE
       SYNTAX  TruthValue
       MAX-ACCESS  read-write
       STATUS      current
       DESCRIPTION
        "When this object is set to True(1), the notifications will be sent
         out depending upon the events.  If set to False(2), the 
         notifications will not go out.  By default, the notifications are
         disabled. "                                
       DEFVAL { false }
       ::=  { rsMPLSNotificationControl 1 }

rsMPLSPrimaryPathFailOver NOTIFICATION-TYPE
       OBJECTS  {
         rsMPLSXCExtendedOperStatus,
         rsMPLSXCExtendedOperStatus
                }
       STATUS      current
       DESCRIPTION
        "This notification is generated when the primary LSP goes down and
         the secondary path (if any) takes over.  First the Fast Reroute
         mecahnism will try to use the primary path.  For this event, fast
         reroute notification will be generated.  If this does not exist
         or if this also fails, then only will this notification will be
         generated and the seconday path will take over.

         The variables included are the operational status of the primary
         path that failed and the secondary path that took over.

         This notificiation is generated by the ingress-router of the LSP."
       ::=  { rsMPLSNotifyPrefix 1 }

rsMPLSPrimaryPathTakeOver NOTIFICATION-TYPE
       OBJECTS  {
         rsMPLSXCExtendedOperStatus
                }
       STATUS      current
       DESCRIPTION
        "This notification is generated when the primary LSP comes back
         up and takes over from the secondary path.

         This notificiation is generated by the ingress-router of the LSP."
       ::=  { rsMPLSNotifyPrefix 2 }

rsMPLSStartedDetourUse NOTIFICATION-TYPE
       OBJECTS  {
         rsMPLSXCExtendedOperStatus,
         rsMPLSXCExtendedOperStatus
                }
       STATUS      current
       DESCRIPTION
        "This notification is generated when the Detour LSP is used to
         circumvent the next hop in the LSP.  

         The objects included are the OperationalStatus of the 
         cross-connect of the original LSP and the operational status of
         the detour LSP being used.

         This notificiation is generated by the ingress-router of the 
         detour LSP."
       ::=  { rsMPLSNotifyPrefix 3 }

rsMPLSEndedDetourUse NOTIFICATION-TYPE
       OBJECTS  {
         rsMPLSXCExtendedOperStatus
                }
       STATUS      current
       DESCRIPTION
        "This notification is generated when the original next hop is
         reachable, and the regular path is used.  At this point the
         the data will go through the regular next hop.

         The object included is the OperationalStatus of the 
         cross-connect of the original LSP.

         This notificiation is generated by the ingress-router of the 
         detour LSP."
       ::=  { rsMPLSNotifyPrefix 4 }

rsMPLSLSPPreempted NOTIFICATION-TYPE
       OBJECTS  {
         rsMPLSXCExtendedOperStatus,
         rsMPLSXCExtendedOperStatus
                }
       STATUS      current
       DESCRIPTION
        "This notification is generated when a higher priority LSP
         pre-empts and tears down a lower priority LSP.  The lower 
         priority LSP then can use a detour or go down.

         The objects included are the OperationalStatus of the 
         cross-connect of the higher priority LSP and that of the lower
         priority LSP.

         This notificiation is generated by the hop of the LSP where the
         pre-emption takes place."
       ::=  { rsMPLSNotifyPrefix 5 }

-- Conformance statements
rsMPLSConformance OBJECT IDENTIFIER ::=  { rsMPLSMIB 3 }
rsMPLSCompliances OBJECT IDENTIFIER ::=  { rsMPLSConformance 1 }
rsMPLSGroups      OBJECT IDENTIFIER ::=  { rsMPLSConformance 2 }
 
rsMPLSCompliance MODULE-COMPLIANCE
    STATUS  current
    DESCRIPTION
            "The compliance statement for SNMP entities which implement
            the Riverstone Router Config Management MIB."
    MODULE  -- this module
        MANDATORY-GROUPS { rsMPLSLSRExtensionGroup }

    ::=  { rsMPLSCompliances 1 }


-- MIB groupings
 
rsMPLSLSRExtensionGroup OBJECT-GROUP
    OBJECTS { rsMPLSXCExtendedOperStatus,
              rsMPLSXCDetourXC,
              rsMPLSXCSecondaryXC
}
                    
    STATUS  current
    DESCRIPTION
     "The collection of objects which are extended from MPLS-LSR-MIB."
   ::=  { rsMPLSGroups 1 }

rsMPLSNotificationGroup NOTIFICATION-GROUP
    NOTIFICATIONS { rsMPLSPrimaryPathFailOver,
                    rsMPLSPrimaryPathTakeOver,
                    rsMPLSStartedDetourUse,
                    rsMPLSEndedDetourUse,
                    rsMPLSLSPPreempted 
}
    STATUS  current
    DESCRIPTION
     "Set of notifications implemented in this module."
   ::=  { rsMPLSGroups 2 }

rsMPLSNotificationControlGroup OBJECT-GROUP
    OBJECTS { rsMPLSEnableNotifications }
                    
    STATUS  current
    DESCRIPTION
     "This object is mandatory to control emission of notifications,
      when the SNMP-NOTIFICATION-MIB is not available in a given agent."
   ::=  { rsMPLSGroups 3 }

END
