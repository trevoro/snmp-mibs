-- 3COM IWFG MIB 
-- MIB File Generated on 14-Dec-1998 at 17:16:18

IWFG-MIB DEFINITIONS ::= BEGIN

IMPORTS
   enterprises,
   IpAddress,
   Counter
      FROM RFC1155-SMI
   DisplayString
      FROM RFC1213-MIB
   OBJECT-TYPE
      FROM RFC-1212;


usr OBJECT IDENTIFIER ::= { enterprises 429 }

nas OBJECT IDENTIFIER ::= { usr 1 }

iwfGWY OBJECT IDENTIFIER ::= { nas 25 }

-- The Gateway Frame Relay LMI confiuration Group

iwfCfgFrRly OBJECT IDENTIFIER ::= { iwfGWY 1 }

iwfCfgFrRlyTable OBJECT-TYPE
SYNTAX SEQUENCE OF IwfCfgFrRlyEntry
ACCESS not-accessible
STATUS mandatory
DESCRIPTION
"Table containing objects for configuring Frame Relay Local 
management Interface parameters for the  Gateway Cards in 
the chassis."
::= { iwfCfgFrRly 1 }

iwfCfgFrRlyEntry OBJECT-TYPE
SYNTAX IwfCfgFrRlyEntry
ACCESS not-accessible
STATUS mandatory
DESCRIPTION
"There is one Configuration row for each Gateway Card in the 
NAS chassis."
INDEX { iwfCfgFrRlyIndex }
::= { iwfCfgFrRlyTable 1 }

IwfCfgFrRlyEntry ::=
SEQUENCE {
iwfCfgFrRlyIndex
    INTEGER,
iwfCfgFrRlyT391StatusEnqryTimr
    INTEGER,
iwfCfgFrRlyT392StatusTimer
    INTEGER,
iwfCfgFrRlyN391StatusEnqrySent
    INTEGER
}

iwfCfgFrRlyIndex OBJECT-TYPE
SYNTAX INTEGER
ACCESS read-only
STATUS mandatory
DESCRIPTION
"A unique index identifying the Gateway Card to which the 
Frame Relay LMI configuration table objects pertain"
::= { iwfCfgFrRlyEntry 1 }

iwfCfgFrRlyT391StatusEnqryTimr OBJECT-TYPE
SYNTAX INTEGER
ACCESS read-write
STATUS mandatory
DESCRIPTION
"This object configures the T391 Status Enquiry Timer. "
::= { iwfCfgFrRlyEntry 2 }

iwfCfgFrRlyT392StatusTimer OBJECT-TYPE
SYNTAX INTEGER
ACCESS read-write
STATUS mandatory
DESCRIPTION
"This object configure the T392 status timer."
::= { iwfCfgFrRlyEntry 3 }

iwfCfgFrRlyN391StatusEnqrySent OBJECT-TYPE
SYNTAX INTEGER
ACCESS read-write
STATUS mandatory
DESCRIPTION
"This object configure the N391 number of status enquiry 
sent."
::= { iwfCfgFrRlyEntry 4 }

-- The Q921 configuration Group

iwfCfgQ921 OBJECT IDENTIFIER ::= { iwfGWY 2 }

iwfCfgQ921Table OBJECT-TYPE
SYNTAX SEQUENCE OF IwfCfgQ921Entry
ACCESS not-accessible
STATUS mandatory
DESCRIPTION
"Table containing objects for Q.921 parameter Configuration 
for wireless Gateway Cards in the chassis."
::= { iwfCfgQ921 1 }

iwfCfgQ921Entry OBJECT-TYPE
SYNTAX IwfCfgQ921Entry
ACCESS not-accessible
STATUS mandatory
DESCRIPTION
"There is one Configuration row for each Gateway Card in the 
NAS chassis."
INDEX { iwfCfgQ921Index }
::= { iwfCfgQ921Table 1 }

IwfCfgQ921Entry ::=
SEQUENCE {
iwfCfgQ921Index
    INTEGER,
iwfCfgQ921KmaxOutStandPkt
    INTEGER,
iwfCfgQ921T200IframeAckTimer
    INTEGER,
iwfCfgQ921T203MaxTimeNoIframe
    INTEGER,
iwfCfgQ921N200MaxFrameRetrans
    INTEGER,
iwfCfgQ921N201RxMaxOctetInfo
    INTEGER,
iwfCfgQ921N201TxMaxOctetInfo
    INTEGER
}

iwfCfgQ921Index OBJECT-TYPE
SYNTAX INTEGER
ACCESS read-only
STATUS mandatory
DESCRIPTION
"A unique index identifying the Gateway Card to which the 
Q.921 Frame Relay Call Control configure Table objects 
pertain."
::= { iwfCfgQ921Entry 1 }

iwfCfgQ921KmaxOutStandPkt OBJECT-TYPE
SYNTAX INTEGER
ACCESS read-write
STATUS mandatory
DESCRIPTION
"This object configure K-Max # of outstanding packets. "
::= { iwfCfgQ921Entry 2 }

iwfCfgQ921T200IframeAckTimer OBJECT-TYPE
SYNTAX INTEGER
ACCESS read-write
STATUS mandatory
DESCRIPTION
"This object configures the T200 I-frame Ack Timer. "
::= { iwfCfgQ921Entry 3 }

iwfCfgQ921T203MaxTimeNoIframe OBJECT-TYPE
SYNTAX INTEGER
ACCESS read-write
STATUS mandatory
DESCRIPTION
"This object configures the T203 max time with no I-frame 
Exchange. "
::= { iwfCfgQ921Entry 4 }

iwfCfgQ921N200MaxFrameRetrans OBJECT-TYPE
SYNTAX INTEGER
ACCESS read-write
STATUS mandatory
DESCRIPTION
"This object configures the N200 max number of 
retransmissions of frame. "
::= { iwfCfgQ921Entry 5 }

iwfCfgQ921N201RxMaxOctetInfo OBJECT-TYPE
SYNTAX INTEGER
ACCESS read-write
STATUS mandatory
DESCRIPTION
"This object configures the N200 Received Max number of 
Octets in info field. "
::= { iwfCfgQ921Entry 6 }

iwfCfgQ921N201TxMaxOctetInfo OBJECT-TYPE
SYNTAX INTEGER
ACCESS read-write
STATUS mandatory
DESCRIPTION
"This object configures the N200 Transmitted Max number of 
Octets in info field. "
::= { iwfCfgQ921Entry 7 }

-- The Q933 configuration Group

iwfCfgQ933 OBJECT IDENTIFIER ::= { iwfGWY 3 }

iwfCfgQ933Table OBJECT-TYPE
SYNTAX SEQUENCE OF IwfCfgQ933Entry
ACCESS not-accessible
STATUS mandatory
DESCRIPTION
"Table containing objects for configuring Q.933 parameter 
for IWF Gateway Cards in the chassis."
::= { iwfCfgQ933 1 }

iwfCfgQ933Entry OBJECT-TYPE
SYNTAX IwfCfgQ933Entry
ACCESS not-accessible
STATUS mandatory
DESCRIPTION
"There is one Configuration row for each Gateway Card in the 
NAS chassis."
INDEX { iwfCfgQ933Index }
::= { iwfCfgQ933Table 1 }

IwfCfgQ933Entry ::=
SEQUENCE {
iwfCfgQ933Index
    INTEGER,
iwfCfgQ933T303SetupTimer
    INTEGER,
iwfCfgQ933T305DisconnectTimer
    INTEGER,
iwfCfgQ933T308ReleaseTimer
    INTEGER,
iwfCfgQ933T309DataLinkDiscTimr
    INTEGER,
iwfCfgQ933T310CallProceedTimer
    INTEGER,
iwfCfgQ933T313ConnectSentTimer
    INTEGER
}

iwfCfgQ933Index OBJECT-TYPE
SYNTAX INTEGER
ACCESS read-only
STATUS mandatory
DESCRIPTION
"A unique index identifying the Gateway Card to which the 
Q.933 table objects pertain"
::= { iwfCfgQ933Entry 1 }

iwfCfgQ933T303SetupTimer OBJECT-TYPE
SYNTAX INTEGER
ACCESS read-write
STATUS mandatory
DESCRIPTION
"This object configures T303- setup timer. "
::= { iwfCfgQ933Entry 2 }

iwfCfgQ933T305DisconnectTimer OBJECT-TYPE
SYNTAX INTEGER
ACCESS read-write
STATUS mandatory
DESCRIPTION
"This object configures T305- Desconnect. "
::= { iwfCfgQ933Entry 3 }

iwfCfgQ933T308ReleaseTimer OBJECT-TYPE
SYNTAX INTEGER
ACCESS read-write
STATUS mandatory
DESCRIPTION
"This object configures T308- Release Timer. "
::= { iwfCfgQ933Entry 4 }

iwfCfgQ933T309DataLinkDiscTimr OBJECT-TYPE
SYNTAX INTEGER
ACCESS read-write
STATUS mandatory
DESCRIPTION
"This object configures T309- Data Link Disconnection 
Timer."
::= { iwfCfgQ933Entry 5 }

iwfCfgQ933T310CallProceedTimer OBJECT-TYPE
SYNTAX INTEGER
ACCESS read-write
STATUS mandatory
DESCRIPTION
"This object configures T310- Call proceeding timer. "
::= { iwfCfgQ933Entry 6 }

iwfCfgQ933T313ConnectSentTimer OBJECT-TYPE
SYNTAX INTEGER
ACCESS read-write
STATUS mandatory
DESCRIPTION
"This object configures T313- Connect sent timer. "
::= { iwfCfgQ933Entry 7 }

iwfCfgCallStats OBJECT IDENTIFIER ::= { iwfGWY 4 }

iwfCfgCallStatsTable OBJECT-TYPE
SYNTAX SEQUENCE OF IwfCfgCallStatsEntry
ACCESS not-accessible
STATUS mandatory
DESCRIPTION
"Table containing objects for configuring Call Statistics 
parameter for IWF Gateway Cards in the chassis."
::= { iwfCfgCallStats 1 }

iwfCfgCallStatsEntry OBJECT-TYPE
SYNTAX IwfCfgCallStatsEntry
ACCESS not-accessible
STATUS mandatory
DESCRIPTION
"There is one Configuration row for each Gateway Card in the 
NAS chassis."
INDEX { iwfCfgCsIndex }
::= { iwfCfgCallStatsTable 1 }

IwfCfgCallStatsEntry ::=
SEQUENCE {
iwfCfgCsIndex
    INTEGER,
iwfCfgCsMobOrigAdStats
    INTEGER,
iwfCfgCsMobOrigFaxStats
    INTEGER,
iwfCfgCsMobTermAdStats
    INTEGER,
iwfCfgCsMobTermFaxStats
    INTEGER,
iwfCfgCsLogStartTrapEna
    INTEGER,
iwfCfgCsLogTermTrapEna
    INTEGER
}

iwfCfgCsIndex OBJECT-TYPE
SYNTAX INTEGER
ACCESS read-only
STATUS mandatory
DESCRIPTION
"A unique index identifying the Gateway Card to which the 
Call Statistics configuration table objects pertain"
::= { iwfCfgCallStatsEntry 1 }

iwfCfgCsMobOrigAdStats OBJECT-TYPE
SYNTAX INTEGER{
  enable(1),
  disable(2)
}
ACCESS read-write
STATUS mandatory
DESCRIPTION
"This object allows to enable/disable the collection of All 
Mobile Originated AD Statistics."
::= { iwfCfgCallStatsEntry 2 }

iwfCfgCsMobOrigFaxStats OBJECT-TYPE
SYNTAX INTEGER{
  enable(1),
  disable(2)
}
ACCESS read-write
STATUS mandatory
DESCRIPTION
"This object allows to enable/disable the collection of All 
Mobile Originated FAX Statistics."
::= { iwfCfgCallStatsEntry 3 }

iwfCfgCsMobTermAdStats OBJECT-TYPE
SYNTAX INTEGER{
  enable(1),
  disable(2)
}
ACCESS read-write
STATUS mandatory
DESCRIPTION
"This object allows to enable/disable the collection of All 
Mobile Terminated AD Statistics."
::= { iwfCfgCallStatsEntry 4 }

iwfCfgCsMobTermFaxStats OBJECT-TYPE
SYNTAX INTEGER{
  enable(1),
  disable(2)
}
ACCESS read-write
STATUS mandatory
DESCRIPTION
"This object allows to enable/disable the collection of All 
Mobile Terminated FAX Statistics."
::= { iwfCfgCallStatsEntry 5 }

iwfCfgCsLogStartTrapEna OBJECT-TYPE
SYNTAX INTEGER{
  enableTraps(1),
  disableAll(2),
  enableLogs(3),
  enableAll(4)
}
ACCESS read-write
STATUS mandatory
DESCRIPTION
"This is to enable the call log start stats trap and 
radius."
::= { iwfCfgCallStatsEntry 6 }

iwfCfgCsLogTermTrapEna OBJECT-TYPE
SYNTAX INTEGER{
  enableTraps(1),
  disableAll(2),
  enableLogs(3),
  enableAll(4)
}
ACCESS read-write
STATUS mandatory
DESCRIPTION
"This is to enable the call log termination stats trap and 
radius."
::= { iwfCfgCallStatsEntry 7 }

iwfCfgPppParam OBJECT IDENTIFIER ::= { iwfGWY 5 }

iwfCfgPppParamTable OBJECT-TYPE
SYNTAX SEQUENCE OF IwfCfgPppParamEntry
ACCESS not-accessible
STATUS mandatory
DESCRIPTION
"Table containing objects for configuring PPP parameter for 
IWF Gateway Cards in the chassis."
::= { iwfCfgPppParam 1 }

iwfCfgPppParamEntry OBJECT-TYPE
SYNTAX IwfCfgPppParamEntry
ACCESS not-accessible
STATUS mandatory
DESCRIPTION
"There is one Configuration row for each Gateway Card in the 
NAS chassis."
INDEX { iwfCfgPppIndex }
::= { iwfCfgPppParamTable 1 }

IwfCfgPppParamEntry ::=
SEQUENCE {
iwfCfgPppIndex
    INTEGER,
iwfCfgPppForceEncryptData
    INTEGER,
iwfCfgPppForceEncryptpassword
    INTEGER,
iwfCfgPppMaxNumbConfigRequests
    INTEGER,
iwfCfgPppMaxNumbConfigNAK
    INTEGER,
iwfCfgPppMaxNumbRejects
    INTEGER,
iwfCfgPppMaxNumbTermRequests
    INTEGER,
iwfCfgPppNegotiateTime
    INTEGER,
iwfCfgPppRestartTime
    INTEGER,
iwfCfgPppIpAddressPoolMax
    IpAddress,
iwfCfgPppIpAddressPoolMin
    IpAddress
}

iwfCfgPppIndex OBJECT-TYPE
SYNTAX INTEGER
ACCESS read-only
STATUS mandatory
DESCRIPTION
"A unique index identifying the Gateway Card to which the 
PPP configuration table objects pertain"
::= { iwfCfgPppParamEntry 1 }

iwfCfgPppForceEncryptData OBJECT-TYPE
SYNTAX INTEGER
ACCESS read-write
STATUS mandatory
DESCRIPTION
"This object is used to control sending of encrypted data."
::= { iwfCfgPppParamEntry 2 }

iwfCfgPppForceEncryptpassword OBJECT-TYPE
SYNTAX INTEGER
ACCESS read-write
STATUS mandatory
DESCRIPTION
"This object is used to control PPP Authentication."
::= { iwfCfgPppParamEntry 3 }

iwfCfgPppMaxNumbConfigRequests OBJECT-TYPE
SYNTAX INTEGER
ACCESS read-write
STATUS mandatory
DESCRIPTION
"This object configures the max number of Config Requests 
allowed without receiving a valid configure-Ack."
::= { iwfCfgPppParamEntry 4 }

iwfCfgPppMaxNumbConfigNAK OBJECT-TYPE
SYNTAX INTEGER
ACCESS read-write
STATUS mandatory
DESCRIPTION
"This object is for Max number of configure-Nak without 
sending a configure-Ack."
::= { iwfCfgPppParamEntry 5 }

iwfCfgPppMaxNumbRejects OBJECT-TYPE
SYNTAX INTEGER
ACCESS read-write
STATUS mandatory
DESCRIPTION
"This object is Max number of configure-rejects before 
assuming PPP negotiation failed."
::= { iwfCfgPppParamEntry 6 }

iwfCfgPppMaxNumbTermRequests OBJECT-TYPE
SYNTAX INTEGER
ACCESS read-write
STATUS mandatory
DESCRIPTION
"This object is Max number of Terminate-Request without 
receiving a Terminate-Ack."
::= { iwfCfgPppParamEntry 7 }

iwfCfgPppNegotiateTime OBJECT-TYPE
SYNTAX INTEGER
ACCESS read-write
STATUS mandatory
DESCRIPTION
"This object is Max Time allowed for PPP negotiation."
::= { iwfCfgPppParamEntry 8 }

iwfCfgPppRestartTime OBJECT-TYPE
SYNTAX INTEGER
ACCESS read-write
STATUS mandatory
DESCRIPTION
"This object is Max Time allowed for PPP Restart."
::= { iwfCfgPppParamEntry 9 }

iwfCfgPppIpAddressPoolMax OBJECT-TYPE
SYNTAX IpAddress
ACCESS read-write
STATUS mandatory
DESCRIPTION
"This object is to define the Max range of the Ip addresses 
used by PPP to dynamically allocate IP addresses."
::= { iwfCfgPppParamEntry 10 }

iwfCfgPppIpAddressPoolMin OBJECT-TYPE
SYNTAX IpAddress
ACCESS read-write
STATUS mandatory
DESCRIPTION
"This object is to define the Min range of the Ip addresses 
used by PPP to dynamically allocate IP addresses."
::= { iwfCfgPppParamEntry 11 }

iwfCfgTcpIp OBJECT IDENTIFIER ::= { iwfGWY 6 }

iwfCfgTcpIpTable OBJECT-TYPE
SYNTAX SEQUENCE OF IwfCfgTcpIpEntry
ACCESS not-accessible
STATUS mandatory
DESCRIPTION
"Table containing objects for configuring TCP/IP parameter 
for IWF Gateway Cards in the chassis."
::= { iwfCfgTcpIp 1 }

iwfCfgTcpIpEntry OBJECT-TYPE
SYNTAX IwfCfgTcpIpEntry
ACCESS not-accessible
STATUS mandatory
DESCRIPTION
"There is one Configuration row for each Gateway Card in the 
NAS chassis."
INDEX { iwfCfgTiIndex }
::= { iwfCfgTcpIpTable 1 }

IwfCfgTcpIpEntry ::=
SEQUENCE {
iwfCfgTiIndex
    INTEGER,
iwfCfgTiDefaultServiceType
    INTEGER,
iwfCfgTiDefaultTimeToLive
    INTEGER,
iwfCfgTiMtuDiscovery
    INTEGER,
iwfCfgTiKeepAliveInterval
    INTEGER,
iwfCfgTiKeepAliveTime
    INTEGER,
iwfCfgTiMaxMtuSize
    INTEGER,
iwfCfgTiMaxConnectReTrans
    INTEGER,
iwfCfgTiMaxDataRetrans
    INTEGER,
iwfCfgTiMaxNumberConnections
    INTEGER,
iwfCfgTiWindowSize
    INTEGER,
iwfCfgTiLocalIpAddress
    IpAddress,
iwfCfgTiSubnetIpMask
    IpAddress,
iwfCfgTiDefualtGatewayIp
    IpAddress
}

iwfCfgTiIndex OBJECT-TYPE
SYNTAX INTEGER
ACCESS read-only
STATUS mandatory
DESCRIPTION
"A unique index identifying the Gateway Card to which the 
TCP/IP configuration table objects pertain"
::= { iwfCfgTcpIpEntry 1 }

iwfCfgTiDefaultServiceType OBJECT-TYPE
SYNTAX INTEGER (0..255)
ACCESS read-write
STATUS mandatory
DESCRIPTION
"This object is for Default Service type it is defined in 
RFC 791."
::= { iwfCfgTcpIpEntry 2 }

iwfCfgTiDefaultTimeToLive OBJECT-TYPE
SYNTAX INTEGER (1..255)
ACCESS read-write
STATUS mandatory
DESCRIPTION
"This object is the Max time an IP packet can live in the 
network without reaching its destination."
::= { iwfCfgTcpIpEntry 3 }

iwfCfgTiMtuDiscovery OBJECT-TYPE
SYNTAX INTEGER
ACCESS read-write
STATUS mandatory
DESCRIPTION
"This object allows discovery of the Maximum Transmission 
Unit over path to remote destination."
::= { iwfCfgTcpIpEntry 4 }

iwfCfgTiKeepAliveInterval OBJECT-TYPE
SYNTAX INTEGER
ACCESS read-write
STATUS mandatory
DESCRIPTION
"This object is the Interval separating Keep Alive 
Retransmissions."
::= { iwfCfgTcpIpEntry 5 }

iwfCfgTiKeepAliveTime OBJECT-TYPE
SYNTAX INTEGER
ACCESS read-write
STATUS mandatory
DESCRIPTION
"This object is how often TCP verifies that an idle 
connection is still intact."
::= { iwfCfgTcpIpEntry 6 }

iwfCfgTiMaxMtuSize OBJECT-TYPE
SYNTAX INTEGER
ACCESS read-write
STATUS mandatory
DESCRIPTION
"This object overrides the default MTU for a network 
interface."
::= { iwfCfgTcpIpEntry 7 }

iwfCfgTiMaxConnectReTrans OBJECT-TYPE
SYNTAX INTEGER
ACCESS read-write
STATUS mandatory
DESCRIPTION
"This object is the number of times TCP retransmits a 
Connect Request (SYN) before aborting the attempt."
::= { iwfCfgTcpIpEntry 8 }

iwfCfgTiMaxDataRetrans OBJECT-TYPE
SYNTAX INTEGER
ACCESS read-write
STATUS mandatory
DESCRIPTION
"This object is the number of times TCP retransmits an 
individual data segment before aborting the attempt."
::= { iwfCfgTcpIpEntry 9 }

iwfCfgTiMaxNumberConnections OBJECT-TYPE
SYNTAX INTEGER
ACCESS read-write
STATUS mandatory
DESCRIPTION
"This object configures the Max number of open TCP 
connection."
::= { iwfCfgTcpIpEntry 10 }

iwfCfgTiWindowSize OBJECT-TYPE
SYNTAX INTEGER
ACCESS read-write
STATUS mandatory
DESCRIPTION
"This object configures the receive window size."
::= { iwfCfgTcpIpEntry 11 }

iwfCfgTiLocalIpAddress OBJECT-TYPE
SYNTAX IpAddress
ACCESS read-write
STATUS mandatory
DESCRIPTION
"This object is the IP address of the EdgeServer."
::= { iwfCfgTcpIpEntry 12 }

iwfCfgTiSubnetIpMask OBJECT-TYPE
SYNTAX IpAddress
ACCESS read-write
STATUS mandatory
DESCRIPTION
"This object Subnet Mask of the EdgeServer."
::= { iwfCfgTcpIpEntry 13 }

iwfCfgTiDefualtGatewayIp OBJECT-TYPE
SYNTAX IpAddress
ACCESS read-write
STATUS mandatory
DESCRIPTION
"This object is the IP address of Gateway Router."
::= { iwfCfgTcpIpEntry 14 }

iwfEthernetNicStat OBJECT IDENTIFIER ::= { iwfGWY 7 }

iwfEthernetNicStatTable OBJECT-TYPE
SYNTAX SEQUENCE OF IwfEthernetNicStatEntry
ACCESS not-accessible
STATUS mandatory
DESCRIPTION
"Table containing objects for Ethernet Nic statistics for 
IWF Gateway Cards in the chassis."
::= { iwfEthernetNicStat 1 }

iwfEthernetNicStatEntry OBJECT-TYPE
SYNTAX IwfEthernetNicStatEntry
ACCESS not-accessible
STATUS mandatory
DESCRIPTION
"There is one Configuration row for each Gateway Card in the 
NAS chassis."
INDEX { iwfEnsIndex }
::= { iwfEthernetNicStatTable 1 }

IwfEthernetNicStatEntry ::=
SEQUENCE {
iwfEnsIndex
    INTEGER,
iwfEnsPacketsRxPerSec
    Counter,
iwfEnsPacketsTxPerSec
    Counter,
iwfEnsBytesRxPerSec
    Counter,
iwfEnsBytesTxPerSec
    Counter,
iwfEnsPacketsRxErrors
    Counter,
iwfEnsPacketsRxUnknown
    Counter,
iwfEnsPacketsOutBoundDiscarded
    Counter,
iwfEnsPacketsOutBoundErrors
    Counter,
iwfEnsOutputQueueLength
    Counter
}

iwfEnsIndex OBJECT-TYPE
SYNTAX INTEGER
ACCESS read-only
STATUS mandatory
DESCRIPTION
"A unique index identifying the Gateway Card to which the 
Ethernet Nic Statistics objects pertain"
::= { iwfEthernetNicStatEntry 1 }

iwfEnsPacketsRxPerSec OBJECT-TYPE
SYNTAX Counter
ACCESS read-only
STATUS mandatory
DESCRIPTION
"This object is the packets received per second."
::= { iwfEthernetNicStatEntry 2 }

iwfEnsPacketsTxPerSec OBJECT-TYPE
SYNTAX Counter
ACCESS read-only
STATUS mandatory
DESCRIPTION
"This object is the packets sent per second."
::= { iwfEthernetNicStatEntry 3 }

iwfEnsBytesRxPerSec OBJECT-TYPE
SYNTAX Counter
ACCESS read-only
STATUS mandatory
DESCRIPTION
"This object is the bytes received per second."
::= { iwfEthernetNicStatEntry 4 }

iwfEnsBytesTxPerSec OBJECT-TYPE
SYNTAX Counter
ACCESS read-only
STATUS mandatory
DESCRIPTION
"This object is the bytes sent per second."
::= { iwfEthernetNicStatEntry 5 }

iwfEnsPacketsRxErrors OBJECT-TYPE
SYNTAX Counter
ACCESS read-only
STATUS mandatory
DESCRIPTION
"This object is the Packets received Errors."
::= { iwfEthernetNicStatEntry 6 }

iwfEnsPacketsRxUnknown OBJECT-TYPE
SYNTAX Counter
ACCESS read-only
STATUS mandatory
DESCRIPTION
"This object is the Packets received Unknown."
::= { iwfEthernetNicStatEntry 7 }

iwfEnsPacketsOutBoundDiscarded OBJECT-TYPE
SYNTAX Counter
ACCESS read-only
STATUS mandatory
DESCRIPTION
"This object is the Packets out-bound discarded."
::= { iwfEthernetNicStatEntry 8 }

iwfEnsPacketsOutBoundErrors OBJECT-TYPE
SYNTAX Counter
ACCESS read-only
STATUS mandatory
DESCRIPTION
"This object is the Packets out-bound Errors."
::= { iwfEthernetNicStatEntry 9 }

iwfEnsOutputQueueLength OBJECT-TYPE
SYNTAX Counter
ACCESS read-only
STATUS mandatory
DESCRIPTION
"This object is the Output Queue Length."
::= { iwfEthernetNicStatEntry 10 }

iwfIpStats OBJECT IDENTIFIER ::= { iwfGWY 8 }

iwfIpStatsTable OBJECT-TYPE
SYNTAX SEQUENCE OF IwfIpStatsEntry
ACCESS not-accessible
STATUS mandatory
DESCRIPTION
"Table containing objects for IP statistics for IWF Gateway 
Cards in the chassis."
::= { iwfIpStats 1 }

iwfIpStatsEntry OBJECT-TYPE
SYNTAX IwfIpStatsEntry
ACCESS not-accessible
STATUS mandatory
DESCRIPTION
"There is one Configuration row for each Gateway Card in the 
NAS chassis."
INDEX { iwfIsIndex }
::= { iwfIpStatsTable 1 }

IwfIpStatsEntry ::=
SEQUENCE {
iwfIsIndex
    INTEGER,
iwfIsPacketsRx
    Counter,
iwfIsRxHeaderErrors
    Counter,
iwfIsIpReceived
    Counter,
iwfIsDatagramsForwarded
    Counter,
iwfIsUnknownProtocolRx
    Counter,
iwfIsRxPacketsDiscarded
    Counter,
iwfIsRxPacketsDelivered
    Counter,
iwfIsOutputRequests
    Counter,
iwfIsRoutingDiscarded
    Counter,
iwfIsDiscardedOutputPackets
    Counter,
iwfIsOutputPacketsNoRoute
    Counter,
iwfIsReAssemblyRequired
    Counter,
iwfIsReAssemblySuccessful
    Counter,
iwfIsReAssmeblyFailures
    Counter,
iwfIsDatagramsSuccessFragment
    Counter,
iwfIsDatagramsFailFragment
    Counter,
iwfIsFragmentCreated
    Counter
}

iwfIsIndex OBJECT-TYPE
SYNTAX INTEGER
ACCESS read-only
STATUS mandatory
DESCRIPTION
"A unique index identifying the Gateway Card to which the IP 
Statistics objects pertain"
::= { iwfIpStatsEntry 1 }

iwfIsPacketsRx OBJECT-TYPE
SYNTAX Counter
ACCESS read-only
STATUS mandatory
DESCRIPTION
"This object is the packets received counter."
::= { iwfIpStatsEntry 2 }

iwfIsRxHeaderErrors OBJECT-TYPE
SYNTAX Counter
ACCESS read-only
STATUS mandatory
DESCRIPTION
"This Object is the reived header errors counter."
::= { iwfIpStatsEntry 3 }

iwfIsIpReceived OBJECT-TYPE
SYNTAX Counter
ACCESS read-only
STATUS mandatory
DESCRIPTION
"This Object is the IP received counter."
::= { iwfIpStatsEntry 4 }

iwfIsDatagramsForwarded OBJECT-TYPE
SYNTAX Counter
ACCESS read-only
STATUS mandatory
DESCRIPTION
"This Object is the datagrams forwarded counter."
::= { iwfIpStatsEntry 5 }

iwfIsUnknownProtocolRx OBJECT-TYPE
SYNTAX Counter
ACCESS read-only
STATUS mandatory
DESCRIPTION
"This Object is the unknown protocol received counter."
::= { iwfIpStatsEntry 6 }

iwfIsRxPacketsDiscarded OBJECT-TYPE
SYNTAX Counter
ACCESS read-only
STATUS mandatory
DESCRIPTION
"This Object is the received packets discarded counter."
::= { iwfIpStatsEntry 7 }

iwfIsRxPacketsDelivered OBJECT-TYPE
SYNTAX Counter
ACCESS read-only
STATUS mandatory
DESCRIPTION
"This Object is the received packets delivered counter."
::= { iwfIpStatsEntry 8 }

iwfIsOutputRequests OBJECT-TYPE
SYNTAX Counter
ACCESS read-only
STATUS mandatory
DESCRIPTION
"This Object is the output requests counter."
::= { iwfIpStatsEntry 9 }

iwfIsRoutingDiscarded OBJECT-TYPE
SYNTAX Counter
ACCESS read-only
STATUS mandatory
DESCRIPTION
"This Object is the routing discards counter."
::= { iwfIpStatsEntry 10 }

iwfIsDiscardedOutputPackets OBJECT-TYPE
SYNTAX Counter
ACCESS read-only
STATUS mandatory
DESCRIPTION
"This Object is the discarded output packeets counter."
::= { iwfIpStatsEntry 11 }

iwfIsOutputPacketsNoRoute OBJECT-TYPE
SYNTAX Counter
ACCESS read-only
STATUS mandatory
DESCRIPTION
"This Object is the output no route counter."
::= { iwfIpStatsEntry 12 }

iwfIsReAssemblyRequired OBJECT-TYPE
SYNTAX Counter
ACCESS read-only
STATUS mandatory
DESCRIPTION
"This Object is the re-assembly required counter."
::= { iwfIpStatsEntry 13 }

iwfIsReAssemblySuccessful OBJECT-TYPE
SYNTAX Counter
ACCESS read-only
STATUS mandatory
DESCRIPTION
"This Object is the re-assembly successful counter."
::= { iwfIpStatsEntry 14 }

iwfIsReAssmeblyFailures OBJECT-TYPE
SYNTAX Counter
ACCESS read-only
STATUS mandatory
DESCRIPTION
"This Object is the re-assembly failures counter."
::= { iwfIpStatsEntry 15 }

iwfIsDatagramsSuccessFragment OBJECT-TYPE
SYNTAX Counter
ACCESS read-only
STATUS mandatory
DESCRIPTION
"This Object is the datagrams successfully fragmented 
counter."
::= { iwfIpStatsEntry 16 }

iwfIsDatagramsFailFragment OBJECT-TYPE
SYNTAX Counter
ACCESS read-only
STATUS mandatory
DESCRIPTION
"This Object is the datagrams failing fragmentation 
counter."
::= { iwfIpStatsEntry 17 }

iwfIsFragmentCreated OBJECT-TYPE
SYNTAX Counter
ACCESS read-only
STATUS mandatory
DESCRIPTION
"This Object is the framents created counter."
::= { iwfIpStatsEntry 18 }

iwfIcmpStats OBJECT IDENTIFIER ::= { iwfGWY 9 }

iwfIcmpStatsTable OBJECT-TYPE
SYNTAX SEQUENCE OF IwfIcmpStatsEntry
ACCESS not-accessible
STATUS mandatory
DESCRIPTION
"Table containing objects for ICMP statistics for IWF 
Gateway Cards in the chassis."
::= { iwfIcmpStats 1 }

iwfIcmpStatsEntry OBJECT-TYPE
SYNTAX IwfIcmpStatsEntry
ACCESS not-accessible
STATUS mandatory
DESCRIPTION
"There is one Configuration row for each Gateway Card in the 
NAS chassis."
INDEX { iwfIcmpStIndex }
::= { iwfIcmpStatsTable 1 }

IwfIcmpStatsEntry ::=
SEQUENCE {
iwfIcmpStIndex
    INTEGER,
iwfIcmpStMessagesRx
    Counter,
iwfIcmpStMessagesTx
    Counter,
iwfIcmpStErrorsRx
    Counter,
iwfIcmpStErrorsTx
    Counter,
iwfIcmpStDestUnreachableTx
    Counter,
iwfIcmpStDestUnreachableRx
    Counter,
iwfIcmpStTimeExceededTx
    Counter,
iwfIcmpStTimeExceededRx
    Counter,
iwfIcmpStParameterProblemsTx
    Counter,
iwfIcmpStParameterProblemsRx
    Counter,
iwfIcmpStSourceQuenchsTx
    Counter,
iwfIcmpStSourceQuenchsRx
    Counter,
iwfIcmpStRedirectsTx
    Counter,
iwfIcmpStRedirectsRx
    Counter,
iwfIcmpStEchosTx
    Counter,
iwfIcmpStEchosRx
    Counter,
iwfIcmpStEchosRepliesTx
    Counter,
iwfIcmpStEchosRepliesRx
    Counter,
iwfIcmpStTimeStampsTx
    Counter,
iwfIcmpStTimeStampsRx
    Counter,
iwfIcmpStAddressMasksTx
    Counter,
iwfIcmpStAddressMasksRx
    Counter,
iwfIcmpStAddressMasksRepliesTx
    Counter,
iwfIcmpStAddressMasksRepliesRx
    Counter
}

iwfIcmpStIndex OBJECT-TYPE
SYNTAX INTEGER
ACCESS read-only
STATUS mandatory
DESCRIPTION
"A unique index identifying the Gateway Card to which the 
ICMP Statistics objects pertain"
::= { iwfIcmpStatsEntry 1 }

iwfIcmpStMessagesRx OBJECT-TYPE
SYNTAX Counter
ACCESS read-only
STATUS mandatory
DESCRIPTION
"This object is the ICMP messages received."
::= { iwfIcmpStatsEntry 2 }

iwfIcmpStMessagesTx OBJECT-TYPE
SYNTAX Counter
ACCESS read-only
STATUS mandatory
DESCRIPTION
"This object is the ICMP messages sent."
::= { iwfIcmpStatsEntry 3 }

iwfIcmpStErrorsRx OBJECT-TYPE
SYNTAX Counter
ACCESS read-only
STATUS mandatory
DESCRIPTION
"This object is the ICMP errors received."
::= { iwfIcmpStatsEntry 4 }

iwfIcmpStErrorsTx OBJECT-TYPE
SYNTAX Counter
ACCESS read-only
STATUS mandatory
DESCRIPTION
"This object is the ICMP errors sent."
::= { iwfIcmpStatsEntry 5 }

iwfIcmpStDestUnreachableTx OBJECT-TYPE
SYNTAX Counter
ACCESS read-only
STATUS mandatory
DESCRIPTION
"This object is the ICMP destination unreachable sent."
::= { iwfIcmpStatsEntry 6 }

iwfIcmpStDestUnreachableRx OBJECT-TYPE
SYNTAX Counter
ACCESS read-only
STATUS mandatory
DESCRIPTION
"This object is the ICMP destination unreachable received."
::= { iwfIcmpStatsEntry 7 }

iwfIcmpStTimeExceededTx OBJECT-TYPE
SYNTAX Counter
ACCESS read-only
STATUS mandatory
DESCRIPTION
"This object is the ICMP time exceeded Sent."
::= { iwfIcmpStatsEntry 8 }

iwfIcmpStTimeExceededRx OBJECT-TYPE
SYNTAX Counter
ACCESS read-only
STATUS mandatory
DESCRIPTION
"This object is the ICMP time exceeded received."
::= { iwfIcmpStatsEntry 9 }

iwfIcmpStParameterProblemsTx OBJECT-TYPE
SYNTAX Counter
ACCESS read-only
STATUS mandatory
DESCRIPTION
"This object is the ICMP parameter problems sent."
::= { iwfIcmpStatsEntry 10 }

iwfIcmpStParameterProblemsRx OBJECT-TYPE
SYNTAX Counter
ACCESS read-only
STATUS mandatory
DESCRIPTION
"This object is the ICMP parameter problems received."
::= { iwfIcmpStatsEntry 11 }

iwfIcmpStSourceQuenchsTx OBJECT-TYPE
SYNTAX Counter
ACCESS read-only
STATUS mandatory
DESCRIPTION
"This object is the ICMP source quenchd sent."
::= { iwfIcmpStatsEntry 12 }

iwfIcmpStSourceQuenchsRx OBJECT-TYPE
SYNTAX Counter
ACCESS read-only
STATUS mandatory
DESCRIPTION
"This object is the ICMP source quenchd received."
::= { iwfIcmpStatsEntry 13 }

iwfIcmpStRedirectsTx OBJECT-TYPE
SYNTAX Counter
ACCESS read-only
STATUS mandatory
DESCRIPTION
"This object is the ICMP redirects sent."
::= { iwfIcmpStatsEntry 14 }

iwfIcmpStRedirectsRx OBJECT-TYPE
SYNTAX Counter
ACCESS read-only
STATUS mandatory
DESCRIPTION
"This object is the ICMP redirects received."
::= { iwfIcmpStatsEntry 15 }

iwfIcmpStEchosTx OBJECT-TYPE
SYNTAX Counter
ACCESS read-only
STATUS mandatory
DESCRIPTION
"This object is the ICMP echos sent."
::= { iwfIcmpStatsEntry 16 }

iwfIcmpStEchosRx OBJECT-TYPE
SYNTAX Counter
ACCESS read-only
STATUS mandatory
DESCRIPTION
"This object is the ICMP echos received."
::= { iwfIcmpStatsEntry 17 }

iwfIcmpStEchosRepliesTx OBJECT-TYPE
SYNTAX Counter
ACCESS read-only
STATUS mandatory
DESCRIPTION
"This object is the ICMP echos replies sent."
::= { iwfIcmpStatsEntry 18 }

iwfIcmpStEchosRepliesRx OBJECT-TYPE
SYNTAX Counter
ACCESS read-only
STATUS mandatory
DESCRIPTION
"This object is the ICMP echos replies received."
::= { iwfIcmpStatsEntry 19 }

iwfIcmpStTimeStampsTx OBJECT-TYPE
SYNTAX Counter
ACCESS read-only
STATUS mandatory
DESCRIPTION
"This object is the ICMP time-stamps sent."
::= { iwfIcmpStatsEntry 20 }

iwfIcmpStTimeStampsRx OBJECT-TYPE
SYNTAX Counter
ACCESS read-only
STATUS mandatory
DESCRIPTION
"This object is the ICMP time-stamps received."
::= { iwfIcmpStatsEntry 21 }

iwfIcmpStAddressMasksTx OBJECT-TYPE
SYNTAX Counter
ACCESS read-only
STATUS mandatory
DESCRIPTION
"This object is the ICMP address masks sent."
::= { iwfIcmpStatsEntry 22 }

iwfIcmpStAddressMasksRx OBJECT-TYPE
SYNTAX Counter
ACCESS read-only
STATUS mandatory
DESCRIPTION
"This object is the ICMP address masks received."
::= { iwfIcmpStatsEntry 23 }

iwfIcmpStAddressMasksRepliesTx OBJECT-TYPE
SYNTAX Counter
ACCESS read-only
STATUS mandatory
DESCRIPTION
"This object is the ICMP address masks replies sent."
::= { iwfIcmpStatsEntry 24 }

iwfIcmpStAddressMasksRepliesRx OBJECT-TYPE
SYNTAX Counter
ACCESS read-only
STATUS mandatory
DESCRIPTION
"This object is the ICMP address masks replies received."
::= { iwfIcmpStatsEntry 25 }

iwfTcpStats OBJECT IDENTIFIER ::= { iwfGWY 10 }

iwfTcpStatsTable OBJECT-TYPE
SYNTAX SEQUENCE OF IwfTcpStatsEntry
ACCESS not-accessible
STATUS mandatory
DESCRIPTION
"Table containing objects for TCP statistics for IWF Gateway 
Cards in the chassis."
::= { iwfTcpStats 1 }

iwfTcpStatsEntry OBJECT-TYPE
SYNTAX IwfTcpStatsEntry
ACCESS not-accessible
STATUS mandatory
DESCRIPTION
"There is one Configuration row for each Gateway Card in the 
NAS chassis."
INDEX { iwfTcpStIndex }
::= { iwfTcpStatsTable 1 }

IwfTcpStatsEntry ::=
SEQUENCE {
iwfTcpStIndex
    INTEGER,
iwfTcpStActiveOpens
    Counter,
iwfTcpStPassiveOpens
    Counter,
iwfTcpStFailedConnectAttempts
    Counter,
iwfTcpStResetConnections
    Counter,
iwfTcpStCurrentConnections
    Counter,
iwfTcpStSegmentRx
    Counter,
iwfTcpStSegmentTx
    Counter,
iwfTcpStSegmentRetransmitted
    Counter
}

iwfTcpStIndex OBJECT-TYPE
SYNTAX INTEGER
ACCESS read-only
STATUS mandatory
DESCRIPTION
"A unique index identifying the Gateway Card to which the 
TCP Statistics objects pertain"
::= { iwfTcpStatsEntry 1 }

iwfTcpStActiveOpens OBJECT-TYPE
SYNTAX Counter
ACCESS read-only
STATUS mandatory
DESCRIPTION
"This object is the TCP active opens."
::= { iwfTcpStatsEntry 2 }

iwfTcpStPassiveOpens OBJECT-TYPE
SYNTAX Counter
ACCESS read-only
STATUS mandatory
DESCRIPTION
"This object is the TCP passive opens."
::= { iwfTcpStatsEntry 3 }

iwfTcpStFailedConnectAttempts OBJECT-TYPE
SYNTAX Counter
ACCESS read-only
STATUS mandatory
DESCRIPTION
"This object is the TCP failed connection attempts."
::= { iwfTcpStatsEntry 4 }

iwfTcpStResetConnections OBJECT-TYPE
SYNTAX Counter
ACCESS read-only
STATUS mandatory
DESCRIPTION
"This object is the TCP reset connections."
::= { iwfTcpStatsEntry 5 }

iwfTcpStCurrentConnections OBJECT-TYPE
SYNTAX Counter
ACCESS read-only
STATUS mandatory
DESCRIPTION
"This object is the TCP current connections."
::= { iwfTcpStatsEntry 6 }

iwfTcpStSegmentRx OBJECT-TYPE
SYNTAX Counter
ACCESS read-only
STATUS mandatory
DESCRIPTION
"This object is the TCP segments received."
::= { iwfTcpStatsEntry 7 }

iwfTcpStSegmentTx OBJECT-TYPE
SYNTAX Counter
ACCESS read-only
STATUS mandatory
DESCRIPTION
"This object is the TCP segments sent."
::= { iwfTcpStatsEntry 8 }

iwfTcpStSegmentRetransmitted OBJECT-TYPE
SYNTAX Counter
ACCESS read-only
STATUS mandatory
DESCRIPTION
"This object is the TCP segments retransmitted."
::= { iwfTcpStatsEntry 9 }

iwfUdpStats OBJECT IDENTIFIER ::= { iwfGWY 11 }

iwfUdpStatsTable OBJECT-TYPE
SYNTAX SEQUENCE OF IwfUdpStatsEntry
ACCESS not-accessible
STATUS mandatory
DESCRIPTION
"Table containing objects for UDP statistics for IWF Gateway 
Cards in the chassis."
::= { iwfUdpStats 1 }

iwfUdpStatsEntry OBJECT-TYPE
SYNTAX IwfUdpStatsEntry
ACCESS not-accessible
STATUS mandatory
DESCRIPTION
"There is one Configuration row for each Gateway Card in the 
NAS chassis."
INDEX { iwfUdpStIndex }
::= { iwfUdpStatsTable 1 }

IwfUdpStatsEntry ::=
SEQUENCE {
iwfUdpStIndex
    INTEGER,
iwfUdpStDatagramRx
    Counter,
iwfUdpStDatagramNoPorts
    Counter,
iwfUdpStErrorsRx
    Counter,
iwfUdpStDatagramtx
    Counter
}

iwfUdpStIndex OBJECT-TYPE
SYNTAX INTEGER
ACCESS read-only
STATUS mandatory
DESCRIPTION
"A unique index identifying the Gateway Card to which the 
UDP Statistics objects pertain"
::= { iwfUdpStatsEntry 1 }

iwfUdpStDatagramRx OBJECT-TYPE
SYNTAX Counter
ACCESS read-only
STATUS mandatory
DESCRIPTION
"This objet is the UDP datagram received counter."
::= { iwfUdpStatsEntry 2 }

iwfUdpStDatagramNoPorts OBJECT-TYPE
SYNTAX Counter
ACCESS read-only
STATUS mandatory
DESCRIPTION
"This objet is the UDP datagram No ports counter."
::= { iwfUdpStatsEntry 3 }

iwfUdpStErrorsRx OBJECT-TYPE
SYNTAX Counter
ACCESS read-only
STATUS mandatory
DESCRIPTION
"This objet is the UDP errors received counter."
::= { iwfUdpStatsEntry 4 }

iwfUdpStDatagramtx OBJECT-TYPE
SYNTAX Counter
ACCESS read-only
STATUS mandatory
DESCRIPTION
"This objet is the UDP datagram sent counter."
::= { iwfUdpStatsEntry 5 }

iwfPppStats OBJECT IDENTIFIER ::= { iwfGWY 12 }

iwfPppStatsTable OBJECT-TYPE
SYNTAX SEQUENCE OF IwfPppStatsEntry
ACCESS not-accessible
STATUS mandatory
DESCRIPTION
"Table containing objects for PPP statistics for IWF Gateway 
Cards in the chassis."
::= { iwfPppStats 1 }

iwfPppStatsEntry OBJECT-TYPE
SYNTAX IwfPppStatsEntry
ACCESS not-accessible
STATUS mandatory
DESCRIPTION
"There is one Configuration row for each Gateway Card in the 
NAS chassis."
INDEX { iwfPppStIndex }
::= { iwfPppStatsTable 1 }

IwfPppStatsEntry ::=
SEQUENCE {
iwfPppStIndex
    INTEGER,
iwfPppStBytesTx
    Counter,
iwfPppStBytesRx
    Counter,
iwfPppStFramesTx
    Counter,
iwfPppStFramesRx
    Counter,
iwfPppStPercentCompressionOut
    Counter,
iwfPppStPercentCompressionIn
    Counter,
iwfPppStCrcErrors
    Counter,
iwfPppStAlignmentErrors
    Counter,
iwfPppStTimeOutErrors
    Counter,
iwfPppStTotalErrors
    Counter,
iwfPppStBytesTxPerSec
    Counter,
iwfPppStBytesRxPerSec
    Counter,
iwfPppStFramesTxPerSec
    Counter,
iwfPppStFramesRxPerSec
    Counter,
iwfPppStTotalErrorPerSec
    Counter,
iwfPppStTotalConnections
    Counter
}

iwfPppStIndex OBJECT-TYPE
SYNTAX INTEGER
ACCESS read-only
STATUS mandatory
DESCRIPTION
"A unique index identifying the Gateway Card to which the 
PPP Statistics objects pertain"
::= { iwfPppStatsEntry 1 }

iwfPppStBytesTx OBJECT-TYPE
SYNTAX Counter
ACCESS read-only
STATUS mandatory
DESCRIPTION
"This object is the PPP bytes transmitted."
::= { iwfPppStatsEntry 2 }

iwfPppStBytesRx OBJECT-TYPE
SYNTAX Counter
ACCESS read-only
STATUS mandatory
DESCRIPTION
"This object is the PPP bytes received."
::= { iwfPppStatsEntry 3 }

iwfPppStFramesTx OBJECT-TYPE
SYNTAX Counter
ACCESS read-only
STATUS mandatory
DESCRIPTION
"This object is the PPP frames transmitted."
::= { iwfPppStatsEntry 4 }

iwfPppStFramesRx OBJECT-TYPE
SYNTAX Counter
ACCESS read-only
STATUS mandatory
DESCRIPTION
"This object is the PPP frames received."
::= { iwfPppStatsEntry 5 }

iwfPppStPercentCompressionOut OBJECT-TYPE
SYNTAX Counter
ACCESS read-only
STATUS mandatory
DESCRIPTION
"This object is the PPP percent compressio out."
::= { iwfPppStatsEntry 6 }

iwfPppStPercentCompressionIn OBJECT-TYPE
SYNTAX Counter
ACCESS read-only
STATUS mandatory
DESCRIPTION
"This object is the PPP percent compressio in."
::= { iwfPppStatsEntry 7 }

iwfPppStCrcErrors OBJECT-TYPE
SYNTAX Counter
ACCESS read-only
STATUS mandatory
DESCRIPTION
"This object is the PPP CRC errors."
::= { iwfPppStatsEntry 8 }

iwfPppStAlignmentErrors OBJECT-TYPE
SYNTAX Counter
ACCESS read-only
STATUS mandatory
DESCRIPTION
"This object is the PPP alignment errors."
::= { iwfPppStatsEntry 9 }

iwfPppStTimeOutErrors OBJECT-TYPE
SYNTAX Counter
ACCESS read-only
STATUS mandatory
DESCRIPTION
"This object is the PPP time-out errors."
::= { iwfPppStatsEntry 10 }

iwfPppStTotalErrors OBJECT-TYPE
SYNTAX Counter
ACCESS read-only
STATUS mandatory
DESCRIPTION
"This object is the PPP total errors."
::= { iwfPppStatsEntry 11 }

iwfPppStBytesTxPerSec OBJECT-TYPE
SYNTAX Counter
ACCESS read-only
STATUS mandatory
DESCRIPTION
"This object is the PPP bytes transmitted per seconds."
::= { iwfPppStatsEntry 12 }

iwfPppStBytesRxPerSec OBJECT-TYPE
SYNTAX Counter
ACCESS read-only
STATUS mandatory
DESCRIPTION
"This object is the PPP bytes received per seconds."
::= { iwfPppStatsEntry 13 }

iwfPppStFramesTxPerSec OBJECT-TYPE
SYNTAX Counter
ACCESS read-only
STATUS mandatory
DESCRIPTION
"This object is the PPP frames transmitted per seconds."
::= { iwfPppStatsEntry 14 }

iwfPppStFramesRxPerSec OBJECT-TYPE
SYNTAX Counter
ACCESS read-only
STATUS mandatory
DESCRIPTION
"This object is the PPP frames received per seconds."
::= { iwfPppStatsEntry 15 }

iwfPppStTotalErrorPerSec OBJECT-TYPE
SYNTAX Counter
ACCESS read-only
STATUS mandatory
DESCRIPTION
"This object is the PPP total errors per seconds."
::= { iwfPppStatsEntry 16 }

iwfPppStTotalConnections OBJECT-TYPE
SYNTAX Counter
ACCESS read-only
STATUS mandatory
DESCRIPTION
"This object is the PPP total connections."
::= { iwfPppStatsEntry 17 }

iwfTdmStats OBJECT IDENTIFIER ::= { iwfGWY 13 }

iwfTdmStatsTable OBJECT-TYPE
SYNTAX SEQUENCE OF IwfTdmStatsEntry
ACCESS not-accessible
STATUS mandatory
DESCRIPTION
"Table containing objects for TDM statistics for IWF Gateway 
Cards in the chassis."
::= { iwfTdmStats 1 }

iwfTdmStatsEntry OBJECT-TYPE
SYNTAX IwfTdmStatsEntry
ACCESS not-accessible
STATUS mandatory
DESCRIPTION
"There is one Configuration row for each Gateway Card in the 
NAS chassis."
INDEX { iwfTdmStIndex }
::= { iwfTdmStatsTable 1 }

IwfTdmStatsEntry ::=
SEQUENCE {
iwfTdmStIndex
    INTEGER,
iwfTdmStFramesOverruns
    Counter,
iwfTdmStAbortFramesrx
    Counter,
iwfTdmStCrcErrors
    Counter,
iwfTdmStClockLossis
    Counter,
iwfTdmStAccumSubsystemErrors
    Counter,
iwfTdmStClkStatus
    INTEGER
}

iwfTdmStIndex OBJECT-TYPE
SYNTAX INTEGER
ACCESS read-only
STATUS mandatory
DESCRIPTION
"A unique index identifying the Gateway Card to which the 
TDM Statistics objects pertain"
::= { iwfTdmStatsEntry 1 }

iwfTdmStFramesOverruns OBJECT-TYPE
SYNTAX Counter
ACCESS read-only
STATUS mandatory
DESCRIPTION
"This object is the TDM Bus frame overruns counter."
::= { iwfTdmStatsEntry 2 }

iwfTdmStAbortFramesrx OBJECT-TYPE
SYNTAX Counter
ACCESS read-only
STATUS mandatory
DESCRIPTION
"This object is the TDM Bus abort frames received counter."
::= { iwfTdmStatsEntry 3 }

iwfTdmStCrcErrors OBJECT-TYPE
SYNTAX Counter
ACCESS read-only
STATUS mandatory
DESCRIPTION
"This object is the TDM Bus CRC errors counter."
::= { iwfTdmStatsEntry 4 }

iwfTdmStClockLossis OBJECT-TYPE
SYNTAX Counter
ACCESS read-only
STATUS mandatory
DESCRIPTION
"This object is the TDM Bus clock losses counter."
::= { iwfTdmStatsEntry 5 }

iwfTdmStAccumSubsystemErrors OBJECT-TYPE
SYNTAX Counter
ACCESS read-only
STATUS mandatory
DESCRIPTION
"This object is the TDM Bus accumulated number of subsystem 
errors counter."
::= { iwfTdmStatsEntry 6 }

iwfTdmStClkStatus OBJECT-TYPE
SYNTAX INTEGER{
  clockUp(1),
  clockDown(2)
}
ACCESS read-only
STATUS mandatory
DESCRIPTION
"This object is the TDM Bus Clock Up/Down status."
::= { iwfTdmStatsEntry 7 }

iwfPbStats OBJECT IDENTIFIER ::= { iwfGWY 14 }

iwfPbStatsTable OBJECT-TYPE
SYNTAX SEQUENCE OF IwfPbStatsEntry
ACCESS not-accessible
STATUS mandatory
DESCRIPTION
"Table containing objects for Packet Bus statistics for IWF 
Gateway Cards in the chassis."
::= { iwfPbStats 1 }

iwfPbStatsEntry OBJECT-TYPE
SYNTAX IwfPbStatsEntry
ACCESS not-accessible
STATUS mandatory
DESCRIPTION
"There is one Configuration row for each Gateway Card in the 
NAS chassis."
INDEX { iwfPbStIndex }
::= { iwfPbStatsTable 1 }

IwfPbStatsEntry ::=
SEQUENCE {
iwfPbStIndex
    INTEGER,
iwfPbStFramesOverruns
    Counter,
iwfPbStAbortFramesrx
    Counter,
iwfPbStCrcErrors
    Counter,
iwfPbStClockLosses
    Counter,
iwfPbStAccumSubsystemErrors
    Counter,
iwfPbStClkStatus
    INTEGER,
iwfPbStLinkLosses
    Counter
}

iwfPbStIndex OBJECT-TYPE
SYNTAX INTEGER
ACCESS read-only
STATUS mandatory
DESCRIPTION
"A unique index identifying the Gateway Card to which the 
Packet Bus Statistics objects pertain"
::= { iwfPbStatsEntry 1 }

iwfPbStFramesOverruns OBJECT-TYPE
SYNTAX Counter
ACCESS read-only
STATUS mandatory
DESCRIPTION
"This object is the Packet Bus frame overruns counter."
::= { iwfPbStatsEntry 2 }

iwfPbStAbortFramesrx OBJECT-TYPE
SYNTAX Counter
ACCESS read-only
STATUS mandatory
DESCRIPTION
"This object is the Packet Bus abort frames received 
counter."
::= { iwfPbStatsEntry 3 }

iwfPbStCrcErrors OBJECT-TYPE
SYNTAX Counter
ACCESS read-only
STATUS mandatory
DESCRIPTION
"This object is the Packet Bus CRC errors counter."
::= { iwfPbStatsEntry 4 }

iwfPbStClockLosses OBJECT-TYPE
SYNTAX Counter
ACCESS read-only
STATUS mandatory
DESCRIPTION
"This object is the Packet Bus clock losses counter."
::= { iwfPbStatsEntry 5 }

iwfPbStAccumSubsystemErrors OBJECT-TYPE
SYNTAX Counter
ACCESS read-only
STATUS mandatory
DESCRIPTION
"This object is the Packet Bus accumulated number of 
subsystem errors counter."
::= { iwfPbStatsEntry 6 }

iwfPbStClkStatus OBJECT-TYPE
SYNTAX INTEGER{
  clockUp(1),
  clockDown(2)
}
ACCESS read-only
STATUS mandatory
DESCRIPTION
"This object is the Packet Bus Clock up/down status."
::= { iwfPbStatsEntry 7 }

iwfPbStLinkLosses OBJECT-TYPE
SYNTAX Counter
ACCESS read-only
STATUS mandatory
DESCRIPTION
"This object is the Packet Bus link losses counter."
::= { iwfPbStatsEntry 8 }

iwfQ921Stats OBJECT IDENTIFIER ::= { iwfGWY 15 }

iwfQ921StatsTable OBJECT-TYPE
SYNTAX SEQUENCE OF IwfQ921StatsEntry
ACCESS not-accessible
STATUS mandatory
DESCRIPTION
"Table containing objects for Q921 Call Control statistics 
for IWF Gateway Cards in the chassis."
::= { iwfQ921Stats 1 }

iwfQ921StatsEntry OBJECT-TYPE
SYNTAX IwfQ921StatsEntry
ACCESS not-accessible
STATUS mandatory
DESCRIPTION
"There is one Configuration row for each Gateway Card in the 
NAS chassis."
INDEX { iwfQ921StIndex }
::= { iwfQ921StatsTable 1 }

IwfQ921StatsEntry ::=
SEQUENCE {
iwfQ921StIndex
    INTEGER,
iwfQ921StAccumLinkLosses
    Counter,
iwfQ921StAccumFrsvcSusSysError
    Counter
}

iwfQ921StIndex OBJECT-TYPE
SYNTAX INTEGER
ACCESS read-only
STATUS mandatory
DESCRIPTION
"A unique index identifying the Gateway Card to which the 
Q921 Call Control Statistics objects pertain"
::= { iwfQ921StatsEntry 1 }

iwfQ921StAccumLinkLosses OBJECT-TYPE
SYNTAX Counter
ACCESS read-only
STATUS mandatory
DESCRIPTION
"This object is the Frame Relay accumulated number of link 
losses for Q921 call control."
::= { iwfQ921StatsEntry 2 }

iwfQ921StAccumFrsvcSusSysError OBJECT-TYPE
SYNTAX Counter
ACCESS read-only
STATUS mandatory
DESCRIPTION
"This object is accumulated number of frame relay service 
subsystem errors for Q921 call control."
::= { iwfQ921StatsEntry 3 }

iwfQ933Stats OBJECT IDENTIFIER ::= { iwfGWY 16 }

iwfQ933StatsTable OBJECT-TYPE
SYNTAX SEQUENCE OF IwfQ933StatsEntry
ACCESS not-accessible
STATUS mandatory
DESCRIPTION
"Table containing objects for Q933 Call Control statistics 
for IWF Gateway Cards in the chassis."
::= { iwfQ933Stats 1 }

iwfQ933StatsEntry OBJECT-TYPE
SYNTAX IwfQ933StatsEntry
ACCESS not-accessible
STATUS mandatory
DESCRIPTION
"There is one Configuration row for each Gateway Card in the 
NAS chassis."
INDEX { iwfQ933StIndex }
::= { iwfQ933StatsTable 1 }

IwfQ933StatsEntry ::=
SEQUENCE {
iwfQ933StIndex
    INTEGER,
iwfQ933StAccumUknownIframes
    Counter,
iwfQ933StAccumOutOfSeqIframes
    Counter
}

iwfQ933StIndex OBJECT-TYPE
SYNTAX INTEGER
ACCESS read-only
STATUS mandatory
DESCRIPTION
"A unique index identifying the Gateway Card to which the 
Q933 Call Control Statistics objects pertain"
::= { iwfQ933StatsEntry 1 }

iwfQ933StAccumUknownIframes OBJECT-TYPE
SYNTAX Counter
ACCESS read-only
STATUS mandatory
DESCRIPTION
"This object is the Q933 accumulated number of unknown 
I-frames."
::= { iwfQ933StatsEntry 2 }

iwfQ933StAccumOutOfSeqIframes OBJECT-TYPE
SYNTAX Counter
ACCESS read-only
STATUS mandatory
DESCRIPTION
"This object is the Q933 accumulated number of out of 
sequence I frames."
::= { iwfQ933StatsEntry 3 }

iwfMdmStats OBJECT IDENTIFIER ::= { iwfGWY 17 }

iwfMdmStatsTable OBJECT-TYPE
SYNTAX SEQUENCE OF IwfMdmStatsEntry
ACCESS not-accessible
STATUS mandatory
DESCRIPTION
"Table containing objects for Modem commands statistics for 
IWF Gateway Cards in the chassis."
::= { iwfMdmStats 1 }

iwfMdmStatsEntry OBJECT-TYPE
SYNTAX IwfMdmStatsEntry
ACCESS not-accessible
STATUS mandatory
DESCRIPTION
"There is one Configuration row for each Gateway Card in the 
NAS chassis."
INDEX { iwfMdmStIndex }
::= { iwfMdmStatsTable 1 }

IwfMdmStatsEntry ::=
SEQUENCE {
iwfMdmStIndex
    INTEGER,
iwfMdmStAccumInvalidAtCmd
    INTEGER
}

iwfMdmStIndex OBJECT-TYPE
SYNTAX INTEGER
ACCESS read-only
STATUS mandatory
DESCRIPTION
"A unique index identifying the Gateway Card to which the 
Modem commands Statistics objects pertain"
::= { iwfMdmStatsEntry 1 }

iwfMdmStAccumInvalidAtCmd OBJECT-TYPE
SYNTAX INTEGER
ACCESS read-only
STATUS mandatory
DESCRIPTION
"This object is the accumulated number of invalid AT 
commands to the modem."
::= { iwfMdmStatsEntry 2 }

iwfCmpStats OBJECT IDENTIFIER ::= { iwfGWY 18 }

iwfCmpStatsTable OBJECT-TYPE
SYNTAX SEQUENCE OF IwfCmpStatsEntry
ACCESS not-accessible
STATUS mandatory
DESCRIPTION
"Table containing objects for Compression statistics for IWF 
Gateway Cards in the chassis."
::= { iwfCmpStats 1 }

iwfCmpStatsEntry OBJECT-TYPE
SYNTAX IwfCmpStatsEntry
ACCESS not-accessible
STATUS mandatory
DESCRIPTION
"There is one Configuration row for each Gateway Card in the 
NAS chassis."
INDEX { iwfCmpStIndex }
::= { iwfCmpStatsTable 1 }

IwfCmpStatsEntry ::=
SEQUENCE {
iwfCmpStIndex
    INTEGER,
iwfCmpStAccumSubsysErrors
    Counter
}

iwfCmpStIndex OBJECT-TYPE
SYNTAX INTEGER
ACCESS read-only
STATUS mandatory
DESCRIPTION
"A unique index identifying the Gateway Card to which the 
Compression Statistics objects pertain"
::= { iwfCmpStatsEntry 1 }

iwfCmpStAccumSubsysErrors OBJECT-TYPE
SYNTAX Counter
ACCESS read-only
STATUS mandatory
DESCRIPTION
"This object is the accumulated number of compression 
subsystem errors."
::= { iwfCmpStatsEntry 2 }

iwfCallStats OBJECT IDENTIFIER ::= { iwfGWY 19 }

iwfCallStatsTable OBJECT-TYPE
SYNTAX SEQUENCE OF IwfCallStatsEntry
ACCESS not-accessible
STATUS mandatory
DESCRIPTION
"Table containing objects for Call statistics for IWF 
Gateway Cards in the chassis."
::= { iwfCallStats 1 }

iwfCallStatsEntry OBJECT-TYPE
SYNTAX IwfCallStatsEntry
ACCESS not-accessible
STATUS mandatory
DESCRIPTION
"There is one Configuration row for each Gateway Card in the 
NAS chassis."
INDEX { iwfCallStIndex }
::= { iwfCallStatsTable 1 }

IwfCallStatsEntry ::=
SEQUENCE {
iwfCallStIndex
    INTEGER,
iwfCallStTotConnAd9600MobOrg
    Counter,
iwfCallStTotConnAd14400MobOrg
    Counter,
iwfCallStTotConnFax9600MobOrg
    Counter,
iwfCallStTotConnFax14400MobOrg
    Counter,
iwfCallStTotConnAd9600MoTerm
    Counter,
iwfCallStTotConnAd14400MoTerm
    Counter,
iwfCallStTotConnFax9600MoTerm
    Counter,
iwfCallStTotConnFax14400MoTerm
    Counter,
iwfCallStTotTermAd9600MoOrg
    Counter,
iwfCallStTotTermAd14400MoOrg
    Counter,
iwfCallStTotTermFax9600MoOrg
    Counter,
iwfCallStTotTermFax14400MoOrg
    Counter,
iwfCallStTotTermAd9600MoTerm
    Counter,
iwfCallStTotTermAd14400MoTerm
    Counter,
iwfCallStTotTermFax9600MoTerm
    Counter,
iwfCallStTotTermFax14400MoTerm
    Counter,
iwfCallStTotCntgAd9600MoOrg
    Counter,
iwfCallStTotCntgAd14400MoOrg
    Counter,
iwfCallStTotCntgFax9600MoOrg
    Counter,
iwfCallStTotCntgFax14400MoOrg
    Counter,
iwfCallStTotCntgAd9600MoTerm
    Counter,
iwfCallStTotCntgAd14400MoTerm
    Counter,
iwfCallStTotCntgFax9600MoTerm
    Counter,
iwfCallStTotCntgFax14400MoTerm
    Counter,
iwfCallStTotDiscAd9600MoOrg
    Counter,
iwfCallStTotDiscAd14400MoOrg
    Counter,
iwfCallStTotDiscFax9600MoOrg
    Counter,
iwfCallStTotDiscFax14400MoOrg
    Counter,
iwfCallStTotDiscAd9600MoTerm
    Counter,
iwfCallStTotDiscAd14400MoTerm
    Counter,
iwfCallStTotDiscFax9600MoTerm
    Counter,
iwfCallStTotDiscFax14400MoTerm
    Counter,
iwfCallStTotCompv42MoOrg
    Counter,
iwfCallStTotCompMmrMoOrg
    Counter,
iwfCallStTotCompv42MoTerm
    Counter,
iwfCallStTotCompMmrMoTerm
    Counter,
iwfCallStTotFailAd9600MoOrg
    Counter,
iwfCallStTotFailAd14400MoOrg
    Counter,
iwfCallStTotFailFax9600MoOrg
    Counter,
iwfCallStTotFailFax14400MoOrg
    Counter,
iwfCallStTotFailAd9600MoTerm
    Counter,
iwfCallStTotFailAd14400MoTerm
    Counter,
iwfCallStTotFailFax9600MoTerm
    Counter,
iwfCallStTotFailFax14400MoTerm
    Counter,
iwfCallStCurrentNumConnCalls
    Counter,
iwfCallStCurrentNumCompCalls
    Counter,
iwfCallStQncConnectedSs9600
    Counter,
iwfCallStQncConnectedL2tp9600
    Counter,
iwfCallStQncConnectedPptp9600
    Counter,
iwfCallStQncConnectedPpp9600
    Counter,
iwfCallStQncTerminatedSs9600
    Counter,
iwfCallStQncTerminatedL2tp9600
    Counter,
iwfCallStQncTerminatedPptp9600
    Counter,
iwfCallStQncTerminatedPpp9600
    Counter,
iwfCallStQncConnectingSs9600
    Counter,
iwfCallStQncConnectingL2tp9600
    Counter,
iwfCallStQncConnectingPptp9600
    Counter,
iwfCallStQncConnectingPpp9600
    Counter,
iwfCallStQncDisconnectingSs9600
    Counter,
iwfCallStQncDisconnectingL2tp9600
    Counter,
iwfCallStQncDisconnectingPptp9600
    Counter,
iwfCallStQncDisconnectingPpp9600
    Counter,
iwfCallStQncConnectedSs14400
    Counter,
iwfCallStQncConnectedL2tp14400
    Counter,
iwfCallStQncConnectedPptp14400
    Counter,
iwfCallStQncConnectedPpp14400
    Counter,
iwfCallStQncTerminatedSs14400
    Counter,
iwfCallStQncTerminatedL2tp14400
    Counter,
iwfCallStQncTerminatedPptp14400
    Counter,
iwfCallStQncTerminatedPpp14400
    Counter,
iwfCallStQncConnectingSs14400
    Counter,
iwfCallStQncConnectingL2tp14400
    Counter,
iwfCallStQncConnectingPptp14400
    Counter,
iwfCallStQncConnectingPpp14400
    Counter,
iwfCallStQncDiscconnectingSs14400
    Counter,
iwfCallStQncDiscconnectingL2tp14400
    Counter,
iwfCallStQncDiscconnectingPptp14400
    Counter,
iwfCallStQncDiscconnectingPpp14400
    Counter
}

iwfCallStIndex OBJECT-TYPE
SYNTAX INTEGER
ACCESS read-only
STATUS mandatory
DESCRIPTION
"A unique index identifying the Gateway Card to which the 
Call Statistics objects pertain"
::= { iwfCallStatsEntry 1 }

iwfCallStTotConnAd9600MobOrg OBJECT-TYPE
SYNTAX Counter
ACCESS read-only
STATUS mandatory
DESCRIPTION
"This object is the accumulated number of Connected AD 9600 
Mobile Originated Calls counter."
::= { iwfCallStatsEntry 2 }

iwfCallStTotConnAd14400MobOrg OBJECT-TYPE
SYNTAX Counter
ACCESS read-only
STATUS mandatory
DESCRIPTION
"This object is the accumulated number of Connected AD 14400 
Mobile Originated Calls counter."
::= { iwfCallStatsEntry 3 }

iwfCallStTotConnFax9600MobOrg OBJECT-TYPE
SYNTAX Counter
ACCESS read-only
STATUS mandatory
DESCRIPTION
"This object is the accumulated number of Connected FAX 9600 
Mobile Originated Calls counter."
::= { iwfCallStatsEntry 4 }

iwfCallStTotConnFax14400MobOrg OBJECT-TYPE
SYNTAX Counter
ACCESS read-only
STATUS mandatory
DESCRIPTION
"This object is the accumulated number of Connected FAX 
14400 Mobile Originated Calls counter."
::= { iwfCallStatsEntry 5 }

iwfCallStTotConnAd9600MoTerm OBJECT-TYPE
SYNTAX Counter
ACCESS read-only
STATUS mandatory
DESCRIPTION
"This object is the accumulated number of Connected AD 9600 
Mobile Terminated Calls counter."
::= { iwfCallStatsEntry 6 }

iwfCallStTotConnAd14400MoTerm OBJECT-TYPE
SYNTAX Counter
ACCESS read-only
STATUS mandatory
DESCRIPTION
"This object is the accumulated number of Connected AD 14400 
Mobile Terminated Calls counter."
::= { iwfCallStatsEntry 7 }

iwfCallStTotConnFax9600MoTerm OBJECT-TYPE
SYNTAX Counter
ACCESS read-only
STATUS mandatory
DESCRIPTION
"This object is the accumulated number of Connected FAX 9600 
Mobile Terminated Calls counter."
::= { iwfCallStatsEntry 8 }

iwfCallStTotConnFax14400MoTerm OBJECT-TYPE
SYNTAX Counter
ACCESS read-only
STATUS mandatory
DESCRIPTION
"This object is the accumulated number of Connected FAX 
14400 Mobile Terminated Calls counter."
::= { iwfCallStatsEntry 9 }

iwfCallStTotTermAd9600MoOrg OBJECT-TYPE
SYNTAX Counter
ACCESS read-only
STATUS mandatory
DESCRIPTION
"This object is the accumulated number of Terminated AD 9600 
Mobile Originated Calls counter."
::= { iwfCallStatsEntry 10 }

iwfCallStTotTermAd14400MoOrg OBJECT-TYPE
SYNTAX Counter
ACCESS read-only
STATUS mandatory
DESCRIPTION
"This object is the accumulated number of Terminated AD 
14400 Mobile Originated Calls counter."
::= { iwfCallStatsEntry 11 }

iwfCallStTotTermFax9600MoOrg OBJECT-TYPE
SYNTAX Counter
ACCESS read-only
STATUS mandatory
DESCRIPTION
"This object is the accumulated number of Terminated FAX 
9600 Mobile Originated Calls counter."
::= { iwfCallStatsEntry 12 }

iwfCallStTotTermFax14400MoOrg OBJECT-TYPE
SYNTAX Counter
ACCESS read-only
STATUS mandatory
DESCRIPTION
"This object is the accumulated number of Terminated FAX 
14400 Mobile Originated Calls counter."
::= { iwfCallStatsEntry 13 }

iwfCallStTotTermAd9600MoTerm OBJECT-TYPE
SYNTAX Counter
ACCESS read-only
STATUS mandatory
DESCRIPTION
"This object is the accumulated number of Terminated AD 9600 
Mobile Terminated Calls counter."
::= { iwfCallStatsEntry 14 }

iwfCallStTotTermAd14400MoTerm OBJECT-TYPE
SYNTAX Counter
ACCESS read-only
STATUS mandatory
DESCRIPTION
"This object is the accumulated number of Terminated AD 
14400 Mobile Terminated Calls counter."
::= { iwfCallStatsEntry 15 }

iwfCallStTotTermFax9600MoTerm OBJECT-TYPE
SYNTAX Counter
ACCESS read-only
STATUS mandatory
DESCRIPTION
"This object is the accumulated number of Terminated FAX 
9600 Mobile Terminated Calls counter."
::= { iwfCallStatsEntry 16 }

iwfCallStTotTermFax14400MoTerm OBJECT-TYPE
SYNTAX Counter
ACCESS read-only
STATUS mandatory
DESCRIPTION
"This object is the accumulated number of Terminated FAX 
14400 Mobile Terminated Calls counter."
::= { iwfCallStatsEntry 17 }

iwfCallStTotCntgAd9600MoOrg OBJECT-TYPE
SYNTAX Counter
ACCESS read-only
STATUS mandatory
DESCRIPTION
"This object is the accumulated number of Connecting AD 9600 
Mobile Originated Calls counter."
::= { iwfCallStatsEntry 18 }

iwfCallStTotCntgAd14400MoOrg OBJECT-TYPE
SYNTAX Counter
ACCESS read-only
STATUS mandatory
DESCRIPTION
"This object is the accumulated number of Connecting AD 
14400 Mobile Originated Calls counter."
::= { iwfCallStatsEntry 19 }

iwfCallStTotCntgFax9600MoOrg OBJECT-TYPE
SYNTAX Counter
ACCESS read-only
STATUS mandatory
DESCRIPTION
"This object is the accumulated number of Connecting FAX 
9600 Mobile Originated Calls counter."
::= { iwfCallStatsEntry 20 }

iwfCallStTotCntgFax14400MoOrg OBJECT-TYPE
SYNTAX Counter
ACCESS read-only
STATUS mandatory
DESCRIPTION
"This object is the accumulated number of Connecting FAX 
14400 Mobile Originated Calls counter."
::= { iwfCallStatsEntry 21 }

iwfCallStTotCntgAd9600MoTerm OBJECT-TYPE
SYNTAX Counter
ACCESS read-only
STATUS mandatory
DESCRIPTION
"This object is the accumulated number of Connecting AD 9600 
Mobile Terminated Calls counter."
::= { iwfCallStatsEntry 22 }

iwfCallStTotCntgAd14400MoTerm OBJECT-TYPE
SYNTAX Counter
ACCESS read-only
STATUS mandatory
DESCRIPTION
"This object is the accumulated number of Connecting AD 
14400 Mobile Terminated Calls counter."
::= { iwfCallStatsEntry 23 }

iwfCallStTotCntgFax9600MoTerm OBJECT-TYPE
SYNTAX Counter
ACCESS read-only
STATUS mandatory
DESCRIPTION
"This object is the accumulated number of Connecting FAX 
9600 Mobile Terminated Calls counter."
::= { iwfCallStatsEntry 24 }

iwfCallStTotCntgFax14400MoTerm OBJECT-TYPE
SYNTAX Counter
ACCESS read-only
STATUS mandatory
DESCRIPTION
"This object is the accumulated number of Connecting FAX 
14400 Mobile Terminated Calls counter."
::= { iwfCallStatsEntry 25 }

iwfCallStTotDiscAd9600MoOrg OBJECT-TYPE
SYNTAX Counter
ACCESS read-only
STATUS mandatory
DESCRIPTION
"This object is the accumulated number of Disconnecting AD 
9600 Mobile Originated Calls counter."
::= { iwfCallStatsEntry 26 }

iwfCallStTotDiscAd14400MoOrg OBJECT-TYPE
SYNTAX Counter
ACCESS read-only
STATUS mandatory
DESCRIPTION
"This object is the accumulated number of Disconnecting AD 
14400 Mobile Originated Calls counter."
::= { iwfCallStatsEntry 27 }

iwfCallStTotDiscFax9600MoOrg OBJECT-TYPE
SYNTAX Counter
ACCESS read-only
STATUS mandatory
DESCRIPTION
"This object is the accumulated number of Disconnecting FAX 
9600 Mobile Originated Calls counter."
::= { iwfCallStatsEntry 28 }

iwfCallStTotDiscFax14400MoOrg OBJECT-TYPE
SYNTAX Counter
ACCESS read-only
STATUS mandatory
DESCRIPTION
"This object is the accumulated number of Disconnecting FAX 
14400 Mobile Originated Calls counter."
::= { iwfCallStatsEntry 29 }

iwfCallStTotDiscAd9600MoTerm OBJECT-TYPE
SYNTAX Counter
ACCESS read-only
STATUS mandatory
DESCRIPTION
"This object is the accumulated number of Disconnecting AD 
9600 Mobile Terminated Calls counter."
::= { iwfCallStatsEntry 30 }

iwfCallStTotDiscAd14400MoTerm OBJECT-TYPE
SYNTAX Counter
ACCESS read-only
STATUS mandatory
DESCRIPTION
"This object is the accumulated number of Disconnecting AD 
14400 Mobile Terminated Calls counter."
::= { iwfCallStatsEntry 31 }

iwfCallStTotDiscFax9600MoTerm OBJECT-TYPE
SYNTAX Counter
ACCESS read-only
STATUS mandatory
DESCRIPTION
"This object is the accumulated number of Disconnecting FAX 
9600 Mobile Terminated Calls counter."
::= { iwfCallStatsEntry 32 }

iwfCallStTotDiscFax14400MoTerm OBJECT-TYPE
SYNTAX Counter
ACCESS read-only
STATUS mandatory
DESCRIPTION
"This object is the accumulated number of Disconnecting FAX 
14400 Mobile Terminated Calls counter."
::= { iwfCallStatsEntry 33 }

iwfCallStTotCompv42MoOrg OBJECT-TYPE
SYNTAX Counter
ACCESS read-only
STATUS mandatory
DESCRIPTION
"This object is the accumulated number of Compressed V.42bis 
Mobile Originated Calls counter."
::= { iwfCallStatsEntry 34 }

iwfCallStTotCompMmrMoOrg OBJECT-TYPE
SYNTAX Counter
ACCESS read-only
STATUS mandatory
DESCRIPTION
"This object is the accumulated number of Compressed MMR 
Mobile Originated Calls counter."
::= { iwfCallStatsEntry 35 }

iwfCallStTotCompv42MoTerm OBJECT-TYPE
SYNTAX Counter
ACCESS read-only
STATUS mandatory
DESCRIPTION
"This object is the accumulated number of Compressed V.42bis 
Mobile Terminated Calls counter."
::= { iwfCallStatsEntry 36 }

iwfCallStTotCompMmrMoTerm OBJECT-TYPE
SYNTAX Counter
ACCESS read-only
STATUS mandatory
DESCRIPTION
"This object is the accumulated number of Compressed MMR 
Mobile Terminated Calls counter."
::= { iwfCallStatsEntry 37 }

iwfCallStTotFailAd9600MoOrg OBJECT-TYPE
SYNTAX Counter
ACCESS read-only
STATUS mandatory
DESCRIPTION
"This object is the accumulated number of Failed AD 9600 
Mobile Originated Calls counter."
::= { iwfCallStatsEntry 38 }

iwfCallStTotFailAd14400MoOrg OBJECT-TYPE
SYNTAX Counter
ACCESS read-only
STATUS mandatory
DESCRIPTION
"This object is the accumulated number of Failed AD 14400 
Mobile Originated Calls counter."
::= { iwfCallStatsEntry 39 }

iwfCallStTotFailFax9600MoOrg OBJECT-TYPE
SYNTAX Counter
ACCESS read-only
STATUS mandatory
DESCRIPTION
"This object is the accumulated number of Failed FAX 9600 
Mobile Originated Calls counter."
::= { iwfCallStatsEntry 40 }

iwfCallStTotFailFax14400MoOrg OBJECT-TYPE
SYNTAX Counter
ACCESS read-only
STATUS mandatory
DESCRIPTION
"This object is the accumulated number of Failed FAX 14400 
Mobile Originated Calls counter."
::= { iwfCallStatsEntry 41 }

iwfCallStTotFailAd9600MoTerm OBJECT-TYPE
SYNTAX Counter
ACCESS read-only
STATUS mandatory
DESCRIPTION
"This object is the accumulated number of Failed AD 9600 
Mobile Terminated Calls counter."
::= { iwfCallStatsEntry 42 }

iwfCallStTotFailAd14400MoTerm OBJECT-TYPE
SYNTAX Counter
ACCESS read-only
STATUS mandatory
DESCRIPTION
"This object is the accumulated number of Failed AD 14400 
Mobile Terminated Calls counter."
::= { iwfCallStatsEntry 43 }

iwfCallStTotFailFax9600MoTerm OBJECT-TYPE
SYNTAX Counter
ACCESS read-only
STATUS mandatory
DESCRIPTION
"This object is the accumulated number of Failed FAX 9600 
Mobile Terminated Calls counter."
::= { iwfCallStatsEntry 44 }

iwfCallStTotFailFax14400MoTerm OBJECT-TYPE
SYNTAX Counter
ACCESS read-only
STATUS mandatory
DESCRIPTION
"This object is the accumulated number of Failed FAX 14400 
Mobile Terminated Calls counter."
::= { iwfCallStatsEntry 45 }

iwfCallStCurrentNumConnCalls OBJECT-TYPE
SYNTAX Counter
ACCESS read-only
STATUS mandatory
DESCRIPTION
"This object is the current number of connected Calls 
counter."
::= { iwfCallStatsEntry 46 }

iwfCallStCurrentNumCompCalls OBJECT-TYPE
SYNTAX Counter
ACCESS read-only
STATUS mandatory
DESCRIPTION
"This object is the current number of compressed Calls 
counter."
::= { iwfCallStatsEntry 47 }

iwfCallStQncConnectedSs9600 OBJECT-TYPE
SYNTAX Counter
ACCESS read-only
STATUS mandatory
DESCRIPTION
"Accumulated # of connected 9600 QNC single stack calls."
::= { iwfCallStatsEntry 48 }

iwfCallStQncConnectedL2tp9600 OBJECT-TYPE
SYNTAX Counter
ACCESS read-only
STATUS mandatory
DESCRIPTION
"Accumulated # of connected 9600 QNC L2TP calls."
::= { iwfCallStatsEntry 49 }

iwfCallStQncConnectedPptp9600 OBJECT-TYPE
SYNTAX Counter
ACCESS read-only
STATUS mandatory
DESCRIPTION
"Accumulated # of connected 9600 QNC PPTP calls."
::= { iwfCallStatsEntry 50 }

iwfCallStQncConnectedPpp9600 OBJECT-TYPE
SYNTAX Counter
ACCESS read-only
STATUS mandatory
DESCRIPTION
"Accumulated # of connected 9600 QNC single stack calls."
::= { iwfCallStatsEntry 51 }

iwfCallStQncTerminatedSs9600 OBJECT-TYPE
SYNTAX Counter
ACCESS read-only
STATUS mandatory
DESCRIPTION
"Accumulated # of terminated 9600 QNC single stack calls."
::= { iwfCallStatsEntry 52 }

iwfCallStQncTerminatedL2tp9600 OBJECT-TYPE
SYNTAX Counter
ACCESS read-only
STATUS mandatory
DESCRIPTION
"Accumulated # of terminated 9600 QNC L2TP calls."
::= { iwfCallStatsEntry 53 }

iwfCallStQncTerminatedPptp9600 OBJECT-TYPE
SYNTAX Counter
ACCESS read-only
STATUS mandatory
DESCRIPTION
"Accumulated # of terminated 9600 QNC PPTP calls."
::= { iwfCallStatsEntry 54 }

iwfCallStQncTerminatedPpp9600 OBJECT-TYPE
SYNTAX Counter
ACCESS read-only
STATUS mandatory
DESCRIPTION
"Accumulated # of terminated 9600 QNC PPP calls."
::= { iwfCallStatsEntry 55 }

iwfCallStQncConnectingSs9600 OBJECT-TYPE
SYNTAX Counter
ACCESS read-only
STATUS mandatory
DESCRIPTION
"Accumulated # of connecting 9600 QNC single stack calls."
::= { iwfCallStatsEntry 56 }

iwfCallStQncConnectingL2tp9600 OBJECT-TYPE
SYNTAX Counter
ACCESS read-only
STATUS mandatory
DESCRIPTION
"Accumulated # of connecting 9600 QNC L2TP calls."
::= { iwfCallStatsEntry 57 }

iwfCallStQncConnectingPptp9600 OBJECT-TYPE
SYNTAX Counter
ACCESS read-only
STATUS mandatory
DESCRIPTION
"Accumulated # of connecting 9600 QNC PPTP calls."
::= { iwfCallStatsEntry 58 }

iwfCallStQncConnectingPpp9600 OBJECT-TYPE
SYNTAX Counter
ACCESS read-only
STATUS mandatory
DESCRIPTION
"Accumulated # of connecting 9600 QNC PPP calls."
::= { iwfCallStatsEntry 59 }

iwfCallStQncDisconnectingSs9600 OBJECT-TYPE
SYNTAX Counter
ACCESS read-only
STATUS mandatory
DESCRIPTION
"Accumulated # of disconnecting 9600 QNC single stack 
calls."
::= { iwfCallStatsEntry 60 }

iwfCallStQncDisconnectingL2tp9600 OBJECT-TYPE
SYNTAX Counter
ACCESS read-only
STATUS mandatory
DESCRIPTION
"Accumulated # of disconnecting 9600 QNC L2TP calls."
::= { iwfCallStatsEntry 61 }

iwfCallStQncDisconnectingPptp9600 OBJECT-TYPE
SYNTAX Counter
ACCESS read-only
STATUS mandatory
DESCRIPTION
"Accumulated # of disconnecting 9600 QNC PPTP calls."
::= { iwfCallStatsEntry 62 }

iwfCallStQncDisconnectingPpp9600 OBJECT-TYPE
SYNTAX Counter
ACCESS read-only
STATUS mandatory
DESCRIPTION
"Accumulated # of disconnecting 9600 QNC PPP calls."
::= { iwfCallStatsEntry 63 }

iwfCallStQncConnectedSs14400 OBJECT-TYPE
SYNTAX Counter
ACCESS read-only
STATUS mandatory
DESCRIPTION
"Accumulated # of connected 14400 QNC single stack calls."
::= { iwfCallStatsEntry 64 }

iwfCallStQncConnectedL2tp14400 OBJECT-TYPE
SYNTAX Counter
ACCESS read-only
STATUS mandatory
DESCRIPTION
"Accumulated # of connected 14400 QNC L2TP calls."
::= { iwfCallStatsEntry 65 }

iwfCallStQncConnectedPptp14400 OBJECT-TYPE
SYNTAX Counter
ACCESS read-only
STATUS mandatory
DESCRIPTION
"Accumulated # of connected 14400 QNC PPTP calls."
::= { iwfCallStatsEntry 66 }

iwfCallStQncConnectedPpp14400 OBJECT-TYPE
SYNTAX Counter
ACCESS read-only
STATUS mandatory
DESCRIPTION
"Accumulated # of connected 14400 QNC PPP calls."
::= { iwfCallStatsEntry 67 }

iwfCallStQncTerminatedSs14400 OBJECT-TYPE
SYNTAX Counter
ACCESS read-only
STATUS mandatory
DESCRIPTION
"Accumulated # of terminated 14400 QNC single stack calls."
::= { iwfCallStatsEntry 68 }

iwfCallStQncTerminatedL2tp14400 OBJECT-TYPE
SYNTAX Counter
ACCESS read-only
STATUS mandatory
DESCRIPTION
"Accumulated # of terminated 14400 QNC L2TP calls."
::= { iwfCallStatsEntry 69 }

iwfCallStQncTerminatedPptp14400 OBJECT-TYPE
SYNTAX Counter
ACCESS read-only
STATUS mandatory
DESCRIPTION
"Accumulated # of terminated 14400 QNC PPTP calls."
::= { iwfCallStatsEntry 70 }

iwfCallStQncTerminatedPpp14400 OBJECT-TYPE
SYNTAX Counter
ACCESS read-only
STATUS mandatory
DESCRIPTION
"Accumulated # of terminated 14400 QNC PPP calls."
::= { iwfCallStatsEntry 71 }

iwfCallStQncConnectingSs14400 OBJECT-TYPE
SYNTAX Counter
ACCESS read-only
STATUS mandatory
DESCRIPTION
"Accumulated # of connecting 14400 QNC single stack calls."
::= { iwfCallStatsEntry 72 }

iwfCallStQncConnectingL2tp14400 OBJECT-TYPE
SYNTAX Counter
ACCESS read-only
STATUS mandatory
DESCRIPTION
"Accumulated # of connecting 14400 QNC L2TP calls."
::= { iwfCallStatsEntry 73 }

iwfCallStQncConnectingPptp14400 OBJECT-TYPE
SYNTAX Counter
ACCESS read-only
STATUS mandatory
DESCRIPTION
"Accumulated # of connecting 14400 QNC PPTP calls."
::= { iwfCallStatsEntry 74 }

iwfCallStQncConnectingPpp14400 OBJECT-TYPE
SYNTAX Counter
ACCESS read-only
STATUS mandatory
DESCRIPTION
"Accumulated # of connecting 14400 QNC PPP calls."
::= { iwfCallStatsEntry 75 }

iwfCallStQncDiscconnectingSs14400 OBJECT-TYPE
SYNTAX Counter
ACCESS read-only
STATUS mandatory
DESCRIPTION
"Accumulated # of disconnecting 14400 QNC single stack 
calls."
::= { iwfCallStatsEntry 76 }

iwfCallStQncDiscconnectingL2tp14400 OBJECT-TYPE
SYNTAX Counter
ACCESS read-only
STATUS mandatory
DESCRIPTION
"Accumulated # of disconnecting 14400 QNC L2TP calls."
::= { iwfCallStatsEntry 77 }

iwfCallStQncDiscconnectingPptp14400 OBJECT-TYPE
SYNTAX Counter
ACCESS read-only
STATUS mandatory
DESCRIPTION
"Accumulated # of disconnecting 14400 QNC PPTP calls."
::= { iwfCallStatsEntry 78 }

iwfCallStQncDiscconnectingPpp14400 OBJECT-TYPE
SYNTAX Counter
ACCESS read-only
STATUS mandatory
DESCRIPTION
"Accumulated # of disconnecting 14400 QNC PPP calls."
::= { iwfCallStatsEntry 79 }

iwfCfgTdmTrap OBJECT IDENTIFIER ::= { iwfGWY 20 }

iwfCfgTdmTrapTable OBJECT-TYPE
SYNTAX SEQUENCE OF IwfTdmTrapEntry
ACCESS not-accessible
STATUS mandatory
DESCRIPTION
"Table containing objects for TDM Trap for the IWF Gateway 
Cards in the chassis."
::= { iwfCfgTdmTrap 1 }

iwfCfgTdmTrapEntry OBJECT-TYPE
SYNTAX IwfTdmTrapEntry
ACCESS not-accessible
STATUS mandatory
DESCRIPTION
"There is one Operational row for each Gateway Card in the 
NAS chassis."
INDEX { iwfTdmTrIndex }
::= { iwfCfgTdmTrapTable 1 }

IwfTdmTrapEntry ::=
SEQUENCE {
iwfTdmTrIndex
    INTEGER,
iwfTdmTrChanMrgOperStatus
    INTEGER,
iwfTdmTrChanNonOperStatus
    INTEGER,
iwfTdmTrChanClearStatus
    INTEGER,
iwfTdmTrChanMrgOperBitMask
    INTEGER,
iwfTdmTrChanMrgOperThreshCnt
    INTEGER,
iwfTdmTrChanNonOperThreshCnt
    INTEGER,
iwfTdmTrChanClearThreshCnt
    INTEGER,
iwfTdmTrChanMrgOperThreshTime
    INTEGER,
iwfTdmTrChanNonOperThreshTime
    INTEGER,
iwfTdmTrChanClearThreshTime
    INTEGER,
iwfTdmTrChCrcErrCnt
    INTEGER,
iwfTdmTrChAbortErrCnt
    INTEGER,
iwfTdmTrChFrameOverflowCnt
    INTEGER,
iwfTdmTrStatus
    INTEGER,
iwfTdmTrTdmChannel
    INTEGER,
iwfTdmTrMunichChip
    INTEGER,
iwfTdmTrMunichChannel
    INTEGER
}

iwfTdmTrIndex OBJECT-TYPE
SYNTAX INTEGER
ACCESS read-only
STATUS mandatory
DESCRIPTION
"A unique index identifying the Gateway Card to which the 
TDM Trap objects pertain"
::= { iwfCfgTdmTrapEntry 1 }

iwfTdmTrChanMrgOperStatus OBJECT-TYPE
SYNTAX INTEGER{
  enableTrap(1),
  disableTrap(2)
}
ACCESS read-write
STATUS mandatory
DESCRIPTION
"This object is the operatinal TDM channel status marginally 
operational trap."
::= { iwfCfgTdmTrapEntry 2 }

iwfTdmTrChanNonOperStatus OBJECT-TYPE
SYNTAX INTEGER{
  enableTrap(1),
  disableTrap(2)
}
ACCESS read-write
STATUS mandatory
DESCRIPTION
"This object is the operatinal TDM channel status non 
operational trap."
::= { iwfCfgTdmTrapEntry 3 }

iwfTdmTrChanClearStatus OBJECT-TYPE
SYNTAX INTEGER{
  enableTrap(1),
  disableTrap(2)
}
ACCESS read-write
STATUS mandatory
DESCRIPTION
"This object is the operatinal TDM channel status clear 
trap."
::= { iwfCfgTdmTrapEntry 4 }

iwfTdmTrChanMrgOperBitMask OBJECT-TYPE
SYNTAX INTEGER
ACCESS read-write
STATUS mandatory
DESCRIPTION
"This object is the TDM channel Marginaly Operational Trap 
Bit Mask."
::= { iwfCfgTdmTrapEntry 5 }

iwfTdmTrChanMrgOperThreshCnt OBJECT-TYPE
SYNTAX INTEGER
ACCESS read-write
STATUS mandatory
DESCRIPTION
"This object is the operatinal TDM channel status marginally 
operational trap threshold count."
::= { iwfCfgTdmTrapEntry 6 }

iwfTdmTrChanNonOperThreshCnt OBJECT-TYPE
SYNTAX INTEGER
ACCESS read-write
STATUS mandatory
DESCRIPTION
"This object is the operatinal TDM channel status Non 
operational trap threshold count."
::= { iwfCfgTdmTrapEntry 7 }

iwfTdmTrChanClearThreshCnt OBJECT-TYPE
SYNTAX INTEGER
ACCESS read-write
STATUS mandatory
DESCRIPTION
"This object is the operatinal TDM channel status Clear trap 
threshold count."
::= { iwfCfgTdmTrapEntry 8 }

iwfTdmTrChanMrgOperThreshTime OBJECT-TYPE
SYNTAX INTEGER
ACCESS read-write
STATUS mandatory
DESCRIPTION
"This object is the operatinal TDM channel status marginally 
operational trap threshold time."
::= { iwfCfgTdmTrapEntry 9 }

iwfTdmTrChanNonOperThreshTime OBJECT-TYPE
SYNTAX INTEGER
ACCESS read-write
STATUS mandatory
DESCRIPTION
"This object is the operational TDM channel status Non 
operational trap threshold time."
::= { iwfCfgTdmTrapEntry 10 }

iwfTdmTrChanClearThreshTime OBJECT-TYPE
SYNTAX INTEGER
ACCESS read-write
STATUS mandatory
DESCRIPTION
"This object is the operational TDM channel status Clear 
trap threshold time."
::= { iwfCfgTdmTrapEntry 11 }

iwfTdmTrChCrcErrCnt OBJECT-TYPE
SYNTAX INTEGER
ACCESS read-only
STATUS mandatory
DESCRIPTION
"This object is the TDM channel CRC ERROR Counter."
::= { iwfCfgTdmTrapEntry 12 }

iwfTdmTrChAbortErrCnt OBJECT-TYPE
SYNTAX INTEGER
ACCESS read-only
STATUS mandatory
DESCRIPTION
"This object is the TDM channel ABORT ERROR Counter."
::= { iwfCfgTdmTrapEntry 13 }

iwfTdmTrChFrameOverflowCnt OBJECT-TYPE
SYNTAX INTEGER
ACCESS read-only
STATUS mandatory
DESCRIPTION
"This object is the TDM channel Frame Overflow Counter."
::= { iwfCfgTdmTrapEntry 14 }

iwfTdmTrStatus OBJECT-TYPE
SYNTAX INTEGER{
  operational(1),
  marginallyOperational(2),
  nonOperational(3)
}
ACCESS read-only
STATUS mandatory
DESCRIPTION
"This object is the TDM channel Trap Status."
::= { iwfCfgTdmTrapEntry 15 }

iwfTdmTrTdmChannel OBJECT-TYPE
SYNTAX INTEGER
ACCESS read-only
STATUS mandatory
DESCRIPTION
"This object is used for event reporting purposes to 
represent the TDM Channel."
::= { iwfCfgTdmTrapEntry 16 }

iwfTdmTrMunichChip OBJECT-TYPE
SYNTAX INTEGER
ACCESS read-only
STATUS mandatory
DESCRIPTION
"This object is used for event reporting purposes to 
represent the Munich Chip."
::= { iwfCfgTdmTrapEntry 17 }

iwfTdmTrMunichChannel OBJECT-TYPE
SYNTAX INTEGER
ACCESS read-only
STATUS mandatory
DESCRIPTION
"This object is used for event reporting purposes to 
represent the Munich Channel."
::= { iwfCfgTdmTrapEntry 18 }

iwfCfgTdmSsTrap OBJECT IDENTIFIER ::= { iwfGWY 21 }

iwfCfgTdmSsTrapTable OBJECT-TYPE
SYNTAX SEQUENCE OF IwfCfgTdmSsTrapEntry
ACCESS not-accessible
STATUS mandatory
DESCRIPTION
"Table containing objects for TDM Sub system Trap for IWF 
Gateway Cards in the chassis."
::= { iwfCfgTdmSsTrap 1 }

iwfCfgTdmSsTrapEntry OBJECT-TYPE
SYNTAX IwfCfgTdmSsTrapEntry
ACCESS not-accessible
STATUS mandatory
DESCRIPTION
"There is one Operatinal row for each Gateway Card in the 
NAS chassis."
INDEX { iwfCfgTdmSsTrIndex }
::= { iwfCfgTdmSsTrapTable 1 }

IwfCfgTdmSsTrapEntry ::=
SEQUENCE {
iwfCfgTdmSsTrIndex
    INTEGER,
iwfTdmSsTrMrgOperStatus
    INTEGER,
iwfTdmSsTrNonOperStatus
    INTEGER,
iwfTdmSsTrClearStatus
    INTEGER,
iwfTdmSsTrMrgOperThreshCnt
    INTEGER,
iwfTdmSsTrNonOperThreshCnt
    INTEGER,
iwfTdmSsTrClearThreshCnt
    INTEGER,
iwfTdmSsTrMrgOperThreshTime
    INTEGER,
iwfTdmSsTrNonOperThreshTime
    INTEGER,
iwfTdmSsTrClearThreshTime
    INTEGER,
iwfTdmSsTrStatus
    INTEGER
}

iwfCfgTdmSsTrIndex OBJECT-TYPE
SYNTAX INTEGER
ACCESS read-only
STATUS mandatory
DESCRIPTION
"A unique index identifying the Gateway Card to which the 
TDM Sub system Trap objects pertain"
::= { iwfCfgTdmSsTrapEntry 1 }

iwfTdmSsTrMrgOperStatus OBJECT-TYPE
SYNTAX INTEGER{
  enableTrap(1),
  disableTrap(2)
}
ACCESS read-write
STATUS mandatory
DESCRIPTION
"This object is the operational TDM channel Sub System 
status marginally operational trap."
::= { iwfCfgTdmSsTrapEntry 2 }

iwfTdmSsTrNonOperStatus OBJECT-TYPE
SYNTAX INTEGER{
  enableTrap(1),
  disableTrap(2)
}
ACCESS read-write
STATUS mandatory
DESCRIPTION
"This object is the operatinal TDM channel Sub System status 
Non operational trap."
::= { iwfCfgTdmSsTrapEntry 3 }

iwfTdmSsTrClearStatus OBJECT-TYPE
SYNTAX INTEGER{
  enableTrap(1),
  disableTrap(2)
}
ACCESS read-write
STATUS mandatory
DESCRIPTION
"This object is the operatinal TDM channel Sub System status 
Clear trap. "
::= { iwfCfgTdmSsTrapEntry 4 }

iwfTdmSsTrMrgOperThreshCnt OBJECT-TYPE
SYNTAX INTEGER
ACCESS read-write
STATUS mandatory
DESCRIPTION
"This object is the operatinal TDM channel sub system status 
marginally operational trap threshold count."
::= { iwfCfgTdmSsTrapEntry 5 }

iwfTdmSsTrNonOperThreshCnt OBJECT-TYPE
SYNTAX INTEGER
ACCESS read-write
STATUS mandatory
DESCRIPTION
"This object is the operatinal TDM channel sub system status 
non operational trap threshold count."
::= { iwfCfgTdmSsTrapEntry 6 }

iwfTdmSsTrClearThreshCnt OBJECT-TYPE
SYNTAX INTEGER
ACCESS read-write
STATUS mandatory
DESCRIPTION
"This object is the operational TDM channel sub system 
status clear operational trap threshold count."
::= { iwfCfgTdmSsTrapEntry 7 }

iwfTdmSsTrMrgOperThreshTime OBJECT-TYPE
SYNTAX INTEGER
ACCESS read-write
STATUS mandatory
DESCRIPTION
"This object is the marginally operational TDM channel sub 
system status clear operational trap threshold timer in 
seconds."
::= { iwfCfgTdmSsTrapEntry 8 }

iwfTdmSsTrNonOperThreshTime OBJECT-TYPE
SYNTAX INTEGER
ACCESS read-write
STATUS mandatory
DESCRIPTION
"This object is the non-operational TDM channel sub system 
status clear operational trap threshold timer in seconds."
::= { iwfCfgTdmSsTrapEntry 9 }

iwfTdmSsTrClearThreshTime OBJECT-TYPE
SYNTAX INTEGER
ACCESS read-write
STATUS mandatory
DESCRIPTION
"This object is the operational TDM channel sub system 
status clear operational trap threshold timer in seconds."
::= { iwfCfgTdmSsTrapEntry 10 }

iwfTdmSsTrStatus OBJECT-TYPE
SYNTAX INTEGER{
  operational(1),
  marginallyOperational(2),
  nonOperational(3)
}
ACCESS read-only
STATUS mandatory
DESCRIPTION
"This object is the TDM channel sub system status."
::= { iwfCfgTdmSsTrapEntry 11 }

iwfCfgPbTrap OBJECT IDENTIFIER ::= { iwfGWY 22 }

iwfCfgPbTrapTable OBJECT-TYPE
SYNTAX SEQUENCE OF IwfPbTrapEntry
ACCESS not-accessible
STATUS mandatory
DESCRIPTION
"Table containing objects for Packet Bus Trap for IWF 
Gateway Cards in the chassis."
::= { iwfCfgPbTrap 1 }

iwfCfgPbTrapEntry OBJECT-TYPE
SYNTAX IwfPbTrapEntry
ACCESS not-accessible
STATUS mandatory
DESCRIPTION
"There is one Operational row for each Gateway Card in the 
NAS chassis."
INDEX { iwfPbTrIndex }
::= { iwfCfgPbTrapTable 1 }

IwfPbTrapEntry ::=
SEQUENCE {
iwfPbTrIndex
    INTEGER,
iwfPbTrChanMrgOperStatus
    INTEGER,
iwfPbTrChanNonOperStatus
    INTEGER,
iwfPbTrChanClearStatus
    INTEGER,
iwfPbTrChanMrgOperBitMask
    INTEGER,
iwfPbTrChanMrgOperThreshCnt
    INTEGER,
iwfPbTrChanNonOperThreshCnt
    INTEGER,
iwfPbTrChanClearThreshCnt
    INTEGER,
iwfPbTrChanMrgOperThreshTime
    INTEGER,
iwfPbTrChanNonOperThreshTime
    INTEGER,
iwfPbTrChanClearThreshTime
    INTEGER,
iwfPbTrChCrcErrCnt
    INTEGER,
iwfPbTrChAbortErrCnt
    INTEGER,
iwfPbTrChFrameOverflowCnt
    INTEGER,
iwfPbTrChStatus
    INTEGER,
iwfPbTrModemSlot
    INTEGER,
iwfPbTrModemChannel
    INTEGER
}

iwfPbTrIndex OBJECT-TYPE
SYNTAX INTEGER
ACCESS read-only
STATUS mandatory
DESCRIPTION
"A unique index identifying the Gateway Card to which the 
Packet Bus Trap objects pertain"
::= { iwfCfgPbTrapEntry 1 }

iwfPbTrChanMrgOperStatus OBJECT-TYPE
SYNTAX INTEGER{
  enableTrap(1),
  disableTrap(2)
}
ACCESS read-write
STATUS mandatory
DESCRIPTION
"This object is the operational the Packet Bus status 
marginally operational trap."
::= { iwfCfgPbTrapEntry 2 }

iwfPbTrChanNonOperStatus OBJECT-TYPE
SYNTAX INTEGER{
  enableTrap(1),
  disableTrap(2)
}
ACCESS read-write
STATUS mandatory
DESCRIPTION
"This object is the operational Packet Bus status non 
operational trap."
::= { iwfCfgPbTrapEntry 3 }

iwfPbTrChanClearStatus OBJECT-TYPE
SYNTAX INTEGER{
  enableTrap(1),
  disableTrap(2)
}
ACCESS read-write
STATUS mandatory
DESCRIPTION
"This object is the operational Packet Bus status clear 
trap."
::= { iwfCfgPbTrapEntry 4 }

iwfPbTrChanMrgOperBitMask OBJECT-TYPE
SYNTAX INTEGER
ACCESS read-write
STATUS mandatory
DESCRIPTION
"This object is the Packet Bus Marginaly Operational Trap 
Bit Mask."
::= { iwfCfgPbTrapEntry 5 }

iwfPbTrChanMrgOperThreshCnt OBJECT-TYPE
SYNTAX INTEGER
ACCESS read-write
STATUS mandatory
DESCRIPTION
"This object is the operational Packet Bus status marginally 
operational trap threshold count."
::= { iwfCfgPbTrapEntry 6 }

iwfPbTrChanNonOperThreshCnt OBJECT-TYPE
SYNTAX INTEGER
ACCESS read-write
STATUS mandatory
DESCRIPTION
"This object is the operational Packet Bus status Non 
operational trap threshold count."
::= { iwfCfgPbTrapEntry 7 }

iwfPbTrChanClearThreshCnt OBJECT-TYPE
SYNTAX INTEGER
ACCESS read-write
STATUS mandatory
DESCRIPTION
"This object is the operational Packet Bus status Clear trap 
threshold count."
::= { iwfCfgPbTrapEntry 8 }

iwfPbTrChanMrgOperThreshTime OBJECT-TYPE
SYNTAX INTEGER
ACCESS read-write
STATUS mandatory
DESCRIPTION
"This object is the operational Packet Bus status marginally 
operational trap threshold time."
::= { iwfCfgPbTrapEntry 9 }

iwfPbTrChanNonOperThreshTime OBJECT-TYPE
SYNTAX INTEGER
ACCESS read-write
STATUS mandatory
DESCRIPTION
"This object is the operational Packet Bus status Non 
operational trap threshold time."
::= { iwfCfgPbTrapEntry 10 }

iwfPbTrChanClearThreshTime OBJECT-TYPE
SYNTAX INTEGER
ACCESS read-write
STATUS mandatory
DESCRIPTION
"This object is the operational Packet Bus status Clear trap 
threshold time."
::= { iwfCfgPbTrapEntry 11 }

iwfPbTrChCrcErrCnt OBJECT-TYPE
SYNTAX INTEGER
ACCESS read-only
STATUS mandatory
DESCRIPTION
"This object is the Packet Bus CRC ERROR Counter."
::= { iwfCfgPbTrapEntry 12 }

iwfPbTrChAbortErrCnt OBJECT-TYPE
SYNTAX INTEGER
ACCESS read-only
STATUS mandatory
DESCRIPTION
"This object is the Packet Bus ABORT ERROR Counter."
::= { iwfCfgPbTrapEntry 13 }

iwfPbTrChFrameOverflowCnt OBJECT-TYPE
SYNTAX INTEGER
ACCESS read-only
STATUS mandatory
DESCRIPTION
"This object is the Packet Bus Frame Overflow Counter."
::= { iwfCfgPbTrapEntry 14 }

iwfPbTrChStatus OBJECT-TYPE
SYNTAX INTEGER{
  operational(1),
  marginallyOperational(2),
  nonOperational(3)
}
ACCESS read-only
STATUS mandatory
DESCRIPTION
"This object is the Packet Bus Link Status."
::= { iwfCfgPbTrapEntry 15 }

iwfPbTrModemSlot OBJECT-TYPE
SYNTAX INTEGER
ACCESS read-only
STATUS mandatory
DESCRIPTION
"This object is used for event reporting purposes to 
represent the modem slot."
::= { iwfCfgPbTrapEntry 16 }

iwfPbTrModemChannel OBJECT-TYPE
SYNTAX INTEGER
ACCESS read-only
STATUS mandatory
DESCRIPTION
"This object is used for event reporting purposes to 
represent the Modem Channel."
::= { iwfCfgPbTrapEntry 17 }

iwfCfgPbSsTrap OBJECT IDENTIFIER ::= { iwfGWY 23 }

iwfCfgPbSsTrapTable OBJECT-TYPE
SYNTAX SEQUENCE OF IwfPbSsTrapEntry
ACCESS not-accessible
STATUS mandatory
DESCRIPTION
"Table containing objects for Packet Bus Sub system Trap for 
IWF Gateway Cards in the chassis."
::= { iwfCfgPbSsTrap 1 }

iwfCfgPbSsTrapEntry OBJECT-TYPE
SYNTAX IwfPbSsTrapEntry
ACCESS not-accessible
STATUS mandatory
DESCRIPTION
"There is one operational row for each Gateway Card in the 
NAS chassis."
INDEX { iwfPbSsTrIndex }
::= { iwfCfgPbSsTrapTable 1 }

IwfPbSsTrapEntry ::=
SEQUENCE {
iwfPbSsTrIndex
    INTEGER,
iwfPbSsTrMrgOperStatus
    INTEGER,
iwfPbSsTrNonOperStatus
    INTEGER,
iwfPbSsTrClearStatus
    INTEGER,
iwfPbSsTrMrgOperThreshCnt
    INTEGER,
iwfPbSsTrNonOperThreshCnt
    INTEGER,
iwfPbSsTrClearThreshCnt
    INTEGER,
iwfPbSsTrMrgOperThreshTime
    INTEGER,
iwfPbSsTrNonOperThreshTime
    INTEGER,
iwfPbSsTrClearThreshtime
    INTEGER,
iwfPbSsTrStatus
    INTEGER
}

iwfPbSsTrIndex OBJECT-TYPE
SYNTAX INTEGER
ACCESS read-only
STATUS mandatory
DESCRIPTION
"A unique index identifying the Gateway Card to which the 
Packet Bus Sub system Trap objects pertain"
::= { iwfCfgPbSsTrapEntry 1 }

iwfPbSsTrMrgOperStatus OBJECT-TYPE
SYNTAX INTEGER{
  enableTrap(1),
  disableTrap(2)
}
ACCESS read-write
STATUS mandatory
DESCRIPTION
"This object is the operational Packet Bus Sub System status 
marginally operational trap."
::= { iwfCfgPbSsTrapEntry 2 }

iwfPbSsTrNonOperStatus OBJECT-TYPE
SYNTAX INTEGER{
  enableTrap(1),
  disableTrap(2)
}
ACCESS read-write
STATUS mandatory
DESCRIPTION
"This object is the operational Packet Bus Sub System status 
Non operational trap."
::= { iwfCfgPbSsTrapEntry 3 }

iwfPbSsTrClearStatus OBJECT-TYPE
SYNTAX INTEGER{
  enableTrap(1),
  disableTrap(2)
}
ACCESS read-write
STATUS mandatory
DESCRIPTION
"This object is the operational Packet Bus Sub System status 
Clear trap. "
::= { iwfCfgPbSsTrapEntry 4 }

iwfPbSsTrMrgOperThreshCnt OBJECT-TYPE
SYNTAX INTEGER
ACCESS read-write
STATUS mandatory
DESCRIPTION
"This object is to configure the Packet Bus sub system 
status marginally operational trap threshold count."
::= { iwfCfgPbSsTrapEntry 5 }

iwfPbSsTrNonOperThreshCnt OBJECT-TYPE
SYNTAX INTEGER
ACCESS read-write
STATUS mandatory
DESCRIPTION
"This object is to configure the Packet Bus sub system 
status non operational trap threshold count."
::= { iwfCfgPbSsTrapEntry 6 }

iwfPbSsTrClearThreshCnt OBJECT-TYPE
SYNTAX INTEGER
ACCESS read-write
STATUS mandatory
DESCRIPTION
"This object is to configure the Packet Bus sub system 
status clear operational trap threshold count."
::= { iwfCfgPbSsTrapEntry 7 }

iwfPbSsTrMrgOperThreshTime OBJECT-TYPE
SYNTAX INTEGER
ACCESS read-write
STATUS mandatory
DESCRIPTION
"This object is to configure the Packet Bus sub system 
status clear marginally operational trap threshold time in 
seconds."
::= { iwfCfgPbSsTrapEntry 8 }

iwfPbSsTrNonOperThreshTime OBJECT-TYPE
SYNTAX INTEGER
ACCESS read-write
STATUS mandatory
DESCRIPTION
"This object is to configure the Packet Bus sub system 
status clear non-operational trap threshold time in 
seconds."
::= { iwfCfgPbSsTrapEntry 9 }

iwfPbSsTrClearThreshtime OBJECT-TYPE
SYNTAX INTEGER
ACCESS read-write
STATUS mandatory
DESCRIPTION
"This object is to configure the Packet Bus sub system 
status clear operational trap threshold time in seconds."
::= { iwfCfgPbSsTrapEntry 10 }

iwfPbSsTrStatus OBJECT-TYPE
SYNTAX INTEGER{
  operational(1),
  marginallyOperational(2),
  nonOperational(3)
}
ACCESS read-only
STATUS mandatory
DESCRIPTION
"This object is the Packet Bus sub system status."
::= { iwfCfgPbSsTrapEntry 11 }

iwfCfgPbClkTrap OBJECT IDENTIFIER ::= { iwfGWY 24 }

iwfCfgPbClkTrapTable OBJECT-TYPE
SYNTAX SEQUENCE OF IwfPbClkTrapEntry
ACCESS not-accessible
STATUS mandatory
DESCRIPTION
"Table containing objects for Packet Bus Clock Trap for IWF 
Gateway Cards in the chassis."
::= { iwfCfgPbClkTrap 1 }

iwfCfgPbClkTrapEntry OBJECT-TYPE
SYNTAX IwfPbClkTrapEntry
ACCESS not-accessible
STATUS mandatory
DESCRIPTION
"There is one Operational row for each Gateway Card in the 
NAS chassis."
INDEX { iwfPbClkTrIndex }
::= { iwfCfgPbClkTrapTable 1 }

IwfPbClkTrapEntry ::=
SEQUENCE {
iwfPbClkTrIndex
    INTEGER,
iwfPbClkTrNonOperStatus
    INTEGER,
iwfPbClkTrClearStatus
    INTEGER,
iwfPbClkTrNonOperThreshTimer
    INTEGER
}

iwfPbClkTrIndex OBJECT-TYPE
SYNTAX INTEGER
ACCESS read-only
STATUS mandatory
DESCRIPTION
"A unique index identifying the Gateway Card to which the 
Packet Bus Clock Trap objects pertain"
::= { iwfCfgPbClkTrapEntry 1 }

iwfPbClkTrNonOperStatus OBJECT-TYPE
SYNTAX INTEGER{
  enableTrap(1),
  disableTrap(2)
}
ACCESS read-write
STATUS mandatory
DESCRIPTION
"This object is the operational Packet Bus Clock status Non 
operational trap."
::= { iwfCfgPbClkTrapEntry 2 }

iwfPbClkTrClearStatus OBJECT-TYPE
SYNTAX INTEGER{
  enableTrap(1),
  disableTrap(2)
}
ACCESS read-write
STATUS mandatory
DESCRIPTION
"This object is the operational Packet Bus Clock status 
Clear trap. "
::= { iwfCfgPbClkTrapEntry 3 }

iwfPbClkTrNonOperThreshTimer OBJECT-TYPE
SYNTAX INTEGER
ACCESS read-write
STATUS mandatory
DESCRIPTION
"This object is the operational Packet Bus Clock status 
clear operational trap threshold Count."
::= { iwfCfgPbClkTrapEntry 4 }

iwfCfgTdmClkTrap OBJECT IDENTIFIER ::= { iwfGWY 25 }

iwfCfgTdmClkTrapTable OBJECT-TYPE
SYNTAX SEQUENCE OF IwfTdmClkTrapEntry
ACCESS not-accessible
STATUS mandatory
DESCRIPTION
"Table containing objects for TDM Clock Trap for IWF Gateway 
Cards in the chassis."
::= { iwfCfgTdmClkTrap 1 }

iwfCfgTdmClkTrapEntry OBJECT-TYPE
SYNTAX IwfTdmClkTrapEntry
ACCESS not-accessible
STATUS mandatory
DESCRIPTION
"There is one Operational row for each Gateway Card in the 
NAS chassis."
INDEX { iwfTdmClkTrIndex }
::= { iwfCfgTdmClkTrapTable 1 }

IwfTdmClkTrapEntry ::=
SEQUENCE {
iwfTdmClkTrIndex
    INTEGER,
iwfTdmClkTrNonOperStatus
    INTEGER,
iwfTdmClkTrClearStatus
    INTEGER,
iwfTdmClkTrNonOperThreshTimer
    INTEGER
}

iwfTdmClkTrIndex OBJECT-TYPE
SYNTAX INTEGER
ACCESS read-only
STATUS mandatory
DESCRIPTION
"A unique index identifying the Gateway Card to which the 
TDM Clock Trap objects pertain"
::= { iwfCfgTdmClkTrapEntry 1 }

iwfTdmClkTrNonOperStatus OBJECT-TYPE
SYNTAX INTEGER{
  enableTrap(1),
  disableTrap(2)
}
ACCESS read-write
STATUS mandatory
DESCRIPTION
"This object is the operational TDM Clock status Non 
operational trap."
::= { iwfCfgTdmClkTrapEntry 2 }

iwfTdmClkTrClearStatus OBJECT-TYPE
SYNTAX INTEGER{
  enableTrap(1),
  disableTrap(2)
}
ACCESS read-write
STATUS mandatory
DESCRIPTION
"This object is the operational TDM Clock status Clear trap. 
"
::= { iwfCfgTdmClkTrapEntry 3 }

iwfTdmClkTrNonOperThreshTimer OBJECT-TYPE
SYNTAX INTEGER
ACCESS read-write
STATUS mandatory
DESCRIPTION
"This object is the operational TDM clock status clear 
operational trap threshold Count."
::= { iwfCfgTdmClkTrapEntry 4 }

iwfCfgCcSsTrap OBJECT IDENTIFIER ::= { iwfGWY 26 }

iwfCfgCcSsTrapTable OBJECT-TYPE
SYNTAX SEQUENCE OF IwfCcSsTrapEntry
ACCESS not-accessible
STATUS mandatory
DESCRIPTION
"Table containing objects for Call Control Trap setting for 
IWF Gateway Cards in the chassis."
::= { iwfCfgCcSsTrap 1 }

iwfCfgCcSsTrapEntry OBJECT-TYPE
SYNTAX IwfCcSsTrapEntry
ACCESS not-accessible
STATUS mandatory
DESCRIPTION
"There is one Operational row for each Gateway Card in the 
NAS chassis."
INDEX { iwfCcSsTrIndex }
::= { iwfCfgCcSsTrapTable 1 }

IwfCcSsTrapEntry ::=
SEQUENCE {
iwfCcSsTrIndex
    INTEGER,
iwfCcSsTrMrgOperStatus
    INTEGER,
iwfCcSsTrNonOperStatus
    INTEGER,
iwfCcSsTrClearStatus
    INTEGER,
iwfCcSsTrMrgOperBitMask
    INTEGER,
iwfCcSsTrMrgOperThreshCnt
    INTEGER,
iwfCcSsTrNonOperThreshCnt
    INTEGER,
iwfCcSsTrClearThreshCnt
    INTEGER,
iwfCcSsTrMrgOperThreshTimer
    INTEGER,
iwfCcSsTrNonOperThreshTimer
    INTEGER,
iwfCcSsTrClearThreshTimer
    INTEGER,
iwfCcSsTrAd9600NoSysResCnt
    INTEGER,
iwfCcSsTrAd14400NoSysResCnt
    INTEGER,
iwfCcSsTrFax9600NoSysResCnt
    INTEGER,
iwfCcSsTrFax14400NoSysResCnt
    INTEGER,
iwfCcSsTrAd9600SktErrCnt
    INTEGER,
iwfCcSsTrAd14400SktErrCnt
    INTEGER,
iwfCcSsTrFax9600SktErrCnt
    INTEGER,
iwfCcSsTrFax14400SktErrCnt
    INTEGER,
iwfCcSsTrAd9600PrtErrCnt
    INTEGER,
iwfCcSsTrAd14400PrtErrCnt
    INTEGER,
iwfCcSsTrFax9600PrtErrCnt
    INTEGER,
iwfCcSsTrFax14400PrtErrCnt
    INTEGER,
iwfCcSsTrAd9600NoMdmResCnt
    INTEGER,
iwfCcSsTrAd14400NoMdmResCnt
    INTEGER,
iwfCcSsTrFax9600NoMdmResCnt
    INTEGER,
iwfCcSsTrFax14400NoMdmResCnt
    INTEGER,
iwfCcSsTrNoResponse
    INTEGER,
iwfCcSsTrStatus
    INTEGER
}

iwfCcSsTrIndex OBJECT-TYPE
SYNTAX INTEGER
ACCESS read-only
STATUS mandatory
DESCRIPTION
"A unique index identifying the Gateway Card to which the 
Call Control Trap objects pertain"
::= { iwfCfgCcSsTrapEntry 1 }

iwfCcSsTrMrgOperStatus OBJECT-TYPE
SYNTAX INTEGER{
  enableTrap(1),
  disableTrap(2)
}
ACCESS read-write
STATUS mandatory
DESCRIPTION
"This object is the current setting of the Call Control 
status Marginally operational trap."
::= { iwfCfgCcSsTrapEntry 2 }

iwfCcSsTrNonOperStatus OBJECT-TYPE
SYNTAX INTEGER{
  enableTrap(1),
  disableTrap(2)
}
ACCESS read-write
STATUS mandatory
DESCRIPTION
"This object is the current setting of the Call Control 
status Non operational trap."
::= { iwfCfgCcSsTrapEntry 3 }

iwfCcSsTrClearStatus OBJECT-TYPE
SYNTAX INTEGER{
  enableTrap(1),
  disableTrap(2)
}
ACCESS read-write
STATUS mandatory
DESCRIPTION
"This object is the current setting of the Call Control 
status Clear trap."
::= { iwfCfgCcSsTrapEntry 4 }

iwfCcSsTrMrgOperBitMask OBJECT-TYPE
SYNTAX INTEGER
ACCESS read-write
STATUS mandatory
DESCRIPTION
"This object is the Call Control Marginally Operational Trap 
Bit Mask."
::= { iwfCfgCcSsTrapEntry 5 }

iwfCcSsTrMrgOperThreshCnt OBJECT-TYPE
SYNTAX INTEGER
ACCESS read-write
STATUS mandatory
DESCRIPTION
"This object is the Call Control Marginally Operational Trap 
Threshold Count."
::= { iwfCfgCcSsTrapEntry 6 }

iwfCcSsTrNonOperThreshCnt OBJECT-TYPE
SYNTAX INTEGER
ACCESS read-write
STATUS mandatory
DESCRIPTION
"This object is the Call Control Non Operational Trap 
Threshold Count."
::= { iwfCfgCcSsTrapEntry 7 }

iwfCcSsTrClearThreshCnt OBJECT-TYPE
SYNTAX INTEGER
ACCESS read-write
STATUS mandatory
DESCRIPTION
"This object is the Call Control Clear Trap Threshold 
Count."
::= { iwfCfgCcSsTrapEntry 8 }

iwfCcSsTrMrgOperThreshTimer OBJECT-TYPE
SYNTAX INTEGER
ACCESS read-write
STATUS mandatory
DESCRIPTION
"This object is the Call Control Marginally Operational Trap 
Threshold Time."
::= { iwfCfgCcSsTrapEntry 9 }

iwfCcSsTrNonOperThreshTimer OBJECT-TYPE
SYNTAX INTEGER
ACCESS read-write
STATUS mandatory
DESCRIPTION
"This object is the Call Control Non Operational Trap 
Threshold Time."
::= { iwfCfgCcSsTrapEntry 10 }

iwfCcSsTrClearThreshTimer OBJECT-TYPE
SYNTAX INTEGER
ACCESS read-write
STATUS mandatory
DESCRIPTION
"This object is the Call Control Clear Trap Threshold Time."
::= { iwfCfgCcSsTrapEntry 11 }

iwfCcSsTrAd9600NoSysResCnt OBJECT-TYPE
SYNTAX INTEGER
ACCESS read-only
STATUS mandatory
DESCRIPTION
"This object is the Call Control System resources Exhausted 
count for AD9600 Calls ."
::= { iwfCfgCcSsTrapEntry 12 }

iwfCcSsTrAd14400NoSysResCnt OBJECT-TYPE
SYNTAX INTEGER
ACCESS read-only
STATUS mandatory
DESCRIPTION
"This object is the Call Control System resources Exhausted 
count for AD14400 Calls ."
::= { iwfCfgCcSsTrapEntry 13 }

iwfCcSsTrFax9600NoSysResCnt OBJECT-TYPE
SYNTAX INTEGER
ACCESS read-only
STATUS mandatory
DESCRIPTION
"This object is the Call Control System resources Exhausted 
count for FAX9600 Calls ."
::= { iwfCfgCcSsTrapEntry 14 }

iwfCcSsTrFax14400NoSysResCnt OBJECT-TYPE
SYNTAX INTEGER
ACCESS read-only
STATUS mandatory
DESCRIPTION
"This object is the Call Control System resources Exhausted 
count for FAX14400 Calls ."
::= { iwfCfgCcSsTrapEntry 15 }

iwfCcSsTrAd9600SktErrCnt OBJECT-TYPE
SYNTAX INTEGER
ACCESS read-only
STATUS mandatory
DESCRIPTION
"This object is the Call Control Socket Error count for 
AD9600 Calls ."
::= { iwfCfgCcSsTrapEntry 16 }

iwfCcSsTrAd14400SktErrCnt OBJECT-TYPE
SYNTAX INTEGER
ACCESS read-only
STATUS mandatory
DESCRIPTION
"This object is the Call Control Socket Error count for 
AD14400 Calls ."
::= { iwfCfgCcSsTrapEntry 17 }

iwfCcSsTrFax9600SktErrCnt OBJECT-TYPE
SYNTAX INTEGER
ACCESS read-only
STATUS mandatory
DESCRIPTION
"This object is the Call Control Socket Error count for 
FAX9600 Calls ."
::= { iwfCfgCcSsTrapEntry 18 }

iwfCcSsTrFax14400SktErrCnt OBJECT-TYPE
SYNTAX INTEGER
ACCESS read-only
STATUS mandatory
DESCRIPTION
"This object is the Call Control Socket Error count for 
FAX14400 Calls ."
::= { iwfCfgCcSsTrapEntry 19 }

iwfCcSsTrAd9600PrtErrCnt OBJECT-TYPE
SYNTAX INTEGER
ACCESS read-only
STATUS mandatory
DESCRIPTION
"This object is the Call Control Protocol Violation Error 
count for AD9600 Calls ."
::= { iwfCfgCcSsTrapEntry 20 }

iwfCcSsTrAd14400PrtErrCnt OBJECT-TYPE
SYNTAX INTEGER
ACCESS read-only
STATUS mandatory
DESCRIPTION
"This object is the Call Control Protocol Violation Error 
count for AD14400 Calls ."
::= { iwfCfgCcSsTrapEntry 21 }

iwfCcSsTrFax9600PrtErrCnt OBJECT-TYPE
SYNTAX INTEGER
ACCESS read-only
STATUS mandatory
DESCRIPTION
"This object is the Call Control Protocol Violation Error 
count for FAX9600 Calls ."
::= { iwfCfgCcSsTrapEntry 22 }

iwfCcSsTrFax14400PrtErrCnt OBJECT-TYPE
SYNTAX INTEGER
ACCESS read-only
STATUS mandatory
DESCRIPTION
"This object is the Call Control Protocol Violation Error 
count for FAX14400 Calls ."
::= { iwfCfgCcSsTrapEntry 23 }

iwfCcSsTrAd9600NoMdmResCnt OBJECT-TYPE
SYNTAX INTEGER
ACCESS read-only
STATUS mandatory
DESCRIPTION
"This object is the Call Control No Modem Resources Error 
count for AD9600 Calls ."
::= { iwfCfgCcSsTrapEntry 24 }

iwfCcSsTrAd14400NoMdmResCnt OBJECT-TYPE
SYNTAX INTEGER
ACCESS read-only
STATUS mandatory
DESCRIPTION
"This object is the Call Control No Modem Resources Error 
count for AD14400 Calls ."
::= { iwfCfgCcSsTrapEntry 25 }

iwfCcSsTrFax9600NoMdmResCnt OBJECT-TYPE
SYNTAX INTEGER
ACCESS read-only
STATUS mandatory
DESCRIPTION
"This object is the Call Control No Modem Resources Error 
count for FAX9600 Calls ."
::= { iwfCfgCcSsTrapEntry 26 }

iwfCcSsTrFax14400NoMdmResCnt OBJECT-TYPE
SYNTAX INTEGER
ACCESS read-only
STATUS mandatory
DESCRIPTION
"This object is the Call Control No Modem Resources Error 
count for FAX14400 Calls ."
::= { iwfCfgCcSsTrapEntry 27 }

iwfCcSsTrNoResponse OBJECT-TYPE
SYNTAX INTEGER
ACCESS read-only
STATUS mandatory
DESCRIPTION
"This object is the Call Control Not Responding Error 
count."
::= { iwfCfgCcSsTrapEntry 28 }

iwfCcSsTrStatus OBJECT-TYPE
SYNTAX INTEGER{
  operational(1),
  marginallyOperational(2),
  nonOperational(3)
}
ACCESS read-only
STATUS mandatory
DESCRIPTION
"This object is the Call Control Status."
::= { iwfCfgCcSsTrapEntry 29 }

iwfCfgDxSsTrap OBJECT IDENTIFIER ::= { iwfGWY 27 }

iwfCfgDxSsTrapTable OBJECT-TYPE
SYNTAX SEQUENCE OF IwfDxSsTrapEntry
ACCESS not-accessible
STATUS mandatory
DESCRIPTION
"Table containing objects for Data Transfer Subsystem Trap 
for IWF Gateway Cards in the chassis."
::= { iwfCfgDxSsTrap 1 }

iwfCfgDxSsTrapEntry OBJECT-TYPE
SYNTAX IwfDxSsTrapEntry
ACCESS not-accessible
STATUS mandatory
DESCRIPTION
"There is one Operational row for each Gateway Card in the 
NAS chassis."
INDEX { iwfDxSsTrIndex }
::= { iwfCfgDxSsTrapTable 1 }

IwfDxSsTrapEntry ::=
SEQUENCE {
iwfDxSsTrIndex
    INTEGER,
iwfDxSsTrMrgOperStatus
    INTEGER,
iwfDxSsTrNonOperStatus
    INTEGER,
iwfDxSsTrClearStatus
    INTEGER,
iwfDxSsTrMrgOperBitMask
    INTEGER,
iwfDxSsTrMrgOperThreshCnt
    INTEGER,
iwfDxSsTrNonOperThreshCnt
    INTEGER,
iwfDxSsTrClearThreshCnt
    INTEGER,
iwfDxSsTrMrgOperThreshTimer
    INTEGER,
iwfDxSsTrNonOperThreshTimer
    INTEGER,
iwfDxSsTrClearThreshTimer
    INTEGER,
iwfDxSsTrAd9600NoSysResCnt
    INTEGER,
iwfDxSsTrAd14400NoSysResCnt
    INTEGER,
iwfDxSsTrFax9600NoSysResCnt
    INTEGER,
iwfDxSsTrFax14400NoSysResCnt
    INTEGER,
iwfDxSsTrAd9600SktErrCnt
    INTEGER,
iwfDxSsTrAd14400SktErrCnt
    INTEGER,
iwfDxSsTrFax9600SktErrCnt
    INTEGER,
iwfDxSsTrFax14400SktErrCnt
    INTEGER,
iwfDxSsTrAd9600PrtErrCnt
    INTEGER,
iwfDxSsTrAd14400PrtErrCnt
    INTEGER,
iwfDxSsTrFax9600PrtErrCnt
    INTEGER,
iwfDxSsTrFax14400PrtErrCnt
    INTEGER,
iwfDxSsTrAd9600NoMdmResCnt
    INTEGER,
iwfDxSsTrAd14400NoMdmResCnt
    INTEGER,
iwfDxSsTrFax9600NoMdmResCnt
    INTEGER,
iwfDxSsTrFax14400NoMdmResCnt
    INTEGER,
iwfDxSsTrNoRespCnt
    INTEGER,
iwfDxSsTrStatus
    INTEGER
}

iwfDxSsTrIndex OBJECT-TYPE
SYNTAX INTEGER
ACCESS read-only
STATUS mandatory
DESCRIPTION
"A unique index identifying the Gateway Card to which the 
Data Transfer Subsystem Trap objects pertain"
::= { iwfCfgDxSsTrapEntry 1 }

iwfDxSsTrMrgOperStatus OBJECT-TYPE
SYNTAX INTEGER{
  enableTrap(1),
  disableTrap(2)
}
ACCESS read-write
STATUS mandatory
DESCRIPTION
"This object is to see the current operation of the Data 
Transfer status Marginally operational trap enable/disable."
::= { iwfCfgDxSsTrapEntry 2 }

iwfDxSsTrNonOperStatus OBJECT-TYPE
SYNTAX INTEGER{
  enableTrap(1),
  disableTrap(2)
}
ACCESS read-write
STATUS mandatory
DESCRIPTION
"This object is to see the current operational setting of 
the Data Transfer status Non operational trap 
enable/disable."
::= { iwfCfgDxSsTrapEntry 3 }

iwfDxSsTrClearStatus OBJECT-TYPE
SYNTAX INTEGER{
  enableTrap(1),
  disableTrap(2)
}
ACCESS read-write
STATUS mandatory
DESCRIPTION
"This object is to see the current operatinal setting of the 
Data Transfer status Clear trap enable/disable."
::= { iwfCfgDxSsTrapEntry 4 }

iwfDxSsTrMrgOperBitMask OBJECT-TYPE
SYNTAX INTEGER
ACCESS read-write
STATUS mandatory
DESCRIPTION
"This object is the Data Transfer Marginally Operational 
Trap Bit Mask."
::= { iwfCfgDxSsTrapEntry 5 }

iwfDxSsTrMrgOperThreshCnt OBJECT-TYPE
SYNTAX INTEGER
ACCESS read-write
STATUS mandatory
DESCRIPTION
"This object is the Data Transfer Marginally Operational 
Trap Threshold Count."
::= { iwfCfgDxSsTrapEntry 6 }

iwfDxSsTrNonOperThreshCnt OBJECT-TYPE
SYNTAX INTEGER
ACCESS read-write
STATUS mandatory
DESCRIPTION
"This object is the Data Transfer Non Operational Trap 
Threshold Count."
::= { iwfCfgDxSsTrapEntry 7 }

iwfDxSsTrClearThreshCnt OBJECT-TYPE
SYNTAX INTEGER
ACCESS read-write
STATUS mandatory
DESCRIPTION
"This object is the Data Transfer Clear Trap Threshold 
Count."
::= { iwfCfgDxSsTrapEntry 8 }

iwfDxSsTrMrgOperThreshTimer OBJECT-TYPE
SYNTAX INTEGER
ACCESS read-write
STATUS mandatory
DESCRIPTION
"This object is the Data Transfer Marginally Operational 
Trap Threshold Time."
::= { iwfCfgDxSsTrapEntry 9 }

iwfDxSsTrNonOperThreshTimer OBJECT-TYPE
SYNTAX INTEGER
ACCESS read-write
STATUS mandatory
DESCRIPTION
"This object is the Data Transfer Non Operational Trap 
Threshold Time."
::= { iwfCfgDxSsTrapEntry 10 }

iwfDxSsTrClearThreshTimer OBJECT-TYPE
SYNTAX INTEGER
ACCESS read-write
STATUS mandatory
DESCRIPTION
"This object is the Data Transfer Clear Trap Threshold 
Time."
::= { iwfCfgDxSsTrapEntry 11 }

iwfDxSsTrAd9600NoSysResCnt OBJECT-TYPE
SYNTAX INTEGER
ACCESS read-only
STATUS mandatory
DESCRIPTION
"This object is the Data Transfer System Resources Exhausted 
count for AD9600 dropped Calls ."
::= { iwfCfgDxSsTrapEntry 12 }

iwfDxSsTrAd14400NoSysResCnt OBJECT-TYPE
SYNTAX INTEGER
ACCESS read-only
STATUS mandatory
DESCRIPTION
"This object is the Data Transfer System Resources Exhausted 
count for AD14400 dropped Calls ."
::= { iwfCfgDxSsTrapEntry 13 }

iwfDxSsTrFax9600NoSysResCnt OBJECT-TYPE
SYNTAX INTEGER
ACCESS read-only
STATUS mandatory
DESCRIPTION
"This object is the Data Transfer System Resources Exhausted 
count for FAX9600 dropped Calls ."
::= { iwfCfgDxSsTrapEntry 14 }

iwfDxSsTrFax14400NoSysResCnt OBJECT-TYPE
SYNTAX INTEGER
ACCESS read-only
STATUS mandatory
DESCRIPTION
"This object is the Data Transfer System Resources Exhausted 
count for FAX14400 dropped Calls ."
::= { iwfCfgDxSsTrapEntry 15 }

iwfDxSsTrAd9600SktErrCnt OBJECT-TYPE
SYNTAX INTEGER
ACCESS read-only
STATUS mandatory
DESCRIPTION
"This object is the Data Transfer Socket Error count for 
AD9600 dropped Calls ."
::= { iwfCfgDxSsTrapEntry 16 }

iwfDxSsTrAd14400SktErrCnt OBJECT-TYPE
SYNTAX INTEGER
ACCESS read-only
STATUS mandatory
DESCRIPTION
"This object is the Data Transfer Socket Error count for 
AD14400 dropped Calls ."
::= { iwfCfgDxSsTrapEntry 17 }

iwfDxSsTrFax9600SktErrCnt OBJECT-TYPE
SYNTAX INTEGER
ACCESS read-only
STATUS mandatory
DESCRIPTION
"This object is the Data Transfer Socket Error count for 
FAX9600 dropped Calls ."
::= { iwfCfgDxSsTrapEntry 18 }

iwfDxSsTrFax14400SktErrCnt OBJECT-TYPE
SYNTAX INTEGER
ACCESS read-only
STATUS mandatory
DESCRIPTION
"This object is the Data Transfer Socket Error count for 
FAX14400 dropped Calls ."
::= { iwfCfgDxSsTrapEntry 19 }

iwfDxSsTrAd9600PrtErrCnt OBJECT-TYPE
SYNTAX INTEGER
ACCESS read-only
STATUS mandatory
DESCRIPTION
"This object is the Data Transfer Protocol Violation Error 
count for AD9600 dropped Calls ."
::= { iwfCfgDxSsTrapEntry 20 }

iwfDxSsTrAd14400PrtErrCnt OBJECT-TYPE
SYNTAX INTEGER
ACCESS read-only
STATUS mandatory
DESCRIPTION
"This object is the Data Transfer Protocol Violation Error 
count for AD14400 dropped Calls ."
::= { iwfCfgDxSsTrapEntry 21 }

iwfDxSsTrFax9600PrtErrCnt OBJECT-TYPE
SYNTAX INTEGER
ACCESS read-only
STATUS mandatory
DESCRIPTION
"This object is the Data Transfer Protocol Violation Error 
count for FAX9600 dropped Calls ."
::= { iwfCfgDxSsTrapEntry 22 }

iwfDxSsTrFax14400PrtErrCnt OBJECT-TYPE
SYNTAX INTEGER
ACCESS read-only
STATUS mandatory
DESCRIPTION
"This object is the Data Transfer Protocol Violation Error 
count for FAX14400 dropped Calls ."
::= { iwfCfgDxSsTrapEntry 23 }

iwfDxSsTrAd9600NoMdmResCnt OBJECT-TYPE
SYNTAX INTEGER
ACCESS read-only
STATUS mandatory
DESCRIPTION
"This object is the Data Transfer No Modem Resources Error 
count for AD9600 dropped Calls ."
::= { iwfCfgDxSsTrapEntry 24 }

iwfDxSsTrAd14400NoMdmResCnt OBJECT-TYPE
SYNTAX INTEGER
ACCESS read-only
STATUS mandatory
DESCRIPTION
"This object is the Data Transfer No Modem Resources Error 
count for AD14400 dropped Calls ."
::= { iwfCfgDxSsTrapEntry 25 }

iwfDxSsTrFax9600NoMdmResCnt OBJECT-TYPE
SYNTAX INTEGER
ACCESS read-only
STATUS mandatory
DESCRIPTION
"This object is the Data Transfer No Modem Resources Error 
count for FAX9600 dropped Calls ."
::= { iwfCfgDxSsTrapEntry 26 }

iwfDxSsTrFax14400NoMdmResCnt OBJECT-TYPE
SYNTAX INTEGER
ACCESS read-only
STATUS mandatory
DESCRIPTION
"This object is the Data Transfer No Modem Resources Error 
count for FAX14400 dropped Calls ."
::= { iwfCfgDxSsTrapEntry 27 }

iwfDxSsTrNoRespCnt OBJECT-TYPE
SYNTAX INTEGER
ACCESS read-only
STATUS mandatory
DESCRIPTION
"This object is the Data Transfer No Response from subsystem 
error cnt."
::= { iwfCfgDxSsTrapEntry 28 }

iwfDxSsTrStatus OBJECT-TYPE
SYNTAX INTEGER{
  operational(1),
  marginallyOperational(2),
  nonOperational(3)
}
ACCESS read-only
STATUS mandatory
DESCRIPTION
"This object is the Data Transfer Status."
::= { iwfCfgDxSsTrapEntry 29 }

iwfCfgCoSsTrap OBJECT IDENTIFIER ::= { iwfGWY 28 }

iwfCfgCoSsTrapTable OBJECT-TYPE
SYNTAX SEQUENCE OF IwfCoSsTrapEntry
ACCESS not-accessible
STATUS mandatory
DESCRIPTION
"Table containing objects for Compression Subsystem Trap 
Configuration for IWF Gateway Cards in the chassis."
::= { iwfCfgCoSsTrap 1 }

iwfCfgCoSsTrapEntry OBJECT-TYPE
SYNTAX IwfCoSsTrapEntry
ACCESS not-accessible
STATUS mandatory
DESCRIPTION
"There is one Operational row for each Gateway Card in the 
NAS chassis."
INDEX { iwfCoSsTrIndex }
::= { iwfCfgCoSsTrapTable 1 }

IwfCoSsTrapEntry ::=
SEQUENCE {
iwfCoSsTrIndex
    INTEGER,
iwfCoSsTrMrgOperStatus
    INTEGER,
iwfCoSsTrNonOperStatus
    INTEGER,
iwfCoSsTrClearStatus
    INTEGER,
iwfCoSsTrMrgOperBitMask
    INTEGER,
iwfCoSsTrMrgOperThreshCnt
    INTEGER,
iwfCoSsTrNonOperThreshCnt
    INTEGER,
iwfCoSsTrClearThreshCnt
    INTEGER,
iwfCoSsTrMrgOperThreshTimer
    INTEGER,
iwfCoSsTrNonOperThreshTimer
    INTEGER,
iwfCoSsTrClearThreshTimer
    INTEGER,
iwfCoSsTrSysNoRespErrCnt
    INTEGER,
iwfCoSsTrDictOutOfSyncCnt
    INTEGER,
iwfCoSsTrStatus
    INTEGER
}

iwfCoSsTrIndex OBJECT-TYPE
SYNTAX INTEGER
ACCESS read-only
STATUS mandatory
DESCRIPTION
"A unique index identifying the Gateway Card to which the 
Compression Subsystem Trap objects pertain"
::= { iwfCfgCoSsTrapEntry 1 }

iwfCoSsTrMrgOperStatus OBJECT-TYPE
SYNTAX INTEGER{
  enableTrap(1),
  disableTrap(2)
}
ACCESS read-write
STATUS mandatory
DESCRIPTION
"This object is to enable the Compression Subsystem status 
Marginally operational trap."
::= { iwfCfgCoSsTrapEntry 2 }

iwfCoSsTrNonOperStatus OBJECT-TYPE
SYNTAX INTEGER{
  enableTrap(1),
  disableTrap(2)
}
ACCESS read-write
STATUS mandatory
DESCRIPTION
"This object is to enable the Compression Subsystem status 
Non operational trap."
::= { iwfCfgCoSsTrapEntry 3 }

iwfCoSsTrClearStatus OBJECT-TYPE
SYNTAX INTEGER{
  enableTrap(1),
  disableTrap(2)
}
ACCESS read-write
STATUS mandatory
DESCRIPTION
"This object is to enable the Compression Subsytem status 
Clear trap."
::= { iwfCfgCoSsTrapEntry 4 }

iwfCoSsTrMrgOperBitMask OBJECT-TYPE
SYNTAX INTEGER
ACCESS read-write
STATUS mandatory
DESCRIPTION
"This object is the Compression Subsystem Marginally 
Operational Trap Bit Mask."
::= { iwfCfgCoSsTrapEntry 5 }

iwfCoSsTrMrgOperThreshCnt OBJECT-TYPE
SYNTAX INTEGER
ACCESS read-write
STATUS mandatory
DESCRIPTION
"This object is the Compression Subsystem Marginally 
Operational Trap Threshold Count."
::= { iwfCfgCoSsTrapEntry 6 }

iwfCoSsTrNonOperThreshCnt OBJECT-TYPE
SYNTAX INTEGER
ACCESS read-write
STATUS mandatory
DESCRIPTION
"This object is the Compressino subsystem Non Operational 
Trap Threshold Count."
::= { iwfCfgCoSsTrapEntry 7 }

iwfCoSsTrClearThreshCnt OBJECT-TYPE
SYNTAX INTEGER
ACCESS read-write
STATUS mandatory
DESCRIPTION
"This object is the Compression Subsystem Clear Trap 
Threshold Count."
::= { iwfCfgCoSsTrapEntry 8 }

iwfCoSsTrMrgOperThreshTimer OBJECT-TYPE
SYNTAX INTEGER
ACCESS read-write
STATUS mandatory
DESCRIPTION
"This object is the Compression Subsystem Marginally 
Operational Trap Threshold Time."
::= { iwfCfgCoSsTrapEntry 9 }

iwfCoSsTrNonOperThreshTimer OBJECT-TYPE
SYNTAX INTEGER
ACCESS read-write
STATUS mandatory
DESCRIPTION
"This object is the Compression subsystem Non Operational 
Trap Threshold Time."
::= { iwfCfgCoSsTrapEntry 10 }

iwfCoSsTrClearThreshTimer OBJECT-TYPE
SYNTAX INTEGER
ACCESS read-write
STATUS mandatory
DESCRIPTION
"This object is the Compression Subsystem Clear Trap 
Threshold Time."
::= { iwfCfgCoSsTrapEntry 11 }

iwfCoSsTrSysNoRespErrCnt OBJECT-TYPE
SYNTAX INTEGER
ACCESS read-only
STATUS mandatory
DESCRIPTION
"This object is the Compression Subsystem Not responding 
error Count."
::= { iwfCfgCoSsTrapEntry 12 }

iwfCoSsTrDictOutOfSyncCnt OBJECT-TYPE
SYNTAX INTEGER
ACCESS read-only
STATUS mandatory
DESCRIPTION
"This object is the Compression Subsystem Dictionary Out of 
Sync Error Count."
::= { iwfCfgCoSsTrapEntry 13 }

iwfCoSsTrStatus OBJECT-TYPE
SYNTAX INTEGER{
  operational(1),
  marginallyOperational(2),
  nonOperational(3)
}
ACCESS read-only
STATUS mandatory
DESCRIPTION
"This object is the Compression Subsystem Status."
::= { iwfCfgCoSsTrapEntry 14 }

iwfCfgPppSsTrap OBJECT IDENTIFIER ::= { iwfGWY 29 }

iwfCfgPppSsTrapTable OBJECT-TYPE
SYNTAX SEQUENCE OF IwfPppSsTrapEntry
ACCESS not-accessible
STATUS mandatory
DESCRIPTION
"Table containing objects for PPP Subsystem Trap for IWF 
Gateway Cards in the chassis."
::= { iwfCfgPppSsTrap 1 }

iwfCfgPppSsTrapEntry OBJECT-TYPE
SYNTAX IwfPppSsTrapEntry
ACCESS not-accessible
STATUS mandatory
DESCRIPTION
"There is one Operational row for each Gateway Card in the 
NAS chassis."
INDEX { iwfPppSsTrIndex }
::= { iwfCfgPppSsTrapTable 1 }

IwfPppSsTrapEntry ::=
SEQUENCE {
iwfPppSsTrIndex
    INTEGER,
iwfPppSsTrMrgOperStatus
    INTEGER,
iwfPppSsTrNonOperStatus
    INTEGER,
iwfPppSsTrClearStatus
    INTEGER,
iwfPppSsTrMrgOperBitMask
    INTEGER,
iwfPppSsTrMrgOperThreshCnt
    INTEGER,
iwfPppSsTrNonOperThreshCnt
    INTEGER,
iwfPppSsTrClearThreshCnt
    INTEGER,
iwfPppSsTrMrgOperThreshTimer
    INTEGER,
iwfPppSsTrNonOperThreshTimer
    INTEGER,
iwfPppSsTrClearThreshTimer
    INTEGER,
iwfPppSsTrSysNoRespErrCnt
    INTEGER,
iwfPppSsTrCrcErrCnt
    INTEGER,
iwfPppSsTrStatus
    INTEGER
}

iwfPppSsTrIndex OBJECT-TYPE
SYNTAX INTEGER
ACCESS read-only
STATUS mandatory
DESCRIPTION
"A unique index identifying the Gateway Card to which the 
PPP Subsystem Trap objects pertain"
::= { iwfCfgPppSsTrapEntry 1 }

iwfPppSsTrMrgOperStatus OBJECT-TYPE
SYNTAX INTEGER{
  enableTrap(1),
  disableTrap(2)
}
ACCESS read-write
STATUS mandatory
DESCRIPTION
"This object is the operatinal PPP Subsystem status 
Marginally operational trap enable/disable."
::= { iwfCfgPppSsTrapEntry 2 }

iwfPppSsTrNonOperStatus OBJECT-TYPE
SYNTAX INTEGER{
  enableTrap(1),
  disableTrap(2)
}
ACCESS read-write
STATUS mandatory
DESCRIPTION
"This object is the operational PPP Subsystem status Non 
operational trap enable/disable."
::= { iwfCfgPppSsTrapEntry 3 }

iwfPppSsTrClearStatus OBJECT-TYPE
SYNTAX INTEGER{
  enableTrap(1),
  disableTrap(2)
}
ACCESS read-write
STATUS mandatory
DESCRIPTION
"This object is the operational PPP Subsytem status Clear 
trap enable/disable."
::= { iwfCfgPppSsTrapEntry 4 }

iwfPppSsTrMrgOperBitMask OBJECT-TYPE
SYNTAX INTEGER
ACCESS read-write
STATUS mandatory
DESCRIPTION
"This object is the PPP Subsystem Marginally Operational 
Trap Bit Mask."
::= { iwfCfgPppSsTrapEntry 5 }

iwfPppSsTrMrgOperThreshCnt OBJECT-TYPE
SYNTAX INTEGER
ACCESS read-write
STATUS mandatory
DESCRIPTION
"This object is the PPP Subsystem Marginally Operational 
Trap Threshold Count."
::= { iwfCfgPppSsTrapEntry 6 }

iwfPppSsTrNonOperThreshCnt OBJECT-TYPE
SYNTAX INTEGER
ACCESS read-write
STATUS mandatory
DESCRIPTION
"This object is the PPP subsystem Non Operational Trap 
Threshold Count."
::= { iwfCfgPppSsTrapEntry 7 }

iwfPppSsTrClearThreshCnt OBJECT-TYPE
SYNTAX INTEGER
ACCESS read-write
STATUS mandatory
DESCRIPTION
"This object is the PPP Subsystem Clear Trap Threshold 
Count."
::= { iwfCfgPppSsTrapEntry 8 }

iwfPppSsTrMrgOperThreshTimer OBJECT-TYPE
SYNTAX INTEGER
ACCESS read-write
STATUS mandatory
DESCRIPTION
"This object is the PPP Subsystem Marginally Operational 
Trap Threshold Time."
::= { iwfCfgPppSsTrapEntry 9 }

iwfPppSsTrNonOperThreshTimer OBJECT-TYPE
SYNTAX INTEGER
ACCESS read-write
STATUS mandatory
DESCRIPTION
"This object is the PPP subsystem Non Operational Trap 
Threshold Time."
::= { iwfCfgPppSsTrapEntry 10 }

iwfPppSsTrClearThreshTimer OBJECT-TYPE
SYNTAX INTEGER
ACCESS read-write
STATUS mandatory
DESCRIPTION
"This object is the PPP Subsystem Clear Trap Threshold 
Time."
::= { iwfCfgPppSsTrapEntry 11 }

iwfPppSsTrSysNoRespErrCnt OBJECT-TYPE
SYNTAX INTEGER
ACCESS read-only
STATUS mandatory
DESCRIPTION
"This object is the PPP Subsystem Not responding error 
Count."
::= { iwfCfgPppSsTrapEntry 12 }

iwfPppSsTrCrcErrCnt OBJECT-TYPE
SYNTAX INTEGER
ACCESS read-only
STATUS mandatory
DESCRIPTION
"This object is the PPP Subsystem Crc Error Count."
::= { iwfCfgPppSsTrapEntry 13 }

iwfPppSsTrStatus OBJECT-TYPE
SYNTAX INTEGER{
  operational(1),
  marginallyOperational(2),
  nonOperational(3)
}
ACCESS read-only
STATUS mandatory
DESCRIPTION
"This object is the PPP Subsystem Status."
::= { iwfCfgPppSsTrapEntry 14 }

iwfCfgTcpSsTrap OBJECT IDENTIFIER ::= { iwfGWY 30 }

iwfCfgTcpSsTrapTable OBJECT-TYPE
SYNTAX SEQUENCE OF IwfTcpSsTrapEntry
ACCESS not-accessible
STATUS mandatory
DESCRIPTION
"Table containing objects for TCP/IP Subsystem Trap for IWF 
Gateway Cards in the chassis."
::= { iwfCfgTcpSsTrap 1 }

iwfCfgTcpSsTrapEntry OBJECT-TYPE
SYNTAX IwfTcpSsTrapEntry
ACCESS not-accessible
STATUS mandatory
DESCRIPTION
"There is one Operational row for each Gateway Card in the 
NAS chassis."
INDEX { iwfTcpSsTrIndex }
::= { iwfCfgTcpSsTrapTable 1 }

IwfTcpSsTrapEntry ::=
SEQUENCE {
iwfTcpSsTrIndex
    INTEGER,
iwfTcpSsTrMrgOperStatus
    INTEGER,
iwfTcpSsTrNonOperStatus
    INTEGER,
iwfTcpSsTrClearStatus
    INTEGER,
iwfTcpSsTrMrgOperBitMask
    INTEGER,
iwfTcpSsTrMrgOperThreshCnt
    INTEGER,
iwfTcpSsTrNonOperThreshCnt
    INTEGER,
iwfTcpSsTrClearThreshCnt
    INTEGER,
iwfTcpSsTrMrgOperThreshTimer
    INTEGER,
iwfTcpSsTrNonOperThreshTimer
    INTEGER,
iwfTcpSsTrClearThreshTimer
    INTEGER,
iwfTcpSsTrSysNoRespErrCnt
    INTEGER,
iwfTcpSsTrStatus
    INTEGER
}

iwfTcpSsTrIndex OBJECT-TYPE
SYNTAX INTEGER
ACCESS read-only
STATUS mandatory
DESCRIPTION
"A unique index identifying the Gateway Card to which the 
TCP/IP Subsystem Trap objects pertain"
::= { iwfCfgTcpSsTrapEntry 1 }

iwfTcpSsTrMrgOperStatus OBJECT-TYPE
SYNTAX INTEGER{
  enableTrap(1),
  disableTrap(2)
}
ACCESS read-write
STATUS mandatory
DESCRIPTION
"This object is the operational TCP/IP Subsystem status 
Marginally operational trap enable/disable."
::= { iwfCfgTcpSsTrapEntry 2 }

iwfTcpSsTrNonOperStatus OBJECT-TYPE
SYNTAX INTEGER{
  enableTrap(1),
  disableTrap(2)
}
ACCESS read-write
STATUS mandatory
DESCRIPTION
"This object is the operational TCP/IP Subsystem status Non 
operational trap enable/disable."
::= { iwfCfgTcpSsTrapEntry 3 }

iwfTcpSsTrClearStatus OBJECT-TYPE
SYNTAX INTEGER{
  enableTrap(1),
  disableTrap(2)
}
ACCESS read-write
STATUS mandatory
DESCRIPTION
"This object is the operational TCP/IP Subsytem status Clear 
trap enable/disable."
::= { iwfCfgTcpSsTrapEntry 4 }

iwfTcpSsTrMrgOperBitMask OBJECT-TYPE
SYNTAX INTEGER
ACCESS read-write
STATUS mandatory
DESCRIPTION
"This object is the TCP/IP Subsystem Marginally Operational 
Trap Bit Mask."
::= { iwfCfgTcpSsTrapEntry 5 }

iwfTcpSsTrMrgOperThreshCnt OBJECT-TYPE
SYNTAX INTEGER
ACCESS read-write
STATUS mandatory
DESCRIPTION
"This object is the TCP/IP Subsystem Marginally Operational 
Trap Threshold Count."
::= { iwfCfgTcpSsTrapEntry 6 }

iwfTcpSsTrNonOperThreshCnt OBJECT-TYPE
SYNTAX INTEGER
ACCESS read-write
STATUS mandatory
DESCRIPTION
"This object is the TCP/IP subsystem Non Operational Trap 
Threshold Count."
::= { iwfCfgTcpSsTrapEntry 7 }

iwfTcpSsTrClearThreshCnt OBJECT-TYPE
SYNTAX INTEGER
ACCESS read-write
STATUS mandatory
DESCRIPTION
"This object is the TCP/IP Subsystem Clear Trap Threshold 
Count."
::= { iwfCfgTcpSsTrapEntry 8 }

iwfTcpSsTrMrgOperThreshTimer OBJECT-TYPE
SYNTAX INTEGER
ACCESS read-write
STATUS mandatory
DESCRIPTION
"This object is the TCP/IP Subsystem Marginally Operational 
Trap Threshold Time."
::= { iwfCfgTcpSsTrapEntry 9 }

iwfTcpSsTrNonOperThreshTimer OBJECT-TYPE
SYNTAX INTEGER
ACCESS read-write
STATUS mandatory
DESCRIPTION
"This object is the TCP/IP subsystem Non Operational Trap 
Threshold Time."
::= { iwfCfgTcpSsTrapEntry 10 }

iwfTcpSsTrClearThreshTimer OBJECT-TYPE
SYNTAX INTEGER
ACCESS read-write
STATUS mandatory
DESCRIPTION
"This object is the TCP/IP Subsystem Clear Trap Threshold 
Time."
::= { iwfCfgTcpSsTrapEntry 11 }

iwfTcpSsTrSysNoRespErrCnt OBJECT-TYPE
SYNTAX INTEGER
ACCESS read-only
STATUS mandatory
DESCRIPTION
"This object is the TCP/IP Subsystem Not responding error 
Count."
::= { iwfCfgTcpSsTrapEntry 12 }

iwfTcpSsTrStatus OBJECT-TYPE
SYNTAX INTEGER{
  operational(1),
  marginallyOperational(2),
  nonOperational(3)
}
ACCESS read-only
STATUS mandatory
DESCRIPTION
"This object is the TCP/IP Subsystem Status."
::= { iwfCfgTcpSsTrapEntry 13 }

iwfOprFrRly OBJECT IDENTIFIER ::= { iwfGWY 31 }

iwfOprFrRlyTable OBJECT-TYPE
SYNTAX SEQUENCE OF IwfOprFrRlyEntry
ACCESS not-accessible
STATUS mandatory
DESCRIPTION
"Table containing objects for Operational Frame Relay Local 
management Interface parameters for the  Gateway Cards in 
the chassis."
::= { iwfOprFrRly 1 }

iwfOprFrRlyEntry OBJECT-TYPE
SYNTAX IwfOprFrRlyEntry
ACCESS not-accessible
STATUS mandatory
DESCRIPTION
"There is one Operational row for each Gateway Card in the 
NAS chassis."
INDEX { iwfOprFrRlyIndex }
::= { iwfOprFrRlyTable 1 }

IwfOprFrRlyEntry ::=
SEQUENCE {
iwfOprFrRlyIndex
    INTEGER,
iwfOprFrRlyT391StatusEnqryTimr
    INTEGER,
iwfOprFrRlyT392StatusTimer
    INTEGER,
iwfOprFrRlyN391StatusEnqrySent
    INTEGER
}

iwfOprFrRlyIndex OBJECT-TYPE
SYNTAX INTEGER
ACCESS read-only
STATUS mandatory
DESCRIPTION
"A unique index identifying the Gateway Card to which the 
Frame Relay LMI operational table objects pertain"
::= { iwfOprFrRlyEntry 1 }

iwfOprFrRlyT391StatusEnqryTimr OBJECT-TYPE
SYNTAX INTEGER
ACCESS read-only
STATUS mandatory
DESCRIPTION
"This object is the operational T391 Status Enquiry Timer. "
::= { iwfOprFrRlyEntry 2 }

iwfOprFrRlyT392StatusTimer OBJECT-TYPE
SYNTAX INTEGER
ACCESS read-only
STATUS mandatory
DESCRIPTION
"This object is the operational T392 status timer."
::= { iwfOprFrRlyEntry 3 }

iwfOprFrRlyN391StatusEnqrySent OBJECT-TYPE
SYNTAX INTEGER
ACCESS read-only
STATUS mandatory
DESCRIPTION
"This object is the operational N391 number of status 
enquiry sent."
::= { iwfOprFrRlyEntry 4 }

iwfOprQ921 OBJECT IDENTIFIER ::= { iwfGWY 32 }

iwfOprQ921Table OBJECT-TYPE
SYNTAX SEQUENCE OF IwfOprQ921Entry
ACCESS not-accessible
STATUS mandatory
DESCRIPTION
"Table containing objects for Q.921 parameter operational 
for wireless Gateway Cards in the chassis."
::= { iwfOprQ921 1 }

iwfOprQ921Entry OBJECT-TYPE
SYNTAX IwfOprQ921Entry
ACCESS not-accessible
STATUS mandatory
DESCRIPTION
"There is one operational row for each Gateway Card in the 
NAS chassis."
INDEX { iwfOprQ921Index }
::= { iwfOprQ921Table 1 }

IwfOprQ921Entry ::=
SEQUENCE {
iwfOprQ921Index
    INTEGER,
iwfOprQ921KmaxOutStandPkt
    INTEGER,
iwfOprQ921T200IframeAckTimer
    INTEGER,
iwfOprQ921T203MaxTimeNoIframe
    INTEGER,
iwfOprQ921N200MaxFrameRetrans
    INTEGER,
iwfOprQ921N201RxMaxOctetInfo
    INTEGER,
iwfOprQ921N201TxMaxOctetInfo
    INTEGER
}

iwfOprQ921Index OBJECT-TYPE
SYNTAX INTEGER
ACCESS read-only
STATUS mandatory
DESCRIPTION
"A unique index identifying the Gateway Card to which the 
Q.921 Frame Relay Call Control operational Table objects 
pertain."
::= { iwfOprQ921Entry 1 }

iwfOprQ921KmaxOutStandPkt OBJECT-TYPE
SYNTAX INTEGER
ACCESS read-only
STATUS mandatory
DESCRIPTION
"This object is the operational K-Max # of outstanding 
packets. "
::= { iwfOprQ921Entry 2 }

iwfOprQ921T200IframeAckTimer OBJECT-TYPE
SYNTAX INTEGER
ACCESS read-only
STATUS mandatory
DESCRIPTION
"This object is the operational T200 I-frame Ack Timer. "
::= { iwfOprQ921Entry 3 }

iwfOprQ921T203MaxTimeNoIframe OBJECT-TYPE
SYNTAX INTEGER
ACCESS read-only
STATUS mandatory
DESCRIPTION
"This object is the operational T203 max time with no 
I-frame Exchange. "
::= { iwfOprQ921Entry 4 }

iwfOprQ921N200MaxFrameRetrans OBJECT-TYPE
SYNTAX INTEGER
ACCESS read-only
STATUS mandatory
DESCRIPTION
"This object is the operational N200 max number of 
retransmissions of frame. "
::= { iwfOprQ921Entry 5 }

iwfOprQ921N201RxMaxOctetInfo OBJECT-TYPE
SYNTAX INTEGER
ACCESS read-only
STATUS mandatory
DESCRIPTION
"This object is the operational N200 Received Max number of 
Octets in info field. "
::= { iwfOprQ921Entry 6 }

iwfOprQ921N201TxMaxOctetInfo OBJECT-TYPE
SYNTAX INTEGER
ACCESS read-only
STATUS mandatory
DESCRIPTION
"This object is the operational N200 Transmitted Max number 
of Octets in info field. "
::= { iwfOprQ921Entry 7 }

iwfOprQ933 OBJECT IDENTIFIER ::= { iwfGWY 33 }

iwfOprQ933Table OBJECT-TYPE
SYNTAX SEQUENCE OF IwfOprQ933Entry
ACCESS not-accessible
STATUS mandatory
DESCRIPTION
"Table containing objects for operational Q.933 parameter 
for IWF Gateway Cards in the chassis."
::= { iwfOprQ933 1 }

iwfOprQ933Entry OBJECT-TYPE
SYNTAX IwfOprQ933Entry
ACCESS not-accessible
STATUS mandatory
DESCRIPTION
"There is one Operational row for each Gateway Card in the 
NAS chassis."
INDEX { iwfOprQ933Index }
::= { iwfOprQ933Table 1 }

IwfOprQ933Entry ::=
SEQUENCE {
iwfOprQ933Index
    INTEGER,
iwfOprQ933T303SetupTimer
    INTEGER,
iwfOprQ933T305DisconnectTimer
    INTEGER,
iwfOprQ933T308ReleaseTimer
    INTEGER,
iwfOprQ933T309DataLinkDiscTimr
    INTEGER,
iwfOprQ933T310CallProceedTimer
    INTEGER,
iwfOprQ933T313ConnectSentTimer
    INTEGER
}

iwfOprQ933Index OBJECT-TYPE
SYNTAX INTEGER
ACCESS read-only
STATUS mandatory
DESCRIPTION
"A unique index identifying the Gateway Card to which the 
Q.933 table objects pertain"
::= { iwfOprQ933Entry 1 }

iwfOprQ933T303SetupTimer OBJECT-TYPE
SYNTAX INTEGER
ACCESS read-only
STATUS mandatory
DESCRIPTION
"This object is the operatinal T303- setup timer. "
::= { iwfOprQ933Entry 2 }

iwfOprQ933T305DisconnectTimer OBJECT-TYPE
SYNTAX INTEGER
ACCESS read-only
STATUS mandatory
DESCRIPTION
"This object is the operational T305- Desconnect. "
::= { iwfOprQ933Entry 3 }

iwfOprQ933T308ReleaseTimer OBJECT-TYPE
SYNTAX INTEGER
ACCESS read-only
STATUS mandatory
DESCRIPTION
"This object is the operational T308- Release Timer. "
::= { iwfOprQ933Entry 4 }

iwfOprQ933T309DataLinkDiscTimr OBJECT-TYPE
SYNTAX INTEGER
ACCESS read-only
STATUS mandatory
DESCRIPTION
"This object is the operational T309- Data Link 
Disconnection Timer. "
::= { iwfOprQ933Entry 5 }

iwfOprQ933T310CallProceedTimer OBJECT-TYPE
SYNTAX INTEGER
ACCESS read-only
STATUS mandatory
DESCRIPTION
"This object is the operational T310- Call proceeding timer. 
"
::= { iwfOprQ933Entry 6 }

iwfOprQ933T313ConnectSentTimer OBJECT-TYPE
SYNTAX INTEGER
ACCESS read-only
STATUS mandatory
DESCRIPTION
"This object is the operational T313- Connect sent timer. "
::= { iwfOprQ933Entry 7 }

iwfOprCallStats OBJECT IDENTIFIER ::= { iwfGWY 34 }

iwfOprCallStatsTable OBJECT-TYPE
SYNTAX SEQUENCE OF IwfOprCallStatsEntry
ACCESS not-accessible
STATUS mandatory
DESCRIPTION
"Table containing objects for Operational Call Statistics 
parameter for IWF Gateway Cards in the chassis."
::= { iwfOprCallStats 1 }

iwfOprCallStatsEntry OBJECT-TYPE
SYNTAX IwfOprCallStatsEntry
ACCESS not-accessible
STATUS mandatory
DESCRIPTION
"There is one Configuration row for each Gateway Card in the 
NAS chassis."
INDEX { iwfOprCsIndex }
::= { iwfOprCallStatsTable 1 }

IwfOprCallStatsEntry ::=
SEQUENCE {
iwfOprCsIndex
    INTEGER,
iwfOprCsMobOrigAdStats
    INTEGER,
iwfOprCsMobOrigFaxStats
    INTEGER,
iwfOprCsMobTermAdStats
    INTEGER,
iwfOprCsMobTermFaxStats
    INTEGER
}

iwfOprCsIndex OBJECT-TYPE
SYNTAX INTEGER
ACCESS read-only
STATUS mandatory
DESCRIPTION
"A unique index identifying the Gateway Card to which the 
Call Statistics Operational table objects pertain"
::= { iwfOprCallStatsEntry 1 }

iwfOprCsMobOrigAdStats OBJECT-TYPE
SYNTAX INTEGER{
  enable(1),
  disable(2)
}
ACCESS read-only
STATUS mandatory
DESCRIPTION
"This object shows the current setting for the collection of 
All Mobile Originated AD Statistics."
::= { iwfOprCallStatsEntry 2 }

iwfOprCsMobOrigFaxStats OBJECT-TYPE
SYNTAX INTEGER{
  enable(1),
  disable(2)
}
ACCESS read-only
STATUS mandatory
DESCRIPTION
"This object shows the current setting for the collection of 
All Mobile Originated FAX Statistics."
::= { iwfOprCallStatsEntry 3 }

iwfOprCsMobTermAdStats OBJECT-TYPE
SYNTAX INTEGER{
  enable(1),
  disable(2)
}
ACCESS read-only
STATUS mandatory
DESCRIPTION
"This object shows the current setting for the collection of 
All Mobile Terminated AD Statistics."
::= { iwfOprCallStatsEntry 4 }

iwfOprCsMobTermFaxStats OBJECT-TYPE
SYNTAX INTEGER{
  enable(1),
  disable(2)
}
ACCESS read-only
STATUS mandatory
DESCRIPTION
"This object show the current setting for the collection of 
All Mobile Terminated FAX Statistics."
::= { iwfOprCallStatsEntry 5 }

iwfOprPppParam OBJECT IDENTIFIER ::= { iwfGWY 35 }

iwfOprPppParamTable OBJECT-TYPE
SYNTAX SEQUENCE OF IwfOprPppParamEntry
ACCESS not-accessible
STATUS mandatory
DESCRIPTION
"Table containing objects for operational PPP parameter for 
IWF Gateway Cards in the chassis."
::= { iwfOprPppParam 1 }

iwfOprPppParamEntry OBJECT-TYPE
SYNTAX IwfOprPppParamEntry
ACCESS not-accessible
STATUS mandatory
DESCRIPTION
"There is one Operational row for each Gateway Card in the 
NAS chassis."
INDEX { iwfOprPppIndex }
::= { iwfOprPppParamTable 1 }

IwfOprPppParamEntry ::=
SEQUENCE {
iwfOprPppIndex
    INTEGER,
iwfOprPppForceEncryptData
    INTEGER,
iwfOprPppForceEncryptpassword
    INTEGER,
iwfOprMaxNumbConfigRequests
    INTEGER,
iwfOprMaxNumbConfigNAK
    INTEGER,
iwfOprPppMaxNumbRejects
    INTEGER,
iwfOprPppMaxNumbTermRequests
    INTEGER,
iwfOprPppNegotiateTime
    INTEGER,
iwfOprPppRestartTime
    INTEGER,
iwfOprPppIpAddressPoolMax
    IpAddress,
iwfOprPppIpAddressPoolMin
    IpAddress
}

iwfOprPppIndex OBJECT-TYPE
SYNTAX INTEGER
ACCESS read-only
STATUS mandatory
DESCRIPTION
"A unique index identifying the Gateway Card to which the 
PPP operational table objects pertain"
::= { iwfOprPppParamEntry 1 }

iwfOprPppForceEncryptData OBJECT-TYPE
SYNTAX INTEGER
ACCESS read-only
STATUS mandatory
DESCRIPTION
"This object is the operational control of sending encrypted 
data."
::= { iwfOprPppParamEntry 2 }

iwfOprPppForceEncryptpassword OBJECT-TYPE
SYNTAX INTEGER
ACCESS read-only
STATUS mandatory
DESCRIPTION
"This object is the operationl control of PPP 
Authentication."
::= { iwfOprPppParamEntry 3 }

iwfOprMaxNumbConfigRequests OBJECT-TYPE
SYNTAX INTEGER
ACCESS read-only
STATUS mandatory
DESCRIPTION
"This object is the operational max number of Config 
Requests allowed without receiving a valid configure-Ack."
::= { iwfOprPppParamEntry 4 }

iwfOprMaxNumbConfigNAK OBJECT-TYPE
SYNTAX INTEGER
ACCESS read-only
STATUS mandatory
DESCRIPTION
"This object is for Max number of configure-Nak without 
sending a configure-Ack."
::= { iwfOprPppParamEntry 5 }

iwfOprPppMaxNumbRejects OBJECT-TYPE
SYNTAX INTEGER
ACCESS read-only
STATUS mandatory
DESCRIPTION
"This object is Max number of configure-rejects before 
assuming PPP negotiation failed."
::= { iwfOprPppParamEntry 6 }

iwfOprPppMaxNumbTermRequests OBJECT-TYPE
SYNTAX INTEGER
ACCESS read-only
STATUS mandatory
DESCRIPTION
"This object is Max number of Terminate-Request without 
receiving a Terminate-Ack."
::= { iwfOprPppParamEntry 7 }

iwfOprPppNegotiateTime OBJECT-TYPE
SYNTAX INTEGER
ACCESS read-only
STATUS mandatory
DESCRIPTION
"This object is Max Time allowed for PPP negotiation."
::= { iwfOprPppParamEntry 8 }

iwfOprPppRestartTime OBJECT-TYPE
SYNTAX INTEGER
ACCESS read-only
STATUS mandatory
DESCRIPTION
"This object is Max Time allowed for PPP Restart."
::= { iwfOprPppParamEntry 9 }

iwfOprPppIpAddressPoolMax OBJECT-TYPE
SYNTAX IpAddress
ACCESS read-only
STATUS mandatory
DESCRIPTION
"This object is the operational Mask which defines the range 
of the Ip addresses used by PPP to dynamically allocate IP 
addresses."
::= { iwfOprPppParamEntry 10 }

iwfOprPppIpAddressPoolMin OBJECT-TYPE
SYNTAX IpAddress
ACCESS read-only
STATUS mandatory
DESCRIPTION
"This object is the operational base address which defines 
the range of the Ip addresses used by PPP to dynamically 
allocate IP addresses."
::= { iwfOprPppParamEntry 11 }

iwfOprTcpIp OBJECT IDENTIFIER ::= { iwfGWY 36 }

iwfOprTcpIpTable OBJECT-TYPE
SYNTAX SEQUENCE OF IwfOprTcpIpEntry
ACCESS not-accessible
STATUS mandatory
DESCRIPTION
"Table containing objects for operatinal TCP/IP parameter 
for IWF Gateway Cards in the chassis."
::= { iwfOprTcpIp 1 }

iwfOprTcpIpEntry OBJECT-TYPE
SYNTAX IwfOprTcpIpEntry
ACCESS not-accessible
STATUS mandatory
DESCRIPTION
"There is one Operational row for each Gateway Card in the 
NAS chassis."
INDEX { iwfOprTiIndex }
::= { iwfOprTcpIpTable 1 }

IwfOprTcpIpEntry ::=
SEQUENCE {
iwfOprTiIndex
    INTEGER,
iwfOprTiDefaultServiceType
    INTEGER,
iwfOprTiDefaultTimeToLive
    INTEGER,
iwfOprTiMtuDiscovery
    INTEGER,
iwfOprTiKeepAliveInterval
    INTEGER,
iwfOprTiKeepAliveTime
    INTEGER,
iwfOprTiMaxMtuSize
    INTEGER,
iwfOprTiMaxConnectReTrans
    INTEGER,
iwfOprTiMaxDataRetrans
    INTEGER,
iwfOprTiMaxNumberConnections
    INTEGER,
iwfOprTiWindowSize
    INTEGER,
iwfOprTiLocalIpAddress
    IpAddress,
iwfOprTiSubnetIpMask
    IpAddress,
iwfOprTiDefualtGatewayIp
    IpAddress
}

iwfOprTiIndex OBJECT-TYPE
SYNTAX INTEGER
ACCESS read-only
STATUS mandatory
DESCRIPTION
"A unique index identifying the Gateway Card to which the 
TCP/IP operational table objects pertain"
::= { iwfOprTcpIpEntry 1 }

iwfOprTiDefaultServiceType OBJECT-TYPE
SYNTAX INTEGER (0..255)
ACCESS read-only
STATUS mandatory
DESCRIPTION
"This object is for Default Service type it is defined in 
RFC 791."
::= { iwfOprTcpIpEntry 2 }

iwfOprTiDefaultTimeToLive OBJECT-TYPE
SYNTAX INTEGER (1..255)
ACCESS read-only
STATUS mandatory
DESCRIPTION
"This object is the Max time an IP packet can live in the 
network without reaching its destination."
::= { iwfOprTcpIpEntry 3 }

iwfOprTiMtuDiscovery OBJECT-TYPE
SYNTAX INTEGER
ACCESS read-only
STATUS mandatory
DESCRIPTION
"This object allows discovery of the Maximum Transmission 
Unit over path to remote destination."
::= { iwfOprTcpIpEntry 4 }

iwfOprTiKeepAliveInterval OBJECT-TYPE
SYNTAX INTEGER
ACCESS read-only
STATUS mandatory
DESCRIPTION
"This object is the Interval separating Keep Alive 
Retransmissions."
::= { iwfOprTcpIpEntry 5 }

iwfOprTiKeepAliveTime OBJECT-TYPE
SYNTAX INTEGER
ACCESS read-only
STATUS mandatory
DESCRIPTION
"This object is how often TCP verifies that an idle 
connection is still intact."
::= { iwfOprTcpIpEntry 6 }

iwfOprTiMaxMtuSize OBJECT-TYPE
SYNTAX INTEGER
ACCESS read-only
STATUS mandatory
DESCRIPTION
"This object overrides the default MTU for a network 
interface."
::= { iwfOprTcpIpEntry 7 }

iwfOprTiMaxConnectReTrans OBJECT-TYPE
SYNTAX INTEGER
ACCESS read-only
STATUS mandatory
DESCRIPTION
"This object is the number of times TCP retransmits a 
Connect Request (SYN) before aborting the attempt."
::= { iwfOprTcpIpEntry 8 }

iwfOprTiMaxDataRetrans OBJECT-TYPE
SYNTAX INTEGER
ACCESS read-only
STATUS mandatory
DESCRIPTION
"This object is the number of times TCP retransmits an 
individual data segment before aborting the attempt."
::= { iwfOprTcpIpEntry 9 }

iwfOprTiMaxNumberConnections OBJECT-TYPE
SYNTAX INTEGER
ACCESS read-only
STATUS mandatory
DESCRIPTION
"This object is the operational Max number of open TCP 
connection."
::= { iwfOprTcpIpEntry 10 }

iwfOprTiWindowSize OBJECT-TYPE
SYNTAX INTEGER
ACCESS read-only
STATUS mandatory
DESCRIPTION
"This object is the operational receive window size."
::= { iwfOprTcpIpEntry 11 }

iwfOprTiLocalIpAddress OBJECT-TYPE
SYNTAX IpAddress
ACCESS read-only
STATUS mandatory
DESCRIPTION
"This object is the IP address of the EdgeServer."
::= { iwfOprTcpIpEntry 12 }

iwfOprTiSubnetIpMask OBJECT-TYPE
SYNTAX IpAddress
ACCESS read-only
STATUS mandatory
DESCRIPTION
"This object Subnet Mask of the EdgeServer."
::= { iwfOprTcpIpEntry 13 }

iwfOprTiDefualtGatewayIp OBJECT-TYPE
SYNTAX IpAddress
ACCESS read-only
STATUS mandatory
DESCRIPTION
"This object is the IP address of Gateway Router."
::= { iwfOprTcpIpEntry 14 }

iwfLogStats OBJECT IDENTIFIER ::= { iwfGWY 37 }

iwfLogStatsTable OBJECT-TYPE
SYNTAX SEQUENCE OF IwfLogStatsEntry
ACCESS not-accessible
STATUS mandatory
DESCRIPTION
"Table containing objects for Call log statistics for IWF 
Gateway Cards in the chassis."
::= { iwfLogStats 1 }

iwfLogStatsEntry OBJECT-TYPE
SYNTAX IwfLogStatsEntry
ACCESS not-accessible
STATUS mandatory
DESCRIPTION
""
INDEX { iwfLogStsIndex, iwfLogStsIndex2 }
::= { iwfLogStatsTable 1 }

IwfLogStatsEntry ::=
SEQUENCE {
iwfLogStsIndex
    INTEGER,
iwfLogStsIndex2
    INTEGER,
iwfLogCallRefNum
    INTEGER,
iwfLogMobileIpAddr
    IpAddress,
iwfLogCallingPartyNum
    DisplayString,
iwfLogCalledPartyNum
    DisplayString,
iwfLogCallType
    INTEGER,
iwfLogESN
    OCTET STRING,
iwfLogCallId
    INTEGER,
iwfLogIMSI
    OCTET STRING,
iwfLogServiceOption
    INTEGER,
iwfLogDisconnectCause
    INTEGER,
iwfLogMobileNumBytesTxed
    INTEGER,
iwfLogMobileNumBytesRxed
    INTEGER,
iwfLogNumFaxPagesProcessed
    INTEGER,
iwfLogCompType
    INTEGER,
iwfLogCallErrorCode
    INTEGER,
iwfLogModemSetupTime
    INTEGER,
iwfLogCallConnectingTime
    INTEGER,
iwfLogTotConnectTime
    INTEGER
}

iwfLogStsIndex OBJECT-TYPE
SYNTAX INTEGER
ACCESS read-only
STATUS mandatory
DESCRIPTION
"A unique index identifying the Gateway Card to which the 
Call Log Statistics objects pertain"
::= { iwfLogStatsEntry 1 }

iwfLogStsIndex2 OBJECT-TYPE
SYNTAX INTEGER
ACCESS read-only
STATUS mandatory
DESCRIPTION
"A unique index identifying the call index to which the Call 
Log Statistics objects pertain"
::= { iwfLogStatsEntry 2 }

iwfLogCallRefNum OBJECT-TYPE
SYNTAX INTEGER
ACCESS read-only
STATUS mandatory
DESCRIPTION
"Call Reference Number for the Call."
::= { iwfLogStatsEntry 3 }

iwfLogMobileIpAddr OBJECT-TYPE
SYNTAX IpAddress
ACCESS read-only
STATUS mandatory
DESCRIPTION
"Mobile IP Address."
::= { iwfLogStatsEntry 4 }

iwfLogCallingPartyNum OBJECT-TYPE
SYNTAX DisplayString (SIZE(0..46))
ACCESS read-only
STATUS mandatory
DESCRIPTION
"Calling Party Number"
::= { iwfLogStatsEntry 5 }

iwfLogCalledPartyNum OBJECT-TYPE
SYNTAX DisplayString (SIZE(0..46))
ACCESS read-only
STATUS mandatory
DESCRIPTION
"Called Party Number"
::= { iwfLogStatsEntry 6 }

iwfLogCallType OBJECT-TYPE
SYNTAX INTEGER{
  mobileOriginate(1),
  mobileTerminate(2),
  rEQINFORMOFDORMANTLL(3),
  iNFORMCHGPKTMOBILITY(4)
}
ACCESS read-only
STATUS mandatory
DESCRIPTION
"Call Type"
::= { iwfLogStatsEntry 7 }

iwfLogESN OBJECT-TYPE
SYNTAX OCTET STRING (SIZE(0..8))
ACCESS read-only
STATUS mandatory
DESCRIPTION
"Electronic Serial Number"
::= { iwfLogStatsEntry 8 }

iwfLogCallId OBJECT-TYPE
SYNTAX INTEGER{
  pSTNCALL(1),
  iwfQncSingleStackCall(2),
  qncPptpCall(3),
  mobileIpCall(4),
  qncL2tpCall(5),
  qncPppCall(6)
}
ACCESS read-only
STATUS mandatory
DESCRIPTION
"IWF Call Identifier"
::= { iwfLogStatsEntry 9 }

iwfLogIMSI OBJECT-TYPE
SYNTAX OCTET STRING (SIZE(0..16))
ACCESS read-only
STATUS mandatory
DESCRIPTION
"Mobile Subsriber Identification"
::= { iwfLogStatsEntry 10 }

iwfLogServiceOption OBJECT-TYPE
SYNTAX INTEGER{
  basicVoiceService(1),
  mobileLoopBack(2),
  enhancedRateCode(3),
  asyncDataServie9dot6kbs(4),
  group3faxService9dot6kbs(5),
  shortMessageService(6),
  asyncDataService14dot4Kbs(7),
  group3faxService14dot4Kbs(8)
}
ACCESS read-only
STATUS mandatory
DESCRIPTION
"Service Option"
::= { iwfLogStatsEntry 11 }

iwfLogDisconnectCause OBJECT-TYPE
SYNTAX INTEGER
ACCESS read-only
STATUS mandatory
DESCRIPTION
"Disconnect Cause Indicator"
::= { iwfLogStatsEntry 12 }

iwfLogMobileNumBytesTxed OBJECT-TYPE
SYNTAX INTEGER
ACCESS read-only
STATUS mandatory
DESCRIPTION
"Mobile number of bytes xmitted."
::= { iwfLogStatsEntry 13 }

iwfLogMobileNumBytesRxed OBJECT-TYPE
SYNTAX INTEGER
ACCESS read-only
STATUS mandatory
DESCRIPTION
"Mobile number of bytes received."
::= { iwfLogStatsEntry 14 }

iwfLogNumFaxPagesProcessed OBJECT-TYPE
SYNTAX INTEGER
ACCESS read-only
STATUS mandatory
DESCRIPTION
"Number of Fax pages processed."
::= { iwfLogStatsEntry 15 }

iwfLogCompType OBJECT-TYPE
SYNTAX INTEGER{
  oFF(1),
  oN(2)
}
ACCESS read-only
STATUS mandatory
DESCRIPTION
"Compression Type."
::= { iwfLogStatsEntry 16 }

iwfLogCallErrorCode OBJECT-TYPE
SYNTAX INTEGER
ACCESS read-only
STATUS mandatory
DESCRIPTION
"Call Error Code."
::= { iwfLogStatsEntry 17 }

iwfLogModemSetupTime OBJECT-TYPE
SYNTAX INTEGER
ACCESS read-only
STATUS mandatory
DESCRIPTION
"Modem Setup Time"
::= { iwfLogStatsEntry 18 }

iwfLogCallConnectingTime OBJECT-TYPE
SYNTAX INTEGER
ACCESS read-only
STATUS mandatory
DESCRIPTION
"Call Connecting Time"
::= { iwfLogStatsEntry 19 }

iwfLogTotConnectTime OBJECT-TYPE
SYNTAX INTEGER
ACCESS read-only
STATUS mandatory
DESCRIPTION
"Total Connect Time"
::= { iwfLogStatsEntry 20 }

iwfCfgQncSrv OBJECT IDENTIFIER ::= { iwfGWY 38 }

iwfCfgQncSrvTable OBJECT-TYPE
SYNTAX SEQUENCE OF IwfCfgQncSrvEntry
ACCESS not-accessible
STATUS mandatory
DESCRIPTION
"Table containing objects for QNC (QUICK NETWORK CONNECTION) 
for IWF Gateway Cards in the chassis."
::= { iwfCfgQncSrv 1 }

iwfCfgQncSrvEntry OBJECT-TYPE
SYNTAX IwfCfgQncSrvEntry
ACCESS not-accessible
STATUS mandatory
DESCRIPTION
""
INDEX { iwfCfgQncSrvIndex, iwfCfgQncSrvIndex2 }
::= { iwfCfgQncSrvTable 1 }

IwfCfgQncSrvEntry ::=
SEQUENCE {
iwfCfgQncSrvIndex
    INTEGER,
iwfCfgQncSrvIndex2
    INTEGER,
iwfCfgQncDialedNumber
    DisplayString,
iwfCfgQncServiceType
    INTEGER,
iwfCfgQncPrimaryIpAddress
    IpAddress,
iwfCfgQncSecondaryIpAddress
    IpAddress
}

iwfCfgQncSrvIndex OBJECT-TYPE
SYNTAX INTEGER
ACCESS read-only
STATUS mandatory
DESCRIPTION
"A unique index identifying the Gateway Card to which the 
QNC objects pertain"
::= { iwfCfgQncSrvEntry 1 }

iwfCfgQncSrvIndex2 OBJECT-TYPE
SYNTAX INTEGER
ACCESS read-only
STATUS mandatory
DESCRIPTION
"A unique index identifying the call index to which the QNC 
objects pertain"
::= { iwfCfgQncSrvEntry 2 }

iwfCfgQncDialedNumber OBJECT-TYPE
SYNTAX DisplayString (SIZE(0..46))
ACCESS read-write
STATUS mandatory
DESCRIPTION
"This object represents the Telephone Number dialed for the 
QNC."
::= { iwfCfgQncSrvEntry 3 }

iwfCfgQncServiceType OBJECT-TYPE
SYNTAX INTEGER{
  notApplicable(1),
  twoStackQncTunneling(2),
  twoStackQncL2tpTunneling(3),
  twoStackQncPptpTunneling(4)
}
ACCESS read-write
STATUS mandatory
DESCRIPTION
"This object represents the Type of tunneling."
::= { iwfCfgQncSrvEntry 4 }

iwfCfgQncPrimaryIpAddress OBJECT-TYPE
SYNTAX IpAddress
ACCESS read-write
STATUS mandatory
DESCRIPTION
"This object represents the Primary HiperArc Server IP"
::= { iwfCfgQncSrvEntry 5 }

iwfCfgQncSecondaryIpAddress OBJECT-TYPE
SYNTAX IpAddress
ACCESS read-write
STATUS mandatory
DESCRIPTION
"This object represents the Secondary HiperArc Server IP"
::= { iwfCfgQncSrvEntry 6 }

iwfOprQncSrv OBJECT IDENTIFIER ::= { iwfGWY 39 }

iwfOprQncSrvTable OBJECT-TYPE
SYNTAX SEQUENCE OF IwfOprQncSrvEntry
ACCESS not-accessible
STATUS mandatory
DESCRIPTION
"Table containing operational objects for QNC (QUICK NETWORK 
CONNECTION) for IWF Gateway Cards in the chassis."
::= { iwfOprQncSrv 1 }

iwfOprQncSrvEntry OBJECT-TYPE
SYNTAX IwfOprQncSrvEntry
ACCESS not-accessible
STATUS mandatory
DESCRIPTION
""
INDEX { iwfQncSrvIndex, iwfQncSrvIndex2 }
::= { iwfOprQncSrvTable 1 }

IwfOprQncSrvEntry ::=
SEQUENCE {
iwfQncSrvIndex
    INTEGER,
iwfQncSrvIndex2
    INTEGER,
iwfQncDialedNumber
    DisplayString,
iwfQncServiceType
    INTEGER,
iwfQncPrimaryIpAddress
    IpAddress,
iwfQncSecondaryIpAddress
    IpAddress
}

iwfQncSrvIndex OBJECT-TYPE
SYNTAX INTEGER
ACCESS read-only
STATUS mandatory
DESCRIPTION
"A unique index identifying the Gateway Card to which the 
QNC objects pertain"
::= { iwfOprQncSrvEntry 1 }

iwfQncSrvIndex2 OBJECT-TYPE
SYNTAX INTEGER
ACCESS read-only
STATUS mandatory
DESCRIPTION
"A unique index identifying the call index to which the QNC 
objects pertain"
::= { iwfOprQncSrvEntry 2 }

iwfQncDialedNumber OBJECT-TYPE
SYNTAX DisplayString (SIZE(0..46))
ACCESS read-only
STATUS mandatory
DESCRIPTION
"This object represents the Telephone Number dialed for the 
QNC."
::= { iwfOprQncSrvEntry 3 }

iwfQncServiceType OBJECT-TYPE
SYNTAX INTEGER{
  notApplicable(1),
  twoStackQncTunneling(2),
  twoStackQncL2tpTunneling(3),
  twoStackQncPptpTunneling(4)
}
ACCESS read-only
STATUS mandatory
DESCRIPTION
"This object represents the Type of tunneling."
::= { iwfOprQncSrvEntry 4 }

iwfQncPrimaryIpAddress OBJECT-TYPE
SYNTAX IpAddress
ACCESS read-only
STATUS mandatory
DESCRIPTION
"This object represents the Primary HiperArc Server IP"
::= { iwfOprQncSrvEntry 5 }

iwfQncSecondaryIpAddress OBJECT-TYPE
SYNTAX IpAddress
ACCESS read-only
STATUS mandatory
DESCRIPTION
"This object represents the Secondary HiperArc Server IP"
::= { iwfOprQncSrvEntry 6 }

END
