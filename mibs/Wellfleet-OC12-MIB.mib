Wellfleet-OC12-MIB DEFINITIONS ::= BEGIN

-- Created 1998


    IMPORTS

      TimeTicks
        FROM RFC1155-SMI
      OBJECT-TYPE
        FROM RFC-1212
      wfSonetGroup
        FROM Wellfleet-COMMON-MIB;

    wfOc12ConfigTable OBJECT-TYPE
        SYNTAX	SEQUENCE OF WfOc12ConfigEntry
        ACCESS	not-accessible
        STATUS	mandatory
        DESCRIPTION
                "Statistics for the SONET medium table"
        ::= { wfSonetGroup 20 }

    wfOc12ConfigEntry OBJECT-TYPE
        SYNTAX	WfOc12ConfigEntry
        ACCESS	not-accessible
        STATUS	mandatory
        DESCRIPTION
                "An entry in the medium table"
        INDEX	{ wfOc12ConfigIndex }
        ::= { wfOc12ConfigTable 1 }

    WfOc12ConfigEntry ::= SEQUENCE {
    	    wfOc12ConfigDelete
    		INTEGER,
    	    wfOc12ConfigDisable
    		INTEGER,
    	    wfOc12ConfigIndex
    		INTEGER,
    	    wfOc12ConfigIfIndex
    		INTEGER,
	    wfOc12ConfigState
		INTEGER,
	    wfOc12ConfigLineStatus
		INTEGER,
	    wfOc12ConfigLastChange
		TimeTicks,
    	    wfOc12ConfigType
    		INTEGER,
    	    wfOc12ConfigLineCoding
    		INTEGER,
    	    wfOc12ConfigLineType
    		INTEGER,
	    wfOc12ConfigLoopbackConfig
    		INTEGER,
	    wfOc12ConfigManagerMethod
    		INTEGER
        }

    wfOc12ConfigDelete OBJECT-TYPE
        SYNTAX  INTEGER {
                    created(1),
                    deleted(2)
                }
        ACCESS  read-write
        STATUS  mandatory
        DESCRIPTION
                "Create/Delete parameter"
        DEFVAL  { created }
        ::= { wfOc12ConfigEntry 1 }

    wfOc12ConfigDisable OBJECT-TYPE
        SYNTAX  INTEGER {
                    enabled(1),
                    disabled(2)
                }
        ACCESS  read-write
        STATUS  mandatory
        DESCRIPTION
                "Create/Delete parameter"
        DEFVAL  { enabled }
        ::= { wfOc12ConfigEntry 2 }

    wfOc12ConfigIndex OBJECT-TYPE
        SYNTAX	INTEGER
        ACCESS	read-only
        STATUS	mandatory
        DESCRIPTION
                "Index for this physical Sonet interface."
        ::= { wfOc12ConfigEntry 3 }

    wfOc12ConfigIfIndex OBJECT-TYPE
        SYNTAX  INTEGER
        ACCESS  read-only
        STATUS  mandatory
        DESCRIPTION
                "this is value of ifIndex from the Interfaces table of
                MIB II (RFC 1213)."
        ::= { wfOc12ConfigEntry 4 }

    wfOc12ConfigState OBJECT-TYPE
        SYNTAX  INTEGER {
                    up(1),
                    down(2),
                    los(3),
                    lof(4),
                    ais(5),
                    rdi(6),
                    loopback(7),
                    notpresent(20)
                }
        ACCESS  read-only
        STATUS  mandatory
        DESCRIPTION
                "State of the OC12 Port."
        DEFVAL  { notpresent }
        ::= { wfOc12ConfigEntry 5 }

    wfOc12ConfigLineStatus OBJECT-TYPE
        SYNTAX  INTEGER {
                    noalarm(1),
                    los(2),
                    lof(4),
                    ais(8),
                    rdi(16),
                    loopback(128),
                    otherfailure(512)
                }
        ACCESS  read-only
        STATUS  mandatory
        DESCRIPTION
                "the status of the OC12"
        DEFVAL  { noalarm }
        ::= { wfOc12ConfigEntry 6 }

    wfOc12ConfigLastChange OBJECT-TYPE
        SYNTAX  TimeTicks
        ACCESS  read-only
        STATUS  mandatory
        DESCRIPTION
                "The value of sysUpTime at the time the interface entered
                its current operational state."
        ::= { wfOc12ConfigEntry 7 }

    wfOc12ConfigType OBJECT-TYPE
        SYNTAX	INTEGER {
		    sonet(1),
		    sdh(2)
		}
        ACCESS	read-only
        STATUS	mandatory
        DESCRIPTION
                "This variable identifies whether a SONET or a SDH signal is used
                across this interface."
        ::= { wfOc12ConfigEntry 8 }

    wfOc12ConfigLineCoding OBJECT-TYPE
        SYNTAX	INTEGER {
    		    other(1),
    		    b3zs(2),
    		    cmi(3),
    		    nrz(4),
    		    rz(5)
    		}
        ACCESS	read-write
        STATUS	mandatory
        DESCRIPTION
                "This variable describes the line coding for this interface."
        DEFVAL	{ nrz }
        ::= { wfOc12ConfigEntry 9 }

    wfOc12ConfigLineType OBJECT-TYPE
        SYNTAX	INTEGER {
    		    other(1),
    		    shortsinglemode(2),
    		    longsinglemode(3),
    		    multimode(4),
    		    coax(5),
    		    utp(6)
    		}
        ACCESS	read-write
        STATUS	mandatory
        DESCRIPTION
                "This variable describes the line type for this interface."
        DEFVAL	{ shortsinglemode }
        ::= { wfOc12ConfigEntry 10 }

    wfOc12ConfigLoopbackConfig OBJECT-TYPE
        SYNTAX  INTEGER {
                    noloop(1),
                    payloadloop(2),
                    lineloop(3)
                }
        ACCESS  read-write
        STATUS  mandatory
        DESCRIPTION
                "the loopback configuration of the OC12 interface"
        DEFVAL { noloop }
        ::= { wfOc12ConfigEntry 11 }

    wfOc12ConfigManagerMethod OBJECT-TYPE
        SYNTAX  INTEGER {
                    frac(1),
                    clear(2)
        }
        ACCESS  read-write
        STATUS  mandatory
        DESCRIPTION
                "This attribute has no affect on the Hardware configuration.
                This attribute is purely for any Network Management Tool
                to determine whether it configured the OC12 as Fractional
                or Clear."
        DEFVAL  { frac }
        ::= { wfOc12ConfigEntry 12 }




    END  -- Wellfleet-OC12-MIB
