--
-- MIB definition for the VocalTec VGK Server follows here:
--

	VGK-MIB DEFINITIONS ::= BEGIN

	IMPORTS
	TRAP-TYPE FROM RFC-1215
		enterprises, Counter, Gauge, TimeTicks
			FROM RFC1155-SMI
		OBJECT-TYPE
			FROM RFC-1212
		DisplayString
			FROM RFC1213-MIB;

	vocaltec	OBJECT IDENTIFIER	::= { enterprises 2516 }
	vgk		OBJECT IDENTIFIER	::= { vocaltec 3 }


	-- groups in the VGK Server MIB

	-- Statistics

	vgkSystem	OBJECT IDENTIFIER ::= { vgk 1 }

	user		OBJECT IDENTIFIER ::= { vgk 2 }

	vtgw		OBJECT IDENTIFIER ::= { vgk 3 }

	connection	OBJECT IDENTIFIER ::= { vgk 4 }

	security	OBJECT IDENTIFIER ::= { vgk 5 }

	internal	OBJECT IDENTIFIER ::= { vgk 6 }


	-- Config Parameters

	cfgConnection	OBJECT IDENTIFIER ::= { vgk 8 }

	license		OBJECT IDENTIFIER ::= { vgk 9 }

	database	OBJECT IDENTIFIER ::= { vgk 10 }

	eventLog	OBJECT IDENTIFIER ::= { vgk 11 }

	statistics	OBJECT IDENTIFIER ::= { vgk 12 }

	clients		OBJECT IDENTIFIER ::= { vgk 13 }

	telephony	OBJECT IDENTIFIER ::= { vgk 14 }

	server		OBJECT IDENTIFIER ::= { vgk 15 }


	-- More Statistics

	gatekeeper	OBJECT IDENTIFIER ::= { vgk 20 }

	gatekeeperProxy	OBJECT IDENTIFIER ::= { vgk 22 }

	domains 	OBJECT IDENTIFIER ::= { vgk 24 }

	surfNCall 	OBJECT IDENTIFIER ::= { vgk 28 }

	
	-- the vgksystem group

	-- This group contains general information about the VGK
	-- server.


	timeSpan	  OBJECT IDENTIFIER ::=	{ vgkSystem 3 }

	total OBJECT-TYPE
		SYNTAX  DisplayString
		ACCESS  read-only
		STATUS  mandatory
		DESCRIPTION
			"The time since the VGK server was started
			 in the following format: hh:mm:ss, where
			 hh - hours,
			 mm - minutes,
			 ss - seconds."
		 ::= { timeSpan 1 }

	interval OBJECT-TYPE
		SYNTAX  DisplayString
		ACCESS  read-only
		STATUS  mandatory
		DESCRIPTION
			"The time since the start of the current interval
			 in the following format: hh:mm:ss, where
			 hh - hours,
			 mm - minutes,
			 ss - seconds."
	::= { timeSpan 2 }

	timeStamp	  OBJECT IDENTIFIER ::= { vgkSystem 4 }


	total OBJECT-TYPE
		SYNTAX  DisplayString
		ACCESS  read-only
		STATUS  mandatory
		DESCRIPTION
			"Time stamp of the time when the VGK server was 
			started.All total counters in the MIB 
			(variables whose names is `total') count events
			that took place since this time."
	::= { timeStamp 1 }

	interval OBJECT-TYPE
		 SYNTAX  DisplayString
		 ACCESS  read-only
		 STATUS  mandatory
		 DESCRIPTION
			"Time stamp of the time when the current interval
			began.All interval counters in the MIB
			(variables whose names is `interval')
			count events that took place since this time."
	::= { timeStamp 2 }


	-- the user group

	-- This group contains information about subscriber objects in the
	-- VGK server.

	usrRequests	  OBJECT IDENTIFIER ::= { user 1 }

	usrReqLogins	 OBJECT IDENTIFIER ::= { usrRequests 1 }

	total OBJECT-TYPE
		 SYNTAX  Counter
		 ACCESS  read-only
		 STATUS  mandatory
		 DESCRIPTION
			"The number of subscriber login requests from
			H.323 terminals since the VGK server was started."
	::= { usrReqLogins	1 }

	interval OBJECT-TYPE
		 SYNTAX  Counter
		 ACCESS  read-only
		 STATUS  mandatory
		 DESCRIPTION
			"The number of subscriber login requests from
			H.323 terminals since the
			beginning of the current time interval."
	::= { usrReqLogins	2 }

	usrReqLogouts	OBJECT IDENTIFIER ::= { usrRequests 2 }

	total OBJECT-TYPE
		 SYNTAX  Counter
		 ACCESS  read-only
		 STATUS  mandatory
		 DESCRIPTION
			"The number of subscriber logout requests from
			H.323 terminals since the VGK server was started."
	::= { usrReqLogouts 1 }

	interval OBJECT-TYPE
		 SYNTAX  Counter
		 ACCESS  read-only
		 STATUS  mandatory
		 DESCRIPTION
			"The number of subscriber logout requests from
			 H.323 terminals since the
			 beginning of the current time interval."
	::= { usrReqLogouts 2 }

	usrReqGets	   OBJECT IDENTIFIER ::= { usrRequests 3 }

	total OBJECT-TYPE
		 SYNTAX  Counter
		 ACCESS  read-only
		 STATUS  mandatory
		 DESCRIPTION
			"The number of requests that query miscellaneous
			 subscriber attributes since the
			 VGK server was	started."
	::= { usrReqGets 1 }

	interval OBJECT-TYPE
		 SYNTAX  Counter
		 ACCESS  read-only
		 STATUS  mandatory
		 DESCRIPTION
			"The number of requests that query miscellaneous
			 subscriber attributes since the since the
			 beginning of the current time interval."
	::= { usrReqGets 2 }

	desk2Desk     OBJECT IDENTIFIER ::= { usrRequests 4 }

	total OBJECT-TYPE
		 SYNTAX  Counter
		 ACCESS  read-only
		 STATUS  mandatory
		 DESCRIPTION
			"The number of non-RAS address resolution requests
			between a desktop client and another desktop client
			since the VGK server was started."
	::= { desk2Desk 1 }

	interval OBJECT-TYPE
		 SYNTAX  Counter
		 ACCESS  read-only
		 STATUS  mandatory
		 DESCRIPTION
			 "The number of non-RAS address resolution requests
			  between a desktop client and another desktop client
			  since the beginning of the current time interval."
	::= { desk2Desk 2 }

	desk2Phone    OBJECT IDENTIFIER ::= { usrRequests 5 }

	total OBJECT-TYPE
		 SYNTAX  Counter
		 ACCESS  read-only
		 STATUS  mandatory
		 DESCRIPTION
			 "The number of non-RAS address resolution requests
			  between a desktop client and phone since the VGK
			  server was started."
	::= { desk2Phone 1 }

	interval OBJECT-TYPE
		 SYNTAX  Counter
		 ACCESS  read-only
		 STATUS  mandatory
		 DESCRIPTION
			 "The number of non-RAS address resolution requests
			  between a desktop client and phone  since the
			  beginning of the current time interval."
	::= { desk2Phone 2 }

	query	  OBJECT IDENTIFIER ::= { usrRequests 6 }

	total OBJECT-TYPE
		SYNTAX  Counter
		ACCESS  read-only
		STATUS  mandatory
		DESCRIPTION
			"The number of subscribers who attempted to call
			 other subscribers using an email address as target
			 address since the VGK server was started."
	::= { query 1 }

	interval OBJECT-TYPE
		SYNTAX  Counter
		ACCESS  read-only
		STATUS  mandatory
		DESCRIPTION
			"The number of subscribers who attempted to call
			other subscribers using an email address as target
			address since the beginning of the current time 
			interval."
	::= { query 2 }

	usrReqHeartBeat     OBJECT IDENTIFIER ::= { usrRequests 7 }

	total OBJECT-TYPE
		 SYNTAX  Counter
		 ACCESS  read-only
		 STATUS  mandatory
		 DESCRIPTION
			 "The number of subscriber heartbeats 
			  teminals since the VGK server was started."
	::= { usrReqHeartBeat 1 }

	interval OBJECT-TYPE
		SYNTAX  Counter
		ACCESS  read-only
		STATUS  mandatory
		DESCRIPTION
			"The number of subscriber heartbeats 
			 teminals since the beginning of the time interval."
	::= { usrReqHeartBeat 2 }

	usrReqCallStart     OBJECT IDENTIFIER ::= { usrRequests 8 }

	total OBJECT-TYPE
		SYNTAX  Counter
		ACCESS  read-only
		STATUS  mandatory
		DESCRIPTION
			"The number call starts  terminals
			 since the VGK server was started."
	::= { usrReqCallStart 1 }

	interval OBJECT-TYPE
		SYNTAX  Counter
		ACCESS  read-only
		STATUS  mandatory
		DESCRIPTION
			"The number call starts  terminals
			 since the beginning of the time interval."
	::= { usrReqCallStart 2 }

	usrReqCallEnd      OBJECT IDENTIFIER ::= { usrRequests 9 }

	total OBJECT-TYPE
		SYNTAX  Counter
		ACCESS  read-only
		STATUS  mandatory
		DESCRIPTION
			"The number of call ends  terminals
			 since the VGK server was started."
	::= { usrReqCallEnd 1 }

	interval OBJECT-TYPE
		SYNTAX  Counter
		ACCESS  read-only
		STATUS  mandatory
		DESCRIPTION
			"The number of call ends from an H.323 terminals
			 since the beginning of the time interval."
	::= { usrReqCallEnd 2 }

	usrReqMakeCall      OBJECT IDENTIFIER ::= { usrRequests	10 }

	total OBJECT-TYPE
		SYNTAX  Counter
		ACCESS  read-only
		STATUS  mandatory
		DESCRIPTION
			"The number of call setup requests sent 
			 terminals on the originating side of the call
			 since the VGK server was started."
	::= { usrReqMakeCall 1 }

	interval OBJECT-TYPE
		SYNTAX  Counter
		ACCESS  read-only
		STATUS  mandatory
		DESCRIPTION
			"The number of call setup requests sent 
			 terminals on the originating side of the call
			 since the beginning of the time interval."
	::= { usrReqMakeCall 2 }

	usrReqAnswerCall     OBJECT IDENTIFIER	::= { usrRequests 11 }

	total OBJECT-TYPE
		 SYNTAX  Counter
		 ACCESS  read-only
		 STATUS  mandatory
		 DESCRIPTION
			"The number of call setup requests sent 
			 terminals on the answering side of the call
			 since the VGK server was started."
	::= { usrReqAnswerCall  1 }

	interval OBJECT-TYPE
		SYNTAX  Counter
		ACCESS  read-only
		STATUS  mandatory
		DESCRIPTION
			"The number of call setup requests sent 
			 terminals on the answering side of the call
			 since the beginning of the time interval."
	::= { usrReqAnswerCall 2 }

	usrReqInformativeRBI	OBJECT IDENTIFIER ::= { usrRequests 12 }

	total OBJECT-TYPE
		 SYNTAX  Counter
		 ACCESS  read-only
		 STATUS  mandatory
		 DESCRIPTION
			 "The number of requests for billing information 
			  terminals since the
			 VGK server was started."
	::= { usrReqInformativeRBI  1 }

	interval OBJECT-TYPE
		SYNTAX  Counter
		ACCESS  read-only
		STATUS  mandatory
		DESCRIPTION
			"The number of requests for billing information 
			  terminals since the
			 beginning of the current time interval."
	::= { usrReqInformativeRBI 2 }


	failures	  OBJECT IDENTIFIER ::=	{ user 2 }

	failLogins	OBJECT IDENTIFIER ::=	{ failures 1 }

	total OBJECT-TYPE
		SYNTAX  Counter
		ACCESS  read-only
		STATUS  mandatory
		DESCRIPTION
			"The number of failed subscriber login requests from
			 H.323 terminals since the VGK server was started"
	::= { failLogins 1 }

	interval OBJECT-TYPE
		SYNTAX  Counter
		ACCESS  read-only
		STATUS  mandatory
		DESCRIPTION
			"The number of failed subscriber login requests from
			 H.323 terminals since the beginning of the time 
			 interval."
	::= { failLogins 2 }

	failLogouts       OBJECT IDENTIFIER ::=	{ failures 2 }

	total OBJECT-TYPE
		SYNTAX  Counter
		ACCESS  read-only
		STATUS  mandatory
		DESCRIPTION
			"The number of failed subscriber logout requests from
			 H.323  terminals since the VGK server was started."
	::= { failLogouts 1 }

	interval OBJECT-TYPE
		SYNTAX  Counter
		ACCESS  read-only
		STATUS  mandatory
		DESCRIPTION
			"The number of failed subscriber logout requests from
			 H.323 terminals since the
			 beginning of the time interval."
	::= { failLogouts 2 }

	failGets	  OBJECT IDENTIFIER ::=	{ failures 3 }

	total OBJECT-TYPE
		SYNTAX  Counter
		ACCESS  read-only
		STATUS  mandatory
		DESCRIPTION
			"The number of failed requests that query miscellaneous
			 subscriber attributes since the VGK server was started."
	::= { failGets 1 }

	interval OBJECT-TYPE
		SYNTAX  Counter
		ACCESS  read-only
		STATUS  mandatory
		DESCRIPTION
			"The number of failed requests that query miscellaneous
			 subscriber attributes since the beginning of the time
			 interval."
	::= { failGets 2 }

	failDesk2Desk     OBJECT IDENTIFIER ::=	{ failures 4 }

	total OBJECT-TYPE
		SYNTAX  Counter
		ACCESS  read-only
		STATUS  mandatory
		DESCRIPTION
			"The number of failed non-RAS address resolution requests
			 between a desktop client and another desktop client
			 since the VGK server was started."
	::= { failDesk2Desk 1 }

	interval OBJECT-TYPE
		SYNTAX  Counter
		ACCESS  read-only
		STATUS  mandatory
		DESCRIPTION
			"The number of failed non-RAS address resolution 
			 requests between a desktop client and another desktop
			 client since the beginning of the time interval."
	::= { failDesk2Desk 2 }

	failDesk2Phone    OBJECT IDENTIFIER ::=	{ failures 5 }

	total OBJECT-TYPE
		SYNTAX  Counter
		ACCESS  read-only
		STATUS  mandatory
		DESCRIPTION
			 "The number of failed non-RAS address
			 resolution requests between a desktop client 
			 and phone since the VGK server was started."
	::= { failDesk2Phone 1 }

	interval OBJECT-TYPE
		 SYNTAX  Counter
		 ACCESS  read-only
		 STATUS  mandatory
		 DESCRIPTION
			 "The number of failed non-RAS address
			 resolution requests between a desktop client 
			 and phone since the beginning of the time
			 interval."
	::= { failDesk2Phone 2 }

	failQuery	 OBJECT IDENTIFIER ::=	{ failures 6 }

	total OBJECT-TYPE
		 SYNTAX  Counter
		 ACCESS  read-only
		 STATUS  mandatory
		 DESCRIPTION
			"The number of subscribers who attempted to call
			 other subscribers using an email address as target
			 address and the attempts failed since the
			 VGK server was started."
	::= { failQuery 1 }

	interval OBJECT-TYPE
		SYNTAX  Counter
		ACCESS  read-only
		STATUS  mandatory
		DESCRIPTION
			"The number of subscribers who attempted to call
			other subscribers using an email address as target
			address and the attempts failed since
			the beginning of the time interval."
	::= { failQuery 2 }

	failHeartBeat     OBJECT IDENTIFIER ::=	{ failures 7 }

	total OBJECT-TYPE
		 SYNTAX  Counter
		 ACCESS  read-only
		 STATUS  mandatory
		 DESCRIPTION
			"The number of failed subscriber heartbeats from
			 H.323 terminals since
			 the VGK server was started."
	::= { failHeartBeat 1 }

	interval OBJECT-TYPE
		 SYNTAX  Counter
		 ACCESS  read-only
		 STATUS  mandatory
		 DESCRIPTION
			"The number of failed subscriber heartbeats from
			 H.323 terminals since
			 the beginning of the time interval."
	::= { failHeartBeat 2 }


	failCallStart      OBJECT IDENTIFIER ::= { failures 8 }

	total OBJECT-TYPE
		 SYNTAX  Counter
		 ACCESS  read-only
		 STATUS  mandatory
		 DESCRIPTION
			"The number of failed call starts 
			 terminals since the VGK server was started."
		 ::= { failCallStart 1 }

	interval OBJECT-TYPE
		 SYNTAX  Counter
		 ACCESS  read-only
		 STATUS  mandatory
		 DESCRIPTION
			"The number of failed call starts 
			 terminals since the beginning of the time interval."
	::= { failCallStart 2 }

	failCallEnd      OBJECT	IDENTIFIER ::= { failures 9 }

	total OBJECT-TYPE
		 SYNTAX  Counter
		 ACCESS  read-only
		 STATUS  mandatory
		 DESCRIPTION
			"The number of failed call ends 
			 terminals since the VGK server was started."
	::= { failCallEnd 1 }

	interval OBJECT-TYPE
		 SYNTAX  Counter
		 ACCESS  read-only
		 STATUS  mandatory
		 DESCRIPTION
			"The number of failed call ends 
			 terminals since the beginning of the time interval."
	::= { failCallEnd 2 }

	failMakeCall      OBJECT IDENTIFIER ::=	{ failures 10 }

	total OBJECT-TYPE
		 SYNTAX  Counter
		 ACCESS  read-only
		 STATUS  mandatory
		 DESCRIPTION
			 "The number of failed call setup requests sent from
			  H.323 terminals on the originating side of the call
			  since the VGK server was started."
	::= { failMakeCall	1 }

	interval OBJECT-TYPE
		 SYNTAX  Counter
		 ACCESS  read-only
		 STATUS  mandatory
		 DESCRIPTION
			"The number of failed call setup requests sent from
			H.323 terminals on the originating side of the call
			since the beginning of the time interval."
	::= { failMakeCall	2 }

	failAnswerCall      OBJECT IDENTIFIER ::= { failures 11 }

	total OBJECT-TYPE
		 SYNTAX  Counter
		 ACCESS  read-only
		 STATUS  mandatory
		 DESCRIPTION
		 "The number of failed call setup requests sent from
			H.323 terminals on the answering side of the call
			since the	VGK server was started."
	::= { failAnswerCall  1 }

	interval OBJECT-TYPE
		 SYNTAX  Counter
		 ACCESS  read-only
		 STATUS  mandatory
		 DESCRIPTION
			"The number of failed call setup requests sent from
			H.323 terminals on the answering side of the call
			since the beginning of the time interval."
	::= { failAnswerCall 2 }

	failInformativeRBI	OBJECT IDENTIFIER ::= { failures 12 }

	total OBJECT-TYPE
		 SYNTAX  Counter
		 ACCESS  read-only
		 STATUS  mandatory
		 DESCRIPTION
			"The number of failed requests for billing
			information  terminals 
			since the VGK server was started."
	::= { failInformativeRBI  1 }

	interval OBJECT-TYPE
		 SYNTAX  Counter
		 ACCESS  read-only
		 STATUS  mandatory
		 DESCRIPTION
			"The number of failed requests for billing
			information  terminals 
			since the beginning of the time interval."
	::= { failInformativeRBI 2 }


	sessions	  OBJECT IDENTIFIER ::=	{ user 3 }

	loggedOn OBJECT-TYPE
		 SYNTAX  Gauge
		 ACCESS  read-only
		 STATUS  mandatory
		 DESCRIPTION
			"The number of subscribers currently logged in
			 to the VGK via H.323 terminals."
	::= { sessions 1 }

	maxLoggedOn   OBJECT IDENTIFIER ::= { sessions 2 }

	total OBJECT-TYPE
		 SYNTAX  Gauge
		 ACCESS  read-only
		 STATUS  mandatory
		 DESCRIPTION
			"The maximum number of subscribers simultaneously
			logged in to the VGK via H.323 terminals since the
			VGK server was started."
	::= { maxLoggedOn 1 }

	interval OBJECT-TYPE
		 SYNTAX  Gauge
		 ACCESS  read-only
		 STATUS  mandatory
		 DESCRIPTION
			"The maximum number of subscribers simultaneously 
			logged in to the VGK via H.323 terminals since the
			beginning of the time interval."
	::= { maxLoggedOn 2 }

	avgLoggedOn	 OBJECT IDENTIFIER ::= { sessions 3 }

	interval OBJECT-TYPE
		 SYNTAX  Gauge
		 ACCESS  read-only
		 STATUS  mandatory
		 DESCRIPTION
			"The average number of subscribers simultaneously
			logged in to the VGK via H.323 terminals since the
			VGK server was started."
	::= { avgLoggedOn 1 }

	total OBJECT-TYPE
		 SYNTAX  Gauge
		 ACCESS  read-only
		 STATUS  mandatory
		 DESCRIPTION
			"The average number of subscribers simultaneously
			logged in to the VGK via H.323 terminals since the
			beginning of the time interval."
	::= { avgLoggedOn 2 }

	expired       OBJECT IDENTIFIER ::= { sessions 4 }

	total OBJECT-TYPE
		 SYNTAX  Counter
		 ACCESS  read-only
		 STATUS  mandatory
		 DESCRIPTION
			"The number of subscriber login sessions that expired
			since the VGK server was started."
	::= { expired 1 }

	interval OBJECT-TYPE
		 SYNTAX  Counter
		 ACCESS  read-only
		 STATUS  mandatory
		 DESCRIPTION
			"The number of subscriber login sessions that expired
			since the beginning of the time interval."
	::= { expired 2 }


	-- the vtgw group

	-- This group contains information about telephony gateway
	-- objects in the VGK server.

	vtgwRequests	  OBJECT IDENTIFIER	::= { vtgw 1 }

	vtgwReqLogins	 OBJECT IDENTIFIER	::= { vtgwRequests 1 }

	total OBJECT-TYPE
		 SYNTAX  Counter
		 ACCESS  read-only
		 STATUS  mandatory
		 DESCRIPTION
			 "The number of gateway login requests since the
			  VGK server was started."
	::= { vtgwReqLogins 1 }

	interval OBJECT-TYPE
		 SYNTAX  Counter
		 ACCESS  read-only
		 STATUS  mandatory
		 DESCRIPTION
			 "The number of gateway login requests since the
			  beginning of the time interval."
	::= { vtgwReqLogins 2 }

	vtgwReqLogouts	OBJECT IDENTIFIER	::= { vtgwRequests 2 }

	total OBJECT-TYPE
		 SYNTAX  Counter
		 ACCESS  read-only
		 STATUS  mandatory
		 DESCRIPTION
			 "The number of gateway logout requests since the
			  VGK server was started."
	::= { vtgwReqLogouts 1 }

	interval OBJECT-TYPE
		 SYNTAX  Counter
		 ACCESS  read-only
		 STATUS  mandatory
		 DESCRIPTION
			 "The number of gateway logout requests since the
			  beginning of the time interval."
	::= { vtgwReqLogouts 2 }

	vtgwReqGets	   OBJECT IDENTIFIER	::= { vtgwRequests 3 }

	total OBJECT-TYPE
		 SYNTAX  Counter
		 ACCESS  read-only
		 STATUS  mandatory
		 DESCRIPTION
			"The number of requests relating to miscellaneous
			gateway attributes since the VGK server was started."
	::= { vtgwReqGets 1 }

	interval OBJECT-TYPE
		 SYNTAX  Counter
		 ACCESS  read-only
		 STATUS  mandatory
		 DESCRIPTION
			 "The number of requests relating to miscellaneous
			  gateway attributes since the
			  beginning of the time interval."
	::= { vtgwReqGets 2	}

	phone2Phone	OBJECT IDENTIFIER ::= { vtgwRequests 4 }

	total OBJECT-TYPE
		 SYNTAX  Counter
		 ACCESS  read-only
		 STATUS  mandatory
		 DESCRIPTION
			"The number of ateway requests to resolve
			a telephone number to a list of destination gateways
			since the VGK server was started."
	::= { phone2Phone 1 }

	interval OBJECT-TYPE
		 SYNTAX  Counter
		 ACCESS  read-only
		 STATUS  mandatory
		 DESCRIPTION
			"The number of gateway requests to resolve
			a telephone number to a list of destination gateways
			since the beginning of the time interval."
	::= { phone2Phone 2 }

	vtgwReqHeartBeat      OBJECT IDENTIFIER ::= { vtgwRequests 5 }

	total OBJECT-TYPE
		 SYNTAX  Counter
		 ACCESS  read-only
		 STATUS  mandatory
		 DESCRIPTION
			"The number of gateway heartbeats since the
			VGK server was started."
	::= { vtgwReqHeartBeat 1 }

	interval OBJECT-TYPE
		 SYNTAX  Counter
		 ACCESS  read-only
		 STATUS  mandatory
		 DESCRIPTION
			"The number of gateway heartbeats since the
			beginning of the time interval."
	::= { vtgwReqHeartBeat 2 }

	vtgwReqCallStart     OBJECT IDENTIFIER ::= { vtgwRequests 6 }

	total OBJECT-TYPE
		 SYNTAX  Counter
		 ACCESS  read-only
		 STATUS  mandatory
		 DESCRIPTION
			"The number of call starts from gateways since the
			VGK server was started."
	::= { vtgwReqCallStart 1 }

	interval OBJECT-TYPE
		 SYNTAX  Counter
		 ACCESS  read-only
		 STATUS  mandatory
		 DESCRIPTION
			"The number of call starts from gateways since the
			beginning of the time interval."
	::= { vtgwReqCallStart 2 }

	vtgwReqCallEnd     OBJECT IDENTIFIER ::= { vtgwRequests 7 }

	total OBJECT-TYPE
		 SYNTAX  Counter
		 ACCESS  read-only
		 STATUS  mandatory
		 DESCRIPTION
			"The number of call ends from gateways since the
			VGK server was started."
	::= { vtgwReqCallEnd 1 }

	interval OBJECT-TYPE
		 SYNTAX  Counter
		 ACCESS  read-only
		 STATUS  mandatory
		 DESCRIPTION
			"The number of call ends from gateways since the
			beginning of the time interval."
	::= { vtgwReqCallEnd 2 }

	vtgwReqMakeCall     OBJECT IDENTIFIER ::= { vtgwRequests 8 }

	total OBJECT-TYPE
		 SYNTAX  Counter
		 ACCESS  read-only
		 STATUS  mandatory
		 DESCRIPTION
			"The number of call setup requests sent from
			gateways on the originating side of the call
			since the VGK server was started."
	::= { vtgwReqMakeCall 1 }

	interval OBJECT-TYPE
		 SYNTAX  Counter
		 ACCESS  read-only
		 STATUS  mandatory
		 DESCRIPTION
			"The number of call setup requests sent from 
			gateways on the originating side of the call
			since the beginning of the time interval."
	::= { vtgwReqMakeCall 2 }

	vtgwReqAnswerCall     OBJECT IDENTIFIER ::= { vtgwRequests 9 }

	total OBJECT-TYPE
		 SYNTAX  Counter
		 ACCESS  read-only
		 STATUS  mandatory
		 DESCRIPTION
			"The number of call setup requests sent from gateways
			on the answering side of the call since the
			VGK server was started."
	::= { vtgwReqAnswerCall  1 }

	interval OBJECT-TYPE
		 SYNTAX  Counter
		 ACCESS  read-only
		 STATUS  mandatory
		 DESCRIPTION
			"The number of call setup requests sent from gateways
			on the answering side of the call since the
			beginning of the time interval."
	::= { vtgwReqAnswerCall 2 }

	vtgwReqInformativeRBI	OBJECT IDENTIFIER ::= {	vtgwRequests 10 }

	total OBJECT-TYPE
		 SYNTAX  Counter
		 ACCESS  read-only
		 STATUS  mandatory
		 DESCRIPTION
			"The number of requests for billing information 
			from gateways since
			the VGK server was started."
	::= { vtgwReqInformativeRBI 1 }

	interval OBJECT-TYPE
		 SYNTAX  Counter
		 ACCESS  read-only
		 STATUS  mandatory
		 DESCRIPTION
			"The number of requests for billing information 
			from gateways since
			the beginning of the time interval."
	::= { vtgwReqInformativeRBI 2 }

	vtgwReqUpdateCallLog     OBJECT	IDENTIFIER ::= { vtgwRequests 11 }

	total OBJECT-TYPE
		 SYNTAX  Counter
		 ACCESS  read-only
		 STATUS  mandatory
		 DESCRIPTION
			"The number of times gateways sent the VGK updates
			with new call information since the
			VGK server was started."
	::= { vtgwReqUpdateCallLog	1 }

	interval OBJECT-TYPE
		 SYNTAX  Counter
		 ACCESS  read-only
		 STATUS  mandatory
		 DESCRIPTION
			"The number of times gateways sent the VGK updates
			with new call information since the
			beginning of the time interval."
	::= { vtgwReqUpdateCallLog 2 }

	vtgwFailures	  OBJECT IDENTIFIER	::= { vtgw 2 }

	vtgwFailLogins	OBJECT IDENTIFIER	::= { vtgwFailures 1 }

	total OBJECT-TYPE
		 SYNTAX  Counter
		 ACCESS  read-only
		 STATUS  mandatory
		 DESCRIPTION
			"The number of failed gateway login requests
			since the VGK server was started."
	::= { vtgwFailLogins 1 }

	interval OBJECT-TYPE
		 SYNTAX  Counter
		 ACCESS  read-only
		 STATUS  mandatory
		 DESCRIPTION
			"The number of failed gateway login requests
			since the beginning of the time interval."
	::= { vtgwFailLogins 2 }

	vtgwFailLogouts       OBJECT IDENTIFIER	::= { vtgwFailures 2 }

	total OBJECT-TYPE
		 SYNTAX  Counter
		 ACCESS  read-only
		 STATUS  mandatory
		 DESCRIPTION
			"The number of failed gateway logout requests since
			the VGK server was started."
	::= { vtgwFailLogouts 1 }

	interval OBJECT-TYPE
		 SYNTAX  Counter
		 ACCESS  read-only
		 STATUS  mandatory
		 DESCRIPTION
			"The number of failed gateway logout requests since
			the beginning of the time interval."
	::= { vtgwFailLogouts 2 }

	vtgwFailGets	  OBJECT IDENTIFIER	::= { vtgwFailures 3 }

	total OBJECT-TYPE
		 SYNTAX  Counter
		 ACCESS  read-only
		 STATUS  mandatory
		 DESCRIPTION
			"The number of failed requests that query
			miscellaneous gateway attributes since
			the VGK server was started."
	::= { vtgwFailGets 1 }

	interval OBJECT-TYPE
		 SYNTAX  Counter
		 ACCESS  read-only
		 STATUS  mandatory
		 DESCRIPTION
			"The number of failed requests that query
			miscellaneous gateway attributes since
			the beginning of the time interval."
	::= { vtgwFailGets 2 }

	vtgwFailPhone2Phone   OBJECT IDENTIFIER ::= { vtgwFailures 4 }

	total OBJECT-TYPE
		 SYNTAX  Counter
		 ACCESS  read-only
		 STATUS  mandatory
		 DESCRIPTION
			"The number of gateway requests to resolve
			a telephone number to a list of destination gateways
			that failed since the VGK server was started."
	::= { vtgwFailPhone2Phone 1   }

	interval OBJECT-TYPE
		 SYNTAX  Counter
		 ACCESS  read-only
		 STATUS  mandatory
		 DESCRIPTION
			"The number of gateway requests to resolve
			a telephone number to a list of destination gateways
			that failed since the beginning of the time interval."
	::= { vtgwFailPhone2Phone 2   }

	vtgwFailHeartBeat     OBJECT IDENTIFIER ::= { vtgwFailures 5 }

	total OBJECT-TYPE
		 SYNTAX  Counter
		 ACCESS  read-only
		 STATUS  mandatory
		 DESCRIPTION
			"The number of failed heartbeats from
			gateways since the VGK server was started."
	::= { vtgwFailHeartBeat 1 }

	interval OBJECT-TYPE
		 SYNTAX  Counter
		 ACCESS  read-only
		 STATUS  mandatory
		 DESCRIPTION
			"The number of failed heartbeats from
			gateways since the beginning of the time interval."
	::= { vtgwFailHeartBeat 2 }

	vtgwFailCallStart     OBJECT IDENTIFIER ::= { vtgwFailures 6 }

	total OBJECT-TYPE
		 SYNTAX  Counter
		 ACCESS  read-only
		 STATUS  mandatory
		 DESCRIPTION
			"The number of failed call starts from gateways
			since the VGK server was started."
	::= { vtgwFailCallStart 1 }

	interval OBJECT-TYPE
		 SYNTAX  Counter
		 ACCESS  read-only
		 STATUS  mandatory
		 DESCRIPTION
			"The number of failed call starts from gateways
			since the beginning of the time interval."
	::= { vtgwFailCallStart 2 }

	vtgwFailCallEnd     OBJECT IDENTIFIER ::= { vtgwFailures 7 }

	total OBJECT-TYPE
		 SYNTAX  Counter
		 ACCESS  read-only
		 STATUS  mandatory
		 DESCRIPTION
			"The number of failed call  ends from gateways
			since the VGK server was started."
	::= { vtgwFailCallEnd 1 }

	interval OBJECT-TYPE
		 SYNTAX  Counter
		 ACCESS  read-only
		 STATUS  mandatory
		 DESCRIPTION
			"The number of failed call ends from gateways
			since the beginning of the time interval."
	::= { vtgwFailCallEnd 2 }

	vtgwFailMakeCall     OBJECT IDENTIFIER ::= { vtgwFailures 8 }

	total OBJECT-TYPE
		 SYNTAX  Counter
		 ACCESS  read-only
		 STATUS  mandatory
		 DESCRIPTION
			"The number of failed call setup requests sent from
			gateways on the originating side of the call since
			the VGK server was started."
	::= { vtgwFailMakeCall 1 }

	interval OBJECT-TYPE
		 SYNTAX  Counter
		 ACCESS  read-only
		 STATUS  mandatory
		 DESCRIPTION
			"The number of failed call setup requests sent from
			gateways on the originating side of the call since
			the beginning of the time interval."
	::= { vtgwFailMakeCall 2 }

	vtgwFailAnswerCall     OBJECT IDENTIFIER ::= { vtgwFailures 9 }

	total OBJECT-TYPE
		 SYNTAX  Counter
		 ACCESS  read-only
		 STATUS  mandatory
		 DESCRIPTION
			"The number of failed call setup requests sent from
			gateways on the answering side of the call since the
			VGK server was started."
	::= { vtgwFailAnswerCall  1	}

	interval OBJECT-TYPE
		 SYNTAX  Counter
		 ACCESS  read-only
		 STATUS  mandatory
		 DESCRIPTION
			"The number of failed call setup requests sent from
			gateways on the answering side of the call since the
			beginning of the time interval."
	::= { vtgwFailAnswerCall 2 }

	vtgwFailInformativeRBI	OBJECT IDENTIFIER ::= { vtgwFailures 10 }

	total OBJECT-TYPE
		 SYNTAX  Counter
		 ACCESS  read-only
		 STATUS  mandatory
		 DESCRIPTION
			"The number of failed requests for billing
			information from gateways
			since the VGK server was started."
	::= { vtgwFailInformativeRBI  1 }

	interval OBJECT-TYPE
		 SYNTAX  Counter
		 ACCESS  read-only
		 STATUS  mandatory
		 DESCRIPTION
			"The number of failed requests for billing
			information from gateways 
			since the beginning of the time interval."
	::= { vtgwFailInformativeRBI 2 }

	vtgwFailUpdateCallLog   OBJECT IDENTIFIER ::= { vtgwFailures 11 }

	total OBJECT-TYPE
		 SYNTAX  Counter
		 ACCESS  read-only
		 STATUS  mandatory
		 DESCRIPTION
			"The number of times gateways sent the VGK updates
			with new call information and the updates
			failed since the VGK server was started."
	::= { vtgwFailUpdateCallLog  1 }

	interval OBJECT-TYPE
		 SYNTAX  Counter
		 ACCESS  read-only
		 STATUS  mandatory
		 DESCRIPTION
			"The number of times gateways sent the VGK updates
			with new call information and the updates
			failed since the beginning of the time interval."
	::= { vtgwFailUpdateCallLog	2 }

	vtgwSessions	  OBJECT IDENTIFIER	::= { vtgw 3 }

	loggedOn OBJECT-TYPE
		 SYNTAX  Gauge
		 ACCESS  read-only
		 STATUS  mandatory
		 DESCRIPTION
			"The number of gateways currently logged in to the VGK."
	::= { vtgwSessions 1 }

	vtgwSessionMaxLogon    OBJECT IDENTIFIER ::= { vtgwSessions 2 }

	total OBJECT-TYPE
		 SYNTAX  Gauge
		 ACCESS  read-only
		 STATUS  mandatory
		 DESCRIPTION
			"The maximum number of simultaneously logged in
			gateways since the VGK server was started."
	::= { vtgwSessionMaxLogon 1 }

	interval OBJECT-TYPE
		 SYNTAX  Gauge
		 ACCESS  read-only
		 STATUS  mandatory
		 DESCRIPTION
			"The maximum number of simultaneously logged in
			gateways since the beginning of the time interval."
	::= { vtgwSessionMaxLogon 2 }

	vtgwSessionAvgLogon	OBJECT IDENTIFIER ::= { vtgwSessions 3 }

	interval OBJECT-TYPE
		 SYNTAX  Gauge
		 ACCESS  read-only
		 STATUS  mandatory
		 DESCRIPTION
			"The average number of simultaneously logged in
			gateways since the VGK server was started."
	::= { vtgwSessionAvgLogon 1 }

	total OBJECT-TYPE
		 SYNTAX  Gauge
		 ACCESS  read-only
		 STATUS  mandatory
		 DESCRIPTION
			"The average number of simultaneously logged in
			gateways since the beginning of the time interval."
	::= { vtgwSessionAvgLogon 2 }

	vtgwSessionExpired	OBJECT IDENTIFIER ::= { vtgwSessions 4 }

	total OBJECT-TYPE
		 SYNTAX  Counter
		 ACCESS  read-only
		 STATUS  mandatory
		 DESCRIPTION
			"The number of gateway login sessions that
			expired since the VGK server was started."
	::= { vtgwSessionExpired 1 }

	interval OBJECT-TYPE
		 SYNTAX  Counter
		 ACCESS  read-only
		 STATUS  mandatory
		 DESCRIPTION
			"The number of gateway login sessions that
			expired since the beginning of the time interval."
	::= { vtgwSessionExpired 2 }


	-- the connection group

	-- This group contains summary information about all objects in
	-- the VGK server (user + telephony gateway).
	-- as well as information about the connections

	totalRequests	 OBJECT IDENTIFIER	::= { connection 1 }

	all	   OBJECT IDENTIFIER	::= { totalRequests 1 }

	total OBJECT-TYPE
		 SYNTAX  Counter
		 ACCESS  read-only
		 STATUS  mandatory
		 DESCRIPTION
			 "The total number of client requests that arrived
			at the VGK since the VGK server was started."
	::= { all 1 }

	interval OBJECT-TYPE
		 SYNTAX  Counter
		 ACCESS  read-only
		 STATUS  mandatory
		 DESCRIPTION
			 "The total number of client requests that arrived
			at the VGK since the beginning of the time interval."
	::= { all 2 }


	connections      OBJECT IDENTIFIER ::= { connection 2 }

	total OBJECT-TYPE
		 SYNTAX  Counter
		 ACCESS  read-only
		 STATUS  mandatory
		 DESCRIPTION
			"The total number of client connections that have
			been made with the VGK since the
			VGK server was started."
	::= { connections 1 }

	interval OBJECT-TYPE
		 SYNTAX  Counter
		 ACCESS  read-only
		 STATUS  mandatory
		 DESCRIPTION
			"The total number of client connections that have
			been made with the VGK since the
			beginning of the time interval."
	::= { connections 2 }

	disconnects  OBJECT IDENTIFIER	::= { connection 3 }

	total OBJECT-TYPE
		 SYNTAX  Counter
		 ACCESS  read-only
		 STATUS  mandatory
		 DESCRIPTION
			"The total number of client connections with the VGK
			that disconnected normally since the
			VGK server was started."
	::= { disconnects 1 }

	interval OBJECT-TYPE
		 SYNTAX  Counter
		 ACCESS  read-only
		 STATUS  mandatory
		 DESCRIPTION
			"The total number of client connections with the VGK
			that disconnected normally since the
			beginning of the time interval."
	::= { disconnects 2 }


	currentConnections	 OBJECT IDENTIFIER ::= { connection 4 }

	connections OBJECT-TYPE
		 SYNTAX  Gauge
		 ACCESS  read-only
		 STATUS  mandatory
		 DESCRIPTION
			"The number of client connections currently active 
			at the VGK."
	::= { currentConnections 1	}


	maxConnection OBJECT IDENTIFIER ::= { connection 5 }

	total OBJECT-TYPE
		 SYNTAX  Gauge
		 ACCESS  read-only
		 STATUS  mandatory
		 DESCRIPTION
			"The maximum number of simultaneously active
			connections between clients and the VGK since the
			VGK server was started."
	::= { maxConnection 1 }

	interval OBJECT-TYPE
		 SYNTAX  Gauge
		 ACCESS  read-only
		 STATUS  mandatory
		 DESCRIPTION
			"The maximum number of simultaneously active
			connections between clients and the VGK since the
			beginning of the time interval."
	::= { maxConnection 2 }

	expiredConnection	OBJECT IDENTIFIER ::= { connection 6 }

	total OBJECT-TYPE
		 SYNTAX  Counter
		 ACCESS  read-only
		 STATUS  mandatory
		 DESCRIPTION
			"The number of client connections with the VGK
			that expired since the VGK server was started."
	::= { expiredConnection 1 }

	interval OBJECT-TYPE
		 SYNTAX  Counter
		 ACCESS  read-only
		 STATUS  mandatory
		 DESCRIPTION
			"The number of client connections with the VGK
			that expired since the beginning of the time interval."
	::= { expiredConnection  2	}



	avgConnections       OBJECT IDENTIFIER ::= { connection 7 }

	total OBJECT-TYPE
		 SYNTAX  Counter
		 ACCESS  read-only
		 STATUS  mandatory
		 DESCRIPTION
			"The average number of simultaneously active
			connections between clients and the VGK since
			the VGK server was started."
	::= { avgConnections 1 }

	interval OBJECT-TYPE
		 SYNTAX  Counter
		 ACCESS  read-only
		 STATUS  mandatory
		 DESCRIPTION
			"The average number of simultaneously active
			connections between clients and the VGK since
			the beginning of the time interval."
	::= { avgConnections 2 }

	connectionTime       OBJECT IDENTIFIER ::= { connection  8 }


	avgConnectionTime  OBJECT IDENTIFIER	::= { connectionTime 1 }

	total OBJECT-TYPE
		 SYNTAX  Counter
		 ACCESS  read-only
		 STATUS  mandatory
		 DESCRIPTION
			"The average time a client connection was active
			at the VGK since the VGK server was started
			(in seconds)."
	::= { avgConnectionTime 1 }

	interval OBJECT-TYPE
		 SYNTAX  Counter
		 ACCESS  read-only
		 STATUS  mandatory
		 DESCRIPTION
			"The average time a client connection was active at
			the VGK since the beginning of the time interval
			(in seconds)."
	::= { avgConnectionTime 2 }


	maxConnectionTime  OBJECT IDENTIFIER	::= { connectionTime 2 }

	total OBJECT-TYPE
		 SYNTAX  Counter
		 ACCESS  read-only
		 STATUS  mandatory
		 DESCRIPTION
			"The maximum time a client connection was active at
			the VGK since the VGK server was started
			(in seconds)."
	::= { maxConnectionTime 1 }

	interval OBJECT-TYPE
		 SYNTAX  Counter
		 ACCESS  read-only
		 STATUS  mandatory
		 DESCRIPTION
			"The maximum time a client connection was active at
			the VGK since the beginning of the time interval
			(in seconds)."
	::= { maxConnectionTime 2 }


	minConnectionTime  OBJECT IDENTIFIER	::= { connectionTime 3 }

	total OBJECT-TYPE
		 SYNTAX  Counter
		 ACCESS  read-only
		 STATUS  mandatory
		 DESCRIPTION
			"The minimum time a client connection was active at the
			VGK since the VGK server was started (in seconds)."
	::= { minConnectionTime 1 }

	interval OBJECT-TYPE
		 SYNTAX  Counter
		 ACCESS  read-only
		 STATUS  mandatory
		 DESCRIPTION
			"The minimum time a client connection was active at the
			VGK since the beginning of the time interval
			(in seconds)."
	::= { minConnectionTime 2 }


	calls       OBJECT IDENTIFIER ::= { connection	9 }

	currentCalls OBJECT-TYPE
		 SYNTAX  Gauge
		 ACCESS  read-only
		 STATUS  mandatory
		 DESCRIPTION
			"The number of active calls currently being
			managed by he VGK."
	::= { calls 1 }

	maxCalls  OBJECT IDENTIFIER ::= { calls 2 }

	total OBJECT-TYPE
		 SYNTAX  Counter
		 ACCESS  read-only
		 STATUS  mandatory
		 DESCRIPTION
			"The maximum number of simultaneous calls that were
			managed by the VGK since the VGK server was started."
	::= { maxCalls 1 }

	interval OBJECT-TYPE
		 SYNTAX  Counter
		 ACCESS  read-only
		 STATUS  mandatory
		 DESCRIPTION
			"The maximum number of simultaneous calls that were
			managed by the VGK since
			the beginning of the time interval."
	::= { maxCalls 2 }



	-- the	security group

	-- This group contains information about security events in the
	-- VGK server.

	authentFailures   OBJECT IDENTIFIER ::= { security 1 }

	total OBJECT-TYPE
		 SYNTAX  Counter
		 ACCESS  read-only
		 STATUS  mandatory
		 DESCRIPTION
			"The number of client authentication failures since
			the VGK server was started."
	::= { authentFailures 1 }

	interval OBJECT-TYPE
		 SYNTAX  Counter
		 ACCESS  read-only
		 STATUS  mandatory
		 DESCRIPTION
			"The number of client authentication failures since
			the beginning of the time interval."
	::= { authentFailures 2 }

	authorzFailures   OBJECT IDENTIFIER ::= { security 2 }

	total OBJECT-TYPE
		 SYNTAX  Counter
		 ACCESS  read-only
		 STATUS  mandatory
		 DESCRIPTION
			"The number of client authorization failures since
			the VGK server was started."
	::= { authorzFailures 1 }

	interval OBJECT-TYPE
		 SYNTAX  Counter
		 ACCESS  read-only
		 STATUS  mandatory
		 DESCRIPTION
			"The number of client authorization failures since
			the beginning of the time interval."
	::= { authorzFailures 2 }

	licenseErrors      OBJECT IDENTIFIER ::= { security 3 }

	total OBJECT-TYPE
		 SYNTAX  Counter
		 ACCESS  read-only
		 STATUS  mandatory
		 DESCRIPTION
			"The number of license errors that occurred
			at the VGK since the VGK server was started."
	::= { licenseErrors 1 }

	interval OBJECT-TYPE
		 SYNTAX  Counter
		 ACCESS  read-only
		 STATUS  mandatory
		 DESCRIPTION
			"The number of license errors that occurred
			at the VGK since the beginning of the time interval."
	::= { licenseErrors 2 }


	-- the internal group

	-- This group contains information about internal errors in the
	-- VGK server.

	memAllocFailures  OBJECT IDENTIFIER ::= { internal 1 }

	total OBJECT-TYPE
		 SYNTAX  Counter
		 ACCESS  read-only
		 STATUS  mandatory
		 DESCRIPTION
			"The number of memory allocation failures at the VGK
			since the VGK server was started."
	::= { memAllocFailures 1 }

	interval OBJECT-TYPE
		 SYNTAX  Counter
		 ACCESS  read-only
		 STATUS  mandatory
		 DESCRIPTION
			"The number of memory allocation failures at the VGK
			since the beginning of the time interval."
	::= { memAllocFailures 2 }



	-- the cfgConnection group

	-- This group contains configuration parameters relating to
	-- the VGK server's connections

	ports	OBJECT IDENTIFIER ::= { cfgConnection 1 }

	rasPort OBJECT-TYPE
		SYNTAX  INTEGER
		ACCESS  read-write
		STATUS  mandatory
		DESCRIPTION
			"The number of the port at which H.323 RAS requests
			arrive."
		DEFVAL  { 1719 }
	::= { ports 1 }

	vgkPort OBJECT-TYPE
		SYNTAX  INTEGER
		ACCESS  read-write
		STATUS  mandatory
		DESCRIPTION
			"The number of the port at which non-RAS requests arrive."
		DEFVAL  { 25793 }
	::= { ports 2 }

	admin	OBJECT IDENTIFIER ::= { cfgConnection 2 }

	adminPort OBJECT-TYPE
		SYNTAX  INTEGER
		ACCESS  read-write
		STATUS  mandatory
		DESCRIPTION
			"The number of the port at which administration
			requests to the VGK server arrive (RCAM port)."
		DEFVAL  { 9123 }
	::= { admin 1 }

	adminClient OBJECT-TYPE
		SYNTAX  DisplayString
		ACCESS  read-write
		STATUS  mandatory
		DESCRIPTION
			 "The VGK server's admin (RCAM) client name."
	::= { admin 2 }

	connectionExpirationInterval OBJECT-TYPE
		SYNTAX  INTEGER
		ACCESS  read-write
		STATUS  mandatory
		DESCRIPTION
			"How often the VGK server checks for expired client
			connections(in seconds)."
		DEFVAL  { 300 }
	::= { cfgConnection 3 }


	timeout  OBJECT IDENTIFIER ::=	{ cfgConnection 4 }

	connectionTimeout OBJECT-TYPE
		SYNTAX  INTEGER
		ACCESS  read-write
		STATUS  mandatory
		DESCRIPTION
			"The number of seconds that can elapse before
			a connection between the gatekeeper and a client
			is timed out."
		DEFVAL  { 60 }
	::= { timeout 1 }

	requestTimeout OBJECT-TYPE
		SYNTAX  INTEGER
		ACCESS  read-write
		STATUS  mandatory
		DESCRIPTION
			"The number of seconds that can elapse before
			a request is timed out."
		DEFVAL  { 30 }
	::= { timeout 2 }





	-- the	database group

	-- This group contains the Database related information

	connect  OBJECT IDENTIFIER ::= { database 1 }

	userId	OBJECT-TYPE
		 SYNTAX  DisplayString
		 ACCESS  read-write
		 STATUS  mandatory
		 DESCRIPTION
			 "ID used by the VGK to connect to the database."
	::= { connect 1 }

	replication  OBJECT IDENTIFIER	::= { database 2 }

	pollingInterval OBJECT-TYPE
		SYNTAX  INTEGER
		ACCESS  read-write
		STATUS  mandatory
		DESCRIPTION
			 "How often the VGK checks for changes in the
			 database (in seconds)."
		DEFVAL  { 60 }
	::= { database 3 }


	-- the eventLog group

	-- This group contains the log related information

	fileName OBJECT-TYPE
		 SYNTAX  DisplayString
		 ACCESS  read-write
		 STATUS  mandatory
		 DESCRIPTION
			 "The full pathname of the VGK event log file."
	::= { eventLog 1 }

	maxFileSize OBJECT-TYPE
		SYNTAX  DisplayString
		ACCESS  read-write
		STATUS  mandatory
		DESCRIPTION
			"How large the VGK event log file can grow before
			it is closed and a new event log file is opened.
			The format of the string is: <number><letter>,
			where:
			<number> is an integer in the range 0..2147483647,
			<letter> is one of the letters in uppercase:
				B - for bytes,
				K - for Kbytes,
				M - for Mbytes,
			for example: '20M', '4560K'."
		DEFVAL  { "1M" }
	::= { eventLog 2 }


	maxFileAge OBJECT-TYPE
		SYNTAX  DisplayString
		ACCESS  read-write
		STATUS  mandatory
		DESCRIPTION
			"How long the VGK event log file can be open before
			it is closed and a new event  log file is opened.
			The format of the string is: <number><letter>,
			where:
			<number> is an integer in the range 0..4294967295,
			<letter> is one of the letters in uppercase:
				S - for seconds,
				M - for minutes,
				H - for hours,
				D - for days,
				W - for weeks,
			for example: '24H', '500D'."
		DEFVAL  { "1D" }
	::= { eventLog 3 }


	-- the statistics group
	-- This group contains the statistics related information

	collectionInterval OBJECT-TYPE
		 SYNTAX  INTEGER
		 ACCESS  read-write
		 STATUS  mandatory
		 DESCRIPTION
			"How often (in seconds) interval statistics are reset."
		DEFVAL  { 86400 }	-- 24 hrs
	::= { statistics 1 }

	logToFile OBJECT-TYPE
		 SYNTAX  INTEGER
		 ACCESS  read-write
		 STATUS  mandatory
		 DESCRIPTION
			"Whether the statistics should be written to file
			at each interval:
			1 = yes, 0 = no."
	::= { statistics 2 }


	--  The  clients Group

	desktop  OBJECT IDENTIFIER ::=	{ clients 1 }

	defaultTtl OBJECT-TYPE
		SYNTAX  INTEGER
		ACCESS  read-write
		STATUS  mandatory
		DESCRIPTION
			"Default time to live (in seconds) for desktop 
			clients."
		DEFVAL  { 900 }
	::= { desktop 1 }

	expirationInterval OBJECT-TYPE
		SYNTAX  INTEGER
		ACCESS  read-write
		STATUS  mandatory
		DESCRIPTION
			"How often (in seconds) the VGK checks for
			expired desktop clients."
		DEFVAL  { 300 }
	::= { desktop 2 }

	gateway  OBJECT IDENTIFIER ::=	{ clients 2 }

	defaultTtl OBJECT-TYPE
		 SYNTAX  INTEGER
		 ACCESS  read-write
		 STATUS  mandatory
		 DESCRIPTION
			"Default time to live (in seconds) for gateway 
			clients."
	::= { gateway 1 }

	expirationInterval OBJECT-TYPE
		 SYNTAX  INTEGER
		 ACCESS  read-write
		 STATUS  mandatory
		 DESCRIPTION
			"How often (in seconds) the VGK checks for
			expired gateway clients."
	::= { gateway 2 }

	-- The telephony Group
	-- All things telephony related

	policy   OBJECT	IDENTIFIER ::= { telephony 1 }

	maxGatewaysToReturn OBJECT-TYPE
		SYNTAX  INTEGER
		ACCESS  read-write
		STATUS  mandatory
		DESCRIPTION
			"Maximum number of gateways the VKG will return in
			the list of remote gateways that can service a call."
		DEFVAL  { 10 }
	::= { policy 1 }

	enforceVersionCompatibility OBJECT-TYPE
		SYNTAX  INTEGER
		ACCESS  read-write
		STATUS  mandatory
		DESCRIPTION
			"Include in the list of remote gateways that
			can service a call only gateways with the same
			(or compatible) version as the originating
			(requesting) gateway:
			1 = yes, 0 = no."
		DEFVAL  { 0 }
	::= { policy 2 }

	randomPolicy OBJECT-TYPE
		 SYNTAX  INTEGER
		 ACCESS  read-write
		 STATUS  mandatory
		 DESCRIPTION
			"Shuffle the list of gateways that can service a call
			to evenly distribute the call load:
			1 = yes, 0 = no."
		DEFVAL  { 1 }
	::= { policy 3 }

	localityPolicy	OBJECT-TYPE
		 SYNTAX  INTEGER
		 ACCESS  read-write
		 STATUS  mandatory
		 DESCRIPTION
			"Order the list of remote gateways that can
			service a call by area/country code with gateways
			that close to the destination phone number ordered
			first in the list:
			1 = yes, 0 = no."
		DEFVAL  { 1 }
	::= { policy 4 }

	onlinePolicy OBJECT-TYPE
		 SYNTAX  INTEGER
		 ACCESS  read-write
		 STATUS  mandatory
		 DESCRIPTION
			"Include in the list of remote gateways that
			 can service a call only the gateways known
			 to be online:
			 1 = yes, 0 = no."
		DEFVAL  { 1 }
	::= { policy 5 }

	hoursOfServicePolicy OBJECT-TYPE
		 SYNTAX  INTEGER
		 ACCESS  read-write
		 STATUS  mandatory
		 DESCRIPTION
			"Include in the list of remote gateways that
			can service a call only the gateways known to be
			in service at the time of the request:
			1 = yes, 0 = no."
		DEFVAL  { 1 }
	::= { policy 6 }

	manualOrAutoPriorities	OBJECT-TYPE
		 SYNTAX  INTEGER
		 ACCESS  read-write
		 STATUS  mandatory
		 DESCRIPTION
			"Use manual priorities established in database
			to order the list of remote gateways that can
			service a call:
			1 = yes, 0 = no."
	::= { policy 7 }

	-- The server group

	serverName OBJECT-TYPE
		 SYNTAX  DisplayString
		 ACCESS  read-write
		 STATUS  mandatory
		 DESCRIPTION
			"The name assigned to VGK server."
	::= { server 1 }

	-- New stuff

	-- the gatekeeper group

	-- This group contains information about gatekeeper objects in the
	-- VGK server.

	gkRequests	 OBJECT IDENTIFIER ::= { gatekeeper 1 }

	gkReqLogins	 OBJECT IDENTIFIER ::= { gkRequests 1 }

	total OBJECT-TYPE
		 SYNTAX  Counter
		 ACCESS  read-only
		 STATUS  mandatory
		 DESCRIPTION
			"The number of gatekeeper login requests
			 since the VGK server was started."
	::= { gkReqLogins	1 }

	interval OBJECT-TYPE
		 SYNTAX  Counter
		 ACCESS  read-only
		 STATUS  mandatory
		 DESCRIPTION
			"The number of gatekeeper login requests 
			 since the beginning of the current time interval."
	::= { gkReqLogins	2 }

	gkReqLogouts	OBJECT IDENTIFIER ::= { gkRequests 2 }

	total OBJECT-TYPE
		 SYNTAX  Counter
		 ACCESS  read-only
		 STATUS  mandatory
		 DESCRIPTION
			"The number of gatekeeper logout requests 
			 since the VGK server was started."
	::= { gkReqLogouts 1 }

	interval OBJECT-TYPE
		 SYNTAX  Counter
		 ACCESS  read-only
		 STATUS  mandatory
		 DESCRIPTION
			"The number of gatekeeper logout requests 
			  since the beginning of the current time interval."
	::= { gkReqLogouts 2 }

	gkReqHeartBeat     OBJECT IDENTIFIER ::= { gkRequests 3 }

	total OBJECT-TYPE
		 SYNTAX  Counter
		 ACCESS  read-only
		 STATUS  mandatory
		 DESCRIPTION
			 "The number of gatekeeper heartbeats 
			  since the VGK server was started."
	::= { gkReqHeartBeat 1 }

	interval OBJECT-TYPE
		SYNTAX  Counter
		ACCESS  read-only
		STATUS  mandatory
		DESCRIPTION
			"The number of gatekeeper heartbeats 
			 since the beginning of the time interval."
	::= { gkReqHeartBeat 2 }

	gkReqResolveTN      OBJECT IDENTIFIER ::= { gkRequests	4 }

	total OBJECT-TYPE
		SYNTAX  Counter
		ACCESS  read-only
		STATUS  mandatory
		DESCRIPTION
			"The number of ResolveTN requests sent 
			 on the originating side of the call
			 since the VGK server was started."
	::= { gkReqResolveTN 1 }

	interval OBJECT-TYPE
		SYNTAX  Counter
		ACCESS  read-only
		STATUS  mandatory
		DESCRIPTION
			"The number of resolveTN requests sent 
			 on the originating side of the call
			 since the beginning of the time interval."
	::= { gkReqResolveTN 2 }

	gkReqMakeCall      OBJECT IDENTIFIER ::= { gkRequests	5 }

	total OBJECT-TYPE
		SYNTAX  Counter
		ACCESS  read-only
		STATUS  mandatory
		DESCRIPTION
			"The number of call setup requests sent 
			 on the originating side of the call
			 since the VGK server was started."
	::= { gkReqMakeCall 1 }

	interval OBJECT-TYPE
		SYNTAX  Counter
		ACCESS  read-only
		STATUS  mandatory
		DESCRIPTION
			"The number of call setup requests sent 
			 on the originating side of the call
			 since the beginning of the time interval."
	::= { gkReqMakeCall 2 }

	gkReqAnswerCall     OBJECT IDENTIFIER	::= { gkRequests 6 }

	total OBJECT-TYPE
		 SYNTAX  Counter
		 ACCESS  read-only
		 STATUS  mandatory
		 DESCRIPTION
			"The number of call setup requests sent 
			 on the answering side of the call
			 since the VGK server was started."
	::= { gkReqAnswerCall  1 }

	interval OBJECT-TYPE
		SYNTAX  Counter
		ACCESS  read-only
		STATUS  mandatory
		DESCRIPTION
			"The number of call setup requests sent 
			 on the answering side of the call
			 since the beginning of the time interval."
	::= { gkReqAnswerCall 2 }


	gkReqCallStart     OBJECT IDENTIFIER ::= { gkRequests 7 }

	total OBJECT-TYPE
		SYNTAX  Counter
		ACCESS  read-only
		STATUS  mandatory
		DESCRIPTION
			"The number of call starts from remote gatekeepers
			 since the VGK server was started."
	::= { gkReqCallStart 1 }

	interval OBJECT-TYPE
		SYNTAX  Counter
		ACCESS  read-only
		STATUS  mandatory
		DESCRIPTION
			"The number call starts from remote gatekeepers
			 since the beginning of the time interval."
	::= { gkReqCallStart 2 }

	gkReqCallEnd      OBJECT IDENTIFIER ::= { gkRequests 8 }

	total OBJECT-TYPE
		SYNTAX  Counter
		ACCESS  read-only
		STATUS  mandatory
		DESCRIPTION
			"The number of call ends from remote gatekeepers
			 since the VGK server was started."
	::= { gkReqCallEnd 1 }

	interval OBJECT-TYPE
		SYNTAX  Counter
		ACCESS  read-only
		STATUS  mandatory
		DESCRIPTION
			"The number of call ends from remote gatekeepers
			 since the beginning of the time interval."
	::= { gkReqCallEnd 2 }

	gkReqUpdateCallLog     OBJECT	IDENTIFIER ::= { gkRequests 9 }

	total OBJECT-TYPE
		 SYNTAX  Counter
		 ACCESS  read-only
		 STATUS  mandatory
		 DESCRIPTION
			"The number of times remote gatekeepers sent the VGK updates
			with new call information since the
			VGK server was started."
	::= { gkReqUpdateCallLog	1 }

	interval OBJECT-TYPE
		 SYNTAX  Counter
		 ACCESS  read-only
		 STATUS  mandatory
		 DESCRIPTION
			"The number of times remote gatekeepers sent the VGK updates
			with new call information since the
			beginning of the time interval."
	::= { gkReqUpdateCallLog 2 }


	gkFailures	OBJECT IDENTIFIER ::=	{ gatekeeper 2 }

	gkFailLogins	 OBJECT IDENTIFIER ::= { gkFailures 1 }

	total OBJECT-TYPE
		 SYNTAX  Counter
		 ACCESS  read-only
		 STATUS  mandatory
		 DESCRIPTION
			"The number of gatekeeper login failures
			 since the VGK server was started."
	::= { gkFailLogins	1 }

	interval OBJECT-TYPE
		 SYNTAX  Counter
		 ACCESS  read-only
		 STATUS  mandatory
		 DESCRIPTION
			"The number of gatekeeper login failures 
			 since the beginning of the current time interval."
	::= { gkFailLogins	2 }

	gkFailLogouts	OBJECT IDENTIFIER ::= { gkFailures 2 }

	total OBJECT-TYPE
		 SYNTAX  Counter
		 ACCESS  read-only
		 STATUS  mandatory
		 DESCRIPTION
			"The number of gatekeeper logout failures 
			 since the VGK server was started."
	::= { gkFailLogouts 1 }

	interval OBJECT-TYPE
		 SYNTAX  Counter
		 ACCESS  read-only
		 STATUS  mandatory
		 DESCRIPTION
			"The number of gatekeeper logout failures 
			  since the beginning of the current time interval."
	::= { gkFailLogouts 2 }

	gkFailHeartBeat     OBJECT IDENTIFIER ::= { gkFailures 3 }

	total OBJECT-TYPE
		 SYNTAX  Counter
		 ACCESS  read-only
		 STATUS  mandatory
		 DESCRIPTION
			 "The number of gatekeeper heartbeats 
			  since the VGK server was started."
	::= { gkFailHeartBeat 1 }

	interval OBJECT-TYPE
		SYNTAX  Counter
		ACCESS  read-only
		STATUS  mandatory
		DESCRIPTION
			"The number of gatekeeper heartbeats 
			 since the beginning of the time interval."
	::= { gkFailHeartBeat 2 }

	gkFailResolveTN      OBJECT IDENTIFIER ::= { gkFailures	4 }

	total OBJECT-TYPE
		SYNTAX  Counter
		ACCESS  read-only
		STATUS  mandatory
		DESCRIPTION
			"The number of failed ResolveTN requests sent 
			 on the originating side of the call
			 since the VGK server was started."
	::= { gkFailResolveTN 1 }

	interval OBJECT-TYPE
		SYNTAX  Counter
		ACCESS  read-only
		STATUS  mandatory
		DESCRIPTION
			"The number of failed resolveTN requests sent 
			 on the originating side of the call
			 since the beginning of the time interval."
	::= { gkFailResolveTN 2 }

	gkFailMakeCall      OBJECT IDENTIFIER ::= { gkFailures	5 }

	total OBJECT-TYPE
		SYNTAX  Counter
		ACCESS  read-only
		STATUS  mandatory
		DESCRIPTION
			"The number of call setup failures sent 
			 on the originating side of the call
			 since the VGK server was started."
	::= { gkFailMakeCall 1 }

	interval OBJECT-TYPE
		SYNTAX  Counter
		ACCESS  read-only
		STATUS  mandatory
		DESCRIPTION
			"The number of call setup failures sent 
			 on the originating side of the call
			 since the beginning of the time interval."
	::= { gkFailMakeCall 2 }

	gkFailAnswerCall     OBJECT IDENTIFIER	::= { gkFailures 6 }

	total OBJECT-TYPE
		 SYNTAX  Counter
		 ACCESS  read-only
		 STATUS  mandatory
		 DESCRIPTION
			"The number of call setup failures sent 
			 on the answering side of the call
			 since the VGK server was started."
	::= { gkFailAnswerCall  1 }

	interval OBJECT-TYPE
		SYNTAX  Counter
		ACCESS  read-only
		STATUS  mandatory
		DESCRIPTION
			"The number of call setup failures sent 
			 on the answering side of the call
			 since the beginning of the time interval."
	::= { gkFailAnswerCall 2 }


	gkFailCallStart     OBJECT IDENTIFIER ::= { gkFailures 7 }

	total OBJECT-TYPE
		SYNTAX  Counter
		ACCESS  read-only
		STATUS  mandatory
		DESCRIPTION
			"The number of failed call starts from remote gatekeepers
			 since the VGK server was started."
	::= { gkFailCallStart 1 }

	interval OBJECT-TYPE
		SYNTAX  Counter
		ACCESS  read-only
		STATUS  mandatory
		DESCRIPTION
			"The number of failed call starts from remote gatekeepers
			 since the beginning of the time interval."
	::= { gkFailCallStart 2 }

	gkFailCallEnd      OBJECT IDENTIFIER ::= { gkFailures 8 }

	total OBJECT-TYPE
		SYNTAX  Counter
		ACCESS  read-only
		STATUS  mandatory
		DESCRIPTION
			"The number of failed call ends from remote gatekeepers
			 since the VGK server was started."
	::= { gkFailCallEnd 1 }

	interval OBJECT-TYPE
		SYNTAX  Counter
		ACCESS  read-only
		STATUS  mandatory
		DESCRIPTION
			"The number of failed call ends from remote gatekeepers
			 since the beginning of the time interval."
	::= { gkFailCallEnd 2 }

	gkFailUpdateCallLog     OBJECT	IDENTIFIER ::= { gkFailures 9 }

	total OBJECT-TYPE
		 SYNTAX  Counter
		 ACCESS  read-only
		 STATUS  mandatory
		 DESCRIPTION
			"The number of times remote gatekeepers failed to send 
			 the VGK updates with new call information since the
			 VGK server was started."
	::= { gkFailUpdateCallLog	1 }

	interval OBJECT-TYPE
		 SYNTAX  Counter
		 ACCESS  read-only
		 STATUS  mandatory
		 DESCRIPTION
			"The number of times remote gatekeepers failed to send
			 the VGK updates with new call information since the
			 beginning of the time interval."
	::= { gkFailUpdateCallLog 2 }


	gkSessions	  OBJECT IDENTIFIER ::=	{ gatekeeper 3 }

	loggedOn OBJECT-TYPE
		 SYNTAX  Gauge
		 ACCESS  read-only
		 STATUS  mandatory
		 DESCRIPTION
			"The number of gatekeepers currently logged in
			 to the VGK."
	::= { gkSessions 1 }

	gkSessionsMaxLoggedOn   OBJECT IDENTIFIER ::= { gkSessions 2 }

	total OBJECT-TYPE
		 SYNTAX  Gauge
		 ACCESS  read-only
		 STATUS  mandatory
		 DESCRIPTION
			"The maximum number of gatekeepers simultaneously
			logged in to the VGK via  since the
			VGK server was started."
	::= { gkSessionsMaxLoggedOn 1 }

	interval OBJECT-TYPE
		 SYNTAX  Gauge
		 ACCESS  read-only
		 STATUS  mandatory
		 DESCRIPTION
			"The maximum number of gatekeepers simultaneously 
			logged in to the VGK via  since the
			beginning of the time interval."
	::= { gkSessionsMaxLoggedOn 2 }

	gkSessionsExpired       OBJECT IDENTIFIER ::= { gkSessions 3 }

	total OBJECT-TYPE
		 SYNTAX  Counter
		 ACCESS  read-only
		 STATUS  mandatory
		 DESCRIPTION
			"The number of gatekeeper login sessions that expired
			since the VGK server was started."
	::= { gkSessionsExpired 1 }

	interval OBJECT-TYPE
		 SYNTAX  Counter
		 ACCESS  read-only
		 STATUS  mandatory
		 DESCRIPTION
			"The number of gatekeeper login sessions that expired
			since the beginning of the time interval."
	::= { gkSessionsExpired 2 }

	-- the gatekeeperProxy group

	-- This group contains information about gatekeeper proxy objects in the
	-- VGK server.

	gkProxyRequests	 OBJECT IDENTIFIER ::= { gatekeeperProxy 1 }

	gkProxyReqLogins OBJECT IDENTIFIER ::= { gkProxyRequests 1 }

	total OBJECT-TYPE
		 SYNTAX  Counter
		 ACCESS  read-only
		 STATUS  mandatory
		 DESCRIPTION
			"The number of gatekeeper login requests to remote gatekeepers
			 since the VGK server was started."
	::= { gkProxyReqLogins	1 }

	interval OBJECT-TYPE
		 SYNTAX  Counter
		 ACCESS  read-only
		 STATUS  mandatory
		 DESCRIPTION
			"The number of gatekeeper login requests to remote gatekeepers
			 since the beginning of the current time interval."
	::= { gkProxyReqLogins	2 }

	gkProxyReqLogouts	OBJECT IDENTIFIER ::= { gkProxyRequests 2 }

	total OBJECT-TYPE
		 SYNTAX  Counter
		 ACCESS  read-only
		 STATUS  mandatory
		 DESCRIPTION
			"The number of gatekeeper logout requests to remote gatekeepers
			 since the VGK server was started."
	::= { gkProxyReqLogouts 1 }

	interval OBJECT-TYPE
		 SYNTAX  Counter
		 ACCESS  read-only
		 STATUS  mandatory
		 DESCRIPTION
			"The number of gatekeeper logout requests to remote gatekeepers
			  since the beginning of the current time interval."
	::= { gkProxyReqLogouts 2 }

	gkProxyReqResolveTN      OBJECT IDENTIFIER ::= { gkProxyRequests  3 }

	total OBJECT-TYPE
		SYNTAX  Counter
		ACCESS  read-only
		STATUS  mandatory
		DESCRIPTION
			"The number of resolveTN requests to remote gatekeepers sent 
			 on the originating side of the call
			 since the VGK server was started."
	::= { gkProxyReqResolveTN 1 }

	interval OBJECT-TYPE
		SYNTAX  Counter
		ACCESS  read-only
		STATUS  mandatory
		DESCRIPTION
			"The number of resolveTN requests to remote gatekeepers sent 
			 on the originating side of the call
			 since the beginning of the time interval."
	::= { gkProxyReqResolveTN 2 }

	gkProxyReqMakeCall      OBJECT IDENTIFIER ::= { gkProxyRequests	4 }

	total OBJECT-TYPE
		SYNTAX  Counter
		ACCESS  read-only
		STATUS  mandatory
		DESCRIPTION
			"The number of call setup requests to remote gatekeepers sent 
			 on the originating side of the call
			 since the VGK server was started."
	::= { gkProxyReqMakeCall 1 }

	interval OBJECT-TYPE
		SYNTAX  Counter
		ACCESS  read-only
		STATUS  mandatory
		DESCRIPTION
			"The number of call setup requests to remote gatekeepers sent 
			 on the originating side of the call
			 since the beginning of the time interval."
	::= { gkProxyReqMakeCall 2 }

	gkProxyReqAnswerCall     OBJECT IDENTIFIER	::= { gkProxyRequests 5 }

	total OBJECT-TYPE
		 SYNTAX  Counter
		 ACCESS  read-only
		 STATUS  mandatory
		 DESCRIPTION
			"The number of call setup requests to remote gatekeepers sent 
			 on the answering side of the call
			 since the VGK server was started."
	::= { gkProxyReqAnswerCall  1 }

	interval OBJECT-TYPE
		SYNTAX  Counter
		ACCESS  read-only
		STATUS  mandatory
		DESCRIPTION
			"The number of call setup requests to remote gatekeepers sent 
			 on the answering side of the call
			 since the beginning of the time interval."
	::= { gkProxyReqAnswerCall 2 }


	gkProxyReqCallStart     OBJECT IDENTIFIER ::= { gkProxyRequests 6 }

	total OBJECT-TYPE
		SYNTAX  Counter
		ACCESS  read-only
		STATUS  mandatory
		DESCRIPTION
			"The number of call starts to remote gatekeepers
			 since the VGK server was started."
	::= { gkProxyReqCallStart 1 }

	interval OBJECT-TYPE
		SYNTAX  Counter
		ACCESS  read-only
		STATUS  mandatory
		DESCRIPTION
			"The number call starts to remote gatekeepers
			 since the beginning of the time interval."
	::= { gkProxyReqCallStart 2 }

	gkProxyReqCallEnd      OBJECT IDENTIFIER ::= { gkProxyRequests 7 }

	total OBJECT-TYPE
		SYNTAX  Counter
		ACCESS  read-only
		STATUS  mandatory
		DESCRIPTION
			"The number of call ends to remote gatekeepers
			 since the VGK server was started."
	::= { gkProxyReqCallEnd 1 }

	interval OBJECT-TYPE
		SYNTAX  Counter
		ACCESS  read-only
		STATUS  mandatory
		DESCRIPTION
			"The number of call ends to remote gatekeepers
			 since the beginning of the time interval."
	::= { gkProxyReqCallEnd 2 }

	gkProxyReqUpdateCallLog     OBJECT	IDENTIFIER ::= { gkProxyRequests 8 }

	total OBJECT-TYPE
		 SYNTAX  Counter
		 ACCESS  read-only
		 STATUS  mandatory
		 DESCRIPTION
			"The number of times VGK updates have been sent to remote gatekeepers
			with new call information since the VGK server was started."
	::= { gkProxyReqUpdateCallLog	1 }

	interval OBJECT-TYPE
		 SYNTAX  Counter
		 ACCESS  read-only
		 STATUS  mandatory
		 DESCRIPTION
			"The number of times remote gatekeepers sent the VGK updates
			with new call information since the
			beginning of the time interval."
	::= { gkProxyReqUpdateCallLog 2 }


	gkProxyFailures	OBJECT IDENTIFIER ::=	{ gatekeeperProxy 2 }


	gkProxyFailLogins OBJECT IDENTIFIER ::= { gkProxyFailures 1 }

	total OBJECT-TYPE
		 SYNTAX  Counter
		 ACCESS  read-only
		 STATUS  mandatory
		 DESCRIPTION
			"The number of gatekeeper login failures to remote gatekeepers
			 since the VGK server was started."
	::= { gkProxyFailLogins	1 }

	interval OBJECT-TYPE
		 SYNTAX  Counter
		 ACCESS  read-only
		 STATUS  mandatory
		 DESCRIPTION
			"The number of gatekeeper login failures to remote gatekeepers
			 since the beginning of the current time interval."
	::= { gkProxyFailLogins	2 }

	gkProxyFailLogouts	OBJECT IDENTIFIER ::= { gkProxyFailures 2 }

	total OBJECT-TYPE
		 SYNTAX  Counter
		 ACCESS  read-only
		 STATUS  mandatory
		 DESCRIPTION
			"The number of gatekeeper logout failures to remote gatekeepers
			 since the VGK server was started."
	::= { gkProxyFailLogouts 1 }

	interval OBJECT-TYPE
		 SYNTAX  Counter
		 ACCESS  read-only
		 STATUS  mandatory
		 DESCRIPTION
			"The number of gatekeeper logout failures to remote gatekeepers
			  since the beginning of the current time interval."
	::= { gkProxyFailLogouts 2 }

	gkProxyFailResolveTN      OBJECT IDENTIFIER ::= { gkProxyFailures  3 }

	total OBJECT-TYPE
		SYNTAX  Counter
		ACCESS  read-only
		STATUS  mandatory
		DESCRIPTION
			"The number of failed resolveTN requests to remote gatekeepers sent 
			 on the originating side of the call
			 since the VGK server was started."
	::= { gkProxyFailResolveTN 1 }

	interval OBJECT-TYPE
		SYNTAX  Counter
		ACCESS  read-only
		STATUS  mandatory
		DESCRIPTION
			"The number of failed resolveTN requests to remote gatekeepers sent 
			 on the originating side of the call
			 since the beginning of the time interval."
	::= { gkProxyFailResolveTN 2 }

	gkProxyFailMakeCall      OBJECT IDENTIFIER ::= { gkProxyFailures 4 }

	total OBJECT-TYPE
		SYNTAX  Counter
		ACCESS  read-only
		STATUS  mandatory
		DESCRIPTION
			"The number of call setup failures to remote gatekeepers sent 
			 on the originating side of the call
			 since the VGK server was started."
	::= { gkProxyFailMakeCall 1 }

	interval OBJECT-TYPE
		SYNTAX  Counter
		ACCESS  read-only
		STATUS  mandatory
		DESCRIPTION
			"The number of call setup failures to remote gatekeepers sent 
			 on the originating side of the call
			 since the beginning of the time interval."
	::= { gkProxyFailMakeCall 2 }

	gkProxyFailAnswerCall     OBJECT IDENTIFIER	::= { gkProxyFailures 5 }

	total OBJECT-TYPE
		 SYNTAX  Counter
		 ACCESS  read-only
		 STATUS  mandatory
		 DESCRIPTION
			"The number of call setup failures to remote gatekeepers sent 
			 on the answering side of the call
			 since the VGK server was started."
	::= { gkProxyFailAnswerCall  1 }

	interval OBJECT-TYPE
		SYNTAX  Counter
		ACCESS  read-only
		STATUS  mandatory
		DESCRIPTION
			"The number of call setup failures to remote gatekeepers sent 
			 on the answering side of the call
			 since the beginning of the time interval."
	::= { gkProxyFailAnswerCall 2 }


	gkProxyFailCallStart     OBJECT IDENTIFIER ::= { gkProxyFailures 6 }

	total OBJECT-TYPE
		SYNTAX  Counter
		ACCESS  read-only
		STATUS  mandatory
		DESCRIPTION
			"The number of call starts to remote gatekeepers
			 since the VGK server was started."
	::= { gkProxyFailCallStart 1 }

	interval OBJECT-TYPE
		SYNTAX  Counter
		ACCESS  read-only
		STATUS  mandatory
		DESCRIPTION
			"The number call starts to remote gatekeepers
			 since the beginning of the time interval."
	::= { gkProxyFailCallStart 2 }

	gkProxyFailCallEnd      OBJECT IDENTIFIER ::= { gkProxyFailures 7 }

	total OBJECT-TYPE
		SYNTAX  Counter
		ACCESS  read-only
		STATUS  mandatory
		DESCRIPTION
			"The number of call ends to remote gatekeepers
			 since the VGK server was started."
	::= { gkProxyFailCallEnd 1 }

	interval OBJECT-TYPE
		SYNTAX  Counter
		ACCESS  read-only
		STATUS  mandatory
		DESCRIPTION
			"The number of call ends to remote gatekeepers
			 since the beginning of the time interval."
	::= { gkProxyFailCallEnd 2 }

	gkProxyFailUpdateCallLog OBJECT IDENTIFIER ::= { gkProxyFailures 8 }

	total OBJECT-TYPE
		 SYNTAX  Counter
		 ACCESS  read-only
		 STATUS  mandatory
		 DESCRIPTION
			"The number of times VGK updates have been sent to remote gatekeepers
			with new call information since the VGK server was started."
	::= { gkProxyFailUpdateCallLog	1 }

	interval OBJECT-TYPE
		 SYNTAX  Counter
		 ACCESS  read-only
		 STATUS  mandatory
		 DESCRIPTION
			"The number of times remote gatekeepers sent the VGK updates
			with new call information since the
			beginning of the time interval."
	::= { gkProxyFailUpdateCallLog 2 }


	gkProxySessions	  OBJECT IDENTIFIER ::=	{ gatekeeperProxy 3 }

	loggedOn OBJECT-TYPE
		 SYNTAX  Gauge
		 ACCESS  read-only
		 STATUS  mandatory
		 DESCRIPTION
			"The number of remote domains that this gatekeeper is 
			 currently logged in."
	::= { gkProxySessions 1 }

	gkProxySessionsMaxLoggedOn   OBJECT IDENTIFIER ::= { gkProxySessions 2 }

	total OBJECT-TYPE
		 SYNTAX  Gauge
		 ACCESS  read-only
		 STATUS  mandatory
		 DESCRIPTION
			"The maximum number of remote domains that this gatekeeper 
			 has been simultaneously logged in to since the
			VGK server was started."
	::= { gkProxySessionsMaxLoggedOn 1 }

	interval OBJECT-TYPE
		 SYNTAX  Gauge
		 ACCESS  read-only
		 STATUS  mandatory
		 DESCRIPTION
			"The maximum number of remote domains that this gatekeeper 
			has been logged in to the VGK since the
			beginning of the time interval."
	::= { gkProxySessionsMaxLoggedOn 2 }


	-- Domains Section

	remoteDomains	  OBJECT IDENTIFIER ::=	{ domains 1 }

	loggedOn OBJECT-TYPE
		 SYNTAX  Gauge
		 ACCESS  read-only
		 STATUS  mandatory
		 DESCRIPTION
			"The number of domains currently logged in
			 to the VGK."
	::= { remoteDomains 1 }

	remoteDomainsMaxLoggedOn   OBJECT IDENTIFIER ::= { remoteDomains 2 }

	total OBJECT-TYPE
		 SYNTAX  Gauge
		 ACCESS  read-only
		 STATUS  mandatory
		 DESCRIPTION
			"The maximum number of domains simultaneously
			logged in to the VGK since the
			VGK server was started."
	::= { remoteDomainsMaxLoggedOn 1 }

	interval OBJECT-TYPE
		 SYNTAX  Gauge
		 ACCESS  read-only
		 STATUS  mandatory
		 DESCRIPTION
			"The maximum number of domains simultaneously 
			logged in to the VGK since the
			beginning of the time interval."
	::= { remoteDomainsMaxLoggedOn 2 }


	-- Surf N Call Section
	surfNCallRequests	  OBJECT IDENTIFIER ::= { surfNCall 1 }

	resolve     OBJECT IDENTIFIER ::= { surfNCallRequests 1 }

	total OBJECT-TYPE
		 SYNTAX  Counter
		 ACCESS  read-only
		 STATUS  mandatory
		 DESCRIPTION
			"The number of successful resolve requests
			that have arrived from surf&Call clients
			since the VGK server was started."
	::= { resolve 1 }

	interval OBJECT-TYPE
		 SYNTAX  Counter
		 ACCESS  read-only
		 STATUS  mandatory
		 DESCRIPTION
			"The number of successful resolve requests
			that have arrived from surf&Call clients
			since the start of the current session."
	::= { resolve 2 }


	surfNCallFailures	  OBJECT IDENTIFIER ::= { surfNCall 2 }

	failResolve     OBJECT IDENTIFIER ::= { surfNCallFailures 1 }

	total OBJECT-TYPE
		 SYNTAX  Counter
		 ACCESS  read-only
		 STATUS  mandatory
		 DESCRIPTION
			"The number of failed resolve requests
			that have arrived from surf&Call clients
			since the VGK server was started."
	::= { failResolve 1 }

	interval OBJECT-TYPE
		 SYNTAX  Counter
		 ACCESS  read-only
		 STATUS  mandatory
		 DESCRIPTION
			"The number of failed resolve requests
			that have arrived from surf&Call clients
			since the start of the current session."
	::= { failResolve 2 }



	-- Traps section

	databaseConnectFail TRAP-TYPE
		 ENTERPRISE	vgk
		 DESCRIPTION
			"This trap is generated by VGK when its attempt
			to connect to a database fails."
	::= 1

	databaseGeneralError  TRAP-TYPE
		 ENTERPRISE	vgk
		 DESCRIPTION
			"This trap is generated by VGK when a database
			error is detected."
	::= 2

	databaseCorrupted  TRAP-TYPE
		 ENTERPRISE	vgk
		 DESCRIPTION
			"This trap is generated by VGK when a database
			corruption is detected."
	::= 3

	dbReloadFail  TRAP-TYPE
		 ENTERPRISE	vgk
		 DESCRIPTION
			"This trap is generated by VGK when its attempt
			to reload the VGK database fails."
	::= 4

	noLicense  TRAP-TYPE
		 ENTERPRISE	vgk
		 DESCRIPTION
			"This trap is generated when the VGK cannot 
			obtain a license at the start or during its execution."
	::= 5

	invalidLicense	TRAP-TYPE
		 ENTERPRISE	vgk
		 DESCRIPTION
			"This trap is generated by VGK when using of
			invalid license is detected."
	::= 6

	licenseExceeded TRAP-TYPE
		 ENTERPRISE	vgk
		 DESCRIPTION
			"This trap is generated by VGK when the maximum value
			of one of licensed parameters is exceeded -
			e.g., the gatekeeper is licensed for a maximum 
			number of ongoing calls, and an attempt was 
			made to exceed the licensed limit."
	::= 7           


	 END
