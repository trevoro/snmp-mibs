AIPPP-MIB DEFINITIONS ::= BEGIN

IMPORTS
	Integer32, IpAddress, MODULE-IDENTITY, OBJECT-TYPE, enterprises
			FROM SNMPv2-SMI
	DisplayString, TruthValue
			FROM SNMPv2-TC;

	PositiveInteger    ::= INTEGER (1..2147483647)

	aii OBJECT IDENTIFIER ::= {enterprises 539}

aiPPP MODULE-IDENTITY
	LAST-UPDATED "9909151700Z"
	ORGANIZATION "Applied Innovation Inc."
	CONTACT-INFO "Engineering MIB Administrator
					Postal: Applied Innovation Inc.
						5800 Innovation Drive
						Dublin, Ohio 43017-3271

					Tel:    614-798-2000
					Fax:    614-798-1770
					Email:  snmp@aiinet.com"
	DESCRIPTION "MIB module for PPP options not covered
		    in the standard PPP MIBS"
	::= {aii 25}

--=========================================================================

aiPPPTable OBJECT-TYPE
	SYNTAX		SEQUENCE OF AiPPPEntry
	MAX-ACCESS	not-accessible
	STATUS		current
	DESCRIPTION
		"Table of PPP information indexed by link number.
		Includes enable/disable for each NCP Type (IPCP and BCP),
                and IP interface parameters."
	::= {aiPPP 1}

aiPPPEntry OBJECT-TYPE
	SYNTAX		AiPPPEntry
	MAX-ACCESS	not-accessible
	STATUS		current
	DESCRIPTION	"Entry of aiPPPTable."
	INDEX		{aipppLinkNumber}
	::= {aiPPPTable 1}

AiPPPEntry ::= SEQUENCE {
	aipppLinkNumber				PositiveInteger,
	aipppNCPProtoOption			INTEGER,
	aipppLocalSecurityOption	INTEGER,
	aipppIpSrcAddr				IpAddress,
	aipppIpDestAddr				IpAddress,
	aipppIpSubnetMask			IpAddress,
	aipppIpBcastAddr			Integer32,
	aipppLocalRadiusOption		INTEGER,
	aipppRemoteSecurityOption	INTEGER,
	aipppMultilinkOption		INTEGER,
	aipppMLGroup				INTEGER
}

aipppLinkNumber OBJECT-TYPE
	SYNTAX		PositiveInteger
	MAX-ACCESS	read-only
	STATUS		current
	DESCRIPTION	"Link number to which this table row applies."
	::= {aiPPPEntry 1}

aipppNCPProtoOption OBJECT-TYPE
	SYNTAX		INTEGER {
			ipcp(1),
			bcp(2),
			ipcpbcp(3)
			}
	MAX-ACCESS	read-write
	STATUS		current
	DESCRIPTION
		"NCP Protocol(s) option for this link:
		ipcp(1):
			Link will attempt to negotiate IPCP
		bcp(2):
			Link will attempt to negotiate BCP.
		ipcp_bcp(3):
			Link will attempt to negotiate IPCP and BCP."
	::= {aiPPPEntry 2}


aipppLocalSecurityOption OBJECT-TYPE
	SYNTAX		INTEGER {
			none(1),
			pap(2),
			chap(3)
			}
	MAX-ACCESS	read-write
	STATUS		current
	DESCRIPTION
		"Authentication protocol enabled for this link:
		none(1):
			Link will not attempt authentication.
		pap(2):
			Link will attempt PAP authentication.
		chap(3):
			Link will attempt CHAP authentication."
	::= {aiPPPEntry 3}


aipppIpSrcAddr OBJECT-TYPE
	SYNTAX			IpAddress
	MAX-ACCESS		read-write
	STATUS			current
	DESCRIPTION
		"The source IP address for the IP interface."
	::= { aiPPPEntry 4 }

aipppIpDestAddr OBJECT-TYPE
	SYNTAX			IpAddress
	MAX-ACCESS		read-write
	STATUS			current
	DESCRIPTION
		"The destination IP address for the IP interface."
	::= { aiPPPEntry 5 }

aipppIpSubnetMask OBJECT-TYPE
	SYNTAX			IpAddress
	MAX-ACCESS		read-write
	STATUS			current
	DESCRIPTION
		"The subnet mask associated with the IP address of
                 this entry.  The value of the mask is an IP
                 address with all the network bits set to 1 and all
                 the hosts bits set to 0."
	::= { aiPPPEntry 6 }

aipppIpBcastAddr		OBJECT-TYPE
	SYNTAX			Integer32
	MAX-ACCESS		read-write
	STATUS			current
	DESCRIPTION
		"The value of the least-significant bit in the IP
                 broadcast address used for sending datagrams on
                 the (logical) interface associated with the IP
                 address of this entry.  For example, when the
                 Internet standard all-ones broadcast address is
                 used, the value will be 1.  This value applies to
                 both the subnet and network broadcast addresses
                 used by the entity on this (logical) interface."
	::= { aiPPPEntry 7 }

aipppLocalRadiusOption OBJECT-TYPE
	SYNTAX		INTEGER {
			disabled(1),
			enabled(2),
			localfallback(3)
			}
	MAX-ACCESS	read-write
	STATUS		current
	DESCRIPTION
		"Authentication protocol enabled for this link:
		disabled(1):
			Authenticate using local security settings for the link.
		enabled(2):
			Authenticate using remote Radius server(s), and if
			Radius server(s) do not respond, the connection
			will fail.
 		localfallback(3):
			Authenticate using remote Radius server(s), and if
			Radius server(s) do not respond, authentication will be
			attempted using local security settings for the link."

	::= {aiPPPEntry 8}

aipppRemoteSecurityOption OBJECT-TYPE
	SYNTAX		INTEGER {
			none(1),
			pap(2),
			chap(3)
			}
	MAX-ACCESS	read-write
	STATUS		current
	DESCRIPTION
		"Authentication protocol enabled for this link:
		none(1):
			Link will not attempt authentication.
		pap(2):
			Link will attempt PAP authentication.
		chap(3):
			Link will attempt CHAP authentication."
	::= {aiPPPEntry 9}

aipppMultilinkOption OBJECT-TYPE
	SYNTAX INTEGER
		{
		reject(1),
		request(2)
		}
	MAX-ACCESS	read-write
	STATUS		current
	DESCRIPTION
		"Multilink options for this link:
		reject(1):   Attempts from the remote host to configure this link
		             as a bundled link will be rejected.
		request(2):  The host will request that this link be bundled with
		             other links with the same multilink group identifier."
	::= {aiPPPEntry 10}

aipppMLGroup OBJECT-TYPE
	SYNTAX			INTEGER (0..255)
	MAX-ACCESS		read-write
	STATUS			current
	DESCRIPTION
		"The multilink group to assign this link to.  Links with
		 the same multilink group identifier will be bundled together."
	::= {aiPPPEntry 11}


--=========================================================================

END
