NE-STAT-MIB DEFINITIONS ::= BEGIN

-- Allot communication V5.1 MIB
-- April 01, 2003

 
IMPORTS
    OBJECT-TYPE, MODULE-IDENTITY, Counter32   FROM SNMPv2-SMI
    allotCom                                  FROM COMPANY-MIB
    OBJECT-GROUP			      FROM SNMPv2-CONF         
    DisplayString                             FROM SNMPv2-TC;
         
neStatistics MODULE-IDENTITY
    LAST-UPDATED "0103130000Z"
    ORGANIZATION "Allot Communications"
    CONTACT-INFO
	"Allot Communications

	 postal:     5 Hanagar St.
                     Industrial Zone Neve Neeman
                     Hod Hasharon 45800 Israel
         phone:      +972-(0)9-761-9200
         fax:        +972-(0)9-744-3626
         email:      support@allot.com"
    DESCRIPTION
	"Allot NE Statistics MIB."
    ::= { allotCom 1 }
    
    
neStatMIB OBJECT IDENTIFIER ::= { neStatistics 1 }
neStat    OBJECT IDENTIFIER ::= { neStatMIB 1 }

-- NE Statistics

neByteCountIn   OBJECT-TYPE
    SYNTAX      Counter32
    MAX-ACCESS  read-only
    STATUS      current
    DESCRIPTION
        "Bytes in on NE"
    ::= { neStat 1 }

neByteCountOut   OBJECT-TYPE
    SYNTAX      Counter32
    MAX-ACCESS  read-only
    STATUS      current
    DESCRIPTION
        "Bytes out on NE"
    ::= { neStat 2 }

neByteCountTotal   OBJECT-TYPE
    SYNTAX      Counter32
    MAX-ACCESS  read-only
    STATUS      current
    DESCRIPTION
        "Total Bytes on NE"
    ::= { neStat 3 }

neLiveConnections   OBJECT-TYPE
    SYNTAX      Counter32
    MAX-ACCESS  read-only
    STATUS      current
    DESCRIPTION
        "Live Connections on NE"
    ::= { neStat 4 }

neNewConnections   OBJECT-TYPE
    SYNTAX      Counter32
    MAX-ACCESS  read-only
    STATUS      current
    DESCRIPTION
        "New Connections on NE"
    ::= { neStat 5 }

nePacketsIn   OBJECT-TYPE
    SYNTAX      Counter32
    MAX-ACCESS  read-only
    STATUS      current
    DESCRIPTION
        "Packets in on NE"
    ::= { neStat 6 }

nePacketsOut   OBJECT-TYPE
    SYNTAX      Counter32
    MAX-ACCESS  read-only
    STATUS      current
    DESCRIPTION
        "Packets out on NE"
    ::= { neStat 7 }

nePacketsTotal   OBJECT-TYPE
    SYNTAX      Counter32
    MAX-ACCESS  read-only
    STATUS      current
    DESCRIPTION
        "Total Packets on NE"
    ::= { neStat 8 }

-- units of conformance

neByteCountersGroup    OBJECT-GROUP
    OBJECTS { neByteCountIn, neByteCountOut, neByteCountTotal,
	      neLiveConnections, neNewConnections,
	      nePacketsIn, nePacketsOut, nePacketsTotal
	      }
    STATUS  current
    DESCRIPTION
            "A collection of objects providing NE counters."
    ::= { neStatMIB 2 }
            
END
