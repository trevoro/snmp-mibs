--      ***************************************************************************
--                      Router MIB definition.
--
--      Eicon Technology Corporation
--      Version 1.1
--      Draft 1
--      Date 1993/07/05
--      ***************************************************************************

-- Documents: 285-534-1.

EICON-MIB-ROUTER DEFINITIONS  ::=  BEGIN

IMPORTS
	Counter, IpAddress, Gauge, TimeTicks, enterprises
		FROM RFC1155-SMI
	OBJECT-TYPE
		FROM RFC-1212
	TRAP-TYPE
		FROM RFC-1215
	DisplayString
		FROM RFC1213-MIB;

eicon           OBJECT IDENTIFIER  ::= { enterprises 434 }
management      OBJECT IDENTIFIER  ::= { eicon 2 }
mibv2           OBJECT IDENTIFIER  ::= { management 2 }
module          OBJECT IDENTIFIER  ::= { mibv2 4 }

--      Title

router  OBJECT IDENTIFIER  ::= { mibv2 8 }

--      The router group contains the information about router software installed in
--  the server.  
--      The information is contained in 28 general information objects and in 
--  the following tables:
--              rtPortTable
--              rtConnTable
--              rtIPMappingTable
--              rtCircuitTable
--              rtCircuitIPTable
--              rtCircuitIPXTable
--              rtCircuitATTable

OperState ::= INTEGER {
	other (1),              -- none of the following
	disabled (2),           -- not in ready state
	ready (3),              -- in ready state
	active (4),             -- ready and operating
	busy (5)                        -- operating but cannot accept more traffic
	}

AdminState ::= INTEGER {
	start (1),
	stop (2),
	dump (3),
	test (4),
	invalid (5)
	}

 ActionState ::= INTEGER {
	done (1),
	failed (2),
	in-progress (3)
	}

EntryStatus ::= INTEGER {
	valid (1),
	createRequest (2),
	underCreation (3),
	invalid (4)
	}

EntryStatusV2 ::= INTEGER {
	valid (1),
	createRequest (2),
	underCreation (3),
	invalid (4),
	modifyRequest (5),
	underModification (6)
	}

ConnectionStatus ::= INTEGER {
	invalid (1),            -- The Console shouldn't display this value.
	listening (2),
	calling (3),
	connected (4),
	hangingup (5),
	hungup (6),
	pending-hungup (7)
	}


-- used to indicate that corresponding control parameters are invalid
ControlOnOff ::= INTEGER {
	stop (1),
	start (2),
	invalid (3)
	}

CardRef ::= INTEGER (1..6)      -- EiconCard reference on the server.

PortRef ::= INTEGER (1..48)     -- Port reference on the server.

PositiveInteger ::= INTEGER (0..2147483647)


--      The router group contains the information about router software installed in
--  the server.  
--      The information is contained in 28 general information objects and in 
--  the following tables:
--              rtPortTable
--              rtConnTable
--              rtIPMappingTable
--              rtCircuitTable
--              rtCircuitIPTable
--              rtCircuitIPXTable
--              rtCircuitATTable


rtName                  OBJECT-TYPE     -- Not supported by Eicon Agent
	SYNTAX  DisplayString (SIZE (1..48))
	ACCESS  read-only
	STATUS  mandatory                       
	DESCRIPTION     
		"The name advertised by the router agent using SAP."
	::= { router 1 }

rtProductName           OBJECT-TYPE
	SYNTAX  DisplayString (SIZE (1..48))
	ACCESS  read-only                       
	STATUS  mandatory       
	DESCRIPTION     
		"The Product name ie. Router for Netware."
	::= { router 2 }

rtReleaseVersion                OBJECT-TYPE
	SYNTAX  INTEGER
	ACCESS  read-only                       
	STATUS  mandatory       
	DESCRIPTION     
		"Ex.:  Ver. 3 Rel. 2."
	::= { router 3 }

rtReleaseDate           OBJECT-TYPE
	SYNTAX  INTEGER
	ACCESS  read-only                       
	STATUS  mandatory       
	DESCRIPTION     
		"Format: 1993/03/25."
	::= { router 4 }

rtOperState             OBJECT-TYPE
	SYNTAX  OperState
	ACCESS  read-only                       
	STATUS  mandatory       
	DESCRIPTION     
		"The operational state of the router."
	::= { router 5 }

rtAdminStateCtr         OBJECT-TYPE
	SYNTAX  AdminState
	ACCESS  read-write                      
	STATUS  mandatory       
	DESCRIPTION     
		"The administrative state of the router. Management station 
		will change this value to start or stop the router."
	::= { router 6 }

rtType          OBJECT-TYPE
	SYNTAX  INTEGER {
		typeNetWareRouter (1),
		typeOS2Router (2),
		typeUnixRouter (3),
		typeNTRouter (4),
		typeSynOpticsRouter (5),
		typeMadrasRouter (6)
		}
	ACCESS  read-only                       
	STATUS  mandatory       
	DESCRIPTION     
		"Type of router."
	::= { router 7 }

rtTimeUp        OBJECT-TYPE
	SYNTAX  TimeTicks
	ACCESS  read-only                       
	STATUS  mandatory       
	DESCRIPTION     
		"The time elapsed since the router was started."
	::= { router 8 }

rtNumberOfPorts         OBJECT-TYPE
	SYNTAX  INTEGER
	ACCESS  read-only                       
	STATUS  mandatory       
	DESCRIPTION     
		"The number of Eicon ports currently used by the router."
	::= { router 9 }

rtMaxCircuits           OBJECT-TYPE
	SYNTAX  INTEGER
	ACCESS  read-only                       
	STATUS  mandatory       
	DESCRIPTION     
		"The maximum number of connections that can be configured for this
		router."
	::= { router 10 }

rtAvailableCircuits             OBJECT-TYPE
	SYNTAX  Gauge
	ACCESS  read-only                       
	STATUS  mandatory       
	DESCRIPTION     
		"The number of connections still available for this router."
	::= { router 11 }

rtAvailableLANMapping           OBJECT-TYPE
	SYNTAX  Gauge
	ACCESS  read-only                       
	STATUS  mandatory       
	DESCRIPTION     
		"The available number of LAN protocol mappings for all connections."
	::= { router 12 }

rtMaxLANMapping         OBJECT-TYPE
	SYNTAX  INTEGER
	ACCESS  read-only                       
	STATUS  mandatory       
	DESCRIPTION     
		"The maximum number of LAN protocol mappings for all connections."
	::= { router 13 }

rtGlobalTxPackets       OBJECT-TYPE
	SYNTAX  Counter
	ACCESS  read-only                       
	STATUS  mandatory       
	DESCRIPTION     
		"The number of packets transmitted by the router on all ports"
	::= { router 14 }

rtGlobalTxBytesLow      OBJECT-TYPE
	SYNTAX  Counter
	ACCESS  read-only                       
	STATUS  mandatory       
	DESCRIPTION     
		"The number of bytes transmitted by the router on all ports - 
		the low 32 bits of the 64 bits counter."
	::= { router 15 }

rtGlobalTxBytesHigh     OBJECT-TYPE
	SYNTAX  Counter
	ACCESS  read-only                       
	STATUS  mandatory       
	DESCRIPTION     
		"The number of bytes transmitted by the router on all ports - 
		the high 32 bits of the 64 bits counter."
	::= { router 16 }

rtGlobalRxPackets       OBJECT-TYPE
	SYNTAX  Counter
	ACCESS  read-only                       
	STATUS  mandatory       
	DESCRIPTION     
		"The number of packets received by the router on all ports"
	::= { router 17 }

rtGlobalRxBytesLow      OBJECT-TYPE
	SYNTAX  Counter
	ACCESS  read-only                       
	STATUS  mandatory       
	DESCRIPTION     
		"The number of bytes received by the router on all ports - 
		the low 32 bits of the 64 bits counter."
	::= { router 18 }

rtGlobalRxBytesHigh     OBJECT-TYPE
	SYNTAX  Counter
	ACCESS  read-only                       
	STATUS  mandatory       
	DESCRIPTION     
		"The number of bytes received by the router on all ports - 
		the high 32 bits of the 64 bits counter."
	::= { router 19 }

rtGlobalTxDropNoRoute   OBJECT-TYPE
	SYNTAX  Counter
	ACCESS  read-only                       
	STATUS  mandatory       
	DESCRIPTION     
		"The number of transmit packets dropped on all ports because 
		no route was found."
	::= { router 20 }

rtGlobalTxDropNoResource        OBJECT-TYPE
	SYNTAX  Counter
	ACCESS  read-only                       
	STATUS  mandatory       
	DESCRIPTION     
		"The number of transmit packets dropped on all ports because resources
		 were exhausted."
	::= { router 21 }

rtGlobalTxDropUnknownProt       OBJECT-TYPE
	SYNTAX  Counter
	ACCESS  read-only                       
	STATUS  mandatory       
	DESCRIPTION     
		"The number of transmit packets dropped because the WAN protocol is not
		 supported."
	::= { router 22 }

rtGlobalRxDropNoResource        OBJECT-TYPE
	SYNTAX  Counter
	ACCESS  read-only                       
	STATUS  mandatory       
	DESCRIPTION     
		"The number of received packets dropped on all ports because resources 
		were exhausted."
	::= { router 23 }

rtGlobalRxDropUnknownProt       OBJECT-TYPE
	SYNTAX  Counter
	ACCESS  read-only                       
	STATUS  mandatory       
	DESCRIPTION     
		"The number of received packets dropped because a LAN protocol is not 
		supported."
	::= { router 24 }

rtGlobalRxError         OBJECT-TYPE
	SYNTAX  Counter
	ACCESS  read-only                       
	STATUS  mandatory       
	DESCRIPTION     
		"The number of errors encountered when receiving from 
		the EiconCard(s)."
	::= { router 25 }

rtGlobalCountersReset   OBJECT-TYPE
	SYNTAX  ControlOnOff
	ACCESS  read-write                      
	STATUS  mandatory       
	DESCRIPTION     
		"This variable is used to reset all router global counters."
	::= { router 26 }

rtTraceCtrl             OBJECT-TYPE     -- Not supported by Eicon Agent
	SYNTAX  ControlOnOff
	ACCESS  read-write                      
	STATUS  mandatory       
	DESCRIPTION     
		"This object is used to start or stop the trace with the parameters
		 specified by the following trace objects."
	::= { router 27 }

rtTraceFileName         OBJECT-TYPE     -- Not supported by Eicon Agent
	SYNTAX  DisplayString (SIZE (1..48))
	ACCESS  read-write                      
	STATUS  mandatory       
	DESCRIPTION     
		"The (fully qualified) file name for the file which will hold the trace."
	::= { router 28 }

rtTraceInterfaceType    OBJECT-TYPE     -- Not supported by Eicon Agent
	SYNTAX  INTEGER
	ACCESS  read-write                      
	STATUS  mandatory       
	DESCRIPTION     
		"The mask which indicates to the Agent the interface type(s) to be traced.
		The trace value for the lower layer is (1) and for the upper 
		layer is (2)."
	::= { router 29 }

--      ***************************************************************************
--                      Router Port Status table.
--      ***************************************************************************

rtPortTable             OBJECT-TYPE
	SYNTAX  SEQUENCE OF RtPortEntry
	ACCESS  not-accessible
	STATUS  mandatory       
	DESCRIPTION     
		"The router port table."
	::= { router 30 }

rtPortEntry             OBJECT-TYPE
	SYNTAX  RtPortEntry
	ACCESS  not-accessible
	STATUS  mandatory       
	DESCRIPTION     
		"The router information for one port."
	INDEX   { rtPortIndex }
	::= { rtPortTable 1 }

RtPortEntry ::= SEQUENCE {
	rtPortIndex
		INTEGER,
	rtPortNumber
		INTEGER,
	rtPortProtocol
		INTEGER,
	rtPortTxThroughput
		Gauge,
	rtPortRxThroughput
		Gauge,
	rtPortTxPackets
		Counter,
	rtPortTxBytesLow
		Counter,
	rtPortTxBytesHigh
		Counter,
	rtPortRxPackets
		Counter,
	rtPortRxBytesLow
		Counter,
	rtPortRxBytesHigh
		Counter,
	rtPortTxDropNoResource
		Counter,
	rtPortRxError
		Counter,
	rtPortCountersReset
		ControlOnOff
	}

rtPortIndex     OBJECT-TYPE
	SYNTAX  INTEGER (1..48)
	ACCESS  read-only                       
	STATUS  mandatory       
	DESCRIPTION     
		"Index of this table"
	::= { rtPortEntry 1 }

rtPortNumber    OBJECT-TYPE
	SYNTAX  INTEGER (1..48)
	ACCESS  read-only                       
	STATUS  mandatory       
	DESCRIPTION     
		"EiconCard port number."
	::= { rtPortEntry 2 }

rtPortProtocol  OBJECT-TYPE
	SYNTAX  INTEGER
	ACCESS  read-only                       
	STATUS  mandatory       
	DESCRIPTION     
		"Mask indicating the choice of WAN protocols:
		 x25 (1), fr (2), ppp (4), sna (8), hdlc (16)."
	::= { rtPortEntry 3 }

rtPortTxThroughput      OBJECT-TYPE
	SYNTAX  Gauge
	ACCESS  read-only                       
	STATUS  mandatory       
	DESCRIPTION
		"Throughput calculated for the transmision."
	::= { rtPortEntry 4 }

rtPortRxThroughput      OBJECT-TYPE
	SYNTAX  Gauge
	ACCESS  read-only                       
	STATUS  mandatory       
	DESCRIPTION     
		"Throughput calculated for the reception."
	::= { rtPortEntry 5 }

rtPortTxPackets OBJECT-TYPE
	SYNTAX  Counter
	ACCESS  read-only                       
	STATUS  mandatory       
	DESCRIPTION     
		"Number of packets transmitted for this port."
	::= { rtPortEntry 6 }

rtPortTxBytesLow        OBJECT-TYPE
	SYNTAX  Counter
	ACCESS  read-only                       
	STATUS  mandatory       
	DESCRIPTION     
		"Number of bytes transmitted for this port; the low 32 bits 
		of the 64 bits counter."
	::= { rtPortEntry 7 }

rtPortTxBytesHigh       OBJECT-TYPE
	SYNTAX  Counter
	ACCESS  read-only                       
	STATUS  mandatory       
	DESCRIPTION     
		"Number of bytes transmitted for this port; the high 32 bits
		of the 64 bits counter."
	::= { rtPortEntry 8 }

rtPortRxPackets         OBJECT-TYPE
	SYNTAX  Counter
	ACCESS  read-only                       
	STATUS  mandatory       
	DESCRIPTION     
		"Number of packets received for this port."
	::= { rtPortEntry 9 }

rtPortRxBytesLow        OBJECT-TYPE
	SYNTAX  Counter
	ACCESS  read-only                       
	STATUS  mandatory       
	DESCRIPTION     
		"Number of bytes received for this port; the low 32 bits 
		of the 64 bits counter."
	::= { rtPortEntry 10 }

rtPortRxBytesHigh       OBJECT-TYPE
	SYNTAX  Counter
	ACCESS  read-only                       
	STATUS  mandatory       
	DESCRIPTION     
		"Number of bytes received for this port; the high 32 bits 
		of the 64 bits  counter."
	::= { rtPortEntry 11 }

rtPortTxDropNoResource  OBJECT-TYPE
	SYNTAX  Counter
	ACCESS  read-only                       
	STATUS  mandatory       
	DESCRIPTION     
		"Number of transmit packets dropped because no resources were
		available."
	::= { rtPortEntry 12 }

rtPortRxError   OBJECT-TYPE
	SYNTAX  Counter
	ACCESS  read-only                       
	STATUS  mandatory       
	DESCRIPTION     
		"Number of packets received with an EiconCard error."
	::= { rtPortEntry 13 }

rtPortCountersReset             OBJECT-TYPE
	SYNTAX  ControlOnOff
	ACCESS  read-write              
	STATUS  mandatory       
	DESCRIPTION     
		"This object is used to reset the values of all counters for this port."
	::= { rtPortEntry 14 }

--      ***************************************************************************
--                      Router WAN Connections Status table.
--      ***************************************************************************

rtConnFreeIndex         OBJECT-TYPE
	SYNTAX  INTEGER         
	ACCESS  read-only                       
	STATUS  mandatory       
	DESCRIPTION     
		"The index value used by the Management station to create the row in the 
		rtConnTable. This value will be used to identify new instance of 
		rtConnEntryStatus object when the Management station attempts to write its
		value to createRequest (2).  If the Agent accepts this value it will change
		it to underCreation (3). After that, the Management station has a limited
		time to create all remaining objects in the rtConnEntry and change
		rtConnEntryStatus to valid (1) or abandon and change rtConnEntryStatus
		to invalid (4).  The entries with the invalid (4) state can be deleted
		from the table by the Agent."
	::= { router 31 }

rtConnTable             OBJECT-TYPE
	SYNTAX  SEQUENCE OF RtConnEntry
	ACCESS  not-accessible
	STATUS  mandatory       
	DESCRIPTION     
		"The table of WAN connections to peer routers."
	::= { router 32 }
	
rtConnEntry             OBJECT-TYPE
	SYNTAX  RtConnEntry
	ACCESS  not-accessible
	STATUS  mandatory       
	DESCRIPTION     
		"The routing information for one destination."
	INDEX   { rtConnIndex }
	::= { rtConnTable 1 }

RtConnEntry ::= SEQUENCE {
	rtConnIndex
		INTEGER,
	rtConnName
		DisplayString,
	rtConnComment
		DisplayString,
	rtConnEntryStatus
		EntryStatus,
	rtConnOperState
		OperState,
	rtConnAdminStateCtr
		AdminState,
	rtConnAutoStart
		INTEGER,
	rtConnType
		INTEGER,
	rtConnInactivityTimeout         
		INTEGER,
	rtConnPortNumber
		PortRef,
	rtConnCompression
		INTEGER,
	rtConnRetryNum
		INTEGER,
	rtConnRetryDelay
		INTEGER,
	rtConnPeerRouter
		INTEGER,
	rtConnLanProtocol
		INTEGER,
	rtConnWanProtocol
		INTEGER,
	rtConnX25LocalDTE
		DisplayString,
	rtConnX25RemoteDTE
		DisplayString,
	rtConnX25CallingFacilities
		DisplayString,
	rtConnX25ListeningFacilities
		DisplayString,
	rtConnX25UserData
		DisplayString,
	rtConnX25Pvc
		INTEGER,
	rtConnFrDlci
		INTEGER,
	rtConnSnaPuName
		DisplayString,
	rtConnSnaLocalFqName
		DisplayString,
	rtConnSnaRemoteFqName
		DisplayString,
	rtConnSnaModeName
		DisplayString,
	rtConnSnaSendPaceWindow
		INTEGER,
	rtConnSnaReceivePaceWindow
		INTEGER,
	rtConnSnaRuSendLow
		INTEGER,
	rtConnSnaRuReceiveLow
		INTEGER,
	rtConnSnaRuSendHigh
		INTEGER,
	rtConnSnaRuReceiveHigh
		INTEGER,
	rtConnUsage
		INTEGER,
	rtConnFrSegmentation
		INTEGER,
	rtConnFrXid
		INTEGER,
	rtConnPrimOrBackName
      DisplayString,
	rtConnRipSapUpdateType
		INTEGER,
	rtConnSAPDelay
		INTEGER,
	rtConnRIPDelay
		INTEGER
	}

rtConnIndex             OBJECT-TYPE
	SYNTAX  INTEGER
	ACCESS  read-only                       
	STATUS  mandatory       
	DESCRIPTION     
		"The index used to identify the connection entry."
	::= { rtConnEntry 1 }

rtConnName              OBJECT-TYPE
	SYNTAX  DisplayString (SIZE (1..16))
	ACCESS  read-write                      
	STATUS  mandatory       
	DESCRIPTION     
		"The name used to identify the connection entry."
	::= { rtConnEntry 2 }

rtConnComment           OBJECT-TYPE
	SYNTAX  DisplayString (SIZE (0..80))
	ACCESS  read-write
	STATUS  mandatory       
	DESCRIPTION     
		"Optional comment about the connection entry."
	::= { rtConnEntry 3 }

rtConnEntryStatus               OBJECT-TYPE
	SYNTAX  EntryStatus
	ACCESS  read-write                      
	STATUS  mandatory       
	DESCRIPTION     
		"The object used to reserve the connection entry during the row
		creation. It also indicates if the entry is valid or not."
	::= { rtConnEntry 4 }

rtConnOperState         OBJECT-TYPE
	SYNTAX  OperState
	ACCESS  read-only                       
	STATUS  mandatory       
	DESCRIPTION     
		"The object describing the state of the connection."
	::= { rtConnEntry 5 }

rtConnAdminStateCtr     OBJECT-TYPE
	SYNTAX  AdminState
	ACCESS  read-write                      
	STATUS  mandatory       
	DESCRIPTION
		"The object used to start and stop the circuit for this connection
		entry."
	::= { rtConnEntry 6 }

rtConnAutoStart         OBJECT-TYPE
	SYNTAX  INTEGER {
		startYes (1),
		startNo (2)
		}
	ACCESS  read-write                      
	STATUS  mandatory       
	DESCRIPTION     
		"The object used to indicate if the connnection should be activated
		every time the router starts. Yes is the default."
	::= { rtConnEntry 7 }

rtConnType              OBJECT-TYPE
	SYNTAX  INTEGER {
		typeIn (1),
		typeOut (2),
		typeTwoWay (3)
		}
	ACCESS  read-write                      
	STATUS  mandatory       
	DESCRIPTION     
		"The type of connection."
	::= { rtConnEntry 8 }

rtConnInactivityTimeout         OBJECT-TYPE
	SYNTAX  INTEGER
	ACCESS  read-write                      
	STATUS  mandatory       
	DESCRIPTION     
		"The connection inactivity timeout in seconds."
	::= { rtConnEntry 9 }

rtConnPortNumber        OBJECT-TYPE
	SYNTAX  PortRef
	ACCESS  read-write                      
	STATUS  mandatory       
	DESCRIPTION     
		"The EiconCard port number for this connection."
	::= { rtConnEntry 10 }

rtConnCompression       OBJECT-TYPE
	SYNTAX  INTEGER {
		comprNo (1),
		comprStac (2),
		comprOther (3)
		}
	ACCESS  read-write                      
	STATUS  mandatory       
	DESCRIPTION     
		"The object indicating the type of compression to use, if any."
	::= { rtConnEntry 11 }

rtConnRetryNum  OBJECT-TYPE
	SYNTAX  INTEGER
	ACCESS  read-write                      
	STATUS  mandatory       
	DESCRIPTION     
		"The connection retry count; value (0) indicates no retry, 
		value (100) indicates infinite retry,  value (5) is the default."
	::= { rtConnEntry 12 }

rtConnRetryDelay        OBJECT-TYPE
	SYNTAX  INTEGER
	ACCESS  read-write                      
	STATUS  mandatory       
	DESCRIPTION     
		"The connection retry delay in seconds."
	::= { rtConnEntry 13 }

rtConnPeerRouter        OBJECT-TYPE
	SYNTAX  INTEGER {
		peerNetWareV2 (1),
		peerNetWareNLM (2),
		peerUniversal (3),
      peerCISCO (4)
		}
	ACCESS  read-write                      
	STATUS  mandatory       
	DESCRIPTION     
		"The type of the peer router for this connection."
	::= { rtConnEntry 14 }

rtConnLanProtocol       OBJECT-TYPE
	SYNTAX  INTEGER
	ACCESS  read-write                      
	STATUS  mandatory       
	DESCRIPTION     
	"The mask used to indicate the type of LAN protocols used for this
	connection. IPX =1, IP=2, AT=4."
	::= { rtConnEntry 15 }

rtConnWanProtocol       OBJECT-TYPE
	SYNTAX  INTEGER {
		connX25Svc (1),
		connX25Pvc (2),
		connFr (3),
		connPpp (4),
		connSna (5),
		connHdlc (6)
		}
	ACCESS  read-write                      
	STATUS  mandatory       
	DESCRIPTION     
		"The object indicates which WAN protocol will be used for this
		connection."
	::= { rtConnEntry 16 }

rtConnX25LocalDTE       OBJECT-TYPE
	SYNTAX  DisplayString (SIZE (1..17))
	ACCESS  read-write
	STATUS  mandatory
	DESCRIPTION
		"The X25 Local DTE Address configured for this connection."
	::= { rtConnEntry 17 }

rtConnX25RemoteDTE      OBJECT-TYPE
	SYNTAX  DisplayString (SIZE (1..17))
	ACCESS  read-write
	STATUS  mandatory
	DESCRIPTION
		"The X25 Remote DTE Address configured for this connection."
	::= { rtConnEntry 18 }

rtConnX25CallingFacilities      OBJECT-TYPE
	SYNTAX  DisplayString (SIZE (1..218))
	ACCESS  read-write
	STATUS  mandatory
	DESCRIPTION
		"The X25 Calling Facilities configured for this connection."
	::= { rtConnEntry 19 }

rtConnX25ListeningFacilities    OBJECT-TYPE
	SYNTAX  DisplayString (SIZE (1..218))
	ACCESS  read-write
	STATUS  mandatory
	DESCRIPTION
		"The X25 Listening Facilities configured for this connection."
	::= { rtConnEntry 20 }

rtConnX25UserData       OBJECT-TYPE
	SYNTAX  DisplayString (SIZE (1..256))
	ACCESS  read-write
	STATUS  mandatory
	DESCRIPTION
		"The X25 User Data configured for this connection."
	::= { rtConnEntry 21 }

rtConnX25Pvc    OBJECT-TYPE
	SYNTAX  INTEGER
	ACCESS  read-write
	STATUS  mandatory
	DESCRIPTION
		"The X25 PVC  configured for this connection."
	::= { rtConnEntry 22 }

rtConnFrDlci    OBJECT-TYPE
	SYNTAX  INTEGER
	ACCESS  read-write
	STATUS  mandatory
	DESCRIPTION
		"The Frame Relay DLCI  configured for this connection."
	::= { rtConnEntry 23 }

rtConnSnaPuName         OBJECT-TYPE
	SYNTAX  DisplayString (SIZE (1..8))
	ACCESS  read-write
	STATUS  mandatory
	DESCRIPTION
		"Physical Unit Name."
	::= { rtConnEntry 24 }

rtConnSnaLocalFqName    OBJECT-TYPE
	SYNTAX  DisplayString (SIZE (1..18))
	ACCESS  read-write
	STATUS  mandatory
	DESCRIPTION
		"Local fully qualified name."
	::= { rtConnEntry 25 }

rtConnSnaRemoteFqName   OBJECT-TYPE
	SYNTAX  DisplayString (SIZE (1..18))
	ACCESS  read-write
	STATUS  mandatory
	DESCRIPTION
		"Remote fully qualified name."
	::= { rtConnEntry 26 }

rtConnSnaModeName       OBJECT-TYPE
	SYNTAX  DisplayString (SIZE (1..8))
	ACCESS  read-write
	STATUS  mandatory
	DESCRIPTION
		"Mode name."
	::= { rtConnEntry 27 }

rtConnSnaSendPaceWindow OBJECT-TYPE
	SYNTAX  INTEGER (1..255)
	ACCESS  read-write
	STATUS  mandatory
	DESCRIPTION
		"Send Pace Window."
	::= { rtConnEntry 28 }

rtConnSnaReceivePaceWindow  OBJECT-TYPE
	SYNTAX  INTEGER (1..255)
	ACCESS  read-write
	STATUS  mandatory
	DESCRIPTION
		"Receive Pace Window."
	::= { rtConnEntry 29 }

rtConnSnaRuSendLow      OBJECT-TYPE
	SYNTAX  INTEGER (133..248)
	ACCESS  read-write
	STATUS  mandatory
	DESCRIPTION
		"Request Unit send low."
	::= { rtConnEntry 30 }

rtConnSnaRuReceiveLow   OBJECT-TYPE
	SYNTAX  INTEGER (133..248)
	ACCESS  read-write
	STATUS  mandatory
	DESCRIPTION
		"Request Unit receive low."
	::= { rtConnEntry 31 }

rtConnSnaRuSendHigh     OBJECT-TYPE
	SYNTAX  INTEGER (133..248)
	ACCESS  read-write
	STATUS  mandatory
	DESCRIPTION
		"Request Unit send high."
	::= { rtConnEntry 32 }

rtConnSnaRuReceiveHigh  OBJECT-TYPE
	SYNTAX  INTEGER (133..248)
	ACCESS  read-write
	STATUS  mandatory
	DESCRIPTION
		"Request unit receive high."
	::= { rtConnEntry 33 }

rtConnUsage  OBJECT-TYPE
	SYNTAX  INTEGER {
			uSagePrimary (1),
			uSageBackup (2)
			   }
	ACCESS  read-write
	STATUS  mandatory
	DESCRIPTION
		"The connection can be defined as a primary or
		  a backup connection for a primary."
	::= { rtConnEntry 34 }

rtConnFrSegmentation  OBJECT-TYPE
   SYNTAX   INTEGER {
		no (1),
		yes (2),
		inProgress (3)
	     }
	ACCESS  read-write
	STATUS  mandatory
	DESCRIPTION
		"The object used to indicate if the Frame Relay
		segmentation (RFC1490) can be used on this connection."
	::= { rtConnEntry 35 }

rtConnFrXid  OBJECT-TYPE
	SYNTAX  INTEGER {
		no (1),
		yes (2),
		inProgress (3)
		}
	ACCESS  read-write
	STATUS  mandatory
	DESCRIPTION
		"The object used to indicate if the Frame-relay 
		XID (RFC1490) can be used on this connection"
	::= { rtConnEntry 36 }

rtConnPrimOrBackName  OBJECT-TYPE
   SYNTAX   DisplayString (SIZE(1..16))
	ACCESS  read-write
	STATUS  mandatory
	DESCRIPTION
		"This parameter applies only if the rtConnFunction
		 field=FuncPrimary. This is the name used to identify 
		 primary connection entry."
	::= { rtConnEntry 37 }

rtConnRipSapUpdateType  OBJECT-TYPE     -- Not supported by Eicon Agent OS/2
	SYNTAX  INTEGER {
		none (1),
		onchange (2),
		periodic (3)
		}
	ACCESS  read-write
	STATUS  mandatory
	DESCRIPTION
		 "The update type of RIP / SAP."
	::= { rtConnEntry 38 }

rtConnSAPDelay  OBJECT-TYPE     -- Not supported by Eicon Agent OS/2
	SYNTAX  INTEGER
	ACCESS  read-write
	STATUS  mandatory
	DESCRIPTION
		"The delay in minutes between the SAP updates on this
		WAN connection."
	::= { rtConnEntry 39 }
	
rtConnRIPDelay  OBJECT-TYPE     -- Not supported by Eicon Agent OS/2
	SYNTAX  INTEGER
	ACCESS  read-write
	STATUS  mandatory
	DESCRIPTION
		"The delay in minutes between the RIP updates on this
		  WAN connection."
	::= { rtConnEntry 40 }

--      ***************************************************************************
--                      IP mapping table.
--      ***************************************************************************

rtIPMapFreeIndex        OBJECT-TYPE     -- Not supported by Eicon Agent
	SYNTAX  INTEGER         
	ACCESS  read-only                       
	STATUS  mandatory       
	DESCRIPTION     
		"The index value used by the Management station to create the row in the 
		rtIPMappingTable.  This value will be used to identify new instance of  
		rtIPMapEntryStatus object when the Management station attempts to write its 
		value to createRequest (2).  If the Agent accepts this value it will change
		it to underCreation (3). After that, the Management station has a limited
		time to create all remaining objects in the rtIPMappingEntry and change
		rtIPMapEntryStatus to valid (1) or abandon and change rtIPMapEntryStatus
		to invalid (4).  The entries with the invalid (4) state can be deleted 
		from the table by the Agent."
	::= { router 33 }

rtIPMappingTable        OBJECT-TYPE
	SYNTAX  SEQUENCE OF RtIPMappingEntry
	ACCESS  not-accessible
	STATUS  mandatory       
	DESCRIPTION     
		"The IP mapping table."
	::= { router 34 }

rtIPMappingEntry        OBJECT-TYPE
	SYNTAX  RtIPMappingEntry
	ACCESS  not-accessible
	STATUS  mandatory       
	DESCRIPTION     
		"One mapping information entry."
	INDEX   { rtIPMapConnIndex, rtIPMapIndex }
	::= { rtIPMappingTable 1 }

RtIPMappingEntry ::= SEQUENCE {
	rtIPMapIndex
		INTEGER,
	rtIPMapConnIndex
		INTEGER,
	rtIPMapEntryStatus
		EntryStatus,
	rtIPMapNextHop 
		IpAddress,
	rtIPMapBroadcast
		INTEGER,
	rtIPMapIPMask
		IpAddress,
	rtIPMapVJCompress
		INTEGER
	}

rtIPMapIndex    OBJECT-TYPE
	SYNTAX  INTEGER
	ACCESS  read-only
	STATUS  mandatory       
	DESCRIPTION     
		"The index used to identify the mapping entry. It is possible to have
		multiple LAN mapping entries for one connection."
	::= { rtIPMappingEntry 1 }

rtIPMapConnIndex        OBJECT-TYPE
	SYNTAX  INTEGER
	ACCESS  read-write                      
	STATUS  mandatory       
	DESCRIPTION     
		"Indicates the connection which uses this mapping. It is equal to one of 
		the rtConnIndex values from the rtConnTable."
	::= { rtIPMappingEntry 2 }

rtIPMapEntryStatus      OBJECT-TYPE
	SYNTAX  EntryStatus
	ACCESS  read-write                      
	STATUS  mandatory       
	DESCRIPTION     
		"The object used to reserve the mapping entry during the row
		creation. It also indicates if the entry is valid or not."
	::= { rtIPMappingEntry 3 }

rtIPMapNextHop  OBJECT-TYPE
	SYNTAX  IpAddress
	ACCESS  read-write                      
	STATUS  mandatory       
	DESCRIPTION     
		"The address of the next hop. It is indicated if the Management station
		knows the address and it can not be discovered by the router."
	::= { rtIPMappingEntry 4 }

rtIPMapBroadcast        OBJECT-TYPE     -- Not supported by Eicon Agent NetWare
	SYNTAX  INTEGER {
		broadNo (1),
		broadYes (2)
		}
	ACCESS  read-write                      
	STATUS  mandatory       
	DESCRIPTION     
		"The object which indicates to the router if it may send
		broadcasts for this connection. 'Yes' is the default value."
	::= { rtIPMappingEntry 5 }

rtIPMapIPMask   OBJECT-TYPE
	SYNTAX  IpAddress
	ACCESS  read-write                      
	STATUS  mandatory       
	DESCRIPTION     
		"The IP address mask to be used for this mapping."
	::= { rtIPMappingEntry 6 }

rtIPMapVJCompress       OBJECT-TYPE     -- Not supported by Eicon Agent
	SYNTAX  INTEGER {
		vjNo (1),
		vjYes (2)
		}
	ACCESS  read-write                      
	STATUS  mandatory       
	DESCRIPTION     
		"The object which indicates if the VanJacobsen compression is to be used
		for this mapping."
	::= { rtIPMappingEntry 7 }


--      ***************************************************************************
--                      Router Circuit Status table.
--      ***************************************************************************

rtCircuitTable  OBJECT-TYPE
	SYNTAX  SEQUENCE OF RtCircuitEntry
	ACCESS  not-accessible
	STATUS  mandatory       
	DESCRIPTION     
		"The router circuit table."
	::= { router 35 }

rtCircuitEntry  OBJECT-TYPE
	SYNTAX  RtCircuitEntry
	ACCESS  not-accessible
	STATUS  mandatory       
	DESCRIPTION     
		"The circuit information for one WAN connection. An entry in this table
		will be created by the Agent when the circuit is opened for a specified 
		connection."
	INDEX   { rtCircuitConnIndex }
	::= { rtCircuitTable 1 }

RtCircuitEntry ::= SEQUENCE {
	rtCircuitConnIndex
		INTEGER,
	rtCircuitStatus
		INTEGER,
	rtCircuitTimeUp
		TimeTicks,
	rtCircuitErrCode        
		INTEGER,
	rtCircuitSessionType
		INTEGER,
	rtCircuitConnLSN
		INTEGER,
	rtCircuitDataLSN
		INTEGER,
	rtCircuitCmSelector
		INTEGER,
	rtCircuitCompression
		INTEGER,
	rtCircuitCompAlgorithm
		INTEGER,
	rtCircuitBeforeComp
		Gauge,
	rtCircuitAfterComp
		Gauge,
	rtCircuitTxErr
		INTEGER,
	rtCircuitBoundLANProtocol
		INTEGER,
	rtCircuitRemoteRouter
		DisplayString,
	rtCircuitCountersReset
		ControlOnOff,
	rtCircuitWanProtocol
		INTEGER,
	rtCircuitX25LocalDTE
		DisplayString,
	rtCircuitX25RemoteDTE
		DisplayString,
	rtCircuitX25CallingFacilities
		DisplayString,
	rtCircuitX25ListeningFacilities
		DisplayString,
	rtCircuitX25UserData
		DisplayString,
	rtCircuitX25Cause
		INTEGER,
	rtCircuitX25Diag
		INTEGER,
	rtCircuitX25Pvc
		INTEGER,
	rtCircuitFrDlci
		INTEGER,
	rtCircuitFrSegmentation
		INTEGER,
	rtCircuitFrXIDNegot
		INTEGER,
	rtCircuitFrXIDPacketSize
		INTEGER,
	rtCircuitFrCongestion
		INTEGER
	}

rtCircuitConnIndex      OBJECT-TYPE
	SYNTAX  INTEGER
	ACCESS  read-only
	STATUS  mandatory       
	DESCRIPTION     
		"Indicates the connection which generated this circuit. It is equal to one
		of the rtConnIndex values from the rtConnTable."
	::= { rtCircuitEntry 1 }

rtCircuitStatus         OBJECT-TYPE
	SYNTAX  INTEGER {
		listening (1),
		calling (2),
		connected (3),
		hangingup (4),
		hungup (5),
		aborted (6),
		idle (7),
		portdisconnected (8),
		notbound (9),
		unknown (10)
		}
	ACCESS  read-only
	STATUS  mandatory       
	DESCRIPTION     
		"Indicates the circuit status."
	::= { rtCircuitEntry 2 }

rtCircuitTimeUp         OBJECT-TYPE
	SYNTAX  TimeTicks
	ACCESS  read-only
	STATUS  mandatory       
	DESCRIPTION     
		"Time elapsed since this circuit was started."
	::= { rtCircuitEntry 3 }

rtCircuitErrCode        OBJECT-TYPE
	SYNTAX  INTEGER
	ACCESS  read-only
	STATUS  mandatory       
	DESCRIPTION     
		"Last error code returned from the EiconCard."
	::= { rtCircuitEntry 4 }

rtCircuitSessionType    OBJECT-TYPE
	SYNTAX  INTEGER
	ACCESS  read-only
	STATUS  mandatory       
	DESCRIPTION     
		"Type of circuit session."
	::= { rtCircuitEntry 5 }

rtCircuitConnLSN        OBJECT-TYPE
	SYNTAX  INTEGER
	ACCESS  read-only
	STATUS  mandatory       
	DESCRIPTION     
		"Connection Manager LSN used for management."
	::= { rtCircuitEntry 6 }

rtCircuitDataLSN        OBJECT-TYPE
	SYNTAX  INTEGER
	ACCESS  read-only
	STATUS  mandatory       
	DESCRIPTION     
		"Connection Manager LSN used for data."
	::= { rtCircuitEntry 7 }

rtCircuitCmSelector             OBJECT-TYPE
	SYNTAX  INTEGER
	ACCESS  read-only
	STATUS  mandatory       
	DESCRIPTION     
		"Handle returned by Connection Manager for this circuit."
	::= { rtCircuitEntry 8 }

rtCircuitCompression    OBJECT-TYPE
	SYNTAX  INTEGER
	ACCESS  read-only
	STATUS  mandatory       
	DESCRIPTION     
		"Compression on/off, after negotiation."
	::= { rtCircuitEntry 9 }

rtCircuitCompAlgorithm  OBJECT-TYPE
	SYNTAX  INTEGER
	ACCESS  read-only
	STATUS  mandatory       
	DESCRIPTION     
		"Compression type, after negotiation."
	::= { rtCircuitEntry 10 }

rtCircuitBeforeComp             OBJECT-TYPE
	SYNTAX  Gauge
	ACCESS  read-only
	STATUS  mandatory       
	DESCRIPTION     
		"Number of bytes sent before compression."
	::= { rtCircuitEntry 11 }

rtCircuitAfterComp      OBJECT-TYPE
	SYNTAX  Gauge
	ACCESS  read-only
	STATUS  mandatory       
	DESCRIPTION     
		"Number of bytes sent after compression."
	::= { rtCircuitEntry 12 }

rtCircuitTxErr  OBJECT-TYPE
	SYNTAX  INTEGER
	ACCESS  read-only
	STATUS  mandatory       
	DESCRIPTION     
		"The number of Transmit errors"
	::= { rtCircuitEntry 13 }

rtCircuitBoundLANProtocol       OBJECT-TYPE
	SYNTAX  INTEGER
	ACCESS  read-only
	STATUS  mandatory       
	DESCRIPTION     
	"The mask used to indicate the type of LAN protocols used for this
	connection.  Possible values are: IPX=1, IP=2, AT=4."
	::= { rtCircuitEntry 14 }

rtCircuitRemoteRouter   OBJECT-TYPE
	SYNTAX  DisplayString (SIZE (1..48))
	ACCESS  read-only
	STATUS  mandatory       
	DESCRIPTION     
		"The name of the remote router discovered by the local router."
	::= { rtCircuitEntry 15 }

rtCircuitCountersReset  OBJECT-TYPE     -- Not supported by Eicon Agent ???
	SYNTAX  ControlOnOff
	ACCESS  read-write
	STATUS  mandatory       
	DESCRIPTION     
		"The object is used to reset all counters for this circuit."
	::= { rtCircuitEntry 16 }
	
rtCircuitWanProtocol    OBJECT-TYPE
	SYNTAX  INTEGER {
		connX25Svc (1),
		connX25Pvc (2),
		connFr (3),
		connPpp (4),
		connSna (5),
		connHdlc (6)
		}
	ACCESS  read-only
	STATUS  mandatory       
	DESCRIPTION     
		"The object indicates which WAN protocol will be used for this
		connection."
	::= { rtCircuitEntry 17 }

rtCircuitX25LocalDTE    OBJECT-TYPE
	SYNTAX  DisplayString (SIZE (1..17))
	ACCESS  read-only
	STATUS  mandatory
	DESCRIPTION
		"The X25 Local DTE Address for this circuit"
	::= { rtCircuitEntry 18 }

rtCircuitX25RemoteDTE   OBJECT-TYPE
	SYNTAX  DisplayString (SIZE (1..17))
	ACCESS  read-only
	STATUS  mandatory
	DESCRIPTION
		"The X25 Remote DTE Address for this circuit"
	::= { rtCircuitEntry 19 }

rtCircuitX25CallingFacilities   OBJECT-TYPE
	SYNTAX  DisplayString (SIZE (1..218))
	ACCESS  read-only
	STATUS  mandatory
	DESCRIPTION
		"The X25 Calling Facilities for this circuit"
	::= { rtCircuitEntry 20 }

rtCircuitX25ListeningFacilities OBJECT-TYPE
	SYNTAX  DisplayString (SIZE (1..218))
	ACCESS  read-only
	STATUS  mandatory
	DESCRIPTION
		"The X25 Listening Facilities for this circuit"
	::= { rtCircuitEntry 21 }

rtCircuitX25UserData    OBJECT-TYPE
	SYNTAX  DisplayString (SIZE (1..256))
	ACCESS  read-only
	STATUS  mandatory
	DESCRIPTION
		"The X25 User Data for this circuit"
	::= { rtCircuitEntry 22 }

rtCircuitX25Cause       OBJECT-TYPE
	SYNTAX  INTEGER
	ACCESS  read-only
	STATUS  mandatory
	DESCRIPTION
		"The Cause of Circuit connection failure"
	::= { rtCircuitEntry 23 }

rtCircuitX25Diag        OBJECT-TYPE
	SYNTAX  INTEGER
	ACCESS  read-only
	STATUS  mandatory
	DESCRIPTION
		"Diagnostics code of the Circuit connection failure."
	::= { rtCircuitEntry 24 }

rtCircuitX25Pvc OBJECT-TYPE
	SYNTAX  INTEGER
	ACCESS  read-only
	STATUS  mandatory
	DESCRIPTION
		"The X25 PVC for this circuit."
	::= { rtCircuitEntry 25 }

rtCircuitFrDlci OBJECT-TYPE
	SYNTAX  INTEGER
	ACCESS  read-only
	STATUS  mandatory
	DESCRIPTION
		"The Frame Relay DLCI for this circuit."
	::= { rtCircuitEntry 26 }

rtCircuitFrSegmentation OBJECT-TYPE
	SYNTAX  INTEGER {
		no (1),
		yes (2),
		inProgress (3)
		}
	ACCESS  read-only
	STATUS  mandatory
	DESCRIPTION
		"The object used to indicate if the Frame Relay
		segmentation (RFC1490) can be used on this circuit."
	::= { rtCircuitEntry 27 }

rtCircuitFrXIDNegot OBJECT-TYPE
	SYNTAX  INTEGER {
		no (1),
		yes (2),
		inProgress (3)
		}
	ACCESS  read-only
	STATUS  mandatory
	DESCRIPTION
		"The object used to indicate if the Frame Relay 
		XID (RFC1490) can be used on this circuit."
	::= { rtCircuitEntry 28 }

rtCircuitFrXIDPacketSize OBJECT-TYPE
	SYNTAX  INTEGER
	ACCESS  read-only
	STATUS  mandatory
	DESCRIPTION
		"The size of the Frame Relay XID packet."
	::= { rtCircuitEntry 29 }

rtCircuitFrCongestion OBJECT-TYPE
	SYNTAX  INTEGER {
		noCongestion (1),
		congested (2)
		}
	ACCESS  read-only
	STATUS  mandatory
	DESCRIPTION
		"The object indicates if Frame Relay can be congested
		 on this circuit."
	::= { rtCircuitEntry 30 }

--      ***************************************************************************
--                      Router IP/WAN Circuit Information table.
--      ***************************************************************************

rtCircuitIPTable        OBJECT-TYPE
	SYNTAX  SEQUENCE OF RtCircuitIPEntry
	ACCESS  not-accessible
	STATUS  mandatory       
	DESCRIPTION     
		"The router IP info table."
	::= { router 36 }

rtCircuitIPEntry        OBJECT-TYPE
	SYNTAX  RtCircuitIPEntry
	ACCESS  not-accessible
	STATUS  mandatory       
	DESCRIPTION     
		"The circuit information specific to IP."
	INDEX   { rtCircuitIPConnIndex }
	::= { rtCircuitIPTable 1 }

RtCircuitIPEntry ::= SEQUENCE {
	rtCircuitIPConnIndex
		INTEGER,
	rtCircuitIPRemoteAddress
		IpAddress,
	rtCircuitIPLocalAddress
		IpAddress,
	rtCircuitIPTxPackets
		Counter,
	rtCircuitIPTxBytes
		Counter,
	rtCircuitIPRxPackets
		Counter,
	rtCircuitIPRxBytes
		Counter
	}

rtCircuitIPConnIndex    OBJECT-TYPE
	SYNTAX  INTEGER
	ACCESS  read-only
	STATUS  mandatory       
	DESCRIPTION     
		"Indicates the connection which generated this circuit. It is 
		equal to one of the rtConnIndex values from the rtConnTable."
	::= { rtCircuitIPEntry 1 }

rtCircuitIPRemoteAddress        OBJECT-TYPE
	SYNTAX  IpAddress
	ACCESS  read-only
	STATUS  mandatory       
	DESCRIPTION     
		"Remote router IP address."
	::= { rtCircuitIPEntry 2 }

rtCircuitIPLocalAddress         OBJECT-TYPE
	SYNTAX  IpAddress
	ACCESS  read-only
	STATUS  mandatory       
	DESCRIPTION     
		"Local router IP address."
	::= { rtCircuitIPEntry 3 }

rtCircuitIPTxPackets            OBJECT-TYPE
	SYNTAX  Counter
	ACCESS  read-only
	STATUS  mandatory       
	DESCRIPTION     
		"Number of transmit packets which carry IP."
	::= { rtCircuitIPEntry 4 }

rtCircuitIPTxBytes      OBJECT-TYPE
	SYNTAX  Counter
	ACCESS  read-only
	STATUS  mandatory       
	DESCRIPTION     
		"Number of transmit bytes which carry IP."
	::= { rtCircuitIPEntry 5 }

rtCircuitIPRxPackets            OBJECT-TYPE
	SYNTAX  Counter
	ACCESS  read-only
	STATUS  mandatory       
	DESCRIPTION     
		"Number of received packets which carry IP."
	::= { rtCircuitIPEntry 6 }

rtCircuitIPRxBytes      OBJECT-TYPE
	SYNTAX  Counter
	ACCESS  read-only
	STATUS  mandatory       
	DESCRIPTION     
		"Number of received bytes which carry IP."
	::= { rtCircuitIPEntry 7 }

--      ***************************************************************************
--                      Router IPX/WAN Circuit Information table.
--      ***************************************************************************

rtCircuitIPXTable       OBJECT-TYPE     -- Not supported by Eicon Agent OS/2
	SYNTAX  SEQUENCE OF RtCircuitIPXEntry
	ACCESS  not-accessible
	STATUS  mandatory       
	DESCRIPTION     
		"The router IPX info table."
	::= { router 37 }

rtCircuitIPXEntry       OBJECT-TYPE
	SYNTAX  RtCircuitIPXEntry
	ACCESS  not-accessible
	STATUS  mandatory       
	DESCRIPTION     
		"The circuit information."
	INDEX   { rtCircuitIPXConnIndex }
	::= { rtCircuitIPXTable 1 }

RtCircuitIPXEntry ::= SEQUENCE {
	rtCircuitIPXConnIndex
		INTEGER,
	rtCircuitIPXRemoteNode
		OCTET STRING,
	rtCircuitIPXRemoteNetwork
		OCTET STRING,
	rtCircuitIPXLocalNode
		OCTET STRING,
	rtCircuitIPXLocalNetwork
		OCTET STRING,
	rtCircuitIPXTxPackets
		Counter,
	rtCircuitIPXTxBytes
		Counter,
	rtCircuitIPXRxPackets
		Counter,
	rtCircuitIPXRxBytes
		Counter
	}

rtCircuitIPXConnIndex   OBJECT-TYPE
	SYNTAX  INTEGER
	ACCESS  read-only
	STATUS  mandatory       
	DESCRIPTION     
		"Indicates the connection which generated this circuit.It is
		equal to one of the rtConnIndex values from the rtConnTable."
	::= { rtCircuitIPXEntry 1 }

rtCircuitIPXRemoteNode  OBJECT-TYPE
	SYNTAX  OCTET STRING (SIZE (1..6))
	ACCESS  read-only
	STATUS  mandatory       
	DESCRIPTION     
		"Remote router node address."
	::= { rtCircuitIPXEntry 2 }

rtCircuitIPXRemoteNetwork       OBJECT-TYPE
	SYNTAX  OCTET STRING (SIZE (1..4))
	ACCESS  read-only
	STATUS  mandatory       
	DESCRIPTION     
		"Remote router network address."
	::= { rtCircuitIPXEntry 3 }

rtCircuitIPXLocalNode   OBJECT-TYPE
	SYNTAX  OCTET STRING (SIZE (1..6))
	ACCESS  read-only
	STATUS  mandatory       
	DESCRIPTION     
		"Local router node address."
	::= { rtCircuitIPXEntry 4 }

rtCircuitIPXLocalNetwork        OBJECT-TYPE
	SYNTAX  OCTET STRING (SIZE (1..4))
	ACCESS  read-only
	STATUS  mandatory       
	DESCRIPTION     
		"Local router network address."
	::= { rtCircuitIPXEntry 5 }

rtCircuitIPXTxPackets   OBJECT-TYPE
	SYNTAX  Counter
	ACCESS  read-only
	STATUS  mandatory       
	DESCRIPTION     
		"Number of transmit packets which carry IPX."
	::= { rtCircuitIPXEntry 6 }

rtCircuitIPXTxBytes             OBJECT-TYPE
	SYNTAX  Counter
	ACCESS  read-only
	STATUS  mandatory       
	DESCRIPTION     
		"Number of transmit bytes which carry IPX."
	::= { rtCircuitIPXEntry 7 }

rtCircuitIPXRxPackets   OBJECT-TYPE
	SYNTAX  Counter
	ACCESS  read-only
	STATUS  mandatory       
	DESCRIPTION     
		"Number of received packets which carry IPX."
	::= { rtCircuitIPXEntry 8 }

rtCircuitIPXRxBytes             OBJECT-TYPE
	SYNTAX  Counter
	ACCESS  read-only
	STATUS  mandatory       
	DESCRIPTION     
		"Number of received bytes which carry IPX."
	::= { rtCircuitIPXEntry 9 }

--      ***************************************************************************
--                      Router AT/WAN Circuit Info table.
--      ***************************************************************************

rtCircuitATTable        OBJECT-TYPE     -- Not supported by Eicon Agent OS/2
	SYNTAX  SEQUENCE OF RtCircuitATEntry
	ACCESS  not-accessible
	STATUS  mandatory       
	DESCRIPTION     
		"The router AT info table."
	::= { router 38 }

rtCircuitATEntry        OBJECT-TYPE
	SYNTAX  RtCircuitATEntry
	ACCESS  not-accessible
	STATUS  mandatory       
	DESCRIPTION     
		"The AT circuit information."
	INDEX   { rtCircuitATConnIndex }
	::= { rtCircuitATTable 1 }

RtCircuitATEntry ::= SEQUENCE {
	rtCircuitATConnIndex
		INTEGER,
	rtCircuitATRemoteNet
		OCTET STRING,
	rtCircuitATRemoteNode
		OCTET STRING,
	rtCircuitATLocalNet
		OCTET STRING,
	rtCircuitATLocalNode
		OCTET STRING,
	rtCircuitATTxPackets
		Counter,
	rtCircuitATTxBytes
		Counter,
	rtCircuitATRxPackets
		Counter,
	rtCircuitATRxBytes
		Counter
	}

rtCircuitATConnIndex    OBJECT-TYPE
	SYNTAX  INTEGER
	ACCESS  read-only
	STATUS  mandatory       
	DESCRIPTION     
		"Indicates the connection which generated this circuit.It is 
		equal to one of the rtConnIndex values from the rtConnTable."
	::= { rtCircuitATEntry 1 }

rtCircuitATRemoteNet    OBJECT-TYPE
	SYNTAX  OCTET STRING (SIZE (1..2))
	ACCESS  read-only
	STATUS  mandatory       
	DESCRIPTION     
		"Remote router network address."
	::= { rtCircuitATEntry 2 }

rtCircuitATRemoteNode   OBJECT-TYPE
	SYNTAX  OCTET STRING (SIZE (1..1))
	ACCESS  read-only
	STATUS  mandatory       
	DESCRIPTION     
		"Remote router node address."
	::= { rtCircuitATEntry 3 }

rtCircuitATLocalNet     OBJECT-TYPE
	SYNTAX  OCTET STRING (SIZE (1..2))
	ACCESS  read-only
	STATUS  mandatory       
	DESCRIPTION     
		"Local router network address."
	::= { rtCircuitATEntry 4 }

rtCircuitATLocalNode    OBJECT-TYPE
	SYNTAX  OCTET STRING (SIZE (1..1))
	ACCESS  read-only
	STATUS  mandatory       
	DESCRIPTION     
		"Local router node address."
	::= { rtCircuitATEntry 5 }

rtCircuitATTxPackets    OBJECT-TYPE
	SYNTAX  Counter
	ACCESS  read-only
	STATUS  mandatory       
	DESCRIPTION     
		"Number of transmit packets which carry AT."
	::= { rtCircuitATEntry 6 }

rtCircuitATTxBytes              OBJECT-TYPE
	SYNTAX  Counter
	ACCESS  read-only
	STATUS  mandatory       
	DESCRIPTION     
		"Number of transmit bytes which carry AT."
	::= { rtCircuitATEntry 7 }

rtCircuitATRxPackets    OBJECT-TYPE
	SYNTAX  Counter
	ACCESS  read-only
	STATUS  mandatory       
	DESCRIPTION     
		"Number of received packets which carry AT."
	::= { rtCircuitATEntry 8 }

rtCircuitATRxBytes              OBJECT-TYPE
	SYNTAX  Counter
	ACCESS  read-only
	STATUS  mandatory       
	DESCRIPTION     
		"Number of received bytes which carry AT."
	::= { rtCircuitATEntry 9 }

--      ***********************************************************************
--                      Router IP Filter.
--      ***********************************************************************

rtMaxIPFilter     OBJECT-TYPE     -- Not supported by Eicon Agent NetWare
	SYNTAX  INTEGER
	ACCESS  read-only
	STATUS  mandatory
	DESCRIPTION
		"The maximum number of IP Filters that can be configured
		for this router."
	::= { router 39 }

rtAvailableIPFilter   OBJECT-TYPE     -- Not supported by Eicon Agent NetWare
	SYNTAX  Gauge
	ACCESS  read-only
	STATUS  mandatory
	DESCRIPTION
		"The number of IP Filters still available for this router."
	::= { router 40 }

rtIPFilterDropStatsIn   OBJECT-TYPE   -- Not supported by Eicon Agent NetWare
	SYNTAX  Counter
	ACCESS  read-only
	STATUS  mandatory
	DESCRIPTION
		"Total number of incoming packets dropped."
	::= { router 41 }

rtIPFilterDropStatsOut   OBJECT-TYPE   -- Not supported by Eicon Agent NetWare
	SYNTAX  Counter
	ACCESS  read-only
	STATUS  mandatory
	DESCRIPTION
		"Total number of outgoing packets dropped."
	::= { router 42 }

rtIPFilterForwardStatsIn   OBJECT-TYPE  -- Not supported by Eicon Agent NetWare
	SYNTAX  Counter
	ACCESS  read-only
	STATUS  mandatory
	DESCRIPTION
		"Total number of incoming packets forwarded."
	::= { router 43 }

rtIPFilterForwardStatsOut   OBJECT-TYPE -- Not supported by Eicon Agent NetWare
	SYNTAX  Counter
	ACCESS  read-only
	STATUS  mandatory
	DESCRIPTION
		"Total number of outgoing packets forwarded."
	::= { router 44 }

rtIPFilterFreeIndex     OBJECT-TYPE     -- Not supported by Eicon Agent NetWare
	SYNTAX  INTEGER
	ACCESS  read-only
	STATUS  mandatory
	DESCRIPTION
		"This number indicating to the Manager the next available
		rtIPFilterIndex for a new Entry in the rtIPFilterTable
		(0 for none). The Manager will first get this value from
		the Agent and then use it to attempt to create an entry
		with that index value for any connection."
	::= { router 45 }

rtIPFilterTable        OBJECT-TYPE      -- Not supported by Eicon Agent NetWare
	SYNTAX  SEQUENCE OF RtIPFilterEntry
	ACCESS  not-accessible
	STATUS  mandatory       
	DESCRIPTION     
		"The IP Filter table."
	::= { router 46 }

rtIPFilterEntry        OBJECT-TYPE
	SYNTAX  RtIPFilterEntry
	ACCESS  not-accessible
	STATUS  mandatory       
	DESCRIPTION     
		"Information on an IP Filter."
	INDEX   { rtIPFilterConnIndex, rtIPFilterIndex }
	::= { rtIPFilterTable 1 }

RtIPFilterEntry ::= SEQUENCE {
	rtIPFilterConnIndex
		INTEGER,
	rtIPFilterIndex
		INTEGER,
	rtIPFilterEntryStatus
		EntryStatusV2,
	rtIPFilterOperState
		OperState,
	rtIPFilterAdminStateCtr
		AdminState,
	rtIPFilterPosition
		INTEGER,
	rtIPFilterAction
		INTEGER,
	rtIPFilterDirection
		INTEGER,
	rtIPFilterPortType
		INTEGER,
	rtIPFilterLowSrcPort
		INTEGER,
	rtIPFilterHighSrcPort
		INTEGER,
	rtIPFilterLowDestPort
		INTEGER,
	rtIPFilterHighDestPort
		INTEGER,
	rtIPFilterIPAddressSrc
		IpAddress,
	rtIPFilterIPMaskSrc
		IpAddress,
	rtIPFilterIPAddressDest
		IpAddress,
	rtIPFilterIPMaskDest
		IpAddress,
	rtIPFilterStatsIn
		Counter,
	rtIPFilterStatsOut
		Counter
	}

rtIPFilterConnIndex    OBJECT-TYPE
	SYNTAX  INTEGER
	ACCESS  read-only
	STATUS  mandatory       
	DESCRIPTION     
		"Same as rtConnIndex."
	::= { rtIPFilterEntry 1 }

rtIPFilterIndex    OBJECT-TYPE
	SYNTAX  INTEGER
	ACCESS  read-only
	STATUS  mandatory       
	DESCRIPTION     
		"Index of IP Filter for the connection."
	::= { rtIPFilterEntry 2 }

rtIPFilterEntryStatus    OBJECT-TYPE
	SYNTAX  EntryStatusV2
	ACCESS  read-write
	STATUS  mandatory       
	DESCRIPTION     
		"The object used to reserve the connection entry during the row
		creation. It also indicates if the entry is valid or not."
	::= { rtIPFilterEntry 3 }

rtIPFilterOperState    OBJECT-TYPE
	SYNTAX  OperState
	ACCESS  read-only
	STATUS  mandatory       
	DESCRIPTION     
		"The object indicates the state of the IP Filter."
	::= { rtIPFilterEntry 4 }

rtIPFilterAdminStateCtr    OBJECT-TYPE
	SYNTAX  AdminState
	ACCESS  read-write
	STATUS  mandatory       
	DESCRIPTION     
		"The object used to start and stop the IP Filter."
	::= { rtIPFilterEntry 5 }

rtIPFilterPosition    OBJECT-TYPE
	SYNTAX  INTEGER
	ACCESS  read-write
	STATUS  mandatory
	DESCRIPTION
		"This variable indicates the order that the router should 
		 apply each filter.  This field can be set only when adding a
		new IP Filter for a connection.  The manager should use
		a valid rtIPFilterIndex to set this variable.  The new
		filter will be inserted after the corresponding filter.
		To insert the filter at the beginning for the connection,
		set the variable to 0."
	::= { rtIPFilterEntry 6 }

rtIPFilterAction    OBJECT-TYPE
	SYNTAX  INTEGER {
		drop (1),
		forward (2)
		}
	ACCESS  read-write
	STATUS  mandatory       
	DESCRIPTION     
		"Drop (1) or Forward (2) the information."
	::= { rtIPFilterEntry 7 }

rtIPFilterDirection    OBJECT-TYPE
	SYNTAX  INTEGER {
		in (1),
		out (2),
		all (3)
		}
	ACCESS  read-write
	STATUS  mandatory       
	DESCRIPTION     
		"Specifies if the filter is applied to outgoing, incoming
		or both ways packets."
	::= { rtIPFilterEntry 8 }

rtIPFilterPortType    OBJECT-TYPE
	SYNTAX  INTEGER {
		tcp (1),
		udp (2),
		all (3)
		}
	ACCESS  read-write
	STATUS  mandatory       
	DESCRIPTION     
		"Protocol type."
	::= { rtIPFilterEntry 9 }

rtIPFilterLowSrcPort    OBJECT-TYPE     -- Not supported by Eicon Agent
	SYNTAX  INTEGER 
	ACCESS  read-write
	STATUS  mandatory       
	DESCRIPTION     
		"Low Source Port."
	::= { rtIPFilterEntry 10 }

rtIPFilterHighSrcPort    OBJECT-TYPE     -- Not supported by Eicon Agent
	SYNTAX  INTEGER 
	ACCESS  read-write
	STATUS  mandatory       
	DESCRIPTION     
		"High Source Port."
	::= { rtIPFilterEntry 11 }

rtIPFilterLowDestPort    OBJECT-TYPE
	SYNTAX  INTEGER 
	ACCESS  read-write
	STATUS  mandatory       
	DESCRIPTION     
		"Low Destination Port."
	::= { rtIPFilterEntry 12 }

rtIPFilterHighDestPort    OBJECT-TYPE
	SYNTAX  INTEGER 
	ACCESS  read-write
	STATUS  mandatory       
	DESCRIPTION     
		"High Destination Port."
	::= { rtIPFilterEntry 13 }

rtIPFilterIPAddressSrc     OBJECT-TYPE
	SYNTAX  IpAddress
	ACCESS  read-write
	STATUS  mandatory
	DESCRIPTION     
		"Source IP Address."
	::= { rtIPFilterEntry 14 }

rtIPFilterIPMaskSrc        OBJECT-TYPE
	SYNTAX  IpAddress
	ACCESS  read-write
	STATUS  mandatory       
	DESCRIPTION     
		"Mask of the source IP Address."
	::= { rtIPFilterEntry 15 }

rtIPFilterIPAddressDest     OBJECT-TYPE
	SYNTAX  IpAddress
	ACCESS  read-write
	STATUS  mandatory
	DESCRIPTION     
		"Destination IP Address."
	::= { rtIPFilterEntry 16 }

rtIPFilterIPMaskDest        OBJECT-TYPE
	SYNTAX  IpAddress
	ACCESS  read-write
	STATUS  mandatory       
	DESCRIPTION     
		"Mask of the destination IP Address."
	::= { rtIPFilterEntry 17 }

rtIPFilterStatsIn   OBJECT-TYPE
	SYNTAX  Counter
	ACCESS  read-only
	STATUS  mandatory
	DESCRIPTION
		"The number of incoming packets that match the filter."
	::= { rtIPFilterEntry 18 }

rtIPFilterStatsOut   OBJECT-TYPE
	SYNTAX  Counter
	ACCESS  read-only
	STATUS  mandatory
	DESCRIPTION
		"The number of outgoing packets that match the filter."
	::= { rtIPFilterEntry 19 }

rtActionState       OBJECT-TYPE
	SYNTAX  ActionState
	ACCESS  read-only 
	STATUS  mandatory
	DESCRIPTION     
		"The state of the operation performed on the router by the
		Agent as a result of setting the values to the 'rtAdminStateCtrl'.
		The Management station will poll that variable after initiating
		an action on the router. The value done(1) indicates that the action
		terminated successfully. The value failed(2) indicates that
		the action terminated with an error. In this case the variable
		'rtActionError' indicates the error code."
	::= { router 47 }

rtActionError           OBJECT-TYPE
	SYNTAX  INTEGER {
		no-error (0),
		err-ALREADY-STARTED (1),
		err-NOT-STARTED (2),
		err-STACK-NOT-BOUND (3),
		err-SHUTDOWN-FAILURE (4),
		err-General (99)
		}
	ACCESS  read-only 
	STATUS  mandatory
	DESCRIPTION     
		"The error code after the unsuccessful operation."
	::= { router 48 }

END
