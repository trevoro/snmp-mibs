BAS-TRAPS-MIB DEFINITIONS ::= BEGIN

IMPORTS
    MODULE-IDENTITY, NOTIFICATION-TYPE          FROM SNMPv2-SMI
    ifIndex                                     FROM IF-MIB
    basTraceLogNotifyComponentId,
    basTraceLogLevel, basTraceLogNotifyString   FROM BAS-TRACE-MIB
    basTraps, basTrapChassis, basTrapSlot,
    basTrapIf, basTrapLPort, 
    basTrapCmtsCmMacAddress,
    basTrapCmtsCmIpAddress, 
    basTrapMgmtOneIpAddress,
    basTrapMgmtTwoIpAddress,
    basTrapCraftIpAddress,
    basTrapIclClass,
    basTrapChassisNumber,	
    basTrapCmtsCmGwAddress,
    basTrapCardType,
    basTrapSubnetType				FROM BAS-MIB;
    
basTrapsMIB MODULE-IDENTITY
    LAST-UPDATED "9812080000Z"
    ORGANIZATION "Broadband Access Systems, Inc."
    CONTACT-INFO
        " Tech Support
          Broadband Access Systems, Inc.
          201 Forest Street
          Marlborough, MA 01752
          USA

          508-485-8200
          support@basystems.com"
    DESCRIPTION
        "This MIB module defines the proprietary notifications
         for Broadband Access Systems, Inc. Network Management."
    ::= { basTraps 1 }

--
-- BAS traps
--

basCardDown NOTIFICATION-TYPE
        OBJECTS { basTrapChassis, basTrapSlot, basTrapIf,
                  basTrapLPort, basTrapCardType }
        STATUS  current
        DESCRIPTION
            "A basCardDown notification indicates that a
            card with the BAS cluster has gone down."
       ::= { basTrapsMIB 1 }

basCardUp NOTIFICATION-TYPE
        OBJECTS { basTrapChassis, basTrapSlot, basTrapIf,
                  basTrapLPort, basTrapCardType }
        STATUS  current
        DESCRIPTION
            "A basCardDown notification indicates that a
            card with the BAS cluster has gone down."
       ::= { basTrapsMIB 2 }

basTraceLogTrap NOTIFICATION-TYPE
        OBJECTS { basTrapChassis, basTrapSlot, basTrapIf,
                  basTrapLPort, basTraceLogNotifyComponentId,
                  basTraceLogLevel, basTraceLogNotifyString }
        STATUS  current
        DESCRIPTION
            "BAS internal use only."
        ::= { basTrapsMIB 3 }

basCmtsCmUp NOTIFICATION-TYPE
        OBJECTS { ifIndex, basTrapCmtsCmMacAddress, basTrapCmtsCmIpAddress }
        STATUS  current
        DESCRIPTION
            "A basCmtsCmUp notification indicates that a
            cable modem has gone up."
       ::= { basTrapsMIB 4 }

basCmtsCmDown NOTIFICATION-TYPE
        OBJECTS { ifIndex, basTrapCmtsCmMacAddress, basTrapCmtsCmIpAddress }
        STATUS  current
        DESCRIPTION
            "A basCmtsCmDown notification indicates that a
            cable modem has gone down."
       ::= { basTrapsMIB 5 }

basBcmStateChange NOTIFICATION-TYPE
        OBJECTS { basTrapChassis, basTrapSlot, basTrapIf,
                  basTrapLPort, basTrapMgmtOneIpAddress,
                  basTrapMgmtTwoIpAddress, basTrapCraftIpAddress }
        STATUS  current
        DESCRIPTION
            "A basBcmStateChange notification indicates a change in the
            IP addresses configuration."
       ::= { basTrapsMIB 6 }

basIclStateChange NOTIFICATION-TYPE
        OBJECTS { ifIndex, basTrapIclClass, basTrapChassisNumber,
		  basTrapChassis, basTrapSlot, basTrapIf,
                  basTrapLPort }
        STATUS  current
        DESCRIPTION
            "A basIclStateChange notification indicates a change in the
            ICL link. Note that the FIA and Chassis number are information
	    about the Peer."
       ::= { basTrapsMIB 7 }

basSoftwareComponentUp NOTIFICATION-TYPE
        OBJECTS { basTrapChassis, basTrapSlot, basTrapIf,
                  basTrapLPort, basTraceLogNotifyComponentId }
        STATUS  current
        DESCRIPTION
            "BAS internal use only."
        ::= { basTrapsMIB 8 }


basSoftwareComponentDown NOTIFICATION-TYPE
        OBJECTS { basTrapChassis, basTrapSlot, basTrapIf,
                  basTrapLPort, basTraceLogNotifyComponentId }
        STATUS  current
        DESCRIPTION
            "BAS internal use only."
        ::= { basTrapsMIB 9 }

basCmtsCmAuthFailure NOTIFICATION-TYPE
        OBJECTS { basTrapCmtsCmMacAddress, basTrapCmtsCmGwAddress }
        STATUS  current
        DESCRIPTION
            "A Cable Modem attempt to connect to the system without authorization."
        ::= { basTrapsMIB 10 }

basDhcpRelayNotConfigured NOTIFICATION-TYPE
        OBJECTS { basTrapChassis, basTrapSlot, basTrapIf,
                  basTrapLPort, basTrapSubnetType }
        STATUS  current
        DESCRIPTION
            "A DHCP configuration error."
        ::= { basTrapsMIB 11 }


END
