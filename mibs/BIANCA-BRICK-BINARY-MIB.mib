-- This file is corresponding to Release 6.1.2.100 from 2001/09/26 00:00:00
-- (C)opyright 1999 BinTec Communications AG, All Rights Reserved
--  $RCSfile: mibbinary,v $ 
-- $Revision: 1.3 $ 

BIANCA-BRICK-BINARY-MIB DEFINITIONS ::= BEGIN

	IMPORTS
	    NetworkAddress, IpAddress, Counter, Gauge, TimeTicks
		FROM RFC1155-SMI

	    OBJECT-TYPE
		FROM RFC-1212;

	org          	OBJECT IDENTIFIER ::= { iso 3 }
	dod          	OBJECT IDENTIFIER ::= { org 6 }
	internet     	OBJECT IDENTIFIER ::= { dod 1 }

	private 	OBJECT IDENTIFIER ::= { internet 4 }
	enterprises 	OBJECT IDENTIFIER ::= { private 1 }
	bintec 		OBJECT IDENTIFIER ::= { enterprises 272 }
	bibo		OBJECT IDENTIFIER ::= { bintec 4 }

    -- Management Information for the IPSec Subsystem of the BIANCA/BRICK, 
    ipsec        OBJECT IDENTIFIER
        ::= { bibo 26 }

	-- textual conventions

	DisplayString ::= OCTET STRING
	    -- This data type is used to model textual information taken
	    -- from the NVT ASCII character set.  By convention, objects
	    -- with this syntax are declared as having
	    --
	    --      SIZE (0..255)


-- Binary Table 

	binTable OBJECT-TYPE
	    SYNTAX  SEQUENCE OF BinEntry
	    ACCESS  not-accessible
	    STATUS  mandatory
	    DESCRIPTION
		"The binTable contains chunks of binary data which 
		 can be chained to larger amounts of data, allowing
		 to store objects of an arbitrary size and format.
                 This table is for internal use only."
	::= { ipsec 65 }

	binEntry OBJECT-TYPE
	    SYNTAX  BinEntry
	    ACCESS  not-accessible
	    STATUS  mandatory
	    DESCRIPTION
		"The binTableEntry objects contain a chunk of binary data
		 each of a maximum of 255 byte in length and can be
		 concatenated to sets of binary data of an arbitrary
		 size and format using the binEntIndex and
		 binEntNextIndex fields. The binEntSetId field is
		 used to identify all blocks of the same set."
	    INDEX { binEntIndex }
	::= { binTable 1 }

	BinEntry ::=
	    SEQUENCE {
		binEntIndex				INTEGER,
		binEntNextIndex				INTEGER,
		binEntSetId				INTEGER,
		binEntData				OCTET STRING
	    }

	binEntIndex OBJECT-TYPE
	    SYNTAX  INTEGER 
	    ACCESS  not-accessible
	    STATUS  mandatory
	    DESCRIPTION
		"The Index is a unique identifier for this entry"
	::= { binEntry 1 }

	binEntNextIndex OBJECT-TYPE
	    SYNTAX  INTEGER 
	    ACCESS  not-accessible
	    STATUS  mandatory
	    DESCRIPTION
		"This object specifies the index of the next chunk of
		 data in a set"
	::= { binEntry 2 }

	binEntSetId OBJECT-TYPE
	    SYNTAX  INTEGER
	    ACCESS  not-accessible
	    STATUS  mandatory
	    DESCRIPTION
		"This object serves as a unique identifier for the
		 binary data set this entry belongs to and is equal
		 for all entries of a set"
	::= { binEntry 3 }

	binEntData OBJECT-TYPE
	    SYNTAX  OCTET STRING (0..255)
	    ACCESS  not-accessible
	    STATUS  mandatory
	    DESCRIPTION
		"This object contains a chunk of binary data"
	::= { binEntry 4 }

-- End of Binary Table

-- File Table

	binFileTable OBJECT-TYPE
	    SYNTAX  SEQUENCE OF BinFileEntry
	    ACCESS  not-accessible
	    STATUS  mandatory
	    DESCRIPTION
		"The binFileTable contains entries which combine a
		 name and a set of binary data from the binTable to a
		 file"
	::= { ipsec 66 }

	binFileEntry OBJECT-TYPE
	    SYNTAX  BinFileEntry
	    ACCESS  not-accessible
	    STATUS  mandatory
	    DESCRIPTION
		"The binFileEntry objects contain a file name and
		 a set identifier referencing a data set from the
		 binTable"
	    INDEX { binFileEntSetId }
	::= { binFileTable 1 }

	BinFileEntry ::=
	    SEQUENCE {
		binFileEntName	DisplayString,
		binFileEntSize	INTEGER,
		binFileEntSetId	INTEGER
	    }

	binFileEntName OBJECT-TYPE
	    SYNTAX  DisplayString
	    ACCESS  read-only
	    STATUS  mandatory
	    DESCRIPTION
		"This object contains the file name"
	::= { binFileEntry 1 }

	binFileEntSize OBJECT-TYPE
	    SYNTAX  INTEGER
	    ACCESS  read-only
	    STATUS  mandatory
	    DESCRIPTION
		"This object contains the current size of the file"
	::= { binFileEntry 2 }

	binFileEntSetId OBJECT-TYPE
	    SYNTAX  INTEGER 
	    ACCESS  read-only
	    STATUS  mandatory
	    DESCRIPTION
		"This object contains the set identifier as a
		 reference to the binTable"
	::= { binFileEntry 17 }

-- End of File Table



END
