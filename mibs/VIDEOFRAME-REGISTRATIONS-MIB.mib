VIDEOFRAME-REGISTRATIONS-MIB DEFINITIONS ::= BEGIN

	IMPORTS
		MODULE-IDENTITY, OBJECT-IDENTITY, enterprises
			FROM SNMPv2-SMI;

	--  Relationship to Other MIBs
	--
	--
	--  The objects defined in this MIB are located under the
	--  private.enterprises subtree as shown below:
	--
	--               iso(1).org(3).dod(6).internet(1)
	--                            |
	--                         private(4)
	--                            |
	--                       enterprises(1)
	--                            |
	--                       videoframe(4596)
	--                            |
	--                        vfGeneric(3)
	--                                 
	--
	--  References
	--
	--  [1]  RFC 1902.  McCloghrie, K., and M. Rose, "Structure 
	--       of Management Information for Version 2 of the Simple
	--       Network Management Protocol (SNMPv2)".  
	--       January, 1996.
	--
	--  [2]  RFC 1903.  McCloghrie, K., and M. Rose, "Textual
	--       Conventions for Version 2 of the Simple Network
	--       Management Protocol (SNMPv2)".  
	--       January, 1996.
	--
	--  [3]  RFC 1904.  McCloghrie, K., and M. Rose, "Conformance
	--       Statements for Version 2 of the Simple Network
	--       Management Protocol (SNMPv2)".  
	--       January, 1996.
	--
	--  [4]  RFC 1907.  McCloghrie, K., and M. Rose, "Management 
	--       Information Base for Version 2 of the Simple Network
	--       Management Protocol (SNMPv2)".  
	--       January, 1996.
	--
	--	[5]  Perkins, David and McGinnis, Evan; "Understanding SNMP
	--		 MIBs".  Prentice Hall, ISBN 0-13-437708-7, 1997.
	--
	--
	--  Object Synopsis
	--  
	--
	--  All objects within this MIB are prefixed with the OBJECT
	--  IDENTIFIER "p", where "p" is:
	--
	--  iso(1).org(3).dod(6).internet(1).private(4).enterprises(1)
	--	
	--  or, 1.3.6.1.4.1
	--
	--  1.3.6.1.4.1.4596 is issued to Videoframe by IANA.
	--  p.4596.1 is defined in the Videoframe rmcMIB module.
	--  p.4596.2 is defined in the Videoframe sapMIB module.
	--
	--  Object Name                               Object Id         
	--  --------------------------------          --------------
	--
	--	videoframe									p.4596
	--		vfGeneric								p.4596.3
	--		vfProducts								p.4596.4
	--		vfExperimental							p.4596.5
	--		vfRegistrations							p.4596.6
	--			vfMIBModules						p.4596.6.1
	--				vfReg							p.4596.6.1.1
	--			vfProductsReg						p.4596.6.2
	--				vfProductsRMCReg				p.4596.6.2.1
	--				vfProductsSAPSCtlReg			p.4596.6.2.2
	--				vfProductsGPIAgentReg			p.4596.6.2.3
	--

	videoframe OBJECT-IDENTITY
		STATUS	current
		DESCRIPTION
			"Enterprise name space assigned to 
			 Videoframe Systems by IANA."
	::= { enterprises 4596 }

	--
	--  Videoframe Systems Enterprise Top-Level Registrations
	--
	--  videoframe.1 is defined in the videoframe rmcMIB module,
	--  and videoframe.2 is defined in the videoframe sapMIB module.
	--

	vfGeneric OBJECT-IDENTITY
		STATUS	current
		DESCRIPTION
			"Name space for object definitions common among
			 Videoframe managed devices."
	::= { videoframe 3 }

	vfProducts OBJECT-IDENTITY
		STATUS	current
		DESCRIPTION
			"Name space for object definitions specific to
			 particular Videoframe managed device types."
	::= { videoframe 4 }

	vfExperimental OBJECT-IDENTITY
		STATUS	current
		DESCRIPTION
			"vfExperimental provides a root OID from 
			which experimental MIBs are temporarily 
			based. MIBs that are placed here are Videoframe
			works-in-progress and have not been 
			assigned a permanent OID by Videoframe, typically because 
			the MIB was not ready for deployment."
	::= { videoframe 5 }

	vfRegistrations OBJECT-IDENTITY
		STATUS	current
		DESCRIPTION
			"Name space for Videoframe's 
			authoritatively assigned registrations and 
			MIB modules."
	::= { videoframe 6 }

	vfMIBModules OBJECT-IDENTITY
		STATUS	current
		DESCRIPTION
			"Name space for Registration of MIB modules defined by
			 videoframe systems."
	::= { vfRegistrations 1 }

	vfReg MODULE-IDENTITY
		LAST-UPDATED "0108270000Z"
		ORGANIZATION "Videoframe Systems"
		CONTACT-INFO
			"Videoframe Systems
			P.O. Box 1991,
			Grass Valley, CA 95945, USA.

			+1 (530) 477-2000

			http://www.videoframesystems.com"
	DESCRIPTION
		"This MIB module describes the upper level
		OID registrations for the Videoframe
		enterprise naming space.

		This module will be extended, or modified as 
		required.

		Videoframe Systems reserves the right to
		make changes in specification and other 
		information contained in this document without 
		prior notice. The reader should consult Videoframe Systems
		to determine whether any such changes have been made.

		In no event shall Videoframe Systems be 
		liable for any incidental, indirect, special, 
		or consequential damages whatsoever (including 
		but not limited to lost profits) arising out of 
		or related to this document or the information 
		contained in it.

		Videoframe Systems grants vendors, end users, 
		and other interested parties a non-exclusive 
		license to use this specification in connection 
		with the management of Videoframe Systems products.

		Copyright 2001 Videoframe, Inc."
	REVISION      "0101180000Z"
	DESCRIPTION
		"First release."
	::= { vfMIBModules 1 }

	vfProductsReg OBJECT-IDENTITY
		STATUS	current
		DESCRIPTION
			"Name space for Registration of products offered by
			 videoframe systems."
	::= { vfRegistrations 2 }

	vfProductsRMCReg OBJECT-IDENTITY
		STATUS	current
		DESCRIPTION
			"VF100 RTU Monitoring Controller."
	::= { vfProductsReg 1 }

	vfProductsSAPSCtlReg OBJECT-IDENTITY
		STATUS	current
		DESCRIPTION
			"VF100 SAPS Controller."
	::= { vfProductsReg 2 }

	vfProductsGPIAgentReg OBJECT-IDENTITY
		STATUS	current
		DESCRIPTION
			"VF100 GPI SNMP Agent."
	::= { vfProductsReg 3 }

END
