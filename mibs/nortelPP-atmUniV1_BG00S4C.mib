Nortel-Magellan-Passport-AtmUniMIB
DEFINITIONS ::= BEGIN



IMPORTS

      OBJECT-TYPE
   FROM RFC-1212

      passportMIBs
   FROM Nortel-Magellan-Passport-UsefulDefinitionsMIB

      Counter32,
      DisplayString,
      StorageType,
      RowStatus,
      Gauge32,
      Integer32,
      Unsigned32
   FROM Nortel-Magellan-Passport-StandardTextualConventionsMIB

      AsciiString,
      Hex,
      NonReplicated,
      AsciiStringIndex
   FROM Nortel-Magellan-Passport-TextualConventionsMIB

      atmIfVptIndex,
      atmIfVpt,
      atmIfIndex,
      atmIf
   FROM Nortel-Magellan-Passport-AtmCoreMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     AtmUni Enterprise MIB."

atmUniMIB OBJECT IDENTIFIER ::= { passportMIBs 69 }










-- AtmIf/n Uni
-- This component represents an ATM UNI interface. If this 
-- component is provisioned the Iisp component can not be 
-- provisioned under that AtmIf component. If this component is 
-- deleted, then all associated Vcc components are deleted.

atmIfUni OBJECT IDENTIFIER ::= { atmIf 6 }



atmIfUniRowStatusTable OBJECT-TYPE
   SYNTAX     SEQUENCE OF AtmIfUniRowStatusEntry
   ACCESS     not-accessible
   STATUS     mandatory
   DESCRIPTION
     "This entry controls the addition and deletion of 
      atmIfUni components."
::= { atmIfUni 1 }

atmIfUniRowStatusEntry OBJECT-TYPE
   SYNTAX     AtmIfUniRowStatusEntry
   ACCESS     not-accessible
   STATUS     mandatory
   DESCRIPTION
     "A single entry in the table represents a single 
      atmIfUni component."
   INDEX {
      atmIfIndex,
      atmIfUniIndex }
::= { atmIfUniRowStatusTable 1 }

AtmIfUniRowStatusEntry ::= SEQUENCE {
   atmIfUniRowStatus
      RowStatus,
   atmIfUniComponentName
      DisplayString,
   atmIfUniStorageType
      StorageType,
   atmIfUniIndex
      NonReplicated }

atmIfUniRowStatus OBJECT-TYPE
   SYNTAX     RowStatus 
   ACCESS     read-write
   STATUS     mandatory
   DESCRIPTION
     "This variable is used as the basis for SNMP naming of
      atmIfUni components.
      These components can be added and deleted."
::= { atmIfUniRowStatusEntry 1 }

atmIfUniComponentName OBJECT-TYPE
   SYNTAX     DisplayString 
   ACCESS     read-only
   STATUS     mandatory
   DESCRIPTION
     "This variable provides the component's string name for
      use with the ASCII Console Interface"
::= { atmIfUniRowStatusEntry 2 }

atmIfUniStorageType OBJECT-TYPE
   SYNTAX     StorageType 
   ACCESS     read-only
   STATUS     mandatory
   DESCRIPTION
     "This variable represents the storage type value for the
      atmIfUni tables."
::= { atmIfUniRowStatusEntry 4 }

atmIfUniIndex OBJECT-TYPE
   SYNTAX     NonReplicated 
   ACCESS     not-accessible
   STATUS     mandatory
   DESCRIPTION
     "This variable represents the index for the atmIfUni tables."
::= { atmIfUniRowStatusEntry 10 }

atmIfUniProvTable OBJECT-TYPE
   SYNTAX     SEQUENCE OF AtmIfUniProvEntry
   ACCESS     not-accessible
   STATUS     mandatory
   DESCRIPTION
     "This group contains the provisionable attributes for the Uni 
      component."
::= { atmIfUni 10 }

atmIfUniProvEntry OBJECT-TYPE
   SYNTAX     AtmIfUniProvEntry
   ACCESS     not-accessible
   STATUS     mandatory
   DESCRIPTION
     "An entry in the atmIfUniProvTable."
   INDEX {
      atmIfIndex,
      atmIfUniIndex }
::= { atmIfUniProvTable 1 }

AtmIfUniProvEntry ::= SEQUENCE {
   atmIfUniVersion
      INTEGER,
   atmIfUniSide
      INTEGER,
   atmIfUniSoftPvcRetryPeriod
      Unsigned32,
   atmIfUniSoftPvpAndPvcRetryPeriod
      Unsigned32,
   atmIfUniSoftPvpAndPvcHoldOffTime
      Unsigned32 }

atmIfUniVersion OBJECT-TYPE
   SYNTAX     INTEGER  {
                 atmForum30(0),
                 atmForum31(1) }
   ACCESS     read-write
   STATUS     mandatory
   DESCRIPTION
     "This attribute specifies which specification the UNI complies with. 
      The options are ATM FORUM 3.0 or ATM FORUM 3.1. If this 
      attribute is changed then all switched Vcc components in this 
      interface are cleared due to the fact that the two versions are 
      incompatible."
   DEFVAL     { atmForum31 }
::= { atmIfUniProvEntry 1 }

atmIfUniSide OBJECT-TYPE
   SYNTAX     INTEGER  {
                 network(0),
                 user(1) }
   ACCESS     read-write
   STATUS     mandatory
   DESCRIPTION
     "This attribute indicates which side the interface is, user or network."
   DEFVAL     { network }
::= { atmIfUniProvEntry 2 }

atmIfUniSoftPvcRetryPeriod OBJECT-TYPE
   SYNTAX     Unsigned32 (20..999999)
   ACCESS     read-write
   STATUS     obsolete
   DESCRIPTION
     "This attribute represents the time in seconds to wait between call set 
      up retries. The resolution is to the nearest 10 seconds. 
      This attribute has been obsoleted and is replaced by the 
      softPvpAndPvcRetryPeriod attribute."
   DEFVAL     { 60 }
::= { atmIfUniProvEntry 3 }

atmIfUniSoftPvpAndPvcRetryPeriod OBJECT-TYPE
   SYNTAX     Unsigned32 (20..999999)
   ACCESS     read-write
   STATUS     mandatory
   DESCRIPTION
     "This attribute represents the time in seconds to wait between soft 
      PVP or soft PVC call setup retries. The resolution is to the nearest 
      10 seconds."
   DEFVAL     { 60 }
::= { atmIfUniProvEntry 4 }

atmIfUniSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { atmIfUniProvEntry 5 }

atmIfUniOperTable OBJECT-TYPE
   SYNTAX     SEQUENCE OF AtmIfUniOperEntry
   ACCESS     not-accessible
   STATUS     mandatory
   DESCRIPTION
     "This attribute group contains the operational attributes for the Uni 
      component."
::= { atmIfUni 11 }

atmIfUniOperEntry OBJECT-TYPE
   SYNTAX     AtmIfUniOperEntry
   ACCESS     not-accessible
   STATUS     mandatory
   DESCRIPTION
     "An entry in the atmIfUniOperTable."
   INDEX {
      atmIfIndex,
      atmIfUniIndex }
::= { atmIfUniOperTable 1 }

AtmIfUniOperEntry ::= SEQUENCE {
   atmIfUniMacAddress
      AsciiString }

atmIfUniMacAddress OBJECT-TYPE
   SYNTAX     AsciiString (SIZE (12))
   ACCESS     read-only
   STATUS     mandatory
   DESCRIPTION
     "This attribute indicates the MAC address of the port, which is used 
      for address registration of the user side as the default ESI."
::= { atmIfUniOperEntry 1 }

atmIfUniAcctOptTable OBJECT-TYPE
   SYNTAX     SEQUENCE OF AtmIfUniAcctOptEntry
   ACCESS     not-accessible
   STATUS     mandatory
   DESCRIPTION
     "This group contains the provisionable attributes for accounting."
::= { atmIfUni 12 }

atmIfUniAcctOptEntry OBJECT-TYPE
   SYNTAX     AtmIfUniAcctOptEntry
   ACCESS     not-accessible
   STATUS     mandatory
   DESCRIPTION
     "An entry in the atmIfUniAcctOptTable."
   INDEX {
      atmIfIndex,
      atmIfUniIndex }
::= { atmIfUniAcctOptTable 1 }

AtmIfUniAcctOptEntry ::= SEQUENCE {
   atmIfUniAccountCollection
      OCTET STRING,
   atmIfUniAccountConnectionType
      INTEGER,
   atmIfUniAccountClass
      Unsigned32,
   atmIfUniServiceExchange
      Unsigned32 }

atmIfUniAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit or force. 
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { atmIfUniAcctOptEntry 1 }

atmIfUniAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { origTerm }
::= { atmIfUniAcctOptEntry 2 }

atmIfUniAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { atmIfUniAcctOptEntry 3 }

atmIfUniServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { atmIfUniAcctOptEntry 4 }


-- AtmIf/n Uni Ilmi
-- This component represents the Interim Local Management Interface 
-- (ILMI) protocol on the interface.

atmIfUniIlmi OBJECT IDENTIFIER ::= { atmIfUni 2 }



atmIfUniIlmiRowStatusTable OBJECT-TYPE
   SYNTAX     SEQUENCE OF AtmIfUniIlmiRowStatusEntry
   ACCESS     not-accessible
   STATUS     mandatory
   DESCRIPTION
     "This entry controls the addition and deletion of 
      atmIfUniIlmi components."
::= { atmIfUniIlmi 1 }

atmIfUniIlmiRowStatusEntry OBJECT-TYPE
   SYNTAX     AtmIfUniIlmiRowStatusEntry
   ACCESS     not-accessible
   STATUS     mandatory
   DESCRIPTION
     "A single entry in the table represents a single 
      atmIfUniIlmi component."
   INDEX {
      atmIfIndex,
      atmIfUniIndex,
      atmIfUniIlmiIndex }
::= { atmIfUniIlmiRowStatusTable 1 }

AtmIfUniIlmiRowStatusEntry ::= SEQUENCE {
   atmIfUniIlmiRowStatus
      RowStatus,
   atmIfUniIlmiComponentName
      DisplayString,
   atmIfUniIlmiStorageType
      StorageType,
   atmIfUniIlmiIndex
      NonReplicated }

atmIfUniIlmiRowStatus OBJECT-TYPE
   SYNTAX     RowStatus 
   ACCESS     read-only
   STATUS     mandatory
   DESCRIPTION
     "This variable is used as the basis for SNMP naming of
      atmIfUniIlmi components.
      These components cannot be added nor deleted."
::= { atmIfUniIlmiRowStatusEntry 1 }

atmIfUniIlmiComponentName OBJECT-TYPE
   SYNTAX     DisplayString 
   ACCESS     read-only
   STATUS     mandatory
   DESCRIPTION
     "This variable provides the component's string name for
      use with the ASCII Console Interface"
::= { atmIfUniIlmiRowStatusEntry 2 }

atmIfUniIlmiStorageType OBJECT-TYPE
   SYNTAX     StorageType 
   ACCESS     read-only
   STATUS     mandatory
   DESCRIPTION
     "This variable represents the storage type value for the
      atmIfUniIlmi tables."
::= { atmIfUniIlmiRowStatusEntry 4 }

atmIfUniIlmiIndex OBJECT-TYPE
   SYNTAX     NonReplicated 
   ACCESS     not-accessible
   STATUS     mandatory
   DESCRIPTION
     "This variable represents the index for the atmIfUniIlmi tables."
::= { atmIfUniIlmiRowStatusEntry 10 }

atmIfUniIlmiStateTable OBJECT-TYPE
   SYNTAX     SEQUENCE OF AtmIfUniIlmiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfUniIlmi 10 }

atmIfUniIlmiStateEntry OBJECT-TYPE
   SYNTAX     AtmIfUniIlmiStateEntry
   ACCESS     not-accessible
   STATUS     mandatory
   DESCRIPTION
     "An entry in the atmIfUniIlmiStateTable."
   INDEX {
      atmIfIndex,
      atmIfUniIndex,
      atmIfUniIlmiIndex }
::= { atmIfUniIlmiStateTable 1 }

AtmIfUniIlmiStateEntry ::= SEQUENCE {
   atmIfUniIlmiAdminState
      INTEGER,
   atmIfUniIlmiOperationalState
      INTEGER,
   atmIfUniIlmiUsageState
      INTEGER }

atmIfUniIlmiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfUniIlmiStateEntry 1 }

atmIfUniIlmiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfUniIlmiStateEntry 2 }

atmIfUniIlmiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfUniIlmiStateEntry 3 }

atmIfUniIlmiProvTable OBJECT-TYPE
   SYNTAX     SEQUENCE OF AtmIfUniIlmiProvEntry
   ACCESS     not-accessible
   STATUS     mandatory
   DESCRIPTION
     "This attribute group contains the provisionable attributes for the Ilmi 
      component."
::= { atmIfUniIlmi 11 }

atmIfUniIlmiProvEntry OBJECT-TYPE
   SYNTAX     AtmIfUniIlmiProvEntry
   ACCESS     not-accessible
   STATUS     mandatory
   DESCRIPTION
     "An entry in the atmIfUniIlmiProvTable."
   INDEX {
      atmIfIndex,
      atmIfUniIndex,
      atmIfUniIlmiIndex }
::= { atmIfUniIlmiProvTable 1 }

AtmIfUniIlmiProvEntry ::= SEQUENCE {
   atmIfUniIlmiVci
      Unsigned32,
   atmIfUniIlmiOperatingMode
      INTEGER }

atmIfUniIlmiVci OBJECT-TYPE
   SYNTAX     Unsigned32 (0..65535)
   ACCESS     read-write
   STATUS     mandatory
   DESCRIPTION
     "This attribute identifies the ILMI channel number."
   DEFVAL     { 16 }
::= { atmIfUniIlmiProvEntry 1 }

atmIfUniIlmiOperatingMode OBJECT-TYPE
   SYNTAX     INTEGER  {
                 addressRegEnabled(0),
                 addressRegDisabled(1),
                 ilmiDisabled(2) }
   ACCESS     read-write
   STATUS     mandatory
   DESCRIPTION
     "This attribute is used to enable/disable the ILMI protocol. 
      addressRegEnabled indicates that the ILMI address registration 
      protocol is enabled. addressRegDisabled indicates that the ILMI 
      address registration protocol is disabled. ilmiDisabled indicates that 
      all of ILMI is disabled."
   DEFVAL     { addressRegEnabled }
::= { atmIfUniIlmiProvEntry 2 }

atmIfUniIlmiStatsTable OBJECT-TYPE
   SYNTAX     SEQUENCE OF AtmIfUniIlmiStatsEntry
   ACCESS     not-accessible
   STATUS     mandatory
   DESCRIPTION
     "This attribute group contains the statistics for the AtmIlmi 
      component."
::= { atmIfUniIlmi 12 }

atmIfUniIlmiStatsEntry OBJECT-TYPE
   SYNTAX     AtmIfUniIlmiStatsEntry
   ACCESS     not-accessible
   STATUS     mandatory
   DESCRIPTION
     "An entry in the atmIfUniIlmiStatsTable."
   INDEX {
      atmIfIndex,
      atmIfUniIndex,
      atmIfUniIlmiIndex }
::= { atmIfUniIlmiStatsTable 1 }

AtmIfUniIlmiStatsEntry ::= SEQUENCE {
   atmIfUniIlmiTxPdus
      Counter32,
   atmIfUniIlmiRxPdus
      Counter32,
   atmIfUniIlmiRxBadPdusDiscarded
      Counter32 }

atmIfUniIlmiTxPdus OBJECT-TYPE
   SYNTAX     Counter32 
   ACCESS     read-only
   STATUS     mandatory
   DESCRIPTION
     "This attribute counts the number of transmitted ILMI PDUs. The 
      counter wraps to 0 when the maximum value is exceeded."
::= { atmIfUniIlmiStatsEntry 1 }

atmIfUniIlmiRxPdus OBJECT-TYPE
   SYNTAX     Counter32 
   ACCESS     read-only
   STATUS     mandatory
   DESCRIPTION
     "This attribute counts the total number of received ILMI PDUs.The 
      counter wraps to 0 when the maximum value is exceeded."
::= { atmIfUniIlmiStatsEntry 2 }

atmIfUniIlmiRxBadPdusDiscarded OBJECT-TYPE
   SYNTAX     Counter32 
   ACCESS     read-only
   STATUS     mandatory
   DESCRIPTION
     "This attribute counts the number of received ILMI PDUs that were 
      discarded due to invalid SNMP format. The counter wraps to 0 
      when the maximum value is exceeded."
::= { atmIfUniIlmiStatsEntry 3 }

atmIfUniIlmiPrefixToRegisterTable OBJECT-TYPE
   SYNTAX     SEQUENCE OF AtmIfUniIlmiPrefixToRegisterEntry
   ACCESS     not-accessible
   STATUS     mandatory
   DESCRIPTION
     "This attribute is a list of zero or more addresses. If the side attribute 
      in the Uni component is set to user, then this attribute must be 
      empty; if the side attribute is set to network, then this attribute is a 
      list of prefixes.This attribute represents a list of prefix addresses (26 
      digits) that are sent to the user side. If no prefixes are entered, then 
      the nodeAddress attribute in the AtmCallRouter component is used 
      for address registration."
::= { atmIfUniIlmi 287 }

atmIfUniIlmiPrefixToRegisterEntry OBJECT-TYPE
   SYNTAX     AtmIfUniIlmiPrefixToRegisterEntry
   ACCESS     not-accessible
   STATUS     mandatory
   DESCRIPTION
     "An entry in the atmIfUniIlmiPrefixToRegisterTable."
   INDEX {
      atmIfIndex,
      atmIfUniIndex,
      atmIfUniIlmiIndex,
      atmIfUniIlmiPrefixToRegisterValue }
::= { atmIfUniIlmiPrefixToRegisterTable 1 }

AtmIfUniIlmiPrefixToRegisterEntry ::= SEQUENCE {
   atmIfUniIlmiPrefixToRegisterValue
      AsciiString,
   atmIfUniIlmiPrefixToRegisterRowStatus
      RowStatus }

atmIfUniIlmiPrefixToRegisterValue OBJECT-TYPE
   SYNTAX     AsciiString (SIZE (26))
   ACCESS     read-write
   STATUS     mandatory
   DESCRIPTION
     "This variable represents both the value and the index for the
      atmIfUniIlmiPrefixToRegisterTable."
::= { atmIfUniIlmiPrefixToRegisterEntry 1 }

atmIfUniIlmiPrefixToRegisterRowStatus OBJECT-TYPE
   SYNTAX     RowStatus 
   ACCESS     write-only
   STATUS     mandatory
   DESCRIPTION
     "This variable is used to control the addition and deletion 
      of individual values of the atmIfUniIlmiPrefixToRegisterTable."
::= { atmIfUniIlmiPrefixToRegisterEntry 2 }

atmIfUniIlmiEsiToRegisterTable OBJECT-TYPE
   SYNTAX     SEQUENCE OF AtmIfUniIlmiEsiToRegisterEntry
   ACCESS     not-accessible
   STATUS     mandatory
   DESCRIPTION
     "This attribute is a list of zero or more addresses. If the side attribute 
      in the Uni component is set to network, then this attribute must be 
      an empty list; if the side attribute is set to user, then this attribute is 
      a list of end system indicators (ESI) addresses (12 hex digits) that 
      are used to compose addresses to register with the network side."
::= { atmIfUniIlmi 288 }

atmIfUniIlmiEsiToRegisterEntry OBJECT-TYPE
   SYNTAX     AtmIfUniIlmiEsiToRegisterEntry
   ACCESS     not-accessible
   STATUS     mandatory
   DESCRIPTION
     "An entry in the atmIfUniIlmiEsiToRegisterTable."
   INDEX {
      atmIfIndex,
      atmIfUniIndex,
      atmIfUniIlmiIndex,
      atmIfUniIlmiEsiToRegisterValue }
::= { atmIfUniIlmiEsiToRegisterTable 1 }

AtmIfUniIlmiEsiToRegisterEntry ::= SEQUENCE {
   atmIfUniIlmiEsiToRegisterValue
      AsciiString,
   atmIfUniIlmiEsiToRegisterRowStatus
      RowStatus }

atmIfUniIlmiEsiToRegisterValue OBJECT-TYPE
   SYNTAX     AsciiString (SIZE (12))
   ACCESS     read-write
   STATUS     mandatory
   DESCRIPTION
     "This variable represents both the value and the index for the
      atmIfUniIlmiEsiToRegisterTable."
::= { atmIfUniIlmiEsiToRegisterEntry 1 }

atmIfUniIlmiEsiToRegisterRowStatus OBJECT-TYPE
   SYNTAX     RowStatus 
   ACCESS     write-only
   STATUS     mandatory
   DESCRIPTION
     "This variable is used to control the addition and deletion 
      of individual values of the atmIfUniIlmiEsiToRegisterTable."
::= { atmIfUniIlmiEsiToRegisterEntry 2 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

atmIfUniSig OBJECT IDENTIFIER ::= { atmIfUni 3 }



atmIfUniSigRowStatusTable OBJECT-TYPE
   SYNTAX     SEQUENCE OF AtmIfUniSigRowStatusEntry
   ACCESS     not-accessible
   STATUS     mandatory
   DESCRIPTION
     "This entry controls the addition and deletion of 
      atmIfUniSig components."
::= { atmIfUniSig 1 }

atmIfUniSigRowStatusEntry OBJECT-TYPE
   SYNTAX     AtmIfUniSigRowStatusEntry
   ACCESS     not-accessible
   STATUS     mandatory
   DESCRIPTION
     "A single entry in the table represents a single 
      atmIfUniSig component."
   INDEX {
      atmIfIndex,
      atmIfUniIndex,
      atmIfUniSigIndex }
::= { atmIfUniSigRowStatusTable 1 }

AtmIfUniSigRowStatusEntry ::= SEQUENCE {
   atmIfUniSigRowStatus
      RowStatus,
   atmIfUniSigComponentName
      DisplayString,
   atmIfUniSigStorageType
      StorageType,
   atmIfUniSigIndex
      NonReplicated }

atmIfUniSigRowStatus OBJECT-TYPE
   SYNTAX     RowStatus 
   ACCESS     read-only
   STATUS     mandatory
   DESCRIPTION
     "This variable is used as the basis for SNMP naming of
      atmIfUniSig components.
      These components cannot be added nor deleted."
::= { atmIfUniSigRowStatusEntry 1 }

atmIfUniSigComponentName OBJECT-TYPE
   SYNTAX     DisplayString 
   ACCESS     read-only
   STATUS     mandatory
   DESCRIPTION
     "This variable provides the component's string name for
      use with the ASCII Console Interface"
::= { atmIfUniSigRowStatusEntry 2 }

atmIfUniSigStorageType OBJECT-TYPE
   SYNTAX     StorageType 
   ACCESS     read-only
   STATUS     mandatory
   DESCRIPTION
     "This variable represents the storage type value for the
      atmIfUniSig tables."
::= { atmIfUniSigRowStatusEntry 4 }

atmIfUniSigIndex OBJECT-TYPE
   SYNTAX     NonReplicated 
   ACCESS     not-accessible
   STATUS     mandatory
   DESCRIPTION
     "This variable represents the index for the atmIfUniSig tables."
::= { atmIfUniSigRowStatusEntry 10 }

atmIfUniSigProvTable OBJECT-TYPE
   SYNTAX     SEQUENCE OF AtmIfUniSigProvEntry
   ACCESS     not-accessible
   STATUS     mandatory
   DESCRIPTION
     "This attribute group contains the provisionable attributes for the 
      Signalling component."
::= { atmIfUniSig 10 }

atmIfUniSigProvEntry OBJECT-TYPE
   SYNTAX     AtmIfUniSigProvEntry
   ACCESS     not-accessible
   STATUS     mandatory
   DESCRIPTION
     "An entry in the atmIfUniSigProvTable."
   INDEX {
      atmIfIndex,
      atmIfUniIndex,
      atmIfUniSigIndex }
::= { atmIfUniSigProvTable 1 }

AtmIfUniSigProvEntry ::= SEQUENCE {
   atmIfUniSigVci
      Unsigned32,
   atmIfUniSigAddressConversion
      INTEGER }

atmIfUniSigVci OBJECT-TYPE
   SYNTAX     Unsigned32 (0..65535)
   ACCESS     read-write
   STATUS     mandatory
   DESCRIPTION
     "This attribute specifies the signalling channel number."
   DEFVAL     { 5 }
::= { atmIfUniSigProvEntry 1 }

atmIfUniSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { atmIfUniSigProvEntry 2 }

atmIfUniSigStateTable OBJECT-TYPE
   SYNTAX     SEQUENCE OF AtmIfUniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfUniSig 11 }

atmIfUniSigStateEntry OBJECT-TYPE
   SYNTAX     AtmIfUniSigStateEntry
   ACCESS     not-accessible
   STATUS     mandatory
   DESCRIPTION
     "An entry in the atmIfUniSigStateTable."
   INDEX {
      atmIfIndex,
      atmIfUniIndex,
      atmIfUniSigIndex }
::= { atmIfUniSigStateTable 1 }

AtmIfUniSigStateEntry ::= SEQUENCE {
   atmIfUniSigAdminState
      INTEGER,
   atmIfUniSigOperationalState
      INTEGER,
   atmIfUniSigUsageState
      INTEGER }

atmIfUniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfUniSigStateEntry 1 }

atmIfUniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfUniSigStateEntry 2 }

atmIfUniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfUniSigStateEntry 3 }

atmIfUniSigOperTable OBJECT-TYPE
   SYNTAX     SEQUENCE OF AtmIfUniSigOperEntry
   ACCESS     not-accessible
   STATUS     mandatory
   DESCRIPTION
     "This attribute contains the operational attributes for the 
      AtmSignalling component."
::= { atmIfUniSig 12 }

atmIfUniSigOperEntry OBJECT-TYPE
   SYNTAX     AtmIfUniSigOperEntry
   ACCESS     not-accessible
   STATUS     mandatory
   DESCRIPTION
     "An entry in the atmIfUniSigOperTable."
   INDEX {
      atmIfIndex,
      atmIfUniIndex,
      atmIfUniSigIndex }
::= { atmIfUniSigOperTable 1 }

AtmIfUniSigOperEntry ::= SEQUENCE {
   atmIfUniSigLastTxCauseCode
      Unsigned32,
   atmIfUniSigLastTxDiagCode
      Hex,
   atmIfUniSigLastRxCauseCode
      Unsigned32,
   atmIfUniSigLastRxDiagCode
      Hex }

atmIfUniSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { atmIfUniSigOperEntry 1 }

atmIfUniSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfUniSigOperEntry 2 }

atmIfUniSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { atmIfUniSigOperEntry 3 }

atmIfUniSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfUniSigOperEntry 4 }

atmIfUniSigStatsTable OBJECT-TYPE
   SYNTAX     SEQUENCE OF AtmIfUniSigStatsEntry
   ACCESS     not-accessible
   STATUS     mandatory
   DESCRIPTION
     "This attribute group contains the statistics associated with the 
      AtmSignalling component."
::= { atmIfUniSig 13 }

atmIfUniSigStatsEntry OBJECT-TYPE
   SYNTAX     AtmIfUniSigStatsEntry
   ACCESS     not-accessible
   STATUS     mandatory
   DESCRIPTION
     "An entry in the atmIfUniSigStatsTable."
   INDEX {
      atmIfIndex,
      atmIfUniIndex,
      atmIfUniSigIndex }
::= { atmIfUniSigStatsTable 1 }

AtmIfUniSigStatsEntry ::= SEQUENCE {
   atmIfUniSigCurrentConnections
      Counter32,
   atmIfUniSigPeakConnections
      Gauge32,
   atmIfUniSigSuccessfulConnections
      Counter32,
   atmIfUniSigFailedConnections
      Counter32,
   atmIfUniSigTxPdus
      Counter32,
   atmIfUniSigRxPdus
      Counter32,
   atmIfUniSigCurrentPmpConnections
      Gauge32,
   atmIfUniSigPeakPmpConnections
      Gauge32,
   atmIfUniSigSuccessfulPmpConnections
      Counter32,
   atmIfUniSigFailedPmpConnections
      Counter32,
   atmIfUniSigNewCurrentConnections
      Gauge32 }

atmIfUniSigCurrentConnections OBJECT-TYPE
   SYNTAX     Counter32 
   ACCESS     read-only
   STATUS     obsolete
   DESCRIPTION
     "This attribute indicates the total number of currently active 
      connections."
::= { atmIfUniSigStatsEntry 1 }

atmIfUniSigPeakConnections OBJECT-TYPE
   SYNTAX     Gauge32 (0..4294967295)
   ACCESS     read-only
   STATUS     mandatory
   DESCRIPTION
     "This attribute indicates the high water mark of active point-to-
      point and point-to-multipoint connections."
::= { atmIfUniSigStatsEntry 2 }

atmIfUniSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { atmIfUniSigStatsEntry 3 }

atmIfUniSigFailedConnections OBJECT-TYPE
   SYNTAX     Counter32 
   ACCESS     read-only
   STATUS     mandatory
   DESCRIPTION
     "This attribute counts the total number of switched connections that 
      were not successfully established.The counter wraps to 0 when the 
      maximum value is exceeded."
::= { atmIfUniSigStatsEntry 4 }

atmIfUniSigTxPdus OBJECT-TYPE
   SYNTAX     Counter32 
   ACCESS     read-only
   STATUS     mandatory
   DESCRIPTION
     "This attribute counts the number of transmitted signalling 
      PDUs.The counter wraps to 0 when the maximum value is 
      exceeded."
::= { atmIfUniSigStatsEntry 5 }

atmIfUniSigRxPdus OBJECT-TYPE
   SYNTAX     Counter32 
   ACCESS     read-only
   STATUS     mandatory
   DESCRIPTION
     "This attribute counts the number of received signalling PDUs.The 
      counter wraps to 0 when the maximum value is exceeded."
::= { atmIfUniSigStatsEntry 6 }

atmIfUniSigCurrentPmpConnections OBJECT-TYPE
   SYNTAX     Gauge32 (0..4294967295)
   ACCESS     read-only
   STATUS     mandatory
   DESCRIPTION
     "This attribute indicates the number of currently active point-to-
      multipoint connections."
::= { atmIfUniSigStatsEntry 7 }

atmIfUniSigPeakPmpConnections OBJECT-TYPE
   SYNTAX     Gauge32 (0..4294967295)
   ACCESS     read-only
   STATUS     mandatory
   DESCRIPTION
     "This attribute indicates the high water mark of active point-to-
      multipoint connections."
::= { atmIfUniSigStatsEntry 8 }

atmIfUniSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { atmIfUniSigStatsEntry 9 }

atmIfUniSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { atmIfUniSigStatsEntry 10 }

atmIfUniSigNewCurrentConnections OBJECT-TYPE
   SYNTAX     Gauge32 (0..4294967295)
   ACCESS     read-only
   STATUS     mandatory
   DESCRIPTION
     "This attribute indicates the total number of currently active point-to-
      point and point-to-multipoint connections."
::= { atmIfUniSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

atmIfUniSigVcd OBJECT IDENTIFIER ::= { atmIfUniSig 2 }



atmIfUniSigVcdRowStatusTable OBJECT-TYPE
   SYNTAX     SEQUENCE OF AtmIfUniSigVcdRowStatusEntry
   ACCESS     not-accessible
   STATUS     mandatory
   DESCRIPTION
     "This entry controls the addition and deletion of 
      atmIfUniSigVcd components."
::= { atmIfUniSigVcd 1 }

atmIfUniSigVcdRowStatusEntry OBJECT-TYPE
   SYNTAX     AtmIfUniSigVcdRowStatusEntry
   ACCESS     not-accessible
   STATUS     mandatory
   DESCRIPTION
     "A single entry in the table represents a single 
      atmIfUniSigVcd component."
   INDEX {
      atmIfIndex,
      atmIfUniIndex,
      atmIfUniSigIndex,
      atmIfUniSigVcdIndex }
::= { atmIfUniSigVcdRowStatusTable 1 }

AtmIfUniSigVcdRowStatusEntry ::= SEQUENCE {
   atmIfUniSigVcdRowStatus
      RowStatus,
   atmIfUniSigVcdComponentName
      DisplayString,
   atmIfUniSigVcdStorageType
      StorageType,
   atmIfUniSigVcdIndex
      NonReplicated }

atmIfUniSigVcdRowStatus OBJECT-TYPE
   SYNTAX     RowStatus 
   ACCESS     read-write
   STATUS     mandatory
   DESCRIPTION
     "This variable is used as the basis for SNMP naming of
      atmIfUniSigVcd components.
      These components can be added and deleted."
::= { atmIfUniSigVcdRowStatusEntry 1 }

atmIfUniSigVcdComponentName OBJECT-TYPE
   SYNTAX     DisplayString 
   ACCESS     read-only
   STATUS     mandatory
   DESCRIPTION
     "This variable provides the component's string name for
      use with the ASCII Console Interface"
::= { atmIfUniSigVcdRowStatusEntry 2 }

atmIfUniSigVcdStorageType OBJECT-TYPE
   SYNTAX     StorageType 
   ACCESS     read-only
   STATUS     mandatory
   DESCRIPTION
     "This variable represents the storage type value for the
      atmIfUniSigVcd tables."
::= { atmIfUniSigVcdRowStatusEntry 4 }

atmIfUniSigVcdIndex OBJECT-TYPE
   SYNTAX     NonReplicated 
   ACCESS     not-accessible
   STATUS     mandatory
   DESCRIPTION
     "This variable represents the index for the atmIfUniSigVcd tables."
::= { atmIfUniSigVcdRowStatusEntry 10 }

atmIfUniSigVcdProvTable OBJECT-TYPE
   SYNTAX     SEQUENCE OF AtmIfUniSigVcdProvEntry
   ACCESS     not-accessible
   STATUS     mandatory
   DESCRIPTION
     "This group contains the provisionable traffic attributes for a control 
      channel."
::= { atmIfUniSigVcd 10 }

atmIfUniSigVcdProvEntry OBJECT-TYPE
   SYNTAX     AtmIfUniSigVcdProvEntry
   ACCESS     not-accessible
   STATUS     mandatory
   DESCRIPTION
     "An entry in the atmIfUniSigVcdProvTable."
   INDEX {
      atmIfIndex,
      atmIfUniIndex,
      atmIfUniSigIndex,
      atmIfUniSigVcdIndex }
::= { atmIfUniSigVcdProvTable 1 }

AtmIfUniSigVcdProvEntry ::= SEQUENCE {
   atmIfUniSigVcdTrafficDescType
      INTEGER,
   atmIfUniSigVcdAtmServiceCategory
      INTEGER,
   atmIfUniSigVcdQosClass
      INTEGER,
   atmIfUniSigVcdTrafficShaping
      INTEGER,
   atmIfUniSigVcdUnshapedTransmitQueueing
      INTEGER,
   atmIfUniSigVcdUsageParameterControl
      INTEGER }

atmIfUniSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { atmIfUniSigVcdProvEntry 1 }

atmIfUniSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { atmIfUniSigVcdProvEntry 3 }

atmIfUniSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { atmIfUniSigVcdProvEntry 21 }

atmIfUniSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { atmIfUniSigVcdProvEntry 50 }

atmIfUniSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { atmIfUniSigVcdProvEntry 60 }

atmIfUniSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { atmIfUniSigVcdProvEntry 70 }

atmIfUniSigVcdTdpTable OBJECT-TYPE
   SYNTAX     SEQUENCE OF AtmIfUniSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { atmIfUniSigVcd 387 }

atmIfUniSigVcdTdpEntry OBJECT-TYPE
   SYNTAX     AtmIfUniSigVcdTdpEntry
   ACCESS     not-accessible
   STATUS     mandatory
   DESCRIPTION
     "An entry in the atmIfUniSigVcdTdpTable."
   INDEX {
      atmIfIndex,
      atmIfUniIndex,
      atmIfUniSigIndex,
      atmIfUniSigVcdIndex,
      atmIfUniSigVcdTdpIndex }
::= { atmIfUniSigVcdTdpTable 1 }

AtmIfUniSigVcdTdpEntry ::= SEQUENCE {
   atmIfUniSigVcdTdpIndex
      Integer32,
   atmIfUniSigVcdTdpValue
      Unsigned32 }

atmIfUniSigVcdTdpIndex OBJECT-TYPE
   SYNTAX     Integer32 (1..5)
   ACCESS     not-accessible
   STATUS     mandatory
   DESCRIPTION
     "This variable represents the atmIfUniSigVcdTdpTable
      specific index for the atmIfUniSigVcdTdpTable."
::= { atmIfUniSigVcdTdpEntry 1 }

atmIfUniSigVcdTdpValue OBJECT-TYPE
   SYNTAX     Unsigned32 (0..2147483647)
   ACCESS     read-write
   STATUS     mandatory
   DESCRIPTION
     "This variable represents an individual value for the
      atmIfUniSigVcdTdpTable."
::= { atmIfUniSigVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

atmIfUniAddr OBJECT IDENTIFIER ::= { atmIfUni 4 }



atmIfUniAddrRowStatusTable OBJECT-TYPE
   SYNTAX     SEQUENCE OF AtmIfUniAddrRowStatusEntry
   ACCESS     not-accessible
   STATUS     mandatory
   DESCRIPTION
     "This entry controls the addition and deletion of 
      atmIfUniAddr components."
::= { atmIfUniAddr 1 }

atmIfUniAddrRowStatusEntry OBJECT-TYPE
   SYNTAX     AtmIfUniAddrRowStatusEntry
   ACCESS     not-accessible
   STATUS     mandatory
   DESCRIPTION
     "A single entry in the table represents a single 
      atmIfUniAddr component."
   INDEX {
      atmIfIndex,
      atmIfUniIndex,
      atmIfUniAddrAddressIndex,
      atmIfUniAddrAddressTypeIndex }
::= { atmIfUniAddrRowStatusTable 1 }

AtmIfUniAddrRowStatusEntry ::= SEQUENCE {
   atmIfUniAddrRowStatus
      RowStatus,
   atmIfUniAddrComponentName
      DisplayString,
   atmIfUniAddrStorageType
      StorageType,
   atmIfUniAddrAddressIndex
      AsciiStringIndex,
   atmIfUniAddrAddressTypeIndex
      INTEGER }

atmIfUniAddrRowStatus OBJECT-TYPE
   SYNTAX     RowStatus 
   ACCESS     read-write
   STATUS     mandatory
   DESCRIPTION
     "This variable is used as the basis for SNMP naming of
      atmIfUniAddr components.
      These components can be added and deleted."
::= { atmIfUniAddrRowStatusEntry 1 }

atmIfUniAddrComponentName OBJECT-TYPE
   SYNTAX     DisplayString 
   ACCESS     read-only
   STATUS     mandatory
   DESCRIPTION
     "This variable provides the component's string name for
      use with the ASCII Console Interface"
::= { atmIfUniAddrRowStatusEntry 2 }

atmIfUniAddrStorageType OBJECT-TYPE
   SYNTAX     StorageType 
   ACCESS     read-only
   STATUS     mandatory
   DESCRIPTION
     "This variable represents the storage type value for the
      atmIfUniAddr tables."
::= { atmIfUniAddrRowStatusEntry 4 }

atmIfUniAddrAddressIndex OBJECT-TYPE
   SYNTAX     AsciiStringIndex (SIZE (1..40))
   ACCESS     not-accessible
   STATUS     mandatory
   DESCRIPTION
     "This variable represents an index for the atmIfUniAddr tables."
::= { atmIfUniAddrRowStatusEntry 10 }

atmIfUniAddrAddressTypeIndex OBJECT-TYPE
   SYNTAX     INTEGER  {
                 primary(0),
                 alternate(1),
                 registered(2),
                 default(3) }
   ACCESS     not-accessible
   STATUS     mandatory
   DESCRIPTION
     "This variable represents an index for the atmIfUniAddr tables."
::= { atmIfUniAddrRowStatusEntry 11 }

atmIfUniAddrOperTable OBJECT-TYPE
   SYNTAX     SEQUENCE OF AtmIfUniAddrOperEntry
   ACCESS     not-accessible
   STATUS     mandatory
   DESCRIPTION
     "This attribute group contains the operational attributes for the 
      Address component."
::= { atmIfUniAddr 10 }

atmIfUniAddrOperEntry OBJECT-TYPE
   SYNTAX     AtmIfUniAddrOperEntry
   ACCESS     not-accessible
   STATUS     mandatory
   DESCRIPTION
     "An entry in the atmIfUniAddrOperTable."
   INDEX {
      atmIfIndex,
      atmIfUniIndex,
      atmIfUniAddrAddressIndex,
      atmIfUniAddrAddressTypeIndex }
::= { atmIfUniAddrOperTable 1 }

AtmIfUniAddrOperEntry ::= SEQUENCE {
   atmIfUniAddrScope
      INTEGER,
   atmIfUniAddrReachability
      INTEGER }

atmIfUniAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { atmIfUniAddrOperEntry 1 }

atmIfUniAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { atmIfUniAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

atmIfUniAddrTermSP OBJECT IDENTIFIER ::= { atmIfUniAddr 2 }



atmIfUniAddrTermSPRowStatusTable OBJECT-TYPE
   SYNTAX     SEQUENCE OF AtmIfUniAddrTermSPRowStatusEntry
   ACCESS     not-accessible
   STATUS     mandatory
   DESCRIPTION
     "This entry controls the addition and deletion of 
      atmIfUniAddrTermSP components."
::= { atmIfUniAddrTermSP 1 }

atmIfUniAddrTermSPRowStatusEntry OBJECT-TYPE
   SYNTAX     AtmIfUniAddrTermSPRowStatusEntry
   ACCESS     not-accessible
   STATUS     mandatory
   DESCRIPTION
     "A single entry in the table represents a single 
      atmIfUniAddrTermSP component."
   INDEX {
      atmIfIndex,
      atmIfUniIndex,
      atmIfUniAddrAddressIndex,
      atmIfUniAddrAddressTypeIndex,
      atmIfUniAddrTermSPIndex }
::= { atmIfUniAddrTermSPRowStatusTable 1 }

AtmIfUniAddrTermSPRowStatusEntry ::= SEQUENCE {
   atmIfUniAddrTermSPRowStatus
      RowStatus,
   atmIfUniAddrTermSPComponentName
      DisplayString,
   atmIfUniAddrTermSPStorageType
      StorageType,
   atmIfUniAddrTermSPIndex
      NonReplicated }

atmIfUniAddrTermSPRowStatus OBJECT-TYPE
   SYNTAX     RowStatus 
   ACCESS     read-write
   STATUS     mandatory
   DESCRIPTION
     "This variable is used as the basis for SNMP naming of
      atmIfUniAddrTermSP components.
      These components can be added and deleted."
::= { atmIfUniAddrTermSPRowStatusEntry 1 }

atmIfUniAddrTermSPComponentName OBJECT-TYPE
   SYNTAX     DisplayString 
   ACCESS     read-only
   STATUS     mandatory
   DESCRIPTION
     "This variable provides the component's string name for
      use with the ASCII Console Interface"
::= { atmIfUniAddrTermSPRowStatusEntry 2 }

atmIfUniAddrTermSPStorageType OBJECT-TYPE
   SYNTAX     StorageType 
   ACCESS     read-only
   STATUS     mandatory
   DESCRIPTION
     "This variable represents the storage type value for the
      atmIfUniAddrTermSP tables."
::= { atmIfUniAddrTermSPRowStatusEntry 4 }

atmIfUniAddrTermSPIndex OBJECT-TYPE
   SYNTAX     NonReplicated 
   ACCESS     not-accessible
   STATUS     mandatory
   DESCRIPTION
     "This variable represents the index for the atmIfUniAddrTermSP tables."
::= { atmIfUniAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

atmIfUniAddrPnniInfo OBJECT IDENTIFIER ::= { atmIfUniAddr 3 }



atmIfUniAddrPnniInfoRowStatusTable OBJECT-TYPE
   SYNTAX     SEQUENCE OF AtmIfUniAddrPnniInfoRowStatusEntry
   ACCESS     not-accessible
   STATUS     mandatory
   DESCRIPTION
     "This entry controls the addition and deletion of 
      atmIfUniAddrPnniInfo components."
::= { atmIfUniAddrPnniInfo 1 }

atmIfUniAddrPnniInfoRowStatusEntry OBJECT-TYPE
   SYNTAX     AtmIfUniAddrPnniInfoRowStatusEntry
   ACCESS     not-accessible
   STATUS     mandatory
   DESCRIPTION
     "A single entry in the table represents a single 
      atmIfUniAddrPnniInfo component."
   INDEX {
      atmIfIndex,
      atmIfUniIndex,
      atmIfUniAddrAddressIndex,
      atmIfUniAddrAddressTypeIndex,
      atmIfUniAddrPnniInfoIndex }
::= { atmIfUniAddrPnniInfoRowStatusTable 1 }

AtmIfUniAddrPnniInfoRowStatusEntry ::= SEQUENCE {
   atmIfUniAddrPnniInfoRowStatus
      RowStatus,
   atmIfUniAddrPnniInfoComponentName
      DisplayString,
   atmIfUniAddrPnniInfoStorageType
      StorageType,
   atmIfUniAddrPnniInfoIndex
      NonReplicated }

atmIfUniAddrPnniInfoRowStatus OBJECT-TYPE
   SYNTAX     RowStatus 
   ACCESS     read-write
   STATUS     mandatory
   DESCRIPTION
     "This variable is used as the basis for SNMP naming of
      atmIfUniAddrPnniInfo components.
      These components can be added and deleted."
::= { atmIfUniAddrPnniInfoRowStatusEntry 1 }

atmIfUniAddrPnniInfoComponentName OBJECT-TYPE
   SYNTAX     DisplayString 
   ACCESS     read-only
   STATUS     mandatory
   DESCRIPTION
     "This variable provides the component's string name for
      use with the ASCII Console Interface"
::= { atmIfUniAddrPnniInfoRowStatusEntry 2 }

atmIfUniAddrPnniInfoStorageType OBJECT-TYPE
   SYNTAX     StorageType 
   ACCESS     read-only
   STATUS     mandatory
   DESCRIPTION
     "This variable represents the storage type value for the
      atmIfUniAddrPnniInfo tables."
::= { atmIfUniAddrPnniInfoRowStatusEntry 4 }

atmIfUniAddrPnniInfoIndex OBJECT-TYPE
   SYNTAX     NonReplicated 
   ACCESS     not-accessible
   STATUS     mandatory
   DESCRIPTION
     "This variable represents the index for the atmIfUniAddrPnniInfo tables."
::= { atmIfUniAddrPnniInfoRowStatusEntry 10 }

atmIfUniAddrPnniInfoProvTable OBJECT-TYPE
   SYNTAX     SEQUENCE OF AtmIfUniAddrPnniInfoProvEntry
   ACCESS     not-accessible
   STATUS     mandatory
   DESCRIPTION
     "This attribute group contains the provisioned attributes relating to 
      PNNI for a PnniInfo component."
::= { atmIfUniAddrPnniInfo 10 }

atmIfUniAddrPnniInfoProvEntry OBJECT-TYPE
   SYNTAX     AtmIfUniAddrPnniInfoProvEntry
   ACCESS     not-accessible
   STATUS     mandatory
   DESCRIPTION
     "An entry in the atmIfUniAddrPnniInfoProvTable."
   INDEX {
      atmIfIndex,
      atmIfUniIndex,
      atmIfUniAddrAddressIndex,
      atmIfUniAddrAddressTypeIndex,
      atmIfUniAddrPnniInfoIndex }
::= { atmIfUniAddrPnniInfoProvTable 1 }

AtmIfUniAddrPnniInfoProvEntry ::= SEQUENCE {
   atmIfUniAddrPnniInfoScope
      INTEGER,
   atmIfUniAddrPnniInfoReachability
      INTEGER }

atmIfUniAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { atmIfUniAddrPnniInfoProvEntry 1 }

atmIfUniAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { atmIfUniAddrPnniInfoProvEntry 2 }


-- AtmIf/n VirtualPathTerminator/m Uni
-- This component represents a virtual ATM UNI interface. If this 
-- component is provisioned, neither an Iisp component, nor a Pnni 
-- component can be provisioned under the same Vpt component. If 
-- this component is deleted, then all associated Vcc components are 
-- deleted.

atmIfVptUni OBJECT IDENTIFIER ::= { atmIfVpt 8 }



atmIfVptUniRowStatusTable OBJECT-TYPE
   SYNTAX     SEQUENCE OF AtmIfVptUniRowStatusEntry
   ACCESS     not-accessible
   STATUS     mandatory
   DESCRIPTION
     "This entry controls the addition and deletion of 
      atmIfVptUni components."
::= { atmIfVptUni 1 }

atmIfVptUniRowStatusEntry OBJECT-TYPE
   SYNTAX     AtmIfVptUniRowStatusEntry
   ACCESS     not-accessible
   STATUS     mandatory
   DESCRIPTION
     "A single entry in the table represents a single 
      atmIfVptUni component."
   INDEX {
      atmIfIndex,
      atmIfVptIndex,
      atmIfVptUniIndex }
::= { atmIfVptUniRowStatusTable 1 }

AtmIfVptUniRowStatusEntry ::= SEQUENCE {
   atmIfVptUniRowStatus
      RowStatus,
   atmIfVptUniComponentName
      DisplayString,
   atmIfVptUniStorageType
      StorageType,
   atmIfVptUniIndex
      NonReplicated }

atmIfVptUniRowStatus OBJECT-TYPE
   SYNTAX     RowStatus 
   ACCESS     read-write
   STATUS     mandatory
   DESCRIPTION
     "This variable is used as the basis for SNMP naming of
      atmIfVptUni components.
      These components can be added and deleted."
::= { atmIfVptUniRowStatusEntry 1 }

atmIfVptUniComponentName OBJECT-TYPE
   SYNTAX     DisplayString 
   ACCESS     read-only
   STATUS     mandatory
   DESCRIPTION
     "This variable provides the component's string name for
      use with the ASCII Console Interface"
::= { atmIfVptUniRowStatusEntry 2 }

atmIfVptUniStorageType OBJECT-TYPE
   SYNTAX     StorageType 
   ACCESS     read-only
   STATUS     mandatory
   DESCRIPTION
     "This variable represents the storage type value for the
      atmIfVptUni tables."
::= { atmIfVptUniRowStatusEntry 4 }

atmIfVptUniIndex OBJECT-TYPE
   SYNTAX     NonReplicated 
   ACCESS     not-accessible
   STATUS     mandatory
   DESCRIPTION
     "This variable represents the index for the atmIfVptUni tables."
::= { atmIfVptUniRowStatusEntry 10 }

atmIfVptUniProvTable OBJECT-TYPE
   SYNTAX     SEQUENCE OF AtmIfVptUniProvEntry
   ACCESS     not-accessible
   STATUS     mandatory
   DESCRIPTION
     "This group contains the provisionable attributes for the Uni 
      component."
::= { atmIfVptUni 10 }

atmIfVptUniProvEntry OBJECT-TYPE
   SYNTAX     AtmIfVptUniProvEntry
   ACCESS     not-accessible
   STATUS     mandatory
   DESCRIPTION
     "An entry in the atmIfVptUniProvTable."
   INDEX {
      atmIfIndex,
      atmIfVptIndex,
      atmIfVptUniIndex }
::= { atmIfVptUniProvTable 1 }

AtmIfVptUniProvEntry ::= SEQUENCE {
   atmIfVptUniVersion
      INTEGER,
   atmIfVptUniSide
      INTEGER,
   atmIfVptUniSoftPvcRetryPeriod
      Unsigned32,
   atmIfVptUniSoftPvpAndPvcRetryPeriod
      Unsigned32,
   atmIfVptUniSoftPvpAndPvcHoldOffTime
      Unsigned32 }

atmIfVptUniVersion OBJECT-TYPE
   SYNTAX     INTEGER  {
                 atmForum30(0),
                 atmForum31(1) }
   ACCESS     read-write
   STATUS     mandatory
   DESCRIPTION
     "This attribute specifies which specification the UNI complies with. 
      The options are ATM FORUM 3.0 or ATM FORUM 3.1. If this 
      attribute is changed then all switched Vcc components in this 
      interface are cleared due to the fact that the two versions are 
      incompatible."
   DEFVAL     { atmForum31 }
::= { atmIfVptUniProvEntry 1 }

atmIfVptUniSide OBJECT-TYPE
   SYNTAX     INTEGER  {
                 network(0),
                 user(1) }
   ACCESS     read-write
   STATUS     mandatory
   DESCRIPTION
     "This attribute indicates which side the interface is, user or network."
   DEFVAL     { network }
::= { atmIfVptUniProvEntry 2 }

atmIfVptUniSoftPvcRetryPeriod OBJECT-TYPE
   SYNTAX     Unsigned32 (20..999999)
   ACCESS     read-write
   STATUS     obsolete
   DESCRIPTION
     "This attribute represents the time in seconds to wait between call set 
      up retries. The resolution is to the nearest 10 seconds. 
      This attribute has been obsoleted and is replaced by the 
      softPvpAndPvcRetryPeriod attribute."
   DEFVAL     { 60 }
::= { atmIfVptUniProvEntry 3 }

atmIfVptUniSoftPvpAndPvcRetryPeriod OBJECT-TYPE
   SYNTAX     Unsigned32 (20..999999)
   ACCESS     read-write
   STATUS     mandatory
   DESCRIPTION
     "This attribute represents the time in seconds to wait between soft 
      PVP or soft PVC call setup retries. The resolution is to the nearest 
      10 seconds."
   DEFVAL     { 60 }
::= { atmIfVptUniProvEntry 4 }

atmIfVptUniSoftPvpAndPvcHoldOffTime OBJECT-TYPE
   SYNTAX     Unsigned32 (0 | 50..20000)
   ACCESS     read-write
   STATUS     mandatory
   DESCRIPTION
     "This attribute specifies how long to hold off retries following a 
      release or the connection. The resolution is to the nearest 50 ms."
   DEFVAL     { 0 }
::= { atmIfVptUniProvEntry 5 }

atmIfVptUniAcctOptTable OBJECT-TYPE
   SYNTAX     SEQUENCE OF AtmIfVptUniAcctOptEntry
   ACCESS     not-accessible
   STATUS     mandatory
   DESCRIPTION
     "This group contains the provisionable attributes for accounting."
::= { atmIfVptUni 11 }

atmIfVptUniAcctOptEntry OBJECT-TYPE
   SYNTAX     AtmIfVptUniAcctOptEntry
   ACCESS     not-accessible
   STATUS     mandatory
   DESCRIPTION
     "An entry in the atmIfVptUniAcctOptTable."
   INDEX {
      atmIfIndex,
      atmIfVptIndex,
      atmIfVptUniIndex }
::= { atmIfVptUniAcctOptTable 1 }

AtmIfVptUniAcctOptEntry ::= SEQUENCE {
   atmIfVptUniAccountCollection
      OCTET STRING,
   atmIfVptUniAccountConnectionType
      INTEGER,
   atmIfVptUniAccountClass
      Unsigned32,
   atmIfVptUniServiceExchange
      Unsigned32 }

atmIfVptUniAccountCollection OBJECT-TYPE
   SYNTAX     OCTET STRING (SIZE (1))
   ACCESS     read-write
   STATUS     mandatory
   DESCRIPTION
     "This attribute is used to turn accounting on or off for SVC and 
      SPVC connections. It also specifies the reason(s) for which 
      accounting data is collected: billing, test, study, audit or force. 
      
      If the set of reasons is not empty then accounting records will be 
      generated by this interface in the following situations:
      - on a TODA changeover if TODA is enabled;
      - every 12 hours (per connection) if TODA is disabled;
      - on every call clear (a call record with final cell counts).
      
      If none of the reasons is present, then accounting will be 
      suppressed.
      
      The reason for collection is recorded in the accounting record, in 
      the attribute callingCollectReason or calledCollectReason as 
      appropriate.

      Description of bits:
      bill(0)
      test(1)
      study(2)
      audit(3)
      force(4)"
::= { atmIfVptUniAcctOptEntry 1 }

atmIfVptUniAccountConnectionType OBJECT-TYPE
   SYNTAX     INTEGER  {
                 origTerm(0),
                 intermediate(1) }
   ACCESS     read-write
   STATUS     mandatory
   DESCRIPTION
     "This attribute specifies whether accounting records generated by 
      this interface should be marked as originating, terminating or 
      intermediate. This attribute, in combination with the direction of the 
      call, determines the value of attribute connPointType of the 
      accounting record and may be used by downstream accounting 
      processes to correlate the records.
      
      If the value is origTerm then records generated for incoming calls 
      will be marked as originating and records generated for outgoing 
      calls will be marked as terminating.
      
      If the value is intermediate then records generated for all calls will 
      be marked as intermediate."
   DEFVAL     { origTerm }
::= { atmIfVptUniAcctOptEntry 2 }

atmIfVptUniAccountClass OBJECT-TYPE
   SYNTAX     Unsigned32 (0..255)
   ACCESS     read-write
   STATUS     mandatory
   DESCRIPTION
     "This attribute specifies the accounting class associated with the 
      interface. Its meaning is determined by the network operator.
      
      Its value is simply recorded in the accounting records generated by 
      this interface, in the attribute callingServiceType or 
      calledServiceType as appropriate."
   DEFVAL     { 0 }
::= { atmIfVptUniAcctOptEntry 3 }

atmIfVptUniServiceExchange OBJECT-TYPE
   SYNTAX     Unsigned32 (0..255)
   ACCESS     read-write
   STATUS     mandatory
   DESCRIPTION
     "This attribute specifies the data service exchange associated with 
      this interface. Its meaning is determined by the network operator.
      
      Its value is simply recorded in the accounting records generated by 
      this interface, in the attribute callingDse or calledDse as 
      appropriate."
   DEFVAL     { 0 }
::= { atmIfVptUniAcctOptEntry 4 }

atmIfVptUniVProvTable OBJECT-TYPE
   SYNTAX     SEQUENCE OF AtmIfVptUniVProvEntry
   ACCESS     not-accessible
   STATUS     mandatory
   DESCRIPTION
     "This group contains the provisionable attributes for the Uni 
      component which are specific to virtual UNI interfaces."
::= { atmIfVptUni 12 }

atmIfVptUniVProvEntry OBJECT-TYPE
   SYNTAX     AtmIfVptUniVProvEntry
   ACCESS     not-accessible
   STATUS     mandatory
   DESCRIPTION
     "An entry in the atmIfVptUniVProvTable."
   INDEX {
      atmIfIndex,
      atmIfVptIndex,
      atmIfVptUniIndex }
::= { atmIfVptUniVProvTable 1 }

AtmIfVptUniVProvEntry ::= SEQUENCE {
   atmIfVptUniVpci
      Unsigned32 }

atmIfVptUniVpci OBJECT-TYPE
   SYNTAX     Unsigned32 (0..255)
   ACCESS     read-write
   STATUS     mandatory
   DESCRIPTION
     "This attribute specifies the Virtual Path Connection Identifier 
      (VPCI) to be used between this signalling entity and its peer. The 
      VPCI of the peer virtual UNI must have the same value for 
      switched connections to be set up across the interface."
   DEFVAL     { 0 }
::= { atmIfVptUniVProvEntry 1 }


-- AtmIf/n Iisp Signalling
-- AtmIf/n Uni Signalling
-- AtmIf/n Pnni Signalling
-- AtmIf/n Vpt/m Iisp Signalling
-- AtmIf/n Vpt/m Uni Signalling
-- AtmIf/n Vpt/m Pnni Signalling
-- 
-- This component represents the signalling entities for the interface.

atmIfVptUniSig OBJECT IDENTIFIER ::= { atmIfVptUni 2 }



atmIfVptUniSigRowStatusTable OBJECT-TYPE
   SYNTAX     SEQUENCE OF AtmIfVptUniSigRowStatusEntry
   ACCESS     not-accessible
   STATUS     mandatory
   DESCRIPTION
     "This entry controls the addition and deletion of 
      atmIfVptUniSig components."
::= { atmIfVptUniSig 1 }

atmIfVptUniSigRowStatusEntry OBJECT-TYPE
   SYNTAX     AtmIfVptUniSigRowStatusEntry
   ACCESS     not-accessible
   STATUS     mandatory
   DESCRIPTION
     "A single entry in the table represents a single 
      atmIfVptUniSig component."
   INDEX {
      atmIfIndex,
      atmIfVptIndex,
      atmIfVptUniIndex,
      atmIfVptUniSigIndex }
::= { atmIfVptUniSigRowStatusTable 1 }

AtmIfVptUniSigRowStatusEntry ::= SEQUENCE {
   atmIfVptUniSigRowStatus
      RowStatus,
   atmIfVptUniSigComponentName
      DisplayString,
   atmIfVptUniSigStorageType
      StorageType,
   atmIfVptUniSigIndex
      NonReplicated }

atmIfVptUniSigRowStatus OBJECT-TYPE
   SYNTAX     RowStatus 
   ACCESS     read-only
   STATUS     mandatory
   DESCRIPTION
     "This variable is used as the basis for SNMP naming of
      atmIfVptUniSig components.
      These components cannot be added nor deleted."
::= { atmIfVptUniSigRowStatusEntry 1 }

atmIfVptUniSigComponentName OBJECT-TYPE
   SYNTAX     DisplayString 
   ACCESS     read-only
   STATUS     mandatory
   DESCRIPTION
     "This variable provides the component's string name for
      use with the ASCII Console Interface"
::= { atmIfVptUniSigRowStatusEntry 2 }

atmIfVptUniSigStorageType OBJECT-TYPE
   SYNTAX     StorageType 
   ACCESS     read-only
   STATUS     mandatory
   DESCRIPTION
     "This variable represents the storage type value for the
      atmIfVptUniSig tables."
::= { atmIfVptUniSigRowStatusEntry 4 }

atmIfVptUniSigIndex OBJECT-TYPE
   SYNTAX     NonReplicated 
   ACCESS     not-accessible
   STATUS     mandatory
   DESCRIPTION
     "This variable represents the index for the atmIfVptUniSig tables."
::= { atmIfVptUniSigRowStatusEntry 10 }

atmIfVptUniSigProvTable OBJECT-TYPE
   SYNTAX     SEQUENCE OF AtmIfVptUniSigProvEntry
   ACCESS     not-accessible
   STATUS     mandatory
   DESCRIPTION
     "This attribute group contains the provisionable attributes for the 
      Signalling component."
::= { atmIfVptUniSig 10 }

atmIfVptUniSigProvEntry OBJECT-TYPE
   SYNTAX     AtmIfVptUniSigProvEntry
   ACCESS     not-accessible
   STATUS     mandatory
   DESCRIPTION
     "An entry in the atmIfVptUniSigProvTable."
   INDEX {
      atmIfIndex,
      atmIfVptIndex,
      atmIfVptUniIndex,
      atmIfVptUniSigIndex }
::= { atmIfVptUniSigProvTable 1 }

AtmIfVptUniSigProvEntry ::= SEQUENCE {
   atmIfVptUniSigVci
      Unsigned32,
   atmIfVptUniSigAddressConversion
      INTEGER }

atmIfVptUniSigVci OBJECT-TYPE
   SYNTAX     Unsigned32 (0..65535)
   ACCESS     read-write
   STATUS     mandatory
   DESCRIPTION
     "This attribute specifies the signalling channel number."
   DEFVAL     { 5 }
::= { atmIfVptUniSigProvEntry 1 }

atmIfVptUniSigAddressConversion OBJECT-TYPE
   SYNTAX     INTEGER  {
                 none(0),
                 nativeE164(1),
                 nsap(2) }
   ACCESS     read-write
   STATUS     mandatory
   DESCRIPTION
     "This attribute specifies the address conversion on the outgoing 
      signalling PDUs. The options are none, nativeE164, or nsap. The 
      none option is the default and if this option is chosen then nothing 
      is done to the address information element (IE) in the outgoing 
      signalling message. If nativeE164 option is chosen, then only 
      NSAP encapsulated E.164 addresses with zeros in the ESI are 
      converted to native E.164 format in the outgoing signalling 
      message. If the NSAP address is not encapsulated E.164 or the ESI 
      field is not zeros and the nativeE164 option is chosen, then the call 
      is cleared. If the nsap option is chosen, then native E.164 addresses 
      are converted to NSAP E.164 with zeros in the ESI field; otherwise 
      the address is in NSAP format and is not changed."
   DEFVAL     { none }
::= { atmIfVptUniSigProvEntry 2 }

atmIfVptUniSigStateTable OBJECT-TYPE
   SYNTAX     SEQUENCE OF AtmIfVptUniSigStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfVptUniSig 11 }

atmIfVptUniSigStateEntry OBJECT-TYPE
   SYNTAX     AtmIfVptUniSigStateEntry
   ACCESS     not-accessible
   STATUS     mandatory
   DESCRIPTION
     "An entry in the atmIfVptUniSigStateTable."
   INDEX {
      atmIfIndex,
      atmIfVptIndex,
      atmIfVptUniIndex,
      atmIfVptUniSigIndex }
::= { atmIfVptUniSigStateTable 1 }

AtmIfVptUniSigStateEntry ::= SEQUENCE {
   atmIfVptUniSigAdminState
      INTEGER,
   atmIfVptUniSigOperationalState
      INTEGER,
   atmIfVptUniSigUsageState
      INTEGER }

atmIfVptUniSigAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfVptUniSigStateEntry 1 }

atmIfVptUniSigOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfVptUniSigStateEntry 2 }

atmIfVptUniSigUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfVptUniSigStateEntry 3 }

atmIfVptUniSigOperTable OBJECT-TYPE
   SYNTAX     SEQUENCE OF AtmIfVptUniSigOperEntry
   ACCESS     not-accessible
   STATUS     mandatory
   DESCRIPTION
     "This attribute contains the operational attributes for the 
      AtmSignalling component."
::= { atmIfVptUniSig 12 }

atmIfVptUniSigOperEntry OBJECT-TYPE
   SYNTAX     AtmIfVptUniSigOperEntry
   ACCESS     not-accessible
   STATUS     mandatory
   DESCRIPTION
     "An entry in the atmIfVptUniSigOperTable."
   INDEX {
      atmIfIndex,
      atmIfVptIndex,
      atmIfVptUniIndex,
      atmIfVptUniSigIndex }
::= { atmIfVptUniSigOperTable 1 }

AtmIfVptUniSigOperEntry ::= SEQUENCE {
   atmIfVptUniSigLastTxCauseCode
      Unsigned32,
   atmIfVptUniSigLastTxDiagCode
      Hex,
   atmIfVptUniSigLastRxCauseCode
      Unsigned32,
   atmIfVptUniSigLastRxDiagCode
      Hex }

atmIfVptUniSigLastTxCauseCode OBJECT-TYPE
   SYNTAX     Unsigned32 (0..255)
   ACCESS     read-only
   STATUS     mandatory
   DESCRIPTION
     "This attribute indicates the cause code in the last transmitted 
      signalling message that contains the CAUSE information element. 
      The cause code is used to describe the reason for generating certain 
      signalling messages."
::= { atmIfVptUniSigOperEntry 1 }

atmIfVptUniSigLastTxDiagCode OBJECT-TYPE
   SYNTAX     Hex (0..255)
   ACCESS     read-only
   STATUS     mandatory
   DESCRIPTION
     "This attribute contains the diagnostic code in the last transmitted 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfVptUniSigOperEntry 2 }

atmIfVptUniSigLastRxCauseCode OBJECT-TYPE
   SYNTAX     Unsigned32 (0..255)
   ACCESS     read-only
   STATUS     mandatory
   DESCRIPTION
     "This attribute contains the cause code in the last received signalling 
      message that contains the CAUSE information element. The cause 
      code is used to describe the reason for generating certain signalling 
      messages."
::= { atmIfVptUniSigOperEntry 3 }

atmIfVptUniSigLastRxDiagCode OBJECT-TYPE
   SYNTAX     Hex (0..255)
   ACCESS     read-only
   STATUS     mandatory
   DESCRIPTION
     "This attribute contains the diagnostic code in the last received 
      signalling message. The diagnostic code is contained in the CAUSE 
      information element and identifies an information element type or 
      timer type. The diagnostic code is present only if a procedural error 
      is detected by the signalling protocol. A diagnostic code is always 
      accompanied by the cause code. If there is no failure, this attribute 
      is set to 0."
::= { atmIfVptUniSigOperEntry 4 }

atmIfVptUniSigStatsTable OBJECT-TYPE
   SYNTAX     SEQUENCE OF AtmIfVptUniSigStatsEntry
   ACCESS     not-accessible
   STATUS     mandatory
   DESCRIPTION
     "This attribute group contains the statistics associated with the 
      AtmSignalling component."
::= { atmIfVptUniSig 13 }

atmIfVptUniSigStatsEntry OBJECT-TYPE
   SYNTAX     AtmIfVptUniSigStatsEntry
   ACCESS     not-accessible
   STATUS     mandatory
   DESCRIPTION
     "An entry in the atmIfVptUniSigStatsTable."
   INDEX {
      atmIfIndex,
      atmIfVptIndex,
      atmIfVptUniIndex,
      atmIfVptUniSigIndex }
::= { atmIfVptUniSigStatsTable 1 }

AtmIfVptUniSigStatsEntry ::= SEQUENCE {
   atmIfVptUniSigCurrentConnections
      Counter32,
   atmIfVptUniSigPeakConnections
      Gauge32,
   atmIfVptUniSigSuccessfulConnections
      Counter32,
   atmIfVptUniSigFailedConnections
      Counter32,
   atmIfVptUniSigTxPdus
      Counter32,
   atmIfVptUniSigRxPdus
      Counter32,
   atmIfVptUniSigCurrentPmpConnections
      Gauge32,
   atmIfVptUniSigPeakPmpConnections
      Gauge32,
   atmIfVptUniSigSuccessfulPmpConnections
      Counter32,
   atmIfVptUniSigFailedPmpConnections
      Counter32,
   atmIfVptUniSigNewCurrentConnections
      Gauge32 }

atmIfVptUniSigCurrentConnections OBJECT-TYPE
   SYNTAX     Counter32 
   ACCESS     read-only
   STATUS     obsolete
   DESCRIPTION
     "This attribute indicates the total number of currently active 
      connections."
::= { atmIfVptUniSigStatsEntry 1 }

atmIfVptUniSigPeakConnections OBJECT-TYPE
   SYNTAX     Gauge32 (0..4294967295)
   ACCESS     read-only
   STATUS     mandatory
   DESCRIPTION
     "This attribute indicates the high water mark of active point-to-
      point and point-to-multipoint connections."
::= { atmIfVptUniSigStatsEntry 2 }

atmIfVptUniSigSuccessfulConnections OBJECT-TYPE
   SYNTAX     Counter32 
   ACCESS     read-only
   STATUS     mandatory
   DESCRIPTION
     "This attribute counts the total number of switched point-to-
      point and point-to-multipoint connections that were successfully 
      established. The counter wraps to 0 when the maximum value is 
      exceeded."
::= { atmIfVptUniSigStatsEntry 3 }

atmIfVptUniSigFailedConnections OBJECT-TYPE
   SYNTAX     Counter32 
   ACCESS     read-only
   STATUS     mandatory
   DESCRIPTION
     "This attribute counts the total number of switched connections that 
      were not successfully established.The counter wraps to 0 when the 
      maximum value is exceeded."
::= { atmIfVptUniSigStatsEntry 4 }

atmIfVptUniSigTxPdus OBJECT-TYPE
   SYNTAX     Counter32 
   ACCESS     read-only
   STATUS     mandatory
   DESCRIPTION
     "This attribute counts the number of transmitted signalling 
      PDUs.The counter wraps to 0 when the maximum value is 
      exceeded."
::= { atmIfVptUniSigStatsEntry 5 }

atmIfVptUniSigRxPdus OBJECT-TYPE
   SYNTAX     Counter32 
   ACCESS     read-only
   STATUS     mandatory
   DESCRIPTION
     "This attribute counts the number of received signalling PDUs.The 
      counter wraps to 0 when the maximum value is exceeded."
::= { atmIfVptUniSigStatsEntry 6 }

atmIfVptUniSigCurrentPmpConnections OBJECT-TYPE
   SYNTAX     Gauge32 (0..4294967295)
   ACCESS     read-only
   STATUS     mandatory
   DESCRIPTION
     "This attribute indicates the number of currently active point-to-
      multipoint connections."
::= { atmIfVptUniSigStatsEntry 7 }

atmIfVptUniSigPeakPmpConnections OBJECT-TYPE
   SYNTAX     Gauge32 (0..4294967295)
   ACCESS     read-only
   STATUS     mandatory
   DESCRIPTION
     "This attribute indicates the high water mark of active point-to-
      multipoint connections."
::= { atmIfVptUniSigStatsEntry 8 }

atmIfVptUniSigSuccessfulPmpConnections OBJECT-TYPE
   SYNTAX     Counter32 
   ACCESS     read-only
   STATUS     mandatory
   DESCRIPTION
     "This attribute counts the total number of switched point-to-
      multipoint connections that were successfully established. 
      The counter wraps to 0 when the maximum value is 
      exceeded."
::= { atmIfVptUniSigStatsEntry 9 }

atmIfVptUniSigFailedPmpConnections OBJECT-TYPE
   SYNTAX     Counter32 
   ACCESS     read-only
   STATUS     mandatory
   DESCRIPTION
     "This attribute counts the number of switched point-to-
      multipoint connections that were not successfully 
      established.The counter wraps to 0 when the maximum value 
      is exceeded."
::= { atmIfVptUniSigStatsEntry 10 }

atmIfVptUniSigNewCurrentConnections OBJECT-TYPE
   SYNTAX     Gauge32 (0..4294967295)
   ACCESS     read-only
   STATUS     mandatory
   DESCRIPTION
     "This attribute indicates the total number of currently active point-to-
      point and point-to-multipoint connections."
::= { atmIfVptUniSigStatsEntry 11 }


-- AtmIf/n Uni Sig VirtualChannelDescriptor
-- AtmIf/n Uni Ilmi VirtualChannelDescriptor
-- AtmIf/n Iisp Sig VirtualChannelDescriptor
-- AtmIf/n Pnni Sig VirtualChannelDescriptor
-- AtmIf/n Pnni Rcc VirtualChannelDescriptor
-- AtmIf/n Vpt/m Uni Sig VirtualChannelDescriptor
-- AtmIf/n Vpt/m Iisp Sig VirtualChannelDescriptor
-- AtmIf/n Vpt/m Pnni Sig VirtualChannelDescriptor
-- AtmIf/n Vpt/m Pnni Rcc VirtualChannelDescriptor
-- 
-- This component contains the provisionable traffic parameters for a 
-- control channel (Sig, Ilmi or Rcc component).

atmIfVptUniSigVcd OBJECT IDENTIFIER ::= { atmIfVptUniSig 2 }



atmIfVptUniSigVcdRowStatusTable OBJECT-TYPE
   SYNTAX     SEQUENCE OF AtmIfVptUniSigVcdRowStatusEntry
   ACCESS     not-accessible
   STATUS     mandatory
   DESCRIPTION
     "This entry controls the addition and deletion of 
      atmIfVptUniSigVcd components."
::= { atmIfVptUniSigVcd 1 }

atmIfVptUniSigVcdRowStatusEntry OBJECT-TYPE
   SYNTAX     AtmIfVptUniSigVcdRowStatusEntry
   ACCESS     not-accessible
   STATUS     mandatory
   DESCRIPTION
     "A single entry in the table represents a single 
      atmIfVptUniSigVcd component."
   INDEX {
      atmIfIndex,
      atmIfVptIndex,
      atmIfVptUniIndex,
      atmIfVptUniSigIndex,
      atmIfVptUniSigVcdIndex }
::= { atmIfVptUniSigVcdRowStatusTable 1 }

AtmIfVptUniSigVcdRowStatusEntry ::= SEQUENCE {
   atmIfVptUniSigVcdRowStatus
      RowStatus,
   atmIfVptUniSigVcdComponentName
      DisplayString,
   atmIfVptUniSigVcdStorageType
      StorageType,
   atmIfVptUniSigVcdIndex
      NonReplicated }

atmIfVptUniSigVcdRowStatus OBJECT-TYPE
   SYNTAX     RowStatus 
   ACCESS     read-write
   STATUS     mandatory
   DESCRIPTION
     "This variable is used as the basis for SNMP naming of
      atmIfVptUniSigVcd components.
      These components can be added and deleted."
::= { atmIfVptUniSigVcdRowStatusEntry 1 }

atmIfVptUniSigVcdComponentName OBJECT-TYPE
   SYNTAX     DisplayString 
   ACCESS     read-only
   STATUS     mandatory
   DESCRIPTION
     "This variable provides the component's string name for
      use with the ASCII Console Interface"
::= { atmIfVptUniSigVcdRowStatusEntry 2 }

atmIfVptUniSigVcdStorageType OBJECT-TYPE
   SYNTAX     StorageType 
   ACCESS     read-only
   STATUS     mandatory
   DESCRIPTION
     "This variable represents the storage type value for the
      atmIfVptUniSigVcd tables."
::= { atmIfVptUniSigVcdRowStatusEntry 4 }

atmIfVptUniSigVcdIndex OBJECT-TYPE
   SYNTAX     NonReplicated 
   ACCESS     not-accessible
   STATUS     mandatory
   DESCRIPTION
     "This variable represents the index for the atmIfVptUniSigVcd tables."
::= { atmIfVptUniSigVcdRowStatusEntry 10 }

atmIfVptUniSigVcdProvTable OBJECT-TYPE
   SYNTAX     SEQUENCE OF AtmIfVptUniSigVcdProvEntry
   ACCESS     not-accessible
   STATUS     mandatory
   DESCRIPTION
     "This group contains the provisionable traffic attributes for a control 
      channel."
::= { atmIfVptUniSigVcd 10 }

atmIfVptUniSigVcdProvEntry OBJECT-TYPE
   SYNTAX     AtmIfVptUniSigVcdProvEntry
   ACCESS     not-accessible
   STATUS     mandatory
   DESCRIPTION
     "An entry in the atmIfVptUniSigVcdProvTable."
   INDEX {
      atmIfIndex,
      atmIfVptIndex,
      atmIfVptUniIndex,
      atmIfVptUniSigIndex,
      atmIfVptUniSigVcdIndex }
::= { atmIfVptUniSigVcdProvTable 1 }

AtmIfVptUniSigVcdProvEntry ::= SEQUENCE {
   atmIfVptUniSigVcdTrafficDescType
      INTEGER,
   atmIfVptUniSigVcdAtmServiceCategory
      INTEGER,
   atmIfVptUniSigVcdQosClass
      INTEGER,
   atmIfVptUniSigVcdTrafficShaping
      INTEGER,
   atmIfVptUniSigVcdUnshapedTransmitQueueing
      INTEGER,
   atmIfVptUniSigVcdUsageParameterControl
      INTEGER }

atmIfVptUniSigVcdTrafficDescType OBJECT-TYPE
   SYNTAX     INTEGER  {
                 n3(3),
                 n6(6),
                 n7(7),
                 n8(8) }
   ACCESS     read-write
   STATUS     mandatory
   DESCRIPTION
     "This attribute specifies the type of traffic management which is 
      applied to both the transmit and receive direction of this connection 
      as defined in the ATM Forum. The trafficDescType determines the 
      number and meaning of the parameters in the trafficDescParm 
      attribute."
   DEFVAL     { n6 }
::= { atmIfVptUniSigVcdProvEntry 1 }

atmIfVptUniSigVcdAtmServiceCategory OBJECT-TYPE
   SYNTAX     INTEGER  {
                 unspecifiedBitRate(0),
                 constantBitRate(1),
                 rtVariableBitRate(2),
                 nrtVariableBitRate(3) }
   ACCESS     read-write
   STATUS     mandatory
   DESCRIPTION
     "This attribute specifies the ATM service category for both directions 
      of the connection. 
      
      The constantBitRate service category is intended for real time 
      applications, that is those requiring tightly constrained delay and 
      delay variation, as would be appropriate for voice and video 
      applications. The consistent availability of a fixed quantity of 
      bandwidth is considered appropriate for CBR service. Cells which 
      are delayed beyond the value specified by CellTransfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { rtVariableBitRate }
::= { atmIfVptUniSigVcdProvEntry 3 }

atmIfVptUniSigVcdQosClass OBJECT-TYPE
   SYNTAX     INTEGER  {
                 n0(0),
                 n1(1),
                 n2(2),
                 n3(3),
                 n4(4) }
   ACCESS     read-write
   STATUS     mandatory
   DESCRIPTION
     "This attribute specifies the quality of service for both the forward 
      and backward direction for this connection.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n2 }
::= { atmIfVptUniSigVcdProvEntry 21 }

atmIfVptUniSigVcdTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      When sameAsCa is selected, traffic shaping for this connection is 
      based on the trafficShaping attribute of the connection's service 
      category component under the AtmIf CA. If the service category has 
      traffic shaping enabled, then traffic shaping is enabled for the 
      connection. Note that enabling traffic shaping may have no effect 
      under certain cases. These cases are listed in the description of the 
      trafficShaping operational attribute, which is under the Vcc Tm and 
      Vpc Tm components.
      
      When disabled is selected, traffic shaping for this connection is 
      disabled."
   DEFVAL     { disabled }
::= { atmIfVptUniSigVcdProvEntry 50 }

atmIfVptUniSigVcdUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. Refer to the unshapedTransmitQueueing attribute 
      under the AtmIf CA service category subcomponent for more details 
      on the meaning of this attribute. 
      
      When this attribute is set to sameAsCa, the transmit queueing 
      method for the connection is based on the 
      unshapedTransmitQueueing attribute of the connection's service 
      category component under the ConnectionAdministrator. 
      
      When this attribute is set to common, transmit traffic on this 
      unshaped connection is destined for the common queue. 
      
      The value sameAsInterface is for migration from previous software 
      releases, but should no longer be used"
   DEFVAL     { sameAsCa }
::= { atmIfVptUniSigVcdProvEntry 60 }

atmIfVptUniSigVcdUsageParameterControl OBJECT-TYPE
   SYNTAX     INTEGER  {
                 disabled(1),
                 sameAsCa(2) }
   ACCESS     read-write
   STATUS     mandatory
   DESCRIPTION
     "This attribute specifies whether this connection enforces usage 
      parameter control when receiving traffic from the ATM interface.
      
      When sameAsCa is selected, UPC for the connection is based on 
      the usageParameterControl attribute of the connection's service 
      category component under the ConnectionAdministrator. If the 
      service category has UPC enabled, then UPC is enabled for the 
      connection. Note that enabling UPC may have no effect under 
      certain cases. These cases are listed in the description of the 
      usageParameterControl operational attribute, which is under the 
      Vcc Tm or Vpc Tm component.
      
      When disabled is selected, UPC for this connection is disabled.
      
      The value sameAsInterface is for migration from previous software 
      releases, but should no longer be used"
   DEFVAL     { disabled }
::= { atmIfVptUniSigVcdProvEntry 70 }

atmIfVptUniSigVcdTdpTable OBJECT-TYPE
   SYNTAX     SEQUENCE OF AtmIfVptUniSigVcdTdpEntry
   ACCESS     not-accessible
   STATUS     mandatory
   DESCRIPTION
     "This attribute is a vector of five traffic parameters whose meanings 
      are defined by the trafficDescType attribute. The values of peak cell 
      rate (PCR), sustained cell rate (SCR) and requested shaping rate are 
      expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When trafficDescType is 3, parameter 1 represents the PCR for CLP 
      equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When trafficDescType is 6, parameter 1 represents the PCR for CLP 
      equal to 0 and 1 traffic; parameter 2 represents the SCR for CLP 
      equal to 0 and 1 traffic; parameter 3 represents the MBS for CLP 
      equal to 0 and 1 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 7, parameter 1 represents the PCR for CLP 
      equal to 0 and 1 traffic; parameter 2 represents the SCR for CLP 
      equal to 0 with cell discard; parameter 3 represents the MBS for 
      CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      When trafficDescType is 8, parameter 1 represents the PCR for CLP 
      equal to 0 and 1 traffic; parameter 2 represents the SCR for CLP 
      equal to 0 traffic with cell tagging; parameter 3 represents the MBS 
      for CLP equal to 0 traffic; parameter 4 represents the CDVT; and 
      parameter 5 represents the requested shaping rate. A non-zero value 
      in parameter 5 overrides any value in parameter 1. This result is 
      used as the PCR. Parameters 1, 2, and 3 must be non-zero. 
      Parameter 1 must be greater than or equal to parameter 2. Parameter 
      5 must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For trafficDescType 3 the traffic is shaped at the next rate less than 
      the PCR. 
      
      For trafficDescType 6, 7, and 8, the traffic is shaped at the highest 
      available rate which is between PCR and SCR. However, if there is 
      no available shaping rate between PCR and SCR, traffic is shaped at 
      the next rate above the PCR."
::= { atmIfVptUniSigVcd 387 }

atmIfVptUniSigVcdTdpEntry OBJECT-TYPE
   SYNTAX     AtmIfVptUniSigVcdTdpEntry
   ACCESS     not-accessible
   STATUS     mandatory
   DESCRIPTION
     "An entry in the atmIfVptUniSigVcdTdpTable."
   INDEX {
      atmIfIndex,
      atmIfVptIndex,
      atmIfVptUniIndex,
      atmIfVptUniSigIndex,
      atmIfVptUniSigVcdIndex,
      atmIfVptUniSigVcdTdpIndex }
::= { atmIfVptUniSigVcdTdpTable 1 }

AtmIfVptUniSigVcdTdpEntry ::= SEQUENCE {
   atmIfVptUniSigVcdTdpIndex
      Integer32,
   atmIfVptUniSigVcdTdpValue
      Unsigned32 }

atmIfVptUniSigVcdTdpIndex OBJECT-TYPE
   SYNTAX     Integer32 (1..5)
   ACCESS     not-accessible
   STATUS     mandatory
   DESCRIPTION
     "This variable represents the atmIfVptUniSigVcdTdpTable
      specific index for the atmIfVptUniSigVcdTdpTable."
::= { atmIfVptUniSigVcdTdpEntry 1 }

atmIfVptUniSigVcdTdpValue OBJECT-TYPE
   SYNTAX     Unsigned32 (0..2147483647)
   ACCESS     read-write
   STATUS     mandatory
   DESCRIPTION
     "This variable represents an individual value for the
      atmIfVptUniSigVcdTdpTable."
::= { atmIfVptUniSigVcdTdpEntry 2 }


-- AtmIf/n Iisp Address/address,type
-- AtmIf/n Uni Address/address,type
-- AtmIf/n Pnni Address/address,type
-- AtmIf/n Vpt/m Iisp Address/address,type
-- AtmIf/n Vpt/m Uni Address/address,type
-- AtmIf/n Vpt/m Pnni Address/address,type
-- 
-- This component represents an address (dynamic or static) 
-- associated with the interface. The index is a string of 1 to 40 hex 
-- digits or a single wildcard ('?'), and a type. The type identifies 
-- whether the Address component is for a primary, alternate, 
-- registered, or default address. 
-- 
-- The types primary and alternate are used for provisioned addresses. 
-- The type registered is used for dynamic addresses registered 
-- through ILMI. The type default is used for Soft PVP and Soft PVC 
-- addresses.Virtual interfaces do not have addresses of 
-- type default.
-- 
-- The wildcard is only valid for provisioned addresses. If the address 
-- is a single wildcard, then that indicates that the interface supports 
-- all addresses. If there is no better match, then this interface may be 
-- chosen in the routing. If there is more than one interface with a 
-- single wildcard static address, then the choice is driven through a 
-- round robin algorithm. 
-- 
-- The round robin algorithm tries the primary routes and then the 
-- alternate routes if none of the primary routes succeed.
-- If this node participates in a PNNI hierarchy, then a PnniInfo 
-- subcomponent can be provisioned under the AtmAddress 
-- component to specify the level to which this address will be 
-- advertised.

atmIfVptUniAddr OBJECT IDENTIFIER ::= { atmIfVptUni 3 }



atmIfVptUniAddrRowStatusTable OBJECT-TYPE
   SYNTAX     SEQUENCE OF AtmIfVptUniAddrRowStatusEntry
   ACCESS     not-accessible
   STATUS     mandatory
   DESCRIPTION
     "This entry controls the addition and deletion of 
      atmIfVptUniAddr components."
::= { atmIfVptUniAddr 1 }

atmIfVptUniAddrRowStatusEntry OBJECT-TYPE
   SYNTAX     AtmIfVptUniAddrRowStatusEntry
   ACCESS     not-accessible
   STATUS     mandatory
   DESCRIPTION
     "A single entry in the table represents a single 
      atmIfVptUniAddr component."
   INDEX {
      atmIfIndex,
      atmIfVptIndex,
      atmIfVptUniIndex,
      atmIfVptUniAddrAddressIndex,
      atmIfVptUniAddrAddressTypeIndex }
::= { atmIfVptUniAddrRowStatusTable 1 }

AtmIfVptUniAddrRowStatusEntry ::= SEQUENCE {
   atmIfVptUniAddrRowStatus
      RowStatus,
   atmIfVptUniAddrComponentName
      DisplayString,
   atmIfVptUniAddrStorageType
      StorageType,
   atmIfVptUniAddrAddressIndex
      AsciiStringIndex,
   atmIfVptUniAddrAddressTypeIndex
      INTEGER }

atmIfVptUniAddrRowStatus OBJECT-TYPE
   SYNTAX     RowStatus 
   ACCESS     read-write
   STATUS     mandatory
   DESCRIPTION
     "This variable is used as the basis for SNMP naming of
      atmIfVptUniAddr components.
      These components can be added and deleted."
::= { atmIfVptUniAddrRowStatusEntry 1 }

atmIfVptUniAddrComponentName OBJECT-TYPE
   SYNTAX     DisplayString 
   ACCESS     read-only
   STATUS     mandatory
   DESCRIPTION
     "This variable provides the component's string name for
      use with the ASCII Console Interface"
::= { atmIfVptUniAddrRowStatusEntry 2 }

atmIfVptUniAddrStorageType OBJECT-TYPE
   SYNTAX     StorageType 
   ACCESS     read-only
   STATUS     mandatory
   DESCRIPTION
     "This variable represents the storage type value for the
      atmIfVptUniAddr tables."
::= { atmIfVptUniAddrRowStatusEntry 4 }

atmIfVptUniAddrAddressIndex OBJECT-TYPE
   SYNTAX     AsciiStringIndex (SIZE (1..40))
   ACCESS     not-accessible
   STATUS     mandatory
   DESCRIPTION
     "This variable represents an index for the atmIfVptUniAddr tables."
::= { atmIfVptUniAddrRowStatusEntry 10 }

atmIfVptUniAddrAddressTypeIndex OBJECT-TYPE
   SYNTAX     INTEGER  {
                 primary(0),
                 alternate(1),
                 registered(2),
                 default(3) }
   ACCESS     not-accessible
   STATUS     mandatory
   DESCRIPTION
     "This variable represents an index for the atmIfVptUniAddr tables."
::= { atmIfVptUniAddrRowStatusEntry 11 }

atmIfVptUniAddrOperTable OBJECT-TYPE
   SYNTAX     SEQUENCE OF AtmIfVptUniAddrOperEntry
   ACCESS     not-accessible
   STATUS     mandatory
   DESCRIPTION
     "This attribute group contains the operational attributes for the 
      Address component."
::= { atmIfVptUniAddr 10 }

atmIfVptUniAddrOperEntry OBJECT-TYPE
   SYNTAX     AtmIfVptUniAddrOperEntry
   ACCESS     not-accessible
   STATUS     mandatory
   DESCRIPTION
     "An entry in the atmIfVptUniAddrOperTable."
   INDEX {
      atmIfIndex,
      atmIfVptIndex,
      atmIfVptUniIndex,
      atmIfVptUniAddrAddressIndex,
      atmIfVptUniAddrAddressTypeIndex }
::= { atmIfVptUniAddrOperTable 1 }

AtmIfVptUniAddrOperEntry ::= SEQUENCE {
   atmIfVptUniAddrScope
      INTEGER,
   atmIfVptUniAddrReachability
      INTEGER }

atmIfVptUniAddrScope OBJECT-TYPE
   SYNTAX     INTEGER (-1..104)
   ACCESS     read-only
   STATUS     mandatory
   DESCRIPTION
     "This attribute indicates the scope of the ATM address, which is the 
      highest level to which this address will be advertised in the PNNI 
      hierarchy. If no PnniInfo subcomponent has been provisioned, then 
      the scope will default to the level of this node in the PNNI 
      hierarchy. If this node does not participate in a PNNI hierarchy, then 
      this attribute will have the value of -1."
::= { atmIfVptUniAddrOperEntry 1 }

atmIfVptUniAddrReachability OBJECT-TYPE
   SYNTAX     INTEGER  {
                 internal(0),
                 exterior(1) }
   ACCESS     read-only
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
::= { atmIfVptUniAddrOperEntry 2 }


-- AtmIf/n Iisp Address/address,type TerminateSPvpAndSPvc
-- AtmIf/n Uni Address/address,type TerminateSPvpAndSPvc
-- AtmIf/n Pnni Address/address,type TerminateSPvpAndSPvc
-- AtmIf/n Vpt/m Iisp Address/address,type TerminateSPvpAndSPvc
-- AtmIf/n Vpt/m Uni Address/address,type TerminateSPvpAndSPvc
-- AtmIf/n Vpt/m Pnni Address/address,type TerminateSPvpAndSPvc
-- 
-- The presence of this subcomponent indicates that SPvp and SPvc 
-- call setups terminate at this node if the destination address of the 
-- SPVP or SPVC matches the Address instance.

atmIfVptUniAddrTermSP OBJECT IDENTIFIER ::= { atmIfVptUniAddr 2 }



atmIfVptUniAddrTermSPRowStatusTable OBJECT-TYPE
   SYNTAX     SEQUENCE OF AtmIfVptUniAddrTermSPRowStatusEntry
   ACCESS     not-accessible
   STATUS     mandatory
   DESCRIPTION
     "This entry controls the addition and deletion of 
      atmIfVptUniAddrTermSP components."
::= { atmIfVptUniAddrTermSP 1 }

atmIfVptUniAddrTermSPRowStatusEntry OBJECT-TYPE
   SYNTAX     AtmIfVptUniAddrTermSPRowStatusEntry
   ACCESS     not-accessible
   STATUS     mandatory
   DESCRIPTION
     "A single entry in the table represents a single 
      atmIfVptUniAddrTermSP component."
   INDEX {
      atmIfIndex,
      atmIfVptIndex,
      atmIfVptUniIndex,
      atmIfVptUniAddrAddressIndex,
      atmIfVptUniAddrAddressTypeIndex,
      atmIfVptUniAddrTermSPIndex }
::= { atmIfVptUniAddrTermSPRowStatusTable 1 }

AtmIfVptUniAddrTermSPRowStatusEntry ::= SEQUENCE {
   atmIfVptUniAddrTermSPRowStatus
      RowStatus,
   atmIfVptUniAddrTermSPComponentName
      DisplayString,
   atmIfVptUniAddrTermSPStorageType
      StorageType,
   atmIfVptUniAddrTermSPIndex
      NonReplicated }

atmIfVptUniAddrTermSPRowStatus OBJECT-TYPE
   SYNTAX     RowStatus 
   ACCESS     read-write
   STATUS     mandatory
   DESCRIPTION
     "This variable is used as the basis for SNMP naming of
      atmIfVptUniAddrTermSP components.
      These components can be added and deleted."
::= { atmIfVptUniAddrTermSPRowStatusEntry 1 }

atmIfVptUniAddrTermSPComponentName OBJECT-TYPE
   SYNTAX     DisplayString 
   ACCESS     read-only
   STATUS     mandatory
   DESCRIPTION
     "This variable provides the component's string name for
      use with the ASCII Console Interface"
::= { atmIfVptUniAddrTermSPRowStatusEntry 2 }

atmIfVptUniAddrTermSPStorageType OBJECT-TYPE
   SYNTAX     StorageType 
   ACCESS     read-only
   STATUS     mandatory
   DESCRIPTION
     "This variable represents the storage type value for the
      atmIfVptUniAddrTermSP tables."
::= { atmIfVptUniAddrTermSPRowStatusEntry 4 }

atmIfVptUniAddrTermSPIndex OBJECT-TYPE
   SYNTAX     NonReplicated 
   ACCESS     not-accessible
   STATUS     mandatory
   DESCRIPTION
     "This variable represents the index for the atmIfVptUniAddrTermSP tables."
::= { atmIfVptUniAddrTermSPRowStatusEntry 10 }


-- AtmIf/n Iisp Addr/address,type PnniInfo
-- AtmIf/n Uni Addr/address,type PnniInfo
-- AtmIf/n Pnni Addr/address,type PnniInfo
-- AtmIf/n Vpt/m Iisp Addr/address,type PnniInfo
-- AtmIf/n Vpt/m Uni Addr/address,type PnniInfo
-- AtmIf/n Vpt/m Pnni Addr/address,type PnniInfo
-- 
-- This component contains provisioned information associated with 
-- the ATM address related to PNNI. This component appears only 
-- under provisioned Address components.

atmIfVptUniAddrPnniInfo OBJECT IDENTIFIER ::= { atmIfVptUniAddr 3 }



atmIfVptUniAddrPnniInfoRowStatusTable OBJECT-TYPE
   SYNTAX     SEQUENCE OF AtmIfVptUniAddrPnniInfoRowStatusEntry
   ACCESS     not-accessible
   STATUS     mandatory
   DESCRIPTION
     "This entry controls the addition and deletion of 
      atmIfVptUniAddrPnniInfo components."
::= { atmIfVptUniAddrPnniInfo 1 }

atmIfVptUniAddrPnniInfoRowStatusEntry OBJECT-TYPE
   SYNTAX     AtmIfVptUniAddrPnniInfoRowStatusEntry
   ACCESS     not-accessible
   STATUS     mandatory
   DESCRIPTION
     "A single entry in the table represents a single 
      atmIfVptUniAddrPnniInfo component."
   INDEX {
      atmIfIndex,
      atmIfVptIndex,
      atmIfVptUniIndex,
      atmIfVptUniAddrAddressIndex,
      atmIfVptUniAddrAddressTypeIndex,
      atmIfVptUniAddrPnniInfoIndex }
::= { atmIfVptUniAddrPnniInfoRowStatusTable 1 }

AtmIfVptUniAddrPnniInfoRowStatusEntry ::= SEQUENCE {
   atmIfVptUniAddrPnniInfoRowStatus
      RowStatus,
   atmIfVptUniAddrPnniInfoComponentName
      DisplayString,
   atmIfVptUniAddrPnniInfoStorageType
      StorageType,
   atmIfVptUniAddrPnniInfoIndex
      NonReplicated }

atmIfVptUniAddrPnniInfoRowStatus OBJECT-TYPE
   SYNTAX     RowStatus 
   ACCESS     read-write
   STATUS     mandatory
   DESCRIPTION
     "This variable is used as the basis for SNMP naming of
      atmIfVptUniAddrPnniInfo components.
      These components can be added and deleted."
::= { atmIfVptUniAddrPnniInfoRowStatusEntry 1 }

atmIfVptUniAddrPnniInfoComponentName OBJECT-TYPE
   SYNTAX     DisplayString 
   ACCESS     read-only
   STATUS     mandatory
   DESCRIPTION
     "This variable provides the component's string name for
      use with the ASCII Console Interface"
::= { atmIfVptUniAddrPnniInfoRowStatusEntry 2 }

atmIfVptUniAddrPnniInfoStorageType OBJECT-TYPE
   SYNTAX     StorageType 
   ACCESS     read-only
   STATUS     mandatory
   DESCRIPTION
     "This variable represents the storage type value for the
      atmIfVptUniAddrPnniInfo tables."
::= { atmIfVptUniAddrPnniInfoRowStatusEntry 4 }

atmIfVptUniAddrPnniInfoIndex OBJECT-TYPE
   SYNTAX     NonReplicated 
   ACCESS     not-accessible
   STATUS     mandatory
   DESCRIPTION
     "This variable represents the index for the atmIfVptUniAddrPnniInfo tables."
::= { atmIfVptUniAddrPnniInfoRowStatusEntry 10 }

atmIfVptUniAddrPnniInfoProvTable OBJECT-TYPE
   SYNTAX     SEQUENCE OF AtmIfVptUniAddrPnniInfoProvEntry
   ACCESS     not-accessible
   STATUS     mandatory
   DESCRIPTION
     "This attribute group contains the provisioned attributes relating to 
      PNNI for a PnniInfo component."
::= { atmIfVptUniAddrPnniInfo 10 }

atmIfVptUniAddrPnniInfoProvEntry OBJECT-TYPE
   SYNTAX     AtmIfVptUniAddrPnniInfoProvEntry
   ACCESS     not-accessible
   STATUS     mandatory
   DESCRIPTION
     "An entry in the atmIfVptUniAddrPnniInfoProvTable."
   INDEX {
      atmIfIndex,
      atmIfVptIndex,
      atmIfVptUniIndex,
      atmIfVptUniAddrAddressIndex,
      atmIfVptUniAddrAddressTypeIndex,
      atmIfVptUniAddrPnniInfoIndex }
::= { atmIfVptUniAddrPnniInfoProvTable 1 }

AtmIfVptUniAddrPnniInfoProvEntry ::= SEQUENCE {
   atmIfVptUniAddrPnniInfoScope
      INTEGER,
   atmIfVptUniAddrPnniInfoReachability
      INTEGER }

atmIfVptUniAddrPnniInfoScope OBJECT-TYPE
   SYNTAX     INTEGER (-1..104)
   ACCESS     read-write
   STATUS     mandatory
   DESCRIPTION
     "This attribute specifies the scope of the ATM address, which is the 
      highest level up to which this address will be advertised in the 
      PNNI hierarchy. The scope must be set to a value numerically less 
      than or equal to the level of the lowest level peer group containing 
      this node. Setting the scope to 0 will cause the address to be 
      advertised globally within this PNNI routing domain."
   DEFVAL     { -1 }
::= { atmIfVptUniAddrPnniInfoProvEntry 1 }

atmIfVptUniAddrPnniInfoReachability OBJECT-TYPE
   SYNTAX     INTEGER  {
                 internal(0),
                 exterior(1) }
   ACCESS     read-write
   STATUS     mandatory
   DESCRIPTION
     "This attribute indicates whether the address is internal or exterior. 
      An internal reachable address is an address of a destination that is 
      directly attached to the logical node advertising the address. An 
      exterior reachable address is an address that can be reached 
      through a PNNI routing domain, but which is not located in that 
      PNNI routing domain."
   DEFVAL     { internal }
::= { atmIfVptUniAddrPnniInfoProvEntry 2 }




-- 
-- Version and Compliance statements
-- 



-- Object-Group Statement:
-- A list of all current accessible leaf objects.

-- OBJECTS { atmIfVptUniSigSuccessfulConnections,
--           atmIfVptUniAddrPnniInfoRowStatus,
--           atmIfUniSigFailedConnections,
--           atmIfUniAddrScope,
--           atmIfVptUniSigVcdUsageParameterControl,
--           atmIfUniSigVcdQosClass,
--           atmIfVptUniSoftPvpAndPvcRetryPeriod,
--           atmIfUniSigLastTxDiagCode,
--           atmIfUniSigOperationalState,
--           atmIfVptUniAddrStorageType,
--           atmIfVptUniStorageType,
--           atmIfUniSigCurrentPmpConnections,
--           atmIfUniSigVci,
--           atmIfUniAddrTermSPComponentName,
--           atmIfUniVersion,
--           atmIfUniSigVcdComponentName,
--           atmIfVptUniSigLastTxDiagCode,
--           atmIfVptUniSide,
--           atmIfUniIlmiVci,
--           atmIfUniMacAddress,
--           atmIfVptUniAddrPnniInfoStorageType,
--           atmIfVptUniSigFailedConnections,
--           atmIfUniAddrPnniInfoComponentName,
--           atmIfVptUniSigVcdTrafficDescType,
--           atmIfUniIlmiComponentName,
--           atmIfUniSigRxPdus,
--           atmIfUniAddrPnniInfoReachability,
--           atmIfUniSigLastRxDiagCode,
--           atmIfVptUniRowStatus,
--           atmIfUniSigLastTxCauseCode,
--           atmIfUniIlmiRxPdus,
--           atmIfVptUniSoftPvpAndPvcHoldOffTime,
--           atmIfVptUniAddrTermSPStorageType,
--           atmIfVptUniSigPeakConnections,
--           atmIfUniSigSuccessfulConnections,
--           atmIfVptUniSigVcdAtmServiceCategory,
--           atmIfUniIlmiEsiToRegisterRowStatus,
--           atmIfVptUniSigStorageType,
--           atmIfVptUniSigVcdTrafficShaping,
--           atmIfVptUniServiceExchange,
--           atmIfUniSigNewCurrentConnections,
--           atmIfVptUniAddrReachability,
--           atmIfVptUniSigAdminState,
--           atmIfUniIlmiEsiToRegisterValue,
--           atmIfUniIlmiRxBadPdusDiscarded,
--           atmIfUniSigVcdTdpValue,
--           atmIfVptUniSigVcdTdpValue,
--           atmIfUniAddrComponentName,
--           atmIfUniComponentName,
--           atmIfVptUniSigRowStatus,
--           atmIfUniSigPeakPmpConnections,
--           atmIfUniSigRowStatus,
--           atmIfUniAddrTermSPStorageType,
--           atmIfUniSigVcdStorageType,
--           atmIfUniSigPeakConnections,
--           atmIfVptUniAddrPnniInfoScope,
--           atmIfUniSigTxPdus,
--           atmIfVptUniAddrComponentName,
--           atmIfUniAccountConnectionType,
--           atmIfVptUniSigUsageState,
--           atmIfUniSigFailedPmpConnections,
--           atmIfUniIlmiStorageType,
--           atmIfVptUniSigVcdStorageType,
--           atmIfVptUniSigLastRxCauseCode,
--           atmIfVptUniSigTxPdus,
--           atmIfVptUniAddrScope,
--           atmIfUniAddrPnniInfoStorageType,
--           atmIfUniIlmiTxPdus,
--           atmIfVptUniSigVcdQosClass,
--           atmIfUniSigVcdUnshapedTransmitQueueing,
--           atmIfUniAddrTermSPRowStatus,
--           atmIfUniSigComponentName,
--           atmIfUniSigVcdRowStatus,
--           atmIfVptUniSigCurrentPmpConnections,
--           atmIfUniIlmiAdminState,
--           atmIfUniAccountClass,
--           atmIfVptUniAddrTermSPComponentName,
--           atmIfVptUniSigVcdComponentName,
--           atmIfUniAddrPnniInfoRowStatus,
--           atmIfUniIlmiRowStatus,
--           atmIfVptUniAddrPnniInfoComponentName,
--           atmIfUniSide,
--           atmIfUniAccountCollection,
--           atmIfVptUniSigRxPdus,
--           atmIfVptUniVersion,
--           atmIfUniAddrStorageType,
--           atmIfUniStorageType,
--           atmIfUniIlmiUsageState,
--           atmIfVptUniSigLastRxDiagCode,
--           atmIfVptUniAccountCollection,
--           atmIfVptUniSigLastTxCauseCode,
--           atmIfVptUniSigPeakPmpConnections,
--           atmIfUniSigSuccessfulPmpConnections,
--           atmIfUniIlmiPrefixToRegisterRowStatus,
--           atmIfUniIlmiOperatingMode,
--           atmIfUniAddrReachability,
--           atmIfUniAddrRowStatus,
--           atmIfVptUniAddrPnniInfoReachability,
--           atmIfUniSigVcdTrafficDescType,
--           atmIfUniIlmiOperationalState,
--           atmIfUniIlmiPrefixToRegisterValue,
--           atmIfVptUniAddrRowStatus,
--           atmIfVptUniSigNewCurrentConnections,
--           atmIfUniSigVcdUsageParameterControl,
--           atmIfUniRowStatus,
--           atmIfUniSigVcdTrafficShaping,
--           atmIfUniSigStorageType,
--           atmIfUniSoftPvpAndPvcHoldOffTime,
--           atmIfVptUniSigAddressConversion,
--           atmIfVptUniComponentName,
--           atmIfVptUniAccountClass,
--           atmIfUniSoftPvpAndPvcRetryPeriod,
--           atmIfVptUniVpci,
--           atmIfUniSigVcdAtmServiceCategory,
--           atmIfUniAddrPnniInfoScope,
--           atmIfVptUniSigOperationalState,
--           atmIfUniServiceExchange,
--           atmIfVptUniAccountConnectionType,
--           atmIfUniSigAdminState,
--           atmIfVptUniSigFailedPmpConnections,
--           atmIfVptUniSigVci,
--           atmIfUniSigLastRxCauseCode,
--           atmIfVptUniSigVcdUnshapedTransmitQueueing,
--           atmIfVptUniAddrTermSPRowStatus,
--           atmIfVptUniSigComponentName,
--           atmIfVptUniSigVcdRowStatus,
--           atmIfUniSigAddressConversion,
--           atmIfVptUniSigSuccessfulPmpConnections,
--           atmIfUniSigUsageState }
-- STATUS  mandatory
-- DESCRIPTION
--   "A list of all current accessible leaf objects."

atmUniGroup OBJECT IDENTIFIER ::= { atmUniMIB 1 }
atmUniGroupBE OBJECT IDENTIFIER ::= { atmUniGroup 5 }
atmUniGroupBE00 OBJECT IDENTIFIER ::= { atmUniGroupBE 1 }
atmUniGroupBE00A OBJECT IDENTIFIER ::= { atmUniGroupBE00 2 }



-- Agent-Capabilities Statement:

-- PRODUCT-RELEASE "Passport Release 7.0 AtmUni."
-- STATUS          mandatory
-- DESCRIPTION     "AtmUni MIB: MIB Version BE00A,
--                  Software Version BG00S4C."
-- SUPPORTS        Nortel-Magellan-Passport-AtmUniMIB
--    INCLUDES     { atmUniGroupBE00A }

atmUniCapabilities OBJECT IDENTIFIER ::= { atmUniMIB 3 }
atmUniCapabilitiesBE OBJECT IDENTIFIER ::= { atmUniCapabilities 5 }
atmUniCapabilitiesBE00 OBJECT IDENTIFIER ::= { atmUniCapabilitiesBE 1 }
atmUniCapabilitiesBE00A OBJECT IDENTIFIER ::= { atmUniCapabilitiesBE00 2 }





END
