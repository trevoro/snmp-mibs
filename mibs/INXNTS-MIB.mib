INXNTS-MIB

DEFINITIONS ::= BEGIN
--
-- MIB Definition File for the Racal Interlan INXNTS Terminal Server.
--                          Release 2.0
IMPORTS
		DisplayString FROM SNMPv2-TC
        OBJECT-TYPE, NetworkAddress, IpAddress,
        Counter, Gauge, TimeTicks
                  FROM RFC1155-SMI;


internet   OBJECT IDENTIFIER ::= { iso org(3) dod(6) 1 }
experimental    OBJECT IDENTIFIER ::= { internet 3 }
private         OBJECT IDENTIFIER ::= { internet 4 }

enterprises     OBJECT IDENTIFIER ::= { private 1 }
dot3            OBJECT IDENTIFIER ::= { experimental 3 }

interlan   OBJECT IDENTIFIER ::= { enterprises 28 }
riTelnet   OBJECT IDENTIFIER ::= { interlan 3 }
riTs       OBJECT IDENTIFIER ::= { interlan 4 }
riBoot     OBJECT IDENTIFIER ::= { interlan 16 }
riThresh   OBJECT IDENTIFIER ::= { interlan 17 }
riSystem   OBJECT IDENTIFIER ::= { interlan 18 }
riTsRates  OBJECT IDENTIFIER ::= { interlan 22 }
riInternext OBJECT IDENTIFIER ::= {interlan 21 }
--               nullSpecific OBJECT IDENTIFIER ::= { 0 0 }

riProducts      OBJECT IDENTIFIER ::= { interlan 1 }
riProdNts       OBJECT IDENTIFIER ::= { riProducts 2 }
riProdLdc       OBJECT IDENTIFIER ::= { riProducts 3 }
riLdcNts        OBJECT IDENTIFIER ::= { riProdLdc 4 }

               -- object types

-- ***********************************************************
-- Ethernet interface MIB Group. This is based on an early version of
-- the Internet Draft for this MIB.
-- ************************************************************

dot3Table OBJECT-TYPE
	SYNTAX SEQUENCE OF Dot3Entry
	ACCESS not-accessible
	STATUS mandatory
		--% ALIAS "INX-NTS Interface Table"
	DESCRIPTION "A list of the INX-NTS Ethernet interface`s
operational attributes, such as whether it is configured for multicast
receive and the status of the MAC sublayer.
You cannot access this variable; it is only a table marker in the
MIB."
	::= { dot3 1 }

dot3Entry OBJECT-TYPE
	SYNTAX Dot3Entry
	ACCESS not-accessible
	STATUS mandatory
		--% ALIAS "Interface Table Entry"
	DESCRIPTION 
 		"An entry in the INX-NTS Interface table.  (See the 
previous variable, INX-NTS Interface Table, for an explanation of this table.)
You cannot access this variable; it is only a table marker in the MIB.
The following variables are entries in the table:

	Interface Table Index
	MAC Initialization Status
	MAC Operational Status
	Multicast Receive Status
	Nonaligned Frames Recd
	FCS Errored Frames Received"

	INDEX	{ dot3Index }
	::= { dot3Table 1 }

Dot3Entry ::= SEQUENCE {
    dot3Index
        INTEGER,
    dot3InitializeMAC
        INTEGER,
    dot3MACSubLayerStatus
        INTEGER,
    dot3MulticastReceiveEnabled
        INTEGER,
    dot3AlignmentErrors
        Counter,
    dot3FCSErrors
        Counter }

dot3Index OBJECT-TYPE
	SYNTAX INTEGER
	ACCESS read-only
	STATUS mandatory
		--% ALIAS "Interface Table Index"
		--% GROUP INX-NTS-Interface-Table
	DESCRIPTION
		"The value assigned to the INX-NTS Ethernet interface. 
Because the INX-NTS has only one interface, this variable always returns 1."
	::= { dot3Entry 1 }

dot3InitializeMAC OBJECT-TYPE
	SYNTAX INTEGER {
				initialize(1)
			}
		ACCESS read-write
	STATUS mandatory
		--% ALIAS "MAC Initialization Status"
		--% GROUP INX-NTS-Interface-Table
	DESCRIPTION
		"The initialization status of the MAC and PLS subsystems 
of the interface.  Because the MAC and PLS subsystems on the INX-NTS are 
initialized at power-up and remain so, this variable always returns 
initialized(1), and may only be set to initialized(1)."
	::= { dot3Entry 2 }

dot3MACSubLayerStatus OBJECT-TYPE
	SYNTAX INTEGER {
				enabled(1)
			}
	ACCESS read-write
	STATUS mandatory
		--% ALIAS "MAC Operational Status"
		--% GROUP INX-NTS-Interface-Table
	DESCRIPTION
		"The operational status of the MAC sublayer, i.e.,
whether it is ready to transmit and receive frames.  Because this sublayer 
is always active in the INX-NTS, this variable always returns enabled(1),
and can only be set to enabled(1)."
	::= { dot3Entry 3 }

dot3MulticastReceiveEnabled OBJECT-TYPE
	SYNTAX INTEGER {
				true(1)
			}
		ACCESS read-write
	STATUS mandatory
		--% ALIAS "Multicast Receive Status"
		--% GROUP INX-NTS-Interface-Table
	DESCRIPTION
		"The Multicast Receive status, i.e., whether the INX-NTS
is configured to receive frames with a multicast address.  Because Multicast 
Receive is always enabled on the INX-NTS, this variable always returns true(1),
and can only be set to true(1)."
	::= { dot3Entry 4 }

dot3AlignmentErrors OBJECT-TYPE
	SYNTAX Counter
	ACCESS read-only
	STATUS mandatory
		--% ALIAS "Nonaligned Frames Recd"
		--% GROUP INX-NTS-Interface-Table
	DESCRIPTION
		"The number of frames received on the interface that are
not an integral number of octets in length (i.e., the number of bits they 
contain is not a multiple of eight) and do not pass the FCS check.  This 
condition indicates that the frames were corrupted during transmission."
	::= { dot3Entry 5 }

dot3FCSErrors OBJECT-TYPE
	SYNTAX Counter
	ACCESS read-only
	STATUS mandatory
		--% ALIAS "FCS Errored Frames Received"
		--% GROUP INX-NTS-Interface-Table
	DESCRIPTION
		"The number of frames received on the interface that are
an integral number of octets in length (i.e., the number of bits they contain
is a multiple of eight) that do not pass the FCS check, indicating that the 
frames were corrupted during transmission."
	::= { dot3Entry 6 }

dot3TxTable OBJECT-TYPE
	SYNTAX SEQUENCE OF Dot3TxEntry
	ACCESS not-accessible
	STATUS mandatory
		--% ALIAS "Interface Transmit Table"
	DESCRIPTION
		"A list of transmit errors and statistics for the INX-NTS
Ethernet interface.  You cannot access this variable; it is only a table 
marker in the MIB."
	::= { dot3 2 }

dot3TxEntry OBJECT-TYPE 
	SYNTAX Dot3TxEntry 
	ACCESS not-accessible 
	STATUS mandatory --% ALIAS "Interface Transmit Entry" 
	DESCRIPTION 
		"An entry in the Interface Transmit table.  (See the
previous variable, Interface Transmit Table, for an explanation of this
table.) You cannot access this variable; it is only a table marker in the MIB.
The following variables are entries in the table:
        Interface Transmit Index 
        Single Collisions Transmitted 
        Multiple Collisions Xmitted 
        Total SQE Test Errors" 
        INDEX	{ dot3TxIndex }
	::= { dot3TxTable 1 }

Dot3TxEntry ::= SEQUENCE {
    dot3TxIndex
        INTEGER,
    dot3TxSingleCollisionFrames
        Counter,
    dot3TxMultipleCollisionFrames
        Counter,
    dot3TxSQETestErrors
        Counter }

dot3TxIndex OBJECT-TYPE
	SYNTAX INTEGER 
	ACCESS read-only
	STATUS mandatory
		--% ALIAS "Interface Transmit Index"
		--% GROUP Interface-Transmit-Table
	DESCRIPTION
		"The value assigned to the INX-NTS Ethernet interface. 
Because the INX-NTS has only one interface, this variable always returns 1."
	::= { dot3TxEntry 1 }

dot3TxSingleCollisionFrames OBJECT-TYPE
	SYNTAX Counter
	ACCESS read-only
	STATUS mandatory
		--% ALIAS "Single Collisions Transmitted"
		--% GROUP Interface-Transmit-Table
	DESCRIPTION
		"The number of frames that were successfully transmitted 
after experiencing one and only one collision."
	::= { dot3TxEntry 2 }

dot3TxMultipleCollisionFrames OBJECT-TYPE
	SYNTAX Counter
	ACCESS read-only
	STATUS mandatory
		--% ALIAS "Multiple Collisions Xmitted"
		--% GROUP Interface-Transmit-Table
	DESCRIPTION
		"The number of frames that were successfully transmitted 
after experiencing more than one collision."
	::= { dot3TxEntry 3 }


dot3TxSQETestErrors OBJECT-TYPE
	SYNTAX Counter 
	ACCESS read-only
	STATUS mandatory
		--% ALIAS "Total SQE Test Errors"
		--% GROUP Interface-Transmit-Table
	DESCRIPTION
		"The number of frames for which the INX-NTS's collision 
detect logic did not detect a Signal-Quality-Error-Test (SQE-Test) signal 
immediately after a packet transmission.  The INX-NTS does not generate 
SQE-Test error messages, so this variable always returns 0."
	::= { dot3TxEntry 4 }

dot3XRxTable OBJECT-TYPE
	SYNTAX SEQUENCE OF Dot3XRxEntry
	ACCESS not-accessible
	STATUS mandatory
		--% ALIAS "Interface Receive Table"
	DESCRIPTION
		"A list of receive errors and statistics for the INX-NTS 
Ethernet interface.  You cannot access this variable; it is only a table 
marker in the MIB."
	::= { dot3 3 }

dot3XRxEntry OBJECT-TYPE
	SYNTAX Dot3XRxEntry
	ACCESS not-accessible
	STATUS mandatory
		--% ALIAS "Interface Receive Entry"
	DESCRIPTION
		"An entry in the Interface Receive table.  (See the
previous variable, Interface Receive Table, for an explanation of this 
table.) You cannot access this variable; it is only a table marker in the MIB.
The following variables are entries in the table:

	Interface Receive Index
	Too Long Frames Recd
	In-Range Length Errors Recd
	Out-Range Length Errors Recd
	MAC Errors Received
	Autopartition Status
	Autopartition Disconnects
	Last Good Source Address Recd
	Source Address Changes Count"

	INDEX	{ dot3XRxIndex }
	::= { dot3XRxTable 1 }

Dot3XRxEntry ::= SEQUENCE {
    dot3XRxIndex
        INTEGER,
    dot3XRxFrameTooLongs
        Counter,
    dot3XRxInRangeLengthErrors
        Counter,
    dot3XRxOutOfRangeLengthFields
        Counter,
    dot3XRxInternalMACReceiveErrors
        Counter,
    dot3XRxAutoPartitionStatus
        INTEGER,
    dot3XRxAutoPartitionLog
        Counter,
    dot3XRxLastSourceAddress
        OCTET STRING,
    dot3XRxSourceAddressLog
        Counter
    }

dot3XRxIndex OBJECT-TYPE
	SYNTAX INTEGER 
	ACCESS read-only
	STATUS mandatory
		--% ALIAS "Interface Receive Index"
		--% GROUP Interface-Receive-Table
	DESCRIPTION
		"The value assigned to the INX-NTS Ethernet interface. 
Because the INX-NTS has only one interface, this variable always returns 1."
	::= { dot3XRxEntry 1 }

dot3XRxFrameTooLongs OBJECT-TYPE
	SYNTAX Counter
	ACCESS read-only
	STATUS mandatory
		--% ALIAS "Too Long Frames Recd"
		--% GROUP Interface-Receive-Table
	DESCRIPTION
		"The number of frames received on the interface that
exceed 	the maximum permitted frame size, i.e., 1180 octets."
	::= { dot3XRxEntry 2 }

dot3XRxInRangeLengthErrors OBJECT-TYPE
	SYNTAX Counter 
	ACCESS read-only
	STATUS mandatory
		--% ALIAS "In-Range Length Errors Recd"
		--% GROUP Interface-Receive-Table
	DESCRIPTION
		"The number of in-range length errors received.  IEEE
802.3 frames contain a length field, indicating the length of the 
frame.  If the value in the length field and the actual length of the frame 
do not match, even if the length of the frame is within 802.3 parameters, 
the receiving device returns an in-range error.  The INX-NTS receives 
Ethernet frames that do not have a length in the length field.  It therefore
cannot 	detect this error, and this variable always returns 0." 
	::= { dot3XRxEntry 3 }

dot3XRxOutOfRangeLengthFields OBJECT-TYPE
	SYNTAX Counter 
	ACCESS read-only
	STATUS mandatory
		--% ALIAS "Out-Range Length Errors Recd"
		--% GROUP Interface-Receive-Table
	DESCRIPTION
		"The number of out-of-range length errors received.  IEEE
802.3 frames contain a length field, indicating the length of the
frame.  If the length of the frame is outside 802.3 parameters, the
receiving device returns an out-of-range error.  The INX-NTS
receives Ethernet frames that do not have a length in the length
field.  It therefore cannot detect this error, and this variable
always returns 0."
	::= { dot3XRxEntry 4 }

dot3XRxInternalMACReceiveErrors OBJECT-TYPE
	SYNTAX Counter
	ACCESS read-only
	STATUS mandatory
		--% ALIAS "MAC Errors Received"
		--% GROUP Interface-Receive-Table
	DESCRIPTION
		"The number of frames the interface could not receive
because of an internal MAC sublayer receive error.  This variable
returns frames not counted by the Too Long Frames Received,
Nonaligned Frames Received, FCS Errored Frames Received, In-Range
Length Errors Recd, and Out-Range Length Errors Recd variables."
	::= { dot3XRxEntry 5 }

dot3XRxAutoPartitionStatus OBJECT-TYPE
	SYNTAX INTEGER {
					notpartitioned(2)
				}
	ACCESS read-write
	STATUS mandatory
		--% ALIAS "Autopartition Status"
		--% GROUP Interface-Receive-Table
	DESCRIPTION
		"The autopartition status of the INX-NTS.  Devices that
support autopartitioning have the ability to autonomously
disconnect from the network when they sense trouble, e.g., a device
with a jabber condition.  Because the INX-NTS interface does not
support autopartitioning, this variable always returns notpartitioned(2).  
This object may be written to with the value notpartitioned(2)."
	::= { dot3XRxEntry 6 }

dot3XRxAutoPartitionLog OBJECT-TYPE
	SYNTAX Counter 
	ACCESS read-only
	STATUS mandatory
		--% ALIAS "Autopartition Disconnects"
		--% GROUP Interface-Receive-Table
	DESCRIPTION
		"The number of autopartitions the INX-NTS has performed. 
Devices that support autopartitioning maintain a log of the number
of times they disconnected from the network.  Because the INX-NTS
interface does not support auto-partitioning, this variable always
returns 0."
	::= { dot3XRxEntry 7 }

dot3XRxLastSourceAddress OBJECT-TYPE
	SYNTAX OCTET STRING
	ACCESS read-only
	STATUS mandatory
		--% ALIAS "Last Good Source Address Recd"
		--% GROUP Interface-Receive-Table
	DESCRIPTION
		"The source address of the last frame successfully
received.  Because this value changes too often to be useful, the
INX-NTS interface does not record the last source address of
received frames; therefore, this variable always returns a null
value."
	::= { dot3XRxEntry 8 }

dot3XRxSourceAddressLog OBJECT-TYPE
	SYNTAX Counter 
	ACCESS read-only
	STATUS mandatory
		--% ALIAS "Source Address Changes Count"
		--% GROUP Interface-Receive-Table
	DESCRIPTION
		"The number of times that the value of Last Good Source
Address Recd has changed.  The INX-NTS interface does not log
source address changes; therefore, this variable always returns 0."
	::= { dot3XRxEntry 9 }

dot3XTxTable OBJECT-TYPE
	SYNTAX SEQUENCE OF Dot3XTxEntry
	ACCESS not-accessible
	STATUS mandatory
		--% ALIAS "Interface Xmit Error/Stat Table"
	DESCRIPTION
		"A list of transmit errors and statistics for the INX-NTS
Ethernet interface.

You cannot access this variable; it is only a table marker in the
MIB."
	::= { dot3 4 }

dot3XTxEntry OBJECT-TYPE
	SYNTAX Dot3XTxEntry
	ACCESS not-accessible
	STATUS mandatory
		--% ALIAS "Interface Xmit Error/Stat Entry"
	DESCRIPTION
		"An entry in the Interface Xmit Error/Stat table.  (See
the previous variable, Interface Xmit Error/Stat Table, for an
explanation of this table.)

You cannot access this variable; it is only a table marker in the
MIB.  The following variables are entries in the table:

	Interface Xmit Error/Stat Index
	Interface Transmit Status
	Transmissions Deferred
	Late Collisions Detected
	Excessive Collisions Detected
	MAC Transmit Errors
	Carrier Sense Errors
	Deferred Frames
	TDR Status"

	INDEX	{ dot3XTxIndex }
	::= { dot3XTxTable 1 }

Dot3XTxEntry ::= SEQUENCE {
    dot3XTxIndex
        INTEGER,
    dot3XTxEnabled
        INTEGER,
    dot3XTxDeferredTransmissions
        Counter,
    dot3XTxLateCollisions
        Counter,
    dot3XTxExcessiveCollisions
        Counter,
    dot3XTxInternalMACTransmitErrors
        Counter,
    dot3XTxCarrierSenseErrors
        Counter,
    dot3XTxExcessiveDeferrals
        Counter,
    dot3XTxTDR
        Gauge }

dot3XTxIndex OBJECT-TYPE
	SYNTAX INTEGER 
	ACCESS read-only
	STATUS mandatory
		--% ALIAS "Interface Xmit Error/Stat Index"
		--% GROUP Interface-Xmit-Error/Stat-Table
	DESCRIPTION
		"The value assigned to the INX-NTS Ethernet interface. 
Because the INX-NTS has only one interface, this variable always
returns 1."
	::= { dot3XTxEntry 1 }

dot3XTxEnabled OBJECT-TYPE
	SYNTAX INTEGER {
					true(1)
				}
	ACCESS read-write
	STATUS mandatory
		--% ALIAS "Interface Transmit Status"
		--% GROUP Interface-Xmit-Error/Stat-Table
	DESCRIPTION
		"The transmit status of the interface, i.e., whether it
is able to transmit frames.  Because transmit is always enabled on
the INX-NTS, this variable always returns true(1), and can only be
set to true(1)."
	::= { dot3XTxEntry 2 }

dot3XTxDeferredTransmissions OBJECT-TYPE
	SYNTAX Counter
	ACCESS read-only
	STATUS mandatory
		--% ALIAS "Transmissions Deferred"
		--% GROUP dot3XTransmitTable
	DESCRIPTION
		"The number of times the INX-NTS deferred transmission
of data because it sensed traffic on the network.  Because the
INX-NTS does not record deferrals, this variable always returns 0."
	::= { dot3XTxEntry 3 }

dot3XTxLateCollisions OBJECT-TYPE
	SYNTAX Counter 
	ACCESS read-only
	STATUS mandatory
		--% ALIAS "Late Collisions Detected"
		--% GROUP Interface-Xmit-Error/Stat-Table
	DESCRIPTION
		"The number of times that a collision has been detected
on this bus later than 512 bit times from frame start."
	::= { dot3XTxEntry 4 }

dot3XTxExcessiveCollisions OBJECT-TYPE
	SYNTAX Counter 
	ACCESS read-only
	STATUS mandatory
		--% ALIAS "Excessive Collisions Detected"
		--% GROUP Interface-Xmit-Error/Stat-Table
	DESCRIPTION
		"The number of frames the interface could not transmit
because of excessive collisions."
	::= { dot3XTxEntry 5 }

dot3XTxInternalMACTransmitErrors OBJECT-TYPE
	SYNTAX Counter
	ACCESS read-only
	STATUS mandatory
		--% ALIAS "MAC Transmit Errors"
		--% GROUP Interface-Xmit-Error/Stat-Table
	DESCRIPTION
		"The number of frames the interface could not transmit
because of an internal MAC sublayer transmit error.  This variable
counts frames not counted by the Late Collisions Detected,
Excessive Collisions Detected, Carrier Sense Errors, and Deferred
Frames variables."
	::= { dot3XTxEntry 6 }

dot3XTxCarrierSenseErrors OBJECT-TYPE
	SYNTAX Counter
	ACCESS read-only
	STATUS mandatory
		--% ALIAS "Carrier Sense Errors"
		--% GROUP Interface-Xmit-Error/Stat-Table
	DESCRIPTION
		"The number of times that the carrier-sense condition was
lost or never asserted when the INX-NTS attempted to transmit a
frame on the interface.

This count is incremented at most once per transmission attempt,
even if the carrier-sense condition fluctuates during the transmit
attempt."
	::= { dot3XTxEntry 7 }

dot3XTxExcessiveDeferrals OBJECT-TYPE
	SYNTAX Counter 
	ACCESS read-only
	STATUS mandatory
		--% ALIAS "Deferred Frames"
		--% GROUP Interface-Xmit-Error/Stat-Table
	DESCRIPTION
		"The number of frames the INX-NTS deferred transmitting
for an excessive period of time.  Because the INX-NTS interface
does not record deferrals, this variable always returns 0."
	::= { dot3XTxEntry 8 }

dot3XTxTDR OBJECT-TYPE
	SYNTAX Gauge 
	ACCESS read-only
	STATUS mandatory
		--% ALIAS "TDR Status"
		--% GROUP Interface-Xmit-Error/Stat-Table
	DESCRIPTION
		"The status of Time Domain Reflectometry (TDR) on the
INX-NTS.  TDR is the ability of a device to check the viability of
a cable by sending a signal to the end of the cable.  The INX-NTS
interface does not support Time Domain Reflectometry,so this
variable always returns 0."
	::= { dot3XTxEntry 9 }

dot3CollTable OBJECT-TYPE
        SYNTAX SEQUENCE OF Dot3CollEntry
        ACCESS not-accessible
        STATUS mandatory
		--% ALIAS "Collision Frequency Table"
	DESCRIPTION
		"A histogram representing the frequency of collisions on
the interface. In the Collision Frequency histogram, one dimension of each 
cell represents Collisions per Frame, and the other dimension represents
Collision Frequency.

You cannot access this variable; it is only a table marker in the
MIB."
        ::= { dot3 5 }

dot3CollEntry OBJECT-TYPE
        SYNTAX Dot3CollEntry
        ACCESS not-accessible
        STATUS mandatory
		--% ALIAS "Collision Frequency Entry"
	DESCRIPTION
		"An entry in the Collision Frequency table.  (See the
previous variable, Collision Frequency Table, for an explanation
of this table.)

You cannot access this variable; it is only a table marker in the
MIB.  The following variables are entries in the table:

	Collision Frequency Index
	Collisions per Frame
	Collision Frequency"

	INDEX	{ dot3CollIndex, dot3CollCount }
        ::= { dot3CollTable 1 }

Dot3CollEntry ::= SEQUENCE {
    dot3CollIndex
        INTEGER,
    dot3CollCount
        INTEGER (1..15),
    dot3CollFrequency
        Counter }

dot3CollIndex OBJECT-TYPE
        SYNTAX INTEGER 
        ACCESS read-only
        STATUS mandatory
		--% ALIAS "Collision Frequency Index"
		--% GROUP Collision-Frequency-Table
	DESCRIPTION
		"The value assigned to the INX-NTS Ethernet interface. 
Because the INX-NTS has only one interface, this variable always
returns 1."
        ::= { dot3CollEntry 1 }

dot3CollCount OBJECT-TYPE
        SYNTAX INTEGER (1..15)
        ACCESS read-only
        STATUS mandatory
		--% ALIAS "Collisions per Frame"
		--% GROUP Collision-Frequency-Table
	DESCRIPTION
		"The number of media collisions per frame indicated by
one cell in the collision histogram.  The INX-NTS tracks the number
of collisions up to 15."
        ::= { dot3CollEntry 2 }

dot3CollFrequency OBJECT-TYPE
        SYNTAX Counter
        ACCESS read-only
        STATUS mandatory
		--% ALIAS "Collision Frequency"
		--% GROUP Collision-Frequency-Table
	DESCRIPTION
		"The number of frames that were transmitted after
experiencing exactly Collisions per Frame collisions on the INX-NTS
Ethernet interface (see the previous variable, Collisions per
Frame)."
        ::= { dot3CollEntry 3 }


-- ***********************************************************************
-- 
-- Following objects are from the Racal Interlan Boot Specification Group.  
-- 
-- ***********************************************************************

riNumBoots OBJECT-TYPE
	SYNTAX INTEGER 
	ACCESS read-write
	STATUS mandatory
		--% ALIAS "Number of Boot Table Entries"
		--% GROUP Racal-InterLan-Boot-Group
	DESCRIPTION
		"The number of entries in the boot table.  Because there
are two files that can be booted (chassis management protocol and
high-level protocol), there will always be two entries in the
INX-NTS boot table.  Therefore, this variable will always return
a 2, and can only be set to 2."
	::={ riBoot 1 }

riBootServiceOffered OBJECT-TYPE
	SYNTAX INTEGER {
					false(1),
					true(2)
				}
	ACCESS read-write
	STATUS mandatory
		--% ALIAS "Boot Image Source"
		--% GROUP Racal-InterLan-Boot-Group
	DESCRIPTION
		"The setting of this variable determines whether this
INX-NTS can provide boot images to other systems, returning true(2)
if it can and false(1) if it cannot."
	::={ riBoot 2 }

riBootTable OBJECT-TYPE
	SYNTAX SEQUENCE OF RiBootEntry
	ACCESS not-accessible
	STATUS mandatory
		--% ALIAS "Boot Table"
	DESCRIPTION
		"This table contains boot information for the INX-NTS. 
 

You cannot access this variable; it is only a table marker in the
MIB."
	::= { riBoot 3 }

riBootEntry OBJECT-TYPE
	SYNTAX RiBootEntry
	ACCESS not-accessible
	STATUS mandatory
		--% ALIAS "Boot Table Entry"
	DESCRIPTION
		"An entry in the Boot table. (See the previous variable,
Boot Table, for an explanation of this table.)   

You cannot access this variable; it is only a table marker in the
MIB.  The following variables are entries in the table:   

Boot Table Index   
Boot File Name   
IP Address for TFTP Boot   
Boot File Version   
Gateway Address for Booting"
	INDEX	{ riBootIndex }
	::={ riBootTable 1 }

RiBootEntry ::= SEQUENCE {
     riBootIndex
          INTEGER,
     riBootFileName
          OCTET STRING,
     riBootIPAddress
          IpAddress,
     riBootVersion
          INTEGER,
     riBootGateway
          IpAddress }

riBootIndex OBJECT-TYPE
	SYNTAX INTEGER
	ACCESS read-only
	STATUS mandatory
		--% ALIAS "Boot Table Index"
		--% GROUP Boot-Table
	DESCRIPTION
		"A unique value for each entry in the boot table.  This
variable returns 1 for the Chassis Management Protocol file and 2
for the operating software image file."
	::= { riBootEntry 1 }

riBootFileName OBJECT-TYPE
	SYNTAX OCTET STRING
	ACCESS read-write
	STATUS mandatory
		--% ALIAS "Boot File Name"
		--% GROUP Boot-Table
	DESCRIPTION
		"The name of the boot file that the INX-NTS will attempt
to load."
	::= { riBootEntry 3 }

riBootIPAddress OBJECT-TYPE
	SYNTAX IpAddress
	ACCESS read-write
	STATUS mandatory
		--% ALIAS "IP Address for TFTP Boot"
		--% GROUP Boot-Table
	DESCRIPTION
		"The IP address of the node from which the INX-NTS will
attempt a TFTP boot."
	::= { riBootEntry 6 }

riBootVersion OBJECT-TYPE
	SYNTAX INTEGER
	ACCESS read-write
	STATUS mandatory
		--% ALIAS "Boot File Version"
		--% GROUP Boot-Table
	DESCRIPTION
		"The revision level of the boot file."
	::= { riBootEntry 7 }

riBootGateway OBJECT-TYPE
	SYNTAX IpAddress
	ACCESS read-write
	STATUS mandatory
		--% ALIAS "Gateway Address for Booting"
		--% GROUP Boot-Table
	DESCRIPTION
		"The IP address of the gateway through which the INX-NTS
can access the boot server."
     ::= { riBootEntry 8 }

-- ***********************************************************************
-- 
-- Following objects are from the Racal Interlan Proprietary System
-- MIB group 
-- 
-- ***********************************************************************

riSystemHardwareRev OBJECT-TYPE
	SYNTAX DisplayString
	ACCESS read-only
	STATUS mandatory
		--% ALIAS "INX-NTS Hardware Rev"
		--% GROUP Racal-InterLan-System-Group
	DESCRIPTION
		"The hardware revision level of the INX-NTS."
	::={ riSystem 1 }

riSystemFirmwareRev OBJECT-TYPE
	SYNTAX DisplayString
	ACCESS read-only
	STATUS mandatory
		--% ALIAS "INX-NTS Firmware Rev"
		--% GROUP Racal-InterLan-System-Group
	DESCRIPTION
		"The firmware revision level of the INX-NTS."
	::={ riSystem 2 }

riSystemSoftwareRev OBJECT-TYPE
	SYNTAX DisplayString
	ACCESS read-only
	STATUS mandatory
		--% ALIAS "INX-NTS Software Rev"
		--% GROUP Racal-InterLan-System-Group
	DESCRIPTION
		"The software revision level of the INX-NTS."
	::={ riSystem 3 }

riSystemSerialNumber OBJECT-TYPE
	SYNTAX DisplayString
	ACCESS read-only
	STATUS mandatory
		--% ALIAS "INX-NTS Serial Number"
		--% GROUP Racal-InterLan-System-Group
	DESCRIPTION
		"The serial number of the INX-NTS."
	::={ riSystem 4 }

riSystemReset OBJECT-TYPE
	SYNTAX INTEGER {
					notreset(1),
					resetupdate(3)
				}
	ACCESS read-write
	STATUS mandatory
		--% ALIAS "INX-NTS Reset Status"
		--% GROUP Racal-InterLan-System-Group
	DESCRIPTION
		"The reset state of the INX-NTS.   
o resetupdate(3) causes the INX-NTS to reset following the next
  NVRAM update.   
o notreset(1) has no effect."
	::={ riSystem 5 }

riSystemTicksPerSecond OBJECT-TYPE
	SYNTAX INTEGER 
	ACCESS read-only
	STATUS mandatory
		--% ALIAS "Internal Clock Ticks/Second"
		--% GROUP Racal-InterLan-System-Group
	DESCRIPTION
		"The number of internal clock ticks that occur each
second on the INX-NTS."
	::= { riSystem 12 }

riSystemRateInterval OBJECT-TYPE
	SYNTAX INTEGER (5..3600)
	ACCESS read-write
	STATUS mandatory
		--% ALIAS "Rate Interval"
		--% GROUP Racal-InterLan-System-Group
	DESCRIPTION
		"How often, in seconds, any rate statistic maintained by
the INX-NTS is checked.  The default is 20 seconds."
	::= { riSystem 13 }

riSystemNVRamWriteCount OBJECT-TYPE
	SYNTAX Counter
	ACCESS read-only
	STATUS mandatory
		--% ALIAS "NVRAM Changes"
		--% GROUP Racal-InterLan-System-Group
	DESCRIPTION
		"The number of times that the NVRAM has been changed."
	::= { riSystem 15 }

-- ***************************************************************
--
-- Racal Interlan Terminal Server Group
--
-- ***************************************************************

     riTsPortCount OBJECT-TYPE
          SYNTAX INTEGER
          ACCESS read-only
          STATUS mandatory
		--% ALIAS "Number of Terminal Ports"
		--% GROUP Generic-Terminal-Server-Group
	DESCRIPTION
		"The number of terminal ports on the INX-NTS.  Because
there are 16 ports on the INX-NTS, this variable always returns
16."
          ::={ riTs 1 }

     riTsSignOn OBJECT-TYPE
          SYNTAX DisplayString
          ACCESS read-write
          STATUS mandatory
		--% ALIAS "Signon Message"
		--% GROUP Generic-Terminal-Server-Group
	DESCRIPTION
		"Allows you to view or change the INX-NTS sign-on
message.  This message is displayed when you enter command mode
from idle mode, and when you connect to a slave port.  The message
can be up to 120 characters long."
          ::={ riTs 3 }

     riTsPrompt OBJECT-TYPE
          SYNTAX DisplayString
          ACCESS read-write
          STATUS mandatory
		--% ALIAS "Command Mode Prompt"
		--% GROUP Generic-Terminal-Server-Group
	DESCRIPTION
		"Allows you to view or change the INX-NTS command-mode
prompt.  The default is inx-nts>.  The prompt can contain up to 80
characters."
          ::={ riTs 4 }

     riTsAdminPW OBJECT-TYPE
          SYNTAX DisplayString
          ACCESS read-only
          STATUS mandatory
		--% ALIAS "Administrative Password"
		--% GROUP Generic-Terminal-Server-Group
	DESCRIPTION
		"The password to use when entering administrative mode
in the INX-NTS.  For security reasons, this variable always returns
the string PASSWORD-RESTRICTED.  

If you are using the INX-LCD, the default password is 123456. 
(Press each of the function keys located to the left of the Unit
key in order from left to right.)  If you are accessing the INX-NTS
by another means, the default password is hello.   

To change this password, use the administrative command PASSWORD. 
Your new password can be up to 20 characters long."
          ::={ riTs 5 }

     riTsDomainName OBJECT-TYPE
          SYNTAX DisplayString
          ACCESS read-write
          STATUS mandatory
		--% ALIAS "Terminal`s Domain Name"
		--% GROUP Generic-Terminal-Server-Group
	DESCRIPTION
		"The name that is appended to the host name when the
INX-NTS requests a name server and the string entered by the user
contains no period. (If the string does contain a period, the
INX-NTS assumes it is a fully qualified domain name.)"
          ::={ riTs 7 }

     riTsUpTimeNodeName OBJECT-TYPE
          SYNTAX DisplayString
          ACCESS read-write
          STATUS mandatory
		--% ALIAS "UpTime Node Name"
		--% GROUP Generic-Terminal-Server-Group
	DESCRIPTION
		"The node name to be contained in future RWHO (UPTIME)
broadcasts.  The name can contain up to seven characters."
          ::={ riTs 8 }

     riTsNumBuffers OBJECT-TYPE
          SYNTAX INTEGER (2..4)
          ACCESS read-write
          STATUS mandatory
		--% ALIAS "Number of Buffers"
		--% GROUP Generic-Terminal-Server-Group
	DESCRIPTION
		"The number of buffers that a Telnet, RLOGIN, or LAT
process can use for receiving inbound traffic."
          ::={ riTs 9 }

     riTsReadBufferSize OBJECT-TYPE
          SYNTAX INTEGER(256..512)
          ACCESS read-write
          STATUS mandatory
		--% ALIAS "TCP Read Buffer Size"
		--% GROUP Generic-Terminal-Server-Group
	DESCRIPTION
		"The TCP read buffer size, in octets."
          ::={ riTs 10 }

     riTsWriteBufferSize OBJECT-TYPE
          SYNTAX INTEGER(48..128)
          ACCESS read-write
          STATUS mandatory
		--% ALIAS "TCP Write Buffer Size"
		--% GROUP Generic-Terminal-Server-Group
	DESCRIPTION
		"The TCP write buffer size, in octets."
          ::={ riTs 11 }

     riTsTcpWindowSize OBJECT-TYPE
          SYNTAX INTEGER(512..1024)
          ACCESS read-write
          STATUS mandatory
		--% ALIAS "TCP Default Window Size"
		--% GROUP Generic-Terminal-Server-Group
	DESCRIPTION
		"The TCP default window size, in octets."
          ::={ riTs 12 }

     riTsTcpMaxSeg OBJECT-TYPE
          SYNTAX INTEGER (256..512)
          ACCESS read-write
          STATUS mandatory
		--% ALIAS "TCP Max Segment Size"
		--% GROUP Generic-Terminal-Server-Group
	DESCRIPTION
		"The TCP maximum segment size, in octets."
          ::={ riTs 13 }

     riTsBreakChar OBJECT-TYPE
          SYNTAX INTEGER (0..256)
          ACCESS read-write
          STATUS mandatory
		--% ALIAS "Break In Character"
		--% GROUP Generic-Terminal-Server-Group
	DESCRIPTION
		"Allows you to view or change the INX-NTS break-in
character, which permits you to escape from a connection and return
to command mode.   

This variable returns the value of the ASCII character to use as
the break-in character. The default value is 256, which sets the
Break key as the break-in character."
          ::={ riTs 14 }

     riTsFarMemoryFree OBJECT-TYPE
          SYNTAX INTEGER
          ACCESS read-only
          STATUS mandatory
		--% ALIAS "Octets Free In Far Memory"
		--% GROUP riTsHardware
	DESCRIPTION
		"The number of available octets in the far memory pool."
          ::={ riTs 22 }

     riTsFarMemoryLowest OBJECT-TYPE
          SYNTAX INTEGER
          ACCESS read-only
          STATUS mandatory
		--% ALIAS "Lowest Octets Free In Far Mem"
		--% GROUP riTsHardware
	DESCRIPTION
		"The lowest number of octets available in the far memory
pool since the INX-NTS was reset."
          ::={ riTs 24 }

     riTsTcpAckTimer OBJECT-TYPE
          SYNTAX INTEGER (50..300)
          ACCESS read-write
          STATUS mandatory
		--% ALIAS "TCP Acknowledgement Timer"
		--% GROUP Generic-Terminal-Server-Group
	DESCRIPTION
		"The number of milliseconds that the INX-NTS TCP
implementation waits between TCP protocol ACK packets.

This variable must be set to a multiple of 50.  If it is set to
some value that is not a multiple of 50, then the value will be
rounded down to a multiple of 50.  For example, if you specify this
variable as 199, it will actually be set to 150."
          ::={ riTs 25 }

     riTsPortTable OBJECT-TYPE
          SYNTAX SEQUENCE OF RiTsPortEntry
          ACCESS not-accessible
          STATUS mandatory
		--% ALIAS "Port Table"
	DESCRIPTION
		"A table containing management information for a specific
port on the INX-NTS.  There are 16 entries in this table, one for
each port.   

You cannot access this variable; it is only a table marker in the
MIB."
          ::={ riTs 28 }

     riTsPortEntry OBJECT-TYPE
          SYNTAX RiTsPortEntry
          ACCESS not-accessible
          STATUS mandatory
		--% ALIAS "Port Entry"
	DESCRIPTION
		"An entry in the Port table (see the previous variable,
Port Table, for an explanation of this table).  

You cannot access this variable; it is only a table marker in the
MIB.  The following variables are entries in the Port Table:  

	Port Index   
	First Session Type  
	Current Session Type   
	Current Number of Sessions   
	Baud Rate for Received Data   
	Baud Rate for Transmitted Data   
	Port Parity   
	Data Bits Sent    
	Modem Control Type   
	Flow Control for Data Received   
	Flow Control for Data Sent  
	RS-232 Ring Indicator   
	Connection Password   
	Telnet Abort Out Character   
	Telnet Interrupt Character   
	Inactivity Timeout Value   
	Time Until Timer Expires   
	Suppress Software Messages   
	Port Function  
	Port State   
	Octets Rec'd   
	Octets Trans   
	XON Character   
	XOFF Character   
	Maximum Allowed Sessions 
	TCP Port Number   
	TCP Port Mode  
	Transparent Mode for the Port   
	Port Echo Setting   
	Domain Name Server IP Addr"

	INDEX	{ riTsPortIndex }
          ::={ riTsPortTable 1 }

     RiTsPortEntry ::= SEQUENCE {
               riTsPortIndex
                    INTEGER,
               riTsPortFirstType
                    INTEGER,
               riTsPortActiveType
                    INTEGER,
               riTsPortNumSessions
                    Gauge,
               riTsPortBaudIn
                    INTEGER,
               riTsPortBaudOut
                    INTEGER,
               riTsPortParity
                    INTEGER,
               riTsPortDataBits
                    INTEGER,
               riTsPortModemControl
                    INTEGER,
               riTsPortFlowControlIn
                    INTEGER,
               riTsPortFlowControlOut
                    INTEGER,
               riTsPortRing
                    INTEGER,
               riTsPortPassword
                    OCTET STRING,
               riTsPortAbortOut
                    INTEGER,
               riTsPortIntProc
                    INTEGER,
               riTsPortInactiveTimeOut
                    INTEGER,
               riTsPortInactiveTimer
                    INTEGER,
               riTsPortMachineInterface
                    INTEGER,
               riTsPortFunction
                    INTEGER,
               riTsPortState
                    INTEGER,
               riTsPortOctetsIn
                    Counter,
               riTsPortOctetsOut
                    Counter,
               riTsPortXONChar
                    INTEGER,
               riTsPortXOFFChar
                    INTEGER,
               riTsPortMaxSess
                    INTEGER,
               riTsPortServerPort
                    INTEGER,
	       riTsPortTCPMode
		    INTEGER,
	       riTsPortDefXparent
	            INTEGER,
	       riTsPortDefEcho
		    INTEGER,
               riTsDomainServerAddress
                    IpAddress
          }


     riTsPortIndex OBJECT-TYPE
          SYNTAX INTEGER (1..16)
          ACCESS read-only
          STATUS mandatory
		--% ALIAS "Port Index"
		--% GROUP Port-Table
	DESCRIPTION
		"A unique value for each port.  Because there are 16
ports on the INX-NTS, this variable always returns a value from 1
through 16."
          ::={ riTsPortEntry 1 }

     riTsPortFirstType OBJECT-TYPE
          SYNTAX INTEGER {
                         telnet(4),
                         dummy(5),
                         none(1)
                    }
          ACCESS read-only
          STATUS mandatory
		--% ALIAS "First Session Type"
		--% GROUP Port-Table
	DESCRIPTION
		"The protocol used by the first session in the set of
sessions for this port.  For the INX-NTS, this variable returns
telnet(4) for Telnet connections and dummy(5) for all other
connections.  If there are no sessions for this port, the variable
returns none(1)."
          ::={ riTsPortEntry 2 }

     riTsPortActiveType OBJECT-TYPE
          SYNTAX INTEGER {
                         telnet(4),
                         dummy(5),
                         none(1)
                    }
          ACCESS read-only
          STATUS mandatory
		--% ALIAS "Current Session Type"
		--% GROUP Port-Table
	DESCRIPTION
		"The protocol that the currently active session is using
to communicate with the other end of the connection.  For the
INX-NTS, this variable returns telnet(4) for Telnet connections and
dummy(5) for all other connections.  If there are no sessions for
this port, the variable returns none(1)."
          ::={ riTsPortEntry 4 }

     riTsPortNumSessions OBJECT-TYPE
          SYNTAX Gauge
          ACCESS read-only
          STATUS mandatory
		--% ALIAS "Current Number of Sessions"
		--% GROUP Port-Table
	DESCRIPTION
		"The current number of sessions that are associated with
this port. This number includes sessions for which there is no MIB
entry (i.e., any session other than a Telnet session)."
          ::={ riTsPortEntry 6 }

     riTsPortBaudIn OBJECT-TYPE
          SYNTAX INTEGER	{
					br-110(110),
					br-300(300),
					br-600(600),
					br-1200(1200),
					br-2400(2400),
					br-4800(4800),
					br-9600(9600),
					br-19200(19200),
					br-38400(38400)
					}
          ACCESS read-write
          STATUS mandatory
		--% ALIAS "Baud Rate for Received Data"
		--% GROUP Port-Table
	DESCRIPTION
		"The baud rate for data received by the port, in bits per
second (bps).   

If you want the INX-NTS to automatically determine baud rates, you
can configure it to do so by setting this variable to 0.  If this
variable returns 0, automatic baud rate determination is already
in effect.  If this variable returns a value other than 0, that
value is the current baud rate.  The default baud rate is 9600.

Note:  The INX-NTS uses only a single baud rate parameter, which
is used in both directions.  Therefore, you cannot set this
variable and the following one, Baud Rate for Transmitted Data, to
different values; the INX-NTS will use whichever value was last
received by the management agent as the baud rate."
          ::={ riTsPortEntry 7 }

     riTsPortBaudOut OBJECT-TYPE
          SYNTAX INTEGER	{
					br-110(110),
					br-300(300),
					br-600(600),
					br-1200(1200),
					br-2400(2400),
					br-4800(4800),
					br-9600(9600),
					br-19200(19200),
					br-38400(38400)
					}
          ACCESS read-write
          STATUS mandatory
		--% ALIAS "Baud Rate for Transmitted Data"
		--% GROUP Port-Table
	DESCRIPTION
		"The baud rate for data transmitted by the port, in bits
per second (bps).   

If you want the INX-NTS to automatically determine baud rates, you
can configure it to do so by setting this variable to 0.  If this
variable returns 0, automatic baud rate determination is already
in effect.  If this variable returns a value other than 0, that
value is the current baud rate.  The default baud rate is 9600.

Note:  The INX-NTS uses only a single baud rate parameter, which
is used in both directions.  Therefore, you cannot set this
variable and the previous one, Baud Rate for Received Data, to
different values; the INX-NTS will use whichever value was last
received by the management agent as the baud rate."
          ::={ riTsPortEntry 8 }

     riTsPortParity OBJECT-TYPE
          SYNTAX INTEGER {
                         none(1),
                         odd(2),
                         even(3)
                    }
          ACCESS read-write
          STATUS mandatory
		--% ALIAS "Port Parity"
		--% GROUP Port-Table
	DESCRIPTION
		"The parity of the port. Enter a value for parity that
matches the parity setting of the device attached to the INX-NTS
port.  The default is none(1). The parity bit is stripped before
the data is sent across the network."
          ::={ riTsPortEntry 9 }

     riTsPortDataBits OBJECT-TYPE
          SYNTAX INTEGER (7..8)
          ACCESS read-write
          STATUS mandatory
		--% ALIAS "Data Bits Sent"
		--% GROUP Port-Table
	DESCRIPTION
		"The number of data bits in each character transmitted
between the INX-NTS port and an attached device.  Enter a value
that matches the setting of the device attached to the port.  The
default is 8."
          ::={ riTsPortEntry 11 }

     riTsPortModemControl OBJECT-TYPE
          SYNTAX INTEGER {
                         none(1),
                         dce(2),
                         dte(3)
                    }
          ACCESS read-write
          STATUS mandatory
		--% ALIAS "Modem Control Type"
		--% GROUP Port-Table
	DESCRIPTION
		"The type of modem control, if any, on this port.  This
setting determines the use of the modem control RS-232 signals. 
Enter a value that matches the setting of the attached device.

o none(1) means that no modem control signals are in use.  This is
  the default.   
o dce(2) means that the INX-NTS port will act as a DCE device in
  monitoring the modem control signals. This is the appropriate
  setting if you are attaching a DTE device (for example, a terminal)
  that uses these signals to the INX-NTS port.  (Ports are always
  wired as DCE, regardless of modem settings.)   
o dte(3) means that the INX-NTS port will act as a DTE (Data
  Terminal Equipment) device in monitoring the modem control signals. 
  Use this setting when attaching a DCE (Data Communication
  Equipment) device (such as a modem) to the INX-NTS port.   

Note:  Setting Modem Control to DTE can require the use of a
cabling adapter at the device."
          ::={ riTsPortEntry 14 }

     riTsPortFlowControlIn OBJECT-TYPE
          SYNTAX INTEGER {
                         none(1),
                         xonxoff(2),
                         hardware(3),
                         handx(4)
                    }
          ACCESS read-write
          STATUS    mandatory
		--% ALIAS "Flow Control for Data Received"
		--% GROUP Port-Table
	DESCRIPTION
		"The type of flow control used on the port for received data.
o None(1) indicates that no flow control is in use   
o Xonxoff(2) indicates that software flow control is in use. 
o Hardware(3) indicates that hardware flow control is in use. 
  (This setting is not valid for use with an NTS-TELCO.)
0 Handx(4) indicates that both hardware and software flow
  control are in use.  (This setting is not valid for use with an
NTS-TELCO.)"
          ::={ riTsPortEntry 15 }

     riTsPortFlowControlOut OBJECT-TYPE
          SYNTAX    INTEGER {
                         none(1),
                         xonxoff(2),
                         hardware(3),
                         handx(4)
                    }
          ACCESS    read-write
          STATUS    mandatory
		--% ALIAS "Flow Control for Data Sent"
		--% GROUP Port-Table
	DESCRIPTION
		"The type of flow control used on the port for data being sent. 
o None(1) indicates that no flow control is in use.   
o Xonxoff(2) indicates that software flow control is in use.  For
  a terminal attached to an INX-NTS port, this setting allows you to
  press the XOFF control character (Ctrl-S by default) in order to
  halt output from the INX-NTS port to the screen, and the XON
  control character (Ctrl-Q by default) to resume output to the
  screen.   
o Hardware(3) indicates that hardware flow control is in use. 
  (This setting not valid for use with an NTS-TELCO.)   
o Handx(4) indicates that both hardware and software flow control
  are in use.  (This setting not valid for use with an NTS-TELCO.)"
          ::={ riTsPortEntry 16 }

     riTsPortRing   OBJECT-TYPE
          SYNTAX    INTEGER {
                         no(1),
                         yes(2)
                    }
          ACCESS    read-write
          STATUS    mandatory
		--% ALIAS "RS-232 Ring Indicator"
		--% GROUP Port-Table
	DESCRIPTION
		"The status of the Ring Indicator (RI) RS-232 signal. 
If you have set modem control (see the Modem Control Type variable)
to DCE, you must set Ring to no(1).  If you have set modem control
to DTE, yes(2) means that the INX-NTS port will use the RI signal;
no(1) means the signal will not be used."
          ::= { riTsPortEntry 17 } 

     riTsPortPassword OBJECT-TYPE
          SYNTAX    OCTET STRING
          ACCESS    read-write
          STATUS    mandatory
		--% ALIAS "Connection Password"
		--% GROUP Port-Table
	DESCRIPTION
		"The password needed to connect to the port. The port
password can be up to seven characters long."
          ::= { riTsPortEntry 18 } 

     riTsPortAbortOut OBJECT-TYPE
          SYNTAX    INTEGER (0..255)
          ACCESS    read-write
          STATUS    mandatory
		--% ALIAS "Telnet Abort Out Character"
		--% GROUP Port-Table
	DESCRIPTION
		"The ASCII value of the character that invokes a Telnet
Abort Output for this port.  You use this character to suspend
output to the screen for a current process."
          ::= { riTsPortEntry 19 } 

     riTsPortIntProc OBJECT-TYPE
          SYNTAX    INTEGER (0..255)
          ACCESS    read-write
          STATUS    mandatory
		--% ALIAS "Telnet Interrupt Character"
		--% GROUP Port-Table
	DESCRIPTION
		"The ASCII value of the character that invokes a Telnet
Interrupt Process for this port. You use this character to kill a
current process on a UNIX machine."
          ::= { riTsPortEntry 20 } 

     riTsPortInactiveTimeOut OBJECT-TYPE
          SYNTAX    INTEGER(0..255)
          ACCESS    read-write
          STATUS    mandatory
		--% ALIAS "Inactivity Timeout Value"
		--% GROUP Port-Table
	DESCRIPTION
		"The number of minutes a port can be inactive before the
INX-NTS closes all existing virtual circuits on that port.  The
timeout range can be from 1 to 255 minutes.   

This feature works on all ports except permanent.  It is disabled
for slave ports configured with network port numbers 7 (echo); 9
(sink); or 19 (source).   

To disable the inactivity timeout function, set this variable to
0."
          ::= { riTsPortEntry 21 } 

     riTsPortInactiveTimer OBJECT-TYPE
          SYNTAX    INTEGER(0..255)
          ACCESS    read-write
          STATUS    mandatory
		--% ALIAS "Time Until Timer Expires"
		--% GROUP Port-Table
	DESCRIPTION
		"Number of minutes left before the inactivity timer (see
the previous variable, Inactivity Timeout Value) expires, and all
virtual circuits for this port are closed.

Setting this variable to 0 temporarily disables the inactivity
timer, so virtual circuits are maintained as long as the port
remains inactive.  When port activity resumes, however, the
inactivity timer is reactivated, and this variable is set to the
value of Inactivity Timeout Value."
          ::= { riTsPortEntry 22 } 

     riTsPortMachineInterface OBJECT-TYPE
          SYNTAX    INTEGER {
                         no(1),
                         yes(2)
                    }
          ACCESS    read-write
          STATUS    mandatory
		--% ALIAS "Suppress Software Messages"
		--% GROUP Port-Table
	DESCRIPTION
		"Whether software-generated messages are passed through
the port.  To suppress the sending of all messages generated by the
LAT/TCP software, set this variable to yes(2).  To enable the
sending of such messages, set it to no(1).  Traffic from network
connections continues to pass through the port regardless of the
setting of this variable."
          ::= { riTsPortEntry 23 } 

     riTsPortFunction OBJECT-TYPE
          SYNTAX    INTEGER {
                         slave(1),
                         terminal(2),
                         permckt(3),
                         both(4),
                         demandckt(5),
                         queue(6)
                    }
          ACCESS    read-write
          STATUS    mandatory
		--% ALIAS "Port Function"
		--% GROUP Port-Table
	DESCRIPTION
		"The ability of the port to initiate and accept connections.   
o slave(1) indicates that the port can only accept connections. 
  If it is busy, it will reject a connection request.   
o terminal(2) indicates that this port can only initiate
  connections.   
o permckt(3) indicates that this port initiates and automatically
  maintains connections.   
o both(4) means this port can both accept and initiate connections. 
o demandckt(5) indicates the same status as permckt except that you
  must first press a key on the keyboard to activate the port.   
o queue(6) means this port accepts and holds connections.  It will
  act like a slave port, except that instead of rejecting a request
  when it is busy, it stores the request until a resource becomes
  available."
          ::={ riTsPortEntry 25 }

     riTsPortState OBJECT-TYPE
          SYNTAX    INTEGER {
                         disabled(1),
                         active(3)
                    }
          ACCESS    read-write
          STATUS    mandatory
		--% ALIAS "Port State"
		--% GROUP Port-Table
	DESCRIPTION
		"The state of the port.   

o disabled(1) indicates that the port cannot be used   
o active(3) means the port is enabled, and a device is connected. 

Setting an active(3) port to the disabled(1) state resets the port. 
All error conditions are cleared, and connections and sessions are
terminated."
          ::={ riTsPortEntry 26 }

     riTsPortOctetsIn OBJECT-TYPE
          SYNTAX    Counter
          ACCESS    read-only
          STATUS    mandatory
		--% ALIAS "Octets Rec'd"
		--% GROUP Port-Table
	DESCRIPTION
		"Total number of octets received on the port from the
network connection(s)."
          ::={ riTsPortEntry 27 }

     riTsPortOctetsOut OBJECT-TYPE
          SYNTAX    Counter
          ACCESS    read-only
          STATUS    mandatory
		--% ALIAS "Octets Trans"
		--% GROUP Port-Table
	DESCRIPTION
		"Total number of octets sent onto the network
connection(s) by the port."
          ::={ riTsPortEntry 28 }

     riTsPortXONChar OBJECT-TYPE
          SYNTAX    INTEGER(1..254)
          ACCESS    read-write
          STATUS    mandatory
		--% ALIAS "XON Character"
		--% GROUP Port-Table
	DESCRIPTION
		"The ASCII value of the XON character.  This setting is
meaningful only if XON/XOFF flow control is in use.  (See the Flow
Control for Data Received and Flow Control for Data Sent variables
for more information.)"
          ::= { riTsPortEntry 30 } 

     riTsPortXOFFChar OBJECT-TYPE
          SYNTAX    INTEGER(1..254)
          ACCESS    read-write
          STATUS    mandatory
		--% ALIAS "XOFF Character"
		--% GROUP Port-Table
	DESCRIPTION
		"The ASCII value of the XOFF character.  This setting is
meaningful only if XON/XOFF flow control is in use.  (See the Flow
Control for Data Received and Flow Control for Data Sent variables
for more information.)"
          ::= { riTsPortEntry 31 } 

     riTsPortMaxSess OBJECT-TYPE
          SYNTAX    INTEGER
          ACCESS    read-only
          STATUS    mandatory
		--% ALIAS "Maximum Allowed Sessions"
		--% GROUP Port-Table
	DESCRIPTION
		"Maximum number of sessions allowed on this port."
          ::= { riTsPortEntry 32 } 

     riTsPortServerPort OBJECT-TYPE
          SYNTAX    INTEGER(0..65535)
          ACCESS    read-write
          STATUS    mandatory
		--% ALIAS "TCP Port Number"
		--% GROUP Port-Table
	DESCRIPTION
		"The TCP port number that this serial port uses when
listening for Telnet connections.  If this port is not configured
to listen for inbound connection requests, this variable returns
65535.  The default TCP port number is 23."
          ::= { riTsPortEntry 33 } 

     riTsPortTCPMode OBJECT-TYPE
          SYNTAX    INTEGER {
                         rawsocket(1),
                         nvt7bit(2),
                         nvt8bit(3)
                    }
          ACCESS    read-write
          STATUS    mandatory
		--% ALIAS "TCP Port Mode"
		--% GROUP Port-Table
	DESCRIPTION
		"The TCP operating mode for the port.
o rawsocket(1) means there is no application protocol; data is
  transferred to and from a TCP socket without interpretation.
o nvt7bit(2) is for standard seven-bit NVT mode, in which the
  Telnet utility transfers 7-bit data.
o nvt8bit(3) is for a modified Telnet NVT mode (data is transferred
  using eight bits per character)."
          ::= { riTsPortEntry 36 } 

     riTsPortDefXparent OBJECT-TYPE
          SYNTAX    INTEGER {
			on(1),
			off(2)
		    }
          ACCESS    read-write
          STATUS    mandatory
		--% ALIAS "Transparent Mode for the Port"
		--% GROUP Port-Table
	DESCRIPTION
		"The default mode of the port.  When this variable is set
to on(1), you make it possible to enable full eight-bit
transparency so that you can send binary or image files across the
network.  To set the port to non-transparent mode, set this
variable to off(2)."
          ::= { riTsPortEntry 37 } 
	
     riTsPortDefEcho OBJECT-TYPE
          SYNTAX    INTEGER {
			local(1),
			remote(2)
		    }
          ACCESS    read-write
          STATUS    mandatory
		--% ALIAS "Port Echo Setting"
		--% GROUP Port-Table
	DESCRIPTION
		"The echo setting for the port.  This echo setting
determines whether echoing and such functions as line editing are
done by the remote host or the local host.

Remote echoing is the default and the recommended setting for your
terminal.  Local echoing allows you to connect to hosts that do not
support remote echoing."
          ::= { riTsPortEntry 38 } 

     riTsDomainServerAddress OBJECT-TYPE
	SYNTAX    IpAddress
	ACCESS    read-write
	STATUS    mandatory
		--% ALIAS "Domain Name Server IP Addr"
		--% GROUP Generic-Terminal-Server-Group
	DESCRIPTION
		"The Internet address of the host you want to have act
as the domain name server."
     	::= { riTs 29 }

-- ************************************************************
--
-- Racal Interlan proprietary telnet group.
--
-- ************************************************************

tnCount OBJECT-TYPE
     SYNTAX    Counter
     ACCESS    read-only
     STATUS    mandatory
		--% ALIAS "Telnet Sessions Initiated"
		--% GROUP Racal-InterLan-Telnet-Group
	DESCRIPTION
		"The number of Telnet sessions that have been initiated
from the INX-NTS."
     ::={ riTelnet 1 }

tnTable OBJECT-TYPE
     SYNTAX    SEQUENCE OF TnEntry
     ACCESS    not-accessible
     STATUS    mandatory
		--% ALIAS "Telnet Session Table"
	DESCRIPTION
		"A table containing Telnet session-specific information
that is appropriate to whatever side of a session the INX-NTS
happens to be.  There is one entry in the table for each telnet
session that is active.   

You cannot access this variable; it is only a table marker in the
MIB."
     ::={ riTelnet 2 }

tnEntry OBJECT-TYPE
     SYNTAX    TnEntry
     ACCESS    not-accessible
     STATUS    mandatory
		--% ALIAS "Telnet Session Table Entry"
	DESCRIPTION
		"Information about a particular Telnet session.  This
variable is an entry in the Telnet Session table.  (See the
previous variable, Telnet Session Table, for an explanation of this
table.)   

You cannot access this variable; it is only a table marker in the
MIB.  The following variables are entries in the table:   

	Telnet Port Identifier   
	Local IP Addr of TCP Cxn
	Remote IP Addr of TCP Cxn
	Local Port of TCP Connection   
	Remote Port of TCP Connection   
	UpTime at Session Start   
	Session Options   
	Telnet Session State   
	Telnet User ID   
	Octets Recd    
	Octets Sent   
	Protocol Type of Next Session   
	Name of Next Session"

	INDEX	{ tnLocalIpAddress, tnLocalPort, 
		  tnRemoteIpAddress, tnRemotePort}
     ::= { tnTable 1 }

TnEntry ::= SEQUENCE {
          tnPort
               INTEGER,
          tnLocalIpAddress
               IpAddress,
          tnRemoteIpAddress
               IpAddress,
          tnLocalPort
               INTEGER (0..65535),
          tnRemotePort
               INTEGER (0..65535),
          tnUpTime
               TimeTicks,
          tnOptionsOn
               OCTET STRING,
          tnState
               INTEGER,
          tnUserId
               DisplayString,
          tnOctetsReceived
               Counter,
          tnOctetsSent
               Counter,
          tnNextType
               INTEGER,
          tnNextName
               OBJECT IDENTIFIER
          }                        

tnPort OBJECT-TYPE
     SYNTAX    INTEGER
     ACCESS    read-only
     STATUS    mandatory
		--% ALIAS "Telnet Port Identifier"
		--% GROUP Telnet-Session-Table
	DESCRIPTION
		"The index value that uniquely identifies the terminal
port table entry to which this entry is applicable."
     ::= { tnEntry 1 }

tnLocalIpAddress OBJECT-TYPE
     SYNTAX    IpAddress
     ACCESS    read-only
     STATUS    mandatory
		--% ALIAS "Local IP Addr of TCP Cxn"
		--% GROUP Telnet-Session-Table
	DESCRIPTION
		"The local IP address of the TCP connection that this
Telnet session is using."
     ::= { tnEntry 2 }

tnRemoteIpAddress OBJECT-TYPE
     SYNTAX    IpAddress
     ACCESS    read-only
     STATUS    mandatory
		--% ALIAS "Remote IP Addr of TCP Cxn"
		--% GROUP Telnet-Session-Table
	DESCRIPTION
		"The remote IP address of the TCP connection that this
Telnet session is using."
     ::= { tnEntry 3 }

tnLocalPort OBJECT-TYPE
     SYNTAX    INTEGER(0..65535)
     ACCESS    read-only
     STATUS    mandatory
		--% ALIAS "Local Port of TCP Connection"
		--% GROUP Telnet-Session-Table
	DESCRIPTION
		"The local port number of the TCP connection that this
Telnet session is using."
     ::= { tnEntry 4 }

tnRemotePort OBJECT-TYPE
     SYNTAX    INTEGER(0..65535)
     ACCESS    read-only
     STATUS    mandatory
		--% ALIAS "Remote Port of TCP Connection"
		--% GROUP Telnet-Session-Table
	DESCRIPTION
		"The remote port number of the TCP connection that this
Telnet session is using."
     ::= { tnEntry 5 }

tnUpTime OBJECT-TYPE
     SYNTAX    TimeTicks
     ACCESS    read-only
     STATUS    mandatory
		--% ALIAS "UpTime at Session Start"
		--% GROUP Telnet-Session-Table
	DESCRIPTION
		"The amount of time that has elapsed since the Telnet
session was established."
     ::= { tnEntry 6 }

tnOptionsOn OBJECT-TYPE
     SYNTAX    OCTET STRING
     ACCESS    read-only
     STATUS    mandatory
		--% ALIAS "Session Options"
		--% GROUP Telnet-Session-Table
	DESCRIPTION
		"Indicates which options are on/enabled/in the will/do
state.  Each octet in the string contains the numerical value of
an option that is on.  For example, if a session had options 1, 4,
10, 15, and 20 on, then Session Options On would return 5 octets,
and the octets would contain the values 1, 4, 10, 15, and 20.  The
option values in the octet would contain the values 1, 4, 10, 15,
and 20.  The option values in the octet string can be in any
order."
     ::= { tnEntry 7 }

tnState OBJECT-TYPE
     SYNTAX    INTEGER {
               serverActive(1),
               client(3)
               }
     ACCESS    read-only
     STATUS    mandatory
		--% ALIAS "Telnet Session State"
		--% GROUP Telnet-Session-Table
	DESCRIPTION
		"The state of the session.   

o serverActive(1) indicates that the INX-NTS is the Telnet server,
  and that a session is active-i.e., a user has logged in to this end
  of the connection.   

o client(3) indicates that the INX-NTS is the client end of the
  connection.  In a typical Telnet session, this is the user's
  terminal."
     ::= { tnEntry 8 }

tnUserId OBJECT-TYPE
     SYNTAX    DisplayString 
     ACCESS    read-only
     STATUS    mandatory
		--% ALIAS "Telnet User ID"
		--% GROUP Telnet-Session-Table
	DESCRIPTION
		"The identification of the user at the INX-NTS end of the
Telnet session.   

Because user IDs are not implemented in the INX-NTS, this variable
always returns a null string."
     ::= { tnEntry 9 }

tnOctetsReceived OBJECT-TYPE
     SYNTAX    Counter 
     ACCESS    read-only
     STATUS    mandatory
		--% ALIAS "Octets Recd"
		--% GROUP Telnet-Session-Table
	DESCRIPTION
		"The number of octets of data received from the other end
of the session.

Because the INX-NTS does not keep octet counts for Telnet
connections, this variable always returns 0."
     ::= { tnEntry 10 }

tnOctetsSent OBJECT-TYPE
     SYNTAX    Counter 
     ACCESS    read-only
     STATUS    mandatory
		--% ALIAS "Octets Sent"
		--% GROUP Telnet-Session-Table
	DESCRIPTION
		"The number of octets of data sent to the other end of
the session.   Because the INX-NTS does not keep octet counts for Telnet
connections, this variable always returns 0."
     ::= { tnEntry 11 }

tnNextType OBJECT-TYPE
     SYNTAX    INTEGER
     ACCESS    read-only
     STATUS    mandatory
		--% ALIAS "Protocol Type of Next Session"
		--% GROUP Telnet-Session-Table
	DESCRIPTION
		"The protocol used by the next session in the set of
sessions currently established on this port.   Because the INX-NTS does 
not keep this information for Telnet connections, this variable always 
returns 0."
     ::= { tnEntry 12 }

tnNextName OBJECT-TYPE
     SYNTAX    OBJECT IDENTIFIER 
     ACCESS    read-only
     STATUS    mandatory
		--% ALIAS "Name of Next Session"
		--% GROUP Telnet-Session-Table
	DESCRIPTION
		"The entry in the application protocol table identified
by Protocol Type of Next Session.  Because the INX-NTS does not keep this 
information, this variable always returns a null value (0.0)."
     ::= { tnEntry 13 }


--
-- Internext Group
--

riInxSlot OBJECT-TYPE
     SYNTAX    INTEGER
     ACCESS    read-only
     STATUS    mandatory
		--% ALIAS "Slot Where Module Resides"
		--% GROUP Racal-InterLan-Internext-Group
	DESCRIPTION
		"The INTERNExT chassis slot in which the INX-NTS is located"
     ::= { riInternext 1 }

riInxBus OBJECT-TYPE
     SYNTAX    INTEGER {
			bus-a(2),
			bus-b(3),
			none(4)
			}
     ACCESS    read-only
     STATUS    mandatory
		--% ALIAS "Bus Connected to INX-NTS"
		--% GROUP Racal-InterLan-Internext-Group
	DESCRIPTION
		"The Ethernet bus connected to the INX-NTS in this slot."
     ::= { riInternext 2 }

riInxSlotConnectivityType OBJECT-TYPE
     SYNTAX    OBJECT IDENTIFIER
     ACCESS    read-only
     STATUS    mandatory
		--% ALIAS "Conn Module Type in Slot"
		--% GROUP Racal-InterLan-Internext-Group
	DESCRIPTION
		"The type of connectivity module attached to the INX-NTS
in this slot.  If this variable returns the object identifier
1.3.6.1.4.1.28.1.3.4.1.1.1, the connectivity module is an NTS-RJ45.
If this variable returns the object identifier
1.3.6.1.4.1.28.1.3.4.1.2.1, the connectivity module is an
NTS-TELCO."
     ::= { riInternext 4 }

riInxSlotConnectivityRev OBJECT-TYPE
     SYNTAX    DisplayString
     ACCESS    read-only
     STATUS    mandatory
		--% ALIAS "Conn Module Hardware Rev"
		--% GROUP Racal-InterLan-Internext-Group
	DESCRIPTION
		"The hardware revision level of the connectivity module
attached to the INX-NTS in this slot."
     ::= { riInternext 5 }

riInxSlotConnectivitySerialNumber OBJECT-TYPE
     SYNTAX    DisplayString
     ACCESS    read-only
     STATUS    mandatory
		--% ALIAS "Conn Module Serial Number"
		--% GROUP Racal-InterLan-Internext-Group
	DESCRIPTION
		"The serial number of the connectivity module attached
to the INX-NTS in this slot."
     ::= { riInternext 6 }

riInxSlotConnectivityState OBJECT-TYPE
     SYNTAX    INTEGER {
			enabled(2)
			}
     ACCESS    read-only
     STATUS    mandatory
		--% ALIAS "Conn Module Status"
		--% GROUP Racal-InterLan-Internext-Group
	DESCRIPTION
		"The state of the connectivity module attached to the
INX-NTS in this slot.  For the INX-NTS, this variable always
returns enabled(2)."
     ::= { riInternext 7 }

riInxSlotConnectivityBus OBJECT-TYPE
     SYNTAX    INTEGER {
			other(3)
			}
     ACCESS    read-only
     STATUS    mandatory
		--% ALIAS "Bus Connected to Conn Module"
		--% GROUP Racal-InterLan-Internext-Group
	DESCRIPTION
		"The bus connected to the connectivity module in this
slot.

Because the connectivity module is connected to the INX-NTS logic
module, rather than to the internal chassis buses, this variable
always returns other(3)."
     ::= { riInternext 8 }

riInxSlotConnectivityMedia OBJECT-TYPE
     SYNTAX    INTEGER {
			other(3)
			}
     ACCESS    read-only
     STATUS    mandatory
		--% ALIAS "Conn Module Media Type"
		--% GROUP Racal-InterLan-Internext-Group
	DESCRIPTION
		"The Ethernet media type setting for the connectivity
module in this slot.

This information is not relevant to the INX-NTS connectivity
module, so this variable always returns other(3)."
     ::= { riInternext 9 }

riInxChassisType OBJECT-TYPE
     SYNTAX    OBJECT IDENTIFIER
     ACCESS    read-only
     STATUS    mandatory
		--% ALIAS "Chassis Type"
		--% GROUP Racal-InterLan-Internext-Group
	DESCRIPTION
		"The type of chassis (i.e., 3-slot or 12-slot) in which
the INX-NTS is located."
     ::= { riInternext 10 }


--
-- Racal InterLan Threshold Group
--
riThCount OBJECT-TYPE
     SYNTAX    Gauge
     ACCESS    read-only
     STATUS    mandatory
		--% ALIAS "Active Entries in Thresh Table"
		--% GROUP Racal-InterLan-Threshold-Group
	DESCRIPTION
		"the number of active entries in the threshold table."
     ::= { riThresh 1 }

riThMaxCount OBJECT-TYPE
     SYNTAX    INTEGER 
     ACCESS    read-only
     STATUS    mandatory
		--% ALIAS "Max Allowed Active Thresholds"
		--% GROUP Racal-InterLan-Threshold-Group
	DESCRIPTION
		"The maximum number of active thresholds allowed."
     ::= { riThresh 2 }

riThUniqueIndex OBJECT-TYPE
     SYNTAX    INTEGER
     ACCESS    read-write
     STATUS    mandatory
		--% ALIAS "Create/Read Threshold Entry"
		--% GROUP Racal-InterLan-Threshold-Group
	DESCRIPTION
		"Setting this variable creates a new entry in the
Threshold table.  You must type a number for the entry when you set
this variable, but the INX-NTS assigns the actual entry number;
that number is the one returned in the response to the set command. 
If you read this variable, it returns the number of the most
recently generated threshold entry.  Each threshold entry must have
a unique index number, but the number assigned to an entry can be
reused after you have deleted it."
     ::= { riThresh 3 }

riThInterval OBJECT-TYPE
     SYNTAX    INTEGER
     ACCESS    read-write
     STATUS    mandatory
		--% ALIAS "How Often Thresholds Checked"
		--% GROUP Racal-InterLan-Threshold-Group
	DESCRIPTION
		"How often, in seconds, thresholds exceeded are checked. 
To  disable threshold checking, set this variable to 0."
     ::= { riThresh 4 }

--
-- Threshold Table
--

riThTable OBJECT-TYPE
     SYNTAX    SEQUENCE OF RiThEntry
     ACCESS    not-accessible
     STATUS    mandatory
		--% ALIAS "Threshold Table"
	DESCRIPTION
		"A table containing information about the thresholds that
have been set.

You cannot access this variable; it is only a table marker in the
MIB."
     ::={ riThresh 5 }

riThEntry OBJECT-TYPE
     SYNTAX    RiThEntry
     ACCESS    not-accessible
     STATUS    mandatory
		--% ALIAS "Threshold Table Entry"
	DESCRIPTION
		"An entry in the Threshold table.  (See the previous
variable, Threshold Table, for an explanation of this table).

You cannot access this variable; it is only a table marker in the
MIB.  The following variables are entries in the table:

	Threshold Table Index
	Threshold Status
	Threshold Object ID
	Threshold Value
	Threshold Hysteresis
	Direction of Approach to Thresh
	Threshold Trigger Count
	Threshold Community Name
	Threshold Eth Addr Destination
	Threshold IP Addr Destination"

	INDEX	{ riThIndex }
     ::= { riThTable 1 }

RiThEntry ::= SEQUENCE {
          riThIndex
               INTEGER,
          riThStatus
               INTEGER,
	  riThObject
	       OBJECT IDENTIFIER,
	  riThThreshold
		INTEGER,
	  riThHysteresis
		INTEGER,
	  riThDirection
		INTEGER,
	  riThTriggeredCount
		Counter,
	  riThCommunity
		OCTET STRING,
	  riThPhysDestination
		OCTET STRING,
	  riThIPDestination
		IpAddress
          }                        

riThIndex OBJECT-TYPE
     SYNTAX    INTEGER
     ACCESS    read-only
     STATUS    mandatory
		--% ALIAS "Threshold Table Index"
		--% GROUP Threshold-Table
	DESCRIPTION
		"A unique value for each threshold."
     ::= { riThEntry 1 }

riThStatus OBJECT-TYPE
     SYNTAX    INTEGER {
			delete(1),
			unset(2),
			armed(3),
			safety(4)
			}
     ACCESS    read-write
     STATUS    mandatory
		--% ALIAS "Threshold Status"
		--% GROUP Threshold-Table
	DESCRIPTION
		"The current status of the threshold.

o delete(1) deletes the threshold entry specified.
o unset(2) means that the threshold is newly created, currently
  being configured, or disabled.
o armed(3) means that the threshold is active and generates a trap
  PDU when it is triggered.
o safety(4) means that the threshold is active, but does not
  generate trap PDUs."
     ::= { riThEntry 2 }

riThObject OBJECT-TYPE
     SYNTAX    OBJECT IDENTIFIER
     ACCESS    read-write
     STATUS    mandatory
		--% ALIAS "Threshold Object ID"
		--% GROUP Threshold-Table
	DESCRIPTION
		"The complete object identifier of the variable on which
this threshold is set.

Threshold Object ID can be set only for Counter or Gauge variables. 
If you attempt to set a threshold for a variable of any other type,
you receive a badValue error."
     ::= { riThEntry 3 }

riThThreshold OBJECT-TYPE
     SYNTAX    INTEGER
     ACCESS    read-write
     STATUS    mandatory
		--% ALIAS "Threshold Value"
		--% GROUP Threshold-Table
	DESCRIPTION
		"The threshold value for the variable identified by
Threshold Object ID.  If this particular variable is a gauge, then
whenever its value rises above or drops below (depending on the
setting of the Direction of Approach to Thresh variable) the value
of Threshold Value, the threshold is considered to have been
triggered.  If this particular variable is a counter, then whenever
its value increments by the value of Threshold Value, the threshold
is considered to have been triggered."
     ::= { riThEntry 4 }

riThHysteresis OBJECT-TYPE
     SYNTAX    INTEGER
     ACCESS    read-write
     STATUS    mandatory
		--% ALIAS "Threshold Hysteresis"
		--% GROUP Threshold-Table
	DESCRIPTION
		"The hysteresis value for the threshold.  After a
variable's threshold is triggered, the value of the variable must
either drop below or rise above a certain value (depending on the
setting of the Direction of Approach to Thresh variable), the
hysteresis, before another trigger can be recognized.

For example, if you set the threshold for module temperature to 80,
the threshold is triggered the first time the temperature rises
above 80.  If you also set the hysteresis for this threshold to 60,
the threshold will only be triggered again if the temperature drops
below 60, and then rises past 80.  If the temperature drops from
80 to 70, and then goes back to 80, the threshold is not triggered.

If the hysteresis value is less than the threshold value, the
variable's value must drop below the hysteresis before another
trigger is recognized.  If the hysteresis value is greater than the
threshold value, the variable's value must rise above the
hysteresis before another trigger is recognized.

The value of the hysteresis depends on the value of the threshold
and whether the value of the variable is rising or falling;
therefore, set this variable in conjunction with both the Threshold
Value and Direction of Approach to Thresh variables.

This variable is relevant only to thresholds set on Gauge
variables."
     ::= { riThEntry 5 }

riThDirection OBJECT-TYPE
     SYNTAX    INTEGER {
			up(1),
			down(2)
			}
     ACCESS    read-write
     STATUS    mandatory
		--% ALIAS "Direction of Approach to Thresh"
		--% GROUP Threshold-Table
	DESCRIPTION
		"The direction in which a change in a Gauge variable's
value causes a threshold to trigger.

If its direction is up, a trigger occurs when the variable's value
rises above the threshold value.  In this case, the hysteresis must
be less than or equal to the threshold value.

If its direction is down, a trigger occurs when the variable's
value falls below the threshold value.  In this case, the
hysteresis must be greater than or equal to the threshold value.

This variable is relevant only to thresholds set on Gauge
variables."
     ::= { riThEntry 6 }

riThTriggeredCount OBJECT-TYPE
     SYNTAX    Counter
     ACCESS    read-only
     STATUS    mandatory
		--% ALIAS "Threshold Trigger Count"
		--% GROUP Threshold-Table
	DESCRIPTION
		"The number of times that this threshold has been
triggered."
     ::= { riThEntry 7 }

riThCommunity OBJECT-TYPE
     SYNTAX    OCTET STRING
     ACCESS    read-write
     STATUS    mandatory
		--% ALIAS "Threshold Community Name"
		--% GROUP Threshold-Table
	DESCRIPTION
		"The community name to place in the authentication header
of the trap PDU.  This variable specifies the community to which
the trap is to be sent when a threshold is triggered."
     ::= { riThEntry 8 }

riThPhysDestination OBJECT-TYPE
     SYNTAX    OCTET STRING
     ACCESS    read-write
     STATUS    mandatory
		--% ALIAS "Threshold Eth Addr Destination"
		--% GROUP Threshold-Table
	DESCRIPTION
		"The Ethernet address of the node to which the trap is
to be sent when the threshold is triggered."
     ::= { riThEntry 9 }

riThIPDestination OBJECT-TYPE
     SYNTAX    IpAddress
     ACCESS    read-write
     STATUS    mandatory
		--% ALIAS "Threshold IP Addr Destination"
		--% GROUP Threshold-Table
	DESCRIPTION
		"The IP address of the node to which the trap is to be
sent when the threshold is triggered."
     ::= { riThEntry 10 }

--
-- Racal InterLan Rate Group
--

riRateTxSingleCollisionFrames OBJECT-TYPE
     SYNTAX    Gauge
     ACCESS    read-only
     STATUS    mandatory
		--% ALIAS "Single Collision Frame Rate"
		--% GROUP Racal-InterLan-Rate-Group
	DESCRIPTION
		"The rate of frames that were successfully transmitted
after experiencing one and only one collision.

This variable corresponds to the Single Collisions Transmitted
variable in the dot3 group."
     ::= { riTsRates 1 }

riRateTxMultipleCollisionFrames OBJECT-TYPE
     SYNTAX    Gauge
     ACCESS    read-only
     STATUS    mandatory
		--% ALIAS "Multiple Collision Frame Rate"
		--% GROUP Racal-InterLan-Rate-Group
	DESCRIPTION
		"The rate of frames that were successfully transmitted
after experiencing more than one collision.

This variable corresponds to the Multiple Collisions Xmitted
variable in the dot3 group."
     ::= { riTsRates 2 }

riRateTxDeferredTransmissions OBJECT-TYPE
     SYNTAX    Gauge 
     ACCESS    read-only
     STATUS    mandatory
		--% ALIAS "Deferred Transmission Rate"
		--% GROUP Racal-InterLan-Rate-Group
	DESCRIPTION
		"The rate of times the INX-NTS deferred transmission of
data because it sensed traffic on the network.  Because the INX-NTS
does not record deferrals, this variable always returns 0.

This variable corresponds to the Transmissions Deferred variable
in the dot3 group."
     ::= { riTsRates 3 }

riRateTxLateCollisions OBJECT-TYPE
     SYNTAX    Gauge 
     ACCESS    read-only
     STATUS    mandatory
		--% ALIAS "Late Collision Rate"
		--% GROUP Racal-InterLan-Rate-Group
	DESCRIPTION
		"The rate of times that a collision has been detected on
this bus later than 512 bit times from frame start.  This count is
not maintained by the INX-NTS, so this variable always returns 0.

This variable corresponds to the Late Collisions Detected variable
in the dot3 group."
     ::= { riTsRates 4 }

riRateTxInternalMACTransmitErrors OBJECT-TYPE
     SYNTAX    Gauge
     ACCESS    read-only
     STATUS    mandatory
		--% ALIAS "Internal MAC Xmit Error Rate"
		--% GROUP Racal-InterLan-Rate-Group
	DESCRIPTION
		"The rate of frames the interface could not transmit
because of an internal MAC sublayer transmit error.

This variable corresponds to the MAC Transmit Errors variable in
the dot3 group."
     ::= { riTsRates 5 }

riRateTxCarrierSenseErrors OBJECT-TYPE
     SYNTAX    Gauge
     ACCESS    read-only
     STATUS    mandatory
		--% ALIAS "Carrier Sense Error Rate"
		--% GROUP Racal-InterLan-Rate-Group
	DESCRIPTION
		"The rate of times that the carrier-sense condition was
lost or never asserted when the INX-NTS attempted to transmit a
frame on the interface.

This variable corresponds to the Carrier Sense Errors variable in
the dot3 group."
     ::= { riTsRates 6 }

riRateTxExcessiveDeferrals OBJECT-TYPE
     SYNTAX    Gauge
     ACCESS    read-only
     STATUS    mandatory
		--% ALIAS "Excessive Deferral Rate"
		--% GROUP Racal-InterLan-Rate-Group
	DESCRIPTION
		"The rate of frames the INX-NTS deferred transmitting for
an excessive period of time.  Because the INX-NTS interface does
not record deferrals, this variable always returns 0.

This variable corresponds to the Deferred Frames variable in the
dot3 group."
     ::= { riTsRates 7 }

riRateRxInternalMACReceiveErrors OBJECT-TYPE
     SYNTAX    Gauge
     ACCESS    read-only
     STATUS    mandatory
		--% ALIAS "Internl MAC Receive Error Rate"
		--% GROUP Racal-InterLan-Rate-Group
	DESCRIPTION
		"The rate of frames the interface could not receive
because of an internal MAC sublayer receive error.

This variable corresponds to the MAC Errors Received variable in
the dot3 group."
     ::= { riTsRates 8 }

riRateRxFCSErrors OBJECT-TYPE
     SYNTAX    Gauge
     ACCESS    read-only
     STATUS    mandatory
		--% ALIAS "FCS Error Rate"
		--% GROUP Racal-InterLan-Rate-Group
	DESCRIPTION
		"The rate of frames received on the interface that are
an integral number of octets in length (i.e., the number of bits
they contain is a multiple of eight) that do not pass the FCS
check, indicating that the frames were corrupted during
transmission.

This variable corresponds to the FCS Errored Frames Received
variable in the dot3 group."
     ::= { riTsRates 9 }

riRateRxAlignmentErrors OBJECT-TYPE
     SYNTAX    Gauge
     ACCESS    read-only
     STATUS    mandatory
		--% ALIAS "Alignment Error Rate"
		--% GROUP Racal-InterLan-Rate-Group
	DESCRIPTION
		"The rate of frames received on the interface that are
not an integral number of octets in length (i.e., the number of
bits they contain is not a multiple of eight) and do not pass the
FCS check.  This indicates that the frames were corrupted during
transmission.

This variable corresponds to the Nonaligned Frames Recd variable
in the dot3 group."
     ::= { riTsRates 10 }

riRateRxInRangeLengthErrors OBJECT-TYPE
     SYNTAX    Gauge 
     ACCESS    read-only
     STATUS    mandatory
		--% ALIAS "In-Range Length Error Rate"
		--% GROUP Racal-InterLan-Rate-Group
	DESCRIPTION
		"The rate of in-range length errors received.  IEEE 802.3
frames contain a length field, indicating the length of the frame. 
If the value in the length field and the actual length of the frame
do not match, even if the length of the frame is within 802.3
parameters, the receiving device returns an in-range error.  The
INX-NTS receives Ethernet frames that do not have a length field. 
It therefore cannot detect this error, and this variable always
returns 0.

This variable corresponds to the In-Range Length Errors Recd
variable in the dot3 group."
     ::= { riTsRates 11 }

riRateRxOutofRangeLengthFields OBJECT-TYPE
     SYNTAX    Gauge 
     ACCESS    read-only
     STATUS    mandatory
		--% ALIAS "Out of Range Length Field Rate"
		--% GROUP Racal-InterLan-Rate-Group
	DESCRIPTION
		"The rate of out-of-range length errors received.  IEEE
802.3 frames contain a length field, indicating the length of the
frame.  If the length of the frame is outside 802.3 parameters, the
receiving device returns an out-of-range error.  The INX-NTS
receives Ethernet frames that do not have a length field.  It
therefore cannot detect this error, and this variable always
returns 0.

This variable corresponds to the Out-Range Length Errors Recd
variable in the dot3 group."
     ::= { riTsRates 12 }

riRateRxFrameTooLongs OBJECT-TYPE
     SYNTAX    Gauge
     ACCESS    read-only
     STATUS    mandatory
		--% ALIAS "Frame Too Long Rate"
		--% GROUP Racal-InterLan-Rate-Group
	DESCRIPTION
		"The rate of frames received on the interface that exceed
the maximum permitted frame size, i.e., 1012 octets.

This variable corresponds to the Too Long Frames Recd variable in
the dot3 group."
     ::= { riTsRates 13 }

END
