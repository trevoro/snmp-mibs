Wellfleet-PPP-MIB DEFINITIONS ::= BEGIN

-- Created by mdl2asn version 3.1
-- Creation date: Wed Aug 30 16:46:33 EDT 1995


    IMPORTS

      IpAddress, Counter, Gauge
        FROM RFC1155-SMI
      OBJECT-TYPE
        FROM RFC-1212
      DisplayString
        FROM RFC1213-MIB
      wfPppGroup
        FROM Wellfleet-COMMON-MIB;


    wfPppLineTable OBJECT-TYPE
        SYNTAX	SEQUENCE OF WfPppLineEntry
        ACCESS	not-accessible
        STATUS	mandatory
        DESCRIPTION
                "The Wellfleet PPP Line Configuration Table containing
                attributes dealing with the link layer and the Link Control
                Protocol (LCP)"
        ::= { wfPppGroup 1 }

    wfPppLineEntry OBJECT-TYPE
        SYNTAX	WfPppLineEntry
        ACCESS	not-accessible
        STATUS	mandatory
        DESCRIPTION
                "per Wellfleet PPP line configuration parameters
                and counters"
        INDEX	{ wfPppLineLineNumber,
    		  wfPppLineLLIndex }
        ::= { wfPppLineTable 1 }

    WfPppLineEntry ::= SEQUENCE {
    	    wfPppLineDelete
    		INTEGER,
    	    wfPppLineDisable
    		INTEGER,
    	    wfPppLineState
    		INTEGER,
    	    wfPppLineLineNumber
    		INTEGER,
    	    wfPppLineLLIndex
    		INTEGER,
    	    wfPppLineLcpCurrentState
    		INTEGER,
    	    wfPppLineRestartTimer
    		INTEGER,
    	    wfPppLineEchoRequestFreq
    		INTEGER,
    	    wfPppLineEchoReplyLoss
    		INTEGER,
    	    wfPppLineMaxConfReq
    		INTEGER,
    	    wfPppLineMaxTermReq
    		INTEGER,
    	    wfPppLineMaxConfFail
    		INTEGER,
    	    wfPppLineMagicNumber
    		Counter,
    	    wfPppLineMru
    		INTEGER,
    	    wfPppLineLocalAuthProtocol
    		INTEGER,
    	    wfPppLineRemoteAuthProtocol
    		INTEGER,
    	    wfPppLineLocalPapId
    		DisplayString,
    	    wfPppLineLocalPapPassword
    		DisplayString,
    	    wfPppLineRemotePapId
    		DisplayString,
    	    wfPppLineRemotePapPassword
    		DisplayString,
    	    wfPppLineLQProtocol
    		INTEGER,
    	    wfPppLineDisableRemoteLQRTimer
    		INTEGER,
    	    wfPppLineCfgLQRRptPrd
    		INTEGER,
    	    wfPppLineLQRRptPrd
    		INTEGER,
    	    wfPppLineCfgInboundQuality
    		INTEGER,
    	    wfPppLineInboundQuality
    		INTEGER,
    	    wfPppLineCfgOutboundQuality
    		INTEGER,
    	    wfPppLineOutboundQuality
    		INTEGER,
    	    wfPppLineOutLQRs
    		Counter,
    	    wfPppLineInLQRs
    		Counter,
    	    wfPppLineChapSecret
    		DisplayString,
    	    wfPppLinePapFallbackDisable
    		INTEGER,
    	    wfPppLineChapLocalName
    		DisplayString,
    	    wfPppLineChapRemoteName
    		DisplayString,
    	    wfPppLineChapPeriodicTimer
    		INTEGER,
    	    wfPppLineBadPackets
    		Counter,
    	    wfPppLineLastBadPacket
    		OCTET STRING,
    	    wfPppLineLevelPktsIn
    		Counter,
    	    wfPppLineAllowPapReject
    		INTEGER,
	    wfPppLineActiveCct
		INTEGER,
	    wfPppLineCfgAsyncMap
		Gauge,
	    wfPppLineActualAsyncMap
		Gauge,
    	    wfPppLineAuthTimer
    		INTEGER,
    	    wfPppLineConvergenceTimer
    		INTEGER,
            wfPppLineMagicNumDisable
                INTEGER,
	    wfPppLineMyLinkDiscr
	        INTEGER,
	    wfPppLinePeerLinkDiscr
	        INTEGER,
            wfPppLineCfgMru
                INTEGER,
            wfPppLineRfc1661Compliance
                INTEGER,
            wfPppLineLqmCurrentState
                INTEGER
        }

    wfPppLineDelete OBJECT-TYPE
        SYNTAX	INTEGER {
    		    created(1),
    		    deleted(2)
    		}
        ACCESS	read-write
        STATUS	mandatory
        DESCRIPTION
                "Create/Delete parameter"
        DEFVAL	{ created }
        ::= { wfPppLineEntry 1 }

    wfPppLineDisable OBJECT-TYPE
        SYNTAX	INTEGER {
    		    enabled(1),
    		    disabled(2)
    		}
        ACCESS	read-write
        STATUS	mandatory
        DESCRIPTION
                "Enable/Disable parameter -- Generates
                Open/Close events to the LCP FSM"
        DEFVAL	{ enabled }
        ::= { wfPppLineEntry 2 }

    wfPppLineState OBJECT-TYPE
        SYNTAX	INTEGER {
    		    up(1),
    		    down(2),
    		    init(3),
                    loopedback(4),
                    notpresent(20)
    		}
        ACCESS	read-only
        STATUS	mandatory
        DESCRIPTION
                "PPP state variable, Not Present, Init, Down, Up"
        DEFVAL	{ notpresent }
        ::= { wfPppLineEntry 3 }

    wfPppLineLineNumber OBJECT-TYPE
        SYNTAX	INTEGER
        ACCESS	read-only
        STATUS	mandatory
        DESCRIPTION
                "Instance identifier. This is the line number assigned
                to the driver PPP is running on top of"
        ::= { wfPppLineEntry 4 }

    wfPppLineLLIndex OBJECT-TYPE
        SYNTAX	INTEGER
        ACCESS	read-only
        STATUS	mandatory
        DESCRIPTION
                "Instance identifier. This is the lower layer index
                presented to PPP by the layer immediately below it
                on the protocol stack. If the lower layer is a driver,
                the index will be 0."
        ::= { wfPppLineEntry 5 }

    wfPppLineLcpCurrentState OBJECT-TYPE
        SYNTAX	INTEGER {
    		    starting(1),
    		    closed(2),
    		    stopped(3),
    		    closing(4),
    		    stopping(5),
    		    reqsent(6),
    		    ackrcvd(7),
    		    acksent(8),
    		    opened(9)
    		}
        ACCESS	read-only
        STATUS	mandatory
        DESCRIPTION
                "the current state of the LCP Finite State Machine"
        ::= { wfPppLineEntry 6 }

    wfPppLineRestartTimer OBJECT-TYPE
        SYNTAX	INTEGER(1..1000)
        ACCESS	read-write
        STATUS	mandatory
        DESCRIPTION
                "value for Restart timer in seconds"
        DEFVAL	{ 3 }
        ::= { wfPppLineEntry 7 }

    wfPppLineEchoRequestFreq OBJECT-TYPE
        SYNTAX	INTEGER
        ACCESS	read-write
        STATUS	mandatory
        DESCRIPTION
                "value for Echo-Request frequency - number of seconds
                between transmission of Echo-Request packets"
        ::= { wfPppLineEntry 8 }

    wfPppLineEchoReplyLoss OBJECT-TYPE
        SYNTAX	INTEGER(1..100)
        ACCESS	read-write
        STATUS	mandatory
        DESCRIPTION
                "value for Echo-Reply acceptable loss - number of
                unacknowledged Echo-Reply packets counted before
                declaring the link down"
        DEFVAL	{ 3 }
        ::= { wfPppLineEntry 9 }

    wfPppLineMaxConfReq OBJECT-TYPE
        SYNTAX	INTEGER(0..100000)
        ACCESS	read-write
        STATUS	mandatory
        DESCRIPTION
                "value for maximum Configure-Requests - number of
                Configure-Request packets sent without receiving a
                valid Configure-Ack, Configure-Nak or Configure-Reject
                before assuming peer is unable to respond"
        DEFVAL	{ 10 }
        ::= { wfPppLineEntry 10 }

    wfPppLineMaxTermReq OBJECT-TYPE
        SYNTAX	INTEGER(0..100)
        ACCESS	read-write
        STATUS	mandatory
        DESCRIPTION
                "value for maximum Terminate-Requests - number of
                Terminate-Request packets sent without receiving a
                Terminate-Ack before assuming peer is unable to respond"
        DEFVAL	{ 2 }
        ::= { wfPppLineEntry 11 }

    wfPppLineMaxConfFail OBJECT-TYPE
        SYNTAX	INTEGER(0..100)
        ACCESS	read-write
        STATUS	mandatory
        DESCRIPTION
                "value for maximum configuration failure count - number of
                Configure-Nak packets sent without sending a
                Configure-Ack before assuming configuration is unable to
                converge"
        DEFVAL	{ 10 }
        ::= { wfPppLineEntry 12 }

    wfPppLineMagicNumber OBJECT-TYPE
        SYNTAX	Counter
        ACCESS	read-only
        STATUS	mandatory
        DESCRIPTION
                "the Magic Number being used on this line"
        ::= { wfPppLineEntry 13 }

    wfPppLineMru OBJECT-TYPE
        SYNTAX	INTEGER
        ACCESS	read-only
        STATUS	mandatory
        DESCRIPTION
                "this is the MRU being used on the line (in both
                directions)"
        ::= { wfPppLineEntry 14 }

    wfPppLineLocalAuthProtocol OBJECT-TYPE
        SYNTAX	INTEGER {
    		    passauth(49187),
    		    chap(49699),
    		    none(1)
    		}
        ACCESS	read-write
        STATUS	mandatory
        DESCRIPTION
                "this is the authorization protocol we require our peer
                to use on our side of the link"
        DEFVAL	{ none }
        ::= { wfPppLineEntry 15 }

    wfPppLineRemoteAuthProtocol OBJECT-TYPE
        SYNTAX	INTEGER {
    		    passauth(49187),
    		    none(1)
    		}
        ACCESS	read-only
        STATUS	mandatory
        DESCRIPTION
                "this is the authorization protocol our peer requires us
                to use on its side of the link"
        DEFVAL	{ none }
        ::= { wfPppLineEntry 16 }

    wfPppLineLocalPapId OBJECT-TYPE
        SYNTAX	DisplayString
        ACCESS	read-write
        STATUS	mandatory
        DESCRIPTION
                "our PAP id - our peer sends this to us in an
                Authenticate-Request message"
        ::= { wfPppLineEntry 17 }

    wfPppLineLocalPapPassword OBJECT-TYPE
        SYNTAX	DisplayString
        ACCESS	read-write
        STATUS	mandatory
        DESCRIPTION
                "our PAP password - our peer sends this to us in an
                Authenticate-Request message"
        ::= { wfPppLineEntry 18 }

    wfPppLineRemotePapId OBJECT-TYPE
        SYNTAX	DisplayString
        ACCESS	read-write
        STATUS	mandatory
        DESCRIPTION
                "our peer's PAP id - we send this to our
                peer in an Authenticate-Request message"
        ::= { wfPppLineEntry 19 }

    wfPppLineRemotePapPassword OBJECT-TYPE
        SYNTAX	DisplayString
        ACCESS	read-write
        STATUS	mandatory
        DESCRIPTION
                "our peer's PAP password - we send this to our
                peer in an Authenticate-Request message"
        ::= { wfPppLineEntry 20 }

    wfPppLineLQProtocol OBJECT-TYPE
        SYNTAX	INTEGER {
    		    linkqr(49189),
    		    none(1)
    		}
        ACCESS	read-write
        STATUS	mandatory
        DESCRIPTION
                "the Link Quality protocol we want to use"
        DEFVAL	{ none }
        ::= { wfPppLineEntry 21 }

    wfPppLineDisableRemoteLQRTimer OBJECT-TYPE
        SYNTAX	INTEGER {
    		    enabled(1),
    		    disabled(2)
    		}
        ACCESS	read-write
        STATUS	mandatory
        DESCRIPTION
                "enable/disable our peer's LQR timer - this allows
                for one side to maintain the timer while the
                other just responds to LQR packets"
        DEFVAL	{ enabled }
        ::= { wfPppLineEntry 22 }

    wfPppLineCfgLQRRptPrd OBJECT-TYPE
        SYNTAX	INTEGER(1..120)
        ACCESS	read-write
        STATUS	mandatory
        DESCRIPTION
                "this is the value in seconds between transmission
                of LQR packets (Reporting-Period) - it will be the
                same on both sides"
        DEFVAL	{ 3 }
        ::= { wfPppLineEntry 23 }

    wfPppLineLQRRptPrd OBJECT-TYPE
        SYNTAX	INTEGER
        ACCESS	read-only
        STATUS	mandatory
        DESCRIPTION
                "this is the Reporting-Period, in seconds, agreed upon
                during negotiation - we allow the peer to negotiate
                down from our configured period, our maximum, but not
                below 1 second"
        ::= { wfPppLineEntry 24 }

    wfPppLineCfgInboundQuality OBJECT-TYPE
        SYNTAX	INTEGER(0..100)
        ACCESS	read-write
        STATUS	mandatory
        DESCRIPTION
                "the percentage of packets sent by our peer that
                we've successfully received (over the last 5 LQR
                Reporting-Periods) - 100 indicates we won't tolerate
                any loss"
        DEFVAL	{ 90 }
        ::= { wfPppLineEntry 25 }

    wfPppLineInboundQuality OBJECT-TYPE
        SYNTAX	INTEGER
        ACCESS	read-only
        STATUS	mandatory
        DESCRIPTION
                "the current inbound quality"
        ::= { wfPppLineEntry 26 }

    wfPppLineCfgOutboundQuality OBJECT-TYPE
        SYNTAX	INTEGER(0..100)
        ACCESS	read-write
        STATUS	mandatory
        DESCRIPTION
                "the percentage of packets sent by us that our
                peer successfully received (over the last 5 LQR
                Reporting-Periods) - 100 indicates we won't tolerate
                any loss"
        DEFVAL	{ 90 }
        ::= { wfPppLineEntry 27 }

    wfPppLineOutboundQuality OBJECT-TYPE
        SYNTAX	INTEGER
        ACCESS	read-only
        STATUS	mandatory
        DESCRIPTION
                "the current inbound quality"
        ::= { wfPppLineEntry 28 }

    wfPppLineOutLQRs OBJECT-TYPE
        SYNTAX	Counter
        ACCESS	read-only
        STATUS	mandatory
        DESCRIPTION
                "the number of Link-Quality-Report packets we've
                transmitted"
        ::= { wfPppLineEntry 29 }

    wfPppLineInLQRs OBJECT-TYPE
        SYNTAX	Counter
        ACCESS	read-only
        STATUS	mandatory
        DESCRIPTION
                "the number of Link-Quality-Report packets we've
                received"
        ::= { wfPppLineEntry 30 }

    wfPppLineChapSecret OBJECT-TYPE
        SYNTAX	DisplayString
        ACCESS	read-write
        STATUS	mandatory
        DESCRIPTION
                "this CHAP secret MUST be the same on both sides of
                the link if CHAP is used as the Authentication
                protocol"
        ::= { wfPppLineEntry 31 }

    wfPppLinePapFallbackDisable OBJECT-TYPE
        SYNTAX	INTEGER {
    		    disabled(2),
    		    enabled(1)
    		}
        ACCESS	read-write
        STATUS	mandatory
        DESCRIPTION
                "if an attempt to negotiate CHAP fails, enabling this
                allows a fallback to PAP"
        DEFVAL	{ disabled }
        ::= { wfPppLineEntry 32 }

    wfPppLineChapLocalName OBJECT-TYPE
        SYNTAX	DisplayString
        ACCESS	read-write
        STATUS	mandatory
        DESCRIPTION
                "This attribute is used to assign a local CHAP Name
                which is used to inform our peer of our identity,
                during WHOAMI processing"
        ::= { wfPppLineEntry 33 }

    wfPppLineChapRemoteName OBJECT-TYPE
        SYNTAX	DisplayString
        ACCESS	read-only
        STATUS	mandatory
        DESCRIPTION
                "This attribute is used to store our peer's CHAP Name
                which is used to learn our peer's identity,
                during WHOAMI processing"
        ::= { wfPppLineEntry 34 }

    wfPppLineChapPeriodicTimer OBJECT-TYPE
        SYNTAX	INTEGER
        ACCESS	read-write
        STATUS	mandatory
        DESCRIPTION
                "Timer for periodic CHAP in seconds. A time of
                0 disables Periodic CHAP. This timer value should
                long enough to allow CHAP to complete one phase
                before entering another."
        ::= { wfPppLineEntry 35 }

    wfPppLineBadPackets OBJECT-TYPE
        SYNTAX	Counter
        ACCESS	read-only
        STATUS	mandatory
        DESCRIPTION
                "These are packets not in correct PPP format"
        ::= { wfPppLineEntry 36 }

    wfPppLineLastBadPacket OBJECT-TYPE
        SYNTAX	OCTET STRING
        ACCESS	read-only
        STATUS	mandatory
        DESCRIPTION
                "This is the first 16 bytes of the last bad packet
                we received"
        ::= { wfPppLineEntry 37 }

    wfPppLineLevelPktsIn OBJECT-TYPE
        SYNTAX	Counter
        ACCESS	read-only
        STATUS	mandatory
        DESCRIPTION
                "This is the count of PPP link-level packets
                (such as Link Control Protocol or Compression
                       Control Protocl) which have been received."
        ::= { wfPppLineEntry 38 }

    wfPppLineAllowPapReject OBJECT-TYPE
        SYNTAX	INTEGER {
    		    enabled(1),
    		    disabled(2)
    		}
        ACCESS	read-write
        STATUS	mandatory
        DESCRIPTION
                "There are some peers that don't want us asking to
                be a PAP authenticator, so accept the Reject and
                remove PAP from the LCP Configure-Request if this
                is enabled."
        DEFVAL	{ disabled }
        ::= { wfPppLineEntry 39 }

    wfPppLineActiveCct OBJECT-TYPE
        SYNTAX	INTEGER
        ACCESS	read-only
        STATUS	mandatory
        DESCRIPTION
                "This is the circuit number that this PPP line belongs to
		 For the any switched lines, this will initially be -1 "
	DEFVAL   {65535}
        ::= { wfPppLineEntry 40 }

    wfPppLineCfgAsyncMap OBJECT-TYPE
	SYNTAX  Gauge
	ACCESS  read-write
	STATUS  mandatory
	DESCRIPTION
		"This is the initial seed value of 
		Async-Control-Character-Map which will be used 
		for LCP negotiations with the peer."
	DEFVAL  { 655360 }
	::= { wfPppLineEntry 41 }

    wfPppLineActualAsyncMap OBJECT-TYPE
	SYNTAX  Gauge
	ACCESS  read-only
	STATUS  mandatory
	DESCRIPTION
		"Async-Control-Character-Map used by the link to
		escape control characters in the data packet. This
		is the result of LCP negotiations with the peer."
	::= { wfPppLineEntry 42 }

    wfPppLineAuthTimer OBJECT-TYPE
        SYNTAX  INTEGER(1..1000)
        ACCESS  read-write
        STATUS  mandatory
        DESCRIPTION
                "value for Authentication timer in seconds"
        DEFVAL  { 10 }
        ::= { wfPppLineEntry 43 }

    wfPppLineConvergenceTimer OBJECT-TYPE
        SYNTAX  INTEGER(1..5000)
        ACCESS  read-write
        STATUS  mandatory
        DESCRIPTION
                "value for Convergence timer in seconds"
        DEFVAL  { 300 }
        ::= { wfPppLineEntry 44 }

     wfPppLineMagicNumDisable OBJECT-TYPE
        SYNTAX  INTEGER {
                    enabled(1),
                    disabled(2)
                }
        ACCESS  read-write
        STATUS  mandatory
        DESCRIPTION "Allows Magic Numbers to be disabled on this interface."
        DEFVAL  { enabled }
        ::= { wfPppLineEntry 45 }

    wfPppLineMyLinkDiscr OBJECT-TYPE
        SYNTAX  INTEGER(1..65535)
        ACCESS  read-write
        STATUS  mandatory
        DESCRIPTION
                "value of Link Discriminator of this endpoint"
        ::= { wfPppLineEntry 46 }

    wfPppLinePeerLinkDiscr OBJECT-TYPE
        SYNTAX  INTEGER(1..65535)
        ACCESS  read-write
        STATUS  mandatory
        DESCRIPTION
                "value of Link Discriminator of peer's endpoint"
        ::= { wfPppLineEntry 47 }

    wfPppLineCfgMru OBJECT-TYPE
        SYNTAX  INTEGER(1..4600)
        ACCESS  read-write
        STATUS  mandatory
        DESCRIPTION
                "this is the Configured MRU being used on the line"
        DEFVAL  { 1500 }
        ::= { wfPppLineEntry 48 }

    wfPppLineRfc1661Compliance OBJECT-TYPE
        SYNTAX  INTEGER {
                    enabled(1),
                    disabled(2)
                }
        ACCESS  read-write
        STATUS  mandatory
        DESCRIPTION
                "Enable/Disable parameter for RFC 1661 compliance"
        DEFVAL  { disabled }
        ::= { wfPppLineEntry 49 }

    wfPppLineLqmCurrentState OBJECT-TYPE
        SYNTAX  INTEGER {
                up(1),
                down(2)
            }
        ACCESS  read-only
        STATUS  mandatory
        DESCRIPTION
                "Indicates whether LQM is running on the line."
        DEFVAL  { down }
        ::= { wfPppLineEntry 50 }
 
    wfPppCircuitTable OBJECT-TYPE
        SYNTAX	SEQUENCE OF WfPppCircuitEntry
        ACCESS	not-accessible
        STATUS	mandatory
        DESCRIPTION
                "The Wellfleet PPP Circuit Configuration Table containing
                attributes dealing with the network layer and each
                Network Control Protocol (NCP)"
        ::= { wfPppGroup 2 }


    wfPppCircuitEntry OBJECT-TYPE
        SYNTAX	WfPppCircuitEntry
        ACCESS	not-accessible
        STATUS	mandatory
        DESCRIPTION
                "per Wellfleet circuit PPP configuration parameters and
                counters"
        INDEX	{ wfPppCircuitID }
        ::= { wfPppCircuitTable 1 }

    WfPppCircuitEntry ::= SEQUENCE {
    	    wfPppCircuitDelete
    		INTEGER,
    	    wfPppCircuitState
    		INTEGER,
    	    wfPppCircuitIpcpCurrentState
    		INTEGER,
    	    wfPppCircuitOsinlcpCurrentState
    		INTEGER,
    	    wfPppCircuitXnscpCurrentState
    		INTEGER,
    	    wfPppCircuitDncpCurrentState
    		INTEGER,
    	    wfPppCircuitAtcpCurrentState
    		INTEGER,
    	    wfPppCircuitIpxcpCurrentState
    		INTEGER,
    	    wfPppCircuitBncpCurrentState
    		INTEGER,
    	    wfPppCircuitVncpCurrentState
    		INTEGER,
    	    wfPppCircuitID
    		INTEGER,
    	    wfPppCircuitIpDisable
    		INTEGER,
    	    wfPppCircuitOsinlDisable
    		INTEGER,
    	    wfPppCircuitXnsDisable
    		INTEGER,
    	    wfPppCircuitDecnetDisable
    		INTEGER,
    	    wfPppCircuitAppletalkDisable
    		INTEGER,
    	    wfPppCircuitIpxDisable
    		INTEGER,
    	    wfPppCircuitBridgeDisable
    		INTEGER,
    	    wfPppCircuitVinesDisable
    		INTEGER,
    	    wfPppCircuitCfgLocalIpAddr
    		IpAddress,
    	    wfPppCircuitLocalIpAddr
    		IpAddress,
    	    wfPppCircuitCfgRemoteIpAddr
    		IpAddress,
    	    wfPppCircuitRemoteIpAddr
    		IpAddress,
    	    wfPppCircuitCfgIpxNetworkNumber
    		OCTET STRING,
    	    wfPppCircuitIpxNetworkNumber
    		OCTET STRING,
    	    wfPppCircuitIpxRemoteNodeNumber
    		OCTET STRING,
    	    wfPppCircuitCfgIpxRoutingProtocol
    		INTEGER,
    	    wfPppCircuitIpxRoutingProtocol
    		INTEGER,
    	    wfPppCircuitLocalIpxRouterName
    		DisplayString,
    	    wfPppCircuitRemoteIpxRouterName
    		DisplayString,
    	    wfPppCircuitIpxConfigComplete
    		INTEGER,
    	    wfPppCircuitCfgAtNetwork
    		INTEGER,
    	    wfPppCircuitAtNetwork
    		INTEGER,
    	    wfPppCircuitCfgLocalAtNode
    		INTEGER,
    	    wfPppCircuitLocalAtNode
    		INTEGER,
    	    wfPppCircuitCfgRemoteAtNode
    		INTEGER,
    	    wfPppCircuitRemoteAtNode
    		INTEGER,
    	    wfPppCircuitCfgAtRoutingProtocol
    		INTEGER,
    	    wfPppCircuitAtRoutingProtocol
    		INTEGER,
    	    wfPppCircuitCfgBridgeEnet
    		INTEGER,
    	    wfPppCircuitBridgeEnet
    		INTEGER,
    	    wfPppCircuitCfgBridgeFddi
    		INTEGER,
    	    wfPppCircuitBridgeFddi
    		INTEGER,
    	    wfPppCircuitCfgBridgeTokenRing
    		INTEGER,
    	    wfPppCircuitBridgeTokenRing
    		INTEGER,
    	    wfPppCircuitBadPackets
    		Counter,
    	    wfPppCircuitLastBadPacket
    		OCTET STRING,
    	    wfPppCircuitCcpCurrentState
    		INTEGER,
    	    wfPppCircuitCcpDisable
    		INTEGER,
    	    wfPppCircuitPppMode
    		INTEGER,
    	    wfPppCircuitMLFragPerm
    		INTEGER,
    	    wfPppCircuitExamPeriod
    		INTEGER,
    	    wfPppCircuitFullThreshold
    		INTEGER,
    	    wfPppCircuitPeriodsCng
    		INTEGER,
    	    wfPppCircuitPrefBwSlot
    		INTEGER,
    	    wfPppCircuitResvBwSlot
    		INTEGER,
    	    wfPppCircuitMLFragTriggerSize
    		INTEGER,
    	    wfPppCircuitMaxLinks
    		INTEGER,
    	    wfPppCircuitRecoverThreshold
    		INTEGER,
    	    wfPppCircuitPeriodsUnCng
    		INTEGER,
    	    wfPppCircuitHistory
    		DisplayString,
    	    wfPppCircuitDebugFlag
    		INTEGER,
            wfPppCircuitActualMode
                INTEGER,
    	    wfPppCircuitMaxBuffers
    		INTEGER,
    	    wfPppCircuitLinksConfigured
    		INTEGER,
    	    wfPppCircuitBacpDisable
    		INTEGER,
    	    wfPppCircuitBacpCurrentState
    		INTEGER,
    	    wfPppCircuitBacpNoPhoneNum
    		INTEGER,
    	    wfPppCircuitIpv6Disable
    		INTEGER,
    	    wfPppCircuitIpv6CurrentState
    		INTEGER,
    	    wfPppCircuitCcpType
    		INTEGER,
    	    wfPppCircuitCfgCcpOptions
    		INTEGER,
     	    wfPppCircuitCcpOptions
    		INTEGER,
   	    wfPppCircuitStacLZSCheckMode
    		INTEGER,
	    wfPppCircuitMLFragStrict
		INTEGER,	
            wfPppCircuitLampreyCompDisable
		INTEGER,	
            wfPppCircuitMsgLevel
                INTEGER,
	    wfPppCircuitType
		INTEGER,
	    wfPppCircuitWRCompatability
                INTEGER
        }

    wfPppCircuitDelete OBJECT-TYPE
        SYNTAX	INTEGER {
    		    created(1),
    		    deleted(2)
    		}
        ACCESS	read-write
        STATUS	mandatory
        DESCRIPTION
                "Create/Delete parameter"
        DEFVAL	{ created }
        ::= { wfPppCircuitEntry 1 }

    wfPppCircuitState OBJECT-TYPE
        SYNTAX	INTEGER {
    		    up(1),
    		    down(2),
    		    init(3),
    		    notpresent(4)
    		}
        ACCESS	read-only
        STATUS	mandatory
        DESCRIPTION
                "PPP state variable, Not Present, Init, Down, Up"
        DEFVAL	{ notpresent }
        ::= { wfPppCircuitEntry 2 }

    wfPppCircuitIpcpCurrentState OBJECT-TYPE
        SYNTAX	INTEGER {
    		    starting(1),
    		    closed(2),
    		    stopped(3),
    		    closing(4),
    		    stopping(5),
    		    reqsent(6),
    		    ackrcvd(7),
    		    acksent(8),
    		    opened(9)
    		}
        ACCESS	read-only
        STATUS	mandatory
        DESCRIPTION
                "the current state of the IPCP Finite State Machine"
        ::= { wfPppCircuitEntry 3 }

    wfPppCircuitOsinlcpCurrentState OBJECT-TYPE
        SYNTAX	INTEGER {
    		    starting(1),
    		    closed(2),
    		    stopped(3),
    		    closing(4),
    		    stopping(5),
    		    reqsent(6),
    		    ackrcvd(7),
    		    acksent(8),
    		    opened(9)
    		}
        ACCESS	read-only
        STATUS	mandatory
        DESCRIPTION
                "the current state of the OSINLCP Finite State Machine"
        ::= { wfPppCircuitEntry 4 }

    wfPppCircuitXnscpCurrentState OBJECT-TYPE
        SYNTAX	INTEGER {
    		    starting(1),
    		    closed(2),
    		    stopped(3),
    		    closing(4),
    		    stopping(5),
    		    reqsent(6),
    		    ackrcvd(7),
    		    acksent(8),
    		    opened(9)
    		}
        ACCESS	read-only
        STATUS	mandatory
        DESCRIPTION
                "the current state of the XNSCP Finite State Machine"
        ::= { wfPppCircuitEntry 5 }

    wfPppCircuitDncpCurrentState OBJECT-TYPE
        SYNTAX	INTEGER {
    		    starting(1),
    		    closed(2),
    		    stopped(3),
    		    closing(4),
    		    stopping(5),
    		    reqsent(6),
    		    ackrcvd(7),
    		    acksent(8),
    		    opened(9)
    		}
        ACCESS	read-only
        STATUS	mandatory
        DESCRIPTION
                "the current state of the DNCP Finite State Machine"
        ::= { wfPppCircuitEntry 6 }

    wfPppCircuitAtcpCurrentState OBJECT-TYPE
        SYNTAX	INTEGER {
    		    starting(1),
    		    closed(2),
    		    stopped(3),
    		    closing(4),
    		    stopping(5),
    		    reqsent(6),
    		    ackrcvd(7),
    		    acksent(8),
    		    opened(9)
    		}
        ACCESS	read-only
        STATUS	mandatory
        DESCRIPTION
                "the current state of the ATCP Finite State Machine"
        ::= { wfPppCircuitEntry 7 }

    wfPppCircuitIpxcpCurrentState OBJECT-TYPE
        SYNTAX	INTEGER {
    		    starting(1),
    		    closed(2),
    		    stopped(3),
    		    closing(4),
    		    stopping(5),
    		    reqsent(6),
    		    ackrcvd(7),
    		    acksent(8),
    		    opened(9)
    		}
        ACCESS	read-only
        STATUS	mandatory
        DESCRIPTION
                "the current state of the IPXCP Finite State Machine"
        ::= { wfPppCircuitEntry 8 }

    wfPppCircuitBncpCurrentState OBJECT-TYPE
        SYNTAX	INTEGER {
    		    starting(1),
    		    closed(2),
    		    stopped(3),
    		    closing(4),
    		    stopping(5),
    		    reqsent(6),
    		    ackrcvd(7),
    		    acksent(8),
    		    opened(9)
    		}
        ACCESS	read-only
        STATUS	mandatory
        DESCRIPTION
                "the current state of the BNCP Finite State Machine"
        ::= { wfPppCircuitEntry 9 }

    wfPppCircuitVncpCurrentState OBJECT-TYPE
        SYNTAX	INTEGER {
    		    starting(1),
    		    closed(2),
    		    stopped(3),
    		    closing(4),
    		    stopping(5),
    		    reqsent(6),
    		    ackrcvd(7),
    		    acksent(8),
    		    opened(9)
    		}
        ACCESS	read-only
        STATUS	mandatory
        DESCRIPTION
                "the current state of the VNCP Finite State Machine"
        ::= { wfPppCircuitEntry 10 }

    wfPppCircuitID OBJECT-TYPE
        SYNTAX	INTEGER(1..1023)
        ACCESS	read-only
        STATUS	mandatory
        DESCRIPTION
                "cct number for this instance"
        ::= { wfPppCircuitEntry 11 }

    wfPppCircuitIpDisable OBJECT-TYPE
        SYNTAX	INTEGER {
    		    enabled(1),
    		    disabled(2)
    		}
        ACCESS	read-write
        STATUS	mandatory
        DESCRIPTION
                "enable/disable IP Protocol - disabling generates
                a Close event to the IPCP FSM and consequently disallows
                IP traffic on this circuit"
        DEFVAL	{ disabled }
        ::= { wfPppCircuitEntry 12 }

    wfPppCircuitOsinlDisable OBJECT-TYPE
        SYNTAX	INTEGER {
    		    enabled(1),
    		    disabled(2)
    		}
        ACCESS	read-write
        STATUS	mandatory
        DESCRIPTION
                "enable/disable OSI Network Layer Protocol -
                disabling generates a Close event to the OSINLCP FSM
                and consequently disallows OSI traffic on this circuit"
        DEFVAL	{ disabled }
        ::= { wfPppCircuitEntry 13 }

    wfPppCircuitXnsDisable OBJECT-TYPE
        SYNTAX	INTEGER {
    		    enabled(1),
    		    disabled(2)
    		}
        ACCESS	read-write
        STATUS	mandatory
        DESCRIPTION
                "enable/disable XNS Protocol - disabling generates
                a Close event to the XNSCP FSM and consequently
                disallows XNS traffic on this circuit"
        DEFVAL	{ disabled }
        ::= { wfPppCircuitEntry 14 }

    wfPppCircuitDecnetDisable OBJECT-TYPE
        SYNTAX	INTEGER {
    		    enabled(1),
    		    disabled(2)
    		}
        ACCESS	read-write
        STATUS	mandatory
        DESCRIPTION
                "enable/disable DECnet Protocol - disabling generates
                a Close event to the DNCP FSM and consequently
                disallows DECnet traffic on this circuit"
        DEFVAL	{ disabled }
        ::= { wfPppCircuitEntry 15 }

    wfPppCircuitAppletalkDisable OBJECT-TYPE
        SYNTAX	INTEGER {
    		    enabled(1),
    		    disabled(2)
    		}
        ACCESS	read-write
        STATUS	mandatory
        DESCRIPTION
                "enable/disable AppleTalk Protocol - disabling generates
                a Close event to the ATCP FSM and consequently
                disallows AppleTalk traffic on this circuit"
        DEFVAL	{ disabled }
        ::= { wfPppCircuitEntry 16 }

    wfPppCircuitIpxDisable OBJECT-TYPE
        SYNTAX	INTEGER {
    		    enabled(1),
    		    disabled(2)
    		}
        ACCESS	read-write
        STATUS	mandatory
        DESCRIPTION
                "enable/disable IPX Protocol - disabling generates
                a Close event to the IPXCP FSM and consequently
                disallows IPX traffic on this circuit"
        DEFVAL	{ disabled }
        ::= { wfPppCircuitEntry 17 }

    wfPppCircuitBridgeDisable OBJECT-TYPE
        SYNTAX	INTEGER {
    		    enabled(1),
    		    disabled(2)
    		}
        ACCESS	read-write
        STATUS	mandatory
        DESCRIPTION
                "enable/disable the Bridge - disabling generates
                a Close event to the BNCP FSM and consequently
                disallows bridge traffic on this circuit"
        DEFVAL	{ disabled }
        ::= { wfPppCircuitEntry 18 }

    wfPppCircuitVinesDisable OBJECT-TYPE
        SYNTAX	INTEGER {
    		    enabled(1),
    		    disabled(2)
    		}
        ACCESS	read-write
        STATUS	mandatory
        DESCRIPTION
                "enable/disable Vines Protocol - disabling generates
                a Close event to the VNCP FSM and consequently
                disallows Vines traffic on this circuit"
        DEFVAL	{ disabled }
        ::= { wfPppCircuitEntry 19 }

    wfPppCircuitCfgLocalIpAddr OBJECT-TYPE
        SYNTAX	IpAddress
        ACCESS	read-write
        STATUS	mandatory
        DESCRIPTION
                "the IP address we're going to use"
        ::= { wfPppCircuitEntry 20 }

    wfPppCircuitLocalIpAddr OBJECT-TYPE
        SYNTAX	IpAddress
        ACCESS	read-only
        STATUS	mandatory
        DESCRIPTION
                "the IP address our peer wants us to use"
        ::= { wfPppCircuitEntry 21 }

    wfPppCircuitCfgRemoteIpAddr OBJECT-TYPE
        SYNTAX	IpAddress
        ACCESS	read-write
        STATUS	mandatory
        DESCRIPTION
                "the IP address we want our peer to use"
        ::= { wfPppCircuitEntry 22 }

    wfPppCircuitRemoteIpAddr OBJECT-TYPE
        SYNTAX	IpAddress
        ACCESS	read-only
        STATUS	mandatory
        DESCRIPTION
                "the IP address our peer wants to use"
        ::= { wfPppCircuitEntry 23 }

    wfPppCircuitCfgIpxNetworkNumber OBJECT-TYPE
        SYNTAX	OCTET STRING
        ACCESS	read-write
        STATUS	mandatory
        DESCRIPTION
                "the configured IPX Network Number to be used by
                both us and our peer"
        ::= { wfPppCircuitEntry 24 }

    wfPppCircuitIpxNetworkNumber OBJECT-TYPE
        SYNTAX	OCTET STRING
        ACCESS	read-only
        STATUS	mandatory
        DESCRIPTION
                "the result of IPX Network Number negotiation"
        ::= { wfPppCircuitEntry 25 }

    wfPppCircuitIpxRemoteNodeNumber OBJECT-TYPE
        SYNTAX	OCTET STRING
        ACCESS	read-write
        STATUS	mandatory
        DESCRIPTION
                "this is what we'll tell our peer to use for node
                number if it sends us a 0"
        ::= { wfPppCircuitEntry 26 }

    wfPppCircuitCfgIpxRoutingProtocol OBJECT-TYPE
        SYNTAX	INTEGER {
    		    ripsap(2)
    		}
        ACCESS	read-write
        STATUS	mandatory
        DESCRIPTION
                "the desired IPX Routing Protocol to be used on
                the link"
        DEFVAL	{ ripsap }
        ::= { wfPppCircuitEntry 27 }

    wfPppCircuitIpxRoutingProtocol OBJECT-TYPE
        SYNTAX	INTEGER
        ACCESS	read-only
        STATUS	mandatory
        DESCRIPTION
                "the negotiated IPX Routing Protocol to be used on
                the link"
        ::= { wfPppCircuitEntry 28 }

    wfPppCircuitLocalIpxRouterName OBJECT-TYPE
        SYNTAX	DisplayString
        ACCESS	read-write
        STATUS	mandatory
        DESCRIPTION
                "our IPX Router Name"
        ::= { wfPppCircuitEntry 29 }

    wfPppCircuitRemoteIpxRouterName OBJECT-TYPE
        SYNTAX	DisplayString
        ACCESS	read-only
        STATUS	mandatory
        DESCRIPTION
                "our peer's IPX Router Name"
        ::= { wfPppCircuitEntry 30 }

    wfPppCircuitIpxConfigComplete OBJECT-TYPE
        SYNTAX	INTEGER {
    		    true(1),
    		    false(2)
    		}
        ACCESS	read-only
        STATUS	mandatory
        DESCRIPTION
                "indicates whether or not IPXCP converged on all
                required options"
        ::= { wfPppCircuitEntry 31 }

    wfPppCircuitCfgAtNetwork OBJECT-TYPE
        SYNTAX	INTEGER
        ACCESS	read-write
        STATUS	mandatory
        DESCRIPTION
                "the configured AppleTalk network number - our
                peer must use the same number"
        ::= { wfPppCircuitEntry 32 }

    wfPppCircuitAtNetwork OBJECT-TYPE
        SYNTAX	INTEGER
        ACCESS	read-only
        STATUS	mandatory
        DESCRIPTION
                "the AppleTalk network number we agreed to use"
        ::= { wfPppCircuitEntry 33 }

    wfPppCircuitCfgLocalAtNode OBJECT-TYPE
        SYNTAX	INTEGER
        ACCESS	read-write
        STATUS	mandatory
        DESCRIPTION
                "the AppleTalk node number we're configured to use"
        ::= { wfPppCircuitEntry 34 }

    wfPppCircuitLocalAtNode OBJECT-TYPE
        SYNTAX	INTEGER
        ACCESS	read-only
        STATUS	mandatory
        DESCRIPTION
                "our AppleTalk node number after negotiation"
        ::= { wfPppCircuitEntry 35 }

    wfPppCircuitCfgRemoteAtNode OBJECT-TYPE
        SYNTAX	INTEGER
        ACCESS	read-write
        STATUS	mandatory
        DESCRIPTION
                "the AppleTalk node number we want our peer to use"
        ::= { wfPppCircuitEntry 36 }

    wfPppCircuitRemoteAtNode OBJECT-TYPE
        SYNTAX	INTEGER
        ACCESS	read-only
        STATUS	mandatory
        DESCRIPTION
                "our peer's AppleTalk node number after negotiation"
        ::= { wfPppCircuitEntry 37 }

    wfPppCircuitCfgAtRoutingProtocol OBJECT-TYPE
        SYNTAX	INTEGER {
    		    rtmp(1),
    		    aurp(2),
    		    abgp(3)
    		}
        ACCESS	read-write
        STATUS	mandatory
        DESCRIPTION
                "the desired AppleTalk Routing Protocol to be used on
                the link"
        DEFVAL	{ rtmp }
        ::= { wfPppCircuitEntry 38 }

    wfPppCircuitAtRoutingProtocol OBJECT-TYPE
        SYNTAX	INTEGER
        ACCESS	read-only
        STATUS	mandatory
        DESCRIPTION
                "the negotiated AppleTalk Routing Protocol to be used on
                the link"
        ::= { wfPppCircuitEntry 39 }

    wfPppCircuitCfgBridgeEnet OBJECT-TYPE
        SYNTAX	INTEGER {
    		    enabled(1),
    		    disabled(2)
    		}
        ACCESS	read-write
        STATUS	mandatory
        DESCRIPTION
                "allow/disallow Ethernet bridged frames"
        DEFVAL	{ enabled }
        ::= { wfPppCircuitEntry 40 }

    wfPppCircuitBridgeEnet OBJECT-TYPE
        SYNTAX	INTEGER {
    		    enabled(1),
    		    disabled(2)
    		}
        ACCESS	read-only
        STATUS	mandatory
        DESCRIPTION
                "result of bridge MAC type negotiation for
                Ethernet"
        ::= { wfPppCircuitEntry 41 }

    wfPppCircuitCfgBridgeFddi OBJECT-TYPE
        SYNTAX	INTEGER {
    		    enabled(1),
    		    disabled(2)
    		}
        ACCESS	read-write
        STATUS	mandatory
        DESCRIPTION
                "allow/disallow FDDI bridged frames"
        DEFVAL	{ enabled }
        ::= { wfPppCircuitEntry 42 }

    wfPppCircuitBridgeFddi OBJECT-TYPE
        SYNTAX	INTEGER {
    		    enabled(1),
    		    disabled(2)
    		}
        ACCESS	read-only
        STATUS	mandatory
        DESCRIPTION
                "result of bridge MAC type negotiation for
                FDDI"
        ::= { wfPppCircuitEntry 43 }

    wfPppCircuitCfgBridgeTokenRing OBJECT-TYPE
        SYNTAX	INTEGER {
    		    enabled(1),
    		    disabled(2)
    		}
        ACCESS	read-write
        STATUS	mandatory
        DESCRIPTION
                "allow/disallow Token Ring bridged frames"
        DEFVAL	{ enabled }
        ::= { wfPppCircuitEntry 44 }

    wfPppCircuitBridgeTokenRing OBJECT-TYPE
        SYNTAX	INTEGER {
    		    enabled(1),
    		    disabled(2)
    		}
        ACCESS	read-only
        STATUS	mandatory
        DESCRIPTION
                "result of bridge MAC type negotiation for
                Token Ring"
        ::= { wfPppCircuitEntry 45 }

    wfPppCircuitBadPackets OBJECT-TYPE
        SYNTAX	Counter
        ACCESS	read-only
        STATUS	mandatory
        DESCRIPTION
                "these are packets not in correct PPP format"
        ::= { wfPppCircuitEntry 46 }

    wfPppCircuitLastBadPacket OBJECT-TYPE
        SYNTAX	OCTET STRING
        ACCESS	read-only
        STATUS	mandatory
        DESCRIPTION
                "this is the first 16 bytes of the last bad packet
                we received"
        ::= { wfPppCircuitEntry 47 }

    wfPppCircuitCcpCurrentState OBJECT-TYPE
        SYNTAX	INTEGER {
    		    starting(1),
    		    closed(2),
    		    stopped(3),
    		    closing(4),
    		    stopping(5),
    		    reqsent(6),
    		    ackrcvd(7),
    		    acksent(8),
    		    opened(9)
    		}
        ACCESS	read-only
        STATUS	mandatory
        DESCRIPTION
                "the current state of the CCP Finite State Machine"
        ::= { wfPppCircuitEntry 48 }

    wfPppCircuitCcpDisable OBJECT-TYPE
        SYNTAX	INTEGER {
    		    enabled(1),
    		    disabled(2)
    		}
        ACCESS	read-write
        STATUS	mandatory
        DESCRIPTION
                "enable/disable compression - disabling generates
                a Close event to the CCP FSM and consequently
                disallows compression traffic on this circuit"
        DEFVAL	{ disabled }
        ::= { wfPppCircuitEntry 49 }

    wfPppCircuitPppMode OBJECT-TYPE
        SYNTAX	INTEGER {
    		    normal(1),
    		    nego(2),
    		    multilink(3),
    		    monitor(4),
    		    dynamic-monitor(5)
    		}
        ACCESS	read-write
        STATUS	mandatory
        DESCRIPTION
                "Pre 9.0 multilines can only negotiate LCP over 1 line. The
                exact line which LCP will occur on is unknown. So in order
                to handle this situation we will wait until we receive an
                LCP Request before we attempt to negotiate LCP by setting
                the mode to PPP_MODE_PEER_SOLICITED_LCP_NEGO. If we are using
                this line as a single PPP Line or we are sure our peer can
                handle LCP on all the members of the multiline, PPP_MODE_NORMAL
                should be selected.
                    Multilink is a PPP protocol extension which provides restoration
                    of packets which arrive out of sequence, a possibility with
                multiple lines.
                Multilink monitor, in conjunction with other configuration data
                    allows the throughput of a line to be monitored. Additional
                    lines can be brought into the bundle and taken down dynamically
                    in response to data traffic volume and other conditions."
        DEFVAL	{ normal }
        ::= { wfPppCircuitEntry 50 }

    wfPppCircuitMLFragPerm OBJECT-TYPE
        SYNTAX	INTEGER {
    		    permitted(1),
    		    prohibited(2)
    		}
        ACCESS	read-write
        STATUS	mandatory
        DESCRIPTION
                "This parameter allows interoperability with PPP Multilink
                implementations which do not allow fragmentation."
        DEFVAL	{ permitted }
        ::= { wfPppCircuitEntry 51 }

    wfPppCircuitExamPeriod OBJECT-TYPE
        SYNTAX	INTEGER(5..200)
        ACCESS	read-write
        STATUS	mandatory
        DESCRIPTION
                "This indicates the interval that the Multilink bundle should
                be polled for possible congestion.  This value is in
                tenths of a second"
        DEFVAL	{ 10 }
        ::= { wfPppCircuitEntry 52 }

    wfPppCircuitFullThreshold OBJECT-TYPE
        SYNTAX	INTEGER(10..2147483647)
        ACCESS	read-write
        STATUS	mandatory
        DESCRIPTION
                "This is the percentage of the theoretical maximum line
                throughput that must be reached or exceeded before the line is
                considered congested."
        DEFVAL	{ 70 }
        ::= { wfPppCircuitEntry 53 }

    wfPppCircuitPeriodsCng OBJECT-TYPE
        SYNTAX	INTEGER(1..100)
        ACCESS	read-write
        STATUS	mandatory
        DESCRIPTION
                "This is the number of consecutive periods where the line
                throughput is above the congestion threshold required to declare
                the line congested and attempt corrective action."
        DEFVAL	{ 10 }
        ::= { wfPppCircuitEntry 54 }

    wfPppCircuitPrefBwSlot OBJECT-TYPE
        SYNTAX	INTEGER
        ACCESS	read-write
        STATUS	mandatory
        DESCRIPTION
                "This is the preferred bandwidth slot.
                When lines are requested to be added to the Multilink bundle
                this parameter denotes the slot which is asked first."
        ::= { wfPppCircuitEntry 55 }

    wfPppCircuitResvBwSlot OBJECT-TYPE
        SYNTAX	INTEGER
        ACCESS	read-write
        STATUS	mandatory
        DESCRIPTION
                "This is the reserve bandwidth slot.
                When lines are requested to be added to the Multilink bundle
                this parameter denotes the slot which is asked if the preferred
                slot can not provide a line."
        ::= { wfPppCircuitEntry 56 }

    wfPppCircuitMLFragTriggerSize OBJECT-TYPE
        SYNTAX	INTEGER
        ACCESS	read-write
        STATUS	mandatory
        DESCRIPTION
                "This is the minimum size of a packet of which Multilink
                will fragment."
        DEFVAL	{ 256 }
        ::= { wfPppCircuitEntry 57 }

    wfPppCircuitMaxLinks OBJECT-TYPE
        SYNTAX	INTEGER(0..4)
        ACCESS	read-write
        STATUS	mandatory
        DESCRIPTION
                "This is the maximum number of links allowed in the Multilink
                bundle for this circuit at any one time."
        DEFVAL	{ 4 }
        ::= { wfPppCircuitEntry 58 }

    wfPppCircuitRecoverThreshold OBJECT-TYPE
        SYNTAX	INTEGER(10..2147483647)
        ACCESS	read-write
        STATUS	mandatory
        DESCRIPTION
                "This is the recovery threshold expressed as a percentage of the
                theoretical maximum bundle throughput.  The actual throughput must fall
                below this percentage in order for the BOD circuit to
                begin to remove lines from the Multilink bundle."
        DEFVAL	{ 50 }
        ::= { wfPppCircuitEntry 59 }

    wfPppCircuitPeriodsUnCng OBJECT-TYPE
        SYNTAX	INTEGER(1..100)
        ACCESS	read-write
        STATUS	mandatory
        DESCRIPTION
                "This parameter is used for recovery. Once a Multilink bundle has
                been declared as congested, this is the number of
                consecutive examination periods where the queue depth is
                below the recovery threshold value required to declare that the
                bundle is no longer congested."
        DEFVAL	{ 10 }
        ::= { wfPppCircuitEntry 60 }

    wfPppCircuitHistory OBJECT-TYPE
        SYNTAX	DisplayString
        ACCESS	read-only
        STATUS	mandatory
        DESCRIPTION
                "DEBUG parameter - This is the BOD history buffer."
        ::= { wfPppCircuitEntry 61 }

    wfPppCircuitDebugFlag OBJECT-TYPE
        SYNTAX	INTEGER
        ACCESS	read-write
        STATUS	mandatory
        DESCRIPTION
                "DEBUG parameter - This is the BOD Debug flag, used to control
                debug code for BOD."
        ::= { wfPppCircuitEntry 62 }

    wfPppCircuitActualMode OBJECT-TYPE
        SYNTAX  INTEGER {
                    normal(1),
                    multilink(3),
                    monitor(4),
                    inactive(20)
                }
        ACCESS  read-only
        STATUS  mandatory
        DESCRIPTION
                "This attribute is the actual ppp mode of the circuit after
                 LCP has negotiated.  "
        DEFVAL  { normal }
        ::= { wfPppCircuitEntry 63 }


    wfPppCircuitMaxBuffers OBJECT-TYPE
        SYNTAX  INTEGER(10..60)
        ACCESS  read-write
        STATUS  mandatory
        DESCRIPTION
                "This is the maximum number of stored buffers allowed in the
                 Multilink Receive logic for this circuit at any one time."
        DEFVAL  { 30 }
        ::= { wfPppCircuitEntry 64 }

    wfPppCircuitLinksConfigured OBJECT-TYPE
        SYNTAX  INTEGER(0..30)
        ACCESS  read-write
        STATUS  mandatory
        DESCRIPTION
                "This is the current number of lines configured for this
                 Multilink circuit."
        ::= { wfPppCircuitEntry 65 }

    wfPppCircuitBacpDisable OBJECT-TYPE
        SYNTAX  INTEGER {
                    enabled(1),
                    disabled(2)
                }
        ACCESS  read-write
        STATUS  mandatory
        DESCRIPTION
                "enable/disable BACP Protocol - disabling generates
                a Close event to the BACP FSM and consequently
                disallows BAP traffic on this circuit"
        DEFVAL  { disabled }
        ::= { wfPppCircuitEntry 66 }

    wfPppCircuitBacpCurrentState OBJECT-TYPE
        SYNTAX  INTEGER {
                    starting(1),
                    closed(2),
                    stopped(3),
                    closing(4),
                    stopping(5),
                    reqsent(6),
                    ackrcvd(7),
                    acksent(8),
                    opened(9)
                }
        ACCESS  read-only
        STATUS  mandatory
        DESCRIPTION
                "the current state of the BACP Finite State Machine"
        ::= { wfPppCircuitEntry 67 }

    wfPppCircuitBacpNoPhoneNum OBJECT-TYPE
        SYNTAX  INTEGER {
                    enabled(1),
                    disabled(2)
                }
        ACCESS  read-write
        STATUS  mandatory
        DESCRIPTION
                "enable/disable sending of the No-Phone-Number-Needed option
                 in BACP Call Request packets"
        DEFVAL  { disabled }
        ::= { wfPppCircuitEntry 68 }

    wfPppCircuitIpv6Disable OBJECT-TYPE
        SYNTAX	INTEGER {
    		    enabled(1),
    		    disabled(2)
    		}
        ACCESS	read-write
        STATUS	mandatory
        DESCRIPTION
                "enable/disable IPv6 Protocol - disabling generates
                a Close event to the IPv6CP FSM and consequently disallows
                IPv6 traffic on this circuit"
        DEFVAL	{ disabled }
        ::= { wfPppCircuitEntry 69 }

    wfPppCircuitIpv6CurrentState OBJECT-TYPE
        SYNTAX	INTEGER {
    		    starting(1),
    		    closed(2),
    		    stopped(3),
    		    closing(4),
    		    stopping(5),
    		    reqsent(6),
    		    ackrcvd(7),
    		    acksent(8),
    		    opened(9)
    	  }
        ACCESS	read-only
        STATUS	mandatory
        DESCRIPTION
                "the current state of the Ipv6 Finite State Machine"
        ::= { wfPppCircuitEntry 70 }

    wfPppCircuitCcpType OBJECT-TYPE
        SYNTAX INTEGER {
             ilccp(1),
             ccp(2)
        }
        ACCESS read-write
        STATUS mandatory
        DESCRIPTION
                "Specifies whether to use CCP or Individual Link CCP"
        DEFVAL  { ccp }  
        ::= { wfPppCircuitEntry 71 }

    wfPppCircuitCfgCcpOptions OBJECT-TYPE
        SYNTAX INTEGER {
             all(1),
             oui-wcp(2),
             staclzs(3)
       }
       ACCESS read-write
       STATUS mandatory
       DESCRIPTION
               "Specifies the compression protocol options in 1st 
                config-request"
       DEFVAL  { all }  
       ::= { wfPppCircuitEntry 72 }

    wfPppCircuitCcpOptions OBJECT-TYPE
        SYNTAX INTEGER {
             none(1),
             oui-wcp(2),
             staclzs(3)
        }
        ACCESS read-only
        STATUS mandatory
        DESCRIPTION
              "The negotiated compression protocol option"
        DEFVAL  { none }  
        ::= { wfPppCircuitEntry 73 }

    wfPppCircuitStacLZSCheckMode OBJECT-TYPE
        SYNTAX INTEGER {
             mode0(1),
             mode3(4)
        }
        ACCESS read-write
        STATUS mandatory
        DESCRIPTION
        "Specifies the check mode for STAC LZS compression protocol. See
         RFC 1974 for more information."
        DEFVAL  { mode3 }  
        ::= { wfPppCircuitEntry 74 }

    wfPppCircuitMLFragStrict OBJECT-TYPE
	SYNTAX  INTEGER {
                    enabled(1),
                    disabled(2)
                }
        ACCESS  read-write
        STATUS  mandatory
        DESCRIPTION
                "enable/disable strict fragmentation algorithm i.e. fragmenting a 
		 packet when its size exceeds the threshold regardless of what the 
		 average packet size is"
        DEFVAL  { disabled }
        ::= { wfPppCircuitEntry 75 }

    wfPppCircuitLampreyCompDisable OBJECT-TYPE
	SYNTAX  INTEGER {
                    slot1   (1),
                    slot2   (2),
                    slot3   (3),
                    slot4   (4),
                    slot5   (5),
                    slot6   (6),
                    slot7   (7),
                    slot8   (8),
                    slot9   (9),
                    slot10  (10),
                    slot11  (11),
                    slot12  (12),
                    slot13  (13),
                    slot14  (14),
                    disabled(99)
                }
        ACCESS  read-write
        STATUS  mandatory
        DESCRIPTION
                "enable/disable hardware compression, either from the compression
                 daugther card on the Lamprey or the old compression daugther 
                 interface card on the link module, it tells you where the
                 compression hardware is"
        DEFVAL  { disabled }
        ::= { wfPppCircuitEntry 76 }

   wfPppCircuitMsgLevel OBJECT-TYPE
        SYNTAX	INTEGER {
    		    all(2031616),
    		    debug(65536),
    		    info(131072),
    		    warning(262144),
    		    fault(524288),
    		    trace(1048576),
                    infofaultwarning(917504)
    		}
        ACCESS  read-write
        STATUS  mandatory
        DESCRIPTION
                "PPP Circuit log messages level.
                To control level of log messages
                             DBG_MSG_ALL         0x001f0000 - 2031616
                             DBG_MSG_DEBUG       0x00010000 -   65536
                             DBG_MSG_INFO        0x00020000 -  131072
                             DBG_MSG_WARNING     0x00040000 -  262144
                             DBG_MSG_FAULT       0x00080000 -  524288
                             DBG_MSG_TRACE       0x00100000 - 1048576"
        DEFVAL	{ infofaultwarning }
        ::= { wfPppCircuitEntry 77 }
 

    wfPppCircuitType OBJECT-TYPE
	SYNTAX  INTEGER {
			  unknown(9),
			  dialup(1),
			  l2tp(2),
			  leased(3)
			}
        ACCESS  read-write
        STATUS  mandatory
        DESCRIPTION
		"To differentiate between a Dial Up PPP circuit from L2TP and Leased Line"
	DEFVAL  { unknown }
	::= { wfPppCircuitEntry 78 }


    wfPppCircuitWRCompatability OBJECT-TYPE
        SYNTAX  INTEGER {
                    enabled(1),
                    disabled(2)
                }
        ACCESS  read-write
        STATUS  mandatory
        DESCRIPTION
                "Enable WebRanger compatability that allows us to accept a config-ack
                 after receiving an invalid config-req"
        DEFVAL  { disabled }
        ::= { wfPppCircuitEntry 79 }


    wfPppWhoamiTable OBJECT-TYPE
        SYNTAX	SEQUENCE OF WfPppWhoamiEntry
        ACCESS	not-accessible
        STATUS	mandatory
        DESCRIPTION
                "The Wellfleet PPP WHOAMI Table, containing a mapping of
                peer CHAP Names and the circuit numbers they map to"
        ::= { wfPppGroup 3 }

    wfPppWhoamiEntry OBJECT-TYPE
        SYNTAX	WfPppWhoamiEntry
        ACCESS	not-accessible
        STATUS	mandatory
        DESCRIPTION
                "Map the value of this entry's CHAP Name to the
                value of this entry's CCT number"
        INDEX	{ wfPppWhoamiName }
        ::= { wfPppWhoamiTable 1 }

    WfPppWhoamiEntry ::= SEQUENCE {
    	    wfPppWhoamiDelete
    		INTEGER,
    	    wfPppWhoamiName
    		DisplayString,
    	    wfPppWhoamiCircuit
    		INTEGER,
    	    wfPppWhoamiSecret
    		DisplayString,
    	    wfPppWhoamiPapPassword
    		DisplayString,
    	    wfPppWhoamiCctGrp
    		INTEGER
        }

    wfPppWhoamiDelete OBJECT-TYPE
        SYNTAX	INTEGER {
    		    created(1),
    		    deleted(2)
    		}
        ACCESS	read-write
        STATUS	mandatory
        DESCRIPTION
                "Create/Delete parameter"
        DEFVAL	{ created }
        ::= { wfPppWhoamiEntry 1 }

    wfPppWhoamiName OBJECT-TYPE
        SYNTAX	DisplayString
        ACCESS	read-only
        STATUS	mandatory
        DESCRIPTION
                "Peer CHAP Name"
        ::= { wfPppWhoamiEntry 2 }

    wfPppWhoamiCircuit OBJECT-TYPE
        SYNTAX	INTEGER
        ACCESS	read-write
        STATUS	mandatory
        DESCRIPTION
                "Circuit number to map to"
        ::= { wfPppWhoamiEntry 3 }

    wfPppWhoamiSecret OBJECT-TYPE
        SYNTAX	DisplayString
        ACCESS	read-write
        STATUS	mandatory
        DESCRIPTION
                "Peer CHAP Secret"
        ::= { wfPppWhoamiEntry 4 }

    wfPppWhoamiPapPassword OBJECT-TYPE
        SYNTAX	DisplayString
        ACCESS	read-write
        STATUS	mandatory
        DESCRIPTION
                "Peer Pap Password"
        ::= { wfPppWhoamiEntry 5 }

    wfPppWhoamiCctGrp OBJECT-TYPE
        SYNTAX	INTEGER
        ACCESS	read-write
        STATUS	mandatory
        DESCRIPTION
                "Unnumbered circuit group to map to"
        ::= { wfPppWhoamiEntry 6 }

    wfPppMlStatsTable OBJECT-TYPE
        SYNTAX	SEQUENCE OF WfPppMlStatsEntry
        ACCESS	not-accessible
        STATUS	mandatory
        DESCRIPTION
                "The Wellfleet PPP Multilink Stats Table, containing statistics
                for each Multilink Circuit"
        ::= { wfPppGroup 4 }

    wfPppMlStatsEntry OBJECT-TYPE
        SYNTAX	WfPppMlStatsEntry
        ACCESS	not-accessible
        STATUS	mandatory
        DESCRIPTION
                "per Wellfleet circuit PPP Multilink counters"
        INDEX	{ wfPppMlStatsCircuitID }
        ::= { wfPppMlStatsTable 1 }

    WfPppMlStatsEntry ::= SEQUENCE {
    	    wfPppMlStatsDelete
    		INTEGER,
    	    wfPppMlStatsCircuitID
    		INTEGER,
    	    wfPppMlStatsHomeSlot
    		INTEGER,
    	    wfPppMlStatsLineCnt
    		Gauge,
    	    wfPppMlStatsBundleSpd
    		Gauge,
    	    wfPppMlStatsMrru
    		Gauge,
    	    wfPppMlStatsEndptDisc
    		OCTET STRING,
    	    wfPppMlStatsTxOctets
    		Counter,
    	    wfPppMlStatsTxPkts
    		Counter,
    	    wfPppMlStatsAvgTxListLen
    		Gauge,
    	    wfPppMlStatsRxOctets
    		Counter,
    	    wfPppMlStatsRxPkts
    		Counter,
    	    wfPppMlStatsReasmFails
    		Counter,
    	    wfPppMlStatsSeqNumberLost
    		Counter,
    	    wfPppMlStatsSeqNumberArrivedLate
    		Counter,
    	    wfPppMlStatsReSeqBufferCnt
    		Gauge,
    	    wfPppMlStatsReSeqBufferMax
    		Counter,
    	    wfPppMlStatsExceededBufferMax
    		Counter,
    	    wfPppMlStatsLinkIdleEvents
    		Counter,
	    wfPppMlStatsCalcPercent
		INTEGER,
	    wfPppMlStatsDebug
		INTEGER,
            wfPppMlStatsReassmBufferCnt
                Gauge,
            wfPppMlStatsReassmBufferMax
    		Counter,
            wfPppMlStatsNumPktsFragmented
    		Counter,
    	    wfPppMlStatsPQHiXmits
    		Counter,
    	    wfPppMlStatsPQNormalXmits
    		Counter,
    	    wfPppMlStatsPQLoXmits
    		Counter,
    	    wfPppMlStatsPQHiClippedPkts
    		Counter,
    	    wfPppMlStatsPQNormalClippedPkts
    		Counter,
    	    wfPppMlStatsPQLoClippedPkts
    		Counter,
    	    wfPppMlStatsPQIntrQHighWaterPkts
    		Gauge,
    	    wfPppMlStatsPQHiQHighWaterPkts
    		Gauge,
    	    wfPppMlStatsPQNormalQHighWaterPkts
    		Gauge,
    	    wfPppMlStatsPQLoQHighWaterPkts
    		Gauge,
    	    wfPppMlStatsPQHighWaterPktsClear
    		INTEGER,
    	    wfPppMlStatsPQDroppedPkts
    		Counter,
    	    wfPppMlStatsPQLargePkts
    		Counter,
    	    wfPppMlStatsPQHiTotalOctets
    		Counter,
    	    wfPppMlStatsPQNormalTotalOctets
    		Counter,
    	    wfPppMlStatsPQLoTotalOctets
    		Counter,
    	    wfPppMlStatsPQPktsNotQueued
    		Counter
        }

    wfPppMlStatsDelete OBJECT-TYPE
        SYNTAX	INTEGER {
    		    created(1),
    		    deleted(2)
    		}
        ACCESS	read-write
        STATUS	mandatory
        DESCRIPTION
                "Create/Delete parameter"
        DEFVAL	{ created }
        ::= { wfPppMlStatsEntry 1 }

    wfPppMlStatsCircuitID OBJECT-TYPE
        SYNTAX	INTEGER(1..1023)
        ACCESS	read-only
        STATUS	mandatory
        DESCRIPTION
                "cct number for this instance"
        ::= { wfPppMlStatsEntry 2 }

    wfPppMlStatsHomeSlot OBJECT-TYPE
        SYNTAX	INTEGER
        ACCESS	read-only
        STATUS	mandatory
        DESCRIPTION
                "Slot on which this Multilink Control Subsystem exists"
        ::= { wfPppMlStatsEntry 3 }

    wfPppMlStatsLineCnt OBJECT-TYPE
        SYNTAX	Gauge
        ACCESS	read-only
        STATUS	mandatory
        DESCRIPTION
                "Current count of lines in Multilink bundle"
        ::= { wfPppMlStatsEntry 4 }

    wfPppMlStatsBundleSpd OBJECT-TYPE
        SYNTAX	Gauge
        ACCESS	read-only
        STATUS	mandatory
        DESCRIPTION
                "Current total bandwidth of Multilink bundle"
        ::= { wfPppMlStatsEntry 5 }

    wfPppMlStatsMrru OBJECT-TYPE
        SYNTAX	Gauge
        ACCESS	read-only
        STATUS	mandatory
        DESCRIPTION
                "Current Maximum Receive Reconstructed Unit (MRRU)
                in use for Multilink bundle"
        ::= { wfPppMlStatsEntry 6 }

    wfPppMlStatsEndptDisc OBJECT-TYPE
        SYNTAX	OCTET STRING
        ACCESS	read-only
        STATUS	mandatory
        DESCRIPTION
                "Current Endpoint Discriminator in use for
                Multilink bundle"
        ::= { wfPppMlStatsEntry 7 }

    wfPppMlStatsTxOctets OBJECT-TYPE
        SYNTAX	Counter
        ACCESS	read-only
        STATUS	mandatory
        DESCRIPTION
                "Number of octets transmitted by Multilink"
        ::= { wfPppMlStatsEntry 8 }

    wfPppMlStatsTxPkts OBJECT-TYPE
        SYNTAX	Counter
        ACCESS	read-only
        STATUS	mandatory
        DESCRIPTION
                "Number of packets transmitted by Multilink"
        ::= { wfPppMlStatsEntry 9 }

    wfPppMlStatsAvgTxListLen OBJECT-TYPE
        SYNTAX	Gauge
        ACCESS	read-only
        STATUS	mandatory
        DESCRIPTION
                "Average number of packets received in the transient
                list by the Multilink Transmit gate."
        ::= { wfPppMlStatsEntry 10 }

    wfPppMlStatsRxOctets OBJECT-TYPE
        SYNTAX	Counter
        ACCESS	read-only
        STATUS	mandatory
        DESCRIPTION
                "Number of octets received without error"
        ::= { wfPppMlStatsEntry 11 }

    wfPppMlStatsRxPkts OBJECT-TYPE
        SYNTAX	Counter
        ACCESS	read-only
        STATUS	mandatory
        DESCRIPTION
                "Number of packets received by Multilink"
        ::= { wfPppMlStatsEntry 12 }

    wfPppMlStatsReasmFails OBJECT-TYPE
        SYNTAX	Counter
        ACCESS	read-only
        STATUS	mandatory
        DESCRIPTION
                "Number of packet reassembly failures"
        ::= { wfPppMlStatsEntry 13 }

    wfPppMlStatsSeqNumberLost OBJECT-TYPE
        SYNTAX	Counter
        ACCESS	read-only
        STATUS	mandatory
        DESCRIPTION
                "Number of Multilink packets considered to be lost on
                the wire"
        ::= { wfPppMlStatsEntry 14 }

    wfPppMlStatsSeqNumberArrivedLate OBJECT-TYPE
        SYNTAX	Counter
        ACCESS	read-only
        STATUS	mandatory
        DESCRIPTION
                "Number of Multilink packets which arrive
                containing an old Sequence Number. IE: packets
                with a more current Sequence Number have already
                been sent up to NCP"
        ::= { wfPppMlStatsEntry 15 }

    wfPppMlStatsReSeqBufferCnt OBJECT-TYPE
        SYNTAX	Gauge
        ACCESS	read-only
        STATUS	mandatory
        DESCRIPTION
                "Number of Multilink packets currently stored
                in the ReSequencing buffer pool."
        ::= { wfPppMlStatsEntry 16 }

    wfPppMlStatsReSeqBufferMax OBJECT-TYPE
        SYNTAX	Counter
        ACCESS	read-only
        STATUS	mandatory
        DESCRIPTION
                "The Maximum Number of Multilink packets stored
                in the ReSequencing buffer pool."
        ::= { wfPppMlStatsEntry 17 }

    wfPppMlStatsExceededBufferMax OBJECT-TYPE
        SYNTAX	Counter
        ACCESS	read-only
        STATUS	mandatory
        DESCRIPTION
                "The number of times a buffer needed to be stored by the 
                 Multilink Receive logic when the count of buffers stored,
                 wfPppMlStatsReSeqBufferMax,was equal to the maximum allowable
                 for this circuit, wfPppCircuitMaxBuffers."
        ::= { wfPppMlStatsEntry 18 }

    wfPppMlStatsLinkIdleEvents OBJECT-TYPE
        SYNTAX  Counter
        ACCESS  read-only
        STATUS  mandatory
        DESCRIPTION
                "The number of times the Multilink Receive logic detected a
                 stored buffer received on a line which has been declared idle."
        ::= { wfPppMlStatsEntry 19 }

    wfPppMlStatsCalcPercent OBJECT-TYPE
        SYNTAX	INTEGER {
    		    enabled(1),
    		    disabled(2)
    		}
        ACCESS	read-write
        STATUS	mandatory
        DESCRIPTION
                "enable/disable collection of Rx percentage line usage"
        DEFVAL	{ disabled }
        ::= { wfPppMlStatsEntry 20 }

    wfPppMlStatsDebug OBJECT-TYPE
        SYNTAX	INTEGER
        ACCESS	read-write
        STATUS	mandatory
        DESCRIPTION
                "DEBUG parameter - this is used to control debug code for the Multilink subsystem"
        ::= { wfPppMlStatsEntry 21 }

    wfPppMlStatsReassmBufferCnt OBJECT-TYPE
        SYNTAX  Gauge
        ACCESS  read-only
        STATUS  mandatory
        DESCRIPTION
                "Number of Multilink packets currently stored
                in the Reassembling buffer pools."
        ::= { wfPppMlStatsEntry 22 }

    wfPppMlStatsReassmBufferMax OBJECT-TYPE
        SYNTAX  Counter
        ACCESS  read-only
        STATUS  mandatory
        DESCRIPTION
                "The Maximum Number of Multilink packets stored
                in the Reassembling buffer pools."
        ::= { wfPppMlStatsEntry 23 }

    wfPppMlStatsNumPktsFragmented OBJECT-TYPE
        SYNTAX  Counter
        ACCESS  read-only
        STATUS  mandatory
        DESCRIPTION
                "The Number of Multilink packets that were 
	         fragmented."
        ::= { wfPppMlStatsEntry 24 }

    wfPppMlStatsPQHiXmits OBJECT-TYPE
        SYNTAX  Counter
        ACCESS  read-only
        STATUS  mandatory
        DESCRIPTION
                "High priority transmit count."
        ::= { wfPppMlStatsEntry 25 }

    wfPppMlStatsPQNormalXmits OBJECT-TYPE
        SYNTAX  Counter
        ACCESS  read-only
        STATUS  mandatory
        DESCRIPTION
                "Normal priority transmit count."
        ::= { wfPppMlStatsEntry 26 }

    wfPppMlStatsPQLoXmits OBJECT-TYPE
        SYNTAX	Counter
        ACCESS	read-only
        STATUS	mandatory
        DESCRIPTION
                "Low priority transmit count"
        ::= { wfPppMlStatsEntry 27 }

    wfPppMlStatsPQHiClippedPkts OBJECT-TYPE
        SYNTAX	Counter
        ACCESS	read-only
        STATUS	mandatory
        DESCRIPTION
                "High priority transmit clip Count"
        ::= { wfPppMlStatsEntry 28 }

    wfPppMlStatsPQNormalClippedPkts OBJECT-TYPE
        SYNTAX	Counter
        ACCESS	read-only
        STATUS	mandatory
        DESCRIPTION
                "Normal priority transmit clip Count"
        ::= { wfPppMlStatsEntry 29 }

    wfPppMlStatsPQLoClippedPkts OBJECT-TYPE
        SYNTAX	Counter
        ACCESS	read-only
        STATUS	mandatory
        DESCRIPTION
                "Low priority transmit clip Count"
        ::= { wfPppMlStatsEntry 30 }

    wfPppMlStatsPQIntrQHighWaterPkts OBJECT-TYPE
        SYNTAX	Gauge
        ACCESS	read-only
        STATUS	mandatory
        DESCRIPTION
                "Interrupt-priority Queue high-water mark"
        ::= { wfPppMlStatsEntry 31 }

    wfPppMlStatsPQHiQHighWaterPkts OBJECT-TYPE
        SYNTAX	Gauge
        ACCESS	read-only
        STATUS	mandatory
        DESCRIPTION
                "High-priority Queue high-water mark"
        ::= { wfPppMlStatsEntry 32 }

    wfPppMlStatsPQNormalQHighWaterPkts OBJECT-TYPE
        SYNTAX	Gauge
        ACCESS	read-only
        STATUS	mandatory
        DESCRIPTION
                "Normal-priority Queue high-water mark"
        ::= { wfPppMlStatsEntry 33 }

    wfPppMlStatsPQLoQHighWaterPkts OBJECT-TYPE
        SYNTAX	Gauge
        ACCESS	read-only
        STATUS	mandatory
        DESCRIPTION
                "Low-priority Queue high-water mark"
        ::= { wfPppMlStatsEntry 34 }

    wfPppMlStatsPQHighWaterPktsClear OBJECT-TYPE
        SYNTAX	INTEGER
        ACCESS	read-write
        STATUS	mandatory
        DESCRIPTION
                "Attribute to clear the high-water marks. When the MIB
                changes, Priority Queueing (if ENABLED) checks to see
                if HighWaterPktsClear is different than the last time the MIB
                was modified in any way.  If it is different,
                all the high water marks (see above) are set to zero."
        ::= { wfPppMlStatsEntry 35 }

    wfPppMlStatsPQDroppedPkts OBJECT-TYPE
        SYNTAX	Counter
        ACCESS	read-only
        STATUS	mandatory
        DESCRIPTION
                "Packets which were filtered in Priority Queueing"
        ::= { wfPppMlStatsEntry 36 }

    wfPppMlStatsPQLargePkts OBJECT-TYPE
        SYNTAX	Counter
        ACCESS	read-only
        STATUS	mandatory
        DESCRIPTION
                "Large Packets which became an exception to latency rules"
        ::= { wfPppMlStatsEntry 37 }

    wfPppMlStatsPQHiTotalOctets OBJECT-TYPE
        SYNTAX	Counter
        ACCESS	read-only
        STATUS	mandatory
        DESCRIPTION
                "Running total of High Octets transmitted when
                using Bandwidth Allocation dequeueing algorithm"
        ::= { wfPppMlStatsEntry 38 }

    wfPppMlStatsPQNormalTotalOctets OBJECT-TYPE
        SYNTAX	Counter
        ACCESS	read-only
        STATUS	mandatory
        DESCRIPTION
                "Running total of Normal Octets transmitted when
                using Bandwidth Allocation dequeueing algorithm"
        ::= { wfPppMlStatsEntry 39 }

    wfPppMlStatsPQLoTotalOctets OBJECT-TYPE
        SYNTAX	Counter
        ACCESS	read-only
        STATUS	mandatory
        DESCRIPTION
                "Running total of Low Octets transmitted when
                using Bandwidth Allocation dequeueing algorithm"
        ::= { wfPppMlStatsEntry 40 }

    wfPppMlStatsPQPktsNotQueued OBJECT-TYPE
        SYNTAX Counter
        ACCESS read-only
        STATUS mandatory
        DESCRIPTION
                "Packets that were not Queued or Dropped by  
                 Priority Queuing "
        ::= { wfPppMlStatsEntry 41 }



    wfPppBapStatsTable OBJECT-TYPE
        SYNTAX	SEQUENCE OF WfPppBapStatsEntry
        ACCESS	not-accessible
        STATUS	mandatory
        DESCRIPTION
                "The Wellfleet PPP BAP Stats Table, containing statistics
                for each BACP Circuit"
        ::= { wfPppGroup 5 }

    wfPppBapStatsEntry OBJECT-TYPE
        SYNTAX	WfPppBapStatsEntry
        ACCESS	not-accessible
        STATUS	mandatory
        DESCRIPTION
                "per Wellfleet circuit PPP BAP counters"
        INDEX	{ wfPppBapStatsCircuitID }
        ::= { wfPppBapStatsTable 1 }

    WfPppBapStatsEntry ::= SEQUENCE {
    	    wfPppBapStatsDelete
    		INTEGER,
    	    wfPppBapStatsCircuitID
    		INTEGER,
    	    wfPppBapCallReqTx
    		Counter,
    	    wfPppBapCallRespAckTx
    		Counter,
    	    wfPppBapCallRespNakTx
    		Counter,
    	    wfPppBapCallRespFullNakTx
    		Counter,
    	    wfPppBapCallRespRejTx
    		Counter,
    	    wfPppBapCallbackReqTx
    		Counter,
    	    wfPppBapCallbackRespAckTx
    		Counter,
    	    wfPppBapCallbackRespNakTx
    		Counter,
    	    wfPppBapCallbackRespFullNakTx
    		Counter,
    	    wfPppBapCallbackRespRejTx
    		Counter,
    	    wfPppBapLdQueryReqTx
    		Counter,
    	    wfPppBapLdQueryRespAckTx
    		Counter,
    	    wfPppBapLdQueryRespNakTx
    		Counter,
    	    wfPppBapLdQueryRespFullNakTx
    		Counter,
    	    wfPppBapCallStatusIndFailTx
    		Counter,
    	    wfPppBapCallStatusIndSuccessTx
    		Counter,
    	    wfPppBapCallStatusRespTx
    		Counter,
    	    wfPppBapCallReqRx
    		Counter,
    	    wfPppBapCallRespAckRx
    		Counter,
    	    wfPppBapCallRespNakRx
    		Counter,
    	    wfPppBapCallRespFullNakRx
    		Counter,
    	    wfPppBapCallRespRejRx
    		Counter,
    	    wfPppBapCallbackReqRx
    		Counter,
    	    wfPppBapCallbackRespAckRx
    		Counter,
    	    wfPppBapCallbackRespNakRx
    		Counter,
    	    wfPppBapCallbackRespFullNakRx
    		Counter,
    	    wfPppBapCallbackRespRejRx
    		Counter,
    	    wfPppBapLdQueryReqRx
    		Counter,
    	    wfPppBapLdQueryRespAckRx
    		Counter,
    	    wfPppBapLdQueryRespNakRx
    		Counter,
    	    wfPppBapLdQueryRespFullNakRx
    		Counter,
    	    wfPppBapCallStatusIndFailRx
    		Counter,
    	    wfPppBapCallStatusIndSuccessRx
    		Counter,
    	    wfPppBapCallStatusRespRx
    		Counter,
    	    wfPppBapCallReqRespDiscardRx
    		Counter,
    	    wfPppBapCallbackReqRespDiscardRx
    		Counter
        }

    wfPppBapStatsDelete OBJECT-TYPE
        SYNTAX	INTEGER {
    		    created(1),
    		    deleted(2)
    		}
        ACCESS	read-write
        STATUS	mandatory
        DESCRIPTION
                "Create/Delete parameter"
        DEFVAL	{ created }
        ::= { wfPppBapStatsEntry 1 }

    wfPppBapStatsCircuitID OBJECT-TYPE
        SYNTAX	INTEGER(1..1023)
        ACCESS	read-only
        STATUS	mandatory
        DESCRIPTION
                "cct number for this instance"
        ::= { wfPppBapStatsEntry 2 }

    wfPppBapCallReqTx OBJECT-TYPE
        SYNTAX	Counter
        ACCESS	read-only
        STATUS	mandatory
        DESCRIPTION
                "Number of Call Requests transmitted by BAP"
        ::= { wfPppBapStatsEntry 3 }

    wfPppBapCallRespAckTx OBJECT-TYPE
        SYNTAX	Counter
        ACCESS	read-only
        STATUS	mandatory
        DESCRIPTION
                "Number of Call Responses transmitted by BAP
                 with a Response Code of Request_Ack"
        ::= { wfPppBapStatsEntry 4 }

    wfPppBapCallRespNakTx OBJECT-TYPE
        SYNTAX	Counter
        ACCESS	read-only
        STATUS	mandatory
        DESCRIPTION
                "Number of Call Responses transmitted by BAP
                 with a Response Code of Request_Nak"
        ::= { wfPppBapStatsEntry 5 }

    wfPppBapCallRespFullNakTx OBJECT-TYPE
        SYNTAX	Counter
        ACCESS	read-only
        STATUS	mandatory
        DESCRIPTION
                "Number of Call Responses transmitted by BAP
                 with a Response Code of Request_Full_Nak"
        ::= { wfPppBapStatsEntry 6 }

    wfPppBapCallRespRejTx OBJECT-TYPE
        SYNTAX	Counter
        ACCESS	read-only
        STATUS	mandatory
        DESCRIPTION
                "Number of Call Responses transmitted by BAP
                 with a Response Code of Request_Rej"
        ::= { wfPppBapStatsEntry 7 }

    wfPppBapCallbackReqTx OBJECT-TYPE
        SYNTAX	Counter
        ACCESS	read-only
        STATUS	mandatory
        DESCRIPTION
                "Number of Callback Requests transmitted by BAP"
        ::= { wfPppBapStatsEntry 8 }

    wfPppBapCallbackRespAckTx OBJECT-TYPE
        SYNTAX	Counter
        ACCESS	read-only
        STATUS	mandatory
        DESCRIPTION
                "Number of Callback Responses transmitted by BAP
                 with a Response Code of Request_Ack"
        ::= { wfPppBapStatsEntry 9 }

    wfPppBapCallbackRespNakTx OBJECT-TYPE
        SYNTAX	Counter
        ACCESS	read-only
        STATUS	mandatory
        DESCRIPTION
                "Number of Callback Responses transmitted by BAP
                 with a Response Code of Request_Nak"
        ::= { wfPppBapStatsEntry 10 }

    wfPppBapCallbackRespFullNakTx OBJECT-TYPE
        SYNTAX	Counter
        ACCESS	read-only
        STATUS	mandatory
        DESCRIPTION
                "Number of Callback Responses transmitted by BAP
                 with a Response Code of Request_Full_Nak"
        ::= { wfPppBapStatsEntry 11 }

    wfPppBapCallbackRespRejTx OBJECT-TYPE
        SYNTAX	Counter
        ACCESS	read-only
        STATUS	mandatory
        DESCRIPTION
                "Number of Callback Responses transmitted by BAP
                 with a Response Code of Request_Rej"
        ::= { wfPppBapStatsEntry 12 }

    wfPppBapLdQueryReqTx OBJECT-TYPE
        SYNTAX	Counter
        ACCESS	read-only
        STATUS	mandatory
        DESCRIPTION
                "Number of LinkDrop Query Requests transmitted by BAP"
        ::= { wfPppBapStatsEntry 13 }

    wfPppBapLdQueryRespAckTx OBJECT-TYPE
        SYNTAX	Counter
        ACCESS	read-only
        STATUS	mandatory
        DESCRIPTION
                "Number of LinkDrop Query Responses transmitted by BAP
                 with a Response Code of Request_Ack"
        ::= { wfPppBapStatsEntry 14 }

    wfPppBapLdQueryRespNakTx OBJECT-TYPE
        SYNTAX	Counter
        ACCESS	read-only
        STATUS	mandatory
        DESCRIPTION
                "Number of LinkDrop Query Responses transmitted by BAP
                 with a Response Code of Request_Nak"
        ::= { wfPppBapStatsEntry 15 }


    wfPppBapLdQueryRespFullNakTx OBJECT-TYPE
        SYNTAX	Counter
        ACCESS	read-only
        STATUS	mandatory
        DESCRIPTION
                "Number of LinkDrop Query Responses transmitted by BAP
                 with a Response Code of Request_Full_Nak"
        ::= { wfPppBapStatsEntry 16 }

    wfPppBapCallStatusIndFailTx OBJECT-TYPE
        SYNTAX	Counter
        ACCESS	read-only
        STATUS	mandatory
        DESCRIPTION
                "Number of Call_Status_Indications transmitted by BAP
                 with a non-zero Call Status"
        ::= { wfPppBapStatsEntry 17 }

    wfPppBapCallStatusIndSuccessTx OBJECT-TYPE
        SYNTAX	Counter
        ACCESS	read-only
        STATUS	mandatory
        DESCRIPTION
                "Number of Call_Status_Indications transmitted by BAP
                 with a zero Call Status"
        ::= { wfPppBapStatsEntry 18 }

    wfPppBapCallStatusRespTx OBJECT-TYPE
        SYNTAX	Counter
        ACCESS	read-only
        STATUS	mandatory
        DESCRIPTION
                "Number of Call_Status_Response transmitted by BAP"
        ::= { wfPppBapStatsEntry 19 }

    wfPppBapCallReqRx OBJECT-TYPE
        SYNTAX	Counter
        ACCESS	read-only
        STATUS	mandatory
        DESCRIPTION
                "Number of Call Requests received by BAP"
        ::= { wfPppBapStatsEntry 20 }

    wfPppBapCallRespAckRx OBJECT-TYPE
        SYNTAX	Counter
        ACCESS	read-only
        STATUS	mandatory
        DESCRIPTION
                "Number of Call Responses received by BAP
                 with a Response Code of Request_Ack"
        ::= { wfPppBapStatsEntry 21 }

    wfPppBapCallRespNakRx OBJECT-TYPE
        SYNTAX	Counter
        ACCESS	read-only
        STATUS	mandatory
        DESCRIPTION
                "Number of Call Responses received by BAP
                 with a Response Code of Request_Nak"
        ::= { wfPppBapStatsEntry 22 }

    wfPppBapCallRespFullNakRx OBJECT-TYPE
        SYNTAX	Counter
        ACCESS	read-only
        STATUS	mandatory
        DESCRIPTION
                "Number of Call Responses received by BAP
                 with a Response Code of Request_Full_Nak"
        ::= { wfPppBapStatsEntry 23 }

    wfPppBapCallRespRejRx OBJECT-TYPE
        SYNTAX	Counter
        ACCESS	read-only
        STATUS	mandatory
        DESCRIPTION
                "Number of Call Responses received by BAP
                 with a Response Code of Request_Rej"
        ::= { wfPppBapStatsEntry 24 }

    wfPppBapCallbackReqRx OBJECT-TYPE
        SYNTAX	Counter
        ACCESS	read-only
        STATUS	mandatory
        DESCRIPTION
                "Number of Callback Requests received by BAP"
        ::= { wfPppBapStatsEntry 25 }

    wfPppBapCallbackRespAckRx OBJECT-TYPE
        SYNTAX	Counter
        ACCESS	read-only
        STATUS	mandatory
        DESCRIPTION
                "Number of Callback Responses received by BAP
                 with a Response Code of Request_Ack"
        ::= { wfPppBapStatsEntry 26 }

    wfPppBapCallbackRespNakRx OBJECT-TYPE
        SYNTAX	Counter
        ACCESS	read-only
        STATUS	mandatory
        DESCRIPTION
                "Number of Callback Responses received by BAP
                 with a Response Code of Request_Nak"
        ::= { wfPppBapStatsEntry 27 }

    wfPppBapCallbackRespFullNakRx OBJECT-TYPE
        SYNTAX	Counter
        ACCESS	read-only
        STATUS	mandatory
        DESCRIPTION
                "Number of Callback Responses received by BAP
                 with a Response Code of Request_Full_Nak"
        ::= { wfPppBapStatsEntry 28 }

    wfPppBapCallbackRespRejRx OBJECT-TYPE
        SYNTAX	Counter
        ACCESS	read-only
        STATUS	mandatory
        DESCRIPTION
                "Number of Callback Responses received by BAP
                 with a Response Code of Request_Rej"
        ::= { wfPppBapStatsEntry 29 }

    wfPppBapLdQueryReqRx OBJECT-TYPE
        SYNTAX	Counter
        ACCESS	read-only
        STATUS	mandatory
        DESCRIPTION
                "Number of LinkDrop Query Requests received by BAP"
        ::= { wfPppBapStatsEntry 30 }

    wfPppBapLdQueryRespAckRx OBJECT-TYPE
        SYNTAX	Counter
        ACCESS	read-only
        STATUS	mandatory
        DESCRIPTION
                "Number of LinkDrop Query Responses received by BAP
                 with a Response Code of Request_Ack"
        ::= { wfPppBapStatsEntry 31 }

    wfPppBapLdQueryRespNakRx OBJECT-TYPE
        SYNTAX	Counter
        ACCESS	read-only
        STATUS	mandatory
        DESCRIPTION
                "Number of LinkDrop Query Responses received by BAP
                 with a Response Code of Request_Nak"
        ::= { wfPppBapStatsEntry 32 }


    wfPppBapLdQueryRespFullNakRx OBJECT-TYPE
        SYNTAX	Counter
        ACCESS	read-only
        STATUS	mandatory
        DESCRIPTION
                "Number of LinkDrop Query Responses received by BAP
                 with a Response Code of Request_Full_Nak"
        ::= { wfPppBapStatsEntry 33 }

    wfPppBapCallStatusIndFailRx OBJECT-TYPE
        SYNTAX	Counter
        ACCESS	read-only
        STATUS	mandatory
        DESCRIPTION
                "Number of Call_Status_Indications received by BAP
                 with a non-zero Call Status"
        ::= { wfPppBapStatsEntry 34 }

    wfPppBapCallStatusIndSuccessRx OBJECT-TYPE
        SYNTAX	Counter
        ACCESS	read-only
        STATUS	mandatory
        DESCRIPTION
                "Number of Call_Status_Indications received by BAP
                 with a zero Call Status"
        ::= { wfPppBapStatsEntry 35 }

    wfPppBapCallStatusRespRx OBJECT-TYPE
        SYNTAX	Counter
        ACCESS	read-only
        STATUS	mandatory
        DESCRIPTION
                "Number of Call_Status_Response received by BAP"
        ::= { wfPppBapStatsEntry 36 }

    wfPppBapCallReqRespDiscardRx OBJECT-TYPE
        SYNTAX	Counter
        ACCESS	read-only
        STATUS	mandatory
        DESCRIPTION
                "Number of Call_Response received by BAP with an
                 old identifier."
        ::= { wfPppBapStatsEntry 37 }

    wfPppBapCallbackReqRespDiscardRx OBJECT-TYPE
        SYNTAX	Counter
        ACCESS	read-only
        STATUS	mandatory
        DESCRIPTION
                "Number of Callback_Response received by BAP with an
                 old identifier."
        ::= { wfPppBapStatsEntry 38 }

    END  -- Wellfleet-PPP-MIB
