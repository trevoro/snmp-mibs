-- $Id: FLARION-TRAP-MIB.txt,v 1.4 2004/08/05 20:56:06 phsu Exp $

FLARION-TRAP-MIB DEFINITIONS ::= BEGIN

IMPORTS
    MODULE-IDENTITY, OBJECT-TYPE, NOTIFICATION-TYPE
        FROM SNMPv2-SMI

    flarion, rrCommonMib, AlarmSeverity, MoType, AddtlInfo
        FROM FLARION-MIB;


flarionTraps        OBJECT IDENTIFIER ::= { flarion 10 }
flaTrapVars         OBJECT IDENTIFIER ::= { flarionTraps 1 }

flaTraps            OBJECT IDENTIFIER ::= { flarionTraps 2 }
flaTrapPrefix       OBJECT IDENTIFIER ::= { flaTraps 0 }


--
-- flaTrapVars - common trap attributes
--
flaTimeStamp        OBJECT-TYPE
    SYNTAX          INTEGER
    MAX-ACCESS      read-only
    STATUS          current
    DESCRIPTION     "The time at which the event was generated.
                     This value is expressed in seconds since
                     00:00:00 UTC, January 1, 1970 (see time(2))."
    ::= { flaTrapVars 1 }

flaSeqNum           OBJECT-TYPE
    SYNTAX          INTEGER
    MAX-ACCESS      read-only
    STATUS          current
    DESCRIPTION     "The event sequence number."
    ::= { flaTrapVars 2 }

flaSeverity         OBJECT-TYPE
    SYNTAX          AlarmSeverity
    MAX-ACCESS      read-only
    STATUS          deprecated
    DESCRIPTION     "The event severity."
    ::= { flaTrapVars 3 }

flaMoType           OBJECT-TYPE
    SYNTAX          MoType
    MAX-ACCESS      read-only
    STATUS          current
    DESCRIPTION     "Type managed object associated with this trap."
    ::= { flaTrapVars 4 }

flaMoId             OBJECT-TYPE
    SYNTAX          INTEGER (0..65535)
    MAX-ACCESS      read-only
    STATUS          current
    DESCRIPTION     "The instance of the managed object logical identifier."
    ::= { flaTrapVars 5 }

flaAddtlInfo        OBJECT-TYPE
    SYNTAX          AddtlInfo
    MAX-ACCESS      read-only
    STATUS          current
    DESCRIPTION     "Event description."
    ::= { flaTrapVars 6 }


mcuBootStatusUp    NOTIFICATION-TYPE
    OBJECTS     { flaTimeStamp, flaSeqNum, flaSeverity,
                  flaMoType, flaMoId, flaAddtlInfo }
    STATUS      current
    DESCRIPTION "The MCU software is up and running."
    ::= { flaTrapPrefix 1 }

mcuBootStatusDown  NOTIFICATION-TYPE
    OBJECTS     { flaTimeStamp, flaSeqNum, flaSeverity,
                  flaMoType, flaMoId, flaAddtlInfo }
    STATUS      current
    DESCRIPTION "The MCU software is shutting down."
    ::= { flaTrapPrefix 2 }

mcuOperStatusUp NOTIFICATION-TYPE
    OBJECTS     { flaTimeStamp, flaSeqNum, flaSeverity,
                  flaMoType, flaMoId, flaAddtlInfo }
    STATUS      deprecated
    DESCRIPTION "MCU operational status is up."
    ::= { flaTrapPrefix 3 }

mcuOperStatusDown   NOTIFICATION-TYPE
    OBJECTS     { flaTimeStamp, flaSeqNum, flaSeverity,
                  flaMoType, flaMoId, flaAddtlInfo }
    STATUS      deprecated
    DESCRIPTION "MCU operational status is down."
    ::= { flaTrapPrefix 4 }

mlpppStatusUp   NOTIFICATION-TYPE
    OBJECTS     { flaTimeStamp, flaSeqNum, flaSeverity,
                  flaMoType, flaMoId, flaAddtlInfo }
    STATUS      current
    DESCRIPTION "Multilink PPP status is up."
    ::= { flaTrapPrefix 5 }

mlpppStatusDown NOTIFICATION-TYPE
    OBJECTS     { flaTimeStamp, flaSeqNum, flaSeverity,
                  flaMoType, flaMoId, flaAddtlInfo }
    STATUS      current
    DESCRIPTION "Multilink PPP status is up."
    ::= { flaTrapPrefix 6 }

bbuOperStatusUp NOTIFICATION-TYPE
    OBJECTS     { flaTimeStamp, flaSeqNum, flaSeverity,
                  flaMoType, flaMoId, flaAddtlInfo }
    STATUS      current
    DESCRIPTION "BBU card operational status is up."
    ::= { flaTrapPrefix 7 }

bbuOperStatusDown   NOTIFICATION-TYPE
    OBJECTS     { flaTimeStamp, flaSeqNum, flaSeverity,
                  flaMoType, flaMoId, flaAddtlInfo }
    STATUS      current
    DESCRIPTION "BBU card operational status is down."
    ::= { flaTrapPrefix 8 }

bbuOperStatusNotPresent NOTIFICATION-TYPE
    OBJECTS     { flaTimeStamp, flaSeqNum, flaSeverity,
                  flaMoType, flaMoId, flaAddtlInfo }
    STATUS      current
    DESCRIPTION "BBU card operational status is not present."
    ::= { flaTrapPrefix 9 }

bbuTempNormal   NOTIFICATION-TYPE
    OBJECTS     { flaTimeStamp, flaSeqNum, flaSeverity,
                  flaMoType, flaMoId, flaAddtlInfo }
    STATUS      current
    DESCRIPTION "BBU temperature has transitioned inot normal operating range."
    ::= { flaTrapPrefix 10 }

bbuTempHigh     NOTIFICATION-TYPE
    OBJECTS     { flaTimeStamp, flaSeqNum, flaSeverity,
                  flaMoType, flaMoId, flaAddtlInfo }
    STATUS      current
    DESCRIPTION "BBU temperature has transitioned into a high operating range."
    ::= { flaTrapPrefix 11 }

bbuTempSevere   NOTIFICATION-TYPE
    OBJECTS     { flaTimeStamp, flaSeqNum, flaSeverity,
                  flaMoType, flaMoId, flaAddtlInfo }
    STATUS      current
    DESCRIPTION "BBU temperature has transitioned into a severe operating
                range."
    ::= { flaTrapPrefix 12 }

bbuTempCritical NOTIFICATION-TYPE
    OBJECTS     { flaTimeStamp, flaSeqNum, flaSeverity,
                  flaMoType, flaMoId, flaAddtlInfo }
    STATUS      current
    DESCRIPTION "BBU temperature has transitioned into a critical operating
                range."
    ::= { flaTrapPrefix 13 }

bbuVoltageNormal    NOTIFICATION-TYPE
    OBJECTS     { flaTimeStamp, flaSeqNum, flaSeverity,
                  flaMoType, flaMoId, flaAddtlInfo }
    STATUS      current
    DESCRIPTION "BBU voltage has transitioned into normal operating range."
    ::= { flaTrapPrefix 14 }

bbuVoltageHigh  NOTIFICATION-TYPE
    OBJECTS     { flaTimeStamp, flaSeqNum, flaSeverity,
                  flaMoType, flaMoId, flaAddtlInfo }
    STATUS      current
    DESCRIPTION "BBU voltage has transitioned above normal operating limits."
    ::= { flaTrapPrefix 15 }

bbuVoltageLow   NOTIFICATION-TYPE
    OBJECTS     { flaTimeStamp, flaSeqNum, flaSeverity,
                  flaMoType, flaMoId, flaAddtlInfo }
    STATUS      current
    DESCRIPTION "BBU voltage has transitioned below normal operating limits."
    ::= { flaTrapPrefix 16 }

dspStatusActive NOTIFICATION-TYPE
    OBJECTS     { flaTimeStamp, flaSeqNum, flaSeverity,
                  flaMoType, flaMoId, flaAddtlInfo }
    STATUS      current
    DESCRIPTION "DSP has transitioned into the Active state. In this state,
                mobiles are allowed to establish connections and data traffic
                can be received/transmitted."
    ::= { flaTrapPrefix 17 }

dspStatusStandby    NOTIFICATION-TYPE
    OBJECTS     { flaTimeStamp, flaSeqNum, flaSeverity,
                  flaMoType, flaMoId, flaAddtlInfo }
    STATUS      current
    DESCRIPTION "DSP has transitioned into the Disabled/Standby state. In this
                state, mobiles can not establish connections and data traffic
                can not be received/transmitted. This is typically caused by
                administrative intervention or the DSP has initiated this state
                change due to an alarm condition elsewhere in the system."
    ::= { flaTrapPrefix 18 }

dspStatusOos    NOTIFICATION-TYPE
    OBJECTS     { flaTimeStamp, flaSeqNum, flaSeverity,
                  flaMoType, flaMoId, flaAddtlInfo }
    STATUS      current
    DESCRIPTION "DSP has transitioned into the Out of Service state."
    ::= { flaTrapPrefix 19 }

dspStatusNonOperational NOTIFICATION-TYPE
    OBJECTS     { flaTimeStamp, flaSeqNum, flaSeverity,
                  flaMoType, flaMoId, flaAddtlInfo }
    STATUS      current
    DESCRIPTION "DSP has transitioned into the Non Operational state. This
                state is entered when the system is unable to determine the
                condition of the DSP."
    ::= { flaTrapPrefix 20 }

accountingRadiusUp  NOTIFICATION-TYPE
    OBJECTS     { flaTimeStamp, flaSeqNum, flaSeverity,
                  flaMoType, flaMoId, flaAddtlInfo }
    STATUS      current
    DESCRIPTION "Accounting/RADIUS server is up."
    ::= { flaTrapPrefix 21 }

accountingRadiusDown    NOTIFICATION-TYPE
    OBJECTS     { flaTimeStamp, flaSeqNum, flaSeverity,
                  flaMoType, flaMoId, flaAddtlInfo }
    STATUS      current
    DESCRIPTION "Accounting/RADIUS server is down."
    ::= { flaTrapPrefix 22 }



--
-- The following traps are deprecated
--

rrTrapVars      OBJECT IDENTIFIER ::= { rrCommonMib 1 }
rrTraps         OBJECT IDENTIFIER ::= { rrCommonMib 2 }


--
-- rrTrapVars - common trap attributes
--
rrTimeStamp         OBJECT-TYPE
    SYNTAX          INTEGER
    MAX-ACCESS      read-only
    STATUS          deprecated
    DESCRIPTION     "The time at which the event was generated.
                     This value is expressed in seconds since
                     00:00:00 UTC, January 1, 1970 (see time(2))."
    ::= { rrTrapVars 1 }

rrSeqNum            OBJECT-TYPE
    SYNTAX          INTEGER
    MAX-ACCESS      read-only
    STATUS          deprecated
    DESCRIPTION     "The event sequence number."
    ::= { rrTrapVars 2 }

rrSeverity          OBJECT-TYPE
    SYNTAX          AlarmSeverity
    MAX-ACCESS      read-only
    STATUS          deprecated
    DESCRIPTION     "The event severity."
    ::= { rrTrapVars 3 }

rrMoType            OBJECT-TYPE
    SYNTAX          MoType
    MAX-ACCESS      read-only
    STATUS          deprecated
    DESCRIPTION     "Type managed object associated with this trap."
    ::= { rrTrapVars 4 }

rrMoId              OBJECT-TYPE
    SYNTAX          INTEGER (0..65535)
    MAX-ACCESS      read-only
    STATUS          deprecated
    DESCRIPTION     "The instance of the managed object logical identifier."
    ::= { rrTrapVars 5 }

rrAddtlInfo         OBJECT-TYPE
    SYNTAX          AddtlInfo
    MAX-ACCESS      read-only
    STATUS          deprecated
    DESCRIPTION     "Event description."
    ::= { rrTrapVars 6 }


--
-- Generic Alarm Trap
--
rrTrapSpecific  OBJECT IDENTIFIER ::= { rrTraps 0 }

alarmTrap       NOTIFICATION-TYPE
    OBJECTS     { rrTimeStamp,
                  rrSeqNum,
                  rrSeverity,
                  rrMoType,
                  rrMoId,
                  rrAddtlInfo 
                }
    STATUS      deprecated
    DESCRIPTION "Alarm notification."
    ::= { rrTrapSpecific 1 }

bootStatusUp    NOTIFICATION-TYPE
    OBJECTS     { rrTimeStamp,
                  rrSeqNum,
                  rrMoType,
                  rrMoId,
                  rrAddtlInfo 
                }
    STATUS      deprecated
    DESCRIPTION "The system is up and running."
    ::= { rrTrapSpecific 2 }

bootStatusDown  NOTIFICATION-TYPE
    OBJECTS     { rrTimeStamp,
                  rrSeqNum,
                  rrMoType,
                  rrMoId,
                  rrAddtlInfo 
                }
    STATUS      deprecated
    DESCRIPTION "The system has failed to boot or the system is shutting down."
    ::= { rrTrapSpecific 3 }


--
-- MCU Traps (specific 120 - 159)
--
mcuOperStatus   NOTIFICATION-TYPE
    OBJECTS     { rrTimeStamp,
                  rrSeqNum,
                  rrSeverity,
                  rrMoType,
                  rrMoId,
                  rrAddtlInfo
                }
    STATUS      deprecated
    DESCRIPTION "MCU operational status changed."
    ::= { rrTrapSpecific 120 }

mcuFaultLedStatus   NOTIFICATION-TYPE
    OBJECTS     { rrTimeStamp,
                  rrSeqNum,
                  rrSeverity,
                  rrMoType,
                  rrMoId,
                  rrAddtlInfo
                }
    STATUS      deprecated
    DESCRIPTION "MCU fault LED status changed."
    ::= { rrTrapSpecific 121 }

mcuTempStatus   NOTIFICATION-TYPE
    OBJECTS     { rrTimeStamp,
                  rrSeqNum,
                  rrSeverity,
                  rrMoType,
                  rrMoId,
                  rrAddtlInfo
                }
    STATUS      deprecated
    DESCRIPTION "MCU temperature status changed."
    ::= { rrTrapSpecific 122 }

mcuVoltageStatus    NOTIFICATION-TYPE
    OBJECTS     { rrTimeStamp,
                  rrSeqNum,
                  rrSeverity,
                  rrMoType,
                  rrMoId,
                  rrAddtlInfo
                }
    STATUS      deprecated
    DESCRIPTION "MCU voltage status changed."
    ::= { rrTrapSpecific 123 }



--
-- Backhaul Traps (specific 160 - 199)
--
mlpppStatus     NOTIFICATION-TYPE
    OBJECTS     { rrTimeStamp,
                  rrSeqNum,
                  rrSeverity,
                  rrMoType,
                  rrMoId,
                  rrAddtlInfo
                }
    STATUS      deprecated
    DESCRIPTION "Multilink PPP status changed."
    ::= { rrTrapSpecific 160 }



--
-- BBU Traps (specific 200 - 249)
--
bbuOperStatus   NOTIFICATION-TYPE
    OBJECTS     { rrTimeStamp,
                  rrSeqNum,
                  rrSeverity,
                  rrMoType,
                  rrMoId,
                  rrAddtlInfo
                }
    STATUS      deprecated
    DESCRIPTION "BBU operational status changed."
    ::= { rrTrapSpecific 200 }

bbuFaultLedStatus   NOTIFICATION-TYPE
    OBJECTS     { rrTimeStamp,
                  rrSeqNum,
                  rrSeverity,
                  rrMoType,
                  rrMoId,
                  rrAddtlInfo
                }
    STATUS      deprecated
    DESCRIPTION "BBU fault LED status changed."
    ::= { rrTrapSpecific 201 }

bbuTempStatus   NOTIFICATION-TYPE
    OBJECTS     { rrTimeStamp,
                  rrSeqNum,
                  rrSeverity,
                  rrMoType,
                  rrMoId,
                  rrAddtlInfo
                }
    STATUS      deprecated
    DESCRIPTION "BBU temperature status changed."
    ::= { rrTrapSpecific 202 }

bbuVoltageStatus    NOTIFICATION-TYPE
    OBJECTS     { rrTimeStamp,
                  rrSeqNum,
                  rrSeverity,
                  rrMoType,
                  rrMoId,
                  rrAddtlInfo
                }
    STATUS      deprecated
    DESCRIPTION "BBU voltage status changed."
    ::= { rrTrapSpecific 203 }

bbuDspStatus    NOTIFICATION-TYPE
    OBJECTS     { rrTimeStamp,
                  rrSeqNum,
                  rrMoType,
                  rrMoId,
                  rrAddtlInfo
                }
    STATUS      deprecated
    DESCRIPTION "BBU DSP status changed."
    ::= { rrTrapSpecific 204 }


--
-- AlarmInput Traps (specific 280 - 299)
--
alarmInputStatus NOTIFICATION-TYPE
    OBJECTS     { rrTimeStamp,
                  rrSeqNum,
                  rrSeverity,
                  rrMoType,
                  rrMoId,
                  rrAddtlInfo 
                }
    STATUS      deprecated
    DESCRIPTION "Alarm input status changed."
    ::= { rrTrapSpecific 280 }


--
-- Accounting/RADIUS Traps (specific 350 - 359)
--
accountingRadiusStatus  NOTIFICATION-TYPE
    OBJECTS     { rrTimeStamp,
                  rrSeqNum,
                  rrSeverity,
                  rrMoType,
                  rrMoId,
                  rrAddtlInfo 
                }
    STATUS      deprecated
    DESCRIPTION "Accounting/RADIUS server status changed."
    ::= { rrTrapSpecific 350 }


END
