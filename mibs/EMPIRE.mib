-- $Id: empire.asn1,v 1.2.2.6 2004/10/25 19:25:54 rpressw Exp $
-- $Log: empire.asn1,v $
-- Revision 1.2.2.6  2004/10/25 19:25:54  rpressw
-- PT42573 PT42373 PT42294 PT42270 PT42138 PT42058 PT41280 PT42143
--
-- Revision 1.2.2.5  2004/09/30 21:05:01  jtrammel
-- b2 sandbox fixes
--
-- Revision 1.2.2.4  2004/08/25 21:17:37  rpressw
-- HP-UX IA64 port
--
-- Revision 1.2.2.3  2004/07/09 15:04:20  rpressw
-- pt35703 empire.asn1 mosmod ccmmod
--
-- Revision 1.2.2.2  2004/06/11 00:42:20  jtrammel
-- sysedge 42p1b1 updates
--
-- Revision 1.2.2.1  2004/06/08 21:25:27  rpressw
-- PT39161 and backport of IS plugin issues
--
-- Revision 1.2  2003/12/12 15:27:52  jtrammel
-- r4_1p4_BRANCH merge
--
-- Revision 1.1.1.1.2.2  2003/10/13 17:57:12  jtrammel
-- viper rtm 10132003
--
-- Revision 1.1.1.1.2.1  2003/08/13 15:15:36  rpressw
-- rpressw checkin for 41pl4b1
--
-- Revision 1.1.1.1  2003/04/23 14:19:42  jtrammel
-- init cvs
--
-- # Revision 1.14  2003/03/24  15:20:41  jtrammel
-- # Checkpoint for 4.1pl3 release
-- #
-- # Revision 1.13  2002/07/26  14:36:09  rdk
-- # Checkpoint for June/July2002 release
-- #
-- Revision 1.12  2001/12/10  21:11:24  rdk
-- Checkpoint for 4.1 release
-- 
-- Revision 1.11  2000/11/07  12:14:59  rdk
-- Checkpoint for 4.0pl3
-- 
-- Revision 1.10  1998/10/09  20:39:31  rdk
-- Checkpoint for 3.1
-- 
-- Revision 1.9  1998/08/25  14:12:15  rdk
-- Checkpoint for 3.1 beta

-- Revision 1.8  1998/06/15  18:25:58  rdk
-- Checkpoint for 3.0PL5, prior to 3.1 development
--
-- Revision 1.7  1998/01/02  16:48:14  rdk
-- Checkpoint for 3.0
-- end
--

-- Concord/Empire Technologies, Inc. Private Enterprise MIB
-- for systems and application management
-- Copyright 2001-2004 Concord Communications, Inc.
-- http://www.concord.com

-- COPYRIGHT 2000 Empire Technologies, Inc. ALL RIGHTS RESERVED.
-- THIS DOCUMENT CONTAINS CONFIDENTIAL AND TRADE SECRET INFORMATION OF 
-- THE Empire Technologies, Inc.  COPYRIGHT NOTICE IS PRECAUTIONARY 
-- ONLY AND DOES NOT IMPLY PUBLICATION.

-- No part of this document may be reproduced, transmitted, transcribed,
-- stored in a retrieval system, or translated into any language or
-- computer language, in any form or by any means, without
-- prior written consent of Empire Technologies, Inc.

-- This MIB describes the Systems Management MIB
-- The MIB has been implemented on several platforms including: V.4 486,
-- SunOS/Sparc, Solaris/Sparc, Solaris/x86, HPUX-9/PARISC, 
-- HPUX-10/PARISC, NT-3.51/4.0/5.0 x86/Alpha, IRIX 6.x,
-- AIX 4.x, HPUX-11, Digital UNIX (Tru64), Linux, FreeBSD

--
-- Agent/MIB Version 4.2
-- 

EMPIRE DEFINITIONS ::= BEGIN
	IMPORTS
                OBJECT-TYPE
			FROM RFC-1212
		TRAP-TYPE
			FROM RFC-1215
                DisplayString
                        FROM RFC1213-MIB
                enterprises, TimeTicks, Counter, Gauge
                        FROM RFC1155-SMI;

-- Defined below is the main UNIX MIB tree

	empire 	   	OBJECT IDENTIFIER ::= { enterprises 546 }
	unix 	   	OBJECT IDENTIFIER ::= { empire 1 }
	dos 	   	OBJECT IDENTIFIER ::= { empire 2 }
	os2 	   	OBJECT IDENTIFIER ::= { empire 3 }
	windows    	OBJECT IDENTIFIER ::= { empire 4 }
	nt 	   	OBJECT IDENTIFIER ::= { empire 5 }
        monitor    	OBJECT IDENTIFIER ::= { empire 6 }
        empireexp  	OBJECT IDENTIFIER ::= { empire 7 }
        distribsys 	OBJECT IDENTIFIER ::= { empire 8 }
	traps      	OBJECT IDENTIFIER ::= { empire 9 }
	empireHistory   OBJECT IDENTIFIER ::= { empire 10 }
        logMonitor      OBJECT IDENTIFIER ::= { empire 11 }
        diskGroup       OBJECT IDENTIFIER ::= { empire 12 }
        cpuGroup        OBJECT IDENTIFIER ::= { empire 13 }
        extensionGroup  OBJECT IDENTIFIER ::= { empire 14 }
        processMonitor  OBJECT IDENTIFIER ::= { empire 15 }
        applications    OBJECT IDENTIFIER ::= { empire 16 }

	sysmgmt    OBJECT IDENTIFIER ::= { unix 1 }

-- DeleteButtonType enumeration for deleting row's in MIB tables

--DeleteButtonType ::= 
--     INTEGER {
--        delete(1),
--        valid(2)
--     }


-- The UNIX System Management MIB is defined below
-- and is intended for implementation on most major UNIX variants
-- 

--
-- The system group
--

	system	OBJECT IDENTIFIER ::= { sysmgmt 1 }

	nodename OBJECT-TYPE
		SYNTAX DisplayString
		ACCESS read-only
		STATUS mandatory
		DESCRIPTION
		   "The name of the system that the agent is
    		    running on as given by the login prompt."
	::= { system 1 }

	cpu OBJECT-TYPE
		SYNTAX DisplayString
		ACCESS read-only
		STATUS mandatory
		DESCRIPTION
		   "The CPU type of the system that the agent is
		    running on (e.g. sun4c, sun4m)."
	::= { system 2 }

	memory OBJECT-TYPE
		SYNTAX INTEGER
		ACCESS read-only
		STATUS mandatory
		DESCRIPTION
		   "The amount of memory in 1024 byte units
		    contained in the system."
	::= { system 3 }

	hostid OBJECT-TYPE
		SYNTAX DisplayString
		ACCESS read-only
		STATUS mandatory
		DESCRIPTION
		   "The hostid number that resides on the mother
                    board of the system that the agent is running
                    on.  The hostid is unique across all machines
                    manufactured by the same vendor."
	::= { system 4 }

	osver OBJECT-TYPE
		SYNTAX DisplayString
		ACCESS read-only
		STATUS mandatory
		DESCRIPTION
		   "The operating system version of the system
		    that the agent resides (e.g. 7).  Each time a
 		    new kernel is re-linked for a given kernel
		    configuration file, this number is incremented."
	::= { system 5 }

	osrel OBJECT-TYPE
		SYNTAX DisplayString
		ACCESS read-only
		STATUS mandatory
		DESCRIPTION
		   "The operating system release of the system
		    that the agent resides (e.g. 4.1.3)."
	::= { system 6 }

--
-- The Device Table
--
	devTable OBJECT-TYPE
                SYNTAX SEQUENCE OF DevTableEntry
 		ACCESS not-accessible
		STATUS mandatory
		DESCRIPTION
		   "This table describes all mounted file systems
		    on the system that the agent resides."
	::= { system 7 }

	devTableEntry OBJECT-TYPE
		SYNTAX DevTableEntry
		ACCESS not-accessible
		STATUS mandatory
		DESCRIPTION
		   "An entry in the device table."
		INDEX { devIndex }
	::= { devTable 1 }

	DevTableEntry ::= SEQUENCE {
		devIndex
			INTEGER,
		devDevice
			DisplayString,
		devMntPt
			DisplayString,
		devBsize
			INTEGER,
		devTblks
			INTEGER,
		devFblks
			Gauge,
		devTfiles
			INTEGER,
		devFfiles
			Gauge,
		devMaxNameLen
			INTEGER,
		devType
			DisplayString,
		devFsid
			INTEGER,
		devFstr
			DisplayString,
		devUnmount
			INTEGER,
		devCapacity
			INTEGER,
		devInodeCapacity
			INTEGER
	}

	devIndex OBJECT-TYPE
		SYNTAX INTEGER
		ACCESS read-only
		STATUS mandatory
		DESCRIPTION
		   "This object does not describe the mounted
		    device.  Its sole purpose is to indicate the
		    row instance.  The instance is derived from
		    the index number from the mounted file systems
		    file. "
		::= { devTableEntry 1 }

	devDevice OBJECT-TYPE
		SYNTAX DisplayString
		ACCESS read-only
		STATUS mandatory
		DESCRIPTION
		   "The device name (e.g. /dev/sd0a)
		    corresponding to the mounted file system.
		    For example, the '/' file system is commonly
		    mounted from the device '/dev/sd0a'.  For
		    network file systems, the value corresponds
		    to the remote host and remote file system
		    name (e.g. emptech:/usr/local)."
	::= { devTableEntry 2 }

	devMntPt OBJECT-TYPE
		SYNTAX DisplayString
		ACCESS read-only
		STATUS mandatory
		DESCRIPTION
		   "The mount point or path name in the local
		    file system where the device is mounted (e.g.
		    /home)." 
	::= { devTableEntry 3 }

	devBsize OBJECT-TYPE
		SYNTAX INTEGER
		ACCESS read-only
		STATUS mandatory
		DESCRIPTION
		   "The block size of the mounted device in
		    bytes.  File systems and disk devices
		    generally allocate data in fixed size
		    'blocks' generally referred to as the device's
		    block size.  Common block sizes are 1024 (1K) and
		    2048 (2K) bytes."
	::= { devTableEntry 4 }

	devTblks OBJECT-TYPE
		SYNTAX INTEGER
		ACCESS read-only
		STATUS mandatory
		DESCRIPTION
		   "The total number of blocks contained in the
		    mounted device." 
		::= { devTableEntry 5 }

	devFblks OBJECT-TYPE
		SYNTAX Gauge
		ACCESS read-only
		STATUS mandatory
		DESCRIPTION
		   "The total number of free or unallocated
		    blocks in the mounted device."
	::= { devTableEntry 6 }

	devTfiles OBJECT-TYPE
		SYNTAX INTEGER
		ACCESS read-only
		STATUS mandatory
		DESCRIPTION
		   "Each disk device and file system allocates a
		    fixed, maximum number of files that can be
		    written to the device.   The value of this
		    object indicates the maximum number of files
		    that can be written to this device."
	::= { devTableEntry 7 }

	devFfiles OBJECT-TYPE
		SYNTAX Gauge
		ACCESS read-only
		STATUS mandatory
		DESCRIPTION
		   "The number of free or unallocated files that
		    can be created on this device."
	::= { devTableEntry 8 }

	devMaxNameLen OBJECT-TYPE
		SYNTAX INTEGER
		ACCESS read-only
		STATUS mandatory
		DESCRIPTION
		   "The maximum file name length that this mounted
		    device supports.  If no fixed limit exists, 0
		    is returned."
	::= { devTableEntry 9 }

	devType OBJECT-TYPE
		SYNTAX DisplayString
		ACCESS read-only
		STATUS mandatory
		DESCRIPTION
		   "The type of the mounted device.  If this
		    underlying device does not support feature, 0
		    is returned. "
	::= { devTableEntry 10 }

	devFsid OBJECT-TYPE
		SYNTAX INTEGER
		ACCESS read-only
		STATUS mandatory
		DESCRIPTION
		   "The (possibly unique) file system ID of the
		    mounted device.  V.4 systems support its
		    uniqueness while SunOS does not.  For devices
		    or operating systems not supporting this
		    object, the object instance identifier is
		    returned instead."
	::= { devTableEntry 11 }

	devFstr OBJECT-TYPE
		SYNTAX DisplayString
		ACCESS read-only
		STATUS mandatory
		DESCRIPTION
		   "Some devices support a description string.
		    If supported by the underlying device and
		    operating system, that device specific
		    description string is returned.  If not
		    supported, the  string 'Not supported' is
		    returned.  An example description string may
		    be 'User home directories'." 
        ::= { devTableEntry 12 }

	devUnmount OBJECT-TYPE
--		SYNTAX DeleteButtonType
		SYNTAX INTEGER {
		  delete(1),
		  valid(2)
                }
		ACCESS read-write
		STATUS mandatory
		DESCRIPTION
		   "Writing a delete(1) to this object causes the agent
		    to unmount this device and remove its entry
		    from the mounted file system table.  Writing any
		    other value to this object will cause no
		    action to be taken by the agent."
	::= { devTableEntry 13 }

	devCapacity OBJECT-TYPE
		SYNTAX INTEGER (0..100)
		ACCESS read-only
		STATUS mandatory
		DESCRIPTION
		   "The percentage of the device's total capacity
		    in use."
	::= { devTableEntry 14 }

        devInodeCapacity OBJECT-TYPE
		SYNTAX INTEGER (0..100)
		ACCESS read-only
		STATUS mandatory
		DESCRIPTION
		   "The percentage of the device's total file capacity
                    (inodes) in use.  File systems often place an
                    upper bound on the number of files that can be
                    created on a filesystem.  This value indicates the
                    percentage of total possible files that are in
                    use.  Many times, NFS clients cannot determine
                    this value for remotely mounted filesystems; in
                    that case, 0 is returned." 
	::= { devTableEntry 15 }

--
-- The system group (continued)
--
	agentVersion OBJECT-TYPE
		SYNTAX DisplayString
		ACCESS read-only
		STATUS mandatory
		DESCRIPTION
		   "The agent's description and software version
		    number (e.g 'Concord . . . Ver 4.1')." 
	::= { system 8 }

--
-- The Kernel Config Group
--
-- This group gives Kernel configuration and identification information
--

        kernelConfig OBJECT IDENTIFIER ::= { system 9 }

        
        maxProcs OBJECT-TYPE 
                SYNTAX INTEGER
                ACCESS read-only
                STATUS mandatory
                DESCRIPTION
		   "Maximum number of slots in the system process
		    table or simply, the maximum number of
		    processes that may run at any one time on the
		    system."
          ::= { kernelConfig 1 }

        serialNumber OBJECT-TYPE 
                SYNTAX INTEGER
                ACCESS read-only
                STATUS mandatory
                DESCRIPTION
		   "The system's serial number.  This number is
		    different from the system's hostid value; it
		    should be unique across all platforms
		    manufactured by the same vendor." 
          ::= { kernelConfig 2 }

        romVersion OBJECT-TYPE 
                SYNTAX DisplayString
                ACCESS read-only
                STATUS mandatory
                DESCRIPTION
		   "The system's ROM version number (e.g 2.6).
		    Different versions of ROM often support
		    different commands and options.  Knowing the
		    system's ROM version number is often helpful
		    in debugging operating system problems."
          ::= { kernelConfig 3 }

        numCPU OBJECT-TYPE 
                SYNTAX Gauge
                ACCESS read-only
                STATUS mandatory
                DESCRIPTION
		   "The number of CPUs contained within this host."
          ::= { kernelConfig 4 }

        clockHZ OBJECT-TYPE 
                SYNTAX INTEGER
                ACCESS read-only
                STATUS mandatory
                DESCRIPTION
		   "The system's clock or 'tick' rate in HZ.
		    This is the rate at operating system is given
		    regularly, periodic interrupts in order to
		    handle I/O, schedule processes, etc.  This
		    value should not be confused with the CPU
		    clock speed which is generally on the order
		    mega-hertz."
          ::= { kernelConfig 5 }

        kernelVers OBJECT-TYPE 
                SYNTAX DisplayString
                ACCESS read-only
                STATUS mandatory
                DESCRIPTION
		   "The kernel version; This description string
		    is compiled into the kernel at kernel build
		    time and is generally used to convey
		    information about its functionality, patch
		    level, or administrative domain."
          ::= { kernelConfig 6 }

        virtualMem OBJECT-TYPE 
                SYNTAX Gauge
                ACCESS read-only
                STATUS mandatory
                DESCRIPTION
		   "The amount of virtual memory in 1024 byte
		    units (KBytes)."
          ::= { kernelConfig 7 }

        maxInode OBJECT-TYPE 
                SYNTAX Gauge
                ACCESS read-only
                STATUS mandatory
                DESCRIPTION
		   "Maximum number of in core file inodes
		    allocated by this host.  An inode is a data
		    structure used by a file system to describe a
		    file.  Part of it is cached in memory (in
		    core) while the other is stored on disk; the
		    kernel allocates a fixed amount of these 
		    structures at kernel boot time for use with
		    file I/O." 
          ::= { kernelConfig 8 }

        maxFiles OBJECT-TYPE 
                SYNTAX Gauge
                ACCESS read-only
                STATUS mandatory
                DESCRIPTION
		   "Maximum number of open files the system can
		    support at any one time.  The kernel
		    pre-allocates, at kernel boot time, a table
		    of structures for file I/O.  If the kernel does
                    not place any upper bound (e.g. Solaris 2.x), than
                    0 is returned." 
          ::= { kernelConfig 9 }

        maxClist OBJECT-TYPE 
                SYNTAX Gauge
                ACCESS read-only
                STATUS mandatory
                DESCRIPTION
		   "The maximum number of 'clist' structures
		    allocated by the kernel.  Line disciplines,
		    like terminals, manipulate data on 'clists'
		    which are essentially linked-lists of data
		    heading to and from terminal or serial
		    devices.  If the underlying operating system
		    does not utilize 'clists', then 0 is returned."
          ::= { kernelConfig 10 }

        maxMemPerProc OBJECT-TYPE 
                SYNTAX Gauge
                ACCESS read-only
                STATUS mandatory
                DESCRIPTION
		   "Maximum memory per process in KBytes.
		    Operating systems often set an upper limit on
		    the amount of memory a process may use.  If
		    the underlying operating system does not set
		    such a limit, than 0 is returned."
          ::= { kernelConfig 11 }

        totalSwap OBJECT-TYPE 
                SYNTAX INTEGER
                ACCESS read-only
                STATUS mandatory
                DESCRIPTION
		   "Total system swap space in KBytes.  Swap is a
		    region on secondary storage (primarily disks)
		    that is used for swapping and paging.
		    Swapping is a memory management policy in
		    which entire processes are written to
		    secondary storage when memory is in short
		    supply.  When a process begins, all its pages
		    are in virtual memory; only those pages
		    actively being used are brought in from disk
		    or swap."
          ::= { kernelConfig 12 }

        openMaxPerProc OBJECT-TYPE 
                SYNTAX INTEGER
                ACCESS read-only
                STATUS mandatory
                DESCRIPTION
		   "Maximum number of open files per process.
		    Each process is generally given a limit on
		    the maximum number of files it may have open
		    at any one time.  If the operating system
		    does not impose such limits, the value 0 is
		    returned."
          ::= { kernelConfig 13 }

        posixJobCtrl OBJECT-TYPE 
                SYNTAX INTEGER {
		    true(1),
		    false(2)
		 }
                ACCESS read-only
                STATUS mandatory
                DESCRIPTION
		   "Boolean variable indicating if Posix Job
		    Control supported.  POSIX, an IEEE standard,
		    defines a portable, open interface to
		    operating systems.  Part of the specification
		    includes the definition of support for
		    advanced job control.  This value indicates
		    whether the system supports POSIX-style job
		    control." 
          ::= { kernelConfig 14 }

        posixVersion OBJECT-TYPE 
                SYNTAX INTEGER
                ACCESS read-only
                STATUS mandatory
                DESCRIPTION
		   "The POSIX version number supported by host operating
		    system.  As new versions of POSIX are
		    released, it may be important to monitor
		    which host supports which version of the
		    POSIX standard." 
          ::= { kernelConfig 15 }

        pageSize OBJECT-TYPE
                SYNTAX INTEGER
                ACCESS read-only
                STATUS mandatory
                DESCRIPTION
		   "This object returns the number of bytes in a
		    page; a 'page' is the fixed size unit of
		    measurement when dealing with both virtual
		    and physical memory.  Page granularity is the
		    granularity of many of the memory statistics
		    and objects throughout the Concord MIB.  This
		    page size is an operating system page size
		    and may not correspond to the underlying
		    hardware page size." 
          ::= { kernelConfig 16 }

        wordSize OBJECT-TYPE
                SYNTAX INTEGER
                ACCESS read-only
                STATUS mandatory
                DESCRIPTION
		   "This object returns the kernel word size.
                    For example, if Solaris is booted with a 
                    64 bit kernel, this object would return
                    64.  If Solaris is booted with a 32 bit
                    kernel, this object would return 32.
                    This object is available in SystemEDGE 
                    4.1 and higher."
          ::= { kernelConfig 17 }

-- 
-- The Boot Config Group
--
-- This group identifies device and partition information that
-- the root, dump, and swap file systems reside on.
--

	bootconf OBJECT IDENTIFIER ::= { system 10 }


        rootName OBJECT-TYPE
                SYNTAX DisplayString
                ACCESS read-only
                STATUS mandatory
                DESCRIPTION
		   "The Device and partition (e.g. sd0a) that the root
		    filesystem is mounted from."
          ::= { bootconf 1 }

        rootFSType OBJECT-TYPE
                SYNTAX DisplayString
                ACCESS read-only
                STATUS mandatory
                DESCRIPTION
		   "The root filesystem type (e.g. 4.2)."
          ::= { bootconf 2 }

        rootBlocks OBJECT-TYPE
                SYNTAX INTEGER
                ACCESS read-only
                STATUS mandatory
                DESCRIPTION
		   "The total number of blocks contained in the
		    root filesystem.  The value 0 is returned if
		    unknown." 
          ::= { bootconf 3 }

        dumpName OBJECT-TYPE
                SYNTAX DisplayString
                ACCESS read-only
                STATUS mandatory
                DESCRIPTION
		   "The device and partition (e.g. sd0b) that the
		    dump filesystem is mounted from.  'Dump' is a
		    area of secondary storage reserved by the
		    operating system so that it may write
		    diagnostic information in the event of a
		    kernel crash."  
          ::= { bootconf 4 }

        dumpFSType OBJECT-TYPE
                SYNTAX DisplayString
                ACCESS read-only
                STATUS mandatory
                DESCRIPTION
		   "The dump filesystem type (e.g. spec).  Dump
		    is generally not a 'normal' file system like
		    UFS, 4.2, etc."
          ::= { bootconf 5 }

        dumpBlocks OBJECT-TYPE
                SYNTAX INTEGER
                ACCESS read-only
                STATUS mandatory
                DESCRIPTION
		   "The total number of blocks contained in the
		    dump filesystem."
          ::= { bootconf 6 } 

        swapName OBJECT-TYPE
                SYNTAX DisplayString
                ACCESS read-only
                STATUS mandatory
                DESCRIPTION
		   "The device and partition (e.g. sd0b) that
		    serves as swap space for the running kernel."
          ::= { bootconf 7 }

        swapFSType OBJECT-TYPE
                SYNTAX DisplayString
                ACCESS read-only
                STATUS mandatory
                DESCRIPTION
		    "The swap filesystem type (e.g. spec).  Swap
		     space is not generally a typical file system
		     like UFS, 4.2, etc."
          ::= { bootconf 8 }

        swapSize OBJECT-TYPE
                SYNTAX INTEGER
                ACCESS read-only
                STATUS mandatory
                DESCRIPTION
		   "The total number of blocks contained in the kernel's
		    swap area."
          ::= { bootconf 9 }


-- 
-- The Stream Group
--
-- This group reports statistics and configuration information for the
-- Streams network/terminal I/O subsystem
--
--
	streams OBJECT IDENTIFIER ::= { system 11 }


        maxmsgSize OBJECT-TYPE
                SYNTAX INTEGER
                ACCESS read-only
                STATUS mandatory
                DESCRIPTION
		    "The maximum Streams message size in bytes.
		     Streams often places a limit on the size of
		     an individual message.  If the underlying
		     system does not place such a limit, 0 is
		     returned." 
          ::= { streams 1 }

        maxNumPush OBJECT-TYPE
                SYNTAX INTEGER
                ACCESS read-only
                STATUS mandatory
                DESCRIPTION
		    "Maximum number of Streams modules that may be 
		     'pushed' onto an individual stream at any one
		     time.  If the underlying system does not
		     define such a limit, 0 is returned." 
          ::= { streams 2 }

        numMuxLinks OBJECT-TYPE
                SYNTAX Gauge
                ACCESS read-only
                STATUS mandatory
                DESCRIPTION
		    "Number of Streams multiplexor links."
          ::= { streams 3 }

        streamUse OBJECT-TYPE
                SYNTAX Gauge
                ACCESS read-only
                STATUS mandatory
                DESCRIPTION
		    "Current number of open 'streams' in the
		     system.  Operating systems often place a
		     limit on the number of streams that may be in
		     use at any one time.  Monitoring this variable 
		     and streamMax can indicate if additional
		     streams should be configured." 
          ::= { streams 4 }

        streamMaxs OBJECT-TYPE
                SYNTAX INTEGER
                ACCESS read-only
                STATUS mandatory
                DESCRIPTION
		    "The largest number of open 'streams' recorded
		     by the system.  This value represents a
		     'high-water' mark."
          ::= { streams 5 }

        streamFails OBJECT-TYPE
                SYNTAX Counter
                ACCESS read-only
                STATUS mandatory
                DESCRIPTION
		    "The number of 'stream' allocation failures
		     that have occurred.  Monitoring the streamUse,
		     streamMax, and streamFail variables can help
		     determine if the Streams subsystem is
		     properly configured." 
          ::= { streams 6 }

        queueUse OBJECT-TYPE
                SYNTAX Gauge
                ACCESS read-only
                STATUS mandatory
                DESCRIPTION
		    "Number of Streams queues currently in use by
		     the system.  Streams are composed of queues,
		     one for each direction of data flow.  The
		     value of this variable indicates the number
		     of queue data structures currently in use."
          ::= { streams 7 }

        queueMaxs OBJECT-TYPE
                SYNTAX INTEGER
                ACCESS read-only
                STATUS mandatory
                DESCRIPTION
		    "The largest number of open 'streams' recorded by 
		     the system.  This value represents the
		     'high-water' mark."
          ::= { streams 8 }

        queueFails OBJECT-TYPE
                SYNTAX Counter
                ACCESS read-only
                STATUS mandatory
                DESCRIPTION
		    "The number of Streams queue allocation
		     failures.  Monitoring the queueUse, queueMax,
		     and queueFail variables can help determine if
		     the Streams subsystem is properly configured."
          ::= { streams 9 }

        mblockUse OBJECT-TYPE
                SYNTAX Gauge
                ACCESS read-only
                STATUS mandatory
                DESCRIPTION
		    "The number of Streams message blocks currently in 
		     use.  Streams messages are composed of
		     message-blocks in a linked-list.  The value
		     of this variable indicates how many of the
		     systems message blocks are in use."
          ::= { streams 10 }

        mblockMaxs OBJECT-TYPE
                SYNTAX INTEGER
                ACCESS read-only
                STATUS mandatory
                DESCRIPTION
		    "The largest number of Streams message blocks in use
		     at any one time.  This value represents a
		     'high-water' mark."
          ::= { streams 11 }

        mblockFails OBJECT-TYPE
                SYNTAX Counter
                ACCESS read-only
                STATUS mandatory
                DESCRIPTION
		    "The number of Streams message block allocation 
		     failures.  Monitoring the mblockUse,
		     mblockMax, and mblockFail variables can help
		     determine if the Streams subsystem is
		     properly configured." 
          ::= { streams 12 }

        dblockUse OBJECT-TYPE
                SYNTAX Gauge
                ACCESS read-only
                STATUS mandatory
                DESCRIPTION
		    "The number of Streams data blocks currently
		     in use.  Message data is stored in
		     data-blocks; the value of this variable
		     indicates how many of the data-blocks are
		     currently in use."  
          ::= { streams 13 }

        dblockMaxs OBJECT-TYPE
                SYNTAX INTEGER
                ACCESS read-only
                STATUS mandatory
                DESCRIPTION
		    "The largest number of Streams data blocks in use
		     at any one time.  This value represents a
		     'high-water' mark."
          ::= { streams 14 }

        dblockFails OBJECT-TYPE
                SYNTAX Counter
                ACCESS read-only
                STATUS mandatory
                DESCRIPTION
		    "The number of Streams data block allocation
		     failures.  Monitoring the dblockUse,
		     dblockMax, and dblockFail variables can help
		     determine if the Streams subsystem is
		     properly configured."  
          ::= { streams 15 }

--
-- The system group (continued)
--
	systemType OBJECT-TYPE
		SYNTAX INTEGER {
                    unknown(1),
                    solarisSparc(2),   -- SunOS 5.x
                    solarisIntel(3),
                    solarisPPC(4),
                    sunosSparc(5),     -- SunOS 4.x
                    hpux9Parisc(6),
                    hpux10Parisc(7),
                    nt351Intel(8),
                    nt351Alpha(9),
                    nt40Intel(10),
                    nt40Alpha(11),
                    irix62Mips(12),
                    irix63Mips(13),
                    irix64Mips(14),
                    aix41RS6000(15),
                    aix42RS6000(16),
                    aix43RS6000(17),
                    irix65Mips(18),
                    digitalUNIX(19),   -- Tru64
                    linuxIntel(20),
                    hpux11Parisc(21),
                    nt50Intel(22),     -- win2k
                    nt50Alpha(23),
                    nt51Intel(24),     -- Windows XP
                    aix5RS6000(25),
                    nt52Intel(26),     -- Windows 2003
                    linuxIA64(27),     -- linux Itanium
                    hpux11IA64(28)     
                }
		ACCESS read-only
		STATUS mandatory
		DESCRIPTION
		   "The underlying system (hardware/OS) type"
	::= { system 12 }

	systemEdgeUptime OBJECT-TYPE
		SYNTAX TimeTicks
		ACCESS read-only
		STATUS mandatory
		DESCRIPTION
		   "The SystemEDGE agent's uptime. Use for uptime
                    calculations with variables in the Concord MIB.
                    This is the same value as returned by the uptime 
                    value in MIB2.  However, on some platforms (e.g. NT), 
                    that value is not returned by SystemEDGE and is 
                    thus inconsistent with the SystemEDGE uptime."
	::= { system 13 }

        sysedgeLicenseString OBJECT-TYPE
		SYNTAX DisplayString
		ACCESS read-only
		STATUS mandatory
		DESCRIPTION
		   "This object is used in conjunction Concord's
                    auto-licensing and remote licensing facility
                    starting in SystemEDGE 4.0."
        ::= { system 14 }

        sysedgeLicenseKey OBJECT-TYPE
		SYNTAX DisplayString
		ACCESS read-write
		STATUS mandatory
		DESCRIPTION
		   "This object is used in conjunction Concord's
                    auto-licensing and remote licensing facility
                    starting in SystemEDGE 4.0."
        ::= { system 16 }

        sysedgeMode OBJECT-TYPE
		SYNTAX INTEGER {
                    fullMode(1),
                    restrictedMode(2)
                }
		ACCESS read-only
		STATUS mandatory
		DESCRIPTION
		   "This object indicates if SystemEDGE is in
                    full-mode or restricted-mode.  Restricted-mode
                    is entered, when SystemEDGE 4.0 and higher,
                    fails to find a valid license.  Once
                    a valid license has been allocated and
                    set, SystemEDGE will then transition to
                    fullMode(1)"
        ::= { system 17 }

        systemTimeZone OBJECT-TYPE
		SYNTAX DisplayString
		ACCESS read-only
		STATUS mandatory
		DESCRIPTION
		   "The timezone this system is in obtained via
                    TZ environment variable (UNIX) or NT win32
                    call.  If SystemEDGE is unable to determine the
                    timezone, 'unknown' is returned.  This value
                    is operating-system depdendent in that each
                    OS often has slightly different names for same
                    timezone."
        ::= { system 18 }

        sysedgeAddressList OBJECT-TYPE
		SYNTAX DisplayString
		ACCESS read-only
		STATUS mandatory
		DESCRIPTION
		   "The space-separated list of up to 5 past IP
                    addresses that this system was configured for.
                    This MIB object, when used with the
		    addrChangeTrap, is useful to pollers trying to poll
		    client machines whose addresses change due to DHCP or
		    with mobile systems or those whose configuration
		    changes over time.  Addresses are ordered with
		    most-recently from most-recently used to
                    least-recently used (left to right)."
        ::= { system 19 }

        sysedgeFQDN OBJECT-TYPE
		SYNTAX DisplayString
		ACCESS read-only
		STATUS mandatory
		DESCRIPTION
		   "The system's fully qualified domain name (FQDN);
		    this MIB object is a duplicate of
		    mib-2.system.sysName but is repeated here for
		    platform consistency (e.g. NT vs. UNIX)."
        ::= {system 20 }

        sysedgeConfProfile OBJECT-TYPE
		SYNTAX DisplayString (SIZE (0..1024))
		ACCESS read-write
		STATUS mandatory
		DESCRIPTION
		   "A space-separated list of configuration profile
		    names currently configured in SystemEDGE.
		    Configuration profiles are managed by AdvantEDGE
		    View; AdvantEDGE View uses this MIB object to
		    store, with each agent, which profiles are
		    currently deployed to that agent.  Writing to or
		    modifying this variable outside of AdvantEDGE View
		    is strongly discouraged.  This MIB variable should
		    not contain single nor double quotations."
        ::= {system 21 }

	sysedgeInstallDir OBJECT-TYPE
		SYNTAX DisplayString 
		ACCESS read-only
		STATUS mandatory
		DESCRIPTION
		   "The directory where the SystemEDGE distribution is
  		    installed (e.g. c:\sysedge or /opt/EMPsysedge).
		    One can use this value to help configure actions,
		    extensions, etc."
        ::= {system 22 }

        sysedgePluginList OBJECT-TYPE
		SYNTAX DisplayString 
		ACCESS read-only
		STATUS mandatory
		DESCRIPTION
		   "A comma-separated list of plugins that are
                    currently loaded into SystemEDGE.  Management
		    software can use this MIB object to determine
		    installation and upgrade requirements.  If no
		    plugins are loaded, a zero-length string is
		    returned." 
        ::= {system 23 }


--
-- The User Table
--

	userTable OBJECT-TYPE
		SYNTAX SEQUENCE OF UserEntry
		ACCESS not-accessible
		STATUS mandatory
		DESCRIPTION
		    "Table describing defined users of the node
		     which the agent resides on.  Normally, the
		     list of valid users is stored in the
		     /etc/passwd file; on systems which run NIS or
		     NIS+, this table represents both users in the
		     /etc/passwd file and in the NIS passwd file."
	::= { sysmgmt 2 }

	userEntry OBJECT-TYPE
		SYNTAX UserEntry
		ACCESS not-accessible
		STATUS mandatory
		DESCRIPTION
		    "An entry in the table describing defined users."
		INDEX { userIndex }
	::= { userTable 1 }

	UserEntry ::= SEQUENCE {
		userIndex
			INTEGER,
		userLoginID
			DisplayString,
		userPasswd
			DisplayString,
		userUID
			INTEGER,
		userGID
			INTEGER,
		userName
			DisplayString,
		userHomeDir
			DisplayString,
		userShell
			DisplayString
	}

	userIndex OBJECT-TYPE
		SYNTAX INTEGER
		ACCESS read-only
		STATUS mandatory
		DESCRIPTION
		   "The instance of the userEntry object, derived
		    from its index number in the password file."
	::= { userEntry 1 }

	userLoginID OBJECT-TYPE
		SYNTAX DisplayString
		ACCESS read-only
		STATUS mandatory
		DESCRIPTION
		   "The user's login ID which is normally given
		    to the system's login prompt (e.g. root)."
	::= { userEntry 2 }

	userPasswd OBJECT-TYPE
		SYNTAX DisplayString
		ACCESS read-only
		STATUS mandatory
		DESCRIPTION
		   "The user's encrypted password.  Users without
		    passwords have an '*' in this field."
	::= { userEntry 3 }

	userUID OBJECT-TYPE
		SYNTAX INTEGER
		ACCESS read-only
		STATUS mandatory
		DESCRIPTION
		   "The user's User-ID or UID (e.g. 0)."
	::= { userEntry 4 }

	userGID OBJECT-TYPE
		SYNTAX INTEGER
		ACCESS read-only
		STATUS mandatory
		DESCRIPTION
		   "The user's Group-ID or GID (e.g. 1)."
	::= { userEntry 5 }

	userName OBJECT-TYPE
		SYNTAX DisplayString
		ACCESS read-only
		STATUS mandatory
		DESCRIPTION
		   "The user's real life name (e.g. John Doe)."
	::= { userEntry 6 }

	userHomeDir OBJECT-TYPE
		SYNTAX DisplayString
		ACCESS read-only
		STATUS mandatory
		DESCRIPTION
		   "The user's home directory when that user logs
		    in (e.g. /home/john)."
	::= { userEntry 7 }

	userShell OBJECT-TYPE
		SYNTAX DisplayString
		ACCESS read-only
		STATUS mandatory
		DESCRIPTION
		   "The user's preferred shell (e.g. /bin/csh)."
	::= { userEntry 8 }

--
-- The Group Table
--

	groupTable OBJECT-TYPE
		SYNTAX SEQUENCE OF GroupEntry
		ACCESS not-accessible
		STATUS mandatory
		DESCRIPTION
		   "Table describing defined groups on node that
		    agent resides.  Normally the list of valid
		    user groups is stored in the file /etc/group.
		    On systems running NIS or NIS+, this table
		    represents valid groups in /etc/group and in
		    the NIS group file." 
	::= { sysmgmt 3 }

	groupEntry OBJECT-TYPE
		SYNTAX GroupEntry
		ACCESS not-accessible
		STATUS mandatory
		DESCRIPTION
		   "Entry in table describing valid groups."
		INDEX { groupIndex }
	::= { groupTable 1 }

	GroupEntry ::= SEQUENCE {
		groupIndex
			INTEGER,
		groupName
			DisplayString,
		groupPasswd
			DisplayString,
		groupGID
			INTEGER
	}

	groupIndex OBJECT-TYPE
		SYNTAX INTEGER
		ACCESS read-only
		STATUS mandatory
		DESCRIPTION
		   "The instance of the groupEntry object,
		    derived from its index in the groups file."
	::= { groupEntry 1 }

	groupName OBJECT-TYPE
		SYNTAX DisplayString
		ACCESS read-only
		STATUS mandatory
		DESCRIPTION
		   "The name of the group (e.g. wheel)."
	::= { groupEntry 2 }

	groupPasswd OBJECT-TYPE
		SYNTAX DisplayString
		ACCESS read-only
		STATUS mandatory
		DESCRIPTION
		   "The encrypted password for the group.  Groups
		    without passwords have an '*' in this field."
	::= { groupEntry 3 }

	groupGID OBJECT-TYPE
		SYNTAX INTEGER
		ACCESS read-only
		STATUS mandatory
		DESCRIPTION
		   "The group-ID or GID (e.g. 1)."
	::= { groupEntry 4 }

--
-- The Process Table
--
-- This group provides access to the kernel's process table which can
-- be queried to find out information on processes currently running
-- on this host.
--

	processTable OBJECT-TYPE
		SYNTAX SEQUENCE OF ProcessEntry
		ACCESS not-accessible
		STATUS mandatory
		DESCRIPTION
		   "Table describing currently running processes
		    on the node which the SNMP agent resides."
	::= { sysmgmt 4 }

	processEntry OBJECT-TYPE
		SYNTAX ProcessEntry
		ACCESS not-accessible
		STATUS mandatory
		DESCRIPTION
		   "Each entry in the process table represents a
		    single running process.  Because the SNMP standard
                    does not allow tables to be indexed with the value
                    0, and because PID 0 is valid on many UNIX and NT
                    systems, SystemEDGE really indexes the
                    processTable with processID+1.  That is, process
                    with PID 0 is contained at table index 1."
		INDEX { processID }
	::= { processTable 1 }

	ProcessEntry ::= SEQUENCE {
		processID
			INTEGER,
		processName
			DisplayString,
		processState
			INTEGER,
		processNice
			INTEGER,
		processFlags
			INTEGER,
		processUID
			INTEGER,
		processGID
			INTEGER,
		processKill
			INTEGER,
		processMEM
			Gauge,
		processSize
			Gauge,
		processRSS
			Gauge,
		processTime
			INTEGER,
                processParentPID
			INTEGER,
                processNumThreads
			INTEGER,
                processInBlks
                        Counter,
                processOutBlks
                        Counter,
                processMsgsSent
                        Counter,
                processMsgsRecv
                        Counter,
                processSysCalls
                        Counter,
                processMinorPgFlts
			Counter,
                processMajorPgFlts
			Counter,
                processNumSwaps
			Counter,
                processVolCtx
			Counter,
                processInvolCtx
			Counter,
                processArgs
			DisplayString,
		processStartTime
			DisplayString,
		processStateStr
			DisplayString,
		processStateInt
			INTEGER
	}

	processID OBJECT-TYPE
		SYNTAX INTEGER
		ACCESS read-only
		STATUS mandatory
		DESCRIPTION
		   "The unique process ID (e.g. 0).  The value of this
		    object also serves as the instance of the
		    processEntry object."
	::= { processEntry 1 }

	processName OBJECT-TYPE
		SYNTAX DisplayString
		ACCESS read-only
		STATUS mandatory
		DESCRIPTION
		   "The name of the running process (e.g. swapper)."
	::= { processEntry 2 }

	processState OBJECT-TYPE
		SYNTAX INTEGER
		ACCESS read-only
		STATUS deprecated
		DESCRIPTION
		   "The process state is operating system
		    dependent.  Possible states (for SunOS 4.1.3)
		    include sleeping(1), waiting(2), running (3),
		    idle (4), zombie (5), stopped(6), unknown(7).
                    This MIB object should be deprecated in favor
                    of processStateStr which is portable and
                    standard across all platforms.  processState
                    values are platform specific and thus harder
                    to handle in platform-independent manner."
	::= { processEntry 3 }

	processNice OBJECT-TYPE
		SYNTAX INTEGER
		ACCESS read-write
		STATUS mandatory
		DESCRIPTION
		   "The 'nice' value of the process which can be
		    modified to give a process greater or lesser
		    priority over other processes.  The 'nice'
		    value reflects the level of priority that the
		    running process has; the higher the value,
		    the lower the priority the process has." 
	::= { processEntry 4 }

	processFlags OBJECT-TYPE
		SYNTAX INTEGER
		ACCESS read-only
		STATUS mandatory
		DESCRIPTION
		   "The process flags; flags are operating system
		    dependent and are generally documented in
		    system header files."
	::= { processEntry 5 }

	processUID OBJECT-TYPE
		SYNTAX INTEGER
		ACCESS read-only
		STATUS mandatory
		DESCRIPTION
		   "The process owner's user ID (e.g. 0 for root)."
	::= { processEntry 6 }

	processGID OBJECT-TYPE
		SYNTAX INTEGER
		ACCESS read-only
		STATUS mandatory
		DESCRIPTION
		   "The process owner's group ID (e.g. 0 for wheel)."
	::= { processEntry 7 }

	processKill OBJECT-TYPE
		SYNTAX INTEGER
		ACCESS read-write
		STATUS mandatory
		DESCRIPTION
		   "This object represents a signal that can be
		    sent to the running process.  When accessed
		    with GET or GetNext, a 0 is returned.  When a
		    valid signal value is written, the agent
		    sends that signal to the corresponding process. 
		    To kill or delete a process from the process
		    table, the value corresponding to SIGKILL(9)
		    should be written to this object.  Signals
		    are defined in a system dependent manner and
		    are usually defined in system header files
		    and manual pages."  
	::= { processEntry 8 }

	processMEM OBJECT-TYPE
		SYNTAX Gauge
		ACCESS read-only
		STATUS mandatory
		DESCRIPTION
		   "The percentage (0-100) of real memory used by
		    this process." 
	::= { processEntry 9 }

	processSize OBJECT-TYPE
		SYNTAX Gauge
		ACCESS read-only
		STATUS mandatory
		DESCRIPTION
		   "The combined size of the text, data and stack segments 
		    in KBytes.  Processes are normally broken
		    into segments including those for text (or
		    program), data, and stack.  This variable
		    indicates how large the variable size portion
		    of a process is.  Monitoring this value can
		    help determine the health of a process."
	::= { processEntry 10 }

	processRSS OBJECT-TYPE
		SYNTAX Gauge
		ACCESS read-only
		STATUS mandatory
		DESCRIPTION
		   "Real memory (resident set) size of the process in
		    kilobytes.  This value indicates how many
		    bytes are held by a process."
	::= { processEntry 11 }

	processTime OBJECT-TYPE
		SYNTAX INTEGER
		ACCESS read-only
		STATUS mandatory
		DESCRIPTION
		   "This process' accumulated CPU time in seconds."
	::= { processEntry 12 }

        processParentPID OBJECT-TYPE
		SYNTAX INTEGER
		ACCESS read-only
		STATUS mandatory
		DESCRIPTION
		   "This process' parent process ID (PID)."
	::= { processEntry 13 }

        processNumThreads OBJECT-TYPE
		SYNTAX INTEGER
		ACCESS read-only
		STATUS mandatory
		DESCRIPTION
		   "The number of threads executing within this
                    process.  Note, on some systems, the operating
                    system may be un-aware of user-level threads
                    executing within the process.  This object
                    reflects the number of threads executing within
                    the process that the operating system is aware of." 
	::= { processEntry 14 }

        processInBlks OBJECT-TYPE
		SYNTAX Counter
		ACCESS read-only
		STATUS mandatory
		DESCRIPTION
		   "The number of blocks of data input by the process."
	::= { processEntry 15 }

        processOutBlks OBJECT-TYPE
		SYNTAX Counter
		ACCESS read-only
		STATUS mandatory
		DESCRIPTION
		   "The number of blocks of data output by the process."
	::= { processEntry 16 }

        processMsgsSent OBJECT-TYPE
		SYNTAX Counter
		ACCESS read-only
		STATUS mandatory
		DESCRIPTION
		   "The number of messages sent by the process."
	::= { processEntry 17 }

        processMsgsRecv OBJECT-TYPE
		SYNTAX Counter
		ACCESS read-only
		STATUS mandatory
		DESCRIPTION
		   "The number of messages received by the process."
	::= { processEntry 18 }

        processSysCalls OBJECT-TYPE
		SYNTAX Counter
		ACCESS read-only
		STATUS mandatory
		DESCRIPTION
		   "The number of system calls invoked by this process."
	::= { processEntry 19 }

        processMinorPgFlts OBJECT-TYPE
		SYNTAX Counter
		ACCESS read-only
		STATUS mandatory
		DESCRIPTION
		   "The number of minor page faults incurred by this
                    process.  Minor faults do not require I/O to
                    retrieve the page." 
	::= { processEntry 20 }

        processMajorPgFlts OBJECT-TYPE
		SYNTAX Counter
		ACCESS read-only
		STATUS mandatory
		DESCRIPTION
		   "The number of major page faults incurred by this
                    process.  Major faults require I/O to retrieve the
                    page."  
	::= { processEntry 21 }

        processNumSwaps OBJECT-TYPE
		SYNTAX Counter
		ACCESS read-only
		STATUS mandatory
		DESCRIPTION
		   "The number of times this process has been swapped."
	::= { processEntry 22 }

        processVolCtx OBJECT-TYPE
		SYNTAX Counter
		ACCESS read-only
		STATUS mandatory
		DESCRIPTION
		   "The number of voluntary context switches incurred
                    by this process.  Voluntary context switches occur
                    when the processor 'voluntary' gives up the CPU
                    (e.g. waiting on I/O.)"
	::= { processEntry 23 }

        processInvolCtx OBJECT-TYPE
		SYNTAX Counter
		ACCESS read-only
		STATUS mandatory
		DESCRIPTION
		   "The number of involuntary context switches
                    incurred by this process.   An involuntary context
                    switch occurs when the process has executed for
                    the duration of its time quantum and is switched
                    out by the process scheduler." 
	::= { processEntry 24 }

        processArgs OBJECT-TYPE
		SYNTAX DisplayString
		ACCESS read-only
		STATUS mandatory
		DESCRIPTION
		   "The parameters supplied to this process when it
                    was initially started."
	::= { processEntry 25 }

	processStartTime OBJECT-TYPE
		SYNTAX DisplayString
		ACCESS read-only
		STATUS mandatory
		DESCRIPTION
		    "The date/time at which this process started.  The
                     format is as follows: to local time in the form
                     of  a  26-character string as shown below. Time
                     zone and daylight savings corrections are  made
                     before  string  generation.  The fields are
                     constant width: 
                          Fri Sep 13 00:00:00 1986\n"
	::= { processEntry 26 }

	processStateStr OBJECT-TYPE
		SYNTAX DisplayString
		ACCESS read-only
		STATUS mandatory
		DESCRIPTION
		   "The process state in an operating-system
                    independent format.  A process-state matrix
                    is included below.  Note that not all operating
                    systems may support a specific process-state.

                State          Description
                --------       --------------------------------
                starting       Process under creation
                runnable       Process is on run queue
                sleeping       Process is waiting for event to complete
                sleep          Uninterruptible sleep (usually IO)
                zombie         Process terminated; parent not waiting
                stop           Process stopped either by job control
                               signal or because it is being traced
                active         The process is running on a processor
                swapped        Process is swapped out to secondary storage
                wait           Process is waiting for memory;
                               subclass of sleeping state
                other          Misc state 
                               (forking, exiting, transition, etc.)
                "       
	::= { processEntry 27 }

        processStateInt OBJECT-TYPE
	        SYNTAX INTEGER {
                   procStateStarting(1),
                   procStateRunnable(2),
                   procStateActive(3),
                   procStateWait(4),
                   procStateSleeping(5),
                   procStateSwapped(6),
                   procStateSleep(7),
                   procStateStop(8),
                   procStateOther(9),
                   procStateZombie(10)
                }
		ACCESS read-only
		STATUS mandatory
		DESCRIPTION
		   "The process state, as above, represented by
	            integer for easier polling and trending."
	::= { processEntry 28 }

--
-- The Who Table
--
-- Who is logged onto this system
--

	whoTable OBJECT-TYPE
		SYNTAX SEQUENCE OF WhoEntry
		ACCESS not-accessible
		STATUS mandatory
		DESCRIPTION
		   "This table represents users who are currently logged
		    into the node which the agent resides."
	::= { sysmgmt 5 }

	whoEntry OBJECT-TYPE
		SYNTAX WhoEntry
		ACCESS not-accessible
		STATUS mandatory
		DESCRIPTION
		   "An entry in the who table."
		INDEX { whoIndex }
	::= { whoTable 1 }

	WhoEntry ::= SEQUENCE {
		whoIndex
			INTEGER,
		whoName
			DisplayString,
		whoDevice
			DisplayString,
		whoPID
			INTEGER,
		whoTime
			TimeTicks,
		whoWhere
			DisplayString
	}

	whoIndex OBJECT-TYPE
		SYNTAX INTEGER
		ACCESS read-only
		STATUS mandatory
		DESCRIPTION
		   "The instance of the whoEntry object."
	::= { whoEntry 1 }

	whoName OBJECT-TYPE
		SYNTAX DisplayString
		ACCESS read-only
		STATUS mandatory
		DESCRIPTION
		   "The user name of a user logged into the node which
		    the agent resides (e.g. root)."
	::= { whoEntry 2 }

	whoDevice OBJECT-TYPE
		SYNTAX DisplayString
		ACCESS read-only
		STATUS mandatory
		DESCRIPTION
		   "The device the user is using to log into the
		    node which the agent resides (e.g. console or
		    ttyp1)." 
	::= { whoEntry 3 }

	whoPID OBJECT-TYPE
		SYNTAX INTEGER
		ACCESS read-only
		STATUS mandatory
		DESCRIPTION
		   "This object represents the process ID for the
		    user's login shell.  This object is not
		    supported on SunOS 4.X systems; 0 is returned
		    instead." 
	::= { whoEntry 4 }

	whoTime OBJECT-TYPE
		SYNTAX TimeTicks
		ACCESS read-only
		STATUS mandatory
		DESCRIPTION
		   "The time, in SNMP TimeTicks, when the user first
		    logged in." 
		::= { whoEntry 5 }

	whoWhere OBJECT-TYPE
		SYNTAX DisplayString
		ACCESS read-only
		STATUS mandatory
		DESCRIPTION
		   "The location the user logged in from if
		    applicable. (e.g. :0.0 if local or host name
		    if logged in from a remote system)."
	::= { whoEntry 6 }

--
-- The Remote Shell Group
--
-- A remote shell is invoked in the following manner via:
--    1) Write (via SNMP SET) a filename that all output
--       from the resulting remote shell invocation will
--       be placed in.  This file shall reside in '/tmp'
--       for safety and security considerations
--
--    2) Write (via SNMP SET) the command and arguments to be executed
--       by the agent.  When the object is SET (given that
--       shellOutput has been properly set) the agent invokes (via
--       fork/exec) the command and redirects the output into the file
--       given by the value in shellOutput.
--
--    3) When complete, the remote shell invocation's exit status
--       is placed in the object shellExitStat
--

	remoteShell OBJECT IDENTIFIER ::= { sysmgmt 6 }

	shellOutput OBJECT-TYPE
		SYNTAX DisplayString
		ACCESS read-write
		STATUS mandatory
		DESCRIPTION
		   "The name of a file that will receive all
		    output from the execution of a UNIX command
		    initiated by the agent.  This file is
		    restricted to the '/tmp' ('\temp' or '\tmp' for
                    NT) directory for security and safety
                    considerations.  If the value object is set to
                    anything other that that residing in '/tmp' or a
                    relative pathname, an error will be returned."
	::= { remoteShell 1 }

	shellCmd OBJECT-TYPE
		SYNTAX DisplayString
		ACCESS read-write
		STATUS mandatory
		DESCRIPTION
		   "The command and arguments to be executed by 
		    the agent.  When this object is SET, (and 
                    a valid shellOutput object exists), the agent 
                    fork/execs the command with STDOUT and STDERR going
                    to the value of shellOutput.  On NT systems, the
                    command is run synchronously so care should be
                    taken not to block the subagent indefinitely." 
	::= { remoteShell 2 }

	shellExitStat
		OBJECT-TYPE
		SYNTAX INTEGER
		ACCESS read-only
		STATUS mandatory
		DESCRIPTION
		   "The exit code from the execution of a shell
		    command.  The value remains unchanged until
		    another command is executed.  Each execution
		    of a shell command overwrites the previous
		    value of this object.  On some systems (HPUX-9),
                    the exit status is not available if the shell
                    command was invoked in the background in order to
                    avoid defunct or zombie processes waiting on that
                    shell command's exit value."
	::= { remoteShell 3 }

        shellOutputContents OBJECT-TYPE
		SYNTAX DisplayString (SIZE (0..512))
		ACCESS read-only
		STATUS mandatory
		DESCRIPTION
		   "This object returns up to the first 512 characters
                    of the last shell-command output stored in the file
                    specified by shellOutput (remoteShell.1).  No
                    attempt at translating the character output is
                    made by the agent."
	::= { remoteShell 4}

--
-- The Performance Group
--
-- Performance related parameters and statistics
--
	performance OBJECT IDENTIFIER ::= { sysmgmt 7 }
	kernelperf  OBJECT IDENTIFIER ::= { performance 8 }

--
-- Kernel performance related stats
--

-- kernelperf objects 1,2,3 deprecated and removed
-- from MIB spec to reduce confusion with other CPU stats
-- monitoring objects in the cpuGroup

        runQLen OBJECT-TYPE
		SYNTAX Gauge
		ACCESS read-only
		STATUS mandatory
		DESCRIPTION
		   "The length of the scheduler's run queue
		    sampled over a fixed period of time.  The
		    sampling interval is system dependent.  In
		    SunOS, the kernel updates this parameter once
		    every 5 seconds.  The system's load average
		    is computed from the value of runQLen; the
		    load average is defined as the average
		    runQLen value over some interval."
	::= { kernelperf 4 }

        diskWaitNum OBJECT-TYPE
		SYNTAX Gauge
		ACCESS read-only
		STATUS mandatory
		DESCRIPTION
		    "The number of jobs that are waiting on disk 
		    I/O sampled over a fixed period of time.  The
		    sampling interval is system dependent.  In
		    SunOS, the kernel updates this parameter once
		    every 5 seconds.  A large value may indicate
		    an overloaded system although larger values
		    may be observed on file server systems."
	::= { kernelperf 5 }

        pageWaitNum OBJECT-TYPE
		SYNTAX Gauge
		ACCESS read-only
		STATUS mandatory
		DESCRIPTION
		    "The number of jobs that are waiting on page
		    I/O sampled over a fixed period of time.  The
		    sampling interval is system dependent.  In
		    SunOS, the kernel updates this parameter once
		    every 5 seconds.  A large value may indicate
		    the system does not have enough memory for
		    the current load." 
	::= { kernelperf 6 }

        swapActive OBJECT-TYPE
		SYNTAX Gauge
		ACCESS read-only
		STATUS mandatory
		DESCRIPTION
		    "The number of jobs that are active yet
		     swapped out of memory, sampled over a fixed
		     period of time.  The sampling interval is
		     system dependent.  In SunOS, the kernel
		     updates this parameter once every 5 seconds.
		     A high value for this object may indicate
		     that system memory is not sufficient for the
		     current load."
	::= { kernelperf 7 }

        sleepActive OBJECT-TYPE
		SYNTAX Gauge
		ACCESS read-only
		STATUS mandatory
		DESCRIPTION
		    "The number of jobs that are active yet
		     sleeping in core, sampled over a fixed
		     period of time.  The sampling interval is
		     system dependent.  In SunOS, the kernel
		     updates this parameter once every 5 seconds.
		     A process is active yet sleeping in core
		     when it is not running and not swapped out
		     to secondary storage (swap)."
	::= { kernelperf 8 }

        memInUse OBJECT-TYPE
		SYNTAX Gauge
		ACCESS read-only
		STATUS mandatory
		DESCRIPTION
		    "The total real KBytes of memory in use
		     sampled over a fixed period of time.  The
		     sampling interval is system dependent.  In
		     SunOS, the kernel updates this parameter
		     once every 5 seconds.  Comparing memInUse to
		     memory (in the Concord 'system' group) can
		     help indicate if a system has sufficent
		     memory for its current load." 
	::= { kernelperf 9 }

        activeMem OBJECT-TYPE
		SYNTAX Gauge
		ACCESS read-only
		STATUS mandatory
		DESCRIPTION
		    "The total active real memory (KBytes)
		     sampled over a fixed period of time.  The
		     sampling interval is system dependent.  In
		     SunOS, the kernel updates this parameter
		     once every 5 seconds.  Memory is active when
		     it is actually being used by a process
		     running in memory.  This value should be
		     less than or equal to memInUse.  A high
		     value may indicate a system with
		     insufficient memory."
	::= { kernelperf 10 }

        numProcs OBJECT-TYPE
		SYNTAX Gauge
		ACCESS read-only
		STATUS mandatory
		DESCRIPTION
		     "The number of processes table slots currently 
		      allocated and in use.  On older BSD-based
                      systems, this metric is important since it
                      places an uppder bound on the total number of
                      processes that may run on the system at any one
                      time." 
	::= { kernelperf 11 }

        numOpenFiles OBJECT-TYPE
		SYNTAX Gauge
		ACCESS read-only
		STATUS mandatory
		DESCRIPTION
		     "The system-wide total number of open files."
	::= { kernelperf 12 }

        swapInUse OBJECT-TYPE
                SYNTAX Gauge
		ACCESS read-only
		STATUS mandatory
		DESCRIPTION
		     "The amount of swap space (KBytes) currently in 
		      use by the system.  Swap space is used when
		      memory is in short supply.  Typically,
		      entire processes are swapped out to
		      secondary storage.  Comparing this value to
		      totalSwap (in Concord's kernelConfig group)
		      can help indicate if additional swap space
		      is needed."
	::= { kernelperf 13 }

        numSwitches OBJECT-TYPE
		SYNTAX Counter
		ACCESS read-only
		STATUS mandatory
		DESCRIPTION
		   "The total number of context switches that
		    have occurred since the kernel was last
		    initialized.  A context switch occurs each
		    time a process gives up the CPU and another
		    takes its place.  This counter reflects the
		    level of system activity; a high rate of
		    context switching is indicative of the system load."
	::= { kernelperf 14 }

        numTraps OBJECT-TYPE
		SYNTAX Counter
		ACCESS read-only
		STATUS mandatory
		DESCRIPTION
		   "The total number of traps switching a process
		    from user to kernel mode that have occurred since
		    the kernel was last initialized.  Traps are
		    hardware exceptions that occur and are
		    usually caused by the currently running
		    process.  Example traps include those for
		    incorrect arithmetic operations, segmentation
		    violations or page faults.  An excessive trap 
		    rate can indicate a faulty program, excessive
		    system loading, or some other abnormality."
	::= { kernelperf 15 }

        numSyscalls OBJECT-TYPE
		SYNTAX Counter
		ACCESS read-only
		STATUS mandatory
		DESCRIPTION
		   "The total number of system calls that
		    have occurred since the kernel was last
		    initialized.  System calls occur when a
		    process calls a function which must execute
		    in kernel or privileged mode; it is a
		    indicator of the system load and may be
		    higher on servers or machines shared by many
		    users."
	::= { kernelperf 16 }

        numInterrupts OBJECT-TYPE
		SYNTAX Counter
		ACCESS read-only
		STATUS mandatory
		DESCRIPTION
		   "The total number of device interrupts that
		    have occurred since the kernel was last
		    initialized.  The operating system is
		    interrupted by devices and peripherals when
		    they require the attention of the system.  An
		    excessive rate of interrupts can indicate a
		    heavily loaded machine; servers and machines
		    shared by many users will typically have a
		    higher rate though."
	::= { kernelperf 17 }

        numPageSwapIns OBJECT-TYPE
		SYNTAX Counter
		ACCESS read-only
		STATUS mandatory
		DESCRIPTION
		   "The total number of pages that have been swapped in
		    since the kernel was last initialized.  Page
		    swapping occurs when a process is swapped to
		    and from secondary storage.  A high rate of
		    page swap activity can indicate an overloaded
		    system."  
	::= { kernelperf 18 }

        numPageSwapOuts OBJECT-TYPE
		SYNTAX Counter
		ACCESS read-only
		STATUS mandatory
		DESCRIPTION
		   "The total number of pages that have been swapped out
		    since the kernel was last initialized.  Page
		    swapping occurs when a process is swapped to
		    and from secondary storage.  A high rate of
		    page swap activity can indicate an overloaded
		    system." 
	::= { kernelperf 19 }

        numSwapIns OBJECT-TYPE
		SYNTAX Counter
		ACCESS read-only
		STATUS mandatory
		DESCRIPTION
		   "The total number of processes that have been swapped
		    in since the kernel was last initialized.
		    Processes are swapped to and from secondary
		    storage when memory is in short supply.  A
		    high rate may indicate an overloaded system." 
	::= { kernelperf 20 }

        numSwapOuts OBJECT-TYPE
		SYNTAX Counter
		ACCESS read-only
		STATUS mandatory
		DESCRIPTION
		   "The total number of processes that have been swapped
		    out since the kernel was last initialized.
		    Processes are swapped to and from secondary
		    storage when memory is in short supply.  A
		    high rate may indicate an overloaded system." 
	::= { kernelperf 21 }

        numPageIns OBJECT-TYPE
		SYNTAX Counter
		ACCESS read-only
		STATUS mandatory
		DESCRIPTION
		   "The total number of pages that have been paged in
		    since the kernel was last initialized.
		    Page-in is an operation performed by the
		    virtual memory system in which the contents
		    of a page are read from secondary storage.  A
		    high rate of change may indicate an
		    overloaded system." 
	::= { kernelperf 22 }

        numPageOuts OBJECT-TYPE
		SYNTAX Counter
		ACCESS read-only
		STATUS mandatory
		DESCRIPTION
		   "The total number of pages that have been paged out
		    since the kernel was last initialized.
		    Page-out is an operation performed by the
		    virtual memory system in which the contents
		    of a page are written to secondary storage.
		    A high rate of change may indicate an
		    overloaded system."  
	::= { kernelperf 23 }

        numPageReclaims OBJECT-TYPE
		SYNTAX Counter
		ACCESS read-only
		STATUS mandatory
		DESCRIPTION
		   "The total pages that have been reclaimed from the
		    freelist since the kernel was last
		    initialized.  Memory pages are stored on a
		    free-list when not in use.  If a page has
		    been acquired from the free-list, it has been
		    reclaimed.  A high rate of changed indicates
		    an active system which is not generally
		    considered to be overloaded."
	::= { kernelperf 24 }

        numPageFaults OBJECT-TYPE
		SYNTAX Counter
		ACCESS read-only
		STATUS mandatory
		DESCRIPTION
		   "The total number of page faults that have
		    occurred since the kernel was last
		    initialized.  A page fault occurs when a
		    running process attempts to access a virtual
		    memory page that is not currently in physical
		    memory resulting in a hardware page fault.  A
		    high rage of page faults may indicate an
		    overloaded system or one with insufficient
		    memory."
	::= { kernelperf 25 }

        loadAverage1Min OBJECT-TYPE
                SYNTAX INTEGER
		ACCESS read-only
		STATUS mandatory
		DESCRIPTION
		   "The load average over the last 1 minute.  The
		    load average represents the average number of
		    jobs in the run queue over the specified time
		    range.  The value reported is the load
		    average multiplied by 100.  For example, if
		    the value 50 represents a load average of 0.50"
	::= { kernelperf 26 }

        loadAverage5Min OBJECT-TYPE
                SYNTAX INTEGER
		ACCESS read-only
		STATUS mandatory
		DESCRIPTION
		   "The load average over the last 5 minutes.  The
		    load average represents the average number of
		    jobs in the run queue over the specified time
		    range.  The value reported is the load
		    average multiplied by 100.  For example, if
		    the value 50 represents a load average of 0.50"
	::= { kernelperf 27 }

        loadAverage15Min OBJECT-TYPE
                SYNTAX INTEGER
		ACCESS read-only
		STATUS mandatory
		DESCRIPTION
		   "The load average over the last 15 minutes.  The
		    load average represents the average number of
		    jobs in the run queue over the specified time
		    range.  The value reported is the load
		    average multiplied by 100.  For example, if
		    the value 50 represents a load average of 0.50"
	::= { kernelperf 28 }

        totalSwapSpace OBJECT-TYPE 
                SYNTAX INTEGER
                ACCESS read-only
                STATUS mandatory
                DESCRIPTION
		   "Total system swap space in KBytes.  This object
                    is identical to the kernelConfig.totalSwap(12)  
                    object and is repeated here for the convenience
                    of management stations which cannot simultaneously
                    poll groups of objects in different branches of
                    the MIB."
    	::= { kernelperf 29 }

        swapCapacity OBJECT-TYPE 
                SYNTAX INTEGER (0..100)
                ACCESS read-only
                STATUS mandatory
                DESCRIPTION
                   "The percentage of the system's total swap in use.
                    The value of this object can be computed by
                    dividing swapInUse(13) by totalSwapSpace(29)
                    and multiplying by 100.  It is included here
                    for convenient polling, monitoring, and history
                    sampling.  This object is an aggregate value over
                    all the swap partitions and areas."
	::= { kernelperf 30 }

        memCapacity OBJECT-TYPE 
                SYNTAX INTEGER (0..100)
                ACCESS read-only
                STATUS mandatory
                DESCRIPTION
                   "The percentage of the system's active memory in use.
                    The value of this object can be approximated by
                    dividing activeMem(10) by memory(system.3) and
                    converting to a percentage.  Because virutal
                    memory allows systems to operate with a higher
                    memCapacity value, this value alone should not
                    be used to judge how loaded a system is.  Managers
                    should also monitor swapCapacity."
	::= { kernelperf 31 }

        memInUseCapacity OBJECT-TYPE 
                SYNTAX INTEGER (0..100)
                ACCESS read-only
                STATUS mandatory
                DESCRIPTION
                   "The percentage of the system's memory in use.
                    The value of this object can be approximated by
                    dividing memInUse(9) by memory(system.3) and
                    converting to a percentage.  Because virutal
                    memory allows systems to operate with a higher
                    memCapacity value, this value alone should not
                    be used to judge how loaded a system is.  Managers
                    should also monitor swapCapacity."
	::= { kernelperf 32 }

        pageScans OBJECT-TYPE
		SYNTAX Counter
		ACCESS read-only
		STATUS mandatory
		DESCRIPTION
		   "Total number of pages examined by pageout daemon.
                    Excessive rates of scans (change in this counter)
                    can indicate a machine with insufficient memory."
	::= { kernelperf 33 }

        numZombieProcs OBJECT-TYPE
                SYNTAX Gauge
                ACCESS read-only
                STATUS mandatory
                DESCRIPTION
                   "Current number of zombie processes found on the
                    system.  This MIB object is found by adding up 
                    all processes with a processStateStr of zombie.
                    The lower the number the better.  Supported in 
                    SystemEDGE 4.1 and higher."
        ::= { kernelperf 34 }

--
-- The Error Table
--
-- Error messages generated from within the kernel and by system
-- daemons are accumulated in this table.  This table depends on
-- system facilities and may not be implemented in all versions.
--
-- Due to lack of support across the various supported platforms, this
-- table has been deprecated.
--

	errorTable OBJECT-TYPE
		SYNTAX SEQUENCE OF ErrorEntry
		ACCESS not-accessible
		STATUS deprecated
		DESCRIPTION
		   "This table contains errors reported to the
		    system console.  On System V.4 platforms, it
		    also contains errors passed up via the system
		    error device.  Note, errors in this table
		    are also sent out as TRAPS.  V.4 derived
		    systems support a flexible, consistent
		    interface for hardware and system errors.
		    This table represents error feedback from
		    this interface.  It is not supported on SunOS
		    4.X systems."  
	::= { sysmgmt 8 }

	errorEntry OBJECT-TYPE
		SYNTAX ErrorEntry
		ACCESS not-accessible
		STATUS deprecated
		DESCRIPTION
		   "An entry in the error table."
		INDEX { seqNum }
	::= { errorTable 1 }

	ErrorEntry ::= SEQUENCE {
		seqNum
			INTEGER,
		mid
			INTEGER,
		sid
			INTEGER,
		time
			TimeTicks,
		tag
			INTEGER,
		type
			DisplayString,
		cause
			DisplayString,
		severity
			DisplayString,
		level
			DisplayString,
		module
			DisplayString,
		subSysmsg
			DisplayString,
		errDelete
			INTEGER
	}

	seqNum OBJECT-TYPE
		SYNTAX INTEGER
		ACCESS read-only
		STATUS deprecated
		DESCRIPTION
		   "The unique sequence number of the error
		    entry.  The value of this object also
		    represents the instance of the errorEntry
		    object."
	::= { errorEntry 1 }

	mid OBJECT-TYPE
		SYNTAX INTEGER
		ACCESS read-only
		STATUS deprecated
		DESCRIPTION
		   "The software module identifier reporting the
		    error."
	::= { errorEntry 2 }

	sid OBJECT-TYPE
		SYNTAX INTEGER
		ACCESS read-only
		STATUS deprecated
		DESCRIPTION
		   "The secondary identifier of the module
		    reporting the error."
	::= { errorEntry 3 }

	time OBJECT-TYPE
		SYNTAX TimeTicks
		ACCESS read-only
		STATUS deprecated
		DESCRIPTION
		   "The time at which the error was reported and
		    the error entry created."
	::= { errorEntry 4 }

	tag OBJECT-TYPE
		SYNTAX INTEGER
		ACCESS read-only
		STATUS deprecated
		DESCRIPTION
		   "A unique number which identifies the type of
		    error that occurred."
	::= { errorEntry 5 }

	type OBJECT-TYPE
		SYNTAX DisplayString
		ACCESS read-only
		STATUS deprecated
		DESCRIPTION
		   "The type of error."
	::= { errorEntry 6 }

	cause OBJECT-TYPE
		SYNTAX DisplayString
		ACCESS read-only
		STATUS deprecated
		DESCRIPTION
		   "The cause of the error."
	::= { errorEntry 7 }

	severity OBJECT-TYPE
		SYNTAX DisplayString
		ACCESS read-only
		STATUS deprecated
		DESCRIPTION
		   "The severity of the error."
	::= { errorEntry 8 }

	level OBJECT-TYPE
		SYNTAX DisplayString
		ACCESS read-only
		STATUS deprecated
		DESCRIPTION
		   "The level of software reporting the error."
	::= { errorEntry 9 }

	module OBJECT-TYPE
		SYNTAX DisplayString
		ACCESS read-only
		STATUS deprecated
		DESCRIPTION
		   "The module name that reported the error."
	::= { errorEntry 10 }

	subSysmsg OBJECT-TYPE
		SYNTAX DisplayString
		ACCESS read-only
		STATUS deprecated
		DESCRIPTION
		   "The sub-system message of the error entry."
	::= { errorEntry 11 }

	errDelete OBJECT-TYPE
--		SYNTAX DeleteButtonType
		SYNTAX INTEGER {
		   delete(1),
		   valid(2)
                }
		ACCESS read-write
		STATUS deprecated
		DESCRIPTION
		   "Setting this object to the value 1 causes the
		    agent to delete this entry from the error
		    table.  Writing any other value causes the
		    agent to take no action."
	::= { errorEntry 12 }

--
-- The IPC Group
--
-- Report System V IPC configuration and usage statistics
-- System V IPC includes message queues, shared memory, and semaphores
--

	ipc OBJECT IDENTIFIER ::= { sysmgmt 9 }

--
-- The Message Queue Table
--

	msgqueTable OBJECT-TYPE
		SYNTAX SEQUENCE OF MsgqueEntry
		ACCESS not-accessible
		STATUS mandatory
		DESCRIPTION
		   "This table contains an entry for each system
		    SysV message queue currently in use."
	::= { ipc 1 }

	msgqueEntry OBJECT-TYPE
		SYNTAX MsgqueEntry
		ACCESS not-accessible
		STATUS mandatory
		DESCRIPTION
		   "An entry in the message queue table."
		INDEX { queID }
	::= { msgqueTable 1 }

	MsgqueEntry ::= SEQUENCE {
		queID
			INTEGER,
		queKey
			DisplayString,
		queMode
			DisplayString,
		queOwner
			DisplayString,
		queGroup
			DisplayString,
		queNBytes
			Gauge,
		queNMesg
			Gauge,
		queDel
			INTEGER
	}

	queID OBJECT-TYPE
		SYNTAX INTEGER
		ACCESS read-only
		STATUS mandatory
		DESCRIPTION
		   "The unique queue ID.  The value of this
		    object also represents the instance for the
		    queEntry object."
	::= { msgqueEntry 1 }

	queKey OBJECT-TYPE
		SYNTAX DisplayString
		ACCESS read-only
		STATUS mandatory
		DESCRIPTION
		   "The message queue key.  Each message queue
		    has a key value chosen by the creating user.
		    Its value is only significant to the creating
		    process." 
	::= { msgqueEntry 2 }

	queMode OBJECT-TYPE
		SYNTAX DisplayString
		ACCESS read-only
		STATUS mandatory
		DESCRIPTION
		   "The message queue permissions mode.  The mode
		    defines access permissions for the message
		    queue as well as status information.  See the
		    man page ipcs(1) for more information."
	::= { msgqueEntry 3 }

	queOwner OBJECT-TYPE
		SYNTAX DisplayString
		ACCESS read-only
		STATUS mandatory
		DESCRIPTION
		   "The login name (e.g. root) of the owner of
		    the message queue."
	::= { msgqueEntry 4 }

	queGroup OBJECT-TYPE
		SYNTAX DisplayString
		ACCESS read-only
		STATUS mandatory
		DESCRIPTION
		   "The group name (e.g. wheel) of the owner of
		    the message queue."
	::= { msgqueEntry 5 }

	queNBytes OBJECT-TYPE
		SYNTAX Gauge
		ACCESS read-only
		STATUS mandatory
		DESCRIPTION
		   "The number of bytes currently in the message queue."
	::= { msgqueEntry 6 }

	queNMesg OBJECT-TYPE
		SYNTAX Gauge
		ACCESS read-only
		STATUS mandatory
		DESCRIPTION
		   "The number of messages currently in the
		    message queue." 
	::= { msgqueEntry 7 }

	queDel OBJECT-TYPE
--		SYNTAX DeleteButtonType
		SYNTAX INTEGER {
		   delete(1),
		   valid(2)
                }
		ACCESS read-write
		STATUS mandatory
		DESCRIPTION
		   "Setting this object to the value 1 causes
		    this agent to remove the message queue from
		    its table.  The message queue identifier is
		    removed from the system-wide table and the
		    kernel message queue and associated data
		    structure are destroyed."
	::= { msgqueEntry 8 }

--
-- The Shared Memory Table
--

	shmemTable OBJECT-TYPE
		SYNTAX SEQUENCE OF ShmemEntry
		ACCESS not-accessible
		STATUS mandatory
		DESCRIPTION
		   "This table contains an entry for each system
		    SysV shared memory segment currently in use."
	::= { ipc 2 }

	shmemEntry
		OBJECT-TYPE
		SYNTAX ShmemEntry
		ACCESS not-accessible
		STATUS mandatory
		DESCRIPTION
		   "An entry in the shared memory table."
		INDEX { shmemID }
	::= { shmemTable 1 }

	ShmemEntry ::= SEQUENCE {
		shmemID
			INTEGER,
		shmemKey
			DisplayString,
		shmemMode
			DisplayString,
		shmemOwner
			DisplayString,
		shmemGroup
			DisplayString,
		shmemSegSz
			INTEGER,
		shmemNLcks
			INTEGER,
		shmemDel
 			INTEGER
	}

	shmemID OBJECT-TYPE
		SYNTAX INTEGER
		ACCESS read-only
		STATUS mandatory
		DESCRIPTION
		   "The unique shared memory segment ID.  The
		    value of this object also represents the
		    instance of the shmemEntry object."
	::= { shmemEntry 1 }

	shmemKey OBJECT-TYPE
		SYNTAX DisplayString
		ACCESS read-only
		STATUS mandatory
		DESCRIPTION
		   "The shared memory segment key.  Each shared
		    memory segment is assigned a key value by the
		    creating user.  Its value is only significant
		    to the creating process." 
	::= { shmemEntry 2 }

	shmemMode OBJECT-TYPE
		SYNTAX DisplayString
		ACCESS read-only
		STATUS mandatory
		DESCRIPTION
		   "The shared memory segment permissions mode. The mode
		    defines access permissions for the message
		    queue as well as status information.  See the
		    man page ipcs(1) for more information." 
	::= { shmemEntry 3 }

	shmemOwner OBJECT-TYPE
		SYNTAX DisplayString
		ACCESS read-only
		STATUS mandatory
		DESCRIPTION
		   "The user login name (e.g. root) of the owner of the
		    shared memory segment."
	::= { shmemEntry 4 }

	shmemGroup OBJECT-TYPE
		SYNTAX DisplayString
		ACCESS read-only
		STATUS mandatory
		DESCRIPTION
		   "The group name (e.g. wheel) of the owner of
		    the shared memory segment."
	::= { shmemEntry 5 }

	shmemSegSz OBJECT-TYPE
		SYNTAX INTEGER
		ACCESS read-only
		STATUS mandatory
		DESCRIPTION
		   "The size in bytes of the shared memory segment"
	::= { shmemEntry 6 }

	shmemNLcks
		OBJECT-TYPE
		SYNTAX INTEGER
		ACCESS read-only
		STATUS mandatory
		DESCRIPTION
		   "The number of times the shared memory segment
		    has been locked."
	::= { shmemEntry 7 }

	shmemDel OBJECT-TYPE
--		SYNTAX DeleteButtonType
		SYNTAX INTEGER {
		   delete(1),
		   valid(2)
                }
		ACCESS read-write
		STATUS mandatory
		DESCRIPTION
		   "Setting this object to the value of 1 causes
		    the agent to remove this entry from the
		    table.  The shared memory identifier is
		    removed from the system-wide table and the
		    kernel shared memory segment and associated
		    data structure are destroyed."
	::= { shmemEntry 8 }

--
-- The Semaphore Table
--

	semTable OBJECT-TYPE
		SYNTAX SEQUENCE OF SemEntry
		ACCESS not-accessible
		STATUS mandatory
		DESCRIPTION
		   "This table contains an entry for each system
		    SysV semaphore currently in use."
	::= { ipc 3 }

	semEntry OBJECT-TYPE
		SYNTAX SemEntry
		ACCESS not-accessible
		STATUS mandatory
		DESCRIPTION
		   "An entry in the semaphore table."
		INDEX { semID }
	::= { semTable 1 }

	SemEntry ::= SEQUENCE {
		semID
			INTEGER,
		semKey
			DisplayString,
		semMode
			DisplayString,
		semOwner
			DisplayString,
		semGroup
			DisplayString,
		semNsems
			INTEGER,
		semDel
			INTEGER
	}

	semID OBJECT-TYPE
		SYNTAX INTEGER
		ACCESS read-only
		STATUS mandatory
		DESCRIPTION
		   "The unique semaphore ID.  The value of this
		    object represents the instance for the
		    semEntry object."
	::= { semEntry 1 }

	semKey OBJECT-TYPE
		SYNTAX DisplayString
		ACCESS read-only
                STATUS mandatory
		DESCRIPTION
		   "The semaphore's key. Each semaphore is
		    assigned a key value by the creating user.
		    Its value is only significant to the creating
		    process."   
	::= { semEntry 2 }

	semMode OBJECT-TYPE
		SYNTAX DisplayString
		ACCESS read-only
		STATUS mandatory
		DESCRIPTION
		"   The semaphore permissions mode.  The mode
		    defines access permissions for the message
		    queue as well as status information.  See the
		    man page ipcs(1) for more information." 
	::= { semEntry 3 }

	semOwner OBJECT-TYPE
		SYNTAX DisplayString
		ACCESS read-only
		STATUS mandatory
		DESCRIPTION
		   "The user login name (e.g. root) of the owner of the
		    semaphore."
	::= { semEntry 4 }

	semGroup OBJECT-TYPE
		SYNTAX DisplayString
		ACCESS read-only
		STATUS mandatory
		DESCRIPTION
		   "The group name (e.g. wheel) of the owner of
		    the semaphore." 
	::= { semEntry 5 }

	semNsems OBJECT-TYPE
		SYNTAX INTEGER
		ACCESS read-only
		STATUS mandatory
		DESCRIPTION
		   "The number of individual semaphores within
		    this semaphore group."
	::= { semEntry 6 }

	semDel OBJECT-TYPE
--		SYNTAX DeleteButtonType
		SYNTAX INTEGER {
		   delete(1),
		   valid(2)
		  }
		ACCESS read-write
		STATUS mandatory
		DESCRIPTION
		   "Setting the value of 1, causes the agent to
		    remove this entry from its semaphore table.
		    The semaphore identifier is removed from the
		    system-wide table and the kernel semaphore
		    group and associated data structures are
		    destroyed."
	::= { semEntry 7 }


--
-- The buffers group.  Buffer allocation and usage is very
-- important to any running operating system.  Therefore, the buffer
-- group is divided into network buffers (mbufs group), Streams 
-- buffers (strbuf), and I/O buffer cache (ioBufferCache group)
--

	buffers OBJECT IDENTIFIER ::= { sysmgmt 10 }

--
-- Mbuf Group
--
	mbufs OBJECT IDENTIFIER ::= { buffers 1 }

	numMbufs OBJECT-TYPE
		SYNTAX Gauge
		ACCESS read-only
		STATUS mandatory
		DESCRIPTION
		   "The total number of mbufs contained in the mbuf
		    pool.  The BSD networking subsystem utilizes
		    a buffer abstraction called 'mbufs'.  This
		    object indicates the number of mbuf buffers
		    pre-allocated by the operating system.  If
		    the BSD networking subsystem is not
		    supported, than 0 is returned."  
	::= { mbufs 1 }

	numClusters OBJECT-TYPE
		SYNTAX Gauge
		ACCESS read-only
		STATUS mandatory
		DESCRIPTION
		   "The total number of logical pages or clusters
		    obtained from the page pool.  Memory pages
		    (or clusters) can also be attached to mbufs
		    if needed.  The size of this pool is returned
		    in this object.  If the BSD subsystem is not
		    supported, than 0 is returned."
	::= { mbufs 2 }

	freeClusters OBJECT-TYPE
		SYNTAX Gauge
		ACCESS read-only
		STATUS mandatory
		DESCRIPTION
		   "The number of free clusters or memory pages
		    in the mbuf cluster pool.  Monitoring the
		    number of free clusters can help determine if
		    the BSD protocol subsystem is properly
		    configured.  On SunOS 4.X systems, TCP/IP is
		    coded in the BSD subsystem.  Monitoring this
		    variable can help determine if TCP/IP
		    performance problems are due to insufficient
		    buffer resources."  
	::= { mbufs 3 }

	numDrops OBJECT-TYPE
		SYNTAX Counter
		ACCESS read-only
		STATUS mandatory
		DESCRIPTION
		   "The number of times requests for mbufs were
		    denied.  An excessive rate of mbuf allocation
		    failures may indicate an overloaded system or
		    one with insufficient memory resources." 
	::= { mbufs 4 }

	numWaits OBJECT-TYPE
		SYNTAX Counter
		ACCESS read-only
		STATUS mandatory
		DESCRIPTION
		   "The number of times requests for mbufs were
		    delayed.  An excessive rate of mbuf
		    allocation 'waits' may indicate an overloaded
		    system or one with insufficient memory
		    resources."  
	::= { mbufs 5 }

	numDrains OBJECT-TYPE
		SYNTAX Counter
		ACCESS read-only
		STATUS mandatory
		DESCRIPTION
		   "The total number of calls to protocol drain
		    routines.  When the protocol subsystem is
		    running low on buffers, it can call each
		    protocol's 'drain' function forcing that
		    protocol to free buffers.  This object
		    reveals how many times this even has occurred.
		    An excessive rate of calls to 'drain' may
		    indicate an overloaded or misconfigured system."
	::= { mbufs 6 }

--
-- The Mbuf Allocation Table
--
-- A table indicating mbuf allocation data by type
--

	mbufAllocTable OBJECT-TYPE
		SYNTAX SEQUENCE OF MbufAllocEntry
		ACCESS not-accessible
		STATUS mandatory
		DESCRIPTION
		   "This table contains an entry for each mbuf
		    type that has been allocated.  In the BSD
		    networking subsystem, when an mbuf is
		    allocated, the mbuf's intended use is
		    categorized.  This table represents the
		    categories and the number of mbuf's allocated
		    to each type."
	::= { mbufs 7 }

	mbufAllocEntry OBJECT-TYPE
		SYNTAX MbufAllocEntry
		ACCESS not-accessible
		STATUS mandatory
		DESCRIPTION
		   "An entry in the mbuf Allocation table."
		INDEX { mbufType }
	::= { mbufAllocTable 1 }

	MbufAllocEntry ::= SEQUENCE {
          	mbufType
            		INTEGER,
          	mbufDesc
            		DisplayString,
          	mbufAlloc
            		Gauge
        }

	mbufType OBJECT-TYPE
		SYNTAX INTEGER
		ACCESS read-only
		STATUS mandatory
		DESCRIPTION
		   "The type of mbuf.  Mbuf types generally range
		    from from 0 to 255; many mbuf types 
		    (numbers > 30) are undefined and generally
		    not used.  Their use and description are a
		    local matter and may vary from system to system." 
	::= { mbufAllocEntry 1 }

	mbufDesc OBJECT-TYPE
		SYNTAX DisplayString
		ACCESS read-only
		STATUS mandatory
		DESCRIPTION
		   "A textual description of the mbuf type.
		    Example mbuf descriptions include 'Packet
		    header', 'Socket structure', etc.  Undefined
		    or unknown mbuf type descriptions return
		    'Unknown mbuf type' as their description."
	::= { mbufAllocEntry 2 }

	mbufAlloc OBJECT-TYPE
		SYNTAX Gauge
		ACCESS read-only
		STATUS mandatory
		DESCRIPTION
		   "The number of mbufs allocated and declared of to
		    be of this type."
	::= { mbufAllocEntry 3 }

--
-- Stream Buffers Group
--
-- Streams buffers are partitioned into buckets of several sizes;
-- this table gives the message sizes and allocation statistics per
-- bucket.
--

	strbufs OBJECT IDENTIFIER ::= { buffers 2 }
--
-- The Streams Buffer Allocation Table
--

	strbufAllocTable OBJECT-TYPE
		SYNTAX SEQUENCE OF StrbufAllocEntry
		ACCESS not-accessible
		STATUS mandatory
		DESCRIPTION
		   "This table contains an entry for each Streams
		    buffer bucket sizes."
	::= { strbufs 1 }

	strbufAllocEntry OBJECT-TYPE
		SYNTAX StrbufAllocEntry
		ACCESS not-accessible
		STATUS mandatory
		DESCRIPTION
		   "An entry in the Streams buffer allocation table."
		INDEX { strbufAllocIndex }
	::= { strbufAllocTable 1 }

	StrbufAllocEntry ::= SEQUENCE {
          	strbufAllocIndex
            		INTEGER,
          	strbufAllocSize
            		INTEGER,
          	strbufAllocCurrent
            		Gauge,
          	strbufAllocMaxs
            		INTEGER,
          	strbufAllocTotals
            		Counter,
          	strbufAllocFails
            		Counter
        }

	strbufAllocIndex OBJECT-TYPE
		SYNTAX INTEGER
		ACCESS read-only
		STATUS mandatory
		DESCRIPTION
		   "The table index of this entry."
	::= { strbufAllocEntry 1 }

	strbufAllocSize OBJECT-TYPE
		SYNTAX INTEGER
		ACCESS read-only
		STATUS mandatory
		DESCRIPTION
		   "The size of this bucket in bytes.  The size is
		    less than or equal to this value yet greater
		    than the previous entry's bucket size.  For
		    example, if the bucket size os 1024 bytes,
		    all Streams buffer requests of less than or
		    equal to 1024 bytes will return a buffer of
		    size 1024."  
	::= { strbufAllocEntry 2 }

	strbufAllocCurrent OBJECT-TYPE
		SYNTAX Gauge
		ACCESS read-only
		STATUS mandatory
		DESCRIPTION
		   "The number of Streams buffers of this currently 
		    allocated.  Comparing the value of this
		    object to strbufAllocMax can help one
		    determine if the system is properly configured."
	::= { strbufAllocEntry 3 }

	strbufAllocMaxs OBJECT-TYPE
		SYNTAX INTEGER
		ACCESS read-only
		STATUS mandatory
		DESCRIPTION
		   "The maximum number of Streams buffers of this
		    size ever allocated at any one time.  This
		    value serves as a high-water mark for buffer
		    allocations of this size." 
	::= { strbufAllocEntry 4 }

	strbufAllocTotals OBJECT-TYPE
		SYNTAX Counter
		ACCESS read-only
		STATUS mandatory
		DESCRIPTION
		   "The total number of allocations of Streams buffers 
		    of this bucket size.  A high allocation rate
		    can help one diagnose an overloaded system."
	::= { strbufAllocEntry 5 }

	strbufAllocFails OBJECT-TYPE
		SYNTAX Counter
		ACCESS read-only
		STATUS mandatory
		DESCRIPTION
		   "The total number of allocation failures for Streams
		    buffers of this bucket size.  A high rate of
		    failure can indicate an overloaded system or
		    one that is not properly configured."
	::= { strbufAllocEntry 6 }

--
-- I/O Buffer Cache Group
--
-- Statistics and allocation information for the I/O Buffer Cache
--
	ioBufferCache OBJECT IDENTIFIER ::= { buffers 3 }

	numBreadRequests OBJECT-TYPE
		SYNTAX Counter
		ACCESS read-only
		STATUS mandatory
		DESCRIPTION
		   "The total number of calls to the kernel's bread()
		    function.  This function is the primary read 
		    interface to the kernel's buffer pool used
		    for file system I/O.  On NT systems, this value is
                    an aggregate of several read variables in the
                    ntCachePerf group." 
	::= { ioBufferCache 1 }

	numBreadHits OBJECT-TYPE
		SYNTAX Counter
		ACCESS read-only
		STATUS mandatory
		DESCRIPTION
		   "The number of kernel buffer cache 'hits'.
		    The kernel caches previously used I/O buffers
		    in an attempt to avoid excessive reading and
		    writing to disk.  A cache 'hit' indicates
		    that this strategy has paid off because a
		    process has requested a buffer that was in
		    the buffer cache thereby avoiding a more
		    expensive disk read.  A high rate of cache
		    hits indicates a relatively smooth running
                    system.  On NT systems, this value is an aggregate
                    of several hit variables in the ntCachePerf group."
	::= { ioBufferCache 2 }

	numBufSleeps OBJECT-TYPE
		SYNTAX Counter
		ACCESS read-only
		STATUS mandatory
		DESCRIPTION
		   "The total number of times the kernel had to 'sleep'
		    for a buffer.  The kernel 'sleeps' for a
		    buffer when it fails to find it in the cache
		    and must access the disk for it.  Excessive
		    buffer 'sleeps' indicates that the caching
		    algorithm is not able to effectively predict
		    and cache disk I/O patterns.  Adding more
		    memory for buffering may improve the cache
		    hit ratio."
	::= { ioBufferCache 3 }

	numAgeAllocs OBJECT-TYPE
		SYNTAX Counter
		ACCESS read-only
		STATUS mandatory
		DESCRIPTION
		   "The total number of times an aged buffer was
		    allocated.  The buffer pool is stored in
		    one of several lists.  One such list, the AGE
		    list, holds buffers buffers that have a lower
		    probability of being used.  New buffer
		    requests are filled from this list first.
		    This variable contains the number of times a
		    buffer request was satisfied by a buffer on
		    the AGE list."  
	::= { ioBufferCache 4 }

	numLRUAllocs OBJECT-TYPE
		SYNTAX Counter
		ACCESS read-only
		STATUS mandatory
		DESCRIPTION
		   "The total number times an LRU buffer was
		    allocated.  The Least-recently-used list is
		    another list on which buffers are stored.
		    They are allocated in a 'least-recently-used'
		    manner.  This variable indicates the number
		    of times a buffer was allocated from the LRU
		    list."
	::= { ioBufferCache 5 }

	minNumBufHdrs OBJECT-TYPE
		SYNTAX Gauge
		ACCESS read-only
		STATUS mandatory
		DESCRIPTION
		   "The minimum number of buffer headers to
		    allocated.  These headers are used at the
		    head of each buffer hash list.  This value
		    represents an upper bound on the number of
		    separate hash lists the buffer cache may
		    use." 
	::= { ioBufferCache 6 }

	numAllocBuf OBJECT-TYPE
		SYNTAX Gauge
		ACCESS read-only
		STATUS mandatory
		DESCRIPTION
		   "Number of buffers that are currently
		    allocated.  Monitoring this variable, and
		    others in the ioBufferCache group, can help
		    indicate if the system is properly configured
		    or has sufficient memory for buffering."
	::= { ioBufferCache 7 }

        ioBufferHitRate OBJECT-TYPE
		SYNTAX INTEGER (0..100)
		ACCESS read-only
		STATUS mandatory
		DESCRIPTION
                   "Percentage of buffer cache lookups that result in a
                    'hit'.  This value is derived from 
                    numBreadHits / numBreadRequests."
	::= { ioBufferCache 8 }

--
-- The directory name lookup cache (dnlc) group.  UNIX kernels
-- typically cache directory and file name to vnode mappings.  The
-- efficiency and effectiveness of this caching can greatly effect I/O
-- performance.  This group contains performance statistics for that
-- cache.
-- 

	dnlc OBJECT IDENTIFIER ::= { sysmgmt 11 }

	dnlcHits OBJECT-TYPE
		SYNTAX Counter
		ACCESS read-only
		STATUS mandatory
		DESCRIPTION
                   "Total number of DNLC cache hits."
	::= { dnlc 1 }

	dnlcMisses OBJECT-TYPE
		SYNTAX Counter
		ACCESS read-only
		STATUS mandatory
		DESCRIPTION
                   "Total number of DNLC cache misses."
	::= { dnlc 2 }

	dnlcEnters OBJECT-TYPE
		SYNTAX Counter
		ACCESS read-only
		STATUS mandatory
		DESCRIPTION
                   "Total number of DNLC enters done."
	::= { dnlc 3 }

	dnlcDblEnters OBJECT-TYPE
		SYNTAX Counter
		ACCESS read-only
		STATUS mandatory
		DESCRIPTION
                   "Total number enters tried when already cached."
	::= { dnlc 4 }

	dnlcLongEnters OBJECT-TYPE
		SYNTAX Counter
		ACCESS read-only
		STATUS mandatory
		DESCRIPTION
                   "Total number of long names tried to enter."
	::= { dnlc 5 }

	dnlcLongLooks OBJECT-TYPE
		SYNTAX Counter
		ACCESS read-only
		STATUS mandatory
		DESCRIPTION
                   "Total number of long name lookup attempts."
	::= { dnlc 6 }

	dnlcLruEmpty OBJECT-TYPE
		SYNTAX Counter
		ACCESS read-only
		STATUS mandatory
		DESCRIPTION
                   "Total number of least-recently used list empty."
	::= { dnlc 7 }

	dnlcPurges OBJECT-TYPE
		SYNTAX Counter
		ACCESS read-only
		STATUS mandatory
		DESCRIPTION
                   "Total number of purges to the DNLC cache."
	::= { dnlc 8 }

        dnlcHitRate OBJECT-TYPE
		SYNTAX INTEGER (0..100)
		ACCESS read-only
		STATUS mandatory
		DESCRIPTION
                   "Percentage of DNLC cache lookups that result in a
                    'hit'.  Hit rates less than 90% are considered
                    poor and may require kernel tuning.  This value is
                    derived from dnlcHits / dnlcHits + dnlcMisses."
	::= { dnlc 9 }

        dnlcCacheSize OBJECT-TYPE
		SYNTAX INTEGER 
		ACCESS read-only
		STATUS mandatory
		DESCRIPTION
                   "The maximum number of possible entries in the DNLC
                    cache.  If there is no set upper bound, 0 is
                    returned." 
	::= { dnlc 10 }

-- The NT Systems Management branch is defined below
-- Objects under the empire(5) branch are intended for the 
-- management and monitoring systems running MS/NT
-- 

--
-- The NT system group
-- 

	ntSystem OBJECT IDENTIFIER ::= { nt 1 }

	ntSystemVersion OBJECT-TYPE
		SYNTAX DisplayString
		ACCESS read-only
		STATUS mandatory
		DESCRIPTION
		   "The kernel/system version including the release,
                    build, and service-pack numbers."
	::= { ntSystem 1 }

	ntBuildNumber OBJECT-TYPE
		SYNTAX INTEGER
		ACCESS read-only
		STATUS mandatory
		DESCRIPTION
		   "The kernel build number (e.g. 1057)"
	::= { ntSystem 2 }

	ntServicePackNumber OBJECT-TYPE
		SYNTAX INTEGER
		ACCESS read-only
		STATUS mandatory
		DESCRIPTION
		   "The system service-pack number.  If no
                    service-packs have been applied, then 0 is returned."
	::= { ntSystem 3 }

        ntWorkstationOrServer OBJECT-TYPE
		SYNTAX INTEGER {
                   server(1),
                   workstation(2),
                   unknown(3)
                  }
		ACCESS read-only
		STATUS mandatory
		DESCRIPTION
		   "The type of NT system -- NT Server or NT Workstation"
	::= { ntSystem 4 }

        ntfsDisable8dot3NameCreation OBJECT-TYPE
		SYNTAX INTEGER {
                   true(1),
                   false(2)
                  }
		ACCESS read-only
		STATUS mandatory
		DESCRIPTION
		   "This object reflects whether the underlying NT
                    system has enabled or disabled the creation of
                    short names to correspond with long filenames.
                    For example, if enabled, then NT will create a
                    short filename to correspond to a file created
                    with a long filename.  This feature is often
                    enabled if backward compatibility with DOS based
                    applications is desired." 
	::= { ntSystem 5 }

        ntWin31FileSystem OBJECT-TYPE
		SYNTAX INTEGER {
                   true(1),
                   false(2)
                  }
		ACCESS read-only
		STATUS mandatory
		DESCRIPTION
		   "This object reflects whether the FAT will allow
                    creation, enumeration, opening, or querying of
                    long file names, and whether extended time stamp
                    information is stored and reported. Setting to
                    true(1) reverts the system back to Win3x semantics." 
	::= { ntSystem 6 }

	ntCriticalSectTimeout OBJECT-TYPE
		SYNTAX INTEGER
		ACCESS read-only
		STATUS mandatory
		DESCRIPTION
		   "The deadlock time-out for critical sections."
	::= { ntSystem 7 }

        ntGlobalFlag OBJECT-TYPE
		SYNTAX INTEGER
		ACCESS read-only
		STATUS mandatory
		DESCRIPTION
		   "NT system global hexadecimal flag that controls
                    various internal operations."
	::= { ntSystem 8 }

        ntIoPageLockLimit OBJECT-TYPE
		SYNTAX INTEGER
		ACCESS read-only
		STATUS mandatory
		DESCRIPTION
		   "Specifies the limit of the number of bytes that
                    can be locked for I/O operations.  When 0, the
                    default (512k) is used."
	::= { ntSystem 9 }

        ntLargeSystemCache OBJECT-TYPE
		SYNTAX INTEGER
		ACCESS read-only
		STATUS mandatory
		DESCRIPTION
		   "A nonzero value indicates that the system favors
                    the system-cache working set rather than the
                    processes working set." 
	::= { ntSystem 10 }

        ntPagedPoolSize OBJECT-TYPE
		SYNTAX INTEGER
		ACCESS read-only
		STATUS mandatory
		DESCRIPTION
		   "Size of paged pool in bytes.  When 0, system uses
                    default size (32 MB)."
	::= { ntSystem 11 }

        ntNonPagedPoolSize OBJECT-TYPE
		SYNTAX INTEGER
		ACCESS read-only
		STATUS mandatory
		DESCRIPTION
		   "Size of nonpaged pool in bytes.  When 0, system uses
                    default size (based on physical memory)."
	::= { ntSystem 12 }

        ntPagingFiles OBJECT-TYPE
		SYNTAX DisplayString
		ACCESS read-only
		STATUS mandatory
		DESCRIPTION
                   "List of paging files and their sizes used by the
                    system for paging. For each paging file the description
                    includes the file pathname, current size in MB and 
                    maximum size in MB."
	::= { ntSystem 13 }

        ntSystemPages OBJECT-TYPE
		SYNTAX INTEGER
		ACCESS read-only
		STATUS mandatory
		DESCRIPTION
                   "This object defines the number of system page
                    table entries reserved for I/O buffers and other
                    information." 
	::= { ntSystem 14 }

        ntOptionalSubsystem OBJECT-TYPE
		SYNTAX DisplayString
		ACCESS read-only
		STATUS mandatory
		DESCRIPTION
                   "This object lists those subsystems that are only
                    loaded when the user starts a depending application."
	::= { ntSystem 15 }

        ntCmdlineOptions OBJECT-TYPE
		SYNTAX DisplayString
		ACCESS read-only
		STATUS mandatory
		DESCRIPTION
                   "This object lists the command-line that runs when
                    an MS-DOS application is launched under NT."
	::= { ntSystem 16 }

        ntLPTTimeout OBJECT-TYPE
		SYNTAX INTEGER
		ACCESS read-only
		STATUS mandatory
		DESCRIPTION
                   "This object defines how many seconds after the LPT
                    port has been used that Windows NT waits before
                    grabbing the port, closing it, and flushing the
                    output.  This value is only needed for MS-DOS
                    based applications that use BIOS and do not close
                    the port."  
	::= { ntSystem 17 }

        ntDosMemSize OBJECT-TYPE
		SYNTAX INTEGER
		ACCESS read-only
		STATUS mandatory
		DESCRIPTION
                   "Size in MBytes of memory to be given to each
                    individual MS-DOS virtual DOS machine (VDM)."
	::= { ntSystem 18 }

        ntWowCmdline OBJECT-TYPE
		SYNTAX DisplayString
		ACCESS read-only
		STATUS mandatory
		DESCRIPTION
                   "This object defines the command line that runs
                    when a 16-bit Windows-based application is
                    started.  The switches instruct NT to start either
                    an MS-DOS VDM or a WOW VDM." 
	::= { ntSystem 19 }

        ntWowSize OBJECT-TYPE
		SYNTAX INTEGER
		ACCESS read-only
		STATUS mandatory
		DESCRIPTION
                   "For RISC based computers, this object defines the
                    amount of memory provided in a VDM when a WOW
                    session is started.  Value is in MBytes." 
	::= { ntSystem 20 }

        ntUserFullScreen OBJECT-TYPE
		SYNTAX INTEGER {
                    windowed(0),
                    fullscreen(1)
                  }
		ACCESS read-only
		STATUS mandatory
		DESCRIPTION
                   "This object indicates whether full-screen or
                    windowed mode is used for the console by default.
                    Valid on x86 machines only." 
	::= { ntSystem 21 }

        ntHistoryBufferSize OBJECT-TYPE
		SYNTAX INTEGER
		ACCESS read-only
		STATUS mandatory
		DESCRIPTION
                   "This object indicates the number of commands
                    stored in the history buffer by default."
	::= { ntSystem 22 }

        ntNumberHistoryBuffers OBJECT-TYPE
		SYNTAX INTEGER
		ACCESS read-only
		STATUS mandatory
		DESCRIPTION
                   "This object indicates the number of history
                    buffers associated with the console by default."
	::= { ntSystem 23 }

        ntQuickEdit OBJECT-TYPE
		SYNTAX INTEGER {
                    disabled(0),
                    enabled(1)
                  }
		ACCESS read-only
		STATUS mandatory
		DESCRIPTION
                   "This object indicates if Quick-Edit mode is
                    enabled by default."
	::= { ntSystem 24 }

        ntScreenBufferSize OBJECT-TYPE
		SYNTAX DisplayString
		ACCESS read-only
		STATUS mandatory
		DESCRIPTION
                   "Width and height of the default console screen buffer."
	::= { ntSystem 25 }

        ntWindowSize OBJECT-TYPE
		SYNTAX DisplayString
		ACCESS read-only
		STATUS mandatory
		DESCRIPTION
                   "Default width and height of the console window."
	::= { ntSystem 26 }

        ntWindowsAppInitDLLs OBJECT-TYPE
		SYNTAX DisplayString
		ACCESS read-only
		STATUS mandatory
		DESCRIPTION
                   "Lists the DLLs that will be attached to all
                    Windows-based applications."
	::= { ntSystem 27 }

        ntWindowsDeviceNotSelectedTimeout OBJECT-TYPE
		SYNTAX INTEGER
		ACCESS read-only
		STATUS mandatory
		DESCRIPTION
                   "Indicates how much time the system waits for a
                    devices to be switched on."
	::= { ntSystem 28 }

        ntWindowsSpooler OBJECT-TYPE
                SYNTAX INTEGER {
		    true(1),
		    false(2)
                }
		ACCESS read-only
		STATUS mandatory
		DESCRIPTION
                   "Indicates whether printer output is be sent
                    through Print Manager."
	::= { ntSystem 29 }

        ntWindowsSwapDisk OBJECT-TYPE
		SYNTAX DisplayString
		ACCESS read-only
		STATUS mandatory
		DESCRIPTION
                   "Indicates the name of disk drive and directory to
                    which Windows for MS-DOS in standard-mode swaps
                    non-Windows-based applications."
	::= { ntSystem 30 }

        ntWindowsXmitRetryTimeout OBJECT-TYPE
		SYNTAX INTEGER
		ACCESS read-only
		STATUS mandatory
		DESCRIPTION
                   "Transmission retry timeout in seconds used by
                    Print Manager." 
	::= { ntSystem 31 }

        ntSystemRoot OBJECT-TYPE
		SYNTAX DisplayString
		ACCESS read-only
		STATUS mandatory
		DESCRIPTION
                   "Drive and directory where the NT system resides."
	::= { ntSystem 32 }

        ntBuildType OBJECT-TYPE
		SYNTAX INTEGER {
                   uniprocessor(1),
                   multiprocessor(2),
                   unknown(3)
                }
		ACCESS read-only
		STATUS mandatory
		DESCRIPTION
                   "System build type (uniprocessor or multiprocessor)."
	::= { ntSystem 33 }

        ntSysStartOptions OBJECT-TYPE
		SYNTAX DisplayString
		ACCESS read-only
		STATUS mandatory
		DESCRIPTION
                   "System start options."
	::= { ntSystem 34 }

        ntSysBiosDate OBJECT-TYPE
		SYNTAX DisplayString
		ACCESS read-only
		STATUS mandatory
		DESCRIPTION
                   "System BIOS date."
	::= { ntSystem 35 }

        ntSysBiosVersion OBJECT-TYPE
		SYNTAX DisplayString
		ACCESS read-only
		STATUS mandatory
		DESCRIPTION
                   "System BIOS version."
	::= { ntSystem 36 }

        ntVideoResolution OBJECT-TYPE
		SYNTAX DisplayString
		ACCESS read-only
		STATUS mandatory
		DESCRIPTION
                   "System video resolution."
	::= { ntSystem 37 }

        ntCrashDumpEnabled OBJECT-TYPE
		SYNTAX INTEGER {
                    disabled(0),
                    enabled(1),
                    unknown(2)
                  }
		ACCESS read-only
		STATUS mandatory
		DESCRIPTION
                   "This object indicates whether debugging
                    information is to be written to a log file in the
                    event of a system crash." 
	::= { ntSystem 38 }

        ntLogEvent OBJECT-TYPE
		SYNTAX INTEGER {
                    disabled(0),
                    enabled(1),
                    unknown(2)
                  }
		ACCESS read-only
		STATUS mandatory
		DESCRIPTION
                   "This object indicates whether NTAS logging is
                    enabled or disabled.  If disabled, NT workstation
                    logging is used."
	::= { ntSystem 39 }

        ntOverwrite OBJECT-TYPE
		SYNTAX INTEGER {
                    disabled(0),
                    enabled(1),
                    unknown(2)
                  }
		ACCESS read-only
		STATUS mandatory
		DESCRIPTION
                   "Indicates whether an existing log file is to be
                    overwritten by the new one.  Enabled for NTAS,
                    disabled for NT workstation." 
	::= { ntSystem 40 }

        ntSendAlert OBJECT-TYPE
		SYNTAX INTEGER {
                    disabled(0),
                    enabled(1),
                    unknown(2)
                  }
		ACCESS read-only
		STATUS mandatory
		DESCRIPTION
                   "Indicates whether an administrative alert is sent;
                    enabled for NTAS, disabled for NT workstation."
	::= { ntSystem 41}

        ntIsClustered OBJECT-TYPE
		SYNTAX INTEGER {
		    true(1),
		    false(2)
                }
		ACCESS read-only
		STATUS mandatory
		DESCRIPTION
                   "Indicates whether this system is installed and/or
		    running in a windows cluster"
	::= { ntSystem 42 }

        ntClusterName OBJECT-TYPE
		SYNTAX DisplayString
		ACCESS read-only
		STATUS mandatory
		DESCRIPTION
                   "The cluster name that this system is a member of.
		    If the system is not a member of any cluster, then
   		    a zero-length string is returned.  The cluster
		    name can then be used with DNS or NetBIOS to determine
		    the virtual address of the logical cluster."
	::= { ntSystem 43 }

        ntClusterMembers OBJECT-TYPE
		SYNTAX DisplayString
		ACCESS read-only
		STATUS mandatory
		DESCRIPTION
                   "A comma-separated list of nodes that are members
		    of the cluster in which this system is a member.
		    Using this information, management software
		    can determine the members of a logical cluster and
		    act accordingly to deal with the logical cluster
		    and the individual nodes."
	::= { ntSystem 44 }

        ntClusterIsActive OBJECT-TYPE
		SYNTAX INTEGER {
		    true(1),
		    false(2)
                }
		ACCESS read-only
		STATUS mandatory
		DESCRIPTION
                   "Indicates whether this system is the primary or
		    active node in the NT cluster.  It does not
  		    necessarily say if the cluster service(s) are active
		    and up and running per se."
	::= { ntSystem 45 }

        ntClusterActiveNode OBJECT-TYPE
		SYNTAX DisplayString
		ACCESS read-only
		STATUS mandatory
		DESCRIPTION
                   "Indicates which of cluster members is active or
		    primary node.  Active node owns the Cluster Name
		    resource object."
	::= { ntSystem 46 }

-- 
-- The NT Thread group
-- 

	ntThreads OBJECT IDENTIFIER ::= { nt 2 }

        ntThreadTable OBJECT-TYPE
		SYNTAX SEQUENCE OF NtThreadEntry
		ACCESS not-accessible
		STATUS mandatory
		DESCRIPTION
		   "Table of NT system threads."
	::= { ntThreads 1 }

	ntThreadEntry OBJECT-TYPE
		SYNTAX NtThreadEntry
		ACCESS not-accessible
		STATUS mandatory
		DESCRIPTION
		   "An entry in the NT system thread table."
		INDEX { ntThreadPID, ntThreadNumber }
	::= { ntThreadTable 1 }

	NtThreadEntry ::= SEQUENCE {
                ntThreadPID
            		INTEGER,
          	ntThreadNumber
            		INTEGER,
                ntThreadPrivTime
			Counter,
                ntThreadProcTime
			Counter,
		ntThreadUserTime
			Counter,
		ntThreadContextSwitches
			Counter,
		ntThreadElapsedTime
			INTEGER,
                ntThreadPriorityBase
			Gauge,
 		ntThreadPriority
			Gauge,
		ntThreadWaitReason
			INTEGER,
		ntThreadStartAddr
			INTEGER,
		ntThreadState
			INTEGER,
		ntThreadID
			INTEGER
        }

        ntThreadPID OBJECT-TYPE
		SYNTAX INTEGER
		ACCESS read-only
		STATUS mandatory
		DESCRIPTION
                    "The unique process ID with which this thread is
                     contained and executing within."
	::= { ntThreadEntry 1 }

      	ntThreadNumber OBJECT-TYPE
		SYNTAX INTEGER
		ACCESS read-only
		STATUS mandatory
		DESCRIPTION
                    "The thread number within a given process.
                     Thread numbers are not unique across all threads
                     in the system." 
	::= { ntThreadEntry 2 }

        ntThreadPrivTime OBJECT-TYPE
		SYNTAX Counter 
		ACCESS read-only
		STATUS mandatory
		DESCRIPTION
                    "The total elapsed time (in centiseconds) that this thread
                     has executed in Privileged Mode."
	::= { ntThreadEntry 3 }

        ntThreadProcTime OBJECT-TYPE
		SYNTAX Counter 
		ACCESS read-only
		STATUS mandatory
		DESCRIPTION
                    "The total elapsed time (in centiseconds) that this thread
                     has used the processor to execute instructions."
	::= { ntThreadEntry 4 }

	ntThreadUserTime OBJECT-TYPE
		SYNTAX Counter 
		ACCESS read-only
		STATUS mandatory
		DESCRIPTION
                    "Total elapsed time (in centiseconds) that this thread has
                     executed in User Mode."
	::= { ntThreadEntry 5 }

	ntThreadContextSwitches OBJECT-TYPE
		SYNTAX Counter
		ACCESS read-only
		STATUS mandatory
		DESCRIPTION
                    "Number of thread context switches."
	::= { ntThreadEntry 6 }

	ntThreadElapsedTime OBJECT-TYPE
		SYNTAX INTEGER
		ACCESS read-only
		STATUS mandatory
		DESCRIPTION
                    "The total elapsed time (in seconds) this thread
                     has been running."
	::= { ntThreadEntry 7 }

        ntThreadPriorityBase OBJECT-TYPE
		SYNTAX Gauge
		ACCESS read-only
		STATUS mandatory
		DESCRIPTION
                    "The current base priority of this thread.  The
                     system may alter the thread's dynamic priority
                     above, below the base priority."
	::= { ntThreadEntry 8 }

	ntThreadPriority OBJECT-TYPE
		SYNTAX Gauge
		ACCESS read-only
		STATUS mandatory
		DESCRIPTION
                    "The current dynamic priority of this thread."
	::= { ntThreadEntry 9 }

	ntThreadWaitReason OBJECT-TYPE
		SYNTAX INTEGER {
                    waitForExecutive(0),
                    waitForFreePage(1),
                    waitForPageIn(2),
                    waitForPoolAlloc(3),
                    executionDelay(4),
                    suspended(5),
                    waitForUserRequest(6),
                    waitForExecutive1(7),
                    waitForFreePage1(8),
                    waitForPageIn1(9),
                    waitForPoolAlloc1(10),
                    executionDelay1(11),
                    suspended1(12),
                    waitForUserRequest1(13),
		    waitForEventPairHigh(14),
		    waitForEventPairLow(15),
		    waitForLPCRecv(16),
                    waitForLPCReply(17),
                    waitForVmem(18),
                    waitForPageOut(19)
                  }
		ACCESS read-only
		STATUS mandatory
		DESCRIPTION
                    "Reason thread is waiting; valid only if
                     ntThreadState is currently wait(5), otherwise
                     undefined."
	::= { ntThreadEntry 10 }

	ntThreadStartAddr OBJECT-TYPE
		SYNTAX INTEGER
		ACCESS read-only
		STATUS mandatory
		DESCRIPTION
                    "The starting virtual address of this thread."
	::= { ntThreadEntry 11 }

	ntThreadState OBJECT-TYPE
		SYNTAX INTEGER {
                    initialized(0),
 		    ready(1),
		    running(2),
		    standby(3),
		    terminated(4),
		    wait(5),
		    transition(6),
		    unknown(7)
                  }
		ACCESS read-only
		STATUS mandatory
		DESCRIPTION
                    "The current state of this thread."
	::= { ntThreadEntry 12 }

      	ntThreadID OBJECT-TYPE
		SYNTAX INTEGER
		ACCESS read-only
		STATUS mandatory
		DESCRIPTION
                    "The system-wide unique identifier associated with
                     this thread."
	::= { ntThreadEntry 13 }

-- 
-- The NT Registry group
-- 
	ntRegistry OBJECT IDENTIFIER ::= { nt 3 }

        ntRegistryCurrentSize OBJECT-TYPE
		SYNTAX INTEGER
		ACCESS read-only
		STATUS mandatory
		DESCRIPTION
                    "The current size of the registry in MBytes."
	::= { ntRegistry 1 }

        ntRegistrySizeLimit OBJECT-TYPE
		SYNTAX INTEGER
		ACCESS read-only
		STATUS mandatory
		DESCRIPTION
                    "The size limit of the registry in MBytes."
	::= { ntRegistry 2 }

-- 
-- The NT Services group
-- 
	ntServices OBJECT IDENTIFIER ::= { nt 4 }

	ntServiceTable OBJECT-TYPE
		SYNTAX SEQUENCE OF NtServiceEntry
		ACCESS not-accessible
		STATUS mandatory
		DESCRIPTION
		   "Table of NT system services"
	::= { ntServices 1 }

        ntServiceEntry OBJECT-TYPE
		SYNTAX NtServiceEntry
		ACCESS not-accessible
		STATUS mandatory
		DESCRIPTION
		   "An entry in the NT system service table."
		INDEX { ntServiceIndex }
	::= { ntServiceTable 1 }

	NtServiceEntry ::= SEQUENCE {
                ntServiceIndex
			 INTEGER,
                ntServiceName
		         DisplayString,
                ntServicePathName
			 DisplayString,
                ntServiceStartType
			 INTEGER,
                ntServiceParameters
			 DisplayString,
                ntServiceState
			 INTEGER,
                ntServiceObjectName
			 DisplayString
        }

        ntServiceIndex OBJECT-TYPE
		SYNTAX INTEGER
		ACCESS read-only
		STATUS mandatory
		DESCRIPTION
                    "The index of this system service."
	::= { ntServiceEntry 1 }

        ntServiceName OBJECT-TYPE
		SYNTAX DisplayString
		ACCESS read-only
		STATUS mandatory
		DESCRIPTION
                    "The system service name."
	::= { ntServiceEntry 2 }

        ntServicePathName OBJECT-TYPE
		SYNTAX DisplayString
		ACCESS read-only
		STATUS mandatory
		DESCRIPTION
                    "The system service path."
	::= { ntServiceEntry 3 }

        ntServiceStartType OBJECT-TYPE
		SYNTAX INTEGER {
                    automatic(1),
		    manual(2),
		    disabled(3),
		    other(4)
                }
		ACCESS read-write
		STATUS mandatory
		DESCRIPTION
                    "The manner in which the service is started;
                     automatic(1) implies that the system starts the
                     service at boot time while manual(2) implies that
                     the service must be started by hand by an
                     administrator.  Disabled(3) indicates that the
                     service cannot be started." 
	::= { ntServiceEntry 4 }

        ntServiceParameters OBJECT-TYPE
		SYNTAX DisplayString
		ACCESS read-only
		STATUS mandatory
		DESCRIPTION
                    "The parameters passed to this service when it is
                     invoked."
	::= { ntServiceEntry 5 }

        ntServiceState OBJECT-TYPE
		SYNTAX INTEGER {
                    running(1),
		    notRunning(2),
		    paused(3),
		    other(4)
                  }
		ACCESS read-write
		STATUS mandatory
		DESCRIPTION
                    "The current state of the system service."
	::= { ntServiceEntry 6 }

        ntServiceObjectName OBJECT-TYPE
		SYNTAX DisplayString
		ACCESS read-only
		STATUS mandatory
		DESCRIPTION
                    "The object name for this service. This indicates
                     the user name the service is currently running as."
	::= { ntServiceEntry 7 }

-- 
-- The NT Performance group(s)
-- 
-- Various NT-specific performance groups are located under the
-- ntPerformance branch
--
	ntPerformance OBJECT IDENTIFIER ::= { nt 5 }

--
-- NT System Performance group
-- 

        ntSystemPerf OBJECT IDENTIFIER ::= { ntPerformance 1 }

        ntTotalPrivTime OBJECT-TYPE
		SYNTAX Counter
		ACCESS read-only
		STATUS mandatory
		DESCRIPTION
                    "Running counter of centiseconds spent by the
                     system processor(s) in Privileged mode."
	::= { ntSystemPerf 1 }

        ntTotalProcessorTime OBJECT-TYPE
		SYNTAX Counter
		ACCESS read-only
		STATUS mandatory
		DESCRIPTION
                    "Running counter of centiseconds spent by the
                     system processor(s) running Idle threads.
		     Note that this is actually the inverse of 
		     the total processor time."
	::= { ntSystemPerf 2 }

        ntTotalUserTime OBJECT-TYPE
		SYNTAX Counter
		ACCESS read-only
		STATUS mandatory
		DESCRIPTION
                    "Running counter of centiseconds spent by the
                     system processor(s) running User mode."
	::= { ntSystemPerf 3 }

        ntAlignFixups OBJECT-TYPE
		SYNTAX Counter
		ACCESS read-only
		STATUS mandatory
		DESCRIPTION
                    "The number of alignment faults fixed by the system."
	::= { ntSystemPerf 4 }

        ntContextSwitches OBJECT-TYPE
		SYNTAX Counter
		ACCESS read-only
		STATUS mandatory
		DESCRIPTION
		   "The total number of context switches that
		    have occurred since the kernel was last
		    initialized.  A context switch occurs each
		    time a thread gives up the CPU and another
		    takes its place.  This counter reflects the
		    level of system activity; a high rate of
		    context switching is indicative of the system
                    load.  This counter is equivalent (for NT systems)
                    to the UNIX counter numSwitches(kernelperf.14)"
	::= { ntSystemPerf 5 }

        ntExceptionDispatches OBJECT-TYPE
		SYNTAX Counter
		ACCESS read-only
		STATUS mandatory
		DESCRIPTION
                    "The total number of exceptions dispacted by the
                     system since it was initialized." 
	::= { ntSystemPerf 6 }

        ntFileCtrlKBytes OBJECT-TYPE
		SYNTAX Counter
		ACCESS read-only
		STATUS mandatory
		DESCRIPTION
                    "An aggregate of KBytes transferred for all file
                     system operations that are neither reads or
                     writes (e.g. file system control requests or
                     device control requests)."
	::= { ntSystemPerf 7 }

        ntFileCtrlOps OBJECT-TYPE
		SYNTAX Counter
		ACCESS read-only
		STATUS mandatory
		DESCRIPTION
                    "Aggregate counter of all file system operations
                     that are neither reads nor writes."
	::= { ntSystemPerf 8 }

        ntFileDataOps OBJECT-TYPE
		SYNTAX Counter
		ACCESS read-only
		STATUS mandatory
		DESCRIPTION
                    "Total number of read and write operations to file
                     system devices issued by the system since system
                     initialization."
	::= { ntSystemPerf 9 }

        ntReadKBytes OBJECT-TYPE
		SYNTAX Counter
		ACCESS read-only
		STATUS mandatory
		DESCRIPTION
                    "Aggregate number of KBytes transferred for all the
                     file system read operations on this system since
                     system initialization."
	::= { ntSystemPerf 10 }

        ntReadOps OBJECT-TYPE
		SYNTAX Counter
		ACCESS read-only
		STATUS mandatory
		DESCRIPTION
                    "Aggregate of all the file system read operations
                     on this system since system initialization."
	::= { ntSystemPerf 11 }

        ntWriteKBytes OBJECT-TYPE
		SYNTAX Counter
		ACCESS read-only
		STATUS mandatory
		DESCRIPTION
                    "Aggregate number of KBytes transferred for all the
                     file system write operations on this system since
                     system initialization."
	::= { ntSystemPerf 12 }

        ntWriteOps OBJECT-TYPE
		SYNTAX Counter
		ACCESS read-only
		STATUS mandatory
		DESCRIPTION
                    "Aggregate number of all the file system write
                     operations on this system since system
                     initialization." 
	::= { ntSystemPerf 13 }

        ntFloatEmuls OBJECT-TYPE
		SYNTAX Counter
		ACCESS read-only
		STATUS mandatory
		DESCRIPTION
                    "Number of floating emulations performed by the
                     system."
	::= { ntSystemPerf 14 }

        ntRunQLen OBJECT-TYPE
		SYNTAX Gauge
		ACCESS read-only
		STATUS mandatory
		DESCRIPTION
                    "Instantaneous processor queue length in threads
                     and is equivalent to runQLen(kernelperf.4)"
	::= { ntSystemPerf 15 }

        ntSystemCalls OBJECT-TYPE
		SYNTAX Counter
		ACCESS read-only
		STATUS mandatory
		DESCRIPTION
                    "The number of calls to system service routines.
                     This object is equivalent to
                     numSyscalls(kernelperf.16)" 
	::= { ntSystemPerf 16 }

        ntInterrupts OBJECT-TYPE
		SYNTAX Counter
		ACCESS read-only
		STATUS mandatory
		DESCRIPTION
                    "The number of hardware interrupts that have
                     occurred.  This object is equivalent to
                     numInterrupts(kernelperf.17)" 
	::= { ntSystemPerf 17 }

--
-- NT Cache Performance group
-- 
        ntCachePerf OBJECT IDENTIFIER ::= { ntPerformance 2 }

        ntAsyncCopyReads OBJECT-TYPE
		SYNTAX Counter
		ACCESS read-only
		STATUS mandatory
		DESCRIPTION
                    "Number of async reads from Cache pages involving a
                     memory copy of the data from the Cache to the
                     application's buffer." 
	::= { ntCachePerf 1 }

        ntAsyncDataMaps OBJECT-TYPE
		SYNTAX Counter
		ACCESS read-only
		STATUS mandatory
		DESCRIPTION
                    "Number of async data maps of file pages into the
                     Cache."
	::= { ntCachePerf 2 }

        ntAsyncFastReads OBJECT-TYPE
		SYNTAX Counter
		ACCESS read-only
		STATUS mandatory
		DESCRIPTION
                    "Number of direct-to-Cache async read operations."
	::= { ntCachePerf 3 }

        ntAsyncMDLReads OBJECT-TYPE
		SYNTAX Counter
		ACCESS read-only
		STATUS mandatory
		DESCRIPTION
                    "Number of async memory descriptor list (MDL)
                     reads from the Cache.  The MDL contains the
                     physical address of each page in the transfer
                     thus permitting DMA of the pages."
	::= { ntCachePerf 4 }

        ntAsyncPinReads OBJECT-TYPE
		SYNTAX Counter
		ACCESS read-only
		STATUS mandatory
		DESCRIPTION
                    "Number of async reads from the Cache in
                     preparation to writing the data back to disk.
                     Pages read in this fashion are pinned in memory
                     at the completion of the read." 
	::= { ntCachePerf 5 }

        ntCopyReadHits OBJECT-TYPE
		SYNTAX Counter
		ACCESS read-only
		STATUS mandatory
		DESCRIPTION
                    "Number of Cache Copy Read requests that hit
                     the cache and did not require a disk read."
	::= { ntCachePerf 6 }

        ntCopyReads OBJECT-TYPE
		SYNTAX Counter
		ACCESS read-only
		STATUS mandatory
		DESCRIPTION
                    "The number of reads from Cache pages that
                     involved a memory copy of data from the Cache to
                     the application's buffer." 
	::= { ntCachePerf 7 }

        ntDataFlushPages OBJECT-TYPE
		SYNTAX Counter
		ACCESS read-only
		STATUS mandatory
		DESCRIPTION
                    "Number of pages of the Cache flushed to disk as a
                     result of a flush request or to satisfy a
                     write-through request." 
	::= { ntCachePerf 8 }

        ntDataFlushes OBJECT-TYPE
		SYNTAX Counter
		ACCESS read-only
		STATUS mandatory
		DESCRIPTION
                    "Number of Cache data flush operations."
	::= { ntCachePerf 9 }

        ntDataMapHits OBJECT-TYPE
		SYNTAX Counter
		ACCESS read-only
		STATUS mandatory
		DESCRIPTION
                    "Numberof data maps in the Cache that could
                     be resolved without retrieval from disk."
	::= { ntCachePerf 10 }

        ntDataMapPins OBJECT-TYPE
		SYNTAX Counter
		ACCESS read-only
		STATUS mandatory
		DESCRIPTION
                    "Number of data maps in the Cache that resulted in
                     pinning a page in main memory."
	::= { ntCachePerf 11 }

        ntDataMaps OBJECT-TYPE
		SYNTAX Counter
		ACCESS read-only
		STATUS mandatory
		DESCRIPTION
                    "Number of times a file system such as NTFS or
                     HPFS has mapped a page of a file into the Cache
                     to read the page." 
	::= { ntCachePerf 12 }

        ntFastReadNotPossible OBJECT-TYPE
		SYNTAX Counter
		ACCESS read-only
		STATUS mandatory
		DESCRIPTION
                    "Number of times an API function call to bypass
                     the file system to get at Cache data could not be
                     honored without invoking the file system after all."
	::= { ntCachePerf 13 }

        ntFastReadResourceMisses OBJECT-TYPE
		SYNTAX Counter
		ACCESS read-only
		STATUS mandatory
		DESCRIPTION
                    "Number of Cache misses necessitated by the lack
                     of available resources to satisfy the request."
	::= { ntCachePerf 14 }

        ntFastReads OBJECT-TYPE
		SYNTAX Counter
		ACCESS read-only
		STATUS mandatory
		DESCRIPTION
                    "Number of reads from Cache pages that bypass
                     installed file systems and read from the Cache
                     directly." 
	::= { ntCachePerf 15 }

        ntLazyWriteFlushes OBJECT-TYPE
		SYNTAX Counter
		ACCESS read-only
		STATUS mandatory
		DESCRIPTION
                    "The number of times the Cache's Lazy Write thread
                     has written to disk."
	::= { ntCachePerf 16 }

        ntLazyWritePages OBJECT-TYPE
		SYNTAX Counter
		ACCESS read-only
		STATUS mandatory
		DESCRIPTION
                    "Number of pages the Cache's Lazy Write thread
                     has written to disk.  Lazy Writing is the process
                     of updating the disk after the page has been
                     changed in memory so the application making the
                     change to the file does not have to wait for the
                     disk write to complete before proceeding."
	::= { ntCachePerf 17 }

        ntMDLReadHits OBJECT-TYPE
		SYNTAX Counter
		ACCESS read-only
		STATUS mandatory
		DESCRIPTION
                    "Number of Cache Memory Descriptor List (MDL)
                     read requests that hit the Cache."
	::= { ntCachePerf 18 }

        ntMDLReads OBJECT-TYPE
		SYNTAX Counter
		ACCESS read-only
		STATUS mandatory
		DESCRIPTION
                    "Number of MDL Cache reads."
	::= { ntCachePerf 19 }

        ntPinReadHits OBJECT-TYPE
		SYNTAX Counter
		ACCESS read-only
		STATUS mandatory
		DESCRIPTION
                    "Number Cache Pin Read requests that hit
                     the Cache."
	::= { ntCachePerf 20 }

        ntPinReads OBJECT-TYPE
		SYNTAX Counter
		ACCESS read-only
		STATUS mandatory
		DESCRIPTION
                    "Number of pages read from the Cache that have
                     been pinned in memory."
	::= { ntCachePerf 21 }

        ntSyncCopyReads OBJECT-TYPE
		SYNTAX Counter
		ACCESS read-only
		STATUS mandatory
		DESCRIPTION
                    "Number of reads from Cache pages that wait for
                     the copy operation to complete before proceeding."
	::= { ntCachePerf 22 }

        ntSyncDataMaps OBJECT-TYPE
		SYNTAX Counter
		ACCESS read-only
		STATUS mandatory
		DESCRIPTION
                    "Number of times that a file system such as NTFS
                     or HPFS maps a page of a file into the Cache to
                     read the page." 
	::= { ntCachePerf 23 }

        ntSyncFastReads OBJECT-TYPE
		SYNTAX Counter
		ACCESS read-only
		STATUS mandatory
		DESCRIPTION
                    "Number of sync reads from Cache pages that bypass
                     the installed file system and retrieve the data
                     directly from the Cache." 
	::= { ntCachePerf 24 }

        ntSyncMDLReads OBJECT-TYPE
		SYNTAX Counter
		ACCESS read-only
		STATUS mandatory
		DESCRIPTION
                    "Number of reads from Cache pages that use a
                     Memory Descriptor List (MDL) to access the pages."
	::= { ntCachePerf 25 }

        ntSyncPinReads OBJECT-TYPE
		SYNTAX Counter
		ACCESS read-only
		STATUS mandatory
		DESCRIPTION
                    "Number of page reads that have resulted in the
                     page being pinned in memory."
	::= { ntCachePerf 26 }

--
-- NT Memory Performance group
-- 

        ntMemoryPerf OBJECT IDENTIFIER ::= { ntPerformance 3 }

        ntAvailKBytes OBJECT-TYPE
		SYNTAX Gauge
		ACCESS read-only
		STATUS mandatory
		DESCRIPTION
                    "Number of KBytes of virtual memory currently on
                     the Zeroed, Free, and Standby lists.  Zeroed and
                     free memory is ready for use.  Standby memory is
                     memory removed from a process's working set but
                     still available."
	::= { ntMemoryPerf 1 }

        ntCacheKBytes OBJECT-TYPE
		SYNTAX Gauge
		ACCESS read-only
		STATUS mandatory
		DESCRIPTION
                    "Number of KBytes currently in use by the system Cache."
	::= { ntMemoryPerf 2 }

        ntCacheKBytesPeak OBJECT-TYPE
		SYNTAX INTEGER
		ACCESS read-only
		STATUS mandatory
		DESCRIPTION
                    "Maximum number of KBytes used by the system Cache."
	::= { ntMemoryPerf 3 }

        ntCacheFaults OBJECT-TYPE
		SYNTAX Counter
		ACCESS read-only
		STATUS mandatory
		DESCRIPTION
                    "Number of Cache faults whereby memory had to be
                     located elsewhere."
	::= { ntMemoryPerf 4 }

        ntCommitLimit OBJECT-TYPE
		SYNTAX INTEGER
		ACCESS read-only
		STATUS mandatory
		DESCRIPTION
                    "Size in KBytes of virtual memory that can be
                     committed without having to expand the paging
                     file(s)." 
	::= { ntMemoryPerf 5 }

        ntCommittedKBytes OBJECT-TYPE
		SYNTAX Gauge
		ACCESS read-only
		STATUS mandatory
		DESCRIPTION
                    "Number of KBytes of virtual memory that have been
                     committed."
	::= { ntMemoryPerf 6 }

        ntDemandZeroFaults OBJECT-TYPE
		SYNTAX Counter
		ACCESS read-only
		STATUS mandatory
		DESCRIPTION
                    "Number of page faults for pages that must be
                     filled with zeros before fault is satisifed."
	::= { ntMemoryPerf 7 }

        ntFreeSysPageTableEntries OBJECT-TYPE
		SYNTAX Gauge
		ACCESS read-only
		STATUS mandatory
		DESCRIPTION
                    "Number of Page Table entries not currently in use
                     by the system."
	::= { ntMemoryPerf 8 }

        ntPageFaults OBJECT-TYPE
		SYNTAX Counter
		ACCESS read-only
		STATUS mandatory
		DESCRIPTION
                    "Number of page faults in the processor and is
                     equivalent to numPageFaults(kernelperf.25)"
	::= { ntMemoryPerf 9 }

        ntPageReads OBJECT-TYPE
		SYNTAX Counter
		ACCESS read-only
		STATUS mandatory
		DESCRIPTION
                    "Number of times the disk was read to retrieve
                     pages of virtual memory."
	::= { ntMemoryPerf 10 }

        ntPageWrites OBJECT-TYPE
		SYNTAX Counter
		ACCESS read-only
		STATUS mandatory
		DESCRIPTION
                    "Number of times pages have been written to disk."
	::= { ntMemoryPerf 11 }

        ntPagesInput OBJECT-TYPE
		SYNTAX Counter
		ACCESS read-only
		STATUS mandatory
		DESCRIPTION
                    "Number of pages read from disk to resolve memory
                     references and is equivalent to numPageIns
                     (kernelperf.22)"
	::= { ntMemoryPerf 12 }

        ntPagesOutput OBJECT-TYPE
		SYNTAX Counter
		ACCESS read-only
		STATUS mandatory
		DESCRIPTION
                    "Number of pages written to disk because the pages
                     were modified and is equivalent to numPageOuts
                     (kernelperf.23)."
	::= { ntMemoryPerf 13 }

        ntPages OBJECT-TYPE
		SYNTAX Counter
		ACCESS read-only
		STATUS mandatory
		DESCRIPTION
                    "Number of pages read or written from/to disk and
                     is a sum of PagesInput(12) and PagesOutput(13)."
	::= { ntMemoryPerf 14 }

        ntPoolNonPagedAllocs OBJECT-TYPE
		SYNTAX Gauge
		ACCESS read-only
		STATUS mandatory
		DESCRIPTION
                    "Number of calls to allocate space in the system
                     Nonpaged pool."
	::= { ntMemoryPerf 15 }

        ntPoolNonPagedKBytes OBJECT-TYPE
		SYNTAX Gauge
		ACCESS read-only
		STATUS mandatory
		DESCRIPTION
                    "Number of KBytes in the Nonpaged pool which is a
                     system memory area where space is acquired by
                     operating systems facilities as they accomplish
                     their tasks.  These pages cannot be paged out to
                     disk." 
	::= { ntMemoryPerf 16 }

        ntPoolPagedAllocs OBJECT-TYPE
		SYNTAX Gauge
		ACCESS read-only
		STATUS mandatory
		DESCRIPTION
                    "Number of calls to allocate space in the system
                     Paged Pool.  Paged Pool is a system memory area
                     where space is acquired by operating systems
                     facilities as they accomplish their tasks.  Paged
                     Pool bytes may be paged out to disk when not
                     accessed by the system for sustained periods of
                     time." 
	::= { ntMemoryPerf 17 }

        ntPoolPagedKBytes OBJECT-TYPE
		SYNTAX Gauge
		ACCESS read-only
		STATUS mandatory
		DESCRIPTION
                    "Number of KBytes in the Paged Pool."
	::= { ntMemoryPerf 18 }

        ntPagedResidentKBytes OBJECT-TYPE
		SYNTAX Gauge
		ACCESS read-only
		STATUS mandatory
		DESCRIPTION
                    "Size of paged Pool resident in core memory in KBytes."
	::= { ntMemoryPerf 19 }

        ntSysCacheResidentKBytes OBJECT-TYPE
		SYNTAX Gauge
		ACCESS read-only
		STATUS mandatory
		DESCRIPTION
                    "Number of KBytes currently resident in the global
                     disk cache."
	::= { ntMemoryPerf 20 }

        ntSysCodeResidentKBytes OBJECT-TYPE
		SYNTAX Gauge
		ACCESS read-only
		STATUS mandatory
		DESCRIPTION
                    "Number of KBytes of System Code Total Bytes
                     currently resident in core memory.  This is the
                     code working set of the pagable executive."
	::= { ntMemoryPerf 21 }

        ntSysCodeTotalKBytes OBJECT-TYPE
		SYNTAX Gauge
		ACCESS read-only
		STATUS mandatory
		DESCRIPTION
                    "Total number of KBytes of pageable pages in
                     ntoskrnl.exe, hal.dll, and the boot drivers and
                     file systems loaded by ntldr/osloader." 
	::= { ntMemoryPerf 22 }

        ntSysDriverResidentKBytes OBJECT-TYPE
		SYNTAX Gauge
		ACCESS read-only
		STATUS mandatory
		DESCRIPTION
                    "Number of KBytes of System Driver Total KBytes
                     currently resident in core memory.  The number is
                     the code working set of the pagable drivers."
	::= { ntMemoryPerf 23 }

        ntSysDriverTotalKBytes OBJECT-TYPE
		SYNTAX Gauge
		ACCESS read-only
		STATUS mandatory
		DESCRIPTION
                    "Number of KBytes of pageable pages in all other
                     loaded device drivers."
	::= { ntMemoryPerf 24 }

        ntTransitionFaults OBJECT-TYPE
		SYNTAX Counter
		ACCESS read-only
		STATUS mandatory
		DESCRIPTION
                    "Number of page faults resolved by recovering
                     pages that were in transition to disk at time of
                     page fault." 
	::= { ntMemoryPerf 25 }

        ntWriteCopies OBJECT-TYPE
		SYNTAX Counter
		ACCESS read-only
		STATUS mandatory
		DESCRIPTION
                    "Number of page faults that have been satisfied by
                     making a copy of a page when an attempt to write
                     the page was made while it was shared." 
	::= { ntMemoryPerf 26 }

--
-- NT Paging-File Performance group
-- 

        ntPageFilePerf OBJECT IDENTIFIER ::= { ntPerformance 4 }

        ntPageFileUsage OBJECT-TYPE
		SYNTAX INTEGER (0..100)
		ACCESS read-only
		STATUS mandatory
		DESCRIPTION
                    "The percentage of the page file(s) used."
	::= { ntPageFilePerf 1 }

        ntPageFilePeakUsage OBJECT-TYPE
		SYNTAX INTEGER (0..100)
		ACCESS read-only
		STATUS mandatory
		DESCRIPTION
                    "The peak usage of the page file(s)."
	::= { ntPageFilePerf 2 }

-- 
-- Concord/Empire NT Event Log monitoring group
-- 
-- This group provides access to the agent's NT Event Log monitoring
-- capabilities.  Via the ntEventMonTable, managers can specify 
-- that the agent monitor certain event logs for certain patterns
-- or regular expressions.  When a match has occurred, the agent
-- sends a Trap to appropriate managers.  Entries can be placed
-- in the ntEventMonTable via two methods: through entries in the
-- agent configuration file (snmpd.empire.conf) or via the SNMP.
-- Note: only entries placed in the agent configuration file 
-- will exist the next time the agent is started.  Entries placed
-- in the table via SNMP will not exist the next time the agent
-- is started.

	ntEvents OBJECT IDENTIFIER ::= { nt 6 }

        ntEventApplicationCount OBJECT-TYPE
		SYNTAX Counter
		ACCESS read-only
		STATUS mandatory
		DESCRIPTION
                    "The number of events in the Application event log."
	::= { ntEvents 1 }

        ntEventSecurityCount OBJECT-TYPE
		SYNTAX Counter
		ACCESS read-only
		STATUS mandatory
		DESCRIPTION
                    "The number of events in the Security event log."
	::= { ntEvents 2 }

        ntEventSystemCount OBJECT-TYPE
		SYNTAX Counter
		ACCESS read-only
		STATUS mandatory
		DESCRIPTION
                    "The number of events in the System event log."
	::= { ntEvents 3 }

	ntEventMonTable OBJECT-TYPE
		SYNTAX SEQUENCE OF NtEventMonEntry
		ACCESS not-accessible
		STATUS mandatory
		DESCRIPTION
                   "Table containing NT Event Log monitor entries; each entry 
                    specifies an Event Log and regular expression.
	            The agent periodically stats the event logs to 
                    see if they have been updated.  If updated, the
                    agent scans the new entries for the regular
                    expressions.  When an entry is found that matches
                    the regular expressions, a trap PDU is
                    sent to appropriate managers."
        ::= { ntEvents 4 }

        ntEventMonEntry OBJECT-TYPE
		SYNTAX NtEventMonEntry
		ACCESS not-accessible
		STATUS mandatory
		DESCRIPTION
                   "An entry in the ntEventMonTable."
		INDEX { ntEventMonIndex }
	::= { ntEventMonTable 1 }

	NtEventMonEntry ::= SEQUENCE {
		ntEventMonIndex
			INTEGER,
		ntEventMonLog
			INTEGER,
		ntEventMonTime
			TimeTicks,
		ntEventMonTraps
			INTEGER,
		ntEventMonTypeLastMatch
			INTEGER,
		ntEventMonTypeFilter
			INTEGER,
		ntEventMonSrcLastMatch
			DisplayString,
		ntEventMonSrcFilter
			DisplayString,
		ntEventMonDescLastMatch
			DisplayString,
		ntEventMonDescFilter
			DisplayString,
		ntEventMonStatus
			INTEGER,
		ntEventMonDescr
			DisplayString,
		ntEventMonAction
			DisplayString,
                ntEventMonFlags
			INTEGER,
		ntEventMonMatches
			Counter

        }

	ntEventMonIndex OBJECT-TYPE
		SYNTAX INTEGER (1..2147483647)
		ACCESS read-only
		STATUS mandatory
		DESCRIPTION
                   "An index that uniquely identifies an entry in the
                    ntEventMonTable."
	::= { ntEventMonEntry 1 } 

	ntEventMonLog OBJECT-TYPE
		SYNTAX INTEGER {
		   application(1),
		   security(2),
		   system(3),
		   dnsServer(4),      -- in 4.1+
		   dirService(5),     -- in 4.1+
		   fileRepService(6)  -- in 4.1+
                }
		ACCESS read-write
		STATUS mandatory
		DESCRIPTION
                   "The number identifying the NT event log to 
                    scan for pattern matches. Possible values are 
                    Application(1), Security(2), and System(3).  On
		    Win2k and higher, dnsServer(4), dirService(5), and
		    fileRepService(6) are also possibly valid.  Not
		    all win2k+ systems have these event logs."
	::= { ntEventMonEntry 2 } 

	ntEventMonTime OBJECT-TYPE
		SYNTAX TimeTicks
		ACCESS read-only
		STATUS mandatory
		DESCRIPTION
                    "The time (based on sysUpTime) at which the event
                     occurred."
	::= { ntEventMonEntry 3 } 

	ntEventMonTraps OBJECT-TYPE
		SYNTAX INTEGER
		ACCESS read-only
		STATUS mandatory
		DESCRIPTION
                   "The number of traps sent by the agent on behalf of
                    this entry.  One trap PDU message is sent for each
                    match the agent detects in the corresponding event
   		    log.  This MIB object used to be called
		    ntEventMonMatches but has been renamed to better
		    reflect its true semantics." 
	::= { ntEventMonEntry 4 } 

	ntEventMonTypeLastMatch OBJECT-TYPE
		SYNTAX INTEGER {
		   error(1),
		   warning(2),
		   information(3),
		   success(4),
		   failure(5),
		   noMatch(6)
                }
		ACCESS read-only
		STATUS mandatory
		DESCRIPTION
                   "The number identifying the event type of the last
		    event that matched the search criteria. Types 
                    1 through 5 are defined by Windows NT. Type 
                    noMatch(6) indicates that there has not yet been
                    a matching event for this monitoring entry."
	::= { ntEventMonEntry 5 } 

	ntEventMonTypeFilter OBJECT-TYPE
		SYNTAX INTEGER {
		   error(1),
		   warning(2),
		   information(3),
		   success(4),
		   failure(5),
		   all(6)
                }
		ACCESS read-write
		STATUS mandatory
		DESCRIPTION
                   "The number identifying the event type to match.
                    Types 1 through 5 are defined by Windows NT.
                    Type all(6) indicates that all event types will match."
	::= { ntEventMonEntry 6 } 

	ntEventMonSrcLastMatch OBJECT-TYPE
		SYNTAX DisplayString (SIZE (0..64))
		ACCESS read-only
		STATUS mandatory
		DESCRIPTION
                   "The source name of the last event log entry that 
                    matched this monitor entry. Each time a match occurs, 
                    this variable is updated."
	::= { ntEventMonEntry 7 } 

	ntEventMonSrcFilter OBJECT-TYPE
		SYNTAX DisplayString (SIZE (0..64))
		ACCESS read-write
		STATUS mandatory
		DESCRIPTION
                   "The display string representation of the regular
                    expression to match the source name in the event log.
                    Valid regular expressions are those as defined in
                    ed(1)."
	::= { ntEventMonEntry 8 } 

	ntEventMonDescLastMatch OBJECT-TYPE
		SYNTAX DisplayString (SIZE (0..512))
		ACCESS read-only
		STATUS mandatory
		DESCRIPTION
                   "The text description message from the last event log 
                    entry that matched this monitor entry. Each time a
                    match occurs, this variable is updated."
	::= { ntEventMonEntry 9 } 

	ntEventMonDescFilter OBJECT-TYPE
		SYNTAX DisplayString (SIZE (0..64))
		ACCESS read-write
		STATUS mandatory
		DESCRIPTION
                   "The display string representation of the regular
                    expression to match the description in the event log.
                    Valid regular expressions are those as defined in
                    ed(1)."
	::= { ntEventMonEntry 10 } 

	ntEventMonStatus OBJECT-TYPE
		SYNTAX INTEGER {
		   active(1),
		   notInService(2),
		   notReady(3),
		   createAndGo(4),
		   createAndWait(5),
		   destroy(6)
                }
		ACCESS read-write
		STATUS mandatory
		DESCRIPTION
		   "The status of this entry.  This variable is
		    equivalent in semantics to the V2 SMI
		    RowStatus textual-convention (see RFC 1443).
		    A value of active(1) indicates that the agent
		    is currently monitoring and evaluating the
		    current row.  A Value of notInService(2)
		    indicates that the agent has suspended
		    evaluation of the row.  Setting this object
		    to destroy(2) causes the agent to suspend
		    evaluation of its row and free its resources.
		    For row creation to occur, the manager must
		    supply active(1), createAndGo(4),
		    createAndWait(5), or notInService(2) as the
		    value of this object.  
		    If an error occurs at any time during the
		    processing of a particular ntEventMon Table entry,
                    its Status column will be set to notReady(3)."
                DEFVAL { createAndWait } 
	::= { ntEventMonEntry 11 } 

	ntEventMonDescr OBJECT-TYPE
		SYNTAX DisplayString (SIZE (0..128))
		ACCESS read-write
		STATUS mandatory
		DESCRIPTION
		   "A textual description of this entry possibly 
	 	    identifying the purpose of this entry and who
		    created it."
	::= { ntEventMonEntry 12 }

	ntEventMonAction OBJECT-TYPE
		SYNTAX DisplayString (SIZE (0..256))
		ACCESS read-write
		STATUS mandatory
		DESCRIPTION
		   "A string specifying the command to be executed 
		    upon finding a match."
	::= { ntEventMonEntry 13 }

	ntEventMonFlags OBJECT-TYPE
		SYNTAX INTEGER
		ACCESS read-write
		STATUS mandatory
		DESCRIPTION
                    "The flags field dictates the behavior of each
                     ntEventMonEntry.  Each bit in the integer
                     represents the toggling of an option.  The flags
                     field of 0x00 is enables default behavior.
                     Logical or'ing together of different bits allows
                     one to combine different options.

               Hex   Function                  Default (if not enabled)

               0x01  Do not execute actions    Execute actions
               0x02  Do not send Traps         Send Traps   
               0x04  Do not re-initialize      Re-initialize
               0x08  Do not log events         Log events
               0x10  Send cont Stop Traps      Send single Stop Trap
               0x100 Prepend event-id to descr Do not pre-pend
               0x200 Logical-not the entry     No operator applied"
	::= { ntEventMonEntry 14 }

	ntEventMonMatches OBJECT-TYPE
		SYNTAX Counter
		ACCESS read-only
		STATUS mandatory
		DESCRIPTION
                   "The number of nt-event matches detected by
   		    SystemEDGE.  This value is incremented regardless
		    of whether Traps are sent for this entry or not.
		    Polling this variable allows you to determine the
		    rate or number of matches over time."
	::= { ntEventMonEntry 15 } 

--
-- 
--

        ntEventApplicationMaxSize OBJECT-TYPE
		SYNTAX Gauge
		ACCESS read-only
		STATUS mandatory
		DESCRIPTION
                    "The maximum size (in Bytes) of the Application event log."
	::= { ntEvents 5 }

        ntEventApplicationRetention OBJECT-TYPE
		SYNTAX Gauge
		ACCESS read-only
		STATUS mandatory
		DESCRIPTION
                    "The retention flag for the Application event log.
                     This flag indicates the settings for the Event
                     Log Wrapping settings."
	::= { ntEvents 6 }

        ntEventSecurityMaxSize OBJECT-TYPE
		SYNTAX Gauge
		ACCESS read-only
		STATUS mandatory
		DESCRIPTION
                    "The maximum size (in Bytes) of the Security event log."
	::= { ntEvents 7 }

        ntEventSecurityRetention OBJECT-TYPE
		SYNTAX Gauge
		ACCESS read-only
		STATUS mandatory
		DESCRIPTION
                    "The retention flag for the Security event log.
                     This flag indicates the settings for the Event
                     Log Wrapping settings."
	::= { ntEvents 8 }

        ntEventSystemMaxSize OBJECT-TYPE
		SYNTAX Gauge
		ACCESS read-only
		STATUS mandatory
		DESCRIPTION
                    "The maximum size (in Bytes) of the System event log."
	::= { ntEvents 9 }

        ntEventSystemRetention OBJECT-TYPE
		SYNTAX Gauge
		ACCESS read-only
		STATUS mandatory
		DESCRIPTION
                    "The retention flag for the System event log.
                     This flag indicates the settings for the Event
                     Log Wrapping settings."
	::= { ntEvents 10 }

        ntEventUnusedIndex OBJECT-TYPE
		SYNTAX INTEGER (1..2147483647)
		ACCESS read-only
                STATUS mandatory
                DESCRIPTION
                   "An SNMP Get of this MIB object returns an un-used
                    NT event monitor Table index number.  It can be used
                    for NT event monitor table row creation optimization."
	::= { ntEvents 11 }

        ntEventMatchDescr OBJECT-TYPE
		SYNTAX DisplayString
		ACCESS read-write
                STATUS mandatory
                DESCRIPTION
                   "This MIB object, when used in conjunction with
                    ntEventMatchIndex can be used to quickly determine
                    the index number corresponding to a particular entry
		    description.  SNMP Set'ing a description to this MIB
		    object causes the agent to search through entries in
		    the NT event monitor table and place the
                    index value of the last entry whose description
                    matches, in the ntEventMatchIndex MIB object."
	::= { ntEvents 12 }

        ntEventMatchIndex OBJECT-TYPE
		SYNTAX INTEGER (1..2147483647)
		ACCESS read-only
                STATUS mandatory
                DESCRIPTION
                   "See description for ntEventMatchDescr."
	::= { ntEvents 13 }

---
--- Concord/Empire NT Registry and Performance Extension Variable Group
---
--- This group allows users of the Concord SystemEDGE Agent on Windows NT
--- to extend the Empire Enterprise MIB by adding new scalar variables. 
--- Each leaf in this group specifies a different MIB scalar value. 
--- The values for these variables are determined by querying the NT 
--- registry as specfied in the SystemEDGE configuration file (sysedge.cf)
--- See the SystemEDGE Agent User Manual for more information. 
---
--- Included here are some sample MIB variables that match the sample 
--- entries in sysedge.cf
---
	ntRegPerf OBJECT IDENTIFIER ::= { nt 7 }

        ntRegPerfDumpFile OBJECT-TYPE
                SYNTAX DisplayString (SIZE (0..256))
                ACCESS read-only
                STATUS mandatory
                DESCRIPTION
                   "The name of the dump file specified by the registry."
        ::= { ntRegPerf 1 }

        ntRegNumberOfThreads OBJECT-TYPE
                SYNTAX Gauge 
                ACCESS read-only
                STATUS mandatory
                DESCRIPTION
                   "The total number of threads currently running in the
                    system. This is obtained from the performance library." 
        ::= { ntRegPerf 2 }

--
-- The Monitor Group
-- 
-- This group provides access to the agent's internal monitoring
-- capabilities.  Via the monitorTable, managers can specifiy which
-- objects (under the agent's control) to monitor give a boolean
-- expression.  This expression tells the agent when to generate an
-- alarm (Trap) to appropriate managers.
--

	monitorTable OBJECT-TYPE
		SYNTAX SEQUENCE OF MonitorEntry
		ACCESS not-accessible
		STATUS mandatory
		DESCRIPTION
		   "Table describing the monitoring activities
		    of the agent.  Adding rows to this table
		    causes the agent to monitor new objects;
		    deleting rows from the table causes the agent
		    to cease monitoring the associated object.
		    Row creation follows the V2 SMI RowStatus
		    textual convention (See RFC 1443)."
	::= { monitor 1 }

	monitorEntry OBJECT-TYPE
		SYNTAX MonitorEntry
		ACCESS not-accessible
		STATUS mandatory
		DESCRIPTION
		   "Each entry in the Monitor Table represents a
		    single variable or function that the agent is
		    monitoring.  Variables are those objects in
		    the MIB for which the agent is tracking.
		    Likewise, functions that the agent are
		    calling periodically as part of its 
		    internal implementation are available for
		    manipulation via this table."
		INDEX { monIndex }
	::= { monitorTable 1 }

	MonitorEntry ::= SEQUENCE {
		monIndex
			INTEGER,
		monDescr
			DisplayString,
		monInterval
			INTEGER,
		monSampleType
			INTEGER,
		monOID
			OBJECT IDENTIFIER,
		monCurrVal
			INTEGER,
		monOperator
			INTEGER,
		monValue
			INTEGER,
		monLastCall
			TimeTicks,
		monNumTraps
			INTEGER,
		monLastTrap
			TimeTicks,
		monRowStatus
			INTEGER,
		monMinValue
			INTEGER,
		monMaxValue
			INTEGER,
		monAction
			DisplayString,
                monFlags
			INTEGER
	}

	monIndex OBJECT-TYPE
		SYNTAX INTEGER (1..2147483647)
		ACCESS read-only
		STATUS mandatory
		DESCRIPTION
		   "A unique value for entry in the monitorTable.
		    The index values in the monitorTable may not
		    necessarily be contiguous, but are unique."
	::= { monitorEntry 1 }

	monDescr OBJECT-TYPE
		SYNTAX DisplayString (SIZE (0..128))
		ACCESS read-write
		STATUS mandatory
		DESCRIPTION
		   "A textual description of this entry possibly
		    identifying the purpose of this entry and who
		    created it." 
	::= { monitorEntry 2 }

	monInterval OBJECT-TYPE
		SYNTAX INTEGER (1..2147483647)
		ACCESS read-write
		STATUS mandatory
		DESCRIPTION
		   "The interval, in seconds, between successive
		    samples by the agent.  It must be a multiple of 30
                    seconds.  For example, if a manager wanted to
                    sample the value of a particular variable every 30
                    seconds, then setting monInterval to 30 would
                    instruct the agent to sample once very 30 seconds.
                    The sampling period is not exact but represents a
		    best-effort by the agent." 
                DEFVAL { 60 }
	::= { monitorEntry 3 }

	monSampleType OBJECT-TYPE
		SYNTAX INTEGER {
		   absoluteValue(1),
		   deltaValue(2)
                }
		ACCESS read-write
		STATUS mandatory
		DESCRIPTION
		   "The type of sampling performed on the object
		    represented by this entry.  For example, for
		    sampling and monitoring objects of type
		    Counter, setting the appropriate
		    monSampleType to deltaValue(2) causes the
		    agent to measure/sample the rate of change in
		    the variable rather than the absolute value.
		    For gauge and gauge-like variables,
		    absoluteValue(1) makes more sense.  The agent
		    does not perform sanity checks on this
		    variable against the type of object being
		    monitoring because there may exist some case
		    where a manage may actually wish to monitor
		    the absolute value of a counter or the delta
		    value of a gauge." 
                DEFVAL { absoluteValue }
	::= { monitorEntry 4 }

	monOID OBJECT-TYPE
		SYNTAX OBJECT IDENTIFIER
		ACCESS read-write
		STATUS mandatory
		DESCRIPTION
		   "The object identifier (including properly
		    formed instance) of the variable being
		    monitoring by this monitorTable entry.  For
		    example, if a manager wanted to monitor the
		    number of packets received on a particular
		    network interface, that manager would write
		    the object identifier corresponding to the
		    appropriate counter (e.g.
		    ifTable.ifEntry.ifInUCastPkts.1 for the first
		    interface).  During row creation, the agent
		    ensures that the object identifier is valid.
		    If invalid, the agent returns BadValue.  This
		    variable can represent both scalar and
		    tabular objects as well.  If, at any point
		    during the row's lifetime, the variable no
		    longer exists in the agent's MIB, the row's
		    status is set to notInService(2)."
--              DEFVAL { 0 0 }
	::= { monitorEntry 5 }

	monCurrVal OBJECT-TYPE
		SYNTAX INTEGER
		ACCESS read-only
		STATUS mandatory
		DESCRIPTION
		   "This variable represents the current value of
		    the object being monitored as last sampled by
		    the agent.  If the monSampleType is
		    deltaValue(2), then this value represents the
		    difference between two successive samples.
		    If monSampleType is absoluteValue(1), then
		    this value represents the actual sampled value." 
	::= { monitorEntry 6 }

	monOperator OBJECT-TYPE
		SYNTAX INTEGER {
		   nop(1),
		   gt(2),
		   lt(3),
		   ge(4),
		   le(5),
		   eq(6),
		   ne(7)
                }
		ACCESS read-write
		STATUS mandatory
		DESCRIPTION
		   "The boolean operator performed in the
		    expression: monCurrVal monOperator monValue.
		    For example, to monitor a value such that an
		    alarm is generated when its value rises about 
		    100, the expression:

		        currValue gt 100

		    could be used.  Likewise, 

		        currValue ge 101 
         
		    could also be used.  The value of nop(1)
		    causes the agent to perform no boolean
		    comparison; it is useful when a manager
		    wishes that an agent track the value 
		    of some object but not perform any evaluation
		    of its value."
                DEFVAL { nop }
	::= { monitorEntry 7 }

	monValue OBJECT-TYPE
		SYNTAX INTEGER
		ACCESS read-write
		STATUS mandatory
		DESCRIPTION
		   "The value against which the agent compares
		    the current value.  This value represents a
		    threshold.  Its semantics are not interpreted
		    by the agent; therefore, the manager is
		    responsible for determining if this value
		    'makes sense'."  
	::= { monitorEntry 8 }

	monLastCall OBJECT-TYPE
		SYNTAX TimeTicks
		ACCESS read-only
		STATUS mandatory
		DESCRIPTION
		   "The time (based on sysUpTime) at which the agent
		    last called or sampled the object being
		    monitored.  If the object has not yet been
		    sampled, 0 is returned." 
	::= { monitorEntry 9 }

	monNumTraps OBJECT-TYPE
		SYNTAX INTEGER
		ACCESS read-only
		STATUS mandatory
		DESCRIPTION
		   "The number of traps sent for this particular
		    monitor entry.  This value indicates how many
		    times the agent has evaluated this entry's
		    expression as true.  Recall, the expression
		    takes the form of:
		         'monCurrVal monOperator monValue'.
		    Because this value depends on the semantics
		    of the variable, the entry's sampling
		    interval (monInterval), and the interval at
		    which the monitoring table is evaluated, it
		    represents a lower bound on the number of
		    times the threshold has actually been crossed."
	::= { monitorEntry 10 }

	monLastTrap OBJECT-TYPE
		SYNTAX TimeTicks
		ACCESS read-only
		STATUS mandatory
		DESCRIPTION
		   "The time (based on sysUpTime) at which the
		    agent last sent a trap for this Monitor Table
		    entry.  If no traps have been sent, the value
		    is 0."
	::= { monitorEntry 11 }

	monRowStatus OBJECT-TYPE
		SYNTAX INTEGER {
		   active(1),
		   notInService(2),
		   notReady(3),
		   createAndGo(4),
		   createAndWait(5),
		   destroy(6)
                }
		ACCESS read-write
		STATUS mandatory
		DESCRIPTION
		   "The status of this entry.  This variable is
		    equivalent in semantics to the V2 SMI
		    RowStatus textual-convention (see RFC 1443).
		    A value of active(1) indicates that the agent
		    is currently monitoring and evaluating the
		    current row.  A Value of notInService(2)
		    indicates that the agent has suspended
		    evaluation of the row.  Setting this object
		    to destroy(2) causes the agent to suspend
		    evaluation of its row and free its resources.
		    For row creation to occur, the manager must
		    supply active(1), createAndGo(4),
		    createAndWait(5), or notInService(2) as the
		    value of this object.  
		    If an error occurs at any time during the
		    processing of a particular Monitor Table entry, its
		    monRowStatus column will be set to 
		    notReady(3)."
                DEFVAL { createAndWait } 
	::= { monitorEntry 12 }

	monMinValue OBJECT-TYPE
		SYNTAX INTEGER 
		ACCESS read-only
		STATUS mandatory
		DESCRIPTION
                    "The minimum sampled value or 0 upon initialization"
	::= { monitorEntry 13 }

	monMaxValue OBJECT-TYPE
		SYNTAX INTEGER 
		ACCESS read-only
		STATUS mandatory
		DESCRIPTION
                    "The maximum sampled value or 0 upon initialization"
	::= { monitorEntry 14 }

	monAction OBJECT-TYPE
		SYNTAX DisplayString (SIZE (0..256))
		ACCESS read-write
		STATUS mandatory
		DESCRIPTION
		   "A string specifying the command to be executed 
		    upon finding a match."
	::= { monitorEntry 15 }

	monFlags OBJECT-TYPE
		SYNTAX INTEGER 
		ACCESS read-write
		STATUS mandatory
		DESCRIPTION
                    "The flags field dictates the behavior of each
                     Monitor Entry.  Each bit in the integer
                     represents the toggling of an option.  The flags
                     field of 0x00 is enables default behavior.
                     Logical or'ing together of different bits allows
                     one to combine different options.

               Hex   Function                  Default (if not enabled)

               0x01  Do not execute actions    Execute actions
               0x02  Do not send Traps         Send Traps   
               0x04  Do not re-initialize      Re-initialize
               0x08  Do not log events         Log events
               0x10  Send cont notReady Traps  Send single notReady Trap

              0x100  Send Clear Traps          Do not send Clear Traps
              0x200  Threshold after X events  Threshold after 1st
              0x400  X consec Thresh Traps     No limit
         0xfff00000  Flags value specification Default is 0"

	::= { monitorEntry 16 }

        monUnusedIndex OBJECT-TYPE
		SYNTAX INTEGER (1..2147483647)
		ACCESS read-only
                STATUS mandatory
                DESCRIPTION
                   "An SNMP Get of this MIB object returns an un-used
                    monitor index number.  It can be used
                    for monitor table row creation optimization."
	::= { monitor 2 }

        monMatchDescr OBJECT-TYPE
		SYNTAX DisplayString
		ACCESS read-write
                STATUS mandatory
                DESCRIPTION
                   "This MIB object, when used in conjunction with
                    monMatchIndex can be used to quickly determine
                    the index number corresponding to a particular entry
		    description.  SNMP Set'ing a description to this MIB
		    object causes the agent to search through entries in
		    the monitor table and place the
                    index value of the last entry whose description
                    matches, in the monMatchIndex MIB object."
	::= { monitor 3 }

        monMatchIndex OBJECT-TYPE
		SYNTAX INTEGER (1..2147483647)
		ACCESS read-only
                STATUS mandatory
                DESCRIPTION
                   "See description for monMatchDescr."
	::= { monitor 4 }

--
-- The Distributed Systems Group
--
-- This group provides object necessary for the monitoring and management
-- of distributed systems facilities like NIS, RPC, and NFS.  Since they
-- these services are available on a variety of operating systems
-- platforms, they are placed under the general Empire MIB rather than
-- its UNIX or platform branches.
--

	rpc OBJECT IDENTIFIER ::= { distribsys 1 }
	nfs OBJECT IDENTIFIER ::= { distribsys 2 }
	nis OBJECT IDENTIFIER ::= { distribsys 3 }

--
-- RPC stats and counters for both clients and servers
-- 
-- This group provides statistics and counters relating to the use of 
-- RPC facilities.  While it should be independent of which RPC 
-- protocol is used, most often it represents counters and statistics
-- for the usage of Sun RPC.  Statistics and counters are divided 
-- according to their applicability towards client and server side
-- protocol operations.  Please refer to the SunRPC specification 
-- (RFC 1057) for more information.
--

	clientRPCCalls OBJECT-TYPE
		SYNTAX Counter
		ACCESS read-only
		STATUS mandatory
		DESCRIPTION
		   "The total number of RPC calls sent by the RPC
		    client protocol software."
		::= { rpc 1 }

	clientRPCBadcalls OBJECT-TYPE
		SYNTAX Counter
		ACCESS read-only
		STATUS mandatory
		DESCRIPTION
		   "The total number of RPC calls rejected by the
		    RPC client protocol software."
		::= { rpc 2 }

	clientRPCRetrans OBJECT-TYPE
		SYNTAX Counter
		ACCESS read-only
		STATUS mandatory
		DESCRIPTION
		   "The total number of times an RPC call had to
		    be retransmitted due to a timeout while
		    waiting for an RPC server reply." 
		::= { rpc 3 }

	clientRPCBadxids OBJECT-TYPE
		SYNTAX Counter
		ACCESS read-only
		STATUS mandatory
		DESCRIPTION
		   "The total number of times a server RPC reply
		    was received for which no outstanding call
		    exists." 
		::= { rpc 4 }

	clientRPCTimeouts OBJECT-TYPE
		SYNTAX Counter
		ACCESS read-only
		STATUS mandatory
		DESCRIPTION
		   "The total number times an RPC call timed out
		    while waiting for a reply from the RPC
		    server." 
		::= { rpc 5 }

	clientRPCWaits OBJECT-TYPE
		SYNTAX Counter
		ACCESS read-only
		STATUS mandatory
		DESCRIPTION
		   "The total number of times an RPC call has to
		    wait because no client handle was available."
		::= { rpc 6 }

	clientRPCNewcreds OBJECT-TYPE
		SYNTAX Counter
		ACCESS read-only
		STATUS mandatory
		DESCRIPTION
		   "The total number of times authentication
		    information had to be refreshed."
		::= { rpc 7 }

	clientRPCTimers OBJECT-TYPE
		SYNTAX Counter
		ACCESS read-only
		STATUS mandatory
		DESCRIPTION
		   "The total number of times the calculated
		    time-out value was greater than or equal to
		    the minimum specified time-out value for an
		    RPC call." 
		::= { rpc 8 }

	serverRPCCalls OBJECT-TYPE
		SYNTAX Counter
		ACCESS read-only
		STATUS mandatory
		DESCRIPTION
		   "The total number of RPC calls received by the
		    RPC server protocol software."
		::= { rpc 9 }

	serverRPCBadcalls OBJECT-TYPE 
		SYNTAX Counter
		ACCESS read-only
		STATUS mandatory
		DESCRIPTION
		   "The total number of calls rejected by the RPC
		    server protocol softeware; it is equivalent
		    to the sum of the MIB objects serverRPCBadlen
		    and serverRPCxdrcall." 
		::= { rpc 10 }

	serverRPCNullrecvs OBJECT-TYPE
		SYNTAX Counter
		ACCESS read-only
		STATUS mandatory
		DESCRIPTION
		   "The number of RPC requests not available
		    when it was thought to be received."
		::= { rpc 11 }

	serverRPCBadlens OBJECT-TYPE
		SYNTAX Counter
		ACCESS read-only
		STATUS mandatory
		DESCRIPTION
		   "The number of RPC requests whose lengths were
		    shorter than the minimum size RPC message."
		::= { rpc 12 }

	serverRPCXdrcalls OBJECT-TYPE
		SYNTAX Counter
		ACCESS read-only
		STATUS mandatory
		DESCRIPTION
		   "The number of RPC requests whose header could
		    not be XDR decoded."
		::= { rpc 13 }

--
-- NFS stats and counters for both clients and servers
-- 
-- This group provides statistics and counters relating to the use of
-- the distributed file services utilizing the NFS protocol.
-- Statistics and counters are divided according to their
-- applicability towards client and server side protocol operations.
-- For more information, please refer to the NFS protocol
-- specification (RFC 1094).
--

	clientNFSCalls OBJECT-TYPE
		SYNTAX Counter
		ACCESS read-only
		STATUS mandatory
		DESCRIPTION
		   "The total number of NFS calls sent by the NFS
		    client protocol software."
		::= { nfs 1 }

	clientNFSBadcalls OBJECT-TYPE
		SYNTAX Counter
		ACCESS read-only
		STATUS mandatory
		DESCRIPTION
		   "The total number of times an NFS call was
		    rejected by the underlying client RPC
		    protocol software." 
		::= { nfs 2 }

	clientNFSNclgets OBJECT-TYPE
		SYNTAX Counter
		ACCESS read-only
		STATUS mandatory
		DESCRIPTION
		   "The total number of times a client NFS handle
		    was received by the NFS client protocol
		    software."
		::= { nfs 3 }

	clientNFSNclsleeps OBJECT-TYPE
		SYNTAX Counter
		ACCESS read-only
		STATUS mandatory
		DESCRIPTION
		   "The total number of times a client NFS call
		    had to sleep while waiting for a client NFS
		    handle." 
		::= { nfs 4 }

	clientNFSNulls OBJECT-TYPE
		SYNTAX Counter
		ACCESS read-only
		STATUS mandatory
		DESCRIPTION
		   "The total number of NFS 'NULL'
		    procedure calls sent by the client NFS protocol
		    software.  The 'NULL' procedure is often used
		    to allow server response testing and timing." 
		::= { nfs 5 }

	clientNFSGetattrs OBJECT-TYPE
		SYNTAX Counter
		ACCESS read-only
		STATUS mandatory
		DESCRIPTION
		   "The total number of NFS 'GetAttr'
		    procedure calls sent by the client NFS protocol
		    software.  This function is used to obtain
		    attributes for a given file." 
		::= { nfs 6 }

	clientNFSSetattrs OBJECT-TYPE
		SYNTAX Counter
		ACCESS read-only
		STATUS mandatory
		DESCRIPTION
		   "The total number of NFS 'SetAttr'
		    procedure calls sent by the client NFS
		    protocol software.  This function is used to
		    set a file's attributes." 
		::= { nfs 7 }

	clientNFSRoots OBJECT-TYPE
		SYNTAX Counter
		ACCESS read-only
		STATUS mandatory
		DESCRIPTION
		   "The total number of NFS 'Root' procedure
		    calls sent by the client NFS protocol
		    software.  This function has been declared
		    obsolete." 
		::= { nfs 8 }

	clientNFSLookups OBJECT-TYPE
		SYNTAX Counter
		ACCESS read-only
		STATUS mandatory
		DESCRIPTION
		   "The total number of NFS 'Lookup'
		    procedure calls sent by the client NFS
		    protocol software.  This function is used to
		    retrieve a file's attributes and handle." 
		::= { nfs 9 }

	clientNFSReadlinks OBJECT-TYPE
		SYNTAX Counter
		ACCESS read-only
		STATUS mandatory
		DESCRIPTION
		   "The total number of NFS 'Read link'
		    procedure calls sent by the client NFS
		    protocol software.  This function is used to
		    read from a symbolic link." 
		::= { nfs 10 }

	clientNFSReads OBJECT-TYPE
		SYNTAX Counter
		ACCESS read-only
		STATUS mandatory
		DESCRIPTION
		   "The total number of NFS 'Read'
		    procedure calls sent by the client NFS
		    protocol software.  This function is used to
		    read data (in units of bytes) from a give
		    file."
		::= { nfs 11 }

	clientNFSWrcaches OBJECT-TYPE
		SYNTAX Counter
		ACCESS read-only
		STATUS mandatory
		DESCRIPTION
		   "The total number of NFS 'Write Cache'
		    procedure calls sent by the client NFS
		    protocol software.   This function is to be
		    used in future versions of the NFS protocol."
		::= { nfs 12 }

	clientNFSWrites OBJECT-TYPE
		SYNTAX Counter
		ACCESS read-only
		STATUS mandatory
		DESCRIPTION
		   "The total number of NFS 'Write'
		    procedure calls sent by the client NFS
		    protocol software.  This function is used to
		    write data (in units of bytes) to a given file." 

		::= { nfs 13 }

	clientNFSCreates OBJECT-TYPE
		SYNTAX Counter
		ACCESS read-only
		STATUS mandatory
		DESCRIPTION
		   "The total number of NFS 'Create'
		    procedure calls sent by the client NFS
		    protocol software.  This function is used to
		    create a file in a given directory." 
		::= { nfs 14 }

	clientNFSRemoves OBJECT-TYPE
		SYNTAX Counter
		ACCESS read-only
		STATUS mandatory
		DESCRIPTION
		   "The total number of NFS 'Remove'
		    procedure calls sent by the client NFS
		    protocol software.  This function is used to
		    remove a file from a given directory." 
		::= { nfs 15 }

	clientNFSRenames OBJECT-TYPE
		SYNTAX Counter
		ACCESS read-only
		STATUS mandatory
		DESCRIPTION
		   "The total number of NFS 'Rename'
		    procedure calls sent by the client NFS
		    protocol software.  This function is used to
		    rename a given file." 
		::= { nfs 16 }

	clientNFSLinks OBJECT-TYPE
		SYNTAX Counter
		ACCESS read-only
		STATUS mandatory
		DESCRIPTION
		   "The total number of NFS 'Create Link'
		    procedure calls sent by the client NFS
		    protocol software.  This function is used to
		    create a link to a given file." 
		::= { nfs 17 }

	clientNFSSymlinks OBJECT-TYPE
		SYNTAX Counter
		ACCESS read-only
		STATUS mandatory
		DESCRIPTION
		   "The total number of NFS 'Create
		    Symbolic Link' procedure calls sent by the
		    client NFS protocol software.  This function
		    is used to create a symbolic link to a given
		    file."  
		::= { nfs 18 }

	clientNFSMkdirs OBJECT-TYPE
		SYNTAX Counter
		ACCESS read-only
		STATUS mandatory
		DESCRIPTION
		   "The total number of NFS 'mkdir'
		    procedure calls sent by the client NFS
		    protocol software.  This function is used to
		    create a directory within a given directory." 
		::= { nfs 19 }

	clientNFSRmdirs OBJECT-TYPE
		SYNTAX Counter
		ACCESS read-only
		STATUS mandatory
		DESCRIPTION
		   "The total number of NFS 'rmdir'
		    procedure calls sent by the client NFS
		    protocol software.  This function is used to
		    remove a given directory." 
		::= { nfs 20 }

	clientNFSReaddirs OBJECT-TYPE
		SYNTAX Counter
		ACCESS read-only
		STATUS mandatory
		DESCRIPTION
		   "The total number of NFS 'readdir'
		    procedure calls sent by the client NFS
		    protocol software.  This function is used to
		    read a variable number of directory entries
		    from the given directory."  
		::= { nfs 21 }

	clientNFSFsstats OBJECT-TYPE
		SYNTAX Counter
		ACCESS read-only
		STATUS mandatory
		DESCRIPTION
		   "The total number of NFS 'stat'
		    procedure calls sent by the client NFS
		    protocol software.  This function is used to
		    retrieve file system statistics." 
		::= { nfs 22 }

	serverNFSCalls OBJECT-TYPE
		SYNTAX Counter
		ACCESS read-only
		STATUS mandatory
		DESCRIPTION
		   "The total number of NFS calls received by the
		    NFS server protocol software."
		::= { nfs 23 }

	serverNFSBadcalls OBJECT-TYPE
		SYNTAX Counter
		ACCESS read-only
		STATUS mandatory
		DESCRIPTION
		   "The total number of times an NFS call was
		    rejected by the underlying server RPC
		    protocol software." 
		::= { nfs 24 }

	serverNFSNulls OBJECT-TYPE
		SYNTAX Counter
		ACCESS read-only
		STATUS mandatory
		DESCRIPTION
		   "The total number of NFS 'NULL'
		    procedure calls received by the server NFS protocol
		    software.  The 'NULL' procedure is often used
		    to allow server response testing and timing." 
		::= { nfs 25 }

	serverNFSGetattrs OBJECT-TYPE
		SYNTAX Counter
		ACCESS read-only
		STATUS mandatory
		DESCRIPTION
		   "The total number of NFS 'GetAttr'
		    procedure calls received by the server NFS protocol
		    software.  This function is used to obtain
		    attributes for a given file." 
		::= { nfs 26 }

	serverNFSSetattrs OBJECT-TYPE
		SYNTAX Counter
		ACCESS read-only
		STATUS mandatory
		DESCRIPTION
		   "The total number of NFS 'SetAttr'
		    procedure calls received by the server NFS
		    protocol software.  This function is used to
		    set a file's attributes." 
		::= { nfs 27 }

	serverNFSRoots OBJECT-TYPE
		SYNTAX Counter
		ACCESS read-only
		STATUS mandatory
		DESCRIPTION
		   "The total number of NFS 'Root' procedure
		    calls received by the server NFS protocol
		    software.  This function has been declared
		    obsolete." 
		::= { nfs 28 }

	serverNFSLookups OBJECT-TYPE
		SYNTAX Counter
		ACCESS read-only
		STATUS mandatory
		DESCRIPTION
		   "The total number of NFS 'Lookup'
		    procedure calls received by the server NFS
		    protocol software.  This function is used to
		    retrieve a file's attributes and handle." 
		::= { nfs 29 }

	serverNFSReadlinks OBJECT-TYPE
		SYNTAX Counter
		ACCESS read-only
		STATUS mandatory
		DESCRIPTION
		   "The total number of NFS 'Read link'
		    procedure calls received by the server NFS
		    protocol software.  This function is used to
		    read from a symbolic link." 
		::= { nfs 30 }

	serverNFSReads OBJECT-TYPE
		SYNTAX Counter
		ACCESS read-only
		STATUS mandatory
		DESCRIPTION
		   "The total number of NFS 'Read'
		    procedure calls received by the server NFS
		    protocol software.  This function is used to
		    read data (in units of bytes) from a give
		    file."
		::= { nfs 31 }

	serverNFSWrcaches OBJECT-TYPE
		SYNTAX Counter
		ACCESS read-only
		STATUS mandatory
		DESCRIPTION
		   "The total number of NFS 'Write Cache'
		    procedure calls received by the server NFS
		    protocol software.   This function is to be
		    used in future versions of the NFS protocol."
		::= { nfs 32 }

	serverNFSWrites OBJECT-TYPE
		SYNTAX Counter
		ACCESS read-only
		STATUS mandatory
		DESCRIPTION
		   "The total number of NFS 'Write'
		    procedure calls received by the server NFS
		    protocol software.  This function is used to
		    write data (in units of bytes) to a given file." 
		::= { nfs 33 }

	serverNFSCreates OBJECT-TYPE
		SYNTAX Counter
		ACCESS read-only
		STATUS mandatory
		DESCRIPTION
		   "The total number of NFS 'Create'
		    procedure calls received by the server NFS
		    protocol software.  This function is used to
		    create a file in a given directory." 
		::= { nfs 34 }

	serverNFSRemoves OBJECT-TYPE
		SYNTAX Counter
		ACCESS read-only
		STATUS mandatory
		DESCRIPTION
		   "The total number of NFS 'Remove'
		    procedure calls received by the server NFS
		    protocol software.  This function is used to
		    remove a file from a given directory." 
		::= { nfs 35 }

	serverNFSRenames OBJECT-TYPE
		SYNTAX Counter
		ACCESS read-only
		STATUS mandatory
		DESCRIPTION
		   "The total number of NFS 'Rename'
		    procedure calls received by the server NFS
		    protocol software.  This function is used to
		    rename a given file." 
		::= { nfs 36 }

	serverNFSLinks OBJECT-TYPE
		SYNTAX Counter
		ACCESS read-only
		STATUS mandatory
		DESCRIPTION
		   "The total number of NFS 'Create Link'
		    procedure calls received by the server NFS
		    protocol software.  This function is used to
		    create a link to a given file." 
		::= { nfs 37 }

	serverNFSSymlinks OBJECT-TYPE
		SYNTAX Counter
		ACCESS read-only
		STATUS mandatory
		DESCRIPTION
		   "The total number of NFS 'Create
		    Symbolic Link' procedure calls received by the
		    server NFS protocol software.  This function
		    is used to create a symbolic link to a given
		    file."  
		::= { nfs 38 }

	serverNFSMkdirs OBJECT-TYPE
		SYNTAX Counter
		ACCESS read-only
		STATUS mandatory
		DESCRIPTION
		   "The total number of NFS 'mkdir'
		    procedure calls received by the server NFS
		    protocol software.  This function is used to
		    create a directory within a given directory." 
		::= { nfs 39 }

	serverNFSRmdirs OBJECT-TYPE
		SYNTAX Counter
		ACCESS read-only
		STATUS mandatory
		DESCRIPTION
		   "The total number of NFS 'rmdir'
		    procedure calls received by the server NFS
		    protocol software.  This function is used to
		    remove a given directory." 
		::= { nfs 40 }

	serverNFSReaddirs OBJECT-TYPE
		SYNTAX Counter
		ACCESS read-only
		STATUS mandatory
		DESCRIPTION
		   "The total number of NFS 'readdir'
		    procedure calls received by the server NFS
		    protocol software.  This function is used to
		    read a variable number of directory entries
		    from the given directory."  
		::= { nfs 41 }

	serverNFSFsstats OBJECT-TYPE
		SYNTAX Counter
		ACCESS read-only
		STATUS mandatory
		DESCRIPTION
		   "The total number of NFS 'stat'
		    procedure calls received by the server NFS
		    protocol software.  This function is used to
		    retrieve file system statistics." 
		::= { nfs 42 }

--
-- NIS Group
--
-- This group contains statistics, counters, and paramters important
-- in the management and configuration of the Network Information
-- Service (formerly known as Yellow Pages)
-- 


-- 
-- Concord/Empire History Group
-- 
-- This group defines 'rmon-like' history control and history tables 
-- that enable the agent to track the value of an object over time.
-- Like the RMON MIB, the agent reserves buckets for each distinct
-- sampling or history control entry
-- 

	empireHistoryCtrlTable OBJECT-TYPE
		SYNTAX SEQUENCE OF EmpireHistoryCtrlEntry
		ACCESS not-accessible
		STATUS mandatory
		DESCRIPTION
		   "Table describing/controlling the object history
		    collection.  Adding rows to this table causes
		    the agent to track the history of additional objects;
		    deleting rows from the table causes the agent
		    to cease tracking the value of an object.  Row
		    creation follows the V2 SMI RowStatus textual
		    convention (See RFC 1443).  Further, the table
		    is similar to the RMON HistoryControlTable in
		    purpose (See RFC 1271)."
		::= { empireHistory 1 }

	empireHistoryCtrlEntry OBJECT-TYPE
		SYNTAX EmpireHistoryCtrlEntry
		ACCESS not-accessible
		STATUS mandatory
		DESCRIPTION
		   "A list of parameters that set up a periodic 
		    sampling of a single object value contained within
		    the agent's internal MIB."
		INDEX { empireHistoryCtrlIndex } 
		::= { empireHistoryCtrlTable 1 }

	EmpireHistoryCtrlEntry ::= SEQUENCE {
	  	empireHistoryCtrlIndex 
			INTEGER,
	  	empireHistoryCtrlDescr
			DisplayString,
	  	empireHistoryCtrlInterval
			INTEGER,
	  	empireHistoryCtrlObjID
			OBJECT IDENTIFIER,
	  	empireHistoryCtrlObjType
			INTEGER,
	  	empireHistoryCtrlBucketsReq
			INTEGER,
	  	empireHistoryCtrlBucketsGrant
			INTEGER,
	  	empireHistoryCtrlLastCall
			TimeTicks,
	  	empireHistoryCtrlCreateTime
			TimeTicks,
	  	empireHistoryCtrlStatus
			INTEGER
        }

  	empireHistoryCtrlIndex OBJECT-TYPE
		SYNTAX INTEGER (1..2147483647)
		ACCESS read-only
		STATUS mandatory
		DESCRIPTION
		   "An index that uniquely identifies an entry in the
		    empireHistoryCtrlTable.  Each such entry defines
		    a periodic sampling/history that the agent
		    performs.  The sample values can be obtained
		    from the empireHistoryTable."
	::= { empireHistoryCtrlEntry 1 } 

  	empireHistoryCtrlDescr OBJECT-TYPE
		SYNTAX DisplayString (SIZE (0..128))
		ACCESS read-write
		STATUS mandatory
		DESCRIPTION
		   "A textual description of this entry possibly 
	 	    identifying the purpose of this entry and who
		    created it."
	::= { empireHistoryCtrlEntry 2 } 

  	empireHistoryCtrlInterval OBJECT-TYPE
		SYNTAX INTEGER
		ACCESS read-write
		STATUS mandatory
		DESCRIPTION
                   "The interval in seconds between successive
                    samples.  The sample interval must be a
                    multiple of 30 seconds."
	::= { empireHistoryCtrlEntry 3 } 

  	empireHistoryCtrlObjID OBJECT-TYPE
		SYNTAX OBJECT IDENTIFIER
		ACCESS read-write
		STATUS mandatory
		DESCRIPTION
		   "The object identifier of the particular object to
		    be sampled.  This object identifier must refer to 
		    a valid object and be of base type INTEGER.  For
                    example, objects of type Counter, INTEGER, and
  		    Gauge can be sampled, but objects of type
                    DisplayString cannot."
	::= { empireHistoryCtrlEntry 4 } 

  	empireHistoryCtrlObjType OBJECT-TYPE
		SYNTAX INTEGER
		ACCESS read-only
		STATUS mandatory
		DESCRIPTION
		   "The ASN1/SNMP tag value of the object being
                    sampled.  For example, an SNMP Gauge would be 0x42
                    or 66 decimal." 
	::= { empireHistoryCtrlEntry 5 } 

  	empireHistoryCtrlBucketsReq OBJECT-TYPE
		SYNTAX INTEGER
		ACCESS read-write
		STATUS mandatory
		DESCRIPTION
		   "The requested number of discrete samples
		    of data to be saved in the empireHistoryTable.
                    When this object is created or modified, the agent
                    sets the empireHistoryCtrlBucketsGrant as close as
                    possible." 
	::= { empireHistoryCtrlEntry 6 } 

 	empireHistoryCtrlBucketsGrant OBJECT-TYPE
		SYNTAX INTEGER
		ACCESS read-only
		STATUS mandatory
		DESCRIPTION
		   "The number of number of discrete samples of data
		    which shall be saved in the empireHistoryCtrlTable."
	::= { empireHistoryCtrlEntry 7 } 

  	empireHistoryCtrlLastCall OBJECT-TYPE
		SYNTAX TimeTicks
		ACCESS read-only
		STATUS mandatory
		DESCRIPTION
		   "The value of sysUpTime when this entry was last
                    evaluated by the agent."
	::= { empireHistoryCtrlEntry 8 } 

  	empireHistoryCtrlCreateTime OBJECT-TYPE
		SYNTAX TimeTicks
		ACCESS read-only
		STATUS mandatory
		DESCRIPTION
		   "The value of sysUpTime when this entry was created
                    by the agent." 
	::= { empireHistoryCtrlEntry 9 } 

  	empireHistoryCtrlStatus OBJECT-TYPE
		SYNTAX INTEGER {
		   active(1),
		   notInService(2),
		   notReady(3),
		   createAndGo(4),
		   createAndWait(5),
		   destroy(6)
                }
		ACCESS read-write
		STATUS mandatory
		DESCRIPTION
		   "The status of this entry.  This variable is
		    equivalent in semantics to the V2 SMI
		    RowStatus textual-convention (see RFC 1443).
		    A value of active(1) indicates that the agent
		    is currently monitoring and evaluating the
		    current row.  A Value of notInService(2)
		    indicates that the agent has suspended
		    evaluation of the row.  Setting this object
		    to destroy(6) causes the agent to suspend
		    evaluation of its row and free its resources.
		    For row creation to occur, the manager must
		    supply active(1), createAndGo(4),
		    createAndWait(5), or notInService(2) as the
		    value of this object.  
		    If an error occurs at any time during the
		    processing of a particular table entry, its
		    Status column will be set to notReady(3)."
                DEFVAL { createAndWait } 
	::= { empireHistoryCtrlEntry 10 } 

	empireHistoryTable OBJECT-TYPE
		SYNTAX SEQUENCE OF EmpireHistoryEntry
		ACCESS not-accessible
		STATUS mandatory
		DESCRIPTION
                   "Table containing the history samples corresponding
		    to history control entries contained in the 
		    empireHistoryCtrlTable.  For each entry in the
		    control table, a set of history samples will
		    exist in this table.  Managers can index
                    a particular sample by combining the corresponding
                    index from the control table with a sample number."
        ::= { empireHistory 2 }

        empireHistoryEntry OBJECT-TYPE
		SYNTAX EmpireHistoryEntry
		ACCESS not-accessible
		STATUS mandatory
		DESCRIPTION
		    "A historical sample of an object in the agent's
                     MIB.  Each sample is associated with an entry
                     in the empireHistoryCtrlTable which set up the
                     parameters for a regular collection of these
		     samples."
		INDEX { empireHistoryIndex, empireHistorySampleIndex }
	::= { empireHistoryTable 1 }

	EmpireHistoryEntry ::= SEQUENCE {
		empireHistoryIndex
			INTEGER,
		empireHistorySampleIndex
			INTEGER,
		empireHistoryStartTime
			TimeTicks,
		empireHistorySampleTime
			TimeTicks,
		empireHistoryValue
			INTEGER
        }

	empireHistoryIndex OBJECT-TYPE
		SYNTAX INTEGER
		ACCESS read-only
		STATUS mandatory
		DESCRIPTION
		   "The history of which this entry is a part.  This
		    value identifies a row in the
                    empireHistoryCtrlTable of which this sample is a
		    part."
	::= { empireHistoryEntry 1 } 

	empireHistorySampleIndex OBJECT-TYPE
		SYNTAX INTEGER
		ACCESS read-only
		STATUS mandatory
		DESCRIPTION
		   "An index that uniquely identifies the particular
 		    sample this entry represents among all samples
		    associated with the same history control entry.
		    This index starts at 1 and increases by one as
		    each new sample is taken." 
	::= { empireHistoryEntry 2 } 

	empireHistoryStartTime OBJECT-TYPE
		SYNTAX TimeTicks
		ACCESS read-only
		STATUS mandatory
		DESCRIPTION
		   "The value of sysUpTime at which the first sample
                    was taken." 
	::= { empireHistoryEntry 3 } 

	empireHistorySampleTime OBJECT-TYPE
		SYNTAX TimeTicks
		ACCESS read-only
		STATUS mandatory
		DESCRIPTION
		   "The value of sysUpTime at which this particular
                    sample was taken." 
	::= { empireHistoryEntry 4 } 

	empireHistoryValue OBJECT-TYPE
		SYNTAX INTEGER
		ACCESS read-only
		STATUS mandatory
		DESCRIPTION
		   "The value of this sample."
	::= { empireHistoryEntry 5 } 

        histCtrlUnusedIndex OBJECT-TYPE
		SYNTAX INTEGER (1..2147483647)
		ACCESS read-only
                STATUS mandatory
                DESCRIPTION
                   "An SNMP Get of this MIB object returns an un-used
                    history control index number.  It can be used
                    for history control table row creation optimization."
	::= { empireHistory 3 }

        histCtrlMatchDescr OBJECT-TYPE
		SYNTAX DisplayString
		ACCESS read-write
                STATUS mandatory
                DESCRIPTION
                   "This MIB object, when used in conjunction with
                    histCtrlMatchIndex can be used to quickly determine
                    the index number corresponding to a particular entry
		    description.  SNMP Set'ing a description to this MIB
		    object causes the agent to search through entries in
		    the history control table and place the
                    index value of the last entry whose description
                    matches, in the histCtrlMatchIndex MIB object."
	::= { empireHistory 4 }

        histCtrlMatchIndex OBJECT-TYPE
		SYNTAX INTEGER (1..2147483647)
		ACCESS read-only
                STATUS mandatory
                DESCRIPTION
                   "See description for histCtrlMatchDescr."
	::= { empireHistory 5 }


-- 
-- Concord/Empire Log monitoring group
-- 
-- This group provides access to the agent's logfile monitoring
-- capabilities.  Via the logMonitorTable, managers can specify 
-- that the agent monitor certain log files for certain patterns
-- or regular expressions.  When a match has occurred, the agent
-- sends a Trap to appropriate managers.  Entries can be placed
-- in the logMonitorTable via two methods: through entries in the
-- agent configuration file (snmpd.empire.conf) or via the SNMP.
-- Note: only entries placed in the agent configuration file 
-- will exist the next time the agent is started.  Entries placed
-- in the table via SNMP will not exist the next time the agent
-- is started.

	logMonitorTable OBJECT-TYPE
		SYNTAX SEQUENCE OF LogMonitorEntry
		ACCESS not-accessible
		STATUS mandatory
		DESCRIPTION
                   "Table containing log monitor entries; each entry 
                    specifies a log file and regular expression.
	            The agent periodically stats the log files to 
                    see if they have been updated.  If updated, the
                    agent scans the new entries for the regular
                    expression.  When that regular expression is found
                    (or matched) in the new entries, a trap PDU is
                    sent to appropriate managers."
        ::= { logMonitor 1 }

        logMonitorEntry OBJECT-TYPE
		SYNTAX LogMonitorEntry
		ACCESS not-accessible
		STATUS mandatory
		DESCRIPTION
                   "An entry in the logMonitorTable."
		INDEX { logMonitorIndex }
	::= { logMonitorTable 1 }

	LogMonitorEntry ::= SEQUENCE {
		logMonitorIndex
			INTEGER,
		logMonitorLogFile
			DisplayString,
		logMonitorRegularExpression
			DisplayString,
		logMonitorNumberTraps
			INTEGER,
		logMonitorLastTrap
			TimeTicks,
		logMonitorLastMatch
			DisplayString,
		logMonitorStatus
			INTEGER,
                logMonitorLogFileSize
			INTEGER,
		logMonitorLogFileLastUpdate
			TimeTicks,
		logMonitorDescr
			DisplayString,
		logMonitorAction
			DisplayString,
                logMonitorFlags
			INTEGER,
		logMonitorMatches
			Counter
        }

	logMonitorIndex OBJECT-TYPE
		SYNTAX INTEGER (1..2147483647)
		ACCESS read-only
		STATUS mandatory
		DESCRIPTION
                   "An index that uniquely identifies an entry in the
                    logMonitorTable."
	::= { logMonitorEntry 1 } 

	logMonitorLogFile OBJECT-TYPE
		SYNTAX DisplayString (SIZE (0..256))
		ACCESS read-write
		STATUS mandatory
		DESCRIPTION
                   "The name of the log file to scan for pattern
                    matches.  This variable must name a valid log
                    filename."
	::= { logMonitorEntry 2 } 

	logMonitorRegularExpression OBJECT-TYPE
		SYNTAX DisplayString (SIZE (0..64))
		ACCESS read-write
		STATUS mandatory
		DESCRIPTION
                   "The display string representation of the regular
                    expression to match in the corresponding log file.
                    Valid regular expressions are those as defined in
                    ed(1)."
	::= { logMonitorEntry 3 } 

	logMonitorNumberTraps OBJECT-TYPE
		SYNTAX INTEGER
		ACCESS read-only
		STATUS mandatory
		DESCRIPTION
                   "The number of traps sent by the agent on behalf of
                    this entry.  One trap PDU message is sent for each
                    match the agent detects in the corresponding log
                    file (if Traps have not been disabled for this
		    entry)."  
	::= { logMonitorEntry 4 } 

	logMonitorLastTrap OBJECT-TYPE
		SYNTAX TimeTicks
		ACCESS read-only
		STATUS mandatory
		DESCRIPTION
                    "The time (based on sysUpTime) at which the agent
                     last sent a trap for this entry.  Alternatively,
                     it is the time at which the last pattern match
                     occurred." 
	::= { logMonitorEntry 5 } 

	logMonitorLastMatch OBJECT-TYPE
--		SYNTAX DisplayString (SIZE (0..128))
--		Starting with 4.1, we bump this size to 256
		SYNTAX DisplayString (SIZE (0..256))
		ACCESS read-only
		STATUS mandatory
		DESCRIPTION
                   "The last log file entry that matched the
                    logMonitorRegularExpression.  Each time a match
                    occurs, this variable is updated."
	::= { logMonitorEntry 6 } 

	logMonitorStatus OBJECT-TYPE
		SYNTAX INTEGER {
		   active(1),
		   notInService(2),
		   notReady(3),
		   createAndGo(4),
		   createAndWait(5),
		   destroy(6)
                }
		ACCESS read-write
		STATUS mandatory
		DESCRIPTION
		   "The status of this entry.  This variable is
		    equivalent in semantics to the V2 SMI
		    RowStatus textual-convention (see RFC 1443).
		    A value of active(1) indicates that the agent
		    is currently monitoring and evaluating the
		    current row.  A Value of notInService(2)
		    indicates that the agent has suspended
		    evaluation of the row.  Setting this object
		    to destroy(2) causes the agent to suspend
		    evaluation of its row and free its resources.
		    For row creation to occur, the manager must
		    supply active(1), createAndGo(4),
		    createAndWait(5), or notInService(2) as the
		    value of this object.  
		    If an error occurs at any time during the
		    processing of a particular logMonitor Table entry,
                    its Status column will be set to notReady(3)."
                DEFVAL { createAndWait } 
	::= { logMonitorEntry 7 } 

	logMonitorLogFileSize OBJECT-TYPE
		SYNTAX INTEGER
		ACCESS read-only
		STATUS mandatory
		DESCRIPTION
                   "The size in bytes of the log file at time of last
                    sample.  By querying this value, one can tell if
                    the log file is growing."
	::= { logMonitorEntry 8 } 

	logMonitorLogFileLastUpdate OBJECT-TYPE
		SYNTAX TimeTicks
		ACCESS read-only
		STATUS mandatory
		DESCRIPTION
                   "The time (based on sysUpTime) that the log file
                    was last modifed by the system or application(s)
                    writing to this file.  Monitoring this value can
                    indicate if the system or application(s) that log
                    to this file are active." 
	::= { logMonitorEntry 9 } 

	logMonitorDescr OBJECT-TYPE
		SYNTAX DisplayString (SIZE (0..128))
		ACCESS read-write
		STATUS mandatory
		DESCRIPTION
		   "A textual description of this entry possibly 
	 	    identifying the purpose of this entry and who
		    created it."
	::= { logMonitorEntry 10 }

	logMonitorAction OBJECT-TYPE
		SYNTAX DisplayString (SIZE (0..256))
		ACCESS read-write
		STATUS mandatory
		DESCRIPTION
		   "A textual string specifying the command to be
		    executed upon finding a match."
	::= { logMonitorEntry 11 }

	logMonitorFlags OBJECT-TYPE
		SYNTAX INTEGER
		ACCESS read-write
		STATUS mandatory
		DESCRIPTION
                    "The flags field dictates the behavior of each
                     logMonitorEntry.  Each bit in the integer
                     represents the toggling of an option.  The flags
                     field of 0x00 is enables default behavior.
                     Logical or'ing together of different bits allows
                     one to combine different options.

               Hex   Function                  Default (if not enabled)

               0x01  Do not execute actions    Execute actions
               0x02  Do not send Traps         Send Traps   
               0x04  Do not re-initialize      Re-initialize
               0x08  Do not log events         Log events
               0x10  Send cont notReady Traps  Send single notReady Trap

              0x100  Apply logical NOT oper    No additional operator"

	::= { logMonitorEntry 12 } 

	logMonitorMatches OBJECT-TYPE
		SYNTAX Counter
		ACCESS read-only
		STATUS mandatory
		DESCRIPTION
                    "The number of logfile entries matching the
		     regular expression; this value is incremented
  		     regardless of whether Traps are sent for this
		     entry or not.  Polling this variable allows you
		     to determine the rate or number of matches over
		     time."
	::= { logMonitorEntry 13 } 

        logmonUnusedIndex OBJECT-TYPE
		SYNTAX INTEGER (1..2147483647)
		ACCESS read-only
                STATUS mandatory
                DESCRIPTION
                   "An SNMP Get of this MIB object returns an un-used
                    logfile monitor index number.  It can be used
                    for logfile monitor table row creation optimization."
	::= { logMonitor 2 }

        logmonMatchDescr OBJECT-TYPE
		SYNTAX DisplayString
		ACCESS read-write
                STATUS mandatory
                DESCRIPTION
                   "This MIB object, when used in conjunction with
                    logmonMatchIndex can be used to quickly determine
                    the index number corresponding to a particular entry
		    description.  SNMP Set'ing a description to this MIB
		    object causes the agent to search through entries in
		    the logfile monitor table and place the
                    index value of the last entry whose description
                    matches, in the logmonMatchIndex MIB object."
	::= { logMonitor 3 }

        logmonMatchIndex OBJECT-TYPE
		SYNTAX INTEGER (1..2147483647)
		ACCESS read-only
                STATUS mandatory
                DESCRIPTION
                   "See description for logmonMatchDescr."
	::= { logMonitor 4 }


---
--- Concord/Empire Disk I/O Group
---
--- Includes table of disk I/O statistics.
---
	diskStatsTable OBJECT-TYPE
		SYNTAX SEQUENCE OF DiskStatsEntry
		ACCESS not-accessible
		STATUS mandatory
		DESCRIPTION
                   "Table containing disk I/O stat entries; each entry 
                    provides the latest disk statistics for one disk.
	            The agent periodically stats the system data structures
                    for each disk and records the values in the table."
        ::= { diskGroup 1 }

        diskStatsEntry OBJECT-TYPE
		SYNTAX DiskStatsEntry
		ACCESS not-accessible
		STATUS mandatory
		DESCRIPTION
                   "An entry in the diskStatsTable."
		INDEX { diskStatsIndex }
	::= { diskStatsTable 1 }

	DiskStatsEntry ::= SEQUENCE {
		diskStatsIndex
			INTEGER,
		diskStatsQueueLength
			Gauge,
		diskStatsServiceTime
			Gauge,
		diskStatsUtilization
			INTEGER,
		diskStatsKBytesTransferred
			Counter,
		diskStatsTransfers
			Counter,
		diskStatsReads
			Counter,
		diskStatsWrites
			Counter,
		diskStatsHostmibDevTableIndex
			INTEGER,
		diskStatsLastUpdate
			TimeTicks,
                diskStatsKBytesXferStr
                        DisplayString,
                diskStatsTransfersStr
                        DisplayString,
                diskStatsReadsStr
                        DisplayString,
                diskStatsWritesStr
                        DisplayString,
                diskStatsKBytesXferHi
			Counter,
                diskStatsXferOpsHi
			Counter,
                diskStatsReadsHi
			Counter,
                diskStatsWritesHi
			Counter
        }

	diskStatsIndex OBJECT-TYPE
		SYNTAX INTEGER (1..2147483647)
		ACCESS read-only
		STATUS mandatory
		DESCRIPTION
                   "An index that uniquely identifies an entry in the
                    diskStatsTable."
	::= { diskStatsEntry 1 } 

	diskStatsQueueLength OBJECT-TYPE
		SYNTAX Gauge
		ACCESS read-only
		STATUS mandatory
		DESCRIPTION
                   "The average number of operations waiting in the disk's
                    service queue over the last measurement period."
	::= { diskStatsEntry 2 } 

	diskStatsServiceTime OBJECT-TYPE
		SYNTAX Gauge
		ACCESS read-only
		STATUS mandatory
		DESCRIPTION
                   "The average service time in milliseconds for operations
                    served on this disk over the last measurement period.
		    This could be expressed as:
		    disk-busy-time / number-of-transfers."
	::= { diskStatsEntry 3 } 

	diskStatsUtilization OBJECT-TYPE
		SYNTAX INTEGER (0..100)
		ACCESS read-only
		STATUS mandatory
		DESCRIPTION
                   "The utilization rate (percentage utilization) for
                    this disk over the last measurement period.
                    This could also be expressed as:
                    (disk-busy-time / elapsed-time) * 100."
	::= { diskStatsEntry 4 } 

	diskStatsKBytesTransferred OBJECT-TYPE
		SYNTAX Counter
		ACCESS read-only
		STATUS mandatory
		DESCRIPTION
                   "The number of KBytes transferred to/from this disk."
	::= { diskStatsEntry 5 } 

	diskStatsTransfers OBJECT-TYPE
		SYNTAX Counter
		ACCESS read-only
		STATUS mandatory
		DESCRIPTION
                   "The number of transfer operations to/from this disk."
	::= { diskStatsEntry 6 } 

	diskStatsReads OBJECT-TYPE
		SYNTAX Counter
		ACCESS read-only
		STATUS mandatory
		DESCRIPTION
                   "The number of read operations from this disk."
	::= { diskStatsEntry 7 } 

	diskStatsWrites OBJECT-TYPE
		SYNTAX Counter
		ACCESS read-only
		STATUS mandatory
		DESCRIPTION
                   "The number of write operations to this disk."
	::= { diskStatsEntry 8 } 

	diskStatsHostmibDevTableIndex OBJECT-TYPE
		SYNTAX INTEGER (1..2147483647)
		ACCESS read-only
		STATUS mandatory
		DESCRIPTION
                   "The index of this disk device in the device table 
                    of the Host Resources MIB."
	::= { diskStatsEntry 9 } 

	diskStatsLastUpdate OBJECT-TYPE
		SYNTAX TimeTicks
		ACCESS read-only
		STATUS mandatory
		DESCRIPTION
                   "The time in SNMP Time Ticks of the last update of
                    this diskStatsTable entry."
	::= { diskStatsEntry 10 } 

        -- support for 64-bit counters, new in 4.1pl3
        -- (via high/low values and string representations)
        -- we do this to squeeze these into an SNMPv1 engine w/o
        -- 64-bit counters and to preserve existing MIB object
        -- semantics

        diskStatsKBytesXferStr OBJECT-TYPE
                SYNTAX DisplayString
		ACCESS read-only
		STATUS mandatory
		DESCRIPTION
                   "Number of KBbytes transfered to/from this disk in
                    ascii string format so that 64-bit values can be
                    passed w/o having to go through high/low order
                    word calculations."
	::= { diskStatsEntry 11 } 

        diskStatsTransfersStr OBJECT-TYPE
                SYNTAX DisplayString
		ACCESS read-only
		STATUS mandatory
		DESCRIPTION
                   "Number of transfer operations to/from this disk in
                    ascii string format so that 64-bit values can be
                    passed w/o having to go through high/low order
                    word calculations."
	::= { diskStatsEntry 12 } 

        diskStatsReadsStr OBJECT-TYPE
                SYNTAX DisplayString
		ACCESS read-only
		STATUS mandatory
		DESCRIPTION
                   "The number of read operations from this disk in
                    ascii string format so that 64-bit values can be
                    passed w/o having to go through high/low order word
                    calculations. "
	::= { diskStatsEntry 13 } 

        diskStatsWritesStr OBJECT-TYPE
                SYNTAX DisplayString
		ACCESS read-only
		STATUS mandatory
		DESCRIPTION
                   "The number of write operations to this disk in
                    ascii string format so that 64-bit values can be
                    passed w/o having to go through high/low order word
                    calculations."
	::= { diskStatsEntry 14 } 

         diskStatsKBytesXferHi OBJECT-TYPE
                 SYNTAX Counter
                 ACCESS read-only
                 STATUS mandatory
                 DESCRIPTION
                    "High-order 32-bits of diskStatsKBytesTransferred if the
                     underlying system supports 64-bit disk stats; zero
                     otherwise.  Recovering the 64-bit counter is as
                     simple as:
                     diskStatsKBytesXferHi << 32 | diskStatsKBytesTransferred"
         ::= { diskStatsEntry 15 }

         diskStatsXferOpsHi OBJECT-TYPE
                 SYNTAX Counter
                 ACCESS read-only
                 STATUS mandatory
                 DESCRIPTION
                    "High-order 32-bits of diskStatsTransfers if the
                     underlying system supports 64-bit disk stats; zero
                     otherwise.  Recovering the 64-bit counter is as
                     simple as: diskStatsXferOpsHi << 32 | diskStatsTransfers"
         ::= { diskStatsEntry 16 }

         diskStatsReadsHi OBJECT-TYPE
                 SYNTAX Counter
                 ACCESS read-only
                 STATUS mandatory
                 DESCRIPTION
                    "High-order 32-bits of diskStatsReads if the
                     underlying system supports 64-bit disk stats; zero
                     otherwise.  Recovering the 64-bit counter is as
                     simple as: diskStatsReadsHi << 32 | diskStatsReads"
         ::= { diskStatsEntry 17 }

         diskStatsWritesHi OBJECT-TYPE
                 SYNTAX Counter
                 ACCESS read-only
                 STATUS mandatory
                 DESCRIPTION
                    "High-order 32-bits of diskStatsWrites if the
                     underlying system supports 64-bit disk stats; zero
                     otherwise.  Recovering the 64-bit counter is as
                     simple as: diskStatsWritesHi << 32 | diskStatsWrites"
         ::= { diskStatsEntry 18 }

---
--- Concord/Empire CPU Group
---
--- Includes per-CPU statistics
---
        cpuStatsTable OBJECT-TYPE
		SYNTAX SEQUENCE OF CpuStatsEntry
		ACCESS not-accessible
		STATUS mandatory
		DESCRIPTION
		   "This table provides per-cpu statistics and
                    counters; the agent periodically (approximately
                    every 60 seconds) updates data contained in
                    this table.  By periodically sampling entries in
                    this table, one can determine the percentage of
                    time spent by each CPU in their respective modes.
                    This percentage can be calculated by summing the
                    total 'ticks' spent in each mode and then dividing
                    the 'ticks' spent in each mode by the total.
                    'Ticks' is a system-dependent quantity whose unit
                    is not necessary when calculating the percentage
                    of time spent in each CPU mode."
	::= { cpuGroup 1 }

        cpuStatsEntry OBJECT-TYPE
		SYNTAX CpuStatsEntry
		ACCESS not-accessible
		STATUS mandatory
		DESCRIPTION
                   "An entry in the cpuStatsTable"
		INDEX { cpuStatsIndex }
	::= { cpuStatsTable 1 }

	CpuStatsEntry ::= SEQUENCE {
		cpuStatsIndex
			INTEGER,
		cpuStatsDescr
			DisplayString,
		cpuStatsIdle
			Counter,
		cpuStatsUser
			Counter,
		cpuStatsSys
			Counter,
		cpuStatsWait
			Counter,
		cpuStatsLastUpdate
			TimeTicks,
		cpuStatsIdlePercent
			INTEGER,
		cpuStatsUserPercent
			INTEGER,
		cpuStatsSysPercent
			INTEGER,
		cpuStatsWaitPercent
			INTEGER
        }

        cpuStatsIndex OBJECT-TYPE
		SYNTAX INTEGER (1..2147483647)
		ACCESS read-only
		STATUS mandatory
		DESCRIPTION
		   "An index that uniquely identifies an entry in the
                    cpuStatsTable."
	::= { cpuStatsEntry 1 }

        cpuStatsDescr OBJECT-TYPE
		SYNTAX DisplayString (SIZE (0..64))
		ACCESS read-only
		STATUS mandatory
		DESCRIPTION
		   "The type of CPU for which statistics are reported.
                    On Solaris 2.x, this description also includes the
                    CPU's clock speed."
	::= { cpuStatsEntry 2 }

        cpuStatsIdle OBJECT-TYPE
		SYNTAX Counter
		ACCESS read-only
		STATUS mandatory
		DESCRIPTION
		   "The total number of 'ticks' spent by this CPU in
                    Idle mode.  This variable is not supported by NT.
                    This value may wrap 32-bit counter."
	::= { cpuStatsEntry 3 }

        cpuStatsUser OBJECT-TYPE
		SYNTAX Counter
		ACCESS read-only
		STATUS mandatory
		DESCRIPTION
		   "The total number of 'ticks' spent by this CPU in
                    User mode.  This value may wrap 32-bit counter."
	::= { cpuStatsEntry 4 }

        cpuStatsSys OBJECT-TYPE
		SYNTAX Counter
		ACCESS read-only
		STATUS mandatory
		DESCRIPTION
		   "The total number of 'ticks' spent by this CPU in
                    Kernel or system mode.  This value may wrap a
                    32-bit counter."
	::= { cpuStatsEntry 5 }

        cpuStatsWait OBJECT-TYPE
		SYNTAX Counter
		ACCESS read-only
		STATUS mandatory
		DESCRIPTION
		   "The total number of 'ticks' spent by this CPU in
                    Wait mode.  Wait mode is that time spent waiting
                    on I/O or swap.  It may wrap a 32-bit
                    counter." 
	::= { cpuStatsEntry 6 }

        cpuStatsLastUpdate OBJECT-TYPE
		SYNTAX TimeTicks
		ACCESS read-only
		STATUS mandatory
		DESCRIPTION
		   "The time (based on sysUpTime) that the counters
                    for this CPU were last updated.  Because these
                    values are cached periodically by the agent, the
                    time of last update is important for determining
                    the interval over which CPU mode percentages are
                    calculated."  
	::= { cpuStatsEntry 7 }

        cpuStatsIdlePercent OBJECT-TYPE
		SYNTAX INTEGER (0..100)
		ACCESS read-only
		STATUS mandatory
		DESCRIPTION
		   "The percentage of time (over the sample
		    period) that the system's CPU was idle."
	::= { cpuStatsEntry 8 }

        cpuStatsUserPercent OBJECT-TYPE
		SYNTAX INTEGER (0..100)
		ACCESS read-only
		STATUS mandatory
		DESCRIPTION
		   "The percentage of time (over the sample
		    period) that the system's CPU was executing in
                    user mode."
	::= { cpuStatsEntry 9 }

        cpuStatsSysPercent OBJECT-TYPE
		SYNTAX INTEGER (0..100)
		ACCESS read-only
		STATUS mandatory
		DESCRIPTION
		   "The percentage of time (over the sample
		    period) that the system's CPU was executing
		    the kernel or operating system."
	::= { cpuStatsEntry 10 }

        cpuStatsWaitPercent OBJECT-TYPE
		SYNTAX INTEGER (0..100)
		ACCESS read-only
		STATUS mandatory
		DESCRIPTION
		   "The percentage of time (over the sample
		    period) that the system's CPU was waiting for
		    I/O.  This object may not be supported by the
                    underlying operating system."
	::= { cpuStatsEntry 11 }

---
--- CPU Totals
--- 
        cpuTotalIdle OBJECT-TYPE
		SYNTAX Counter
		ACCESS read-only
		STATUS mandatory
		DESCRIPTION
		   "The total number of 'ticks' spent by all CPUs in
                    Idle mode.  This variable is not supported by NT.
                    This value may wrap 32-bit counter."
	::= { cpuGroup 2 }

        cpuTotalUser OBJECT-TYPE
		SYNTAX Counter
		ACCESS read-only
		STATUS mandatory
		DESCRIPTION
		   "The total number of 'ticks' spent by all CPUs in
                    User mode.  This value may wrap 32-bit counter."
	::= { cpuGroup 3 }

        cpuTotalSys OBJECT-TYPE
		SYNTAX Counter
		ACCESS read-only
		STATUS mandatory
		DESCRIPTION
		   "The total number of 'ticks' spent by all CPUs in
                    Kernel or system mode.  This value may wrap a
                    32-bit counter."
	::= { cpuGroup 4 }

        cpuTotalWait OBJECT-TYPE
		SYNTAX Counter
		ACCESS read-only
		STATUS mandatory
		DESCRIPTION
		   "The total number of 'ticks' spent by all CPUs in
                    Wait mode.  Wait mode is that time spent waiting
                    on I/O or swap.  It may wrap a 32-bit counter." 
	::= { cpuGroup 5 }

        cpuTotalLastUpdate OBJECT-TYPE
		SYNTAX TimeTicks
		ACCESS read-only
		STATUS mandatory
		DESCRIPTION
		   "The time (based on sysUpTime) that these counters
                    were last updated.  Because these values are cached 
                    periodically by the agent, the time of last update 
                    is important for determining the interval over which 
                    CPU mode percentages are calculated."  
	::= { cpuGroup 6 }

        cpuTotalIdlePercent OBJECT-TYPE
		SYNTAX INTEGER (0..100)
		ACCESS read-only
		STATUS mandatory
		DESCRIPTION
		   "The percentage of time (over the sample
		    period) that the system's CPUs were idle."
	::= { cpuGroup 7 }

        cpuTotalUserPercent OBJECT-TYPE
		SYNTAX INTEGER (0..100)
		ACCESS read-only
		STATUS mandatory
		DESCRIPTION
		   "The percentage of time (over the sample
		    period) that the system's CPUs were executing in
                    user mode."
	::= { cpuGroup 8 }

        cpuTotalSysPercent OBJECT-TYPE
		SYNTAX INTEGER (0..100)
		ACCESS read-only
		STATUS mandatory
		DESCRIPTION
		   "The percentage of time (over the sample
		    period) that the system's CPUs were executing
		    the kernel or operating system."
	::= { cpuGroup 9 }

        cpuTotalWaitPercent OBJECT-TYPE
		SYNTAX INTEGER (0..100)
		ACCESS read-only
		STATUS mandatory
		DESCRIPTION
		   "The percentage of time (over the sample
		    period) that the system's CPUs were waiting for
		    I/O.  This object may not be supported by the
                    underlying operating system."
	::= { cpuGroup 10 }

---
--- Concord/Empire Extension Variable Group
---
--- This group allows users of the SystemEDGE Agent to extend the
--- Concord/Empire Enterprise MIB by adding new scalar variables. Each
--- leaf in this group specifies a different MIB scalar value. The
--- values for these variables are determined by executing a command
--- on the host where the agent is running.  The command is specified
--- in the SystemEDGE configuration file (sysedge.cf) See the
--- SystemEDGE Agent User Manual for more information. 
---
--- Included here are some sample MIB variables that match the sample 
--- entries in sysedge.cf
---

        extensionDomainName OBJECT-TYPE
                SYNTAX DisplayString (SIZE (0..256))
                ACCESS read-only
                STATUS mandatory
                DESCRIPTION
                   "The Domain Name Service domain name for this host.
                    This value is obtained by a shell script included with the
                    agent distribution."
        ::= { extensionGroup 1 }

        extensionNisServer OBJECT-TYPE
                SYNTAX DisplayString (SIZE (0..256))
                ACCESS read-only
                STATUS mandatory
                DESCRIPTION
                   "The NIS (YP) server currently being used by this host.
                    This value is obtained by a shell script included with the
                    agent distribution."
        ::= { extensionGroup 2 }

        extensionMotd OBJECT-TYPE
                SYNTAX DisplayString (SIZE (0..256))
                ACCESS read-only
                STATUS mandatory
                DESCRIPTION
                   "The Message Of The Day. Return the first line of
                    the /etc/motd file on this host.  This value is
                    obtained by a shell script included with the agent
                    distribution."
        ::= { extensionGroup 3 }

        extensionPing OBJECT-TYPE
                SYNTAX DisplayString (SIZE (0..256))
                ACCESS read-write
                STATUS mandatory
                DESCRIPTION
                   "This variable allows the agent to support remote
                    Ping operations.  This functionality is useful for
                    remote troubleshooting of routing problems.  Sets
                    to this object indicate which system to Ping while
                    Get and GetNext operations perform the Ping
                    operation and return its output."
        ::= { extensionGroup 31 }

--
-- Concord/Empire Process Monitoring group
-- Contains process monitoring table, process group monitoring, 
-- and auxiliary MIB objects
--

	processMonTable OBJECT-TYPE
		SYNTAX SEQUENCE OF ProcessMonEntry
		ACCESS not-accessible
		STATUS mandatory
		DESCRIPTION
		   "The process monitor table used for monitoring
                    single instances of processes."
	::= { processMonitor 1 }

	processMonEntry OBJECT-TYPE
		SYNTAX ProcessMonEntry
		ACCESS not-accessible
		STATUS mandatory
		DESCRIPTION
		   "A process monitor entry; one entry per process to
                    monitor."
		INDEX { pmonIndex }
	::= { processMonTable 1 }

	ProcessMonEntry ::= SEQUENCE {
		pmonIndex
			INTEGER,
		pmonDescr
			DisplayString,
		pmonInterval
			INTEGER,
		pmonSampleType
			INTEGER,
		pmonAttribute
			INTEGER,
		pmonCurrVal
			INTEGER,
		pmonOperator
			INTEGER,
		pmonValue
			INTEGER,
		pmonLastCall
			TimeTicks,
		pmonNumTraps
			INTEGER,
		pmonLastTrap
			TimeTicks,
                pmonFlags
			INTEGER,
		pmonAction
			DisplayString,
		pmonRegExpr
			DisplayString,
		pmonMinValue
			INTEGER,
		pmonMaxValue
			INTEGER,
		pmonCurrentPID
			INTEGER,
		pmonRowStatus
			INTEGER,
		pmonNumEvents
			Counter
	}

	pmonIndex OBJECT-TYPE
		SYNTAX INTEGER (1..2147483647)
		ACCESS read-only
		STATUS mandatory
		DESCRIPTION
		   "A unique value for entry in the processMonTable.
		    The index values in the processMonTable may not
		    necessarily be contiguous, but are unique."
	::= { processMonEntry 1 }

	pmonDescr OBJECT-TYPE
		SYNTAX DisplayString (SIZE (0..128))
		ACCESS read-write
		STATUS mandatory
		DESCRIPTION
		   "A textual description of this entry possibly
		    identifying the purpose of this entry and who
		    created it." 
	::= { processMonEntry 2 }

	pmonInterval OBJECT-TYPE
		SYNTAX INTEGER (1..2147483647)
		ACCESS read-write
		STATUS mandatory
		DESCRIPTION
		   "The interval, in seconds, between successive
		    samples by the agent.  It must be a multiple of 30
                    seconds.  For example, if a manager wanted to
                    sample the value of a particular variable every 30
                    seconds, then setting monInterval to 30 would
                    instruct the agent to sample once very 30 seconds.
                    The sampling period is not exact but represents a
		    best-effort by the agent." 
                DEFVAL { 60 }
	::= { processMonEntry 3 }

	pmonSampleType OBJECT-TYPE
		SYNTAX INTEGER {
		   absoluteValue(1),
		   deltaValue(2)
                }
		ACCESS read-write
		STATUS mandatory
		DESCRIPTION
		   "The type of sampling performed on the object
		    represented by this entry.  For example, for
		    sampling and monitoring objects of type
		    Counter, setting the appropriate
		    monSampleType to deltaValue(2) causes the
		    agent to measure/sample the rate of change in
		    the variable rather than the absolute value.
		    For gauge and gauge-like variables,
		    absoluteValue(1) makes more sense.  The agent
		    does not perform sanity checks on this
		    variable against the type of object being
		    monitoring because there may exist some case
		    where a manage may actually wish to monitor
		    the absolute value of a counter or the delta
		    value of a gauge." 
                DEFVAL { absoluteValue }
	::= { processMonEntry 4 }

	pmonAttribute OBJECT-TYPE
		SYNTAX INTEGER {
                   procAlive(1),
                   procMemory(2),
                   procSize(3),
                   procRSS(4),
                   procTime(5),
                   procInBlks(6),
                   procOutBlks(7),
                   procMsgsSent(8),
                   procMsgsRecv(9),
                   procNice(10),
                   procNumThreads(11),
                   procNumSwaps(12),
                   procSysCalls(13),
                   procMinorPgFlts(14),
                   procMajorPgFlts(15),
                   procVolCtx(16),
                   procInvolCtx(17)
                }
		ACCESS read-write
		STATUS mandatory
		DESCRIPTION
		   "The process attribute being monitored.  These
                    enumerated values map directly to columns in the
                    Empire Process table." 
	::= { processMonEntry 5 }

	pmonCurrVal OBJECT-TYPE
		SYNTAX INTEGER
		ACCESS read-only
		STATUS mandatory
		DESCRIPTION
		   "This variable represents the current value of
		    the object being monitored as last sampled by
		    the agent.  If the pmonSampleType is
		    deltaValue(2), then this value represents the
		    difference between two successive samples.
		    If pmonSampleType is absoluteValue(1), then
		    this value represents the actual sampled value." 
	::= { processMonEntry 6 }

	pmonOperator OBJECT-TYPE
		SYNTAX INTEGER {
		   nop(1),
		   gt(2),
		   lt(3),
		   ge(4),
		   le(5),
		   eq(6),
		   ne(7)
                }
		ACCESS read-write
		STATUS mandatory
		DESCRIPTION
		   ""
                DEFVAL { nop }
	::= { processMonEntry 7 }

	pmonValue OBJECT-TYPE
		SYNTAX INTEGER
		ACCESS read-write
		STATUS mandatory
		DESCRIPTION
		   "The value against which the agent compares
		    the current value.  This value represents a
		    threshold.  Its semantics are not interpreted
		    by the agent; therefore, the manager is
		    responsible for determining if this value
		    'makes sense'."  
	::= { processMonEntry 8 }

	pmonLastCall OBJECT-TYPE
		SYNTAX TimeTicks
		ACCESS read-only
		STATUS mandatory
		DESCRIPTION
		   "The time (based on sysUpTime) at which the agent
		    last called or sampled the object being
		    monitored.  If the object has not yet been
		    sampled, 0 is returned." 
	::= { processMonEntry 9 }

	pmonNumTraps OBJECT-TYPE
		SYNTAX INTEGER
		ACCESS read-only
		STATUS mandatory
		DESCRIPTION
		   "The number of traps sent for this particular
		    monitor entry.  This value indicates how many
		    times the agent has evaluated this entry's
		    expression as true.  Recall, the expression
		    takes the form of:
		         'pmonCurrVal pmonOperator pmonValue'.
		    Because this value depends on the semantics
		    of the variable, the entry's sampling
		    interval (monInterval), and the interval at
		    which the monitoring table is evaluated, it
		    represents a lower bound on the number of
		    times the threshold has actually been crossed."
	::= { processMonEntry 10 }

	pmonLastTrap OBJECT-TYPE
		SYNTAX TimeTicks
		ACCESS read-only
		STATUS mandatory
		DESCRIPTION
		   "The time (based on sysUpTime) at which the
		    agent last sent a trap for this Monitor Table
		    entry.  If no traps have been sent, the value
		    is 0."
	::= { processMonEntry 11 }

	pmonFlags OBJECT-TYPE
		SYNTAX INTEGER 
		ACCESS read-write
		STATUS mandatory
		DESCRIPTION
                    "The flags field dictates the behavior of each
                     processMonEntry.  Each bit in the integer
                     represents the toggling of an option.  The flags
                     field of 0x00 is enables default behavior.
                     Logical or'ing together of different bits allows
                     one to combine different options.

               Hex   Function                  Default (if not enabled)

               0x01  Do not execute actions    Execute actions
               0x02  Do not send Traps         Send Traps   
               0x04  Do not re-initialize      Re-initialize
               0x08  Do not log events         Log events
               0x10  Send cont Stop Traps      Send single Stop Trap

              0x100  Monitor parent process    Monitor first found
              0x200  Do not send Start Trap    Send Start Trap
              0x400  Send Clear Traps          Send Clear Traps
              0x800  Match name and args       Match process name only
             0x1000  Threshold after X events  Threshold after 1st
             0x2000  X consec Thresh Traps     No limit
             0x4000  Monitor for X processes   Monitor for single process
         0xfff00000  Flags value specification Default is 0"

	::= { processMonEntry 12 }

	pmonAction OBJECT-TYPE
		SYNTAX DisplayString (SIZE (0..256))
		ACCESS read-write
		STATUS mandatory
		DESCRIPTION
		   "A string specifying the command to be executed 
		    upon finding a match."
	::= { processMonEntry 13 }

	pmonRegExpr OBJECT-TYPE
		SYNTAX DisplayString (SIZE (0..128))
		ACCESS read-write
		STATUS mandatory
		DESCRIPTION
		   "The regular expression to use for matching
                    processes by name or NT services by name"
	::= { processMonEntry 14 }

	pmonMinValue OBJECT-TYPE
		SYNTAX INTEGER 
		ACCESS read-only
		STATUS mandatory
		DESCRIPTION
                    "The minimum sampled value or 0 upon initialization"
	::= { processMonEntry 15 }

	pmonMaxValue OBJECT-TYPE
		SYNTAX INTEGER 
		ACCESS read-only
		STATUS mandatory
		DESCRIPTION
                    "The maximum sampled value or 0 upon initialization"
	::= { processMonEntry 16 }

	pmonCurrentPID OBJECT-TYPE
		SYNTAX INTEGER 
		ACCESS read-write
		STATUS mandatory
		DESCRIPTION
                    "The PID of the process being monitored"
	::= { processMonEntry 17 }

	pmonRowStatus OBJECT-TYPE
		SYNTAX INTEGER {
		   active(1),
		   notInService(2),
		   notReady(3),
		   createAndGo(4),
		   createAndWait(5),
		   destroy(6)
                }
		ACCESS read-write
		STATUS mandatory
		DESCRIPTION
		   "The status of this entry.  This variable is
		    equivalent in semantics to the V2 SMI
		    RowStatus textual-convention (see RFC 1443).
		    A value of active(1) indicates that the agent
		    is currently monitoring and evaluating the
		    current row.  A Value of notInService(2)
		    indicates that the agent has suspended
		    evaluation of the row.  Setting this object
		    to destroy(2) causes the agent to suspend
		    evaluation of its row and free its resources.
		    For row creation to occur, the manager must
		    supply active(1), createAndGo(4),
		    createAndWait(5), or notInService(2) as the
		    value of this object.  
		    If an error occurs at any time during the
		    processing of a particular processMonTable entry, its
		    pmonRowStatus column will be set to 
		    notReady(3)."
                DEFVAL { createAndWait } 
	::= { processMonEntry 18 }

	pmonNumEvents OBJECT-TYPE
		SYNTAX Counter
		ACCESS read-only
		STATUS mandatory
		DESCRIPTION
		   "The number of events for this process monitor
  		    entry.  Events do not necessarily imply traps
		    because Traps may be turned off for this row via
  		    flags setting." 
	::= { processMonEntry 19 }

        pmonUnusedIndex OBJECT-TYPE
		SYNTAX INTEGER (1..2147483647)
		ACCESS read-only
                STATUS mandatory
                DESCRIPTION
                   "An SNMP Get of this MIB object returns an un-used
                    processMonitorTable index number.  It can be used
                    for processMonitor table row creation optimization."
	::= { processMonitor 2 }

        pmonMatchDescr OBJECT-TYPE
		SYNTAX DisplayString
		ACCESS read-write
                STATUS mandatory
                DESCRIPTION
                   "This MIB object, when used in conjunction with
                    pmonMatchIndex can be used to quickly determine
                    the index number corresponding to a particular entry
		    description.  SNMP Set'ing a description to this MIB
		    object causes the agent to search through entries in
		    the process monitor table and place the index value of
		    the last entry whose description matches, in the
		    pmonMatchIndex MIB object."
	::= { processMonitor 3 }

        pmonMatchIndex OBJECT-TYPE
		SYNTAX INTEGER (1..2147483647)
		ACCESS read-only
                STATUS mandatory
                DESCRIPTION
                   "See description for pmonMatchDescr."
	::= { processMonitor 4 }

--
-- Process Group monitoring table
-- Contains process group monitoring table for monitoring
-- arbitrary groups of processes as single entity.
-- Each row in the table represents a group of processes
-- that SystemEDGE will monitor; SystemEDGE will track
-- various attributes of the group of processes and maintain
-- historical and current statistics about the group.

	processGroupMonTable OBJECT-TYPE
		SYNTAX SEQUENCE OF ProcessGroupMonEntry
		ACCESS not-accessible
		STATUS mandatory
		DESCRIPTION
		   "The process group monitor table used for monitoring
                    arbitrary groups of processes."
	::= { processMonitor 10 }

        processGroupMonEntry OBJECT-TYPE
		SYNTAX ProcessGroupMonEntry
		ACCESS not-accessible
		STATUS mandatory
		DESCRIPTION
		   "A process group monitor entry; one entry per
                    group of processes to monitor."
		INDEX { pgmonIndex }
	::= { processGroupMonTable 1 }

	ProcessGroupMonEntry ::= SEQUENCE {
		pgmonIndex
			INTEGER,
		pgmonDescr
			DisplayString,
		pgmonInterval
			INTEGER,
                pgmonProcRegExpr
			DisplayString,
		pgmonFlags
			INTEGER,
		pgmonNumProcs
			Gauge,
		pgmonPIDList
			DisplayString,
		pgmonStatusList
			DisplayString,
		pgmonAction
			DisplayString,
		pgmonNumEvents
			Counter,
		pgmonNumTraps
			Counter,
		pgmonLastTrap
			TimeTicks,
		pgmonRowStatus
			INTEGER,
		pgmonRSS
			Gauge,
		pgmonSize
			Gauge,
		pgmonThreadCount
			Gauge,
		pgmonMEM
			Gauge,
		pgmonInBlks
			Counter,
		pgmonOutBlks
			Counter,
		pgmonMsgsSent
			Counter,
		pgmonMsgsRecv
			Counter,
		pgmonSysCalls
			Counter,
		pgmonMinorPgFlts
			Counter,
		pgmonMajorPgFlts
			Counter,
		pgmonNumSwaps
			Counter,
		pgmonVolCtx
			Counter,
		pgmonInvolCtx
			Counter,
		pgmonCPUSecs
			Counter,
		pgmonMatchUser
			DisplayString,
		pgmonMatchGroup
			DisplayString
        }

	pgmonIndex OBJECT-TYPE
		SYNTAX INTEGER (1..2147483647)
		ACCESS read-only
		STATUS mandatory
		DESCRIPTION
		   "A unique value for entry in the processGroupMonTable.
		    The index values in the processGroupMonTable may not
		    necessarily be contiguous, but are unique."
	::= { processGroupMonEntry 1 }

	pgmonDescr OBJECT-TYPE
		SYNTAX DisplayString (SIZE (0..128))
		ACCESS read-write
		STATUS mandatory
		DESCRIPTION
		   "A textual description of this entry possibly
		    identifying the purpose of this entry and who
		    created it." 
	::= { processGroupMonEntry 2 }

	pgmonInterval OBJECT-TYPE
		SYNTAX INTEGER (1..2147483647)
		ACCESS read-write
		STATUS mandatory
		DESCRIPTION
		   "The interval, in seconds, between successive
		    samples by the agent.  It must be a multiple of 30
                    seconds.  For example, if a manager wanted to
                    sample the value of a particular variable every 30
                    seconds, then setting monInterval to 30 would
                    instruct the agent to sample once very 30 seconds.
                    The sampling period is not exact but represents a
		    best-effort by the agent." 
                DEFVAL { 60 }
	::= { processGroupMonEntry 3 }

	pgmonProcRegExpr OBJECT-TYPE
		SYNTAX DisplayString (SIZE (0..128))
		ACCESS read-write
		STATUS mandatory
		DESCRIPTION
		   "The regular expression to use for matching
                    processes by name"
	::= { processGroupMonEntry 4 }

	pgmonFlags OBJECT-TYPE
		SYNTAX INTEGER 
		ACCESS read-write
		STATUS mandatory
		DESCRIPTION
                    "The flags field dictates the behavior of each
                     processGroupMonEntry.  Each bit in the integer
                     represents the toggling of an option.  The flags
                     field of 0x00 is enables default behavior.
                     Logical or'ing together of different bits allows
                     one to combine different options.  SystemEDGE
                     common-table flags apply to this table.
		     Table-specific flags include are defined below.

               Hex   Function                  Default (if not enabled)
              0x100  Match name and args       Match process name only
                     "
	::= { processGroupMonEntry 5 }

	pgmonNumProcs OBJECT-TYPE
		SYNTAX Gauge 
		ACCESS read-only
		STATUS mandatory
		DESCRIPTION
                    "The current number of processes in the process
                     group being tracked by this table entry.  A
		     process belongs to the process-group if its name
                     (and possibly args) match the regular expression
                     configured for this entry."
	::= { processGroupMonEntry 6 }

	pgmonPIDList OBJECT-TYPE
		SYNTAX DisplayString
		ACCESS read-only
		STATUS mandatory
		DESCRIPTION
		    "A list of the numeric PIDs in this process group
		     separated by space character."
	::= { processGroupMonEntry 7 }

	pgmonStatusList OBJECT-TYPE
		SYNTAX DisplayString
		ACCESS read-only
		STATUS mandatory
		DESCRIPTION
		    "A list of the process states in this process group
		     separated by space character.  See
		     processStateInt for explanation of the state
                     of a process.  Entries in the status list have a
		     one-to-one correspondence with entries in the PID
                     list." 
	::= { processGroupMonEntry 8 }

	pgmonAction OBJECT-TYPE
		SYNTAX DisplayString (SIZE (0..256))
		ACCESS read-write
		STATUS mandatory
		DESCRIPTION
		   "A string specifying the command to be executed 
		    upon process group event."
	::= { processGroupMonEntry 9 }

        pgmonNumEvents OBJECT-TYPE
		SYNTAX Counter 
		ACCESS read-only
		STATUS mandatory
		DESCRIPTION
                   "The number of events for this process group table
		    entry.  Events do not necessarily imply traps
		    because Traps may be turned off for this row via
		    flags setting."
	::= { processGroupMonEntry 10 }

        pgmonNumTraps OBJECT-TYPE
		SYNTAX Counter 
		ACCESS read-only
		STATUS mandatory
		DESCRIPTION
                    "The number Traps sent for this process group
		     table entry."
	::= { processGroupMonEntry 11 }

	pgmonLastTrap OBJECT-TYPE
		SYNTAX TimeTicks
		ACCESS read-only
		STATUS mandatory
		DESCRIPTION
		   "The time (based on sysUpTime) at which the
		    agent last sent a trap for this entry.  If no
                    traps have been sent, the value is 0."
	::= { processGroupMonEntry 12 }

	pgmonRowStatus OBJECT-TYPE
		SYNTAX INTEGER {
		   active(1),
		   notInService(2),
		   notReady(3),
		   createAndGo(4),
		   createAndWait(5),
		   destroy(6)
                }
		ACCESS read-write
		STATUS mandatory
		DESCRIPTION
		   "The status of this entry.  This variable is
		    equivalent in semantics to the V2 SMI
		    RowStatus textual-convention (see RFC 1443).
		    A value of active(1) indicates that the agent
		    is currently monitoring and evaluating the
		    current row.  A Value of notInService(2)
		    indicates that the agent has suspended
		    evaluation of the row.  Setting this object
		    to destroy(2) causes the agent to suspend
		    evaluation of its row and free its resources.
		    For row creation to occur, the manager must
		    supply active(1), createAndGo(4),
		    createAndWait(5), or notInService(2) as the
		    value of this object.  
		    If an error occurs at any time during the
		    processing of a particular processGroupMonTable
                    entry, its pgmonRowStatus column will be set to 
		    notReady(3)."
                DEFVAL { createAndWait } 
	::= { processGroupMonEntry 13 }

        pgmonRSS OBJECT-TYPE
		SYNTAX Gauge 
		ACCESS read-only
		STATUS mandatory
		DESCRIPTION
                   "The combined resident set size of the group of
		    processes.  (See processRSS).  RSS for each
                    process in the group is summed each interval and
                    stored in this MIB variable.  Because RSS also
		    includes shared-memory, the total RSS for a group
		    could actually exceed total possible physical
		    memory for the underlying system."
	::= { processGroupMonEntry 14 }

        pgmonSize OBJECT-TYPE
		SYNTAX Gauge 
		ACCESS read-only
		STATUS mandatory
		DESCRIPTION
                   "The cobmined size of text/data/stack segments of
		    the group of processes.  (See processSize)  Size
		    for each process in the group is summed each
		    interval and stored in this MIB variable.  Because 
		    Size also includes shared-memory, the total Size
		    for a group could actually exceed total virtual
		    memory for the underlying system."
	::= { processGroupMonEntry 15 }

        pgmonThreadCount OBJECT-TYPE
		SYNTAX Gauge 
		ACCESS read-only
		STATUS mandatory
		DESCRIPTION
                   "The total number of threads for the group of
		    processes.  (See processNumThreads)  The number of
		    threads running in each process in the group is
		    summed each interval and stored in this MIB
		    variable."
	::= { processGroupMonEntry 16 }

        pgmonMEM OBJECT-TYPE
		SYNTAX Gauge 
		ACCESS read-only
		STATUS mandatory
		DESCRIPTION
                   "The total percentage of real memory used by the
		    processes in this group.  The percentage of memory
		    used by each process in the group is summed each
		    interval and stored in this MIB variable.  Because
		    memory usage includes shared memory (e.g. shared
		    librarys and DLLs), the total percentage may
		    exceed 100." 
	::= { processGroupMonEntry 17 }

        pgmonInBlks OBJECT-TYPE
		SYNTAX Counter 
		ACCESS read-only
		STATUS mandatory
		DESCRIPTION
                   "Number of blocks of data input by processes in
		    this group.  SystemEDGE maintains a 'history' of
		    group membership and tracks process stats even
		    after an individual process has left the group."
	::= { processGroupMonEntry 18 }

        pgmonOutBlks OBJECT-TYPE
		SYNTAX Counter 
		ACCESS read-only
		STATUS mandatory
		DESCRIPTION
                   "Number of blocks of data output by processes in
		    this group.  SystemEDGE maintains a 'history' of
		    group membership and tracks process stats even
		    after an individual process has left the group."
	::= { processGroupMonEntry 19 }

        pgmonMsgsSent OBJECT-TYPE
		SYNTAX Counter 
		ACCESS read-only
		STATUS mandatory
		DESCRIPTION
                   "Number of messages sent by processes in this
		    group.  SystemEDGE maintains a 'history' of
		    group membership and tracks process stats even
		    after an individual process has left the group."
	::= { processGroupMonEntry 20 }

        pgmonMsgsRecv OBJECT-TYPE
		SYNTAX Counter 
		ACCESS read-only
		STATUS mandatory
		DESCRIPTION
                   "Number of messages received by processes in this
		    group. SystemEDGE maintains a 'history' of
		    group membership and tracks process stats even
		    after an individual process has left the group."
	::= { processGroupMonEntry 21 }

        pgmonSysCalls OBJECT-TYPE
		SYNTAX Counter 
		ACCESS read-only
		STATUS mandatory
		DESCRIPTION
                   "Number of system calls invoked by processes in
		    this group.  SystemEDGE maintains a 'history' of
		    group membership and tracks process stats even
		    after an individual process has left the group."
	::= { processGroupMonEntry 22 }

        pgmonMinorPgFlts OBJECT-TYPE
		SYNTAX Counter 
		ACCESS read-only
		STATUS mandatory
		DESCRIPTION
                   "Number of minor page faults incurred by processes
		    in this group.  SystemEDGE maintains a 'history' of
		    group membership and tracks process stats even
		    after an individual process has left the group."
	::= { processGroupMonEntry 23 }

        pgmonMajorPgFlts OBJECT-TYPE
		SYNTAX Counter 
		ACCESS read-only
		STATUS mandatory
		DESCRIPTION
                   "Number of major page faults incurred by processes
		    in this group.  SystemEDGE maintains a 'history' of
		    group membership and tracks process stats even
		    after an individual process has left the group."
	::= { processGroupMonEntry 24 }

        pgmonNumSwaps OBJECT-TYPE
		SYNTAX Counter 
		ACCESS read-only
		STATUS mandatory
		DESCRIPTION
                   "Number of times processes in this gropu have been
		    swapped.  SystemEDGE maintains a 'history' of
		    group membership and tracks process stats even
		    after an individual process has left the group."
	::= { processGroupMonEntry 25 }

        pgmonVolCtx OBJECT-TYPE
		SYNTAX Counter 
		ACCESS read-only
		STATUS mandatory
		DESCRIPTION
                   "Number of voluntary context switches incurred by
		    processes in this group.  SystemEDGE maintains a
		    'history' of group membership and tracks process
		    stats even after an individual process has left
		    the group." 
	::= { processGroupMonEntry 26 }

        pgmonInvolCtx OBJECT-TYPE
		SYNTAX Counter 
		ACCESS read-only
		STATUS mandatory
		DESCRIPTION
                   "Number of involuntary context switches incurred by
		    processes in this group.  SystemEDGE maintains a
		    'history' of group membership and tracks process
		    stats even after an individual process has left
		    the group." 
	::= { processGroupMonEntry 27 }

        pgmonCPUSecs OBJECT-TYPE
		SYNTAX Counter 
		ACCESS read-only
		STATUS mandatory
		DESCRIPTION
                   "Number of seconds of CPU time used by processes in
		    this group.  SystemEDGE maintains a 'history' of
		    group membership and tracks process stats even
		    after an individual process has left the group."
       ::= { processGroupMonEntry 28 }

       pgmonMatchUser OBJECT-TYPE
		SYNTAX DisplayString (SIZE (0..32))
		ACCESS read-write
		STATUS mandatory
		DESCRIPTION
                   "If set to a valid username, SystemEDGE will match
		    running processes by username in addition to any
		    process name regular expression.  Only valid on UNIX."
       ::= { processGroupMonEntry 29 }

       pgmonMatchGroup OBJECT-TYPE
		SYNTAX DisplayString (SIZE (0..32))
		ACCESS read-write
		STATUS mandatory
		DESCRIPTION
                   "If set to a valid groupname, SystemEDGE will match
		    running processes by group name in addition to any
		    process name regular expression and username
   		    matching.  Only valid on UNIX." 
       ::= { processGroupMonEntry 30 }

--
-- Row-creation optimization MIB objects 
-- 

        pgmonUnusedIndex OBJECT-TYPE
		SYNTAX INTEGER (1..2147483647)
		ACCESS read-only
                STATUS mandatory
                DESCRIPTION
                   "An SNMP Get of this MIB object returns an un-used
                    processGroupMonitorTable index number.  It can be used
                    for processMonitor table row creation optimization."
	::= { processMonitor 11 }

        pgmonMatchDescr OBJECT-TYPE
		SYNTAX DisplayString
		ACCESS read-write
                STATUS mandatory
                DESCRIPTION
                   "This MIB object, when used in conjunction with
                    pgmonMatchIndex can be used to quickly determine
                    the index number corresponding to a particular entry
		    description.  SNMP Set'ing a description to this MIB
		    object causes the agent to search through entries in
		    the process group monitor table and place the
                    index value of the last entry whose description
                    matches, in the pgmonMatchIndex MIB object."
	::= { processMonitor 12 }

        pgmonMatchIndex OBJECT-TYPE
		SYNTAX INTEGER (1..2147483647)
		ACCESS read-only
                STATUS mandatory
                DESCRIPTION
                   "See description for pgmonMatchDescr."
	::= { processMonitor 13 }

--
-- Concord/Empire Applications Group
--

        msExchange   OBJECT IDENTIFIER ::= { applications 1 }
        msIIS        OBJECT IDENTIFIER ::= { applications 2 }
        apacheSrv    OBJECT IDENTIFIER ::= { applications 3 }
        oracledb     OBJECT IDENTIFIER ::= { applications 4 }
        sybase       OBJECT IDENTIFIER ::= { applications 5 }
        svcRsp       OBJECT IDENTIFIER ::= { applications 6 }
        topProcs     OBJECT IDENTIFIER ::= { applications 7 }
        sqlServer    OBJECT IDENTIFIER ::= { applications 8 }
        -- netService   OBJECT IDENTIFIER ::= { applications 9 }
        domino       OBJECT IDENTIFIER ::= { applications 10 }
        surveyor     OBJECT IDENTIFIER ::= { applications 11 }
        mosMod       OBJECT IDENTIFIER ::= { applications 12 } 
        ccmmod       OBJECT IDENTIFIER ::= { applications 13 }
        siebelmod    OBJECT IDENTIFIER ::= { applications 14 }
        testplugin   OBJECT IDENTIFIER ::= { applications 16 }
        firewall     OBJECT IDENTIFIER ::= { applications 17 }
        dirmwp       OBJECT IDENTIFIER ::= { applications 18 }
        custom       OBJECT IDENTIFIER ::= { applications 100 }

--
-- Traps Group
--
-- This group defines private enterprise Trap types for Empire
-- UNIX Systems Management Agents
-- Each trap has a corresponding object identifier in the Empire 
-- 'traps' group
--

        monitorEvent OBJECT IDENTIFIER ::= { traps 1 } 
	monitorTrap TRAP-TYPE
		ENTERPRISE sysmgmt
		VARIABLES { monDescr, monOID, monCurrVal, monValue,
                            monRowStatus, monOperator, monIndex, monFlags }
		DESCRIPTION
		   "A Monitor event has occurred.  Recall a
		    monitor event occurs when a Monitor Table row
		    expression evaluates to true.  The expression
		    is: 'monCurrVal monOperator monValue'." 
		::= 1

        kernelErrorEvent OBJECT IDENTIFIER ::= { traps 2 } 
	kernelErrorTrap TRAP-TYPE
		ENTERPRISE sysmgmt
		VARIABLES { seqNum, type, cause, severity }
		DESCRIPTION 
		   "A kernel error event has occurred; on V.4
		    derived operating systems, the kernel relays
		    errors and events via the system error
		    device.  See the Empire errorTable objects."
		::= 2

        monitorEntryNotReadyEvent OBJECT IDENTIFIER ::= { traps 3 } 
	monitorEntryNotReadyTrap TRAP-TYPE
		ENTERPRISE sysmgmt
		VARIABLES { monDescr, monOID, monCurrVal, monValue,
                            monRowStatus, monOperator, monIndex, monFlags }
		DESCRIPTION 
		   "This trap is sent when a Monitor Table entry's
		    monRowStatus is set to 'notReady(3)'.  One reason
		    this may occur is that the object-instance
		    identifier being monitored by its corresponding
		    Monitor Table entry is no longer in existence.
		    For example, when a process is being monitored (via
		    the Empire processTable), and that process should
		    exit, its corresponding entry in the Empire
		    processTable would no longer exist.  Consequently,
		    the object-instance identifier (for that process)
		    being monitored would no longer exist and the
		    agent would send a monitorEntryNotReady trap to
		    all properly configured managers."
		::= 3

        logMonMatchEvent    OBJECT IDENTIFIER ::= { traps 4 } 
        logMonMatchTrap  TRAP-TYPE
		ENTERPRISE sysmgmt
		VARIABLES { logMonitorLogFile, logMonitorRegularExpression,
                            logMonitorLastTrap, logMonitorLastMatch, 
                            logMonitorDescr, logMonitorIndex, logMonitorFlags }
		DESCRIPTION
		   "This trap is sent when the log monitoring
		    subsystem detects a match in a log file it is
		    currently monitoring.  Periodically, the agent
		    stats each log file for changes; if any changes
		    have occurred, the agent scans only those changes
		    for a pattern match.  Pattern matches result in
		    logMonMatch events.  Changes to log files occur
		    when new entries are added by syslogd(1M) or other
		    logging daemons."
		::= 4

        logMonNotReadyEvent OBJECT IDENTIFIER ::= { traps 5 } 
        logMonNotReadyTrap  TRAP-TYPE
		ENTERPRISE sysmgmt
		VARIABLES { logMonitorLogFile, logMonitorRegularExpression,
                            logMonitorLastTrap, logMonitorLastMatch,
                            logMonitorDescr, logMonitorIndex, 
                            logMonitorFlags }
		DESCRIPTION
		   "This trap is sent when the status of a log
		    monitoring entry becomes 'notReady(3)'.  An entry
		    becomes 'notReady(3)' if an error occurs during log
		    file scaning, if the regular expression is
		    syntactically incorrect, or if the log file does
		    not exist.  An entry that is 'notReady(3)' will
		    undergo no further evaluation until its status
		    becomes 'active(1)'."
		::= 5

        -- Empire management tool, 'sendtrap', uses sendTrapEvent OID
        -- as its enterprise ObjectID and is registered here for
        -- completeness; no EMPuma should issue traps with this
        -- Trap type nor Enterprise OBJECT-ID

        sendTrapEvent OBJECT IDENTIFIER ::= { traps 6 } 

        ntEventMonMatchEvent OBJECT IDENTIFIER ::= { traps 7 } 
        ntEventMonMatchTrap  TRAP-TYPE
		ENTERPRISE sysmgmt
		VARIABLES { ntEventMonLog, ntEventMonTypeLastMatch,
                            ntEventMonTime, ntEventMonSrcLastMatch, 
                            ntEventMonDescLastMatch, ntEventMonDescr, 
                            ntEventMonIndex, ntEventMonFlags }
		DESCRIPTION
		   "This trap is sent when the event log monitoring
		    subsystem detects a match in a log it is
		    currently monitoring.  Periodically, the agent
		    checks each event log for changes; if any changes
		    have occurred, the agent scans only those changes
		    for a pattern match.  Pattern matches result in
		    ntEventMonMatch events." 
		::= 7

        ntEventMonNotReadyEvent OBJECT IDENTIFIER ::= { traps 8 } 
        ntEventMonNotReadyTrap  TRAP-TYPE
		ENTERPRISE sysmgmt
		VARIABLES { ntEventMonLog, ntEventMonTypeFilter,
                            ntEventMonSrcFilter, ntEventMonDescFilter, 
                            ntEventMonDescr, ntEventMonIndex, ntEventMonFlags }
		DESCRIPTION
		   "This trap is sent when the status of an event log 
		    monitoring entry becomes 'notReady(3)'.  An entry
		    becomes 'notReady(3)' if an error occurs during log
		    file scaning, if the regular expression is
		    syntactically incorrect, or if the log file does
		    not exist.  An entry that is 'notReady(3)' will
		    undergo no further evaluation until its status
		    becomes 'active(1)'."
		::= 8

        monitorClearEvent OBJECT IDENTIFIER ::= { traps 9 } 
        monitorClearTrap  TRAP-TYPE
		ENTERPRISE sysmgmt
		VARIABLES { monDescr, monOID, monCurrVal, monValue,
                            monRowStatus, monOperator, monIndex, monFlags }
		DESCRIPTION 
		   "This Trap is sent when a Monitor Table entry
                    transitions from True to False and has specified
                    the monitor clearTrap flag.  This Trap represents
                    an indication that the condition that previously
                    had existed no longer does.  This Trap provides
                    management software the ability to determine that
                    an alarm can be canceled or marked as corrected.
                    This event only occurs when a monitor table entry
                    evaluates to True and then evaluates to False.
                    This Trap is sent each time the entry transitions
                    from True to false." 
		::= 9

	processStopEvent OBJECT IDENTIFIER ::= { traps 10 }
        processStopTrap TRAP-TYPE
                ENTERPRISE sysmgmt
                VARIABLES { pmonIndex, pmonDescr, pmonAttribute,
                            pmonCurrVal, pmonOperator, pmonValue,
                            pmonFlags, pmonRegExpr, pmonCurrentPID }
                DESCRIPTION
                   "This Trap is sent when using a Process Monitor
                    Table entry to monitor the state of a process.
                    When the processing being monitored dies or
                    transitions into a Zombie (or not runnable state),
                    this Trap is sent.  This Trap is sent if the value
                    of pmonFlags does not preclude sending Traps." 
                ::= 10

        processStartEvent OBJECT IDENTIFIER ::= { traps 11 }
        processStartTrap TRAP-TYPE
                ENTERPRISE sysmgmt
                VARIABLES { pmonIndex, pmonDescr, pmonAttribute,
                            pmonCurrVal, pmonOperator, pmonValue,
                            pmonFlags, pmonRegExpr, pmonCurrentPID }
                DESCRIPTION
                   "This Trap is sent when using a Process Monitor
                    Table entry to monitor the state of a process.
                    When a process is re-started, and subsequently
                    re-acquired by the SystemEDGE agent, this Trap is
                    sent.  This Trap is sent if the value of pmonFlags
                    specifies  that processStart Traps should be pay."
                ::= 11

        processThresholdEvent OBJECT IDENTIFIER ::= { traps 12 }
        processThresholdTrap TRAP-TYPE
                ENTERPRISE sysmgmt
                VARIABLES { pmonIndex, pmonDescr, pmonAttribute,
                            pmonCurrVal, pmonOperator, pmonValue,
                            pmonFlags, pmonRegExpr, pmonCurrentPID }
                DESCRIPTION
                   "This Trap is sent when using a Process Monitor
                    Table entry to monitor some attribute (e.g. memory
                    usage, process size) of a process for some
                    threshold.  When a Process Monitor table
                    expression evaluates to True, this Trap is sent.
                    The expression is: 'pmonCurrVal pmonOperator pmonValue'.
                    This Trap is sent if the value of pmonFlags does
                    not preclude the sending of Traps."
                ::= 12

        processClearEvent OBJECT IDENTIFIER ::= { traps 13 }
        processClearTrap TRAP-TYPE
                ENTERPRISE sysmgmt
                VARIABLES { pmonIndex, pmonDescr, pmonAttribute,
                            pmonCurrVal, pmonOperator, pmonValue,
                            pmonFlags, pmonRegExpr, pmonCurrentPID }
                DESCRIPTION
                   "This Trap is sent when using a Process Monitor
                    Table entry to monitor some attribute (e.g. memory
                    usage, process size) of a process for some
                    threshold.  When the threshold is crossed, a
                    processThreshold Trap is sent.  When the attribute
                    threshold expression first transitions from True
                    to False, this Trap is sent." 
                ::= 13

        licenseEvent OBJECT IDENTIFIER ::= { traps 16 }
        licenseTrap TRAP-TYPE
                ENTERPRISE sysmgmt
                VARIABLES { sysedgeLicenseString }
                DESCRIPTION
                   "This Trap is sent when SystemEDGE or associated
                    modules failed to find a valid license.  It can
                    be used in conjunction with auto-licensing or 
                    remote-licensing starting with SystemEDGE 4.0.
                    This Trap contains a single MIB object
                    denoting which product or module failed to
                    find a valid license and a string containing
                    the license information for that product or module."
                ::= 16

        fwLogmonEvent OBJECT IDENTIFIER ::= { traps 17 }

        addrChangeEvent OBJECT IDENTIFIER ::= { traps 18 }

        addrChangeTrap TRAP-TYPE
                ENTERPRISE sysmgmt
                VARIABLES { nodename, sysedgeAddressList }
                DESCRIPTION
                   "This Trap is sent when SystemEDGE when it detects
                    that its underlying IP address has changed perhaps
                    due to DHCP or other administrative means.  It
                    includes up to the last 5 IP addresses that it
                    this system was configured with.  The addresses
                    are ordered with most recently used addresses
                    occuring first in the address list.  This Trap may
                    be useless on multi-homed systems."
                ::= 18

        procGroupChangeEvent OBJECT IDENTIFIER ::= { traps 19 }
        procGroupChangeTrap TRAP-TYPE
                ENTERPRISE sysmgmt
                VARIABLES { pgmonIndex, pgmonDescr, pgmonFlags,
                            pgmonNumProcs, pgmonProcRegExpr, pgmonRowStatus,
                            pgmonPIDList, pgmonStatusList }
                DESCRIPTION
                   "Membership in a process group has changed
                   (e.g. members have joined, left, or changed)."
                ::= 19


END
