CXACTE-MIB DEFINITIONS ::= BEGIN

--#CURRENT_VERSION 1

IMPORTS
   OBJECT-TYPE         FROM RFC-1212
   DisplayString       FROM RFC1213-MIB
   cxACTE              FROM CXProduct-SMI;

--   This module uses the extended OBJECT-TYPE macro as defined
--   in RFC 1212. This is the MIB module for the ACTE objects.


--  The DS1 Debug Table

--   The DS1 Debug table is reserved for engineering manipulation
--   for the debugging of the T1/E1 I/O card part of the CX1000's
--   AC600 T1/E1 product.
--
--   This table permit the writing and reading of any register of
--   the T1 or E1 chip transceiver on the T1/E1 I/O card.


acteDebugTable           OBJECT-TYPE
      SYNTAX    SEQUENCE OF ActeDebugEntry
      ACCESS    not-accessible
      STATUS    mandatory
      DESCRIPTION
"The DS1 debug table."
      ::= { cxACTE 30 }


acteDebugEntry           OBJECT-TYPE
      SYNTAX    ActeDebugEntry
      ACCESS    not-accessible
      STATUS    mandatory
      DESCRIPTION
"An entry in the DS1 Debug Table."
      INDEX { acteDebugLinkIndex, acteDebugIndex }
      ::= { acteDebugTable 1 }



ActeDebugEntry ::=
      SEQUENCE {
-- Parameters
         acteDebugLinkIndex       INTEGER,
         acteDebugIndex           INTEGER,

         acteDebugRegister        DisplayString,
-- Status
         acteDebugResult          DisplayString,
-- Control
         acteDebugWrite           DisplayString,
         acteDebugTvdStat         INTEGER,
         acteDebugDs1Stat         INTEGER,
         acteDebugSvdStat         INTEGER,
         acteDebugSvdEvt          INTEGER
      }



acteDebugLinkIndex        OBJECT-TYPE
      SYNTAX    INTEGER (1..2)
      ACCESS    read-only
      STATUS    mandatory
      DESCRIPTION
"Identifies the T1/E1 (DS1) interface port."
      ::= { acteDebugEntry 1 }


acteDebugIndex           OBJECT-TYPE
      SYNTAX    INTEGER (1..31)
      ACCESS    read-only
      STATUS    mandatory
      DESCRIPTION
"The index value uniquely identifies the T1/E1 (DS0) channel
for which these table entries are applicable."
      ::= { acteDebugEntry 2 }


acteDebugRegister        OBJECT-TYPE
      SYNTAX    DisplayString (SIZE(0..5))
      ACCESS    read-write
      STATUS    mandatory
      DESCRIPTION
"Determines which register on the T1/E1 I/O card will be affected
by the 'read' or 'write' operation initiated by the
acteDebugOperation object."
      ::= { acteDebugEntry 10 }


 acteDebugResult              OBJECT-TYPE
      SYNTAX    DisplayString (SIZE(0..25))
      ACCESS    read-only
      STATUS    mandatory
      DESCRIPTION
"Indicates the values of each of the 8 registers following the
address specified for the acteDebugRegister object following a
'get' command."
      ::= { acteDebugEntry 50 }


acteDebugWrite           OBJECT-TYPE
      SYNTAX    DisplayString (SIZE(0..2))
      ACCESS    write-only
      STATUS    mandatory
      DESCRIPTION
"Determines the value to be written to the T1/E1 I/O card
register specified by the acteDebugRegister object. The command
is activated by entering a value in this object. "
      ::= { acteDebugEntry 80 }


acteDebugTvdStat         OBJECT-TYPE
      SYNTAX    INTEGER (1..3)
      ACCESS    write-only
      STATUS    mandatory
      DESCRIPTION
"This object displays the statistics relative to this TVD 
control block for the specified DS0 channel on the specified 
DVC card which corresponds to acteDebugCfgIndex. 
If acteDebugTvdStat is set to 1, nothing occurs, 2 displays 
the debugging information and 3 clears the counters."
      ::= { acteDebugEntry 81 }


acteDebugDs1Stat         OBJECT-TYPE
      SYNTAX    INTEGER (1..3)
      ACCESS    write-only
      STATUS    mandatory
      DESCRIPTION
"This object displays the statistics relative to this DS1 
control block. When acteDebugIndex is set to 1, it displays 
the port information, 2 displays the counter information for 
channels 0 to 14 and 3 displays the counter information for 
channels 15 to 29. If acteDebugDs1Stat is set to 1, nothing 
occurs, 2 displays the debugging information and 3 clears 
the counters."
      ::= { acteDebugEntry 82 }


acteDebugSvdStat         OBJECT-TYPE
      SYNTAX    INTEGER (1..3)
      ACCESS    write-only
      STATUS    mandatory
      DESCRIPTION
"This object displays the statistics relative to this SVD 
control block for the specified DS0 channel specified by 
acteDebugIndex. If acteDebugSvdStat is set to 1, nothing 
occurs, 2 displays the debugging information and 3 clears 
the counters."
      ::= { acteDebugEntry 83 }


acteDebugSvdEvt          OBJECT-TYPE
      SYNTAX    INTEGER (1..3)
      ACCESS    write-only
      STATUS    mandatory
      DESCRIPTION
"This object displays the timestamps concerning particular 
events relative to this TVD control block for the specified 
DS0 channel specified by acteDebugIndex. If acteDebugSvdEvt 
is set to 1, nothing occurs, 2 displays the debugging 
information and 3 clears the counters."
      ::= { acteDebugEntry 84 }

END
