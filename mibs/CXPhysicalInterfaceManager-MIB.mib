CXPhysicalInterfaceManager-MIB DEFINITIONS ::= BEGIN

IMPORTS
	OBJECT-TYPE    FROM RFC-1212

--  Proprietary Imports

     cxPortManager   FROM CXProduct-SMI;

cxPhyIfTable OBJECT-TYPE
	SYNTAX  SEQUENCE OF CxPhyIfEntry
	ACCESS  not-accessible
	STATUS  mandatory
	DESCRIPTION
"A table of physical interface configuration."
	REFERENCE
		" "
	::= { cxPortManager 3 }


cxPhyIfEntry OBJECT-TYPE
	SYNTAX CxPhyIfEntry
	ACCESS  not-accessible
	STATUS  mandatory
	DESCRIPTION
"Defines a row in the cxPhyIfTable. Each row contains the objects which 
are used to define a physical interface."
	INDEX { cxPhyIfIndex }
	::= { cxPhyIfTable 1 }

 CxPhyIfEntry::=
	SEQUENCE {
		cxPhyIfIndex                    INTEGER,
		cxPhyIfType                     INTEGER
		}

cxPhyIfIndex    OBJECT-TYPE
	SYNTAX  INTEGER
	ACCESS read-only
	STATUS mandatory
	DESCRIPTION
"Identifies the port that this table row defines. 

For the CX900, this object specifies the slot and port number. The first 
digit identifies the slot number the I/O board resides in, the second 
digit identifies the number of the port on the I/O board. For example: 11, 
21, 31, 41, 51, 61 or 71. 

For the CX1000, this object specifies the port number only. The range of 
available port numbers varies according to the type of module. For 
example, the LAN module supports only one port per I/O board and the Voice 
module supports only two ports per I/O board, but the Frame Relay module 
supports four ports per I/O board. You distinguish between module port 
numbers by specifying the slot number of the I/O board using a different 
object.

Default Value: none"

	::= { cxPhyIfEntry 1 }

cxPhyIfType     OBJECT-TYPE
	SYNTAX  INTEGER{
				others (1),
				v24 (2),
				v35 (3),
				x21 (4),
				v34 (5),
				u-isdn-bri (6),                         
				st-isdn-bri (8),
				dds-56k (10),
				dds-t1e1 (11),
				fxs-voice (12),
				fxo-voice (13),
				em-voice (14),
				ethernet (15),
				token-ring (16),
				v35-eu (17),
				hsIO (18),
				usIO (19),
				lanIO (20),
				elIO (21),
				voxIO (22),
				tlIO (23),
				t1e1IO (24),
				dvc (25),
				multi-io (26),
				fast-ethernet (27),
				atm-cell-io	(28)
	}
	ACCESS read-only
	STATUS mandatory
	DESCRIPTION
"Identifies the physical interface type of the port.

Options:

others (1) 

v24 (2) 

v35 (3)

x21 (4)

v34 (5)

u-isdn-bri (6) 

u-isdn-pri (7)

st-isdn-bri (8)

st-isdn-pri (9)

dds-56k (10)

dds-t1e1 (11) 

fxs-voice (12)

fxo-voice (13)

em-voice (14)

ethernet (15)

token-ring (16)

v35-eu (17)

HSIO (18)

USIO (19)

LANIO (20)

ELIO (21)

VOXIO (22)

TLIO (23)

T1E1IO (24)

DVC (25)

multi-io (26)

fast-ethernet (27)

atm-cell-io	(28) The speed that this card can handle is T1/E1 up to T3/E3.

Default Value: none"

	::= { cxPhyIfEntry 2 }


END
