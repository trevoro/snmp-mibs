Nortel-MsCarrier-MscPassport-X25TraceRcvrMIB
DEFINITIONS ::= BEGIN



IMPORTS

      OBJECT-TYPE
   FROM RFC-1212

      mscPassportMIBs
   FROM Nortel-MsCarrier-MscPassport-UsefulDefinitionsMIB

      DisplayString,
      StorageType,
      RowStatus,
      Integer32,
      Unsigned32
   FROM Nortel-MsCarrier-MscPassport-StandardTextualConventionsMIB

      Hex,
      NonReplicated,
      HexString,
      EnterpriseDateAndTime,
      DigitString
   FROM Nortel-MsCarrier-MscPassport-TextualConventionsMIB

      mscTraceIndex,
      mscTraceRcvr,
      mscTraceSessionIndex,
      mscTraceRcvrIndex,
      mscTraceSession
   FROM Nortel-MsCarrier-MscPassport-TraceBaseMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     X25TraceRcvr Enterprise MIB."

x25TraceRcvrMIB OBJECT IDENTIFIER ::= { mscPassportMIBs 62 }










-- Trace Rcvr/<string> X25
-- This component identifies the access method used by the receiver of 
-- the trace data as X.25.

mscTraceRcvrX25 OBJECT IDENTIFIER ::= { mscTraceRcvr 2 }



mscTraceRcvrX25RowStatusTable OBJECT-TYPE
   SYNTAX     SEQUENCE OF MscTraceRcvrX25RowStatusEntry
   ACCESS     not-accessible
   STATUS     mandatory
   DESCRIPTION
     "This entry controls the addition and deletion of 
      mscTraceRcvrX25 components."
::= { mscTraceRcvrX25 1 }

mscTraceRcvrX25RowStatusEntry OBJECT-TYPE
   SYNTAX     MscTraceRcvrX25RowStatusEntry
   ACCESS     not-accessible
   STATUS     mandatory
   DESCRIPTION
     "A single entry in the table represents a single 
      mscTraceRcvrX25 component."
   INDEX {
      mscTraceIndex,
      mscTraceRcvrIndex,
      mscTraceRcvrX25Index }
::= { mscTraceRcvrX25RowStatusTable 1 }

MscTraceRcvrX25RowStatusEntry ::= SEQUENCE {
   mscTraceRcvrX25RowStatus
      RowStatus,
   mscTraceRcvrX25ComponentName
      DisplayString,
   mscTraceRcvrX25StorageType
      StorageType,
   mscTraceRcvrX25Index
      NonReplicated }

mscTraceRcvrX25RowStatus OBJECT-TYPE
   SYNTAX     RowStatus 
   ACCESS     read-write
   STATUS     mandatory
   DESCRIPTION
     "This variable is used as the basis for SNMP naming of
      mscTraceRcvrX25 components.
      These components can be added and deleted."
::= { mscTraceRcvrX25RowStatusEntry 1 }

mscTraceRcvrX25ComponentName OBJECT-TYPE
   SYNTAX     DisplayString 
   ACCESS     read-only
   STATUS     mandatory
   DESCRIPTION
     "This variable provides the component's string name for
      use with the ASCII Console Interface"
::= { mscTraceRcvrX25RowStatusEntry 2 }

mscTraceRcvrX25StorageType OBJECT-TYPE
   SYNTAX     StorageType 
   ACCESS     read-only
   STATUS     mandatory
   DESCRIPTION
     "This variable represents the storage type value for the
      mscTraceRcvrX25 tables."
::= { mscTraceRcvrX25RowStatusEntry 4 }

mscTraceRcvrX25Index OBJECT-TYPE
   SYNTAX     NonReplicated 
   ACCESS     not-accessible
   STATUS     mandatory
   DESCRIPTION
     "This variable represents the index for the mscTraceRcvrX25 tables."
::= { mscTraceRcvrX25RowStatusEntry 10 }


-- Trace Rcvr/<string> X25 DataNetworkAddress
-- This component defines the calling end of the trace connection. It 
-- includes the set of attributes which apply to a Vc connection to an 
-- X.25 trace receiver.

mscTraceRcvrX25Dna OBJECT IDENTIFIER ::= { mscTraceRcvrX25 2 }



mscTraceRcvrX25DnaRowStatusTable OBJECT-TYPE
   SYNTAX     SEQUENCE OF MscTraceRcvrX25DnaRowStatusEntry
   ACCESS     not-accessible
   STATUS     mandatory
   DESCRIPTION
     "This entry controls the addition and deletion of 
      mscTraceRcvrX25Dna components."
::= { mscTraceRcvrX25Dna 1 }

mscTraceRcvrX25DnaRowStatusEntry OBJECT-TYPE
   SYNTAX     MscTraceRcvrX25DnaRowStatusEntry
   ACCESS     not-accessible
   STATUS     mandatory
   DESCRIPTION
     "A single entry in the table represents a single 
      mscTraceRcvrX25Dna component."
   INDEX {
      mscTraceIndex,
      mscTraceRcvrIndex,
      mscTraceRcvrX25Index,
      mscTraceRcvrX25DnaIndex }
::= { mscTraceRcvrX25DnaRowStatusTable 1 }

MscTraceRcvrX25DnaRowStatusEntry ::= SEQUENCE {
   mscTraceRcvrX25DnaRowStatus
      RowStatus,
   mscTraceRcvrX25DnaComponentName
      DisplayString,
   mscTraceRcvrX25DnaStorageType
      StorageType,
   mscTraceRcvrX25DnaIndex
      NonReplicated }

mscTraceRcvrX25DnaRowStatus OBJECT-TYPE
   SYNTAX     RowStatus 
   ACCESS     read-only
   STATUS     mandatory
   DESCRIPTION
     "This variable is used as the basis for SNMP naming of
      mscTraceRcvrX25Dna components.
      These components cannot be added nor deleted."
::= { mscTraceRcvrX25DnaRowStatusEntry 1 }

mscTraceRcvrX25DnaComponentName OBJECT-TYPE
   SYNTAX     DisplayString 
   ACCESS     read-only
   STATUS     mandatory
   DESCRIPTION
     "This variable provides the component's string name for
      use with the ASCII Console Interface"
::= { mscTraceRcvrX25DnaRowStatusEntry 2 }

mscTraceRcvrX25DnaStorageType OBJECT-TYPE
   SYNTAX     StorageType 
   ACCESS     read-only
   STATUS     mandatory
   DESCRIPTION
     "This variable represents the storage type value for the
      mscTraceRcvrX25Dna tables."
::= { mscTraceRcvrX25DnaRowStatusEntry 4 }

mscTraceRcvrX25DnaIndex OBJECT-TYPE
   SYNTAX     NonReplicated 
   ACCESS     not-accessible
   STATUS     mandatory
   DESCRIPTION
     "This variable represents the index for the mscTraceRcvrX25Dna tables."
::= { mscTraceRcvrX25DnaRowStatusEntry 10 }

mscTraceRcvrX25DnaAddressTable OBJECT-TYPE
   SYNTAX     SEQUENCE OF MscTraceRcvrX25DnaAddressEntry
   ACCESS     not-accessible
   STATUS     mandatory
   DESCRIPTION
     "This group contains attributes common to all Dnas. This group is 
      composed of two attributes which define a Dna. These attributes are 
      used to interpret the format of the address digits."
::= { mscTraceRcvrX25Dna 10 }

mscTraceRcvrX25DnaAddressEntry OBJECT-TYPE
   SYNTAX     MscTraceRcvrX25DnaAddressEntry
   ACCESS     not-accessible
   STATUS     mandatory
   DESCRIPTION
     "An entry in the mscTraceRcvrX25DnaAddressTable."
   INDEX {
      mscTraceIndex,
      mscTraceRcvrIndex,
      mscTraceRcvrX25Index,
      mscTraceRcvrX25DnaIndex }
::= { mscTraceRcvrX25DnaAddressTable 1 }

MscTraceRcvrX25DnaAddressEntry ::= SEQUENCE {
   mscTraceRcvrX25DnaNumberingPlanIndicator
      INTEGER,
   mscTraceRcvrX25DnaDataNetworkAddress
      DigitString }

mscTraceRcvrX25DnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. The address may belong to an E.164 or X.121 
      plan."
   DEFVAL     { x121 }
::= { mscTraceRcvrX25DnaAddressEntry 1 }

mscTraceRcvrX25DnaDataNetworkAddress OBJECT-TYPE
   SYNTAX     DigitString (SIZE (1..15))
   ACCESS     read-write
   STATUS     mandatory
   DESCRIPTION
     "The Dna attribute contains digits which form a unique identifier for 
      the calling end of the trace connection. Dna digits are selected and 
      assigned by network operators. The maximum Dna length is 15 
      digits."
::= { mscTraceRcvrX25DnaAddressEntry 2 }

mscTraceRcvrX25DnaOutgoingOptionsTable OBJECT-TYPE
   SYNTAX     SEQUENCE OF MscTraceRcvrX25DnaOutgoingOptionsEntry
   ACCESS     not-accessible
   STATUS     mandatory
   DESCRIPTION
     "This group defines call options for outgoing calls."
::= { mscTraceRcvrX25Dna 11 }

mscTraceRcvrX25DnaOutgoingOptionsEntry OBJECT-TYPE
   SYNTAX     MscTraceRcvrX25DnaOutgoingOptionsEntry
   ACCESS     not-accessible
   STATUS     mandatory
   DESCRIPTION
     "An entry in the mscTraceRcvrX25DnaOutgoingOptionsTable."
   INDEX {
      mscTraceIndex,
      mscTraceRcvrIndex,
      mscTraceRcvrX25Index,
      mscTraceRcvrX25DnaIndex }
::= { mscTraceRcvrX25DnaOutgoingOptionsTable 1 }

MscTraceRcvrX25DnaOutgoingOptionsEntry ::= SEQUENCE {
   mscTraceRcvrX25DnaOutCalls
      INTEGER,
   mscTraceRcvrX25DnaOutDefaultPriority
      INTEGER,
   mscTraceRcvrX25DnaOutIntl
      INTEGER,
   mscTraceRcvrX25DnaOutDefaultPathSensitivity
      INTEGER,
   mscTraceRcvrX25DnaOutDefaultPathReliability
      INTEGER,
   mscTraceRcvrX25DnaOutPathReliabilityOverRide
      INTEGER,
   mscTraceRcvrX25DnaOutPathReliabilitySignal
      INTEGER,
   mscTraceRcvrX25DnaOutAccess
      INTEGER }

mscTraceRcvrX25DnaOutCalls OBJECT-TYPE
   SYNTAX     INTEGER  {
                 disallowed(0),
                 allowed(1) }
   ACCESS     read-only
   STATUS     mandatory
   DESCRIPTION
     "This attribute specifies that outgoing calls (from the DTE to the 
      network) can be made using this particular Dna component."
   DEFVAL     { allowed }
::= { mscTraceRcvrX25DnaOutgoingOptionsEntry 1 }

mscTraceRcvrX25DnaOutDefaultPriority OBJECT-TYPE
   SYNTAX     INTEGER  {
                 normal(0),
                 high(1) }
   ACCESS     read-write
   STATUS     mandatory
   DESCRIPTION
     "If this attribute is set to normal, then the default priority for 
      outgoing calls (from the DTE to the network) using this particular 
      Dna is normal priority when the priority is not specified in the call. 
      If this attribute is set to high then the default priority for outgoing 
      calls using this particular Dna is high priority."
   DEFVAL     { high }
::= { mscTraceRcvrX25DnaOutgoingOptionsEntry 7 }

mscTraceRcvrX25DnaOutIntl OBJECT-TYPE
   SYNTAX     INTEGER  {
                 disallowed(0),
                 allowed(1) }
   ACCESS     read-only
   STATUS     mandatory
   DESCRIPTION
     "This attribute specifies that outgoing international calls (from the 
      DTE to the network) can be made using this particular Dna.
      
      This attribute also controls access to another numbering plan, and 
      specifies that cross-numbering plan calls are allowed."
   DEFVAL     { allowed }
::= { mscTraceRcvrX25DnaOutgoingOptionsEntry 8 }

mscTraceRcvrX25DnaOutDefaultPathSensitivity OBJECT-TYPE
   SYNTAX     INTEGER  {
                 throughput(0),
                 delay(1) }
   ACCESS     read-only
   STATUS     obsolete
   DESCRIPTION
     "This attribute specifies the default class of routing (delay/
      throughput) for all outgoing calls (from the DTE to the network) 
      using this particular Dna. The chosen default class of routing 
      applies to all outgoing calls established using this Dna, and applies 
      to the packets travelling in both directions on all outgoing calls 
      (local to remote, and remote to local).
      This attribute, if set to a value of throughput, specifies that the 
      default class of routing is throughput sensitive. If set to a value of 
      delay, then the default class of routing is delay sensitive.
      
      This attribute is obsoleted. Please refer to defaultTransferPriority 
      for the corresponding new attribute."
   DEFVAL     { throughput }
::= { mscTraceRcvrX25DnaOutgoingOptionsEntry 11 }

mscTraceRcvrX25DnaOutDefaultPathReliability OBJECT-TYPE
   SYNTAX     INTEGER  {
                 high(0),
                 normal(1) }
   ACCESS     read-only
   STATUS     mandatory
   DESCRIPTION
     "This attribute specifies the default reliability class of routing for all 
      calls (from the DTE to the network) using this particular Dna. The 
      chosen default reliability class of routing normally applies to all 
      packets (including the call packets) travelling into the network.
      A value of high specifies that packets are to be overflowed or 
      retransmitted at various routing levels. Typically high reliability 
      results in duplication and disordering of packets in the network, 
      when errors are detected or during link congestion. The VC handles 
      the duplication and disordering to ensure that packets are delivered 
      to the interface in the proper sequence and without duplication."
   DEFVAL     { high }
::= { mscTraceRcvrX25DnaOutgoingOptionsEntry 14 }

mscTraceRcvrX25DnaOutPathReliabilityOverRide OBJECT-TYPE
   SYNTAX     INTEGER  {
                 no(0),
                 yes(1) }
   ACCESS     read-only
   STATUS     mandatory
   DESCRIPTION
     "This attribute specifies that the called end of the connection will not 
      use the calling end provisioning data for reliability class of routing 
      to override the provisioning data at the called end."
   DEFVAL     { no }
::= { mscTraceRcvrX25DnaOutgoingOptionsEntry 15 }

mscTraceRcvrX25DnaOutPathReliabilitySignal OBJECT-TYPE
   SYNTAX     INTEGER  {
                 disallowed(0),
                 allowed(1) }
   ACCESS     read-only
   STATUS     mandatory
   DESCRIPTION
     "This attribute specifies that reliability routing signaling is not used."
   DEFVAL     { disallowed }
::= { mscTraceRcvrX25DnaOutgoingOptionsEntry 16 }

mscTraceRcvrX25DnaOutAccess OBJECT-TYPE
   SYNTAX     INTEGER  {
                 disallowed(0),
                 allowed(1) }
   ACCESS     read-write
   STATUS     mandatory
   DESCRIPTION
     "This attribute is an extension of the Closed User Group (CUG) 
      facility. If this attribute is set to a value of allowed, it specifies that 
      outgoing calls (from the DTE to the network) to the open (non-
      CUG) part of the network are permitted. It also permits outgoing 
      calls to interfaces that have Incoming Access capabilities. If set to a 
      value of disallowed, then such calls cannot be made using this Dna 
      (the calls will be cleared by the local DCE).
      This attribute corresponds to the ITU-T 'Closed User Group with 
      Outgoing Access' feature."
   DEFVAL     { disallowed }
::= { mscTraceRcvrX25DnaOutgoingOptionsEntry 17 }

mscTraceRcvrX25DnaIncomingOptionsTable OBJECT-TYPE
   SYNTAX     SEQUENCE OF MscTraceRcvrX25DnaIncomingOptionsEntry
   ACCESS     not-accessible
   STATUS     mandatory
   DESCRIPTION
     "This group defines the call options for incoming calls."
::= { mscTraceRcvrX25Dna 12 }

mscTraceRcvrX25DnaIncomingOptionsEntry OBJECT-TYPE
   SYNTAX     MscTraceRcvrX25DnaIncomingOptionsEntry
   ACCESS     not-accessible
   STATUS     mandatory
   DESCRIPTION
     "An entry in the mscTraceRcvrX25DnaIncomingOptionsTable."
   INDEX {
      mscTraceIndex,
      mscTraceRcvrIndex,
      mscTraceRcvrX25Index,
      mscTraceRcvrX25DnaIndex }
::= { mscTraceRcvrX25DnaIncomingOptionsTable 1 }

MscTraceRcvrX25DnaIncomingOptionsEntry ::= SEQUENCE {
   mscTraceRcvrX25DnaIncCalls
      INTEGER }

mscTraceRcvrX25DnaIncCalls OBJECT-TYPE
   SYNTAX     INTEGER  {
                 disallowed(0),
                 allowed(1) }
   ACCESS     read-only
   STATUS     mandatory
   DESCRIPTION
     "This attribute specifies that incoming calls (from the network to the 
      DTE) cannot be made to this Dna."
   DEFVAL     { disallowed }
::= { mscTraceRcvrX25DnaIncomingOptionsEntry 1 }

mscTraceRcvrX25DnaCallOptionsTable OBJECT-TYPE
   SYNTAX     SEQUENCE OF MscTraceRcvrX25DnaCallOptionsEntry
   ACCESS     not-accessible
   STATUS     mandatory
   DESCRIPTION
     "The CallOptions group defines additional options for calls which 
      are not specific to the direction of the call."
::= { mscTraceRcvrX25Dna 13 }

mscTraceRcvrX25DnaCallOptionsEntry OBJECT-TYPE
   SYNTAX     MscTraceRcvrX25DnaCallOptionsEntry
   ACCESS     not-accessible
   STATUS     mandatory
   DESCRIPTION
     "An entry in the mscTraceRcvrX25DnaCallOptionsTable."
   INDEX {
      mscTraceIndex,
      mscTraceRcvrIndex,
      mscTraceRcvrX25Index,
      mscTraceRcvrX25DnaIndex }
::= { mscTraceRcvrX25DnaCallOptionsTable 1 }

MscTraceRcvrX25DnaCallOptionsEntry ::= SEQUENCE {
   mscTraceRcvrX25DnaPacketSizes
      OCTET STRING,
   mscTraceRcvrX25DnaDefaultRecvFrmNetworkPacketSize
      INTEGER,
   mscTraceRcvrX25DnaDefaultSendToNetworkPacketSize
      INTEGER,
   mscTraceRcvrX25DnaDefaultRecvFrmNetworkThruputClass
      Unsigned32,
   mscTraceRcvrX25DnaDefaultSendToNetworkThruputClass
      Unsigned32,
   mscTraceRcvrX25DnaDefaultRecvFrmNetworkWindowSize
      Unsigned32,
   mscTraceRcvrX25DnaDefaultSendToNetworkWindowSize
      Unsigned32,
   mscTraceRcvrX25DnaPacketSizeNegotiation
      INTEGER,
   mscTraceRcvrX25DnaCugFormat
      INTEGER }

mscTraceRcvrX25DnaPacketSizes OBJECT-TYPE
   SYNTAX     OCTET STRING (SIZE (2))
   ACCESS     read-only
   STATUS     mandatory
   DESCRIPTION
     "This attribute specifies the allowable packet sizes supported for calls 
      using this Dna.

      Description of bits:
      n16(0)
      n32(1)
      n64(2)
      n128(3)
      n256(4)
      n512(5)
      n1024(6)
      n2048(7)
      n4096(8)"
   DEFVAL     { '0100'H }
::= { mscTraceRcvrX25DnaCallOptionsEntry 2 }

mscTraceRcvrX25DnaDefaultRecvFrmNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute specifies the default local receive packet size from 
      network to DTE for calls using this particular Dna."
   DEFVAL     { n2048 }
::= { mscTraceRcvrX25DnaCallOptionsEntry 3 }

mscTraceRcvrX25DnaDefaultSendToNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute specifies the default local send packet size from DTE 
      to network for all calls using this particular Dna."
   DEFVAL     { n2048 }
::= { mscTraceRcvrX25DnaCallOptionsEntry 4 }

mscTraceRcvrX25DnaDefaultRecvFrmNetworkThruputClass OBJECT-TYPE
   SYNTAX     Unsigned32 (0..15)
   ACCESS     read-write
   STATUS     mandatory
   DESCRIPTION
     "This attribute specifies the default receive throughput class, 
      (towards the interface) for all calls using this particular Dna."
   DEFVAL     { 10 }
::= { mscTraceRcvrX25DnaCallOptionsEntry 5 }

mscTraceRcvrX25DnaDefaultSendToNetworkThruputClass OBJECT-TYPE
   SYNTAX     Unsigned32 (0..15)
   ACCESS     read-write
   STATUS     mandatory
   DESCRIPTION
     "This attribute specifies the default send throughput class (towards 
      the network) for all calls using this particular Dna."
   DEFVAL     { 10 }
::= { mscTraceRcvrX25DnaCallOptionsEntry 6 }

mscTraceRcvrX25DnaDefaultRecvFrmNetworkWindowSize OBJECT-TYPE
   SYNTAX     Unsigned32 (1..7)
   ACCESS     read-only
   STATUS     mandatory
   DESCRIPTION
     "This attribute specifies the default value for the number of data 
      packets that can be send to the interface before any 
      acknowledgment."
   DEFVAL     { 1 }
::= { mscTraceRcvrX25DnaCallOptionsEntry 7 }

mscTraceRcvrX25DnaDefaultSendToNetworkWindowSize OBJECT-TYPE
   SYNTAX     Unsigned32 (1..7)
   ACCESS     read-only
   STATUS     mandatory
   DESCRIPTION
     "This attribute specifies the default value for the number of data 
      packets that can be received from the interface before any 
      acknowledgment."
   DEFVAL     { 1 }
::= { mscTraceRcvrX25DnaCallOptionsEntry 8 }

mscTraceRcvrX25DnaPacketSizeNegotiation OBJECT-TYPE
   SYNTAX     INTEGER  {
                 endToEnd(0),
                 local(1) }
   ACCESS     read-only
   STATUS     mandatory
   DESCRIPTION
     "This attribute, if set to local specifies that packet sizes can be 
      negotiated locally at the interface irrespective of the setting at the 
      remote interface. If set to endtoEnd, then the packet size 
      negotiation is between the local and remote interface (i.e. packet 
      sizes are the same on both interfaces)."
   DEFVAL     { local }
::= { mscTraceRcvrX25DnaCallOptionsEntry 9 }

mscTraceRcvrX25DnaCugFormat OBJECT-TYPE
   SYNTAX     INTEGER  {
                 basic(0),
                 extended(1) }
   ACCESS     read-only
   STATUS     mandatory
   DESCRIPTION
     "This attribute specifies the format to signal CUG indices as basic or 
      extended. A basic CUG index format is two digits long. An 
      extended CUG index format is four digits long."
   DEFVAL     { basic }
::= { mscTraceRcvrX25DnaCallOptionsEntry 10 }


-- Trace Rcvr/<string> X25 Dna ClosedUserGroup
-- The ClosedUserGroup component defines options associated with a 
-- national or international closed user group identifier. When a Dna is 
-- defined with a Cug, calls to other Dnas which do not have the same 
-- Cug interlockCode defined are refused. When a Dna is not defined 
-- with a Cug, calls to other Dnas which have any Cug interlockCode 
-- defined are refused. The Dna attributes outAccess and incAccess 
-- can override these rules.
-- If this component is present, the X.25 interface which connects to 
-- the X.25 trace receiver must be provisioned with the same Cug 
-- interlockCode.

mscTraceRcvrX25DnaCug OBJECT IDENTIFIER ::= { mscTraceRcvrX25Dna 2 }



mscTraceRcvrX25DnaCugRowStatusTable OBJECT-TYPE
   SYNTAX     SEQUENCE OF MscTraceRcvrX25DnaCugRowStatusEntry
   ACCESS     not-accessible
   STATUS     mandatory
   DESCRIPTION
     "This entry controls the addition and deletion of 
      mscTraceRcvrX25DnaCug components."
::= { mscTraceRcvrX25DnaCug 1 }

mscTraceRcvrX25DnaCugRowStatusEntry OBJECT-TYPE
   SYNTAX     MscTraceRcvrX25DnaCugRowStatusEntry
   ACCESS     not-accessible
   STATUS     mandatory
   DESCRIPTION
     "A single entry in the table represents a single 
      mscTraceRcvrX25DnaCug component."
   INDEX {
      mscTraceIndex,
      mscTraceRcvrIndex,
      mscTraceRcvrX25Index,
      mscTraceRcvrX25DnaIndex,
      mscTraceRcvrX25DnaCugIndex }
::= { mscTraceRcvrX25DnaCugRowStatusTable 1 }

MscTraceRcvrX25DnaCugRowStatusEntry ::= SEQUENCE {
   mscTraceRcvrX25DnaCugRowStatus
      RowStatus,
   mscTraceRcvrX25DnaCugComponentName
      DisplayString,
   mscTraceRcvrX25DnaCugStorageType
      StorageType,
   mscTraceRcvrX25DnaCugIndex
      Integer32 }

mscTraceRcvrX25DnaCugRowStatus OBJECT-TYPE
   SYNTAX     RowStatus 
   ACCESS     read-write
   STATUS     mandatory
   DESCRIPTION
     "This variable is used as the basis for SNMP naming of
      mscTraceRcvrX25DnaCug components.
      These components can be added and deleted."
::= { mscTraceRcvrX25DnaCugRowStatusEntry 1 }

mscTraceRcvrX25DnaCugComponentName OBJECT-TYPE
   SYNTAX     DisplayString 
   ACCESS     read-only
   STATUS     mandatory
   DESCRIPTION
     "This variable provides the component's string name for
      use with the ASCII Console Interface"
::= { mscTraceRcvrX25DnaCugRowStatusEntry 2 }

mscTraceRcvrX25DnaCugStorageType OBJECT-TYPE
   SYNTAX     StorageType 
   ACCESS     read-only
   STATUS     mandatory
   DESCRIPTION
     "This variable represents the storage type value for the
      mscTraceRcvrX25DnaCug tables."
::= { mscTraceRcvrX25DnaCugRowStatusEntry 4 }

mscTraceRcvrX25DnaCugIndex OBJECT-TYPE
   SYNTAX     Integer32 (1..1)
   ACCESS     not-accessible
   STATUS     mandatory
   DESCRIPTION
     "This variable represents the index for the mscTraceRcvrX25DnaCug tables."
::= { mscTraceRcvrX25DnaCugRowStatusEntry 10 }

mscTraceRcvrX25DnaCugCugOptionsTable OBJECT-TYPE
   SYNTAX     SEQUENCE OF MscTraceRcvrX25DnaCugCugOptionsEntry
   ACCESS     not-accessible
   STATUS     mandatory
   DESCRIPTION
     "Attributes in this group define ClosedUserGroup options associated 
      with interlockCode. Dnas with the same CUG (interlockCode) can 
      make calls within this group. Various combinations of attributes are 
      defined under this option which permit or prevent calls in the same 
      CUG group."
::= { mscTraceRcvrX25DnaCug 10 }

mscTraceRcvrX25DnaCugCugOptionsEntry OBJECT-TYPE
   SYNTAX     MscTraceRcvrX25DnaCugCugOptionsEntry
   ACCESS     not-accessible
   STATUS     mandatory
   DESCRIPTION
     "An entry in the mscTraceRcvrX25DnaCugCugOptionsTable."
   INDEX {
      mscTraceIndex,
      mscTraceRcvrIndex,
      mscTraceRcvrX25Index,
      mscTraceRcvrX25DnaIndex,
      mscTraceRcvrX25DnaCugIndex }
::= { mscTraceRcvrX25DnaCugCugOptionsTable 1 }

MscTraceRcvrX25DnaCugCugOptionsEntry ::= SEQUENCE {
   mscTraceRcvrX25DnaCugType
      INTEGER,
   mscTraceRcvrX25DnaCugDnic
      DigitString,
   mscTraceRcvrX25DnaCugInterlockCode
      Unsigned32,
   mscTraceRcvrX25DnaCugPreferential
      INTEGER,
   mscTraceRcvrX25DnaCugOutCalls
      INTEGER,
   mscTraceRcvrX25DnaCugIncCalls
      INTEGER,
   mscTraceRcvrX25DnaCugPrivileged
      INTEGER }

mscTraceRcvrX25DnaCugType OBJECT-TYPE
   SYNTAX     INTEGER  {
                 national(0),
                 international(1) }
   ACCESS     read-write
   STATUS     mandatory
   DESCRIPTION
     "This attribute specifies the CUG type as either national or 
      international. A national CUG has significance within the local 
      network only. An international CUG has significance across 
      network boundaries."
   DEFVAL     { national }
::= { mscTraceRcvrX25DnaCugCugOptionsEntry 1 }

mscTraceRcvrX25DnaCugDnic OBJECT-TYPE
   SYNTAX     DigitString (SIZE (4))
   ACCESS     read-write
   STATUS     mandatory
   DESCRIPTION
     "This attribute specifies the Data Network ID Code of the network 
      that is administering the international CUG. This attribute is not 
      used for a national CUG and should be left at its default value.
      The dnic value is not an arbitrary number. It is assigned by 
      international agreement and controlled by ITU-T."
   DEFVAL     { '30303030'H }  -- "0000"
::= { mscTraceRcvrX25DnaCugCugOptionsEntry 2 }

mscTraceRcvrX25DnaCugInterlockCode OBJECT-TYPE
   SYNTAX     Unsigned32 (0..65535)
   ACCESS     read-write
   STATUS     mandatory
   DESCRIPTION
     "This attribute specifies a numeric identifier of a national or 
      international closed user group. It is an arbitrary number. This 
      attribute may also be called CUG in some descriptions. Dnas 
      defined with this number can only make calls to Dnas defined with 
      the same interlockCode."
   DEFVAL     { 0 }
::= { mscTraceRcvrX25DnaCugCugOptionsEntry 3 }

mscTraceRcvrX25DnaCugPreferential OBJECT-TYPE
   SYNTAX     INTEGER  {
                 no(0),
                 yes(1) }
   ACCESS     read-only
   STATUS     mandatory
   DESCRIPTION
     "This attribute specifies that this Cug is to be used on all outgoing 
      calls to the X.25 trace receiver."
   DEFVAL     { yes }
::= { mscTraceRcvrX25DnaCugCugOptionsEntry 4 }

mscTraceRcvrX25DnaCugOutCalls OBJECT-TYPE
   SYNTAX     INTEGER  {
                 disallowed(0),
                 allowed(1) }
   ACCESS     read-only
   STATUS     mandatory
   DESCRIPTION
     "This attribute specifies that outgoing calls (from the DTE into the 
      network) can be made using this particular Cug."
   DEFVAL     { allowed }
::= { mscTraceRcvrX25DnaCugCugOptionsEntry 5 }

mscTraceRcvrX25DnaCugIncCalls OBJECT-TYPE
   SYNTAX     INTEGER  {
                 disallowed(0),
                 allowed(1) }
   ACCESS     read-only
   STATUS     mandatory
   DESCRIPTION
     "This attribute specifies that incoming calls (from the network to the 
      DTE) cannot be accepted using this Cug."
   DEFVAL     { disallowed }
::= { mscTraceRcvrX25DnaCugCugOptionsEntry 6 }

mscTraceRcvrX25DnaCugPrivileged OBJECT-TYPE
   SYNTAX     INTEGER  {
                 no(0),
                 yes(1) }
   ACCESS     read-write
   STATUS     mandatory
   DESCRIPTION
     "This attribute specifies that this Cug is privileged. For a call 
      between two closed user group Dnas to connect, at least one Dna 
      must have a privileged Cug."
   DEFVAL     { yes }
::= { mscTraceRcvrX25DnaCugCugOptionsEntry 7 }


-- Trace Rcvr/<string> X25 DirectCall
-- This component defines direct call options for the call to the X.25 
-- trace receiver. The connection is initiated on receipt of a Start 
-- FrUni/n Trace command.

mscTraceRcvrX25Dc OBJECT IDENTIFIER ::= { mscTraceRcvrX25 3 }



mscTraceRcvrX25DcRowStatusTable OBJECT-TYPE
   SYNTAX     SEQUENCE OF MscTraceRcvrX25DcRowStatusEntry
   ACCESS     not-accessible
   STATUS     mandatory
   DESCRIPTION
     "This entry controls the addition and deletion of 
      mscTraceRcvrX25Dc components."
::= { mscTraceRcvrX25Dc 1 }

mscTraceRcvrX25DcRowStatusEntry OBJECT-TYPE
   SYNTAX     MscTraceRcvrX25DcRowStatusEntry
   ACCESS     not-accessible
   STATUS     mandatory
   DESCRIPTION
     "A single entry in the table represents a single 
      mscTraceRcvrX25Dc component."
   INDEX {
      mscTraceIndex,
      mscTraceRcvrIndex,
      mscTraceRcvrX25Index,
      mscTraceRcvrX25DcIndex }
::= { mscTraceRcvrX25DcRowStatusTable 1 }

MscTraceRcvrX25DcRowStatusEntry ::= SEQUENCE {
   mscTraceRcvrX25DcRowStatus
      RowStatus,
   mscTraceRcvrX25DcComponentName
      DisplayString,
   mscTraceRcvrX25DcStorageType
      StorageType,
   mscTraceRcvrX25DcIndex
      NonReplicated }

mscTraceRcvrX25DcRowStatus OBJECT-TYPE
   SYNTAX     RowStatus 
   ACCESS     read-only
   STATUS     mandatory
   DESCRIPTION
     "This variable is used as the basis for SNMP naming of
      mscTraceRcvrX25Dc components.
      These components cannot be added nor deleted."
::= { mscTraceRcvrX25DcRowStatusEntry 1 }

mscTraceRcvrX25DcComponentName OBJECT-TYPE
   SYNTAX     DisplayString 
   ACCESS     read-only
   STATUS     mandatory
   DESCRIPTION
     "This variable provides the component's string name for
      use with the ASCII Console Interface"
::= { mscTraceRcvrX25DcRowStatusEntry 2 }

mscTraceRcvrX25DcStorageType OBJECT-TYPE
   SYNTAX     StorageType 
   ACCESS     read-only
   STATUS     mandatory
   DESCRIPTION
     "This variable represents the storage type value for the
      mscTraceRcvrX25Dc tables."
::= { mscTraceRcvrX25DcRowStatusEntry 4 }

mscTraceRcvrX25DcIndex OBJECT-TYPE
   SYNTAX     NonReplicated 
   ACCESS     not-accessible
   STATUS     mandatory
   DESCRIPTION
     "This variable represents the index for the mscTraceRcvrX25Dc tables."
::= { mscTraceRcvrX25DcRowStatusEntry 10 }

mscTraceRcvrX25DcOptionsTable OBJECT-TYPE
   SYNTAX     SEQUENCE OF MscTraceRcvrX25DcOptionsEntry
   ACCESS     not-accessible
   STATUS     mandatory
   DESCRIPTION
     "The Options group defines attributes associated with the SVC direct 
      call."
::= { mscTraceRcvrX25Dc 10 }

mscTraceRcvrX25DcOptionsEntry OBJECT-TYPE
   SYNTAX     MscTraceRcvrX25DcOptionsEntry
   ACCESS     not-accessible
   STATUS     mandatory
   DESCRIPTION
     "An entry in the mscTraceRcvrX25DcOptionsTable."
   INDEX {
      mscTraceIndex,
      mscTraceRcvrIndex,
      mscTraceRcvrX25Index,
      mscTraceRcvrX25DcIndex }
::= { mscTraceRcvrX25DcOptionsTable 1 }

MscTraceRcvrX25DcOptionsEntry ::= SEQUENCE {
   mscTraceRcvrX25DcRemoteNpi
      INTEGER,
   mscTraceRcvrX25DcRemoteDna
      DigitString,
   mscTraceRcvrX25DcType
      INTEGER,
   mscTraceRcvrX25DcUserData
      HexString }

mscTraceRcvrX25DcRemoteNpi OBJECT-TYPE
   SYNTAX     INTEGER  {
                 x121(0),
                 e164(1) }
   ACCESS     read-write
   STATUS     mandatory
   DESCRIPTION
     "This attribute indicates the numbering plan used for the remoteDna."
   DEFVAL     { x121 }
::= { mscTraceRcvrX25DcOptionsEntry 3 }

mscTraceRcvrX25DcRemoteDna OBJECT-TYPE
   SYNTAX     DigitString (SIZE (1..15))
   ACCESS     read-write
   STATUS     mandatory
   DESCRIPTION
     "This attribute specifies the Data Network Address of the remote end 
      of the connection. This is the DNA of the X.25 trace receiver which 
      will receive the trace data."
::= { mscTraceRcvrX25DcOptionsEntry 4 }

mscTraceRcvrX25DcType OBJECT-TYPE
   SYNTAX     INTEGER  {
                 switched(0),
                 permanentMaster(1),
                 permanentSlave(2),
                 permanentBackupSlave(3) }
   ACCESS     read-only
   STATUS     mandatory
   DESCRIPTION
     "This attribute specifies the type of call as switched. For a switched 
      call, no information is defined at the remote end about the local end 
      of the connection."
   DEFVAL     { switched }
::= { mscTraceRcvrX25DcOptionsEntry 6 }

mscTraceRcvrX25DcUserData OBJECT-TYPE
   SYNTAX     HexString (SIZE (0..16))
   ACCESS     read-write
   STATUS     mandatory
   DESCRIPTION
     "This attribute contains the user data. It is a 0 to 16 byte length string 
      which is appended to the call request packet that is presented to the 
      called (destination) DTE."
   DEFVAL     { ''H }  -- ""
::= { mscTraceRcvrX25DcOptionsEntry 8 }

-- 
-- *** THIS SUBTREE CURRENTLY NOT IMPLEMENTED ***
-- 

-- Trace Session/<n> X25
-- This component identifies the access method used by the receiver of 
-- the trace data as X.25.

mscTraceSessionX25 OBJECT IDENTIFIER ::= { mscTraceSession 2 }



mscTraceSessionX25RowStatusTable OBJECT-TYPE
   SYNTAX     SEQUENCE OF MscTraceSessionX25RowStatusEntry
   ACCESS     not-accessible
   STATUS     mandatory
   DESCRIPTION
     "*** THIS TABLE CURRENTLY NOT IMPLEMENTED ***

      This entry controls the addition and deletion of 
      mscTraceSessionX25 components."
::= { mscTraceSessionX25 1 }

mscTraceSessionX25RowStatusEntry OBJECT-TYPE
   SYNTAX     MscTraceSessionX25RowStatusEntry
   ACCESS     not-accessible
   STATUS     mandatory
   DESCRIPTION
     "A single entry in the table represents a single 
      mscTraceSessionX25 component."
   INDEX {
      mscTraceIndex,
      mscTraceSessionIndex,
      mscTraceSessionX25Index }
::= { mscTraceSessionX25RowStatusTable 1 }

MscTraceSessionX25RowStatusEntry ::= SEQUENCE {
   mscTraceSessionX25RowStatus
      RowStatus,
   mscTraceSessionX25ComponentName
      DisplayString,
   mscTraceSessionX25StorageType
      StorageType,
   mscTraceSessionX25Index
      NonReplicated }

mscTraceSessionX25RowStatus OBJECT-TYPE
   SYNTAX     RowStatus 
   ACCESS     read-only
   STATUS     mandatory
   DESCRIPTION
     "This variable is used as the basis for SNMP naming of
      mscTraceSessionX25 components.
      These components cannot be added nor deleted."
::= { mscTraceSessionX25RowStatusEntry 1 }

mscTraceSessionX25ComponentName OBJECT-TYPE
   SYNTAX     DisplayString 
   ACCESS     read-only
   STATUS     mandatory
   DESCRIPTION
     "This variable provides the component's string name for
      use with the ASCII Console Interface"
::= { mscTraceSessionX25RowStatusEntry 2 }

mscTraceSessionX25StorageType OBJECT-TYPE
   SYNTAX     StorageType 
   ACCESS     read-only
   STATUS     mandatory
   DESCRIPTION
     "This variable represents the storage type value for the
      mscTraceSessionX25 tables."
::= { mscTraceSessionX25RowStatusEntry 4 }

mscTraceSessionX25Index OBJECT-TYPE
   SYNTAX     NonReplicated 
   ACCESS     not-accessible
   STATUS     mandatory
   DESCRIPTION
     "This variable represents the index for the mscTraceSessionX25 tables."
::= { mscTraceSessionX25RowStatusEntry 10 }

-- 
-- *** THIS SUBTREE CURRENTLY NOT IMPLEMENTED ***
-- 

-- ... Vc()
-- This component defines display of general Vc dynamic attributes

mscTraceSessionX25Vc OBJECT IDENTIFIER ::= { mscTraceSessionX25 2 }



mscTraceSessionX25VcRowStatusTable OBJECT-TYPE
   SYNTAX     SEQUENCE OF MscTraceSessionX25VcRowStatusEntry
   ACCESS     not-accessible
   STATUS     mandatory
   DESCRIPTION
     "*** THIS TABLE CURRENTLY NOT IMPLEMENTED ***

      This entry controls the addition and deletion of 
      mscTraceSessionX25Vc components."
::= { mscTraceSessionX25Vc 1 }

mscTraceSessionX25VcRowStatusEntry OBJECT-TYPE
   SYNTAX     MscTraceSessionX25VcRowStatusEntry
   ACCESS     not-accessible
   STATUS     mandatory
   DESCRIPTION
     "A single entry in the table represents a single 
      mscTraceSessionX25Vc component."
   INDEX {
      mscTraceIndex,
      mscTraceSessionIndex,
      mscTraceSessionX25Index,
      mscTraceSessionX25VcIndex }
::= { mscTraceSessionX25VcRowStatusTable 1 }

MscTraceSessionX25VcRowStatusEntry ::= SEQUENCE {
   mscTraceSessionX25VcRowStatus
      RowStatus,
   mscTraceSessionX25VcComponentName
      DisplayString,
   mscTraceSessionX25VcStorageType
      StorageType,
   mscTraceSessionX25VcIndex
      NonReplicated }

mscTraceSessionX25VcRowStatus OBJECT-TYPE
   SYNTAX     RowStatus 
   ACCESS     read-only
   STATUS     mandatory
   DESCRIPTION
     "This variable is used as the basis for SNMP naming of
      mscTraceSessionX25Vc components.
      These components cannot be added nor deleted."
::= { mscTraceSessionX25VcRowStatusEntry 1 }

mscTraceSessionX25VcComponentName OBJECT-TYPE
   SYNTAX     DisplayString 
   ACCESS     read-only
   STATUS     mandatory
   DESCRIPTION
     "This variable provides the component's string name for
      use with the ASCII Console Interface"
::= { mscTraceSessionX25VcRowStatusEntry 2 }

mscTraceSessionX25VcStorageType OBJECT-TYPE
   SYNTAX     StorageType 
   ACCESS     read-only
   STATUS     mandatory
   DESCRIPTION
     "This variable represents the storage type value for the
      mscTraceSessionX25Vc tables."
::= { mscTraceSessionX25VcRowStatusEntry 4 }

mscTraceSessionX25VcIndex OBJECT-TYPE
   SYNTAX     NonReplicated 
   ACCESS     not-accessible
   STATUS     mandatory
   DESCRIPTION
     "This variable represents the index for the mscTraceSessionX25Vc tables."
::= { mscTraceSessionX25VcRowStatusEntry 10 }

mscTraceSessionX25VcCadTable OBJECT-TYPE
   SYNTAX     SEQUENCE OF MscTraceSessionX25VcCadEntry
   ACCESS     not-accessible
   STATUS     mandatory
   DESCRIPTION
     "*** THIS TABLE CURRENTLY NOT IMPLEMENTED ***

      This group represents operational call data related to General Vc. It 
      can be displayed only for General Vc which is created by 
      application."
::= { mscTraceSessionX25Vc 10 }

mscTraceSessionX25VcCadEntry OBJECT-TYPE
   SYNTAX     MscTraceSessionX25VcCadEntry
   ACCESS     not-accessible
   STATUS     mandatory
   DESCRIPTION
     "An entry in the mscTraceSessionX25VcCadTable."
   INDEX {
      mscTraceIndex,
      mscTraceSessionIndex,
      mscTraceSessionX25Index,
      mscTraceSessionX25VcIndex }
::= { mscTraceSessionX25VcCadTable 1 }

MscTraceSessionX25VcCadEntry ::= SEQUENCE {
   mscTraceSessionX25VcType
      INTEGER,
   mscTraceSessionX25VcState
      INTEGER,
   mscTraceSessionX25VcPreviousState
      INTEGER,
   mscTraceSessionX25VcDiagnosticCode
      Unsigned32,
   mscTraceSessionX25VcPreviousDiagnosticCode
      Unsigned32,
   mscTraceSessionX25VcCalledNpi
      INTEGER,
   mscTraceSessionX25VcCalledDna
      DigitString,
   mscTraceSessionX25VcCalledLcn
      Unsigned32,
   mscTraceSessionX25VcCallingNpi
      INTEGER,
   mscTraceSessionX25VcCallingDna
      DigitString,
   mscTraceSessionX25VcCallingLcn
      Unsigned32,
   mscTraceSessionX25VcAccountingEnabled
      INTEGER,
   mscTraceSessionX25VcFastSelectCall
      INTEGER,
   mscTraceSessionX25VcLocalRxPktSize
      INTEGER,
   mscTraceSessionX25VcLocalTxPktSize
      INTEGER,
   mscTraceSessionX25VcLocalTxWindowSize
      Unsigned32,
   mscTraceSessionX25VcLocalRxWindowSize
      Unsigned32,
   mscTraceSessionX25VcPathReliability
      INTEGER,
   mscTraceSessionX25VcAccountingEnd
      INTEGER,
   mscTraceSessionX25VcPriority
      INTEGER,
   mscTraceSessionX25VcSegmentSize
      Unsigned32,
   mscTraceSessionX25VcSubnetTxPktSize
      INTEGER,
   mscTraceSessionX25VcSubnetTxWindowSize
      Unsigned32,
   mscTraceSessionX25VcSubnetRxPktSize
      INTEGER,
   mscTraceSessionX25VcSubnetRxWindowSize
      Unsigned32,
   mscTraceSessionX25VcMaxSubnetPktSize
      Unsigned32,
   mscTraceSessionX25VcTransferPriorityToNetwork
      INTEGER,
   mscTraceSessionX25VcTransferPriorityFromNetwork
      INTEGER }

mscTraceSessionX25VcType OBJECT-TYPE
   SYNTAX     INTEGER  {
                 svc(0),
                 pvc(1) }
   ACCESS     read-only
   STATUS     mandatory
   DESCRIPTION
     "This attribute displays the type of call, pvc or svc. type is provided 
      at provisioning time."
::= { mscTraceSessionX25VcCadEntry 1 }

mscTraceSessionX25VcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { mscTraceSessionX25VcCadEntry 2 }

mscTraceSessionX25VcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { mscTraceSessionX25VcCadEntry 3 }

mscTraceSessionX25VcDiagnosticCode OBJECT-TYPE
   SYNTAX     Unsigned32 (0..255)
   ACCESS     read-only
   STATUS     mandatory
   DESCRIPTION
     "This attribute displays the internal substate of call control. It is used 
      to further refine state of call processing."
::= { mscTraceSessionX25VcCadEntry 4 }

mscTraceSessionX25VcPreviousDiagnosticCode OBJECT-TYPE
   SYNTAX     Unsigned32 (0..255)
   ACCESS     read-only
   STATUS     mandatory
   DESCRIPTION
     "This attribute displays the internal substate of call control. It is used 
      to further refine state of call processing."
::= { mscTraceSessionX25VcCadEntry 5 }

mscTraceSessionX25VcCalledNpi OBJECT-TYPE
   SYNTAX     INTEGER  {
                 x121(0),
                 e164(1) }
   ACCESS     read-only
   STATUS     mandatory
   DESCRIPTION
     "This attribute displays the Numbering Plan Indicator (NPI) of the 
      called end."
::= { mscTraceSessionX25VcCadEntry 6 }

mscTraceSessionX25VcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { mscTraceSessionX25VcCadEntry 7 }

mscTraceSessionX25VcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { mscTraceSessionX25VcCadEntry 8 }

mscTraceSessionX25VcCallingNpi OBJECT-TYPE
   SYNTAX     INTEGER  {
                 x121(0),
                 e164(1) }
   ACCESS     read-only
   STATUS     mandatory
   DESCRIPTION
     "This attribute displays the Numbering Plan Indicator (NPI) of the 
      calling end."
::= { mscTraceSessionX25VcCadEntry 9 }

mscTraceSessionX25VcCallingDna OBJECT-TYPE
   SYNTAX     DigitString (SIZE (1..15))
   ACCESS     read-only
   STATUS     mandatory
   DESCRIPTION
     "This attribute displays the Data Network Address (Dna) of the 
      calling end."
::= { mscTraceSessionX25VcCadEntry 10 }

mscTraceSessionX25VcCallingLcn OBJECT-TYPE
   SYNTAX     Unsigned32 (1..65535)
   ACCESS     read-only
   STATUS     mandatory
   DESCRIPTION
     "This attribute displays the Logical Channel Number of the calling 
      end."
::= { mscTraceSessionX25VcCadEntry 11 }

mscTraceSessionX25VcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { mscTraceSessionX25VcCadEntry 12 }

mscTraceSessionX25VcFastSelectCall OBJECT-TYPE
   SYNTAX     INTEGER  {
                 no(0),
                 yes(1) }
   ACCESS     read-only
   STATUS     mandatory
   DESCRIPTION
     "This attribute displays that this is a fast select call."
::= { mscTraceSessionX25VcCadEntry 13 }

mscTraceSessionX25VcLocalRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { mscTraceSessionX25VcCadEntry 14 }

mscTraceSessionX25VcLocalTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { mscTraceSessionX25VcCadEntry 15 }

mscTraceSessionX25VcLocalTxWindowSize OBJECT-TYPE
   SYNTAX     Unsigned32 (0..127)
   ACCESS     read-only
   STATUS     mandatory
   DESCRIPTION
     "This attribute displays the send window size provided on incoming 
      call packets or the default when a call request packet does not 
      explicitly provide the window size."
::= { mscTraceSessionX25VcCadEntry 16 }

mscTraceSessionX25VcLocalRxWindowSize OBJECT-TYPE
   SYNTAX     Unsigned32 (0..127)
   ACCESS     read-only
   STATUS     mandatory
   DESCRIPTION
     "This attribute displays the receive window size provided on 
      incoming call packets or the default when a call request does not 
      explicitly provide the window sizes."
::= { mscTraceSessionX25VcCadEntry 17 }

mscTraceSessionX25VcPathReliability OBJECT-TYPE
   SYNTAX     INTEGER  {
                 high(0),
                 normal(1) }
   ACCESS     read-only
   STATUS     mandatory
   DESCRIPTION
     "This attribute displays the path reliability."
::= { mscTraceSessionX25VcCadEntry 19 }

mscTraceSessionX25VcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { mscTraceSessionX25VcCadEntry 20 }

mscTraceSessionX25VcPriority OBJECT-TYPE
   SYNTAX     INTEGER  {
                 normal(0),
                 high(1) }
   ACCESS     read-only
   STATUS     mandatory
   DESCRIPTION
     "This attribute displays whether the call is a normal or a high 
      priority call."
::= { mscTraceSessionX25VcCadEntry 21 }

mscTraceSessionX25VcSegmentSize OBJECT-TYPE
   SYNTAX     Unsigned32 (0..4096)
   ACCESS     read-only
   STATUS     mandatory
   DESCRIPTION
     "This attribute displays the segment size (in bytes) used on the call. 
      It is used to calculate the number of segments transmitted and 
      received."
::= { mscTraceSessionX25VcCadEntry 22 }

mscTraceSessionX25VcSubnetTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of the data packets 
      on this Vc."
::= { mscTraceSessionX25VcCadEntry 23 }

mscTraceSessionX25VcSubnetTxWindowSize OBJECT-TYPE
   SYNTAX     Unsigned32 (0..4096)
   ACCESS     read-only
   STATUS     mandatory
   DESCRIPTION
     "This attribute displays the current send window size of Vc."
::= { mscTraceSessionX25VcCadEntry 24 }

mscTraceSessionX25VcSubnetRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of receive packets."
::= { mscTraceSessionX25VcCadEntry 25 }

mscTraceSessionX25VcSubnetRxWindowSize OBJECT-TYPE
   SYNTAX     Unsigned32 (0..4096)
   ACCESS     read-only
   STATUS     mandatory
   DESCRIPTION
     "This attribute displays the receive window size provided on 
      incoming call packets and to the default when a call request does 
      not explicitly provide the window sizes."
::= { mscTraceSessionX25VcCadEntry 26 }

mscTraceSessionX25VcMaxSubnetPktSize OBJECT-TYPE
   SYNTAX     Unsigned32 (0..4096)
   ACCESS     read-only
   STATUS     mandatory
   DESCRIPTION
     "This attribute displays the maximum packet size allowed on Vc."
::= { mscTraceSessionX25VcCadEntry 27 }

mscTraceSessionX25VcTransferPriorityToNetwork OBJECT-TYPE
   SYNTAX     INTEGER  {
                 normal(0),
                 high(9) }
   ACCESS     read-only
   STATUS     mandatory
   DESCRIPTION
     "This attribute displays the priority in which data is transferred to the 
      network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput).
      
      When the transfer priority is set at high, the trunk queue is set to 
      high, the routing metric is set to delay.
      
      When the transfer priority is set at normal, the trunk queue is set to 
      normal, the routing metric is set to throughput."
::= { mscTraceSessionX25VcCadEntry 28 }

mscTraceSessionX25VcTransferPriorityFromNetwork OBJECT-TYPE
   SYNTAX     INTEGER  {
                 normal(0),
                 high(9) }
   ACCESS     read-only
   STATUS     mandatory
   DESCRIPTION
     "This attribute displays the priority in which data is transferred from 
      the network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, and the trunk queue is set 
      to high, the routing metric is set to delay.
      
      When the transfer priority is set at normal, the trunk queue is set to 
      normal, and the routing metric is set to throughput."
::= { mscTraceSessionX25VcCadEntry 29 }

mscTraceSessionX25VcIntdTable OBJECT-TYPE
   SYNTAX     SEQUENCE OF MscTraceSessionX25VcIntdEntry
   ACCESS     not-accessible
   STATUS     mandatory
   DESCRIPTION
     "*** THIS TABLE CURRENTLY NOT IMPLEMENTED ***

      This group defines display of interval data collected by Vc. Data in 
      this group is variable and may depend on time when this display 
      command is issued."
::= { mscTraceSessionX25Vc 11 }

mscTraceSessionX25VcIntdEntry OBJECT-TYPE
   SYNTAX     MscTraceSessionX25VcIntdEntry
   ACCESS     not-accessible
   STATUS     mandatory
   DESCRIPTION
     "An entry in the mscTraceSessionX25VcIntdTable."
   INDEX {
      mscTraceIndex,
      mscTraceSessionIndex,
      mscTraceSessionX25Index,
      mscTraceSessionX25VcIndex }
::= { mscTraceSessionX25VcIntdTable 1 }

MscTraceSessionX25VcIntdEntry ::= SEQUENCE {
   mscTraceSessionX25VcCallReferenceNumber
      Hex,
   mscTraceSessionX25VcElapsedTimeTillNow
      Unsigned32,
   mscTraceSessionX25VcSegmentsRx
      Unsigned32,
   mscTraceSessionX25VcSegmentsSent
      Unsigned32,
   mscTraceSessionX25VcStartTime
      EnterpriseDateAndTime,
   mscTraceSessionX25VcCallReferenceNumberDecimal
      Unsigned32 }

mscTraceSessionX25VcCallReferenceNumber OBJECT-TYPE
   SYNTAX     Hex (0..16777215)
   ACCESS     read-only
   STATUS     obsolete
   DESCRIPTION
     "This attribute is obsolete. It is replaced by the callReferenceNumber 
      attribute to display the call reference number in decimal. The 
      SNMP reference for the callReferenceNumber attribute is 
      callReferenceNumberDecimal."
::= { mscTraceSessionX25VcIntdEntry 1 }

mscTraceSessionX25VcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { mscTraceSessionX25VcIntdEntry 2 }

mscTraceSessionX25VcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { mscTraceSessionX25VcIntdEntry 3 }

mscTraceSessionX25VcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { mscTraceSessionX25VcIntdEntry 4 }

mscTraceSessionX25VcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { mscTraceSessionX25VcIntdEntry 5 }

mscTraceSessionX25VcCallReferenceNumberDecimal OBJECT-TYPE
   SYNTAX     Unsigned32 (0..4294967295)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { mscTraceSessionX25VcIntdEntry 7 }

mscTraceSessionX25VcStatsTable OBJECT-TYPE
   SYNTAX     SEQUENCE OF MscTraceSessionX25VcStatsEntry
   ACCESS     not-accessible
   STATUS     mandatory
   DESCRIPTION
     "*** THIS TABLE CURRENTLY NOT IMPLEMENTED ***

      ... Statistics(Stats)
      This group defines general attributes collected by general Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods."
::= { mscTraceSessionX25Vc 12 }

mscTraceSessionX25VcStatsEntry OBJECT-TYPE
   SYNTAX     MscTraceSessionX25VcStatsEntry
   ACCESS     not-accessible
   STATUS     mandatory
   DESCRIPTION
     "An entry in the mscTraceSessionX25VcStatsTable."
   INDEX {
      mscTraceIndex,
      mscTraceSessionIndex,
      mscTraceSessionX25Index,
      mscTraceSessionX25VcIndex }
::= { mscTraceSessionX25VcStatsTable 1 }

MscTraceSessionX25VcStatsEntry ::= SEQUENCE {
   mscTraceSessionX25VcAckStackingTimeouts
      Unsigned32,
   mscTraceSessionX25VcOutOfRangeFrmFromSubnet
      Unsigned32,
   mscTraceSessionX25VcDuplicatesFromSubnet
      Unsigned32,
   mscTraceSessionX25VcFrmRetryTimeouts
      Unsigned32,
   mscTraceSessionX25VcPeakRetryQueueSize
      Unsigned32,
   mscTraceSessionX25VcPeakOoSeqQueueSize
      Unsigned32,
   mscTraceSessionX25VcPeakOoSeqFrmForwarded
      Unsigned32,
   mscTraceSessionX25VcPeakStackedAcksRx
      Unsigned32,
   mscTraceSessionX25VcSubnetRecoveries
      Unsigned32,
   mscTraceSessionX25VcWindowClosuresToSubnet
      Unsigned32,
   mscTraceSessionX25VcWindowClosuresFromSubnet
      Unsigned32,
   mscTraceSessionX25VcWrTriggers
      Unsigned32 }

mscTraceSessionX25VcAckStackingTimeouts OBJECT-TYPE
   SYNTAX     Unsigned32 (0..5000)
   ACCESS     read-only
   STATUS     mandatory
   DESCRIPTION
     "This attribute counts the number of ack stacking timer expiries.
      It is used as an indicator of the acknowledgment behavior across the 
      subnet when ack stacking is in effect. If it expires often, usually this 
      means end users will experience longer delay.
      The ack stacking timer specifies how long the Vc will wait before 
      finally sending the subnet acknowledgment. if this attribute is set to 
      a value of 0, then the Vc will automatically return acknowledgment 
      packets without delay. If this attribute is set to a value other than 
      zero, then the Vc will wait for this amount of time in an attempt to 
      piggyback the acknowledgment packet on another credit or data 
      packet. If the Vc cannot piggyback the acknowledgment packet 
      within this time, then the packet is returned without piggybacking."
::= { mscTraceSessionX25VcStatsEntry 1 }

mscTraceSessionX25VcOutOfRangeFrmFromSubnet OBJECT-TYPE
   SYNTAX     Unsigned32 (0..5000)
   ACCESS     read-only
   STATUS     mandatory
   DESCRIPTION
     "This attribute counts the number of subnet frames discarded due to 
      the sequence number being out of range.
      Two Categories apply for the General Vc
      1) lost Acks (previous Range)
      2) unexpected Packets (next Range)
      Vc internally maintains its own sequence number of packet order 
      and sequencing. Due to packet retransmission, Vc may receive 
      duplicate packets that have the same Vc internal sequence number. 
      Only 1 copy is accepted by the Vc and other copies of the same 
      packets are detected through this count. This attribute can be used to 
      record the frequency of packet retransmission due to Vc and other 
      part of the subnet."
::= { mscTraceSessionX25VcStatsEntry 2 }

mscTraceSessionX25VcDuplicatesFromSubnet OBJECT-TYPE
   SYNTAX     Unsigned32 (0..5000)
   ACCESS     read-only
   STATUS     mandatory
   DESCRIPTION
     "This attribute counts the number of subnet packets discarded due to 
      duplication. It is used to detect software error fault or duplication 
      caused by retransmitting."
::= { mscTraceSessionX25VcStatsEntry 3 }

mscTraceSessionX25VcFrmRetryTimeouts OBJECT-TYPE
   SYNTAX     Unsigned32 (0..5000)
   ACCESS     read-only
   STATUS     mandatory
   DESCRIPTION
     "This attribute counts the number of frames which have 
      retransmission time-out.
      If packets from Vc into the subnet are discarded by the subnet, the 
      source Vc will not receive any acknowledgment. The retransmission 
      timer then expires and packets will be retransmitted again. Note that 
      the Vc idle probe may be retransmitted and is included in this count. 
      This statistics does not show the distribution of how many times 
      packets are retransmitted (e.g. first retransmission results in 
      successful packet forwarding)."
::= { mscTraceSessionX25VcStatsEntry 4 }

mscTraceSessionX25VcPeakRetryQueueSize OBJECT-TYPE
   SYNTAX     Unsigned32 (0..5000)
   ACCESS     read-only
   STATUS     mandatory
   DESCRIPTION
     "This attribute indicates the peak size of the retransmission queue.
      This attribute is used as an indicator of the acknowledgment 
      behavior across the subnet. It records the largest body of 
      unacknowledged packets."
::= { mscTraceSessionX25VcStatsEntry 5 }

mscTraceSessionX25VcPeakOoSeqQueueSize OBJECT-TYPE
   SYNTAX     Unsigned32 (0..5000)
   ACCESS     read-only
   STATUS     mandatory
   DESCRIPTION
     "This attribute indicates the peak size of the out of sequence queue.
      This attribute is used as an indicator of the sequencing behavior 
      across the subnet. It records the largest body of out of sequence 
      packets."
::= { mscTraceSessionX25VcStatsEntry 6 }

mscTraceSessionX25VcPeakOoSeqFrmForwarded OBJECT-TYPE
   SYNTAX     Unsigned32 (0..5000)
   ACCESS     read-only
   STATUS     mandatory
   DESCRIPTION
     "This attribute indicates the peak size of the sequence packet queue.
      This attribute is used as an indicator of the sequencing behavior 
      across the subnet. It records the largest body of out of sequence 
      packets, which by the receipt of an expected packet have been 
      transformed to expected packets. The number of times this peak is 
      reached is not recorded as it is traffic dependent."
::= { mscTraceSessionX25VcStatsEntry 7 }

mscTraceSessionX25VcPeakStackedAcksRx OBJECT-TYPE
   SYNTAX     Unsigned32 (0..5000)
   ACCESS     read-only
   STATUS     mandatory
   DESCRIPTION
     "This attribute indicates the peak size of wait acks.
      This attribute is used as an indicator of the acknowledgment 
      behavior across the subnet. It records the largest collective 
      acknowledgment."
::= { mscTraceSessionX25VcStatsEntry 8 }

mscTraceSessionX25VcSubnetRecoveries OBJECT-TYPE
   SYNTAX     Unsigned32 (0..5000)
   ACCESS     read-only
   STATUS     mandatory
   DESCRIPTION
     "This attribute counts the number of successful Vc recovery attempts.
      This attribute is used as an indicator of how many times the Vc path 
      is broken but can be recovered. This attribute is useful to record the 
      number of network path failures."
::= { mscTraceSessionX25VcStatsEntry 9 }

mscTraceSessionX25VcWindowClosuresToSubnet OBJECT-TYPE
   SYNTAX     Unsigned32 (0..5000)
   ACCESS     read-only
   STATUS     mandatory
   DESCRIPTION
     "This attribute counts the number of window closures to subnet.
      A packet may have been sent into the subnet but its 
      acknowledgment from the remote Vc has not yet been received. 
      This is a 8 bit sequence number.This number is useful in detecting 
      whether the Vc is sending any packet into the subnet."
::= { mscTraceSessionX25VcStatsEntry 10 }

mscTraceSessionX25VcWindowClosuresFromSubnet OBJECT-TYPE
   SYNTAX     Unsigned32 (0..5000)
   ACCESS     read-only
   STATUS     mandatory
   DESCRIPTION
     "This attribute counts the number of window closures from subnet.
      This attribute is useful in detecting whether the Vc is receiving any 
      packet from the subnet."
::= { mscTraceSessionX25VcStatsEntry 11 }

mscTraceSessionX25VcWrTriggers OBJECT-TYPE
   SYNTAX     Unsigned32 (0..5000)
   ACCESS     read-only
   STATUS     mandatory
   DESCRIPTION
     "This attribute displays the number of times the Vc stays within the 
      W-R region. The W-R region is a value used to determined the 
      timing of credit transmission. Should the current window size be 
      beneath this value, the credits will be transmitted immediately. 
      Otherwise, they will be transmitted later with actual data. The 
      wrTriggers statistic is therefore used to analyze the flow control and 
      credit mechanism."
::= { mscTraceSessionX25VcStatsEntry 12 }




-- 
-- Version and Compliance statements
-- 



-- Object-Group Statement:
-- A list of all current accessible leaf objects.

-- OBJECTS { mscTraceRcvrX25StorageType,
--           mscTraceSessionX25VcWindowClosuresToSubnet,
--           mscTraceSessionX25VcCalledLcn,
--           mscTraceRcvrX25DnaCugComponentName,
--           mscTraceRcvrX25DnaCugDnic,
--           mscTraceSessionX25VcSubnetRxWindowSize,
--           mscTraceSessionX25VcOutOfRangeFrmFromSubnet,
--           mscTraceRcvrX25DnaDefaultRecvFrmNetworkThruputClass,
--           mscTraceSessionX25VcSegmentsRx,
--           mscTraceRcvrX25DnaCugInterlockCode,
--           mscTraceRcvrX25DnaDefaultSendToNetworkPacketSize,
--           mscTraceRcvrX25DnaComponentName,
--           mscTraceSessionX25VcCalledNpi,
--           mscTraceSessionX25VcType,
--           mscTraceSessionX25VcAccountingEnabled,
--           mscTraceSessionX25ComponentName,
--           mscTraceSessionX25VcSegmentsSent,
--           mscTraceSessionX25VcSubnetTxPktSize,
--           mscTraceRcvrX25DnaCugPrivileged,
--           mscTraceSessionX25VcTransferPriorityToNetwork,
--           mscTraceRcvrX25DnaPacketSizes,
--           mscTraceSessionX25VcPreviousState,
--           mscTraceRcvrX25DcRowStatus,
--           mscTraceSessionX25VcSubnetRecoveries,
--           mscTraceRcvrX25DnaOutPathReliabilityOverRide,
--           mscTraceSessionX25VcAckStackingTimeouts,
--           mscTraceSessionX25VcRowStatus,
--           mscTraceSessionX25VcLocalTxPktSize,
--           mscTraceRcvrX25DcRemoteDna,
--           mscTraceSessionX25VcFastSelectCall,
--           mscTraceRcvrX25DnaOutPathReliabilitySignal,
--           mscTraceRcvrX25DcRemoteNpi,
--           mscTraceRcvrX25RowStatus,
--           mscTraceSessionX25VcStartTime,
--           mscTraceSessionX25VcSegmentSize,
--           mscTraceRcvrX25DnaCugPreferential,
--           mscTraceRcvrX25DnaOutAccess,
--           mscTraceRcvrX25DnaDefaultSendToNetworkWindowSize,
--           mscTraceSessionX25VcElapsedTimeTillNow,
--           mscTraceSessionX25VcAccountingEnd,
--           mscTraceRcvrX25DcComponentName,
--           mscTraceSessionX25VcPriority,
--           mscTraceRcvrX25DnaCugIncCalls,
--           mscTraceRcvrX25DnaDefaultRecvFrmNetworkPacketSize,
--           mscTraceSessionX25VcCallingDna,
--           mscTraceSessionX25VcComponentName,
--           mscTraceRcvrX25DnaNumberingPlanIndicator,
--           mscTraceSessionX25VcPeakOoSeqQueueSize,
--           mscTraceSessionX25VcCalledDna,
--           mscTraceSessionX25VcCallingLcn,
--           mscTraceSessionX25VcCallingNpi,
--           mscTraceSessionX25VcPeakRetryQueueSize,
--           mscTraceSessionX25VcPeakOoSeqFrmForwarded,
--           mscTraceSessionX25VcSubnetTxWindowSize,
--           mscTraceSessionX25VcFrmRetryTimeouts,
--           mscTraceSessionX25VcLocalRxPktSize,
--           mscTraceRcvrX25DnaCugStorageType,
--           mscTraceSessionX25VcSubnetRxPktSize,
--           mscTraceRcvrX25DnaDataNetworkAddress,
--           mscTraceRcvrX25DnaCugOutCalls,
--           mscTraceSessionX25VcPathReliability,
--           mscTraceSessionX25VcStorageType,
--           mscTraceSessionX25VcWrTriggers,
--           mscTraceRcvrX25DnaCugFormat,
--           mscTraceRcvrX25DcUserData,
--           mscTraceSessionX25VcTransferPriorityFromNetwork,
--           mscTraceRcvrX25DnaStorageType,
--           mscTraceRcvrX25DnaCugType,
--           mscTraceSessionX25StorageType,
--           mscTraceRcvrX25DnaOutIntl,
--           mscTraceRcvrX25DnaOutDefaultPriority,
--           mscTraceRcvrX25DnaOutDefaultPathReliability,
--           mscTraceRcvrX25DnaIncCalls,
--           mscTraceRcvrX25DnaDefaultSendToNetworkThruputClass,
--           mscTraceRcvrX25ComponentName,
--           mscTraceRcvrX25DnaOutCalls,
--           mscTraceRcvrX25DcType,
--           mscTraceSessionX25VcMaxSubnetPktSize,
--           mscTraceRcvrX25DnaCugRowStatus,
--           mscTraceSessionX25VcDuplicatesFromSubnet,
--           mscTraceSessionX25VcLocalTxWindowSize,
--           mscTraceSessionX25VcState,
--           mscTraceRcvrX25DnaPacketSizeNegotiation,
--           mscTraceSessionX25VcPeakStackedAcksRx,
--           mscTraceSessionX25VcCallReferenceNumberDecimal,
--           mscTraceRcvrX25DnaDefaultRecvFrmNetworkWindowSize,
--           mscTraceSessionX25VcDiagnosticCode,
--           mscTraceSessionX25VcPreviousDiagnosticCode,
--           mscTraceRcvrX25DnaRowStatus,
--           mscTraceSessionX25VcWindowClosuresFromSubnet,
--           mscTraceRcvrX25DcStorageType,
--           mscTraceSessionX25RowStatus,
--           mscTraceSessionX25VcLocalRxWindowSize }
-- STATUS  mandatory
-- DESCRIPTION
--   "A list of all current accessible leaf objects."

x25TraceRcvrGroup OBJECT IDENTIFIER ::= { x25TraceRcvrMIB 1 }
x25TraceRcvrGroupCA OBJECT IDENTIFIER ::= { x25TraceRcvrGroup 1 }
x25TraceRcvrGroupCA02 OBJECT IDENTIFIER ::= { x25TraceRcvrGroupCA 3 }
x25TraceRcvrGroupCA02A OBJECT IDENTIFIER ::= { x25TraceRcvrGroupCA02 2 }



-- Agent-Capabilities Statement:

-- PRODUCT-RELEASE "MscPassport Release 1.2 X25TraceRcvr."
-- STATUS          mandatory
-- DESCRIPTION     "Carrier Passport X25TraceRcvr MIB: MIB Version CA02A,
--                  Software Version CA02S9C."
-- SUPPORTS        Nortel-MsCarrier-MscPassport-X25TraceRcvrMIB
--    INCLUDES     { x25TraceRcvrGroupCA02A }

x25TraceRcvrCapabilities OBJECT IDENTIFIER ::= { x25TraceRcvrMIB 3 }
x25TraceRcvrCapabilitiesCA OBJECT IDENTIFIER ::= { x25TraceRcvrCapabilities 1 }
x25TraceRcvrCapabilitiesCA02 OBJECT IDENTIFIER ::= { x25TraceRcvrCapabilitiesCA 3 }
x25TraceRcvrCapabilitiesCA02A OBJECT IDENTIFIER ::= { x25TraceRcvrCapabilitiesCA02 2 }





END
