SONICWALL-SSL DEFINITIONS ::= BEGIN

IMPORTS
    enterprises, IpAddress, Integer32,
	MODULE-IDENTITY 			FROM SNMPv2-SMI
	TRAP-TYPE				FROM RFC-1215
	OBJECT-TYPE				FROM RFC-1212;

-- Our enterprise

sonicWALL	OBJECT IDENTIFIER ::= { enterprises 8714 }

sonicSEC MODULE-IDENTITY
    LAST-UPDATED "200203061330Z"
    ORGANIZATION "SonicWALL, Inc."
    CONTACT-INFO
                "       SonicWall Inc.

                Postal: 1160 Bordeaux Dr.
                        Sunnyvale, CA 94089
                        USA

                   Tel: +1 408 745 9600
                   Fax: +1 408 745 9300

                E-mail: support@sonicwall.com"
    DESCRIPTION
        "The MIB module for SonicWALL enterprise security devices."
    ::= { sonicWALL 2 }

END
