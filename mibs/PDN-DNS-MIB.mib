PDN-DNS-MIB DEFINITIONS ::= BEGIN

-- Version :  0.1 DRAFT
-- Enterprise pdn DNS mib
-- Copyright (C) 2000 Paradyne Corporation.

-- Created by : Prakash Easwar

IMPORTS
OBJECT-TYPE
FROM RFC-1212
pdn-dns
FROM PDN-HEADER-MIB
RowStatus,DisplayString 
FROM SNMPv2-TC
IpAddress
FROM RFC1155-SMI
DomainName,
DNSServerType
FROM PDN-TC
;

pdnDNSMIBObjects      OBJECT IDENTIFIER ::= { pdn-dns 1 }
pdnDNSMIBTraps        OBJECT IDENTIFIER ::= { pdn-dns 2 }

-- DNS (Domain Name Server) group

        devDNSDefaultDomainName OBJECT-TYPE
              SYNTAX  DomainName
              ACCESS  read-write
              STATUS  mandatory
              DESCRIPTION
               "the object allows the NMS to configure the default 
                domain name for the device"
              ::= { pdnDNSMIBObjects 1 }

        devDNSRetryTimeout OBJECT-TYPE
              SYNTAX  INTEGER
              ACCESS  read-write
              STATUS  mandatory
             DESCRIPTION
                 "the object allows the NMS to configure in 
                  seconds the time to wait  for a response from
                  a DNS server. The default value for this object
                  is 5"
              ::= { pdnDNSMIBObjects 2 }

        devDNSMaxRetries OBJECT-TYPE
              SYNTAX  INTEGER
              ACCESS  read-write
              STATUS  mandatory
              DESCRIPTION
                "the object allows the NMS to configure the 
                 number of maximum number of retires by the 
                 device before giving up or trying one of the
                 secondary DNS servers if they have been 
                 configured. The default value for this object
                 is 2"
              ::= { pdnDNSMIBObjects 3 }


        devDNSServerTable OBJECT-TYPE
              SYNTAX  SEQUENCE OF DevDNSServerEntry
              ACCESS  not-accessible
              STATUS  mandatory
              DESCRIPTION
                "A Table that contains information about 
                 the DNS server IP addresses"
              ::= { pdnDNSMIBObjects 4 }

        devDNSServerEntry OBJECT-TYPE
              SYNTAX  DevDNSServerEntry
              ACCESS  not-accessible
              STATUS  mandatory
              DESCRIPTION
                  "A Table that contains information about the 
                   DNS server IP addresses"
              INDEX  { devDNSServerIP }
              ::= { devDNSServerTable 1 }

        DevDNSServerEntry ::=
                SEQUENCE
                {
                   devDNSServerIP     IpAddress,
                   devDNSServerType   DNSServerType,
                   devDNSRowStatus    RowStatus
                }

        devDNSServerIP OBJECT-TYPE
                SYNTAX  IpAddress
                ACCESS  read-only
                STATUS  mandatory
                DESCRIPTION
                    "This Objects allows an NMS to configure 
                     a DNS server IP address Default value is 1"
                ::= { devDNSServerEntry 1 }

        devDNSServerType OBJECT-TYPE
                SYNTAX  DNSServerType
                ACCESS  read-write
                STATUS  mandatory
                DESCRIPTION
                   "This Objects allows an NMS to specify 
                    whether the Server IP address is the
                    primary DNS server or the secondary DNS
                    server. Only One Primary DNS server
                    is allowed to be configured."
                ::= { devDNSServerEntry 2 }

        devDNSRowStatus OBJECT-TYPE
                SYNTAX  RowStatus
                ACCESS  read-write
                STATUS  mandatory
                DESCRIPTION
                 "Use CreateAndGo to Create a new object. use 
                   Destroy to remove an entry from this table"
                ::= { devDNSServerEntry 3 }

--
--           Host Mapping Table
--
        devHostMappingTable OBJECT-TYPE
              SYNTAX  SEQUENCE OF DevHostMappingEntry
              ACCESS  not-accessible
              STATUS  mandatory
              DESCRIPTION
                "A Table that contains information about 
                 host names for devices"
              ::= { pdnDNSMIBObjects 5 }

        devHostMappingEntry OBJECT-TYPE
              SYNTAX  DevHostMappingEntry
              ACCESS  not-accessible
              STATUS  mandatory
              DESCRIPTION
                  "An entry that contains information
                   about a device host name"
              INDEX  { devHostMappingIpAddress }
              ::= { devHostMappingTable 1 }

        DevHostMappingEntry ::=
                SEQUENCE
                {
                   devHostMappingIpAddress     IpAddress,
                   devHostMappingHostName      DisplayString,
                   devHostMappingRowStatus     RowStatus
                }
        devHostMappingIpAddress OBJECT-TYPE
              SYNTAX IpAddress 
              ACCESS  read-only
              STATUS  mandatory
              DESCRIPTION
               "This object contains the IP Address
                of the  host"
              ::= { devHostMappingEntry  1 }

        devHostMappingHostName  OBJECT-TYPE
              SYNTAX DisplayString (SIZE (1..64))
              ACCESS  read-write
              STATUS  mandatory
              DESCRIPTION
               "This object contains the  name of the host"
              ::= { devHostMappingEntry  2 }

        devHostMappingRowStatus OBJECT-TYPE
              SYNTAX RowStatus 
              ACCESS  read-write
              STATUS  mandatory
              DESCRIPTION
               "This object is used to create or delete a row
                from the table"
              ::= { devHostMappingEntry  3 }

END
