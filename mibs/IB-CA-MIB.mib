-- extracted from draft-ietf-ipoib-channel-adapter-mib-08.txt
-- at Mon Oct 23 06:07:20 2006

   IB-CA-MIB DEFINITIONS ::= BEGIN  
        
   IMPORTS   
      MODULE-IDENTITY, OBJECT-TYPE, 
      Unsigned32                                     FROM SNMPv2-SMI   
      TruthValue                                     FROM SNMPv2-TC   
    
      MODULE-COMPLIANCE, OBJECT-GROUP                FROM SNMPv2-CONF   
      infinibandMIB, IbPhysPort                      FROM IB-TC-MIB; 
    
   ibCaMIB MODULE-IDENTITY   
      LAST-UPDATED    "200610101200Z"   -- October 10, 2006 12:00:00 GMT 
      ORGANIZATION    "IETF IP Over IB (IPOIB) Working Group" 
      CONTACT-INFO   
          "Hal Rosenstock 
           Postal: HNR Consulting   
                   200 Old Harvard Road 
                   Boxboro MA 01719-1834 
                   United States 
           Email:  hnrose@earthlink.net 
    
           Email comments to the IPOIB WG Mailing List at 
           ipoverib@ietf.org." 
      DESCRIPTION   
         "Copyright (C) The Internet Society (2006).  The initial  
          version of this MIB module was published in RFC XXXX; for 
          full legal notices see the RFC itself.  Supplementary  
          information may be available on  
          http://www.ietf.org/copyrights/ianamib.html. 
    
          This module contains managed object definitions for  
          the instrumentation for an InfiniBand Channel Adapter (CA)." 
      REVISION     
         "200610101200Z"  -- 10 October 2006 12:00:00 GMT 
      DESCRIPTION  
         "Initial version published as part of RFC XXXX." 
      ::= { infinibandMIB 4 } 
    
   --****************************************************************  
   --  Object Identifiers for the IPOIB CA MIB   
   --****************************************************************  
    
   ibCaObjects         OBJECT IDENTIFIER ::= { ibCaMIB 1 }   
   ibCaConformance     OBJECT IDENTIFIER ::= { ibCaMIB 2 }   
    
   --****************************************************************  
   -- General Channel Adapter Info Group 
   -- 
   -- DESCRIPTION: This group contains a table that describes 
   --    general information about the Channel Adapters present in 
   --    this Managed System Element.  
   --**************************************************************** 
    
   ibCaGeneralInfo OBJECT IDENTIFIER ::= { ibCaObjects 1 }  
    
   --****************************************************************  
   --  Channel Adapters General Information Table                          
   --****************************************************************  
    
   ibCaGeneralInfoTable OBJECT-TYPE 
      SYNTAX SEQUENCE OF IbCaGeneralInfoEntry  
      MAX-ACCESS not-accessible   
      STATUS current  
      DESCRIPTION  
         "A table containing general information about the Channel 
          Adapters on this network entity."  
      ::= { ibCaGeneralInfo 1 } 

   ibCaGeneralInfoEntry OBJECT-TYPE 
      SYNTAX IbCaGeneralInfoEntry  
      MAX-ACCESS not-accessible  
      STATUS current  
      DESCRIPTION  
         "A conceptual row of the ibCaGeneralInfoTable containing 
          information about the general characteristics of each 
          Channel Adapter on this network entity." 
      INDEX   { ibCaIndex }   
      ::= { ibCaGeneralInfoTable 1 } 
    
   IbCaGeneralInfoEntry ::= SEQUENCE {  
      ibCaIndex Unsigned32, 
      ibCaType INTEGER, 
      ibCaNodeGuid OCTET STRING, 
      ibCaNumPorts Unsigned32 
      } 
    
   ibCaIndex OBJECT-TYPE 
      SYNTAX Unsigned32(1..254) 
      MAX-ACCESS not-accessible  
      STATUS current  
      DESCRIPTION   
         "Index that identifies the specific CA on this network 
          entity.  The index is defined for a range of CAs from 
          1 to N, where N can have a maximum value of 254."  
      ::= { ibCaGeneralInfoEntry 1 } 
    
   ibCaType OBJECT-TYPE 
      SYNTAX INTEGER { 
                     unknown(1), 
                     hca(2),            -- host CA 
                     tca(3)             -- target CA 
                     }  
      MAX-ACCESS read-only 
      STATUS current 
      DESCRIPTION 
         "Type of Channel Adapter: either a Host Channel Adapter (HCA), 
          or a Target Channel Adapter (TCA).  The key difference between 
          an HCA and a TCA is that the HCA supports the IBA Verbs layer, 
          while the TCA uses an implementation dependent interface to 
          the transport layer.  If the type of CA cannot be determined,  
          the unknown(1) value is returned." 
      REFERENCE 
         "InfiniBand Architecture Release 1.2 Vol. 1. Section 17.1." 
      ::= { ibCaGeneralInfoEntry 2 } 
 
   ibCaNodeGuid OBJECT-TYPE  
      SYNTAX OCTET STRING (SIZE(8))  
      MAX-ACCESS read-only  
      STATUS current  
      DESCRIPTION  
         "The GUID of this CA.  All ports on the same node shall 
          report the same CA node GUID value.  This provides a  
          means for uniquely identifying a CA node within a  
          subnet and helps to determine the co-location of 
          the ports."  
      REFERENCE 
         "InfiniBand Architecture Release 1.2 Vol. 1. Section 17.2.5." 
      ::= { ibCaGeneralInfoEntry 3 } 
    
   ibCaNumPorts OBJECT-TYPE 
      SYNTAX Unsigned32(1..254)  
      MAX-ACCESS read-only  
      STATUS current  
      DESCRIPTION 
         "Number of physical IB data ports on this Channel Adapter. 
   Ports 
          are numbered starting from 1. If there is more than one port, 
          the ports are numbered sequentially." 
      REFERENCE 
         "InfiniBand Architecture Release 1.2 Vol. 1. 
          Section 17.2.1.3; Table 313 Port Attributes & Functions." 
      ::= { ibCaGeneralInfoEntry 4 } 
    
   --****************************************************************  
   -- Channel Adapter Attributes Info Group 
   -- 
   -- DESCRIPTION: This group contains a table that describes more  
   --    specific attributes about each CA on the network entity.  
   --****************************************************************  
    
   ibCaAttrInfo OBJECT IDENTIFIER ::= { ibCaObjects 2 }  
    
   --****************************************************************  
   -- Channel Adapter Attributes Table 
   --****************************************************************  
    
   ibCaAttributeTable OBJECT-TYPE 
      SYNTAX SEQUENCE OF IbCaAttributeEntry  
      MAX-ACCESS not-accessible   
      STATUS current  
      DESCRIPTION  
         "A table containing information about the Channel Adapter  
          attributes on this network entity."  
      ::= { ibCaAttrInfo 1 } 

   ibCaAttributeEntry OBJECT-TYPE 
      SYNTAX IbCaAttributeEntry  
      MAX-ACCESS not-accessible  
      STATUS current  
      DESCRIPTION  
         "A conceptual row of the ibCaAttributeTable containing  
          information about the general characteristics of each 
          Channel Adapter on this network entity." 
      INDEX   { ibCaIndex }   
      ::= { ibCaAttributeTable 1 } 
    
   IbCaAttributeEntry ::= SEQUENCE {  
      ibCaHasReliableConnection TruthValue, 
      ibCaHasUnreliableConnection TruthValue, 
      ibCaHasReliableDatagram TruthValue, 
      ibCaHasUnreliableDatagram TruthValue, 
      ibCaSupportsAtomicOperations TruthValue, 
      ibCaSupportsOtherOperations TruthValue, 
      ibCaSupportsSolicitedEvents TruthValue, 
      ibCaPathMtuSetSupport INTEGER, 
      ibCaGenEndToEndFlowControl TruthValue, 
      ibCaSupportsMulticast TruthValue, 
      ibCaSupportsAutoPathMigration TruthValue, 
      ibCaSupportsMemoryProtection TruthValue, 
      ibCaSupportsLoopback TruthValue, 
      ibCaSupportsSubnetManager TruthValue 
      } 
    
   ibCaHasReliableConnection OBJECT-TYPE 
      SYNTAX TruthValue  
      MAX-ACCESS read-only  
      STATUS current  
      DESCRIPTION 
         "Flag that indicates whether this CA supports  
          Reliable Connection (RC) transport service." 
      REFERENCE 
         "InfiniBand Architecture Release 1.2 Vol. 1. 
          Section 17.2.2; Table 314 Channel Adapter Attributes." 
      ::= { ibCaAttributeEntry 1 } 
    
   ibCaHasUnreliableConnection OBJECT-TYPE 
      SYNTAX TruthValue  
      MAX-ACCESS read-only  
      STATUS current  
      DESCRIPTION 
         "Flag that indicates whether this CA supports  
          Unreliable Connection (UC) transport service." 
      REFERENCE 
         "InfiniBand Architecture Release 1.2 Vol. 1. 
          Section 17.2.2; Table 314 Channel Adapter Attributes." 
      ::= { ibCaAttributeEntry 2 } 
    
   ibCaHasReliableDatagram OBJECT-TYPE 
      SYNTAX TruthValue  
      MAX-ACCESS read-only  
      STATUS current  
      DESCRIPTION 
         "Flag that indicates whether this CA supports  
          Reliable Datagram (RD) transport service." 
      REFERENCE 
         "InfiniBand Architecture Release 1.2 Vol. 1. 
          Section 17.2.2; Table 314 Channel Adapter Attributes." 
      ::= { ibCaAttributeEntry 3 } 
    
   ibCaHasUnreliableDatagram OBJECT-TYPE 
      SYNTAX TruthValue  
      MAX-ACCESS read-only  
      STATUS current  
      DESCRIPTION 
         "Flag that indicates whether this CA supports  
          Unreliable Datagram (UD) transport service." 
      REFERENCE 
         "InfiniBand Architecture Release 1.2 Vol. 1. 
          Section 17.2.2; Table 314 Channel Adapter Attributes." 
      ::= { ibCaAttributeEntry 4 } 
    
   ibCaSupportsAtomicOperations OBJECT-TYPE 
      SYNTAX TruthValue  
      MAX-ACCESS read-only  
      STATUS current  
      DESCRIPTION 
         "Flag that indicates whether this CA supports  
          atomic operations.  An atomic operation is an operation 
          that is guaranteed to finish without having another  
          operation alter the results once the atomic operation  
          has been initiated." 
      REFERENCE 
         "InfiniBand Architecture Release 1.2 Vol. 1. 
          Section 17.2.2; Table 314 Channel Adapter Attributes." 
      ::= { ibCaAttributeEntry 5 } 
    
   ibCaSupportsOtherOperations OBJECT-TYPE 
      SYNTAX TruthValue  
      MAX-ACCESS read-only  
      STATUS current  
      DESCRIPTION 
         "Flag that indicates whether this CA supports  
          all of the other operations (excluding atomic operations) 
          defined for a particular supported transport service." 
      REFERENCE 
         "InfiniBand Architecture Release 1.2 Vol. 1. 
          Section 17.2.2; Table 314 Channel Adapter Attributes." 
      ::= { ibCaAttributeEntry 6 } 
    
   ibCaSupportsSolicitedEvents OBJECT-TYPE 
      SYNTAX TruthValue  
      MAX-ACCESS read-only  
      STATUS current  
      DESCRIPTION 
         "Flag that indicates whether this CA supports the  
          generation and reception of solicited events.  A solicited 
          event is a feature by which a queue pair consumer on a  
          CA can cause an event to be generated at the destination 
          when its message is received." 
      REFERENCE 
         "InfiniBand Architecture Release 1.2 Vol. 1. 
          Section 17.2.2; Table 314 Channel Adapter Attributes. 
          and Section 9.2.3 Solicited Event (SE) - 1 bit." 
      ::= { ibCaAttributeEntry 7 } 
    
   ibCaPathMtuSetSupport OBJECT-TYPE 
      SYNTAX INTEGER { 
                     mtu256(1), 
                     mtu256n512(2), 
                     mtu256n512n1024(3), 
                     mtu256n512n1024n2048(4), 
                     mtu256n512n1024n2048n4096(5) 
                     }  
      MAX-ACCESS read-only 
      STATUS current 
      DESCRIPTION 
         "Set of MTU values (in bytes) supported by this CA for all 
          transport service classes.  The Maximum Transfer Unit is the 
          largest size allowable for the packet payload." 
      REFERENCE 
         "InfiniBand Architecture Release 1.2 Vol. 1. 
          Section 17.2.2; Table 314 Channel Adapter Attributes." 
      ::= { ibCaAttributeEntry 8 } 
    
   ibCaGenEndToEndFlowControl OBJECT-TYPE 
      SYNTAX TruthValue  
      MAX-ACCESS read-only  
      STATUS current  
      DESCRIPTION 
         "Flag that indicates whether this CA supports  
          the generation of end-to-end flow control.  End-to-end 
          flow control is a mechanism that prevents sending messages 
          when the destination does not have adequate receive buffers 
          to receive the message." 
      REFERENCE 
         "InfiniBand Architecture Release 1.2 Vol. 1. 
          Section 17.2.2; Table 314 Channel Adapter Attributes." 
      ::= { ibCaAttributeEntry 9 } 
    
   ibCaSupportsMulticast OBJECT-TYPE 
      SYNTAX TruthValue  
      MAX-ACCESS read-only  
      STATUS current  
      DESCRIPTION 
         "Flag that indicates whether this CA supports multicast  
          operations.  Multicast is the ability to deliver a single  
          packet to multiple ports." 
      REFERENCE 
         "InfiniBand Architecture Release 1.2 Vol. 1. 
          Section 17.2.2; Table 314 Channel Adapter Attributes." 
      ::= { ibCaAttributeEntry 10 } 
    
   ibCaSupportsAutoPathMigration OBJECT-TYPE 
      SYNTAX TruthValue  
      MAX-ACCESS read-only  
      STATUS current  
      DESCRIPTION 
         "Flag that indicates whether this CA supports  
          automatic path migration.  Automatic path migration 
          is the process by which a CA (on a per QP basis) 
          signals another CA to cause path migration to a  
          preset alternate path." 
      REFERENCE 
         "InfiniBand Architecture Release 1.2 Vol. 1. 
          Section 17.2.2; Table 314 Channel Adapter Attributes." 
      ::= { ibCaAttributeEntry 11 } 
    
   ibCaSupportsMemoryProtection OBJECT-TYPE 
      SYNTAX TruthValue  
      MAX-ACCESS read-only  
      STATUS current  
      DESCRIPTION 
         "Flag that indicates whether this CA supports InfiniBand  
          memory management protection mechanisms." 
      REFERENCE 
         "InfiniBand Architecture Release 1.2 Vol. 1. 
          Section 17.2.2; Table 314 Channel Adapter Attributes. 
          and Section 10.6 Memory Management." 
      ::= { ibCaAttributeEntry 12 } 
    
   ibCaSupportsLoopback OBJECT-TYPE 
      SYNTAX TruthValue  
      MAX-ACCESS read-only  
      STATUS current  
      DESCRIPTION 
         "Flag that indicates whether this CA supports  
          loopback operations.  Loopback support allows for the  
          sending and receiving of self-addressed packets that 
          do not go out on the wire.  If this feature is supported, 
          self-addressed packets must work, even if no switch is 
          present." 
      REFERENCE 
         "InfiniBand Architecture Release 1.2 Vol. 1. 
          Section 17.2.2; Table 314 Channel Adapter Attributes." 
      ::= { ibCaAttributeEntry 13 } 
    
   ibCaSupportsSubnetManager OBJECT-TYPE 
      SYNTAX TruthValue  
      MAX-ACCESS read-only  
      STATUS current  
      DESCRIPTION 
         "Flag that indicates whether this CA supports  
          a Subnet Manager (SM) instance." 
      REFERENCE 
         "InfiniBand Architecture Release 1.2 Vol. 1. 
          Section 17.2.2; Table 314 Channel Adapter Attributes." 
      ::= { ibCaAttributeEntry 14 } 
    
   --****************************************************************  
   -- Channel Adapter Port Attributes and GID Info Group 
   -- 
   -- DESCRIPTION: This group contains information about the CA ports 
   --    on the network entity and the GID table associated with each 
   --    port. 
   --****************************************************************  
    
   ibCaPortAttrInfo OBJECT IDENTIFIER ::= { ibCaObjects 3 }  
    
   --****************************************************************  
   -- Channel Adapter Port Attribute Table 
   --****************************************************************  
    
   ibCaPortAttributeTable OBJECT-TYPE 
      SYNTAX SEQUENCE OF IbCaPortAttributeEntry  
      MAX-ACCESS not-accessible   
      STATUS current  
      DESCRIPTION  
         "A table containing information about the Channel Adapter  
          port attributes on this network entity."  
      ::= { ibCaPortAttrInfo 1 } 

   ibCaPortAttributeEntry OBJECT-TYPE 
      SYNTAX IbCaPortAttributeEntry  
      MAX-ACCESS not-accessible  
      STATUS current  
      DESCRIPTION  
         "A conceptual row of the ibCaPortAttributeTable containing  
          information about the general characteristics of each 
          Channel Adapter port on this network entity." 
      INDEX { ibCaIndex, ibCaPortIndex }   
      ::= { ibCaPortAttributeTable 1 } 
    
   IbCaPortAttributeEntry ::= SEQUENCE {  
      ibCaPortIndex IbPhysPort, 
      ibCaPortGuid OCTET STRING, 
      ibCaPhysicalInterface INTEGER, 
      ibCaSupportsStaticRateControl TruthValue, 
      ibCaInterpacketDelayValue Unsigned32, 
      ibCaSupportsMultipathing TruthValue, 
      ibCaValidatesInPktDlid TruthValue, 
      ibCaMaxGidsPerPort Unsigned32 
      } 
    
   ibCaPortIndex OBJECT-TYPE 
      SYNTAX IbPhysPort 
      MAX-ACCESS not-accessible  
      STATUS current  
      DESCRIPTION   
         "Index that identifies the InfiniBand data port.  The IBA 
          defines a range of valid data ports from 1 to N, where   
          N can have a maximum value of 254 for an IBA switch."  
      ::= { ibCaPortAttributeEntry 1 } 
    
    
   ibCaPortGuid OBJECT-TYPE  
      SYNTAX OCTET STRING (SIZE(8))  
      MAX-ACCESS read-only  
      STATUS current  
      DESCRIPTION  
         "The GUID of this CA port.  All ports on the same CA shall 
          report a unique ibCaPortGuid value.  This provides a means 
          for uniquely identifying a CA port on a node within a subnet  
          and helps to determine the co-location of the ports."  
      REFERENCE 
         "InfiniBand Architecture Release 1.2 Vol. 1. Section 17.2.5." 
      ::= { ibCaPortAttributeEntry 2 } 
    
   ibCaPhysicalInterface OBJECT-TYPE 
      SYNTAX INTEGER { 
                     cable(1), 
                     fiber(2),      
                     backplane(3)      
                     } 
      MAX-ACCESS read-only  
      STATUS current  
      DESCRIPTION 
         "The physical interface for this CA.  When the value 
          is cable(1), the CA supports a cable connector physical 
          interface.  This physical attach point is defined for use  
          with copper cables. When the value is fiber(2), the CA 
          supports a fiber connector physical interface. This 
          physical attach point is defined for use with optical 
          cables.  When the value is backplane(3), the CA supports 
          a backplane connector physical interface.  This physical 
          attach point is defined for accepting a specified form 
          factor that houses the channel adapter." 
      REFERENCE 
         "InfiniBand Architecture Release 1.2 Vol. 1. 
          Section 17.2.1.3 Port Attributes and Functions; 
          Vol. 2. 3.1 Introduction (Physical Layer Overview)." 
      ::= { ibCaPortAttributeEntry 3 } 
    
   ibCaSupportsStaticRateControl OBJECT-TYPE 
      SYNTAX TruthValue  
      MAX-ACCESS read-only  
      STATUS current  
      DESCRIPTION 
         "Flag that indicates whether this CA supports static 
          rate control.  Static rate controls are required for 
          all IB ports that support a data rate over 2.5 Gbps." 
      REFERENCE 
         "InfiniBand Architecture Release 1.2 Vol. 1.  
          Section 17.2.6 Static Rate Control." 
      ::= { ibCaPortAttributeEntry 4 } 
    
   ibCaInterpacketDelayValue OBJECT-TYPE 
      SYNTAX Unsigned32 (0..255) 
      MAX-ACCESS read-only  
      STATUS current  
      DESCRIPTION 
         "Interpacket Delay Value (IPD) supported for CAs that have 
          static rate control (i.e., the ibCaSupportsStaticRateControl 
          object must have a value of true(1) for this object to  
          contain a valid value; Otherwise, 0 is returned).  
          The IPD allows for the slowing of the packet rate for all  
          of the standard link rates." 
      REFERENCE 
         "InfiniBand Architecture Release 1.2 Vol. 1. 
          Section 17.2.6 Static Rate Control, and Table 315 
          Static Rate Control IPD Values. 
          Section 9.11.1 Static Rate Control for Heterogeneous Links,  
          and Table 63 Inter Packet Delay" 
      ::= { ibCaPortAttributeEntry 5 } 
          
   ibCaSupportsMultipathing OBJECT-TYPE 
      SYNTAX TruthValue  
      MAX-ACCESS read-only  
      STATUS current  
      DESCRIPTION 
         "Flag that indicates whether this CA supports multipathing. 
          The CA link layer port checks the unicast DLID in the  
          received packet for validity by masking the number of low 
          order bits indicated by the LID Mask Control field (LMC)  
          before comparing the DLID to its assigned LID if this 
          object is true(1)." 
      REFERENCE 
         "InfiniBand Architecture Release 1.2 Vol. 1.  
          Section 17.2.1.3 and Table 313 Port Attributes & Functions;  
          Also, Section 7.11.1 Multipathing Requirements on End Node." 
      ::= { ibCaPortAttributeEntry 6 } 
    
   ibCaValidatesInPktDlid OBJECT-TYPE 
      SYNTAX TruthValue  
      MAX-ACCESS read-only  
      STATUS current  
      DESCRIPTION 
         "Flag that indicates whether this CA supports the validation 
          of incoming packet DLIDs, and if the GRH is present, the 
          DGID." 
      REFERENCE 
         "InfiniBand Architecture Release 1.2 Vol. 1.  
          Section 17.2.1.3. and Table 313 Port Attributes & Functions." 
      ::= { ibCaPortAttributeEntry 7 } 
    
   ibCaMaxGidsPerPort OBJECT-TYPE 
      SYNTAX Unsigned32(1..65535) 
      MAX-ACCESS read-only  
      STATUS current  
      DESCRIPTION 
         "Maximum number of GIDs per port.  The maximum number of 
          unicast GIDs supported per CA port is implementation specific. 
          Each port will support at least one (1) GID." 
      REFERENCE 
         "InfiniBand Architecture Release 1.2 Vol. 1. 
          Section 17.2.1.3. and Table 313 Port Attributes & Functions." 
      ::= { ibCaPortAttributeEntry 8 } 

   --****************************************************************  
   -- Channel Adapter Port Global Identifier (GID) Table 
   --****************************************************************  
    
   ibCaPortGidTable OBJECT-TYPE 
      SYNTAX SEQUENCE OF IbCaPortGidEntry  
      MAX-ACCESS not-accessible   
      STATUS current  
      DESCRIPTION  
         "A table containing the port GIDs for each CA."  
      ::= { ibCaPortAttrInfo 2 } 
    
   ibCaPortGidEntry OBJECT-TYPE 
      SYNTAX IbCaPortGidEntry     
      MAX-ACCESS not-accessible  
      STATUS current  
      DESCRIPTION  
         "A conceptual row of the ibCaPortGidTable containing  
          information about a particular GID on an IB port 
          for a particular CA." 
      INDEX { ibCaIndex, ibCaPortIndex, ibCaPortGidIndex }   
      ::= { ibCaPortGidTable 1 } 
    
   IbCaPortGidEntry ::= SEQUENCE {    
      ibCaPortGidIndex Unsigned32, 
      ibCaPortGidValue OCTET STRING 
      } 
    
   ibCaPortGidIndex OBJECT-TYPE 
      SYNTAX Unsigned32(1..65535) 
      MAX-ACCESS not-accessible  
      STATUS current  
      DESCRIPTION   
         "Index that identifies the GID entry for this IB data port. 
          Each port on a CA is assigned at least 1 unicast GID. 
          Note, the value of ibCaPortGidIndex will never be greater  
          than the value of ibCaMaxGidsPerPort that defines the  
          upper value for this index." 
      ::= { ibCaPortGidEntry 1 } 
    
   ibCaPortGidValue OBJECT-TYPE 
      SYNTAX OCTET STRING (SIZE(16)) 
      MAX-ACCESS read-only  
      STATUS current  
      DESCRIPTION   
         "The Global Identifier (GID) is a 128-bit (16-byte) unicast  
          or multicast identifier used to identify a channel adapter  
          port.  A GID is a valid 128-bit IPv6 address (as defined in  
          RFC 2373) with additional IBA modifications that facilitate 
          node discovery, routing, and communications." 
      REFERENCE 
         "InfiniBand Architecture Release 1.2 Vol. 1.  
          Section 4.1.1 GID Usage and Properties." 
      ::= { ibCaPortGidEntry 2 } 
    
   --****************************************************************  
   -- Module Conformance Statement  
   -- 
   -- DESCRIPTION: The module conformance statement includes the 
   --    compliance statements and the units of conformance 
   --    section. 
   --****************************************************************  
    
   ibCaCompliances OBJECT IDENTIFIER ::= { ibCaConformance 1 } 
    
   ibCaGroups OBJECT IDENTIFIER ::= { ibCaConformance 2 } 
    
   --****************************************************************  
   -- Compliance Statements  
   --****************************************************************  
    
   ibCaBasicCompliance MODULE-COMPLIANCE 
      STATUS current 
      DESCRIPTION 
         "The basic CA implementation requirements for agents that 
          support the IPOIB CA MIB." 
    
      MODULE -- this module 
          MANDATORY-GROUPS {  
                           ibCaGeneralGroup 
                           } 
      ::= { ibCaCompliances 1 } 
    
   ibCaFullCompliance MODULE-COMPLIANCE 
      STATUS current 
      DESCRIPTION 
         "The complete node implementation requirements for agents that 
          support the full IPOIB CA MIB." 
      MODULE -- this module 
          MANDATORY-GROUPS {  
                           ibCaGeneralGroup, 
                           ibCaAttrGroup, 
                           ibCaPortAttrGroup, 
                           ibCaPortGidGroup 
                           } 
      ::= { ibCaCompliances 2 } 
    
   --****************************************************************  
   -- Units of Conformance  
   --****************************************************************  
    
   ibCaGeneralGroup OBJECT-GROUP 
      OBJECTS  { 
          ibCaType, 
          ibCaNodeGuid, 
          ibCaNumPorts 
      } 
      STATUS current 
      DESCRIPTION 
         "The ibCaGeneralGroup defines the MIB objects that describe 
          the general characteristics of this Channel Adapter." 
      ::= { ibCaGroups 1 } 
    
   ibCaAttrGroup OBJECT-GROUP 
      OBJECTS  { 
          ibCaHasReliableConnection, 
          ibCaHasUnreliableConnection, 
          ibCaHasReliableDatagram, 
          ibCaHasUnreliableDatagram, 
          ibCaSupportsAtomicOperations, 
          ibCaSupportsOtherOperations, 
          ibCaSupportsSolicitedEvents, 
          ibCaPathMtuSetSupport, 
          ibCaGenEndToEndFlowControl, 
          ibCaSupportsMulticast, 
          ibCaSupportsAutoPathMigration, 
          ibCaSupportsMemoryProtection, 
          ibCaSupportsLoopback, 
          ibCaSupportsSubnetManager 
      } 
    
      STATUS current 
      DESCRIPTION 
         "The ibCaAttrGroup defines the MIB objects that describe 
          more specific attributes about the Channel Adapter." 
      ::= { ibCaGroups 2 } 
    
   ibCaPortAttrGroup OBJECT-GROUP 
      OBJECTS  { 
          ibCaPortGuid, 
          ibCaPhysicalInterface, 
          ibCaSupportsStaticRateControl, 
          ibCaInterpacketDelayValue, 
          ibCaSupportsMultipathing, 
          ibCaValidatesInPktDlid, 
          ibCaMaxGidsPerPort 
      } 
      STATUS current 
      DESCRIPTION 
         "The ibCaPortAttrGroup defines the MIB objects that describe 
          attributes about the Channel Adapter ports." 
      ::= { ibCaGroups 3 } 
    
   ibCaPortGidGroup OBJECT-GROUP 
      OBJECTS  { 
          ibCaPortGidValue  
      } 
      STATUS current 
      DESCRIPTION 
         "The ibCaPortGidGroup defines the MIB objects that describe 
          attributes about the Channel Adapter port GIDs." 
      ::= { ibCaGroups 4 } 
    
   END 

--     
--    Copyright (C) The Internet Society (2006).  This document is 
--    subject to the rights, licenses and restrictions contained in BCP 
--    78, and except as set forth therein, the authors retain all their 
--    rights. 
--        
--    This document and translations of it may be copied and 
--    furnished to others, and derivative works that comment on 
--    or otherwise explain it or assist in its implementation may 
--    be prepared, copied, published and distributed, in whole or 
--    in part, without restriction of any kind, provided that the 
--    above copyright notice and this paragraph are included on 
--    all such copies and derivative works.  However, this document 
--    itself may not be modified in any way, such as by removing the 
--    copyright notice or references to the Internet Society or other  
--    Internet organizations, except as needed for the purpose of  
--    developing Internet standards in which case the procedures for  
--    copyrights defined in the Internet Standards process must be  
--    followed, or as required to translate it into languages other  
--    than English. 
--        
--    The limited permissions granted above are perpetual and 
--    will not be revoked by the Internet Society or its 
--    successors or assigns.  
--     
--    This document and the information contained herein are provided 
--    on an "AS IS" basis and THE CONTRIBUTOR, THE ORGANIZATION HE/SHE 
--    REPRESENTS OR IS SPONSORED BY (IF ANY), THE INTERNET SOCIETY AND 
--    THE INTERNET ENGINEERING TASK FORCE DISCLAIM ALL WARRANTIES, 
--    EXPRESS OR IMPLIED, INCLUDING BUT NOT LIMITED TO ANY WARRANTY THAT 
--    THE USE OF THE INFORMATION HEREIN WILL NOT INFRINGE ANY RIGHTS OR 
--    ANY IMPLIED WARRANTIES OF MERCHANTABILITY OR FITNESS FOR A 
--    PARTICULAR PURPOSE. 
--        
--  
-- Acknowledgment 
--     
--    Funding for the RFC Editor function is currently provided by the 
--    Internet Society.
