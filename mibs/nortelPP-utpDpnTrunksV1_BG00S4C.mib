Nortel-Magellan-Passport-UtpDpnTrunksMIB
DEFINITIONS ::= BEGIN



IMPORTS

      OBJECT-TYPE
   FROM RFC-1212

      passportMIBs
   FROM Nortel-Magellan-Passport-UsefulDefinitionsMIB

      Counter32,
      DisplayString,
      StorageType,
      RowStatus,
      Gauge32,
      Unsigned32
   FROM Nortel-Magellan-Passport-StandardTextualConventionsMIB

      NonReplicated,
      Link
   FROM Nortel-Magellan-Passport-TextualConventionsMIB

      dpnGate,
      dpnGateIndex
   FROM Nortel-Magellan-Passport-DpnTrunksMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     UtpDpnTrunks Enterprise MIB."

utpDpnTrunksMIB OBJECT IDENTIFIER ::= { passportMIBs 67 }










-- DpnGateway/n Utp
-- The Utp component provides the Utp Level2 link protocol, an 
-- acknowledged protocol that provides selective retransmission of 
-- frames. A Framer subcomponent is automatically added providing 
-- the underlying HDLC framing and associated hardware that the Utp 
-- component will use.

dpnGateUtp OBJECT IDENTIFIER ::= { dpnGate 2 }



dpnGateUtpRowStatusTable OBJECT-TYPE
   SYNTAX     SEQUENCE OF DpnGateUtpRowStatusEntry
   ACCESS     not-accessible
   STATUS     mandatory
   DESCRIPTION
     "This entry controls the addition and deletion of 
      dpnGateUtp components."
::= { dpnGateUtp 1 }

dpnGateUtpRowStatusEntry OBJECT-TYPE
   SYNTAX     DpnGateUtpRowStatusEntry
   ACCESS     not-accessible
   STATUS     mandatory
   DESCRIPTION
     "A single entry in the table represents a single 
      dpnGateUtp component."
   INDEX {
      dpnGateIndex,
      dpnGateUtpIndex }
::= { dpnGateUtpRowStatusTable 1 }

DpnGateUtpRowStatusEntry ::= SEQUENCE {
   dpnGateUtpRowStatus
      RowStatus,
   dpnGateUtpComponentName
      DisplayString,
   dpnGateUtpStorageType
      StorageType,
   dpnGateUtpIndex
      NonReplicated }

dpnGateUtpRowStatus OBJECT-TYPE
   SYNTAX     RowStatus 
   ACCESS     read-write
   STATUS     mandatory
   DESCRIPTION
     "This variable is used as the basis for SNMP naming of
      dpnGateUtp components.
      These components can be added and deleted."
::= { dpnGateUtpRowStatusEntry 1 }

dpnGateUtpComponentName OBJECT-TYPE
   SYNTAX     DisplayString 
   ACCESS     read-only
   STATUS     mandatory
   DESCRIPTION
     "This variable provides the component's string name for
      use with the ASCII Console Interface"
::= { dpnGateUtpRowStatusEntry 2 }

dpnGateUtpStorageType OBJECT-TYPE
   SYNTAX     StorageType 
   ACCESS     read-only
   STATUS     mandatory
   DESCRIPTION
     "This variable represents the storage type value for the
      dpnGateUtp tables."
::= { dpnGateUtpRowStatusEntry 4 }

dpnGateUtpIndex OBJECT-TYPE
   SYNTAX     NonReplicated 
   ACCESS     not-accessible
   STATUS     mandatory
   DESCRIPTION
     "This variable represents the index for the dpnGateUtp tables."
::= { dpnGateUtpRowStatusEntry 10 }

dpnGateUtpProvTable OBJECT-TYPE
   SYNTAX     SEQUENCE OF DpnGateUtpProvEntry
   ACCESS     not-accessible
   STATUS     mandatory
   DESCRIPTION
     "This group of provisionable attributes contains the parameters used 
      by Unacknowledged, Utp, and FrAccess for monitoring link quality."
::= { dpnGateUtp 10 }

dpnGateUtpProvEntry OBJECT-TYPE
   SYNTAX     DpnGateUtpProvEntry
   ACCESS     not-accessible
   STATUS     mandatory
   DESCRIPTION
     "An entry in the dpnGateUtpProvTable."
   INDEX {
      dpnGateIndex,
      dpnGateUtpIndex }
::= { dpnGateUtpProvTable 1 }

DpnGateUtpProvEntry ::= SEQUENCE {
   dpnGateUtpMaximumErroredInterval
      Unsigned32,
   dpnGateUtpReceiveErrorSensitivity
      Unsigned32 }

dpnGateUtpMaximumErroredInterval OBJECT-TYPE
   SYNTAX     Unsigned32 (0 | 1..15)
   ACCESS     read-write
   STATUS     mandatory
   DESCRIPTION
     "This attribute specifies the interval time over which the error 
      threshold (as specified by receiveErrorSensitivity) must be 
      continuously exceeded before the Unacknowledged, Utp, or 
      FrAccess component can be degraded. Once the error interval count 
      exceeds the provisioned value, the Unacknowledged, Utp, or 
      FrAccess component issues an alarm indicating that link quality has 
      degraded, and it disables its parent component. The exception to 
      this is a value of zero, the default, which indicates that the 
      mechanism is completely disabled."
   DEFVAL     { 0 }
::= { dpnGateUtpProvEntry 1 }

dpnGateUtpReceiveErrorSensitivity OBJECT-TYPE
   SYNTAX     Unsigned32 (0 | 1..10)
   ACCESS     read-write
   STATUS     mandatory
   DESCRIPTION
     "This attribute is the allowable error rate beyond which the 
      Unacknowledged, Utp, or FrAccess component can be degraded if it 
      persists for a duration longer than the maximumErrorInterval. The 
      threshold is expressed as a percentage of number of errored frames 
      in the last interval per number of frames received in the last interval. 
      The exception to this is a value of zero, which indicates that the 
      mechanism is completely disabled. The configurable values are:
      0 = the mechanism is completely disabled
      1 = 1/(2**1)
      2 = 1/(2**2)
      3 = 1/(2**3)
      :
      10 = 1/(2**10)"
   DEFVAL     { 3 }
::= { dpnGateUtpProvEntry 2 }

dpnGateUtpStateTable OBJECT-TYPE
   SYNTAX     SEQUENCE OF DpnGateUtpStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { dpnGateUtp 11 }

dpnGateUtpStateEntry OBJECT-TYPE
   SYNTAX     DpnGateUtpStateEntry
   ACCESS     not-accessible
   STATUS     mandatory
   DESCRIPTION
     "An entry in the dpnGateUtpStateTable."
   INDEX {
      dpnGateIndex,
      dpnGateUtpIndex }
::= { dpnGateUtpStateTable 1 }

DpnGateUtpStateEntry ::= SEQUENCE {
   dpnGateUtpAdminState
      INTEGER,
   dpnGateUtpOperationalState
      INTEGER,
   dpnGateUtpUsageState
      INTEGER,
   dpnGateUtpAvailabilityStatus
      OCTET STRING,
   dpnGateUtpProceduralStatus
      OCTET STRING,
   dpnGateUtpControlStatus
      OCTET STRING,
   dpnGateUtpAlarmStatus
      OCTET STRING,
   dpnGateUtpStandbyStatus
      INTEGER,
   dpnGateUtpUnknownStatus
      INTEGER }

dpnGateUtpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { dpnGateUtpStateEntry 1 }

dpnGateUtpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { dpnGateUtpStateEntry 2 }

dpnGateUtpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { dpnGateUtpStateEntry 3 }

dpnGateUtpAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { dpnGateUtpStateEntry 4 }

dpnGateUtpProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { dpnGateUtpStateEntry 5 }

dpnGateUtpControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { dpnGateUtpStateEntry 6 }

dpnGateUtpAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { dpnGateUtpStateEntry 7 }

dpnGateUtpStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { dpnGateUtpStateEntry 8 }

dpnGateUtpUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { dpnGateUtpStateEntry 9 }

dpnGateUtpOpTable OBJECT-TYPE
   SYNTAX     SEQUENCE OF DpnGateUtpOpEntry
   ACCESS     not-accessible
   STATUS     mandatory
   DESCRIPTION
     "This group of attributes contains the set of UTP operational 
      parameters measured and maintained by this component."
::= { dpnGateUtp 12 }

dpnGateUtpOpEntry OBJECT-TYPE
   SYNTAX     DpnGateUtpOpEntry
   ACCESS     not-accessible
   STATUS     mandatory
   DESCRIPTION
     "An entry in the dpnGateUtpOpTable."
   INDEX {
      dpnGateIndex,
      dpnGateUtpIndex }
::= { dpnGateUtpOpTable 1 }

DpnGateUtpOpEntry ::= SEQUENCE {
   dpnGateUtpRoundTripDelay
      Gauge32 }

dpnGateUtpRoundTripDelay OBJECT-TYPE
   SYNTAX     Gauge32 (0..1500)
   ACCESS     read-only
   STATUS     mandatory
   DESCRIPTION
     "This is the measured Round Trip Delay (ms) discovered with the 
      remote through the UTP staging protocol. The value includes 
      emission, propagation, and queuing delays. A 2 byte control frame 
      is used to perform the measurement. A value of zero is displayed 
      when the link is disabled or the measured Round Trip Delay is 
      unknown."
::= { dpnGateUtpOpEntry 1 }

dpnGateUtpStatsTable OBJECT-TYPE
   SYNTAX     SEQUENCE OF DpnGateUtpStatsEntry
   ACCESS     not-accessible
   STATUS     mandatory
   DESCRIPTION
     "This group of attributes contains the set of Utp frame counters 
      collected by this component."
::= { dpnGateUtp 13 }

dpnGateUtpStatsEntry OBJECT-TYPE
   SYNTAX     DpnGateUtpStatsEntry
   ACCESS     not-accessible
   STATUS     mandatory
   DESCRIPTION
     "An entry in the dpnGateUtpStatsTable."
   INDEX {
      dpnGateIndex,
      dpnGateUtpIndex }
::= { dpnGateUtpStatsTable 1 }

DpnGateUtpStatsEntry ::= SEQUENCE {
   dpnGateUtpDiscardBadFromIf
      Counter32,
   dpnGateUtpDiscardExcessToIf
      Counter32,
   dpnGateUtpFrmRexmtToIf
      Counter32,
   dpnGateUtpAreYouThereModeEntries
      Counter32,
   dpnGateUtpWindowClosures
      Counter32 }

dpnGateUtpDiscardBadFromIf OBJECT-TYPE
   SYNTAX     Counter32 
   ACCESS     read-only
   STATUS     mandatory
   DESCRIPTION
     "This attribute is the number of received frames discarded by the Utp 
      component. UTP discards any received frame that is unknown to its 
      protocol. This counter wraps around to zero when the maximum 
      value is reached."
::= { dpnGateUtpStatsEntry 1 }

dpnGateUtpDiscardExcessToIf OBJECT-TYPE
   SYNTAX     Counter32 
   ACCESS     read-only
   STATUS     mandatory
   DESCRIPTION
     "This attribute is the number of transmitted frames discarded by the 
      Utp component. Transmitted frames are discarded if the wait for 
      transmission queue is congested. This counter wraps around to zero 
      when the maximum value is reached."
::= { dpnGateUtpStatsEntry 2 }

dpnGateUtpFrmRexmtToIf OBJECT-TYPE
   SYNTAX     Counter32 
   ACCESS     read-only
   STATUS     mandatory
   DESCRIPTION
     "This attribute is the number of frames retransmitted by the Utp 
      component. This counter wraps around to zero when the maximum 
      value is reached."
::= { dpnGateUtpStatsEntry 3 }

dpnGateUtpAreYouThereModeEntries OBJECT-TYPE
   SYNTAX     Counter32 
   ACCESS     read-only
   STATUS     mandatory
   DESCRIPTION
     "This attribute is the number of times the Utp component entered the 
      AreYouThere mode. UTP enters this mode whenever the 
      acknowledgment for the last transmitted frame has not been 
      received within a certain time interval. In this mode UTP verifies 
      that the remote end is still active. If so, it will retransmit all frames 
      that were waiting to be acknowledged. This counter wraps around 
      to zero when the maximum value is reached."
::= { dpnGateUtpStatsEntry 4 }

dpnGateUtpWindowClosures OBJECT-TYPE
   SYNTAX     Counter32 
   ACCESS     read-only
   STATUS     mandatory
   DESCRIPTION
     "This attribute is the number of times the Utp component closed its 
      frame window. The frame window determines the maximum 
      number of unacknowledged frames allowed. Typically, the frame 
      window closes when the remote end cannot keep up with the frame 
      arrival rate. This counter wraps around to zero when the maximum 
      value is reached."
::= { dpnGateUtpStatsEntry 5 }


-- 
-- Trunk/n Utp Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

dpnGateUtpFramer OBJECT IDENTIFIER ::= { dpnGateUtp 2 }



dpnGateUtpFramerRowStatusTable OBJECT-TYPE
   SYNTAX     SEQUENCE OF DpnGateUtpFramerRowStatusEntry
   ACCESS     not-accessible
   STATUS     mandatory
   DESCRIPTION
     "This entry controls the addition and deletion of 
      dpnGateUtpFramer components."
::= { dpnGateUtpFramer 1 }

dpnGateUtpFramerRowStatusEntry OBJECT-TYPE
   SYNTAX     DpnGateUtpFramerRowStatusEntry
   ACCESS     not-accessible
   STATUS     mandatory
   DESCRIPTION
     "A single entry in the table represents a single 
      dpnGateUtpFramer component."
   INDEX {
      dpnGateIndex,
      dpnGateUtpIndex,
      dpnGateUtpFramerIndex }
::= { dpnGateUtpFramerRowStatusTable 1 }

DpnGateUtpFramerRowStatusEntry ::= SEQUENCE {
   dpnGateUtpFramerRowStatus
      RowStatus,
   dpnGateUtpFramerComponentName
      DisplayString,
   dpnGateUtpFramerStorageType
      StorageType,
   dpnGateUtpFramerIndex
      NonReplicated }

dpnGateUtpFramerRowStatus OBJECT-TYPE
   SYNTAX     RowStatus 
   ACCESS     read-only
   STATUS     mandatory
   DESCRIPTION
     "This variable is used as the basis for SNMP naming of
      dpnGateUtpFramer components.
      These components cannot be added nor deleted."
::= { dpnGateUtpFramerRowStatusEntry 1 }

dpnGateUtpFramerComponentName OBJECT-TYPE
   SYNTAX     DisplayString 
   ACCESS     read-only
   STATUS     mandatory
   DESCRIPTION
     "This variable provides the component's string name for
      use with the ASCII Console Interface"
::= { dpnGateUtpFramerRowStatusEntry 2 }

dpnGateUtpFramerStorageType OBJECT-TYPE
   SYNTAX     StorageType 
   ACCESS     read-only
   STATUS     mandatory
   DESCRIPTION
     "This variable represents the storage type value for the
      dpnGateUtpFramer tables."
::= { dpnGateUtpFramerRowStatusEntry 4 }

dpnGateUtpFramerIndex OBJECT-TYPE
   SYNTAX     NonReplicated 
   ACCESS     not-accessible
   STATUS     mandatory
   DESCRIPTION
     "This variable represents the index for the dpnGateUtpFramer tables."
::= { dpnGateUtpFramerRowStatusEntry 10 }

dpnGateUtpFramerProvTable OBJECT-TYPE
   SYNTAX     SEQUENCE OF DpnGateUtpFramerProvEntry
   ACCESS     not-accessible
   STATUS     mandatory
   DESCRIPTION
     "This group contains the base provisioning data for the Framer 
      component. Application or hardware interface specific provisioning 
      data is contained in other provisionable Framer groups."
::= { dpnGateUtpFramer 10 }

dpnGateUtpFramerProvEntry OBJECT-TYPE
   SYNTAX     DpnGateUtpFramerProvEntry
   ACCESS     not-accessible
   STATUS     mandatory
   DESCRIPTION
     "An entry in the dpnGateUtpFramerProvTable."
   INDEX {
      dpnGateIndex,
      dpnGateUtpIndex,
      dpnGateUtpFramerIndex }
::= { dpnGateUtpFramerProvTable 1 }

DpnGateUtpFramerProvEntry ::= SEQUENCE {
   dpnGateUtpFramerInterfaceName
      Link }

dpnGateUtpFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { dpnGateUtpFramerProvEntry 1 }

dpnGateUtpFramerLinkTable OBJECT-TYPE
   SYNTAX     SEQUENCE OF DpnGateUtpFramerLinkEntry
   ACCESS     not-accessible
   STATUS     mandatory
   DESCRIPTION
     "This group contains attributes defining the framing of data on the 
      link interface."
::= { dpnGateUtpFramer 11 }

dpnGateUtpFramerLinkEntry OBJECT-TYPE
   SYNTAX     DpnGateUtpFramerLinkEntry
   ACCESS     not-accessible
   STATUS     mandatory
   DESCRIPTION
     "An entry in the dpnGateUtpFramerLinkTable."
   INDEX {
      dpnGateIndex,
      dpnGateUtpIndex,
      dpnGateUtpFramerIndex }
::= { dpnGateUtpFramerLinkTable 1 }

DpnGateUtpFramerLinkEntry ::= SEQUENCE {
   dpnGateUtpFramerFramingType
      INTEGER,
   dpnGateUtpFramerDataInversion
      INTEGER,
   dpnGateUtpFramerFrameCrcType
      INTEGER,
   dpnGateUtpFramerFlagsBetweenFrames
      Unsigned32 }

dpnGateUtpFramerFramingType OBJECT-TYPE
   SYNTAX     INTEGER  {
                 hdlc(0) }
   ACCESS     read-write
   STATUS     mandatory
   DESCRIPTION
     "This attribute defines the type of framing on the link."
   DEFVAL     { hdlc }
::= { dpnGateUtpFramerLinkEntry 1 }

dpnGateUtpFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted."
   DEFVAL     { off }
::= { dpnGateUtpFramerLinkEntry 2 }

dpnGateUtpFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used."
   DEFVAL     { crc16 }
::= { dpnGateUtpFramerLinkEntry 3 }

dpnGateUtpFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { dpnGateUtpFramerLinkEntry 4 }

dpnGateUtpFramerStateTable OBJECT-TYPE
   SYNTAX     SEQUENCE OF DpnGateUtpFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dpnGateUtpFramer 12 }

dpnGateUtpFramerStateEntry OBJECT-TYPE
   SYNTAX     DpnGateUtpFramerStateEntry
   ACCESS     not-accessible
   STATUS     mandatory
   DESCRIPTION
     "An entry in the dpnGateUtpFramerStateTable."
   INDEX {
      dpnGateIndex,
      dpnGateUtpIndex,
      dpnGateUtpFramerIndex }
::= { dpnGateUtpFramerStateTable 1 }

DpnGateUtpFramerStateEntry ::= SEQUENCE {
   dpnGateUtpFramerAdminState
      INTEGER,
   dpnGateUtpFramerOperationalState
      INTEGER,
   dpnGateUtpFramerUsageState
      INTEGER }

dpnGateUtpFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dpnGateUtpFramerStateEntry 1 }

dpnGateUtpFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dpnGateUtpFramerStateEntry 2 }

dpnGateUtpFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dpnGateUtpFramerStateEntry 3 }

dpnGateUtpFramerStatsTable OBJECT-TYPE
   SYNTAX     SEQUENCE OF DpnGateUtpFramerStatsEntry
   ACCESS     not-accessible
   STATUS     mandatory
   DESCRIPTION
     "This group contains the operational statistics data for a UTP Framer 
      component."
::= { dpnGateUtpFramer 13 }

dpnGateUtpFramerStatsEntry OBJECT-TYPE
   SYNTAX     DpnGateUtpFramerStatsEntry
   ACCESS     not-accessible
   STATUS     mandatory
   DESCRIPTION
     "An entry in the dpnGateUtpFramerStatsTable."
   INDEX {
      dpnGateIndex,
      dpnGateUtpIndex,
      dpnGateUtpFramerIndex }
::= { dpnGateUtpFramerStatsTable 1 }

DpnGateUtpFramerStatsEntry ::= SEQUENCE {
   dpnGateUtpFramerFrmToIf
      Counter32,
   dpnGateUtpFramerFrmFromIf
      Counter32,
   dpnGateUtpFramerOctetFromIf
      Counter32,
   dpnGateUtpFramerAborts
      Counter32,
   dpnGateUtpFramerCrcErrors
      Counter32,
   dpnGateUtpFramerLrcErrors
      Counter32,
   dpnGateUtpFramerNonOctetErrors
      Counter32,
   dpnGateUtpFramerOverruns
      Counter32,
   dpnGateUtpFramerUnderruns
      Counter32,
   dpnGateUtpFramerLargeFrmErrors
      Counter32,
   dpnGateUtpFramerFrmModeErrors
      Counter32,
   dpnGateUtpFramerOutOfSequenceFrm
      Counter32,
   dpnGateUtpFramerRepeatedFrm
      Counter32 }

dpnGateUtpFramerFrmToIf OBJECT-TYPE
   SYNTAX     Counter32 
   ACCESS     read-only
   STATUS     mandatory
   DESCRIPTION
     "The number of frames transmitted to the link interface by Framer.
      
      Note: This does not include the number of frames transmitted 
      directly to the hardware queue, thus bypassing the Framer 
      component."
::= { dpnGateUtpFramerStatsEntry 1 }

dpnGateUtpFramerFrmFromIf OBJECT-TYPE
   SYNTAX     Counter32 
   ACCESS     read-only
   STATUS     mandatory
   DESCRIPTION
     "The number of frames received from the link interface by Framer."
::= { dpnGateUtpFramerStatsEntry 2 }

dpnGateUtpFramerOctetFromIf OBJECT-TYPE
   SYNTAX     Counter32 
   ACCESS     read-only
   STATUS     mandatory
   DESCRIPTION
     "The number of bytes received from the link interface by Framer."
::= { dpnGateUtpFramerStatsEntry 3 }

dpnGateUtpFramerAborts OBJECT-TYPE
   SYNTAX     Counter32 
   ACCESS     read-only
   STATUS     mandatory
   DESCRIPTION
     "This attribute is the total number of aborts received."
::= { dpnGateUtpFramerStatsEntry 4 }

dpnGateUtpFramerCrcErrors OBJECT-TYPE
   SYNTAX     Counter32 
   ACCESS     read-only
   STATUS     mandatory
   DESCRIPTION
     "This attribute is the total number of frames with CRC errors, 
      occurring in the receive direction from the link."
::= { dpnGateUtpFramerStatsEntry 5 }

dpnGateUtpFramerLrcErrors OBJECT-TYPE
   SYNTAX     Counter32 
   ACCESS     read-only
   STATUS     mandatory
   DESCRIPTION
     "This attribute is the total number of frames with LRC errors, 
      occurring in the Tx link prior to transmission onto the link."
::= { dpnGateUtpFramerStatsEntry 6 }

dpnGateUtpFramerNonOctetErrors OBJECT-TYPE
   SYNTAX     Counter32 
   ACCESS     read-only
   STATUS     mandatory
   DESCRIPTION
     "This attribute is the total number of frames that were non octet 
      aligned."
::= { dpnGateUtpFramerStatsEntry 7 }

dpnGateUtpFramerOverruns OBJECT-TYPE
   SYNTAX     Counter32 
   ACCESS     read-only
   STATUS     mandatory
   DESCRIPTION
     "This attribute is the total number of frames received from the link 
      for which overruns occurred."
::= { dpnGateUtpFramerStatsEntry 8 }

dpnGateUtpFramerUnderruns OBJECT-TYPE
   SYNTAX     Counter32 
   ACCESS     read-only
   STATUS     mandatory
   DESCRIPTION
     "This attribute is the total number of frames transmitted to the link 
      for which underruns occurred."
::= { dpnGateUtpFramerStatsEntry 9 }

dpnGateUtpFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { dpnGateUtpFramerStatsEntry 10 }

dpnGateUtpFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { dpnGateUtpFramerStatsEntry 11 }

dpnGateUtpFramerOutOfSequenceFrm OBJECT-TYPE
   SYNTAX     Counter32 
   ACCESS     read-only
   STATUS     mandatory
   DESCRIPTION
     "This attribute is the total number of out of sequence frames in 
      interrupting mode that have been received from the link."
::= { dpnGateUtpFramerStatsEntry 12 }

dpnGateUtpFramerRepeatedFrm OBJECT-TYPE
   SYNTAX     Counter32 
   ACCESS     read-only
   STATUS     mandatory
   DESCRIPTION
     "This attribute is the total number of repeated frames (frames with 
      the same sequence number) in interrupting mode that have been 
      received from the link."
::= { dpnGateUtpFramerStatsEntry 13 }

dpnGateUtpFramerUtilTable OBJECT-TYPE
   SYNTAX     SEQUENCE OF DpnGateUtpFramerUtilEntry
   ACCESS     not-accessible
   STATUS     mandatory
   DESCRIPTION
     "This group contains the link utilization operational data for a 
      Framer component."
::= { dpnGateUtpFramer 14 }

dpnGateUtpFramerUtilEntry OBJECT-TYPE
   SYNTAX     DpnGateUtpFramerUtilEntry
   ACCESS     not-accessible
   STATUS     mandatory
   DESCRIPTION
     "An entry in the dpnGateUtpFramerUtilTable."
   INDEX {
      dpnGateIndex,
      dpnGateUtpIndex,
      dpnGateUtpFramerIndex }
::= { dpnGateUtpFramerUtilTable 1 }

DpnGateUtpFramerUtilEntry ::= SEQUENCE {
   dpnGateUtpFramerNormPrioLinkUtilToIf
      Gauge32,
   dpnGateUtpFramerHighPrioLinkUtilToIf
      Gauge32,
   dpnGateUtpFramerNormPrioLinkUtilFromIf
      Gauge32,
   dpnGateUtpFramerHighPrioLinkUtilFromIf
      Gauge32 }

dpnGateUtpFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities (TP) of 0, 6 and 9 and/or Emission Priority of 2 
      and 3. The utilization is the average for the last minute."
   DEFVAL     { 0 }
::= { dpnGateUtpFramerUtilEntry 1 }

dpnGateUtpFramerHighPrioLinkUtilToIf OBJECT-TYPE
   SYNTAX     Gauge32 (0..100)
   ACCESS     read-only
   STATUS     mandatory
   DESCRIPTION
     "This attribute is the utilization of the interrupting priority data traffic 
      sent to the link as a percentage of the available bandwidth on the 
      link. Note that this includes traffic with a Transfer Priority (TP) of 
      11 and/or Emission Priority of 1. The utilization is the average for 
      the last minute."
   DEFVAL     { 0 }
::= { dpnGateUtpFramerUtilEntry 2 }

dpnGateUtpFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { dpnGateUtpFramerUtilEntry 3 }

dpnGateUtpFramerHighPrioLinkUtilFromIf OBJECT-TYPE
   SYNTAX     Gauge32 (0..100)
   ACCESS     read-only
   STATUS     mandatory
   DESCRIPTION
     "This attribute is the utilization of the interrupting priority data 
      (interrupting traffic) received from the link as a percentage of the 
      available bandwidth on the link. Note that this includes traffic with 
      a Transfer Priority (TP) of 11 and/or Emission Priority of 1. The 
      utilization is the average for the last minute."
   DEFVAL     { 0 }
::= { dpnGateUtpFramerUtilEntry 4 }

dpnGateUtpFramerUtilThresholdTable OBJECT-TYPE
   SYNTAX     SEQUENCE OF DpnGateUtpFramerUtilThresholdEntry
   ACCESS     not-accessible
   STATUS     mandatory
   DESCRIPTION
     "This group contains all of the provisioning data required to set the 
      link utilization alarm thresholds. All thresholds are percentages 
      which can take on any value in the range of 0% through 100%. The 
      value 100% is used to disable an individual threshold. For values 
      other than 100%, a semantic check ensures that the minor alarm 
      threshold is less than the other thresholds and that the major alarm 
      threshold is less than the critical alarm threshold."
::= { dpnGateUtpFramer 15 }

dpnGateUtpFramerUtilThresholdEntry OBJECT-TYPE
   SYNTAX     DpnGateUtpFramerUtilThresholdEntry
   ACCESS     not-accessible
   STATUS     mandatory
   DESCRIPTION
     "An entry in the dpnGateUtpFramerUtilThresholdTable."
   INDEX {
      dpnGateIndex,
      dpnGateUtpIndex,
      dpnGateUtpFramerIndex }
::= { dpnGateUtpFramerUtilThresholdTable 1 }

DpnGateUtpFramerUtilThresholdEntry ::= SEQUENCE {
   dpnGateUtpFramerMinorLinkUtilAlarmThreshold
      Unsigned32,
   dpnGateUtpFramerMajorLinkUtilAlarmThreshold
      Unsigned32,
   dpnGateUtpFramerCriticalLinkUtilAlarmThreshold
      Unsigned32,
   dpnGateUtpFramerLinkUtilAlarmStatus
      INTEGER }

dpnGateUtpFramerMinorLinkUtilAlarmThreshold OBJECT-TYPE
   SYNTAX     Unsigned32 (0..100)
   ACCESS     read-write
   STATUS     mandatory
   DESCRIPTION
     "This attribute provides the threshold value which defines when a 
      minor alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the minor 
      alarm threshold is less than the other thresholds."
   DEFVAL     { 75 }
::= { dpnGateUtpFramerUtilThresholdEntry 1 }

dpnGateUtpFramerMajorLinkUtilAlarmThreshold OBJECT-TYPE
   SYNTAX     Unsigned32 (0..100)
   ACCESS     read-write
   STATUS     mandatory
   DESCRIPTION
     "This attribute provides the threshold value which defines when a 
      major alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the major 
      alarm threshold is greater than the minor threshold and less than the 
      critical threshold."
   DEFVAL     { 85 }
::= { dpnGateUtpFramerUtilThresholdEntry 2 }

dpnGateUtpFramerCriticalLinkUtilAlarmThreshold OBJECT-TYPE
   SYNTAX     Unsigned32 (0..100)
   ACCESS     read-write
   STATUS     mandatory
   DESCRIPTION
     "This attribute provides the threshold value which defines when a 
      critical alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the critical 
      alarm threshold is greater than the other thresholds."
   DEFVAL     { 95 }
::= { dpnGateUtpFramerUtilThresholdEntry 3 }

dpnGateUtpFramerLinkUtilAlarmStatus OBJECT-TYPE
   SYNTAX     INTEGER  {
                 disabled(0),
                 enabled(1) }
   ACCESS     read-write
   STATUS     mandatory
   DESCRIPTION
     "This attribute provides control of the generation of link utilization 
      alarms. If the value is disabled, none of the alarms are generated 
      (this is equivalent to setting all of the thresholds to 100%). If the 
      value is enabled, the individual thresholds are handled."
   DEFVAL     { disabled }
::= { dpnGateUtpFramerUtilThresholdEntry 4 }




-- 
-- Version and Compliance statements
-- 



-- Object-Group Statement:
-- A list of all current accessible leaf objects.

-- OBJECTS { dpnGateUtpDiscardBadFromIf,
--           dpnGateUtpFramerNonOctetErrors,
--           dpnGateUtpFramerLargeFrmErrors,
--           dpnGateUtpFramerUsageState,
--           dpnGateUtpFramerHighPrioLinkUtilToIf,
--           dpnGateUtpFramerNormPrioLinkUtilFromIf,
--           dpnGateUtpFramerOutOfSequenceFrm,
--           dpnGateUtpFramerRepeatedFrm,
--           dpnGateUtpAlarmStatus,
--           dpnGateUtpRoundTripDelay,
--           dpnGateUtpFramerCrcErrors,
--           dpnGateUtpFramerUnderruns,
--           dpnGateUtpUsageState,
--           dpnGateUtpFramerInterfaceName,
--           dpnGateUtpUnknownStatus,
--           dpnGateUtpStandbyStatus,
--           dpnGateUtpFramerComponentName,
--           dpnGateUtpFramerFramingType,
--           dpnGateUtpComponentName,
--           dpnGateUtpFramerFlagsBetweenFrames,
--           dpnGateUtpStorageType,
--           dpnGateUtpFramerOperationalState,
--           dpnGateUtpFramerLinkUtilAlarmStatus,
--           dpnGateUtpFramerFrmToIf,
--           dpnGateUtpFramerDataInversion,
--           dpnGateUtpFramerOctetFromIf,
--           dpnGateUtpOperationalState,
--           dpnGateUtpFramerFrmModeErrors,
--           dpnGateUtpFramerMinorLinkUtilAlarmThreshold,
--           dpnGateUtpFramerAborts,
--           dpnGateUtpReceiveErrorSensitivity,
--           dpnGateUtpFramerCriticalLinkUtilAlarmThreshold,
--           dpnGateUtpFramerFrameCrcType,
--           dpnGateUtpFrmRexmtToIf,
--           dpnGateUtpAreYouThereModeEntries,
--           dpnGateUtpMaximumErroredInterval,
--           dpnGateUtpFramerLrcErrors,
--           dpnGateUtpFramerAdminState,
--           dpnGateUtpControlStatus,
--           dpnGateUtpAdminState,
--           dpnGateUtpFramerRowStatus,
--           dpnGateUtpFramerNormPrioLinkUtilToIf,
--           dpnGateUtpWindowClosures,
--           dpnGateUtpFramerStorageType,
--           dpnGateUtpFramerHighPrioLinkUtilFromIf,
--           dpnGateUtpDiscardExcessToIf,
--           dpnGateUtpRowStatus,
--           dpnGateUtpFramerOverruns,
--           dpnGateUtpFramerMajorLinkUtilAlarmThreshold,
--           dpnGateUtpProceduralStatus,
--           dpnGateUtpFramerFrmFromIf,
--           dpnGateUtpAvailabilityStatus }
-- STATUS  mandatory
-- DESCRIPTION
--   "A list of all current accessible leaf objects."

utpDpnTrunksGroup OBJECT IDENTIFIER ::= { utpDpnTrunksMIB 1 }
utpDpnTrunksGroupBE OBJECT IDENTIFIER ::= { utpDpnTrunksGroup 5 }
utpDpnTrunksGroupBE00 OBJECT IDENTIFIER ::= { utpDpnTrunksGroupBE 1 }
utpDpnTrunksGroupBE00A OBJECT IDENTIFIER ::= { utpDpnTrunksGroupBE00 2 }



-- Agent-Capabilities Statement:

-- PRODUCT-RELEASE "Passport Release 7.0 UtpDpnTrunks."
-- STATUS          mandatory
-- DESCRIPTION     "UtpDpnTrunks MIB: MIB Version BE00A,
--                  Software Version BG00S4C."
-- SUPPORTS        Nortel-Magellan-Passport-UtpDpnTrunksMIB
--    INCLUDES     { utpDpnTrunksGroupBE00A }

utpDpnTrunksCapabilities OBJECT IDENTIFIER ::= { utpDpnTrunksMIB 3 }
utpDpnTrunksCapabilitiesBE OBJECT IDENTIFIER ::= { utpDpnTrunksCapabilities 5 }
utpDpnTrunksCapabilitiesBE00 OBJECT IDENTIFIER ::= { utpDpnTrunksCapabilitiesBE 1 }
utpDpnTrunksCapabilitiesBE00A OBJECT IDENTIFIER ::= { utpDpnTrunksCapabilitiesBE00 2 }





END
