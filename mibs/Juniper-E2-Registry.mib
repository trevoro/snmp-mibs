-- *****************************************************************************
-- Juniper-E2-Registry
--
-- Juniper Networks enterprise SNMP MIB.
--   Registry for the second generation E-series edge router product entities.
--
-- Copyright (c) 2003 Juniper Networks, Inc.
--   All Rights Reserved.
-- *****************************************************************************

Juniper-E2-Registry  DEFINITIONS ::= BEGIN

IMPORTS
    MODULE-IDENTITY, OBJECT-IDENTITY
        FROM SNMPv2-SMI
    juniAdmin
        FROM Juniper-Registry;

juniE2Registry  MODULE-IDENTITY
    LAST-UPDATED "200405191742Z"  -- 19-May-04 01:42 PM EDT
    ORGANIZATION "Juniper Networks, Inc."
    CONTACT-INFO
        "       Juniper Networks, Inc.
        Postal: 10 Technology Park Drive
                Westford, MA  01886-3146
                USA
        Tel:    +1 978 589 5800
        Email:  mib@Juniper.net"
    DESCRIPTION
        "Juniper second generation E-series product family system-specific
        object identification values.  This module defines AutonomousType (OID)
        values for all the physical entity types (entPhysicalVendorType).  This
        module will be updated whenever a new type of module or other hardware
        becomes available in second generation E-series systems."
    -- Revision History
    REVISION    "200405191742Z"  -- 19-May-04 01:42 PM EDT  - JUNOSe 6.0
    DESCRIPTION
        "Updated for revised E320 hardware."
    REVISION    "200308182027Z"  -- 18-Aug-03 04:27 PM EDT  - JUNOSe 6.0
    DESCRIPTION
        "Initial version of this SNMP management information module."
    ::= { juniAdmin 3 }


-- +++++++++++++++++++++++++++++++++++++++++++++++++++++++++++++++++++++++++++++
--  Second generation E-series physical entity identifiers.
--  The OID values under juniE2EntPhysicalType are used by the SNMP agent in
--  the second generation E-series product as the AutonomousType values for the
--  entPhysicalVendorType varbinds for the second generation E-series objects in
--  the entPhysicalTable.
-- +++++++++++++++++++++++++++++++++++++++++++++++++++++++++++++++++++++++++++++
juniE2EntPhysicalType OBJECT IDENTIFIER ::= { juniE2Registry 1 }


--
-- Chassis class
--
e2Chassis  OBJECT-IDENTITY
    STATUS      current
    DESCRIPTION
        "The vendor type ID for a second generation E-series chassis.  This
         identifies an 'overall' physical entity for any second generation
         E-series system."
    ::= { juniE2EntPhysicalType 1 }

e320Chassis  OBJECT-IDENTITY
    STATUS      current
    DESCRIPTION
        "The vendor type ID for an E320 chassis.  This is the 'overall' physical
         entity for an E320 system."
    ::= { e2Chassis 1 }


--
-- Fan class
--
e2FanAssembly  OBJECT-IDENTITY
    STATUS      current
    DESCRIPTION
        "The vendor type ID for a second generation E-series fan assembly."
    ::= { juniE2EntPhysicalType 2 }

e320PrimaryFanAssembly  OBJECT-IDENTITY
    STATUS      current
    DESCRIPTION
        "The vendor type ID for the primary fan assembly for an E320 chassis."
    ::= { e2FanAssembly 1 }

e320AuxiliaryFanAssembly  OBJECT-IDENTITY
    STATUS      current
    DESCRIPTION
        "The vendor type ID for the auxiliary fan assembly for an E320 chassis."
    ::= { e2FanAssembly 2 }


--
-- Power Supply class
--
e2PowerInput  OBJECT-IDENTITY
    STATUS      current
    DESCRIPTION
        "The vendor type ID for a second generation E-series power distribution
         module."
    ::= { juniE2EntPhysicalType 3 }

e320PowerDistributionModule  OBJECT-IDENTITY
    STATUS      current
    DESCRIPTION
        "The vendor type ID for the power distribution module for an E320
         chassis."
    ::= { e2PowerInput 1 }


--
-- Backplane class
--
e2Midplane  OBJECT-IDENTITY
    STATUS      current
    DESCRIPTION
        "The vendor type ID for a second generation E-series midplane."
    ::= { juniE2EntPhysicalType 4 }

e320Midplane  OBJECT-IDENTITY
    STATUS      current
    DESCRIPTION
        "The vendor type ID for the midplane for an E320 chassis."
    ::= { e2Midplane 1 }


--
-- Module class - integrated system controller/switch fabric
--
e2SrpModule  OBJECT-IDENTITY
    STATUS      current
    DESCRIPTION
        "The vendor type ID for a second generation E-series system controller/
         switch fabric module."
    ::= { juniE2EntPhysicalType 5 }

e320Srp100Module  OBJECT-IDENTITY
    STATUS      current
    DESCRIPTION
        "The vendor type ID for an integrated system contoller/switch fabric
         module for an E320 chassis."
    ::= { e2SrpModule 1 }

-- FIXME(iwolf) Remove for first customer release; internal h/w only
e320Srp320Module  OBJECT-IDENTITY
    STATUS      current
    DESCRIPTION
        "The vendor type ID for an integrated system contoller/switch fabric
         module for an E320 chassis.  For internal use only."
    ::= { e2SrpModule 99 }


--
-- Module class - switch fabric
--
e2SwitchFabricModule  OBJECT-IDENTITY
    STATUS      current
    DESCRIPTION
        "The vendor type ID for a second generation E-series switch fabric
         module."
    ::= { juniE2EntPhysicalType 6 }

e320FabricSlice100Module  OBJECT-IDENTITY
    STATUS      current
    DESCRIPTION
        "The vendor type ID for a switch fabric module for an E320 chassis.
         For internal use only."
    ::= { e2SwitchFabricModule 1 }

e320FabricSlice320Module  OBJECT-IDENTITY
    STATUS      current
    DESCRIPTION
        "The vendor type ID for a switch fabric module for an E320 chassis.
         For internal use only."
    ::= { e2SwitchFabricModule 99 }


--
-- Adapter class - system controller I/O Adapter
--
e2SrpIoa  OBJECT-IDENTITY
    STATUS      current
    DESCRIPTION
        "The vendor type ID for the system controller I/O adapter for a second
         generation E-series system."
    ::= { juniE2EntPhysicalType 7 }

e320SrpIoa  OBJECT-IDENTITY
    STATUS      current
    DESCRIPTION
        "The vendor type ID for an SRP IOA for an E320 chassis."
    ::= { e2SrpIoa 1 }


--
-- Module class - forwarding
--
e2ForwardingModule  OBJECT-IDENTITY
    STATUS      current
    DESCRIPTION
        "The vendor type ID for a second generation E-series forwarding module."
    ::= { juniE2EntPhysicalType 8 }

e3204gLeModule  OBJECT-IDENTITY
    STATUS      current
    DESCRIPTION
        "The vendor type ID for a 4 Gigabit Line Card for an E320 chassis."
    ::= { e2ForwardingModule 1 }

e320Ge4PortModule  OBJECT-IDENTITY
    STATUS      current
    DESCRIPTION
        "The vendor type ID for a Gigabit Ethernet 4 Port line card for an
         E320 chassis."
    ::= { e2ForwardingModule 2 }

e320Oc48Pos1PortModule  OBJECT-IDENTITY
    STATUS      current
    DESCRIPTION
        "The vendor type ID for an OC48 POS 1 Port line card for an
         E320 chassis."
    ::= { e2ForwardingModule 3 }

e320Oc48RPos1PortModule  OBJECT-IDENTITY
    STATUS      current
    DESCRIPTION
        "The vendor type ID for an OC48R POS 1 Port line card for an
         E320 chassis."
    ::= { e2ForwardingModule 4 }

-- FIXME(iwolf) Get complete name for boardIdLogicalA2GOcx
e320OcXModule  OBJECT-IDENTITY
    STATUS      current
    DESCRIPTION
        "The vendor type ID for an OCx line card for an E320 chassis."
    ::= { e2ForwardingModule 5 }

e320MfgSerdesTestModule  OBJECT-IDENTITY
    STATUS      current
    DESCRIPTION
        "The vendor type ID for a Manufacturing Serdes Test line card for an
         E320 chassis.  For internal use only."
    ::= { e2ForwardingModule 99 }


--
-- Adapter class - forwarding I/O adapter
--
e2ForwardingIoa  OBJECT-IDENTITY
    STATUS      current
    DESCRIPTION
        "The vendor type ID for a second generation E-series I/O adapter for a
        forwarding module."
    ::= { juniE2EntPhysicalType 9 }

e3204GeIoa  OBJECT-IDENTITY
    STATUS      current
    DESCRIPTION
        "The vendor type ID for a 4GE IOA for an E320 chassis."
    ::= { e2ForwardingIoa 1 }

e320Oc48PosIoa  OBJECT-IDENTITY
    STATUS      current
    DESCRIPTION
        "The vendor type ID for an OC48 POS IOA for an E320 chassis."
    ::= { e2ForwardingIoa 2 }

e320Oc48RPosIoa  OBJECT-IDENTITY
    STATUS      current
    DESCRIPTION
        "The vendor type ID for an OC48R POS IOA for an E320 chassis."
    ::= { e2ForwardingIoa 3 }

END
