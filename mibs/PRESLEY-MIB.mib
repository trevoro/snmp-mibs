-- --------------------------------------------------------------------
-- ************ THE STARTING POINT FOR ALL MIB DEFINITIONS ************
-- --------------------------------------------------------------------

PRESLEY-MIB DEFINITIONS ::= BEGIN

        IMPORTS
--               a3Com	    	    	    FROM A3Com-products-MIB
    	    	 enterprises	    	    FROM RFC1155-SMI
                 DisplayString, sysContact,sysName,sysLocation  FROM RFC1213-MIB
                 OBJECT-TYPE                 FROM RFC-1212
	         TRAP-TYPE		     FROM RFC-1215;

a3Com    OBJECT IDENTIFIER ::= { enterprises 43 }
generic  OBJECT IDENTIFIER ::= { a3Com 10 }
alertLed OBJECT IDENTIFIER ::= { generic 23 }

alertLedState OBJECT-TYPE
	SYNTAX  INTEGER  {
		active (1),
		inactive (2)
	}
	ACCESS  read-only
	STATUS  mandatory
	DESCRIPTION
		"This Read-only object shows the state of the Alert LED."
	DEFVAL  { inactive }
	::= { alertLed 1  }

alertLedTrap TRAP-TYPE
	ENTERPRISE  a3Com
	VARIABLES  {alertLedState, alertDescription, sysContact, sysName, sysLocation }
	DESCRIPTION
		"When the Alert LED is Activated or Inactivated this trap is
		generated. The variables provided with it are the current state
		of the Alert LED and the alertDescription of the last Activated
		Alert LED condition, the name of the managed hub, it's location
		and contact information."
	::= 73

alertTable OBJECT-TYPE
	SYNTAX  SEQUENCE OF AlertTableEntry
	ACCESS  not-accessible
	STATUS  mandatory
	DESCRIPTION
		"A table of descriptive, status and configuration information
		about the Alert LED Conditions."
	::= { alertLed 3 }

alertTableEntry OBJECT-TYPE
	SYNTAX	AlertTableEntry
	ACCESS  not-accessible
	STATUS  mandatory
	DESCRIPTION
		"An entry in the Alert LED table containing information about a
		single condition."
	INDEX  { alertIdentifier }
	::= { alertTable 1 }

AlertTableEntry ::=
SEQUENCE {
	alertIdentifier INTEGER,
	alertDescription DisplayString,
	alertStatus INTEGER,
	alertType INTEGER,
	alertConfiguration INTEGER
}


--	
--	Alert LED Conditions
--	================
--	
--	For each condition if the configuartion option has been set to Disabled,
--      an Active condition will not affect the Alert LED.
--	
--	There are three types of Alert Conditions, (1) State Alert Conditions, 
--      (2) Latched Alert Conditions, and (3) Threshold Alert Conditions.
--	
--	Any Condition configured as Disabled has no influence on the alert LED.
--	Each Condition is in iether an Active or Inactive state.
--	
--	State Alert Conditions can be configured to be either Enabled or
--      Disabled.  They are conditions that can occur when the system enters a
--      certain state.  The underlying problem has to be fixed in order to
--      Inactivate the condition.
--
--	The configuration options are to Enable or Disable activation of the
--      Alert LED when the condition arises. If a state condition has the
--      potential to effectively look like a latched condition it will have the
--      option of being Acknowledged.
--	
--	Latched Alert Conditions can be configured to be either Enabled or
--      Disabled, and when they are Active they can be Acknowledged.  They are
--      potential events that warrant raising a flag.  Latched alert conditions
--	have to be individually acknowledged to Inactivate the condition.
--	The options are to Enable or Disable activation of the Alert LED when
--      the condition arises.
--	
--	Threshold Alert Conditions are derived from Smart MIB Entries.
--	When the value exceeds a user selected threshold the Alert Condition
--      goes active.  When the utilisation has dropped below the threshold, if
--      there is noother reason for keeping the LED active, it is deactivated.
--	The configuration options are to Disable activation of the Alert LED
--      or to the activate the LED when the High, Medium or Low utilisation
--      condition arises.
--	
--	NetworkUtilization (1),
--	================
--	Network Utilization is a Threshold Alert condition with the threshold
--      settings -
--		Low	> 12%
--		Med	> 50%
--		High	> 80%
--	Network Utilisation will be checked once a second by reading the SNMP
--      object mrmMonRepBandwidth Used. The bandwidth used is a 'smart MIB'
--      object maintained as a part of the MRM MIB.
--	The default configuration will be High.
--	This feature is independent of the SNMP trap repRepTopUsage which
--      happens to utilise the same SNMP object and can be configured to trigger
--      at any chosen utilisation.
--	
--	NetworkErrorRate (2),
--	================
--	The Network Error Rate is a Threshold Alert condition with the threshold
--      settings -
--		Low	> 100 errors in 10,000 frames
--		Med	> 10 errors in 10,000 frames
--		High	> 1 error in 10,000 frames
--	Network error rate will be checked once a second by reading the SNMP
--      object mrmMonRepErrosPer10000Packets.
--	The errors per 10000 is a 'smart MIB' object maintained as a part of
--      the MRM MIB.
--	The default configuration will be Disabled.
--	This feature is independent of the SNMP trap repRepErrors which happens
--      to utilise the same SNMP object and can be configured to trigger at any
--      chosen utilisation.
--	
--	UTPPortPartitioned (3) & CoaxPortPartitioned (4),
--	====================================
--	Port Partitioning is a State Alert.
--	The partition state of each of the eight UTP ports and the Coax port
--      will be determined by polling the SNMP object mrmPortAutoPartitionState
--      once a second.  If any port has auto-partioned , the port is enabled and
--	the 'UTP / Coax Port Partitioned' configuration is Enabled the Alert LED
--      will be activated. When the port is no longer partitioned, if there is
--      no other reason for keeping the LED active, it is deactivated.
--	It should be noted that if the port partition configuration is enabled
--      and a port partitions, it will be shown on the Port Status LED and the
--      Alert LED.
--	Disabling a port will not de-activate any possible port partition state,
--      but will de-activate the LED.
--	The default configuration will be Enabled for UTP and Disabled for COAX.
--	This feature is independent of the SNMP trap repPartitionStateChange and
--      the SNMP object mrmPortPartitionEvent used to configure whether the trap
--      is generated.
--	
--	LoginSecurityViolation (5),
--	===================
--	Login Security Violation is a Latched Condition.
--	When ever the SNMP trap securityViolation is generated and the 'Forms
--      Login Security Violation' configuration is Enabled the Alert LED will be
--      activated.
--	The default configuration will be Disabled.
--	
--	SNMPSecurityViolation (6),
--	===================
--	SNMP Authentication Failure is a Latched condition.
--	When ever the SNMP trap authenticationFailure is generated and the
--      'SNMP Authentication Failure' configuration is Enabled the Alert LED
--      will be activated.
--      
--	It will not be possible to enable the SNMP Authentication Failure
--      configuration while the SNMP object snmpEnableAuthTraps is set to
--      disable the generation of the trap.
--      The default configuration will be Disabled.
--	
--	PortSecurityViolation (7),
--	==================
--	Port Security Violation is a Latched condition.
--	When ever the SNMP trap secureViolation is generated and the 'Port
--      Security Violation' configuration is Enabled the Alert LED will be
--      activated.
--	The default configuration will be Disabled.
--	
--	StationConnectivity (8),
--	=================
--	Station Conectivity is a State condition.
--	This is a State condition that can appear to be latched and so can be
--      Acknowledged when Active.
--	When ever the SNMP trap polledTableFailed Trap is generated and the
--      'Station Conectivity' configuration is Enabled the Alert LED will be
--      activated.
--	When ever the SNMP trap polledTableSuccess Trap is generated and there
--      is no other reason for the LED to be active it will be deactivated.
--	The default configuration will be Disabled.
--	
--	AlertLedTest (9),
--	=============
--	The alertLedTest is a state condition.  It is by default Active.
--	The Enable / Disable configuration options can be used to test turning
--      ON & OFF the LED.
--	The default configuration will be Disabled.
--	

alertIdentifier OBJECT-TYPE
	SYNTAX  INTEGER  {
		networkUtilization (1),
		networkErrorRate (2),
		utpPortPartitioned (3),
		coaxPortPartitioned (4),
		loginSecurityViolation (5),
		snmpSecurityViolation (6),
		portSecurityViolation (7),
		stationConnectivity (8),
		alertLedTest (9)
	}
	ACCESS  read-only
	STATUS  mandatory
	DESCRIPTION
		"This identifies a particular Alert LED Condition."
	::= { alertTableEntry 1 }

alertDescription OBJECT-TYPE
	SYNTAX  DisplayString (SIZE (1..32))
	ACCESS  read-only
	STATUS  mandatory
	DESCRIPTION
		"Description of Alert LED Condition."
	::= { alertTableEntry 2 }

alertStatus OBJECT-TYPE
	SYNTAX  INTEGER {
		active (1),
		inactive (2)
	}
	ACCESS  read-only
	STATUS  mandatory
	DESCRIPTION
		"Status of Alert LED Condition."
	::= { alertTableEntry 3 }

alertType OBJECT-TYPE
	SYNTAX  INTEGER {
		threshold (1),
		state (2),
		latched (3)
	}
	ACCESS  read-only
	STATUS  mandatory
	DESCRIPTION
		"Type of Alert LED Condition."
	::= { alertTableEntry 4 }

alertConfiguration OBJECT-TYPE
	SYNTAX  INTEGER {
		enabled (1),
		disabled (2),
		high (3),
		medium (4),
		low (5),
		acknowledge (6)
	}
	ACCESS  read-write
	STATUS  mandatory
	DESCRIPTION
		"Configuration of Alert LED Condition.
		For Threshold Conditions this can be High, Medium, Low or 
		Disabled.
		For State Conditions it is Enabled or Disabled.
		For Latched Conditions it is Enabled, Disabled, or if the
		Condition is Active the additional option of Acknowledge."
	::= { alertTableEntry 5 }

END
