TERAWAVE-teraMau-MIB DEFINITIONS ::= BEGIN
        -- Created by sml2mib compiler 
        IMPORTS

 enterprises,  OBJECT-TYPE,  Counter,  Gauge,  TimeTicks
        FROM RFC1155-SMI;

terawave OBJECT IDENTIFIER ::=  { enterprises 4513 }

     -- teraMauTable

teraMauTable OBJECT-TYPE
     SYNTAX SEQUENCE OF TeraMauTableEntryType
     ACCESS not-accessible
     STATUS mandatory
     DESCRIPTION
          " table teraMauTable"
     ::= { terawave 18 }

teraMauTableEntry OBJECT-TYPE
          SYNTAX TeraMauTableEntryType
          ACCESS not-accessible
          STATUS mandatory
          DESCRIPTION
               " table entry teraMauTableEntry "
          INDEX {                   ifMauIfIndex,                  ifMauIndex }
     ::= { teraMauTable 1 }

TeraMauTableEntryType ::= SEQUENCE {
          teraMauLinkState   
             INTEGER,
          teraMauDuplexMode   
             INTEGER,
          teraMauSpeed   
             INTEGER,
          teraMauPauseHighThreshold   
             INTEGER (0..100),
          teraMauPauseLowThreshold   
             INTEGER (0..100)
}

teraMauLinkState OBJECT-TYPE
          SYNTAX INTEGER
                  {
                  up(1),
                  down(2)
                  }
          ACCESS read-only
          STATUS mandatory
          DESCRIPTION
               ""
          ::= { teraMauTableEntry 1 }

teraMauDuplexMode OBJECT-TYPE
          SYNTAX INTEGER
                  {
                  fDX(1),
                  hDX(2)
                  }
          ACCESS read-only
          STATUS mandatory
          DESCRIPTION
               ""
          ::= { teraMauTableEntry 2 }

teraMauSpeed OBJECT-TYPE
          SYNTAX INTEGER
                  {
                  mbps100(1),
                  mbps10(2)
                  }
          ACCESS read-only
          STATUS mandatory
          DESCRIPTION
               ""
          ::= { teraMauTableEntry 3 }

teraMauPauseHighThreshold OBJECT-TYPE
          SYNTAX INTEGER (0..100)
          ACCESS read-write
          STATUS mandatory
          DESCRIPTION
               ""
          ::= { teraMauTableEntry 4 }

teraMauPauseLowThreshold OBJECT-TYPE
          SYNTAX INTEGER (0..100)
          ACCESS read-write
          STATUS mandatory
          DESCRIPTION
               ""
          ::= { teraMauTableEntry 5 }

END
