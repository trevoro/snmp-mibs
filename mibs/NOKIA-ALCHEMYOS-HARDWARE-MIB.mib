NOKIA-ALCHEMYOS-HARDWARE-MIB DEFINITIONS ::= BEGIN

IMPORTS  alchemyOSProducts, alchemyOSModules, hardware
             FROM NOKIA-ALCHEMYOS-MIB
         MODULE-IDENTITY, OBJECT-TYPE, Integer32, IpAddress
             FROM SNMPv2-SMI
         DisplayString
             FROM SNMPv2-TC;

nokiaAlchemyOSHardwareMIB MODULE-IDENTITY
    LAST-UPDATED "200101180000Z"
    ORGANIZATION "Nokia Internet Communications."
    CONTACT-INFO 
		 "	Nokia, Inc.
			Customer Support

		  Postal: 100 Enterprise Way, Module B
			Scotts Valley, CA 95066
			USA
                  E-Mail: snmp-contact@cips.nokia.com"

    DESCRIPTION "Hardware (and version) MIB module."
    REVISION "200101180000Z"
    DESCRIPTION "Cleanup."
    ::= { alchemyOSModules 4 }

hardwarePrimaryCPU OBJECT-TYPE
    SYNTAX      Integer32
    MAX-ACCESS	read-only
    STATUS	current
    DESCRIPTION "Primary CPU load (percent)."
    ::= { hardware 1 }

hardwareSecondaryCpu OBJECT-TYPE
    SYNTAX      Integer32
    MAX-ACCESS	read-only
    STATUS	current
    DESCRIPTION "Secondary CPU load (percent). Value -1 indicates that
                 second CPU is not present."
    ::= { hardware 2 }

hardwareHifnLoadAve OBJECT-TYPE
    SYNTAX      Integer32
    MAX-ACCESS	read-only
    STATUS	current
    DESCRIPTION "Cryptographic co-processor load (percent). Value -1 indicates
                that cryptographic co-processor is not present."
    ::= { hardware 3 }

hardwareMemoryUsage OBJECT-TYPE
    SYNTAX      Integer32
    MAX-ACCESS	read-only
    STATUS	current
    DESCRIPTION "Percent of memory currently in use."
    ::= { hardware 4 }

hardwarIOLoad OBJECT-TYPE
    SYNTAX      Integer32
    MAX-ACCESS	read-only
    STATUS	current
    DESCRIPTION "Packets per second sent and received."
    ::= { hardware 5 }

hardwareUpTime OBJECT-TYPE
    SYNTAX      Integer32
    MAX-ACCESS	read-only
    STATUS	current
    DESCRIPTION "Uptime in seconds."
    ::= { hardware 6 }

hardwareOSName OBJECT-TYPE
    SYNTAX      DisplayString
    MAX-ACCESS	read-only
    STATUS	current
    DESCRIPTION "Operating system name."
    ::= { hardware 7 }

hardwareOSVersion OBJECT-TYPE
    SYNTAX      DisplayString
    MAX-ACCESS	read-only
    STATUS	current
    DESCRIPTION "Operating system (kernel) version."
    ::= { hardware 8 }

hardwareCompileUser OBJECT-TYPE
    SYNTAX      DisplayString
    MAX-ACCESS	read-only
    STATUS	current
    DESCRIPTION "What user compiled this kernel."
    ::= { hardware 9 }

hardwareCompileDate OBJECT-TYPE
    SYNTAX      DisplayString
    MAX-ACCESS	read-only
    STATUS	current
    DESCRIPTION "Compile date and time."
    ::= { hardware 10 }

hardwareCompileHost OBJECT-TYPE
    SYNTAX      DisplayString
    MAX-ACCESS	read-only
    STATUS	current
    DESCRIPTION "Computer where this build was made."
    ::= { hardware 11 }

hardwareConfigVersion OBJECT-TYPE
    SYNTAX      Integer32
    MAX-ACCESS	read-only
    STATUS	current
    DESCRIPTION "Version of config file (number of config saves)."
    ::= { hardware 12 }

END
