REDLINE-BS-MIB DEFINITIONS ::= BEGIN

IMPORTS
	redlineSystem
		FROM REDLINE-MIB
	MODULE-IDENTITY,
	OBJECT-TYPE,
	NOTIFICATION-TYPE,
	Integer32,
	Unsigned32
		FROM SNMPv2-SMI
	OBJECT-GROUP,
	NOTIFICATION-GROUP,
	MODULE-COMPLIANCE
		FROM SNMPv2-CONF
	DateAndTime,
	DisplayString,
	RowStatus
		FROM SNMPv2-TC
	InetAddress,
	InetAddressType,
	InetPortNumber
		FROM INET-ADDRESS-MIB;

redlineBsMib MODULE-IDENTITY
	LAST-UPDATED "200510281543Z"
	ORGANIZATION "Redline Communications Inc."
	CONTACT-INFO
		"Henryk Kijak
		email: hkijak@redlinecommunications.com"
	DESCRIPTION
		"This MIB module contains object definitions
		applicable only to Redline Base Station."
	REVISION "200510281543Z"
	DESCRIPTION
		"Initial version."
	::= { redlineSystem 2 }


-- Scalars and Tables
--

-- Base Station dhcp variables

redlineBsDhcpObjects OBJECT IDENTIFIER 	::= { redlineBsMib 1 }


redlineBsIpAddressSource OBJECT-TYPE
	SYNTAX  INTEGER {
			dhcp(1),
			static(2) }
	MAX-ACCESS read-write
	STATUS current
	DESCRIPTION
		"Setting this variable to 1 causes the Base Station to 
                 obatain its ip address from DHCP server."
	::= { redlineBsDhcpObjects 1 }


redlineBsDhcpPacketsRelay OBJECT-TYPE
	SYNTAX  INTEGER {
			relay(1),
			notRelay(2) }
	MAX-ACCESS read-write
	STATUS current
	DESCRIPTION
		"Setting this variable to 1 causes the Base Station to
                 act as DHCP relay agent for SS.

                 Note: This object can not be set to 'relay' if usage of 
                 DHCP server is disabled. An attempt to set the
                 address will fail and return 'resourceUnavailable' error"
	::= { redlineBsDhcpObjects 2 }

-- Base Station clock synchronization variables

redlineBsSntpObjects OBJECT IDENTIFIER 	::= { redlineBsMib 2 }


redlineBsRefreshTime OBJECT-TYPE
	SYNTAX  INTEGER {
			noop(1),
			refresh(2) }
	MAX-ACCESS read-write
	STATUS current
	DESCRIPTION
		"Setting this variable to 1 causes the Base Station to 
                 reconect to time server and synchronize the time"
	::= { redlineBsSntpObjects 1 }


redlineBsDayLightSaving OBJECT-TYPE
	SYNTAX  INTEGER {
			on(1),
			off(2) }
	MAX-ACCESS read-write
	STATUS current
	DESCRIPTION
		"This variable indicates if Dalight saving is on."
	::= { redlineBsSntpObjects 2 }


redlineBsTimezone OBJECT-TYPE
	SYNTAX  INTEGER
	MAX-ACCESS read-write
	STATUS current
	DESCRIPTION
		"This variable is a time zone set as +/- hours from 
                 Greenwich Mean Time (GMT).

                 Note: This object can not be set if usage of DHCP 
                 server is enabled. An attempt to set the timezone will 
                 fail and return 'resourceUnavailable' error"
	::= { redlineBsSntpObjects 3 }


redlineBsTimeServerIpAddressType OBJECT-TYPE
	SYNTAX  InetAddressType {
			ipv4(1) }
	MAX-ACCESS read-write
	STATUS current
	DESCRIPTION
		"The INET address type of Ip address of time server.
		IPv4 type supported only."
	::= { redlineBsSntpObjects 4 }


redlineBsTimeServerIpAddress OBJECT-TYPE
	SYNTAX  InetAddress
	MAX-ACCESS read-write
	STATUS current
	DESCRIPTION
		"The INET address of time server to whom Bs will
                 communicate using SNTP protocol to obtain the GMT time."
	::= { redlineBsSntpObjects 5 }


redlineBsTimezoneMin OBJECT-TYPE
	SYNTAX  INTEGER
	MAX-ACCESS read-write
	STATUS current
	DESCRIPTION
		"This variable contains a minutes part of time zone defined
                 in 'redlineBsTimezone'.

                 Note: This object can not be set if usage of DHCP 
                 server is enabled. An attempt to set the timezone will 
                 fail and return 'resourceUnavailable' error"
	::= { redlineBsSntpObjects 6 }


-- Base Station objects used to request configuration saving in non-volatile 
-- memory

redlineBsConfigSaveObjects OBJECT IDENTIFIER 	::= { redlineBsMib 3 }


redlineBsSnmpConfigSave OBJECT-TYPE
	SYNTAX  INTEGER {
			noop(1),
			save(2) }
	MAX-ACCESS read-write
	STATUS current
	DESCRIPTION
		"Setting this variable to 1 causes SNMP Configuration to be save 
		in flash."
	::= { redlineBsConfigSaveObjects 1 }


redlineBsSfConfigSave OBJECT-TYPE
	SYNTAX  INTEGER {
			noop(1),
			save(2) }
	MAX-ACCESS read-write
	STATUS current
	DESCRIPTION
		"Setting this variable to 2 causes Service Flow Configuration to 
		be saved in flash."
	::= { redlineBsConfigSaveObjects 2 }

-- Base Station system general objects 

redlineBsSystemObjects OBJECT IDENTIFIER 	::= { redlineBsMib 4 }

redlineBsRadioType OBJECT-TYPE
        SYNTAX      OCTET STRING (SIZE(0..16))
        MAX-ACCESS  read-only
        STATUS      current
        DESCRIPTION
            "This object indicates the radio type of Redline Bs."
        ::= { redlineBsSystemObjects 1 }

-- Base Station RF objects 

redlineBsRfObjects OBJECT IDENTIFIER 	::= { redlineBsMib 5 }

redlineBsDownlinkChanFreq OBJECT-TYPE
        SYNTAX      Unsigned32
        UNITS       "kHz"
        MAX-ACCESS  read-only
        STATUS      current
        DESCRIPTION
            "Current downlink channel frequency (kHz)"
        ::= { redlineBsRfObjects 1 }

redlineBsUplinkChanFreq OBJECT-TYPE
        SYNTAX      Unsigned32
        UNITS       "kHz"
        MAX-ACCESS  read-only
        STATUS      current
        DESCRIPTION
            "Current uplink channel frequency (kHz)"
        ::= { redlineBsRfObjects 2 }

-- Base Station PHY objects 

redlineBsPhyObjects OBJECT IDENTIFIER 	::= { redlineBsMib 6 }

redlineBsChannelSize OBJECT-TYPE
	SYNTAX  Unsigned32
        UNITS       "KHz"
	MAX-ACCESS read-only
	STATUS current
	DESCRIPTION
		"Current channel size (Khz)."
	::= { redlineBsPhyObjects 1 }

-- Base Station Ethernet Interface objects 

redlineBsEthObjects OBJECT IDENTIFIER 	::= { redlineBsMib 7 }

redlineBsManagementAccess OBJECT-TYPE
	SYNTAX  INTEGER {
			dataPort(1),
			mgtPort(2) }
	MAX-ACCESS read-only
	STATUS current
	DESCRIPTION
		"Indicates current management access configuration( either 
		data or mgt port."
	::= { redlineBsEthObjects 1 }

redlineBsDataPortSettings OBJECT-TYPE
	SYNTAX  INTEGER {
			autoDetect(1),
			fullDuplex100(2),
			fullDuplex10(3), 
			halfDuplex100(4), 
			halfDuplex10(5) }
	MAX-ACCESS read-only
	STATUS current
	DESCRIPTION
		"Indicates current settings of data port."
	::= { redlineBsEthObjects 2 }

redlineBsMgtPortSettings OBJECT-TYPE
	SYNTAX  INTEGER {
			autoDetect(1),
			fullDuplex100(2), 
			fullDuplex10(3), 
			halfDuplex100(4), 
			halfDuplex10(5) }
	MAX-ACCESS read-only
	STATUS current
	DESCRIPTION
		"Indicates current settings of mgt port."
	::= { redlineBsEthObjects 3 }


redlineBsVlanObjects OBJECT IDENTIFIER 	::= { redlineBsMib 8 }

redlineBsVlanTrafficTagging OBJECT-TYPE
	SYNTAX  INTEGER {
			enabled(1),
			disabled(2) }
	MAX-ACCESS read-only
	STATUS current
	DESCRIPTION
		"Indicates that management with VLAN tagged traffic
		is enabled."
	::= { redlineBsVlanObjects 1 }

redlineBsVlanId OBJECT-TYPE
        SYNTAX      Unsigned32
	MAX-ACCESS read-only
	STATUS current
	DESCRIPTION
		"VLAN identifier used to tag managment traffic."
	::= { redlineBsVlanObjects 2 }

redlineBsSmcObjects OBJECT IDENTIFIER 	::= { redlineBsMib 9 }

redlineBsSmcCurrentOperMode OBJECT-TYPE
	SYNTAX  INTEGER {
			normal(1),
			maintenance(2) }
	MAX-ACCESS read-write
	STATUS current
	DESCRIPTION
		"Indicates BS SMC (Secondary Management Channel) operation 
		window. At the beginning of a maintenance window (upgrade, 
		config backup etc), the SMC will be assigned maximum bandwidth 
		to the predetermined fixed rate. At the end of the maintenance 
		window, the maximum bandwidth for the SMC will be reset to its 
		normal rate."
	::= { redlineBsSmcObjects 1 }

-- Power supply and cooling hardware objects

redlineBsPowerSupplyAndCoolingObjects OBJECT IDENTIFIER ::= { redlineBsMib 10 }

redlineBsPowerSupplyTable OBJECT-TYPE
	SYNTAX  SEQUENCE OF RedlineBsPowerSupplyEntry
	MAX-ACCESS not-accessible
	STATUS current
	DESCRIPTION
		"This table contains identification and status information about 
                 base station power supplies. A trap will be generated each time 
                 the power supply goes on or off. The traps generation can be 
                 enabled/disabled using Redline Trap Activation Table."
	::= { redlineBsPowerSupplyAndCoolingObjects 1 }


redlineBsPowerSupplyEntry OBJECT-TYPE
	SYNTAX  RedlineBsPowerSupplyEntry
	MAX-ACCESS not-accessible
	STATUS current
	DESCRIPTION
		"This entry contains status information about base station power 
		supply."
	INDEX { redlineBsPowerSupplyIndex }
	::= { redlineBsPowerSupplyTable 1 }


RedlineBsPowerSupplyEntry ::= SEQUENCE {

	redlineBsPowerSupplyIndex         Integer32,
	redlineBsPowerSupplyName          DisplayString,
	redlineBsPowerSupplyType          INTEGER,
	redlineBsPowerSupplyStatus        INTEGER }


redlineBsPowerSupplyIndex OBJECT-TYPE
	SYNTAX  Integer32
	MAX-ACCESS not-accessible
	STATUS current
	DESCRIPTION 
		"The index of the BS power supply table."
	::= { redlineBsPowerSupplyEntry 1 }

redlineBsPowerSupplyName OBJECT-TYPE
	SYNTAX  DisplayString (SIZE (0..32))
	MAX-ACCESS read-only
	STATUS current
	DESCRIPTION
		"Textual identification of base station power supply."
        ::= { redlineBsPowerSupplyEntry 2 }

redlineBsPowerSupplyType OBJECT-TYPE
	SYNTAX  INTEGER {
                        internal(1),
                        external(2),
                        externalShared(3) }
	MAX-ACCESS read-only
	STATUS current
	DESCRIPTION
		"The power supply type."
        ::= { redlineBsPowerSupplyEntry 3 }

redlineBsPowerSupplyStatus OBJECT-TYPE
        SYNTAX  INTEGER {
                        on(1),
                        off(2) }
        MAX-ACCESS read-only
        STATUS current
        DESCRIPTION
                "Indicates if the power supply is on/off."
        ::= { redlineBsPowerSupplyEntry 4 }

-- Base station temperature table
redlineBsTemperatureTable OBJECT-TYPE
	SYNTAX  SEQUENCE OF RedlineBsTemperatureEntry
	MAX-ACCESS not-accessible
	STATUS current
	DESCRIPTION
		"This table contains information about current temperature of
                 base station hardware units."
	::= { redlineBsPowerSupplyAndCoolingObjects 2 }


redlineBsTemperatureEntry OBJECT-TYPE
	SYNTAX  RedlineBsTemperatureEntry
	MAX-ACCESS not-accessible
	STATUS current
	DESCRIPTION
		"This entry contains temperature information about single base 
                 station hardware unit."
	INDEX { redlineBsUnitIndex }
	::= { redlineBsTemperatureTable 1 }


RedlineBsTemperatureEntry ::= SEQUENCE {

	redlineBsUnitIndex           Integer32,
	redlineBsUnitName            DisplayString,
	redlineBsUnitType            INTEGER,
	redlineBsCurrTemperature     Integer32 }

redlineBsUnitIndex OBJECT-TYPE
	SYNTAX  Integer32
	MAX-ACCESS not-accessible
	STATUS current
	DESCRIPTION
		"The index of the BS current temperature table."
	::= { redlineBsTemperatureEntry 1 }

redlineBsUnitName OBJECT-TYPE
	SYNTAX  DisplayString (SIZE (0..32))
	MAX-ACCESS read-only
	STATUS current
	DESCRIPTION
		"The base station hardware unit name."
        ::= { redlineBsTemperatureEntry 2 }

redlineBsUnitType OBJECT-TYPE
	SYNTAX  INTEGER {
                        indoor(1),
                        outdoor(2) }
	MAX-ACCESS read-only
	STATUS current
	DESCRIPTION
		"The base station hardware unit type."
        ::= { redlineBsTemperatureEntry 3 }

redlineBsCurrTemperature OBJECT-TYPE
        SYNTAX Integer32 (-60..100)
	UNITS "degrees Celsius"
        MAX-ACCESS read-only
        STATUS current
        DESCRIPTION
                "Indicates the current temperature of base station hardware 
                 unit in Celsius."
        ::= { redlineBsTemperatureEntry 4 }


-- Base station temperature threshold table
redlineBsTempThresholdTable OBJECT-TYPE
	SYNTAX  SEQUENCE OF RedlineBsTempThresholdEntry
	MAX-ACCESS not-accessible
	STATUS current
	DESCRIPTION
		"This table contains various temperature threshold which are
                 used to trigger traps to alarm network manager about unit
		 mulfunction.  The table is indexed by 'redlineBsUnitIndex' and
                 'redlineBsTempThresholdIndex' objects. Some of the traps 
                 require clearing after the temperature is going back to normal.
                 The traps can be enabled/disabled using Redline Trap Activation
                 table."
	::= { redlineBsPowerSupplyAndCoolingObjects 3 }


redlineBsTempThresholdEntry OBJECT-TYPE
	SYNTAX  RedlineBsTempThresholdEntry
	MAX-ACCESS not-accessible
	STATUS current
	DESCRIPTION
		"This entry contains single base station hardware unit 
                 temperarure threshold information."
	INDEX { redlineBsUnitIndex, redlineBsTempThresholdIndex }
	::= { redlineBsTempThresholdTable 1 }


RedlineBsTempThresholdEntry ::= SEQUENCE {

	redlineBsTempThresholdIndex         Integer32,
	redlineBsTempTrapThreshold          Integer32,
	redlineBsTempTrapClrThreshold       Integer32,
	redlineBsTempThresholdName          DisplayString,
	redlineBsTemperatureTrapTrigger     INTEGER
}

redlineBsTempThresholdIndex OBJECT-TYPE
	SYNTAX  Integer32
	MAX-ACCESS not-accessible
	STATUS current
	DESCRIPTION
		"The index of the temperature threshold table."
	::= { redlineBsTempThresholdEntry 1 }


redlineBsTempTrapThreshold OBJECT-TYPE
        SYNTAX Integer32 (-60..100)
	UNITS "degrees Celsius"
        MAX-ACCESS read-only
        STATUS current
        DESCRIPTION
                "Indicates the temperature threshold value which will be used
                 to trigger a trap."
        ::= { redlineBsTempThresholdEntry 2 }

redlineBsTempTrapClrThreshold OBJECT-TYPE
        SYNTAX Integer32 (-60..100)
	UNITS "degrees Celsius"
        MAX-ACCESS read-only
        STATUS current
        DESCRIPTION
                "Indicates the temperature threshold value which will be used
                 to clear a previosly generated trap."
        ::= { redlineBsTempThresholdEntry 3 }

redlineBsTempThresholdName OBJECT-TYPE
	SYNTAX  DisplayString (SIZE (0..32))
	MAX-ACCESS read-only
	STATUS current
	DESCRIPTION
		"Textual identification of temperature threshold."
        ::= { redlineBsTempThresholdEntry 4 }

redlineBsTemperatureTrapTrigger OBJECT-TYPE
	SYNTAX  INTEGER {
                        temperatureRising(1),
                        temperatureFalling(2) }
	MAX-ACCESS read-only
	STATUS current
	DESCRIPTION
		"Indicates if temperature traversal in upper or lower 
                 value direction is causing the trap."
        ::= { redlineBsTempThresholdEntry 5 }


-- Base station fans table

redlineBsFanTable OBJECT-TYPE
	SYNTAX  SEQUENCE OF RedlineBsFanEntry
	MAX-ACCESS not-accessible
	STATUS current
	DESCRIPTION
		"This table contains name and status information about 
                 base station cooling fans. Up to 3 entries are supported."
	::= { redlineBsPowerSupplyAndCoolingObjects 4 }


redlineBsFanEntry OBJECT-TYPE
	SYNTAX  RedlineBsFanEntry
	MAX-ACCESS not-accessible
	STATUS current
	DESCRIPTION
		"This entry contains information about single cooling fan."
	INDEX { redlineBsFanIndex }
	::= { redlineBsFanTable 1 }


RedlineBsFanEntry ::= SEQUENCE {

	redlineBsFanIndex         Integer32,
	redlineBsFanName          DisplayString,
	redlineBsFanStatus        INTEGER }


redlineBsFanIndex OBJECT-TYPE
	SYNTAX  Integer32
	MAX-ACCESS not-accessible
	STATUS current
	DESCRIPTION
		"The index of the colling fans table."
	::= { redlineBsFanEntry 1 }

redlineBsFanName OBJECT-TYPE
	SYNTAX  DisplayString (SIZE (0..32))
	MAX-ACCESS read-only
	STATUS current
	DESCRIPTION
		"Textual identification of  base station fan."
        ::= { redlineBsFanEntry 2 }

redlineBsFanStatus OBJECT-TYPE
        SYNTAX  INTEGER {
                        on(1),
                        off(2) }
        MAX-ACCESS read-only
        STATUS current
        DESCRIPTION
                "Indicates the base station fan is on/off."
        ::= { redlineBsFanEntry 3 }

redlineBsNotificationObjects OBJECT IDENTIFIER 	::= { redlineBsMib 11 }

-- MIB variables used as varbinds in traps
redlineBsTrapMibObjects OBJECT IDENTIFIER ::= { redlineBsNotificationObjects 1 }

redlineBsTrapType OBJECT-TYPE
        SYNTAX  INTEGER {
                        trapSet(1),
                        trapClr(2) }
        MAX-ACCESS accessible-for-notify
        STATUS current
        DESCRIPTION
                "Indicates if the trap is for alarm condition or for its clearing."
        ::= { redlineBsTrapMibObjects 1 }

redlineBsTrapPowerSupplyIndex OBJECT-TYPE
	SYNTAX  Integer32
	MAX-ACCESS accessible-for-notify
	STATUS current
	DESCRIPTION 
		"The index in the table representing BS power supply triggering the 
                 trap."
	::= { redlineBsTrapMibObjects 2 }

redlineBsTrapUnitIndex OBJECT-TYPE
	SYNTAX  Integer32
	MAX-ACCESS accessible-for-notify
	STATUS current
	DESCRIPTION
		"The index of temperature table representing BS unit triggering the
                 trap."
	::= { redlineBsTrapMibObjects 3 }

redlineBsTrapTempThresholdIndex OBJECT-TYPE
	SYNTAX  Integer32
	MAX-ACCESS accessible-for-notify
	STATUS current
	DESCRIPTION
		"The index of the temperature threshold table representing the 
                 temperature threshold which passing is triggering the trap."
	::= { redlineBsTrapMibObjects 4 }

-- Trap definitions are registered under this node.

redlineBsTrapDefinitions OBJECT IDENTIFIER 	::= { redlineBsNotificationObjects 0 }

redlineBsPowerSupplyStatusTrap NOTIFICATION-TYPE
	OBJECTS {
		redlineBsTrapPowerSupplyIndex,
		redlineBsPowerSupplyStatus }
	STATUS current
	DESCRIPTION 
		"Event that reports base station power supply status change (on/off)."
	::= { redlineBsTrapDefinitions 1 }

redlineBsTempThresholdTrap NOTIFICATION-TYPE
	OBJECTS {
		redlineBsTrapUnitIndex,
		redlineBsTrapTempThresholdIndex,
		redlineBsCurrTemperature,
		redlineBsTemperatureTrapTrigger,
		redlineBsTrapType }
	STATUS current
	DESCRIPTION 
		"Event that reports SW Upgrade progress and status changes."
	::= { redlineBsTrapDefinitions 2 }

--
-- Conformance
--

redlineBsConformance OBJECT IDENTIFIER 	::= { redlineBsMib 12 }

--
-- Groups
--

redlineBsGroups OBJECT IDENTIFIER 	::= { redlineBsConformance 1 }

--
-- Compliance
--

redlineBsCompls OBJECT IDENTIFIER 	::= { redlineBsConformance 2 }

redlineBsDhcpGroup OBJECT-GROUP
	OBJECTS {
		redlineBsIpAddressSource,
		redlineBsDhcpPacketsRelay }
	STATUS current
	DESCRIPTION
		"Dhcp objects."
	::= { redlineBsGroups 1 }


redlineBsSntpGroup OBJECT-GROUP
	OBJECTS {
		redlineBsRefreshTime,
		redlineBsDayLightSaving,
                redlineBsTimezone,
                redlineBsTimeServerIpAddressType,
                redlineBsTimeServerIpAddress,
		redlineBsTimezoneMin }
	STATUS current
	DESCRIPTION
		"Sntp objects."
	::= { redlineBsGroups 2 }


redlineBsConfigSaveGroup OBJECT-GROUP
	OBJECTS {
		redlineBsSnmpConfigSave,
		redlineBsSfConfigSave }
	STATUS current
	DESCRIPTION
		"Config save objects."
	::= { redlineBsGroups 3 }

redlineBsSystemGroup OBJECT-GROUP
	OBJECTS {
		redlineBsRadioType }
	STATUS current
	DESCRIPTION
		"Config save objects."
	::= { redlineBsGroups 4 }

redlineBsRfGroup OBJECT-GROUP
	OBJECTS {
		redlineBsDownlinkChanFreq,
		redlineBsUplinkChanFreq }
	STATUS current
	DESCRIPTION
		"Config save objects."
	::= { redlineBsGroups 5 }

redlineBsPhyGroup OBJECT-GROUP
	OBJECTS {
		redlineBsChannelSize }
	STATUS current
	DESCRIPTION
		"Config save objects."
	::= { redlineBsGroups 6 }

redlineBsEthGroup OBJECT-GROUP
	OBJECTS {
		redlineBsManagementAccess,
		redlineBsDataPortSettings }
	STATUS current
	DESCRIPTION
		"Ethernet interface objects."
	::= { redlineBsGroups 7 }

redlineBsVlanGroup OBJECT-GROUP
	OBJECTS {
		redlineBsVlanTrafficTagging,
		redlineBsVlanId }
	STATUS current
	DESCRIPTION
		"Vlan objects."
	::= { redlineBsGroups 8 }

redlineBsSmcGroup OBJECT-GROUP
	OBJECTS {
		redlineBsSmcCurrentOperMode }
	STATUS current
	DESCRIPTION
		"Smc objects."
	::= { redlineBsGroups 9 }

redlineBsPowerSupplyAndCoolingGroup OBJECT-GROUP
	OBJECTS {
		redlineBsPowerSupplyName,
  		redlineBsPowerSupplyType,
		redlineBsPowerSupplyStatus,
		redlineBsUnitName,
		redlineBsUnitType,
		redlineBsCurrTemperature,
		redlineBsTempTrapThreshold,
		redlineBsTempTrapClrThreshold,
		redlineBsTempThresholdName,
		redlineBsTemperatureTrapTrigger,
		redlineBsFanName,
		redlineBsFanStatus,
		redlineBsTrapType }
	STATUS current
	DESCRIPTION
		"Power supply, temperature and fans objects."
	::= { redlineBsGroups 10 }

redlineBsNotificationGroup NOTIFICATION-GROUP
	NOTIFICATIONS {
		redlineBsPowerSupplyStatusTrap,
		redlineBsTempThresholdTrap }
	STATUS current
	DESCRIPTION ""
	::= { redlineBsGroups 11 }

redlineBsCompliance MODULE-COMPLIANCE
	STATUS current
	DESCRIPTION
		"The compliance statement for SNMP entities that
		implement this MIB module."
	MODULE 
	MANDATORY-GROUPS {
			redlineBsDhcpGroup,
			redlineBsSntpGroup,
                        redlineBsConfigSaveGroup,
			redlineBsSystemGroup,
			redlineBsRfGroup,
			redlineBsPhyGroup,
			redlineBsEthGroup,
			redlineBsVlanGroup,
			redlineBsSmcGroup,
			redlineBsPowerSupplyAndCoolingGroup,
			redlineBsNotificationGroup }
	::= { redlineBsCompls 1 }

END
