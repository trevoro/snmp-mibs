ENVIROMUX DEFINITIONS ::= BEGIN
IMPORTS
   MODULE-IDENTITY, OBJECT-TYPE, 
   NOTIFICATION-TYPE, enterprises               FROM  SNMPv2-SMI
   DisplayString                                FROM  SNMPv2-TC;
      
enviromux-sems-16 MODULE-IDENTITY
     LAST-UPDATED "200503301400Z"
     ORGANIZATION "Network Technologies Inc."
     CONTACT-INFO 
         "Adrian Bica - Engineering
         
         Postal: 1275 Danner Dr,
                 Aurora, OH 442022
                 US
                 
             Tel: 330-562-7070
             Fax: 330-562-1999
             
             WEB: www.nti1.com"
     DESCRIPTION  "ENVIROMUX-SEMS-16 MIB module - Master Unit with no slaves connected"
     REVISION     "200609201400Z" 
     DESCRIPTION  "Rev. 1.0 - initial version"
     ::= { hardware 2 }

-- the root of the subtree for Network Technologies Inc
nti				        OBJECT IDENTIFIER ::= { enterprises 3699 }

-- subtree for products
products		        OBJECT IDENTIFIER ::= { nti 1 }
experimental		    OBJECT IDENTIFIER ::= { nti 2 }
hardware		        OBJECT IDENTIFIER ::= { products 1 }
software		        OBJECT IDENTIFIER ::= { products 2 }
otherProduct            OBJECT IDENTIFIER ::= { hardware 200 }

-- enviromux subtree
masterUnit	            OBJECT IDENTIFIER ::= { enviromux-sems-16 1 }
envTraps                OBJECT IDENTIFIER ::= { enviromux-sems-16 100 }
hostSystem              OBJECT IDENTIFIER ::= { masterUnit 1 }
users                   OBJECT IDENTIFIER ::= { masterUnit 2 }
groups					OBJECT IDENTIFIER ::= { masterUnit 3 }
intSensors				OBJECT IDENTIFIER ::= { masterUnit 4 }
extSensors				OBJECT IDENTIFIER ::= { masterUnit 5 }
digInputs 				OBJECT IDENTIFIER ::= { masterUnit 6 }
rlyOutputs				OBJECT IDENTIFIER ::= { masterUnit 7 }
ipDevices 				OBJECT IDENTIFIER ::= { masterUnit 8 }
ipLinks  				OBJECT IDENTIFIER ::= { masterUnit 9 }

-- hostSystem subtree

sysTime					OBJECT-TYPE
	SYNTAX				DisplayString
	MAX-ACCESS			read-only
	STATUS				current
	DESCRIPTION		    "System time"
	::= { hostSystem 1 }

sysEnterpriseName		OBJECT-TYPE
	SYNTAX				DisplayString
	MAX-ACCESS  		read-only
	STATUS				current
	DESCRIPTION		    "EnterpriseName"
	::= { hostSystem 2 }

sysEnterpriseLocation	OBJECT-TYPE
	SYNTAX				DisplayString
	MAX-ACCESS  		read-only
	STATUS				current
	DESCRIPTION		    "Enterprise Location"
	::= { hostSystem 3 }

sysEnterpriseContact	OBJECT-TYPE
	SYNTAX				DisplayString
	MAX-ACCESS  		read-only
	STATUS				current
	DESCRIPTION		    "Enterprise Contact"
	::= { hostSystem 4 }

sysEnterprisePhone  	OBJECT-TYPE
	SYNTAX				DisplayString
	MAX-ACCESS  		read-only
	STATUS				current
	DESCRIPTION		    "Enterprise Phone"
	::= { hostSystem 5 }

-- internal sensors description

intSensorTable			OBJECT-TYPE
	SYNTAX	            SEQUENCE OF	IntSensorEntry
	MAX-ACCESS          not-accessible
	STATUS	            current
	DESCRIPTION         "Table of internal Sensor entries"
	::= { intSensors 1 }

intSensorEntry     		OBJECT-TYPE
    SYNTAX              IntSensorEntry
	MAX-ACCESS          not-accessible
	STATUS	            current
	DESCRIPTION         "An internal sensor entry"
	INDEX               { intSensorIndex }
	::= { intSensorTable 1 }

IntSensorEntry ::= 
	SEQUENCE {
		intSensorIndex
			INTEGER,
		intSensorType
			INTEGER,
		intSensorDescription
			DisplayString,
		intSensorGroupNb
			INTEGER,
		intSensorGroup
			DisplayString,
        intSensorValue
            INTEGER,
		intSensorUnit
			INTEGER,
		intSensorUnitName
			DisplayString,
		intSensorStatus
			INTEGER,
		intSensorMinThreshold
			INTEGER,
		intSensorMaxThreshold						
			INTEGER
	}

intSensorIndex			OBJECT-TYPE
	SYNTAX				INTEGER (1..3)
	MAX-ACCESS			read-only
	STATUS				current
	DESCRIPTION	        "The index of the internal sensor entry 1..12"
	::= { intSensorEntry 1 }

intSensorType		    OBJECT-TYPE
	SYNTAX				INTEGER { undefined(0), temperature(1), humidity(2), power(3) }
	MAX-ACCESS  		read-only
	STATUS				current
	DESCRIPTION	        "Sensor Type"
	::= { intSensorEntry 2 }

intSensorDescription    OBJECT-TYPE
	SYNTAX				DisplayString
	MAX-ACCESS  		read-write
	STATUS				current
	DESCRIPTION	        "Internal Sensor Description"
	::= { intSensorEntry 3 }
    
intSensorGroupNb        OBJECT-TYPE
	SYNTAX				INTEGER (0..15)
	MAX-ACCESS  		read-write
	STATUS				current
	DESCRIPTION	        "Internal Sensor Group Number"
	::= { intSensorEntry 4 }
    
intSensorGroup          OBJECT-TYPE
	SYNTAX				DisplayString
	MAX-ACCESS  		read-only
	STATUS				current
	DESCRIPTION	        "Internal Sensor Group Name"
	::= { intSensorEntry 5 }
    
intSensorValue			OBJECT-TYPE
	SYNTAX				INTEGER (0..1000)
	MAX-ACCESS			read-only
	STATUS				current
	DESCRIPTION	        "The value of the internal sensor reading. For temperature it is presented in tenths of degrees"
	::= { intSensorEntry 6 }
	
intSensorUnit			OBJECT-TYPE
	SYNTAX				INTEGER (0..1)
	MAX-ACCESS			read-write
	STATUS				current
	DESCRIPTION	        "The measuremnet unit for this sensor. It is important only for temperature"
	::= { intSensorEntry 7 }
	
intSensorUnitName   	OBJECT-TYPE
	SYNTAX				DisplayString
	MAX-ACCESS			read-only
	STATUS				current
	DESCRIPTION	        "The measuremnet unit for this sensor in readable format"
	::= { intSensorEntry 8 }
	
intSensorStatus			OBJECT-TYPE
	SYNTAX				INTEGER {notconnected(0), normal(1), prealert(2), alert(3), acknoledged(4), dismissed(5), disconnected(6) }
	MAX-ACCESS			read-only
	STATUS				current
	DESCRIPTION	        "The status of the sensor"
	::= { intSensorEntry 9 }
	
intSensorMinThreshold	OBJECT-TYPE
	SYNTAX				INTEGER (0..1000)
	MAX-ACCESS			read-write
	STATUS				current
	DESCRIPTION	        "The value of the internal sensor lower threshold"
	::= { intSensorEntry 10 }
	
intSensorMaxThreshold	OBJECT-TYPE
	SYNTAX				INTEGER (0..1000)
	MAX-ACCESS			read-write
	STATUS				current
	DESCRIPTION	        "The value of the internal sensor upper threshold"
	::= { intSensorEntry 11 }
	

-- external sensors description

extSensorTable			OBJECT-TYPE
	SYNTAX	            SEQUENCE OF	ExtSensorEntry
	MAX-ACCESS          not-accessible
	STATUS	            current
	DESCRIPTION         "Table of external Sensors entries"
	::= { extSensors 1 }

extSensorEntry     		OBJECT-TYPE
    SYNTAX              ExtSensorEntry
	MAX-ACCESS          not-accessible
	STATUS	            current
	DESCRIPTION         "An external sensor entry"
	INDEX               { extSensorIndex }
	::= { extSensorTable 1 }

ExtSensorEntry ::= 
	SEQUENCE {
		extSensorIndex
			INTEGER,
		extSensorType
			INTEGER,
		extSensorDescription
			DisplayString,
		extSensorConnector
			INTEGER,
		extSensorGroupNb
			INTEGER,
		extSensorGroup
			DisplayString,
        extSensorValue
            INTEGER,
		extSensorUnit
			INTEGER,
		extSensorUnitName
			DisplayString,
		extSensorStatus
			INTEGER,
		extSensorMinThreshold
			INTEGER,
		extSensorMaxThreshold
			INTEGER
	}

extSensorIndex			OBJECT-TYPE
	SYNTAX				INTEGER (1..32)
	MAX-ACCESS			read-only
	STATUS				current
	DESCRIPTION	        "The index of the external sensor entry 1..32"
	::= { extSensorEntry 1 }

extSensorType		    OBJECT-TYPE
	SYNTAX				INTEGER { undefined(0), temperature(1), humidity(2), power(3), water(4), smoke(5), vibration(6), glass(7), door(8), temp-hum(513) }
	MAX-ACCESS  		read-only
	STATUS				current
	DESCRIPTION	        "Sensor Type"
	::= { extSensorEntry 2 }

extSensorDescription    OBJECT-TYPE
	SYNTAX				DisplayString
	MAX-ACCESS  		read-write
	STATUS				current
	DESCRIPTION	        "Sensor Description"
	::= { extSensorEntry 3 }
    
extSensorConnector      OBJECT-TYPE
	SYNTAX				INTEGER (1..16)
	MAX-ACCESS  		read-only
	STATUS				current
	DESCRIPTION	        "Connector where the sensor is attached"
	::= { extSensorEntry 4 }
    
extSensorGroupNb        OBJECT-TYPE
	SYNTAX				INTEGER (1..16)
	MAX-ACCESS  		read-write
	STATUS				current
	DESCRIPTION	        "Sensor's Group"
	::= { extSensorEntry 5 }
    
extSensorGroup          OBJECT-TYPE
	SYNTAX				DisplayString
	MAX-ACCESS  		read-only
	STATUS				current
	DESCRIPTION	        "Sensor's Group Name"
	::= { extSensorEntry 6 }
    
extSensorValue			OBJECT-TYPE
	SYNTAX				INTEGER { closed(0), open(1) }
	MAX-ACCESS			read-only
	STATUS				current
	DESCRIPTION	        "The value of the external sensor reading. For temperature it is presented in tenths of degrees"
	::= { extSensorEntry 7 }
	
extSensorUnit			OBJECT-TYPE
	SYNTAX				INTEGER (0..1)
	MAX-ACCESS			read-write
	STATUS				current
	DESCRIPTION	        "The measuremnet unit for this sensor. It is important only for temperature"
	::= { extSensorEntry 8 }
	
extSensorUnitName   	OBJECT-TYPE
	SYNTAX				DisplayString
	MAX-ACCESS			read-only
	STATUS				current
	DESCRIPTION	        "The measuremnet unit for this sensor in readable format"
	::= { extSensorEntry 9 }
	
extSensorStatus			OBJECT-TYPE
	SYNTAX				INTEGER {notconnected(0), normal(1), prealert(2), alert(3), acknoledged(4), dismissed(5), disconnected(6) }
	MAX-ACCESS			read-only
	STATUS				current
	DESCRIPTION	        "The status of the sensor"
	::= { extSensorEntry 10 }
	
extSensorMinThreshold	OBJECT-TYPE
	SYNTAX				INTEGER (0..1000)
	MAX-ACCESS			read-write
	STATUS				current
	DESCRIPTION	        "The value of the sensor lower threshold"
	::= { extSensorEntry 11 }
	
extSensorMaxThreshold	OBJECT-TYPE
	SYNTAX				INTEGER (0..1000)
	MAX-ACCESS			read-write
	STATUS				current
	DESCRIPTION	        "The value of the sensor upper threshold"
	::= { extSensorEntry 12 }
	
-- Digital inputs description

digInputTable           OBJECT-TYPE
    SYNTAX              SEQUENCE OF DigInputEntry
	MAX-ACCESS          not-accessible
	STATUS	            current
	DESCRIPTION         "Table of Digital Inputs entries"
	::= { digInputs 1 }

digInputEntry     		OBJECT-TYPE
    SYNTAX              DigInputEntry
	MAX-ACCESS          not-accessible
	STATUS	            current
	DESCRIPTION         "A Digital Input entry"
	INDEX               { digInputIndex }
	::= { digInputTable 1 }

DigInputEntry ::= 
	SEQUENCE {
		digInputIndex
			INTEGER,
		digInputDescription
			DisplayString,
		digInputGroupNb
			INTEGER,
		digInputGroup
			DisplayString,
        digInputValue
            INTEGER,
        digInputNormalValue
            INTEGER,
		digInputStatus
			INTEGER
	}

digInputIndex			OBJECT-TYPE
	SYNTAX				INTEGER (1..8)
	MAX-ACCESS			read-only
	STATUS				current
	DESCRIPTION	        "The index of the digital input entry 1..8"
	::= { digInputEntry 1 }

digInputDescription     OBJECT-TYPE
	SYNTAX				DisplayString
	MAX-ACCESS  		read-write
	STATUS				current
	DESCRIPTION	        "Digital Input Description"
	::= { digInputEntry 2 }
    
digInputGroupNb         OBJECT-TYPE
	SYNTAX				INTEGER (1..16)
	MAX-ACCESS  		read-write
	STATUS				current
	DESCRIPTION	        "Digital Input's Group Number"
	::= { digInputEntry 3 }
    
digInputGroup           OBJECT-TYPE
	SYNTAX				DisplayString
	MAX-ACCESS  		read-only
	STATUS				current
	DESCRIPTION	        "Digital Input's Group Name"
	::= { digInputEntry 4 }
    
digInputValue			OBJECT-TYPE
	SYNTAX				INTEGER { closed(0), open(1) }
	MAX-ACCESS			read-only
	STATUS				current
	DESCRIPTION	        "The value of the Digital Input reading"
	::= { digInputEntry 5 }
	
digInputNormalValue	    OBJECT-TYPE
	SYNTAX				INTEGER { closed(0), open(1) }
	MAX-ACCESS			read-only
	STATUS				current
	DESCRIPTION	        "The value of the Digital Input reading in normal status"
	::= { digInputEntry 6 }
	
digInputStatus			OBJECT-TYPE
	SYNTAX				INTEGER {notconnected(0), normal(1), prealert(2), alert(3), acknoledged(4), dismissed(5), disconnected(6) }
	MAX-ACCESS			read-only
	STATUS				current
	DESCRIPTION	        "The status of the Digital Input"
	::= { digInputEntry 7 }
	
-- Relay outputs description

rlyOutputTable          OBJECT-TYPE
    SYNTAX              SEQUENCE OF RlyOutputEntry
	MAX-ACCESS          not-accessible
	STATUS	            current
	DESCRIPTION         "Table of Relay Outputs entries"
	::= { rlyOutputs 1 }

rlyOutputEntry    		OBJECT-TYPE
    SYNTAX              RlyOutputEntry
	MAX-ACCESS          not-accessible
	STATUS	            current
	DESCRIPTION         "A Relay Output entry"
	INDEX               { rlyOutputIndex }
	::= { rlyOutputTable 1 }

RlyOutputEntry ::= 
	SEQUENCE {
		rlyOutputIndex
			INTEGER,
		rlyOutputDescription
			DisplayString,
		rlyOutputGroupNb
			INTEGER,
		rlyOutputGroup
			DisplayString,
        rlyOutputValue
			INTEGER,
        rlyOutputNormalValue
            INTEGER
	}


rlyOutputIndex			OBJECT-TYPE
	SYNTAX				INTEGER (1..4)
	MAX-ACCESS			read-only
	STATUS				current
	DESCRIPTION	        "The index of the control output entry 1..4"
	::= { rlyOutputEntry 1 }

rlyOutputDescription    OBJECT-TYPE
	SYNTAX				DisplayString
	MAX-ACCESS  		read-write
	STATUS				current
	DESCRIPTION	        "Relay Output Description"
	::= { rlyOutputEntry 2 }
    
rlyOutputGroupNb        OBJECT-TYPE
	SYNTAX				INTEGER (1..16)
	MAX-ACCESS  		read-write
	STATUS				current
	DESCRIPTION	        "Relay Output's Group Number"
	::= { rlyOutputEntry 3 }
    
rlyOutputGroup          OBJECT-TYPE
	SYNTAX				DisplayString
	MAX-ACCESS  		read-only
	STATUS				current
	DESCRIPTION	        "Relay Output's Group Name"
	::= { rlyOutputEntry 4 }
    
rlyOutputValue			OBJECT-TYPE
	SYNTAX				INTEGER { closed(0), open(1) }
	MAX-ACCESS			read-only
	STATUS				current
	DESCRIPTION	        "The value of the Relay Output reading"
	::= { rlyOutputEntry 5 }
	
rlyOutputNormalValue	OBJECT-TYPE
	SYNTAX				INTEGER { closed(0), open(1) }
	MAX-ACCESS			read-only
	STATUS				current
	DESCRIPTION	        "The value of the Relay Output reading in normal status"
	::= { rlyOutputEntry 6 }
	
-- IP Devices description

ipDeviceTable           OBJECT-TYPE
    SYNTAX              SEQUENCE OF IpDeviceEntry
	MAX-ACCESS          not-accessible
	STATUS	            current
	DESCRIPTION         "Table of IP Devices entries"
	::= { ipDevices 1 }

ipDeviceEntry    		OBJECT-TYPE
    SYNTAX              IpDeviceEntry
	MAX-ACCESS          not-accessible
	STATUS	            current
	DESCRIPTION         "An IP Device entry"
	INDEX               { ipDeviceIndex }
	::= { ipDeviceTable 1 }

IpDeviceEntry ::= 
	SEQUENCE {
		ipDeviceIndex
			INTEGER,
		ipDeviceAddress
			DisplayString,
		ipDeviceDescription
			DisplayString,
		ipDeviceGroupNb
			INTEGER,
		ipDeviceGroup
			DisplayString,
		ipDeviceTimeout
			INTEGER,
		ipDeviceRetries
			INTEGER,
		ipDeviceValue
			INTEGER,
		ipDeviceStatus
			INTEGER
	}

ipDeviceIndex			OBJECT-TYPE
	SYNTAX				INTEGER (1..64)
	MAX-ACCESS			read-only
	STATUS				current
	DESCRIPTION	        "The index of the IP Device entry 1..64"
	::= { ipDeviceEntry 1 }

ipDeviceAddress   OBJECT-TYPE
	SYNTAX				DisplayString
	MAX-ACCESS  		read-write
	STATUS				current
	DESCRIPTION	        "IP Device URL"
	::= { ipDeviceEntry 2 }
    
ipDeviceDescription     OBJECT-TYPE
	SYNTAX				DisplayString
	MAX-ACCESS  		read-write
	STATUS				current
	DESCRIPTION	        "IP Device Description"
	::= { ipDeviceEntry 3 }
    
ipDeviceGroupNb         OBJECT-TYPE
	SYNTAX				INTEGER (1..16)
	MAX-ACCESS  		read-write
	STATUS				current
	DESCRIPTION	        "Index of the group the IP Device belongs to"
	::= { ipDeviceEntry 4 }
    
ipDeviceGroup           OBJECT-TYPE
	SYNTAX				DisplayString
	MAX-ACCESS  		read-only
	STATUS				current
	DESCRIPTION	        "Name of the group the IP Device belongs to"
	::= { ipDeviceEntry 5 }
    
ipDeviceTimeout         OBJECT-TYPE
	SYNTAX				INTEGER (1..16)
	MAX-ACCESS  		read-write
	STATUS				current
	DESCRIPTION	        "IP Device ping timeout (in seconds)"
	::= { ipDeviceEntry 6 }
    
ipDeviceRetries         OBJECT-TYPE
	SYNTAX				INTEGER (1..16)
	MAX-ACCESS  		read-only
	STATUS				current
	DESCRIPTION	        "Number of ping retries to the IP device, until responding"
	::= { ipDeviceEntry 7 }
    
ipDeviceValue           OBJECT-TYPE
	SYNTAX				INTEGER (1..16)
	MAX-ACCESS  		read-write
	STATUS				current
	DESCRIPTION	        "Responding status"
	::= { ipDeviceEntry 8 }
    
ipDeviceStatus         OBJECT-TYPE
	SYNTAX				INTEGER (1..16)
	MAX-ACCESS  		read-only
	STATUS				current
	DESCRIPTION	        "Alarm status of the IP Device"
	::= { ipDeviceEntry 9 }
    
-- IP Links description

ipLinkTable             OBJECT-TYPE
    SYNTAX              SEQUENCE OF IpLinkEntry
	MAX-ACCESS          not-accessible
	STATUS	            current
	DESCRIPTION         "Table of Links entries"
	::= { ipLinks 1 }

ipLinkEntry    		    OBJECT-TYPE
    SYNTAX              IpLinkEntry
	MAX-ACCESS          not-accessible
	STATUS	            current
	DESCRIPTION         "A Link entry"
	INDEX               { ipLinkIndex }
	::= { ipLinkTable 1 }

IpLinkEntry ::= 
	SEQUENCE {
		ipLinkIndex
			INTEGER,
		ipLinkAddress
			DisplayString,
		ipLinkDescription
			DisplayString
	}

ipLinkIndex			    OBJECT-TYPE
	SYNTAX				INTEGER (1..64)
	MAX-ACCESS			read-only
	STATUS				current
	DESCRIPTION	        "The index of the IP Link entry 1..64"
	::= { ipLinkEntry 1 }

ipLinkAddress           OBJECT-TYPE
	SYNTAX				DisplayString
	MAX-ACCESS  		read-write
	STATUS				current
	DESCRIPTION	        "IP Link URL"
	::= { ipLinkEntry 2 }
    
ipLinkDescription       OBJECT-TYPE
	SYNTAX				DisplayString
	MAX-ACCESS  		read-write
	STATUS				current
	DESCRIPTION	        "IP Link Description"
	::= { ipLinkEntry 3 }
    


    
END
