--
-- Root of olivetti private MIB, LMS resource MIBs must be added to this file
--

OLIVETTI-MIB --{ iso org(3) dod(6) internet(1) private(4) enterprises(1) 279 }

DEFINITIONS ::= BEGIN

IMPORTS
		DisplayString FROM SNMPv2-TC
        private, enterprises, OBJECT-TYPE
            FROM RFC1155-SMI
		TRAP-TYPE FROM RFC-1215;

olivetti	OBJECT IDENTIFIER ::= { enterprises 279 }
experiments	OBJECT IDENTIFIER ::= { olivetti 1 }
smuxpeersid	OBJECT IDENTIFIER ::= { experiments 2 } 

-- object types

olisysObjectID OBJECT-TYPE
	SYNTAX	DisplayString
	ACCESS	read-only
	STATUS	mandatory
	::= { experiments 1 }

--
-- lms tree starting here
--

lms          OBJECT IDENTIFIER ::= { olivetti 2 }
lms-trap     OBJECT IDENTIFIER ::= { olivetti 3 }

lsx-unix OBJECT IDENTIFIER ::= { lms 6 }

lms-SysName OBJECT-TYPE
	  SYNTAX DisplayString(SIZE(0..17))
	  ACCESS not-accessible
	  STATUS mandatory
	  ::={lms-trap 1}

lms-SubAddress OBJECT-TYPE
	  SYNTAX DisplayString(SIZE(0..17))
	  ACCESS not-accessible
	  STATUS mandatory
	  ::={lms-trap 2}

lms-LogType OBJECT-TYPE
	  SYNTAX DisplayString(SIZE(0..6))
	  ACCESS not-accessible
	  STATUS mandatory
	  ::={lms-trap 3}

lms-FilterType OBJECT-TYPE
	  SYNTAX DisplayString(SIZE(0..10))
	  ACCESS not-accessible
	  STATUS mandatory
	  ::={lms-trap 4}

lms-RecLevel OBJECT-TYPE
	  SYNTAX DisplayString(SIZE(0..4))
	  ACCESS not-accessible
	  STATUS mandatory
	  ::={lms-trap 5}

lms-RecCode OBJECT-TYPE
	  SYNTAX DisplayString(SIZE(0..5))
	  ACCESS not-accessible
	  STATUS mandatory
	  ::={lms-trap 6}

lms-ProductId OBJECT-TYPE
	  SYNTAX DisplayString(SIZE(0..9))
	  ACCESS not-accessible
	  STATUS mandatory
	  ::={lms-trap 7}

lms-Class OBJECT-TYPE
	  SYNTAX DisplayString(SIZE(0..7))
	  ACCESS not-accessible
	  STATUS mandatory
	  ::={lms-trap 8}

lms-SubClass OBJECT-TYPE
	  SYNTAX DisplayString(SIZE(0..9))
	  ACCESS not-accessible
	  STATUS mandatory
	  ::={lms-trap 9}

lms-ResourceName OBJECT-TYPE
	  SYNTAX DisplayString(SIZE(0..15))
	  ACCESS not-accessible
	  STATUS mandatory
	  ::={lms-trap 10}

lms-GenerationDate OBJECT-TYPE
	  SYNTAX DisplayString(SIZE(0..18))
	  ACCESS not-accessible
	  STATUS mandatory
	  ::={lms-trap 11}

lms-LogString OBJECT-TYPE
	  SYNTAX DisplayString(SIZE(0..5000))
	  ACCESS not-accessible
	  STATUS mandatory
	  ::={lms-trap 12}


uxlms-systemrm    OBJECT IDENTIFIER ::= { lsx-unix 7}

uxlms-system      OBJECT IDENTIFIER ::= { uxlms-systemrm 1 }

uxlms-systemrmTable    OBJECT-TYPE
       SYNTAX SEQUENCE OF Uxlms-systemrmEntry
	   ACCESS not-accessible
	   STATUS mandatory
	   ::= { uxlms-system 1 }

uxlms-systemrmEntry    OBJECT-TYPE
       SYNTAX Uxlms-systemrmEntry  
	   ACCESS not-accessible
	   STATUS mandatory
	   ::= { uxlms-systemrmTable 1 }

Uxlms-systemrmEntry ::= SEQUENCE {
                       uxlms-systemrmInstName DisplayString,
                       uxlms-systemrmSubAddr DisplayString
					   }
					   
uxlms-systemrmInstName OBJECT-TYPE
       SYNTAX DisplayString (SIZE(0..14))
	   ACCESS read-only
	   STATUS mandatory
	   ::= { uxlms-systemrmEntry 1 }

uxlms-systemrmSubAddr OBJECT-TYPE
       SYNTAX DisplayString (SIZE(0..14))
	   ACCESS read-only
	   STATUS mandatory
	   ::= { uxlms-systemrmEntry 2 }

-- Trap Definitions

lmstrap   TRAP-TYPE
     ENTERPRISE	olivetti
     VARIABLES	{lms-SysName, lms-SubAddress, lms-LogType, lms-FilterType,
	 lms-RecLevel, lms-RecCode, lms-ProductId, lms-Class, lms-SubClass,
	 lms-ResourceName, lms-GenerationDate, lms-LogString}
	 ::= 138

--
-- lms tree ending here
--
END
