-- File Name : AVENTAIL-FIPS-MIBS
AVENTAIL-FIPS-MIBS	DEFINITIONS ::= BEGIN
	IMPORTS
		aventail
			FROM AVENTAIL-MIB
		InternationalDisplayString 
			FROM HOST-RESOURCES-MIB
		OBJECT-TYPE, Integer32,NOTIFICATION-TYPE, MODULE-IDENTITY
			FROM SNMPv2-SMI;


aventailFIPS MODULE-IDENTITY
             LAST-UPDATED       "200409071432Z" 
             ORGANIZATION       "Aventail"
             CONTACT-INFO       "email:support@aventail.com"
             DESCRIPTION      "This Aventail MIB provides FIPS Statistics"
        	::= {aventail 6}

fipsCardState       OBJECT-TYPE	
		SYNTAX			 InternationalDisplayString
		MAX-ACCESS	 read-only 	
		STATUS		        current	
		DESCRIPTION	"This oid conveys the state of the FIPS Card. \
		                             A string 'NO-FIPS-HWACCEL-SUPPORT' is displayed \
		                             in case of no hardware support. \
		                             If the hardware server is running, either of the two \
		                             strings will be displayed based on the appliance \
		                             configuration: FIPS - SERVER - UP: LEVEL 2 or \
		                             FIPS - SERVER - UP: LEVEL 3. \
		                             If the hardware server is not running, \
		                             FIPS-SERVER-NOT-RUNNING string will be displayed \
		                             and if licensing itself is generating error, \
		                             then NOT-APPLICABLE string will be displayed."
		::=  {  aventailFIPS  1  }

smartCardState OBJECT-TYPE
		SYNTAX			InternationalDisplayString
		MAX-ACCESS	read-only
		STATUS			current
		DESCRIPTION	"This oid conveys the state of the Smart Card. \
		                              A string 'NO-FIPS-HWACCEL-SUPPORT' is displayed \
		                              in case of no hardware support. If the hardware \
		                              server is not running, FIPS-SERVER-NOT-RUNNING \
		                              string will be displayed and if licensing itself is \
		                              generating error, then NOT-APPLICABLE string \
		                              will be displayed.
		                              if Operator smart card is inserted in the slot then, \
		                              OPERATOR-CARD-IN-SLOT' message is displayed. \
		                              If Admin smart card is inserted in the slot then, \
		                              ADMIN-CARD-IN-SLOT' message is displayed.
		                              If the smart card is faulty then, \
                                            FAULTY-CARD-IN-SLOT' message is displayed. \
                                            if the smart card is unformatted then, \
                                            'UNFORMATTED-CARD-IN-SLOT' message is displayed. \
                                            If smart card slot is empty then, \
                                            'NO-CARD-IN-SLOT' message is displayed."
		::=  {  aventailFIPS  2  }

hsUptime OBJECT-TYPE
		SYNTAX		InternationalDisplayString
		MAX-ACCESS	read-only
		STATUS		current
		DESCRIPTION	"  A textual string describing FIPS card up time in seconds\
						    This field will display string as NO-FIPS-HWACCEL-SUPPORT \
		                                if hardware support is not provided. \ 
                                              If the hardware server is not running, \
		                                FIPS-SERVER-NOT-RUNNING \
		                                string will be displayed and if licensing itself is \
		                                generating error, then NOT-APPLICABLE string \
		                                will be displayed."
		::=  { aventailFIPS 3 }
		
fipsCardStateChange	NOTIFICATION-TYPE
		STATUS			    current
		DESCRIPTION	    "Notification of state of change for FIPS hardware \
		                                 card. This trap will provide information about the \
		                                 current FIPS card state."
		::=  {  aventailFIPS  100  }
END
